RUBYTECH-ES2410C-MIB DEFINITIONS ::= BEGIN

IMPORTS
    DisplayString FROM SNMPv2-TC
    MODULE-COMPLIANCE,OBJECT-GROUP, NOTIFICATION-GROUP       FROM SNMPv2-CONF
    enterprises,MODULE-IDENTITY,OBJECT-TYPE,NOTIFICATION-TYPE,Counter32,IpAddress        FROM SNMPv2-SMI
    MacAddress         FROM SNMPv2-TC
    ifIndex    FROM RFC1213-MIB;

-- @ENTERPRISE-SECTION-START
rubytech MODULE-IDENTITY
    LAST-UPDATED "200709190000Z"
        ORGANIZATION "Ruby Tech Corp."
        CONTACT-INFO
            "2F, No.7, Lane 50, Nan Kang Road, Sec.3, Taipei, Taiwan
                 Email: rubytech@mail.rubytech.com.tw
                 TEL: 886-2-2785-3961
                 FAX: 886-2-2786-3012"
        DESCRIPTION
                "The MIB module is for Ruby Tech."
        ::= { enterprises 5205 }

switch               OBJECT IDENTIFIER ::= { rubytech 2 }

es2410cProductID         OBJECT IDENTIFIER ::= { switch 35 }
-- @ENTERPRISE-SECTION-END

es2410cProduces            OBJECT IDENTIFIER ::= { es2410cProductID 1 }

es2410cSystem            OBJECT IDENTIFIER ::= { es2410cProduces 1 }

es2410cCommonSys             OBJECT IDENTIFIER ::= { es2410cSystem 1 }

es2410cReboot OBJECT-TYPE
    SYNTAX      INTEGER(0|1|2)
    MAX-ACCESS      read-write
    STATUS      current
    DESCRIPTION
        "Reboot the system. Get this OID always return zero.
            0 - do nothing
            1 - Reboot without saving start
            2 - Reboot with saving start"
    ::= { es2410cCommonSys 1 }

es2410cBiosVsersion  OBJECT-TYPE
    SYNTAX      DisplayString
    MAX-ACCESS      read-only
    STATUS      current
    DESCRIPTION
        "Get the BIOS version of the system."
    ::= { es2410cCommonSys 2 }

es2410cFirmwareVersion   OBJECT-TYPE
    SYNTAX      DisplayString
    MAX-ACCESS      read-only
    STATUS      current
    DESCRIPTION
        "Get the firmware version of the system."
    ::= { es2410cCommonSys 3 }

es2410cHardwareVersion   OBJECT-TYPE
    SYNTAX      DisplayString
    MAX-ACCESS      read-only
    STATUS      current
    DESCRIPTION
        "Get the hardware version of the system."
    ::= { es2410cCommonSys 4 }

es2410cMechanicalVersion OBJECT-TYPE
    SYNTAX      DisplayString
    MAX-ACCESS      read-only
    STATUS      current
    DESCRIPTION
        "Get the mechanical version of the system."
    ::= { es2410cCommonSys 5 }

es2410cSerialNumber  OBJECT-TYPE
    SYNTAX      DisplayString
    MAX-ACCESS      read-only
    STATUS      current
    DESCRIPTION
        "Get the Serial number of the system."
    ::= { es2410cCommonSys 6 }

es2410cHostMacAddress    OBJECT-TYPE
    SYNTAX      DisplayString
    MAX-ACCESS      read-only
    STATUS      current
    DESCRIPTION
        "Get the MAC address of the system."
    ::= { es2410cCommonSys 7 }

es2410cDevicePort    OBJECT-TYPE
    SYNTAX      DisplayString
    MAX-ACCESS      read-only
    STATUS      current
    DESCRIPTION
        "Get the quantity of ports that this system owns now."
    ::= { es2410cCommonSys 8 }

es2410cRamSize  OBJECT-TYPE
    SYNTAX      DisplayString
    MAX-ACCESS      read-only
    STATUS      current
    DESCRIPTION
        "Get the RAM size of the system."
    ::= { es2410cCommonSys 9 }

es2410cFlashSize  OBJECT-TYPE
    SYNTAX      DisplayString
    MAX-ACCESS      read-only
    STATUS      current
    DESCRIPTION
        "Get the flash size of the system."
    ::= { es2410cCommonSys 10 }

es2410cCPULoad  OBJECT-TYPE
    SYNTAX      DisplayString
    MAX-ACCESS      read-only
    STATUS      current
    DESCRIPTION
        "Get the CPU load of the system."
    ::= { es2410cCommonSys 11 }

es2410cIP            OBJECT IDENTIFIER ::= { es2410cSystem 2 }

es2410cDhcpSetting OBJECT-TYPE
    SYNTAX          INTEGER(0|1)
    MAX-ACCESS          read-write
    STATUS          current
    DESCRIPTION
        "Get/Set DHCP status of the system.
            0 - DHCP disable
            1 - DHCP enable
            When DHCP Relay is already running. Please disable DHCP Relay first, and then enable DHCP again."
    ::= { es2410cIP 1 }

es2410cIPAddress OBJECT-TYPE
    SYNTAX      IpAddress
    MAX-ACCESS      read-write
    STATUS      current
    DESCRIPTION
        "Get/Set the IP address of the system.
         You can't set this OID if DHCP status is enabled."
    ::= { es2410cIP 2 }

es2410cNetMask OBJECT-TYPE
    SYNTAX      IpAddress
    MAX-ACCESS      read-write
    STATUS      current
    DESCRIPTION
        "Get/Set the subnet mask of the system.
         You can't set this OID if DHCP status is enabled."
    ::= { es2410cIP 3 }

es2410cDefaultGateway OBJECT-TYPE
    SYNTAX      IpAddress
    MAX-ACCESS      read-write
    STATUS      current
    DESCRIPTION
        "Get/Set the default gateway of the system.
         You can't set this OID if DHCP status is enabled."
    ::= { es2410cIP 4 }

es2410cDnsSetting OBJECT-TYPE
    SYNTAX      INTEGER(0|1)
    MAX-ACCESS      read-write
    STATUS      current
    DESCRIPTION
        "Get/Set the source of DNS server.
            0 - manual, the DNS server is from manual setting
            1 - Auto, the DNS server is assigned by DHCP server."
    ::= { es2410cIP 5 }

es2410cDnsServer OBJECT-TYPE
    SYNTAX      IpAddress
    MAX-ACCESS      read-write
    STATUS      current
    DESCRIPTION
        "Get/Set the DNS server of the system."
    ::= { es2410cIP 6 }

es2410cTime              OBJECT IDENTIFIER ::= { es2410cSystem 3 }

es2410cSystemCurrentTime OBJECT-TYPE
    SYNTAX      DisplayString
    MAX-ACCESS      read-only
    STATUS      current
    DESCRIPTION
        "Get the current time of the system."
    ::= { es2410cTime 1 }

es2410cManualTimeSetting OBJECT-TYPE
    SYNTAX      DisplayString
    MAX-ACCESS      read-write
    STATUS      current
    DESCRIPTION
        "Get/Set the system time of the device.
        The input format is 'Year/Month/Day/Hour/Minute/Second'.
        Ex: 2004/1/1/12/34/25 means 2004/1/1 - 12:24:25.
        Value range:
        Year    : 2000 - 2036,
        Mouth   : 1 - 12,
        Day     : 1 - 31,
        Hour    : 0 - 23,
        Minute  : 0 - 59,
        Sec     : 0 - 59."
    ::= { es2410cTime 2 }

es2410cNTPServer OBJECT-TYPE
    SYNTAX      DisplayString
    MAX-ACCESS      read-write
    STATUS      current
    DESCRIPTION
        "Get/Set the NTP Time Server. You can use the IP address or domain name."
    ::= { es2410cTime 3 }

es2410cNTPTimeZone OBJECT-TYPE
    SYNTAX      INTEGER(-12..13)
    MAX-ACCESS      read-write
    STATUS      current
    DESCRIPTION
        "Get/Set the NTP Time Zone.
        Value range is between -12 and 13
        -12 - GMT -12:00,
        -11 - GMT -11:00,
        -10 - GMT -10:00,
         -9 - GMT -09:00,
         -8 - GMT -08:00,
         -7 - GMT -07:00,
         -6 - GMT -06:00,
         -5 - GMT -05:00,
         -4 - GMT -04:00,
         -3 - GMT -03:00,
         -2 - GMT -02:00,
         -1 - GMT -01:00,
          0 - GMT +00:00,
          1 - GMT +01:00,
          2 - GMT +02:00,
          3 - GMT +03:00,
          4 - GMT +04:00,
          5 - GMT +05:00,
          6 - GMT +06:00,
          7 - GMT +07:00,
          8 - GMT +08:00,
          9 - GMT +09:00,
         10 - GMT +10:00,
         11 - GMT +11:00,
         12 - GMT +12:00,
         13 - GMT +13:00. "
    ::= { es2410cTime 4 }

es2410cNTPTimeSync OBJECT-TYPE
    SYNTAX      INTEGER(0|1)
    MAX-ACCESS      read-write
    STATUS      current
    DESCRIPTION
        "Sync time from NTP Server. Get this OID always return zero.
        Set the Time Server and Time Zone before doing time sync.
        Notice that time server must be correct!
        Value range (1|0):
        1 - Sync.
        0 - do nothing."
    ::= { es2410cTime 5 }

es2410cDaylightSavingTime OBJECT-TYPE
    SYNTAX      INTEGER(-5..5)
    MAX-ACCESS      read-write
    STATUS      current
    DESCRIPTION
        "Get/Set the daylight saving time.
        Value range is between -5 and 5. Unit: hour. "
    ::= { es2410cTime 6 }

es2410cDaylightStartTime OBJECT-TYPE
    SYNTAX      DisplayString
    MAX-ACCESS      read-write
    STATUS      current
    DESCRIPTION
        "Get/Set the Start time of Daylight Saving.
        The input format is 'MM/DD/HH',
        and daylight saving start month can't equal end month.
        Example: month/day/hour   10/01/00
        Month: 01~12, day: 01~31, hour: 00~23."
    ::= { es2410cTime 7 }

es2410cDaylightEndTime OBJECT-TYPE
    SYNTAX      DisplayString
    MAX-ACCESS      read-write
    STATUS      current
    DESCRIPTION
        "Get/Set the End time of Daylight Saving.
        The input format is 'MM/DD/HH',
        and daylight saving start month can't equal end month.
        Example: month/day/hour   04/01/00
        Month: 01~12, day: 01~31, hour: 00~23."
    ::= { es2410cTime 8 }


es2410cAccount               OBJECT IDENTIFIER ::= { es2410cSystem 4 }

es2410cAccountNumber OBJECT-TYPE
    SYNTAX      INTEGER(1..5)
    MAX-ACCESS      read-only
    STATUS      current
    DESCRIPTION
        "Get the current account number(s) of the system."
    ::= { es2410cAccount 1 }

es2410cAccountTable  OBJECT-TYPE
    SYNTAX      SEQUENCE OF ES2410CAccountEntry
    MAX-ACCESS  not-accessible
    STATUS      current
    DESCRIPTION
        "This is a list of es2410cAccountEntry. The numbers of entries are given by
        the value of es2410cAccountNumber."
    ::= { es2410cAccount 2 }

es2410cAccountEntry  OBJECT-TYPE
    SYNTAX      ES2410CAccountEntry
    MAX-ACCESS      not-accessible
    STATUS      current
    DESCRIPTION
        "This is the Entry(s) for account information."
    INDEX {es2410cAccountIndex}
    ::= { es2410cAccountTable 1 }

ES2410CAccountEntry ::=
SEQUENCE {
    es2410cAccountIndex          INTEGER,
    es2410cAccountAuthorization  DisplayString,
    es2410cAccountName             DisplayString,
    es2410cAccountPassword         DisplayString
}

es2410cAccountIndex  OBJECT-TYPE
    SYNTAX      INTEGER(1..5)
    MAX-ACCESS      read-only
    STATUS      current
    DESCRIPTION
        "This is the index of the account entry."
    ::= { es2410cAccountEntry 1 }

es2410cAccountAuthorization  OBJECT-TYPE
    SYNTAX      DisplayString
    MAX-ACCESS      read-only
    STATUS      current
    DESCRIPTION
        "This is the authorization of the account entry."
    ::= { es2410cAccountEntry 2 }

es2410cAccountName   OBJECT-TYPE
    SYNTAX      DisplayString
    MAX-ACCESS      read-write
    STATUS      current
    DESCRIPTION
        "This is the username of the account entry."
    ::= { es2410cAccountEntry 3 }

es2410cAccountPassword   OBJECT-TYPE
    SYNTAX      DisplayString
    MAX-ACCESS      read-write
    STATUS      current
    DESCRIPTION
        "This is the password of the account entry. The return value is always '********'."
    ::= { es2410cAccountEntry 4 }

es2410cAccountAddName OBJECT-TYPE
    SYNTAX      DisplayString
    MAX-ACCESS      read-write
    STATUS      current
    DESCRIPTION
        "This is the account name for adding operation."
    ::= { es2410cAccount 3 }

es2410cAccountAddPassword OBJECT-TYPE
    SYNTAX      DisplayString
    MAX-ACCESS      read-write
    STATUS      current
    DESCRIPTION
        "This is the account password for adding operation. The return value is always '********'."
    ::= { es2410cAccount 4 }

es2410cDoAccountAdd OBJECT-TYPE
    SYNTAX      INTEGER(0|1)
    MAX-ACCESS      read-write
    STATUS      current
    DESCRIPTION
        "Add account name. OID es2410cAccountAddName and es2410cAccountAddPassword must be
        filled first. Get this OID always return zero.
            1 - Add account.
            0 - do nothing."
    ::= { es2410cAccount 5 }

es2410cAccountDel    OBJECT-TYPE
    SYNTAX      INTEGER(2..5)
    MAX-ACCESS      read-write
    STATUS      current
    DESCRIPTION
        "Delete account. The value is valid es2410cAccountIndex(Can't delete administrator)."
    ::= { es2410cAccount 6 }


es2410cSnmp              OBJECT IDENTIFIER ::= { es2410cProduces 2 }

es2410cGetCommunity OBJECT-TYPE
    SYNTAX      DisplayString
    MAX-ACCESS      read-write
    STATUS      current
    DESCRIPTION
        "Get/Set the get-community of the SNMP."
    ::= { es2410cSnmp 1 }

es2410cSetCommunity OBJECT-TYPE
    SYNTAX      DisplayString
    MAX-ACCESS      read-write
    STATUS      current
    DESCRIPTION
        "Get/Set the set-community of the SNMP."
    ::= { es2410cSnmp 2 }

es2410cTrapBootDelayTime OBJECT-TYPE
    SYNTAX      INTEGER(0..120)
    MAX-ACCESS      read-write
    STATUS      current
    DESCRIPTION
        "Get/Set trap boot delay time in second. Default: 0"
    ::= { es2410cSnmp 3 }

es2410cTrapHostNumber OBJECT-TYPE
    SYNTAX      INTEGER(1..6)
    MAX-ACCESS      read-only
    STATUS      current
    DESCRIPTION
        "Get the number of trap hosts."
    ::= { es2410cSnmp 4 }

es2410cTrapHostTable OBJECT-TYPE
    SYNTAX      SEQUENCE OF ES2410CTrapHostEntry
    MAX-ACCESS  not-accessible
    STATUS      current
    DESCRIPTION
        "A list of trap host entry. The numbers of entries are given by the value of es2410cTrapHostNumber."
    ::= { es2410cSnmp 5 }

es2410cTrapHostEntry OBJECT-TYPE
    SYNTAX      ES2410CTrapHostEntry
    MAX-ACCESS      not-accessible
    STATUS      current
    DESCRIPTION
        "This is the entry information for trap host."
    INDEX {es2410cTrapHostIndex}
    ::= { es2410cTrapHostTable 1 }

ES2410CTrapHostEntry ::=
SEQUENCE {
    es2410cTrapHostIndex         INTEGER,
    es2410cTrapHostIP            IpAddress,
    es2410cTrapHostPort            INTEGER,
    es2410cTrapHostCommunity       DisplayString
}

es2410cTrapHostIndex OBJECT-TYPE
    SYNTAX      INTEGER(1..6)
    MAX-ACCESS      read-only
    STATUS      current
    DESCRIPTION
        "The index of the trap host entry."
    ::= { es2410cTrapHostEntry 1 }

es2410cTrapHostIP    OBJECT-TYPE
    SYNTAX      IpAddress
    MAX-ACCESS      read-write
    STATUS      current
    DESCRIPTION
        "This is the IP of the trap host."
    ::= { es2410cTrapHostEntry 2 }


es2410cTrapHostPort  OBJECT-TYPE
    SYNTAX      INTEGER(1..65535)
    MAX-ACCESS      read-write
    STATUS      current
    DESCRIPTION
        "This is the receiving-port number of the trap host."
    ::= { es2410cTrapHostEntry 3 }


es2410cTrapHostCommunity OBJECT-TYPE
    SYNTAX      DisplayString
    MAX-ACCESS      read-write
    STATUS      current
    DESCRIPTION
        "The community name for the trap PDU."
    ::= { es2410cTrapHostEntry 4 }


es2410cAlarm             OBJECT IDENTIFIER ::= { es2410cProduces 3 }

es2410cEvent             OBJECT IDENTIFIER ::= { es2410cAlarm 1 }

es2410cEventNumber OBJECT-TYPE
    SYNTAX      INTEGER(1..2147483647)
    MAX-ACCESS      read-only
    STATUS      current
    DESCRIPTION
        "Get the total number of alarm events."
    ::= { es2410cEvent 1 }

es2410cEventTable    OBJECT-TYPE
    SYNTAX      SEQUENCE OF ES2410CEventEntry
    MAX-ACCESS  not-accessible
    STATUS      current
    DESCRIPTION
        "This is a list of alarm event entry. The numbers of entries are given by the value of es2410cEventNumber."
    ::= { es2410cEvent 2 }

es2410cEventEntry    OBJECT-TYPE
    SYNTAX      ES2410CEventEntry
    MAX-ACCESS      not-accessible
    STATUS      current
    DESCRIPTION
        "This is the entry information for alarm event."
    INDEX {es2410cEventIndex}
    ::= { es2410cEventTable 1 }

ES2410CEventEntry ::=
SEQUENCE {
    es2410cEventIndex            INTEGER,
    es2410cEventName             DisplayString,
    es2410cEventSendEmail      INTEGER,
    es2410cEventSendTrap       INTEGER
}

es2410cEventIndex    OBJECT-TYPE
    SYNTAX      INTEGER(1..2147483647)
    MAX-ACCESS      read-only
    STATUS      current
    DESCRIPTION
        "This is the index of the alarm event entry."
    ::= { es2410cEventEntry 1 }

es2410cEventName OBJECT-TYPE
    SYNTAX      DisplayString
    MAX-ACCESS      read-only
    STATUS      current
    DESCRIPTION
        "This is the alarm event name."
    ::= { es2410cEventEntry 2 }

es2410cEventSendEmail    OBJECT-TYPE
    SYNTAX      INTEGER(0|1)
    MAX-ACCESS      read-write
    STATUS      current
    DESCRIPTION
        "Send email when alarm event is triggered."
    ::= { es2410cEventEntry 3 }

es2410cEventSendTrap OBJECT-TYPE
    SYNTAX      INTEGER(0|1)
    MAX-ACCESS      read-write
    STATUS      current
    DESCRIPTION
        "Send trap when alarm event is triggered."
    ::= { es2410cEventEntry 4 }


es2410cEmail             OBJECT IDENTIFIER ::= { es2410cAlarm 2 }

es2410cEmailServer OBJECT-TYPE
    SYNTAX      DisplayString
    MAX-ACCESS      read-write
    STATUS      current
    DESCRIPTION
        "This is the SMTP server for alarm event."
    ::= { es2410cEmail 1 }

es2410cEmailUsername OBJECT-TYPE
    SYNTAX      DisplayString
    MAX-ACCESS      read-write
    STATUS      current
    DESCRIPTION
        "This is the Username of SMTP server."
    ::= { es2410cEmail 2 }

es2410cEmailPassword OBJECT-TYPE
    SYNTAX      DisplayString
    MAX-ACCESS      read-write
    STATUS      current
    DESCRIPTION
        "This is the User Password of SMTP server."
    ::= { es2410cEmail 3 }

es2410cEmailSender OBJECT-TYPE
	SYNTAX      DisplayString
	MAX-ACCESS	    read-write
	STATUS		current
	DESCRIPTION
		"This is the Sender of SMTP server."
	::= { es2410cEmail 4 }

es2410cEmailReturnPath OBJECT-TYPE
	SYNTAX      DisplayString
	MAX-ACCESS	    read-write
	STATUS		current
	DESCRIPTION
		"This is the return path of mail."
	::= { es2410cEmail 5 }

es2410cEmailUserNumber OBJECT-TYPE
    SYNTAX      INTEGER(1..6)
    MAX-ACCESS      read-only
    STATUS      current
    DESCRIPTION
        "The number of the email users that you want to send the alarm notification."
    ::= { es2410cEmail 6 }

es2410cEmailUserTable    OBJECT-TYPE
    SYNTAX      SEQUENCE OF ES2410CEmailUserEntry
    MAX-ACCESS  not-accessible
    STATUS      current
    DESCRIPTION
        "This is a list of email user entry. The numbers of entries are given by the value of es2410cEmailUserNumber."
    ::= { es2410cEmail 7 }

es2410cEmailUserEntry    OBJECT-TYPE
    SYNTAX      ES2410CEmailUserEntry
    MAX-ACCESS      not-accessible
    STATUS      current
    DESCRIPTION
        "This is the Entry information for email user entry."
    INDEX {es2410cEmailUserIndex}
    ::= { es2410cEmailUserTable 1 }

ES2410CEmailUserEntry ::=
SEQUENCE {
    es2410cEmailUserIndex            INTEGER,
    es2410cEmailUserAddress          DisplayString
}

es2410cEmailUserIndex    OBJECT-TYPE
    SYNTAX      INTEGER(1..6)
    MAX-ACCESS      read-only
    STATUS      current
    DESCRIPTION
        "This is the index of the email user entry."
    ::= { es2410cEmailUserEntry 1 }

es2410cEmailUserAddress  OBJECT-TYPE
    SYNTAX      DisplayString
    MAX-ACCESS      read-write
    STATUS      current
    DESCRIPTION
        "This is the email address of the email user entry."
    ::= { es2410cEmailUserEntry 2 }

es2410cTftp              OBJECT IDENTIFIER ::= { es2410cProduces 4 }

es2410cTftpServer OBJECT-TYPE
    SYNTAX      IpAddress
    MAX-ACCESS      read-write
    STATUS      current
    DESCRIPTION
        "Get/Set the tftp server."
    ::= { es2410cTftp 1 }


es2410cConfiguration             OBJECT IDENTIFIER ::= { es2410cProduces 5 }

es2410cSaveRestore               OBJECT IDENTIFIER ::= { es2410cConfiguration 1 }

es2410cSaveStart OBJECT-TYPE
    SYNTAX      INTEGER(0|1)
    MAX-ACCESS      read-write
    STATUS      current
    DESCRIPTION
        "Save current configuration into flash memory (Save as Start Configuration).
        Get this OID always return zero.
            1 - Save.
            0 - do nothing. "
    ::= { es2410cSaveRestore 1 }

es2410cSaveUser OBJECT-TYPE
    SYNTAX      INTEGER(0|1)
    MAX-ACCESS      read-write
    STATUS      current
    DESCRIPTION
        "Save current configuration into flash memory (Save as User Configuration).
        Get this OID always return zero.
            1 - Save.
            0 - do nothing. "
    ::= { es2410cSaveRestore 2 }

es2410cRestoreDefault OBJECT-TYPE
    SYNTAX      INTEGER(0|1|2)
    MAX-ACCESS      read-write
    STATUS      current
    DESCRIPTION
        "Restore factory default configuration.
        Get this OID always return zero.
            2 - Restore default included default ip address.
        1 - Restore default without changing current ip address.
            0 - do nothing. "
    ::= { es2410cSaveRestore 3 }

es2410cRestoreUser OBJECT-TYPE
    SYNTAX      INTEGER(0|1)
    MAX-ACCESS      read-write
    STATUS      current
    DESCRIPTION
        "Restore user configuration.
        Get this OID always return zero.
            1 - Restore.
            0 - do nothing. "
    ::= { es2410cSaveRestore 4 }


es2410cConfigFile            OBJECT IDENTIFIER ::= { es2410cConfiguration 2 }

es2410cExportConfigName OBJECT-TYPE
    SYNTAX      DisplayString
    MAX-ACCESS      read-write
    STATUS      current
    DESCRIPTION
        "Get/Set the export file path and name."
    ::= { es2410cConfigFile 1 }

es2410cDoExportConfig OBJECT-TYPE
    SYNTAX      INTEGER(1|2)
    MAX-ACCESS      read-write
    STATUS      current
    DESCRIPTION
        "Do export-config.
        Get this OID always return zero.
            1   -   Export start section.
            2   -   Export user-conf section."
    ::= { es2410cConfigFile 2 }

es2410cImportConfigName OBJECT-TYPE
    SYNTAX      DisplayString
    MAX-ACCESS      read-write
    STATUS      current
    DESCRIPTION
        "Get/Set the import file path and name."
    ::= { es2410cConfigFile 3 }

es2410cDoImportConfig OBJECT-TYPE
    SYNTAX      INTEGER(1|2)
    MAX-ACCESS      read-write
    STATUS      current
    DESCRIPTION
        "Do import-config.
        Get this OID always return zero.
            1   -   Import start section.
            2   -   Import user-conf section."
    ::= { es2410cConfigFile 4 }

es2410cDiagnostic            OBJECT IDENTIFIER ::= { es2410cProduces 6 }

es2410cEEPROMTest OBJECT-TYPE
    SYNTAX      DisplayString
    MAX-ACCESS      read-only
    STATUS      current
    DESCRIPTION
        "EEPROM access test."
    ::= { es2410cDiagnostic 1 }

es2410cUartTest OBJECT-TYPE
    SYNTAX      DisplayString
    MAX-ACCESS      read-only
    STATUS      current
    DESCRIPTION
        "UART access test."
    ::= { es2410cDiagnostic 2 }

es2410cDramTest OBJECT-TYPE
    SYNTAX      DisplayString
    MAX-ACCESS      read-only
    STATUS      current
    DESCRIPTION
        "DRAM access test."
    ::= { es2410cDiagnostic 3 }

es2410cFlashTest OBJECT-TYPE
    SYNTAX      DisplayString
    MAX-ACCESS      read-only
    STATUS      current
    DESCRIPTION
        "Flash memory access test."
    ::= { es2410cDiagnostic 4 }

es2410cInternalLoopbackTest OBJECT-TYPE
    SYNTAX      DisplayString
    MAX-ACCESS      read-only
    STATUS      current
    DESCRIPTION
        "Internal loop back test."
    ::= { es2410cDiagnostic 5 }

es2410cExternalLoopbackTest OBJECT-TYPE
    SYNTAX      DisplayString
    MAX-ACCESS      read-only
    STATUS      current
    DESCRIPTION
        "External loop back test."
    ::= { es2410cDiagnostic 6 }

es2410cPingTest OBJECT-TYPE
    SYNTAX      DisplayString
    MAX-ACCESS      read-write
    STATUS      current
    DESCRIPTION
        "Set the host address that you want to ping and the system will return the test result."
    ::= { es2410cDiagnostic 7 }

es2410cLog               OBJECT IDENTIFIER ::= { es2410cProduces 7 }

es2410cClearLog OBJECT-TYPE
    SYNTAX      INTEGER(0|1)
    MAX-ACCESS      read-write
    STATUS      current
    DESCRIPTION
        "Clear system log.
        Get this OID always return zero.
            1 - Clear log.
            0 - do nothing. "
    ::= { es2410cLog 1 }

es2410cUploadLog OBJECT-TYPE
    SYNTAX      INTEGER(0|1)
    MAX-ACCESS      read-write
    STATUS      current
    DESCRIPTION
        "Upload current system log. Set the correct tftp server first.
        The format of log file is 'ModelName_SerialNumbuer_YYMMDD_HHMM'.
        Get this OID always return zero.
            1 - Upload log
            0 - do nothing. "
    ::= { es2410cLog 2 }

es2410cAutoUploadLogState OBJECT-TYPE
    SYNTAX      INTEGER(0|1)
    MAX-ACCESS      read-write
    STATUS      current
    DESCRIPTION
        "Enable auto-upload log function. Set the correct tftp server first.
        The format of log file is 'ModelName_SerialNumbuer_YYMMDD_HHMM'.
        Get this OID always return zero.
            1 - Enable auto-upload
            0 - do nothing. "
    ::= { es2410cLog 3 }

es2410cLogNumber OBJECT-TYPE
    SYNTAX      INTEGER(0..120)
    MAX-ACCESS      read-only
    STATUS      current
    DESCRIPTION
        "Get the number of current system log."
    ::= { es2410cLog 4 }

es2410cLogTable  OBJECT-TYPE
    SYNTAX      SEQUENCE OF ES2410CLogEntry
    MAX-ACCESS  not-accessible
    STATUS      current
    DESCRIPTION
        "This is a list of log entry. The numbers of entries are given by the value of es2410cLogNumber."
    ::= { es2410cLog 5 }

es2410cLogEntry  OBJECT-TYPE
    SYNTAX      ES2410CLogEntry
    MAX-ACCESS      not-accessible
    STATUS      current
    DESCRIPTION
        "This is the Entry information for system log."
    INDEX {es2410cLogIndex}
    ::= { es2410cLogTable 1 }

ES2410CLogEntry ::=
SEQUENCE {
    es2410cLogIndex          INTEGER,
    es2410cLogEvent              DisplayString
}

es2410cLogIndex  OBJECT-TYPE
    SYNTAX      INTEGER(1..120)
    MAX-ACCESS      read-only
    STATUS      current
    DESCRIPTION
        "This is the index of the log entry."
    ::= { es2410cLogEntry 1 }

es2410cLogEvent  OBJECT-TYPE
    SYNTAX      DisplayString
    MAX-ACCESS      read-only
    STATUS      current
    DESCRIPTION
        "This is the detail information of the log entry."
    ::= { es2410cLogEntry 2 }

es2410cFirmware              OBJECT IDENTIFIER ::= { es2410cProduces 8 }

es2410cFirmwareFileName OBJECT-TYPE
    SYNTAX      DisplayString
    MAX-ACCESS      read-write
    STATUS      current
    DESCRIPTION
        "Get/Set the path and filename for firmware upgrading."
    ::= { es2410cFirmware 1 }

es2410cDoFirmwareUpgrade OBJECT-TYPE
    SYNTAX      INTEGER(0|1)
    MAX-ACCESS      read-write
    STATUS      current
    DESCRIPTION
        "Do firmware upgrade. Get this OID always return zero.
            1 - Do firmware upgrade.
            0 - do nothing."
    ::= { es2410cFirmware 2 }


es2410cPort              OBJECT IDENTIFIER ::= { es2410cProduces 9 }

es2410cPortStatus            OBJECT IDENTIFIER ::= { es2410cPort 1 }

es2410cPortStatusNumber OBJECT-TYPE
    SYNTAX      INTEGER(1..2147483647)
    MAX-ACCESS      read-only
    STATUS      current
    DESCRIPTION
        "Get the number of port."
    ::= { es2410cPortStatus 1 }

es2410cPortStatusTable   OBJECT-TYPE
    SYNTAX      SEQUENCE OF ES2410CPortStatusEntry
    MAX-ACCESS  not-accessible
    STATUS      current
    DESCRIPTION
        "This is a list of port status entry. The numbers of entries are given by the value of es2410cPortStatusNumber."
    ::= { es2410cPortStatus 2 }

es2410cPortStatusEntry   OBJECT-TYPE
    SYNTAX      ES2410CPortStatusEntry
    MAX-ACCESS      not-accessible
    STATUS      current
    DESCRIPTION
        "This is the entry(s) for port status information."
    INDEX {es2410cPortStatusIndex}
    ::= { es2410cPortStatusTable 1 }

ES2410CPortStatusEntry ::=
SEQUENCE {
    es2410cPortStatusIndex           INTEGER,
    es2410cPortStatusMedia          DisplayString,
    es2410cPortStatusLink           DisplayString,
    es2410cPortStatusPortState      DisplayString,
    es2410cPortStatusAutoNego       DisplayString,
    es2410cPortStatusSpdDpx         DisplayString,
    es2410cPortStatusRxPause        DisplayString,
    es2410cPortStatusTxPause        DisplayString,
    es2410cPortStatusDescription     DisplayString
}

es2410cPortStatusIndex   OBJECT-TYPE
    SYNTAX      INTEGER(1..2147483647)
    MAX-ACCESS      read-only
    STATUS      current
    DESCRIPTION
        "This is the index of the port status entry."
    ::= { es2410cPortStatusEntry 1 }

es2410cPortStatusMedia   OBJECT-TYPE
    SYNTAX      DisplayString
    MAX-ACCESS      read-only
    STATUS      current
    DESCRIPTION
        "This is the port media type of the port status entry."
    ::= { es2410cPortStatusEntry 2 }

es2410cPortStatusLink    OBJECT-TYPE
    SYNTAX      DisplayString
    MAX-ACCESS      read-only
    STATUS      current
    DESCRIPTION
        "This is the port link of the port status entry."
    ::= { es2410cPortStatusEntry 3 }

es2410cPortStatusPortState   OBJECT-TYPE
    SYNTAX      DisplayString
    MAX-ACCESS      read-only
    STATUS      current
    DESCRIPTION
        "This is the port state of the port status entry."
    ::= { es2410cPortStatusEntry 4 }

es2410cPortStatusAutoNego    OBJECT-TYPE
    SYNTAX      DisplayString
    MAX-ACCESS      read-only
    STATUS      current
    DESCRIPTION
        "This is the auto negotiation of the port status entry."
    ::= { es2410cPortStatusEntry 5 }

es2410cPortStatusSpdDpx  OBJECT-TYPE
    SYNTAX      DisplayString
    MAX-ACCESS      read-only
    STATUS      current
    DESCRIPTION
        "This is the speed/duplex of the port status entry."
    ::= { es2410cPortStatusEntry 6 }

es2410cPortStatusRxPause     OBJECT-TYPE
    SYNTAX      DisplayString
    MAX-ACCESS      read-only
    STATUS      current
    DESCRIPTION
        "The Rx Pause of the port status entry."
    ::= { es2410cPortStatusEntry 7 }

es2410cPortStatusTxPause     OBJECT-TYPE
    SYNTAX      DisplayString
    MAX-ACCESS      read-only
    STATUS      current
    DESCRIPTION
        "The Tx Pause of the port status entry."
    ::= { es2410cPortStatusEntry 8 }

es2410cPortStatusDescription  OBJECT-TYPE
    SYNTAX      DisplayString
    MAX-ACCESS  read-only
    STATUS      current
    DESCRIPTION
        "This is the description of port."
    ::= { es2410cPortStatusEntry 9 }

es2410cPortConf              OBJECT IDENTIFIER ::= { es2410cPort 2 }

es2410cPortConfNumber OBJECT-TYPE
    SYNTAX      INTEGER(1..2147483647)
    MAX-ACCESS      read-only
    STATUS      current
    DESCRIPTION
        "Get the number of port configuration."
    ::= { es2410cPortConf 1 }

es2410cPortConfTable OBJECT-TYPE
    SYNTAX      SEQUENCE OF ES2410CPortConfEntry
    MAX-ACCESS  not-accessible
    STATUS      current
    DESCRIPTION
        "This is a list of port configuration entry. The numbers of entries are given by the value of es2410cPortConfNumber."
    ::= { es2410cPortConf 2 }

es2410cPortConfEntry OBJECT-TYPE
    SYNTAX      ES2410CPortConfEntry
    MAX-ACCESS      not-accessible
    STATUS      current
    DESCRIPTION
        "This is the Entry(s) for port configuration information."
    INDEX {es2410cPortConfIndex}
    ::= { es2410cPortConfTable 1 }

ES2410CPortConfEntry ::=
SEQUENCE {
    es2410cPortConfIndex         INTEGER,
    es2410cPortConfPortState        INTEGER,
    es2410cPortConfSpdDpx           INTEGER,
    es2410cPortConfFlwCtrl          INTEGER,
    es2410cPortConfPowerSaving      INTEGER,
    es2410cPortConfDescription      DisplayString
}

es2410cPortConfIndex OBJECT-TYPE
    SYNTAX      INTEGER(1..2147483647)
    MAX-ACCESS      read-only
    STATUS      current
    DESCRIPTION
        "This is the index of the port configuration entry."
    ::= { es2410cPortConfEntry 1 }

es2410cPortConfPortState OBJECT-TYPE
    SYNTAX      INTEGER(0|1)
    MAX-ACCESS      read-write
    STATUS      current
    DESCRIPTION
        "This is the port state of the port configuration entry.
         0 - disabled.
         1 - enabled. "
    ::= { es2410cPortConfEntry 2 }

es2410cPortConfSpdDpx    OBJECT-TYPE
    SYNTAX      INTEGER(0..5)
    MAX-ACCESS      read-write
    STATUS      current
    DESCRIPTION
        "This is the speed/duplex of the port configuration entry.
         0 - auto.
         1 - 10M/Half.
         2 - 10M/Full.
         3 - 100M/Half.
         4 - 100M/Full.
         5 - 1G/Full.  "
    ::= { es2410cPortConfEntry 3 }

es2410cPortConfFlwCtrl   OBJECT-TYPE
    SYNTAX      INTEGER(0..2)
    MAX-ACCESS      read-write
    STATUS      current
    DESCRIPTION
        "This is the flow control of the port configuration entry.
         0 - disable
         1 - symmetric.
         2 - asymmetric.  "
    ::= { es2410cPortConfEntry 4 }

es2410cPortConfPowerSaving   OBJECT-TYPE
    SYNTAX      INTEGER(0|1)
    MAX-ACCESS  read-write
    STATUS      current
    DESCRIPTION
        "This is the power saving of the port configuration entry.
         0 - disable
         1 - enable."
    ::= { es2410cPortConfEntry 5 }

es2410cPortConfDescription   OBJECT-TYPE
    SYNTAX      DisplayString
    MAX-ACCESS  read-write
    STATUS      current
    DESCRIPTION
        "This is the description of port."
    ::= { es2410cPortConfEntry 6 }

es2410cPortBandwidth             OBJECT IDENTIFIER ::= { es2410cPort 3 }

es2410cPortBandwidthNumber   OBJECT-TYPE
    SYNTAX      INTEGER(1..2147483647)
    MAX-ACCESS      read-only
    STATUS      current
    DESCRIPTION
        "Get the number of port bandwidth number."
    ::= { es2410cPortBandwidth 1 }

es2410cPortBandwidthTable    OBJECT-TYPE
    SYNTAX      SEQUENCE OF ES2410CPortBandwidthEntry
    MAX-ACCESS  not-accessible
    STATUS      current
    DESCRIPTION
        "A list of port bandwidth entry. The number of entries are given by the value of es2410cPortBandwidthNumber."
    ::= { es2410cPortBandwidth 2 }

es2410cPortBandwidthEntry    OBJECT-TYPE
    SYNTAX      ES2410CPortBandwidthEntry
    MAX-ACCESS      not-accessible
    STATUS      current
    DESCRIPTION
        "Entry(s) for port bandwidth informaion."
    INDEX {es2410cPortBandwidthIndex}
    ::= { es2410cPortBandwidthTable 1 }

ES2410CPortBandwidthEntry ::=
SEQUENCE {
    es2410cPortBandwidthIndex              INTEGER,
    es2410cPortBandwidthIngressRate        INTEGER,
    es2410cPortBandwidthEgressRate         INTEGER,
    es2410cPortBandwidthStormType          INTEGER,
    es2410cPortBandwidthStormRate          INTEGER
}

es2410cPortBandwidthIndex    OBJECT-TYPE
    SYNTAX      INTEGER(1..10)
    MAX-ACCESS      read-only
    STATUS      current
    DESCRIPTION
        "The index of the port bandwidth entry."
    ::= { es2410cPortBandwidthEntry 1 }

es2410cPortBandwidthIngressRate  OBJECT-TYPE
    SYNTAX      INTEGER(64..1024000)
    MAX-ACCESS      read-write
    STATUS      current
    DESCRIPTION
        "The Ingress rate(64~1024000) of the Bandwidth configuration."
    ::= { es2410cPortBandwidthEntry 2 }

es2410cPortBandwidthEgressRate   OBJECT-TYPE
    SYNTAX      INTEGER(64..1024000)
    MAX-ACCESS      read-write
    STATUS      current
    DESCRIPTION
        "The Egress rate(64~1024000) of the Bandwidth configuration."
    ::= { es2410cPortBandwidthEntry 3 }

es2410cPortBandwidthStormType    OBJECT-TYPE
    SYNTAX      INTEGER(0..7)
    MAX-ACCESS      read-write
    STATUS      current
    DESCRIPTION
        "The storm type of the Bandwidth configuration.
         0 - Disable.
             1 - BC.
             2 - UC.
             3 - BC,UC.
             4 - MC.
             5 - BC,MC.
             6 - UC,MC.
             7 - BC,UC,MC."
    ::= { es2410cPortBandwidthEntry 4 }

es2410cPortBandwidthStormRate    OBJECT-TYPE
    SYNTAX      INTEGER(64..1024000)
    MAX-ACCESS      read-write
    STATUS      current
    DESCRIPTION
        "The storm rate(64~1024000) of the Bandwidth configuration."
    ::= { es2410cPortBandwidthEntry 5 }

es2410cPortSFPInfo               OBJECT IDENTIFIER ::= { es2410cPort 4 }

es2410cPortSFPInfoNumber OBJECT-TYPE
    SYNTAX      INTEGER(1..2147483647)
    MAX-ACCESS      read-only
    STATUS      current
    DESCRIPTION
        "Get the number of sfp info entry."
    ::= { es2410cPortSFPInfo 1 }

es2410cPortSFPInfoTable  OBJECT-TYPE
    SYNTAX      SEQUENCE OF ES2410CPORTSFPInfoEntry
    MAX-ACCESS  not-accessible
    STATUS      current
    DESCRIPTION
        "A list of sfp info entry. The numbers of entries are given by the value of es2410cPortSFPInfoNumber."
    ::= { es2410cPortSFPInfo 2 }

es2410cPortSFPInfoEntry  OBJECT-TYPE
    SYNTAX      ES2410CPORTSFPInfoEntry
    MAX-ACCESS      not-accessible
    STATUS      current
    DESCRIPTION
        "Entry(s) for SFP information."
    INDEX {es2410cPortSFPInfoIndex}
    ::= { es2410cPortSFPInfoTable 1 }

ES2410CPORTSFPInfoEntry ::=
SEQUENCE {
    es2410cPortSFPInfoIndex      INTEGER,
    es2410cPortSFPConnectorType  DisplayString,
    es2410cPortSFPFiberType      DisplayString,
    es2410cPortSFPWavelength     DisplayString,
    es2410cPortSFPBaudRate       DisplayString,
    es2410cPortSFPVendorOUI      DisplayString,
    es2410cPortSFPVendorName     DisplayString,
    es2410cPortSFPVendorPN       DisplayString,
    es2410cPortSFPVendorRev      DisplayString,
    es2410cPortSFPVendorSN       DisplayString,
    es2410cPortSFPDateCode       DisplayString,
    es2410cPortSFPTemperature    DisplayString,
    es2410cPortSFPVcc            DisplayString,
    es2410cPortSFPTxBias         DisplayString,
    es2410cPortSFPTxPWR          DisplayString,
    es2410cPortSFPRxPWR          DisplayString
}

es2410cPortSFPInfoIndex  OBJECT-TYPE
    SYNTAX      INTEGER(1..2147483647)
    MAX-ACCESS      read-only
    STATUS      current
    DESCRIPTION
        "The index of the sfp info entry."
    ::= { es2410cPortSFPInfoEntry 1 }

es2410cPortSFPConnectorType  OBJECT-TYPE
    SYNTAX      DisplayString
    MAX-ACCESS      read-only
    STATUS      current
    DESCRIPTION
        "Get connector type of the sfp."
    ::= { es2410cPortSFPInfoEntry 2 }

es2410cPortSFPFiberType  OBJECT-TYPE
    SYNTAX      DisplayString
    MAX-ACCESS      read-only
    STATUS      current
    DESCRIPTION
        "Get fiber type of the sfp."
    ::= { es2410cPortSFPInfoEntry 3 }

es2410cPortSFPWavelength OBJECT-TYPE
    SYNTAX      DisplayString
    MAX-ACCESS      read-only
    STATUS      current
    DESCRIPTION
        "Get tx central wavelength of the sfp."
    ::= { es2410cPortSFPInfoEntry 4 }

es2410cPortSFPBaudRate   OBJECT-TYPE
    SYNTAX      DisplayString
    MAX-ACCESS      read-only
    STATUS      current
    DESCRIPTION
        "Get baud rate of the sfp."
    ::= { es2410cPortSFPInfoEntry 5 }

es2410cPortSFPVendorOUI  OBJECT-TYPE
    SYNTAX      DisplayString
    MAX-ACCESS      read-only
    STATUS      current
    DESCRIPTION
        "Get vendor OUI of the sfp."
    ::= { es2410cPortSFPInfoEntry 6 }

es2410cPortSFPVendorName OBJECT-TYPE
    SYNTAX      DisplayString
    MAX-ACCESS      read-only
    STATUS      current
    DESCRIPTION
        "Get vendor name of the sfp."
    ::= { es2410cPortSFPInfoEntry 7 }

es2410cPortSFPVendorPN   OBJECT-TYPE
    SYNTAX      DisplayString
    MAX-ACCESS      read-only
    STATUS      current
    DESCRIPTION
        "Get vendor part number of the sfp."
    ::= { es2410cPortSFPInfoEntry 8 }

es2410cPortSFPVendorRev  OBJECT-TYPE
    SYNTAX      DisplayString
    MAX-ACCESS      read-only
    STATUS      current
    DESCRIPTION
        "Get vendor revision number of the sfp."
    ::= { es2410cPortSFPInfoEntry 9 }

es2410cPortSFPVendorSN   OBJECT-TYPE
    SYNTAX      DisplayString
    MAX-ACCESS      read-only
    STATUS      current
    DESCRIPTION
        "Get vendor serial number of the sfp."
    ::= { es2410cPortSFPInfoEntry 10 }

es2410cPortSFPDateCode   OBJECT-TYPE
    SYNTAX      DisplayString
    MAX-ACCESS      read-only
    STATUS      current
    DESCRIPTION
        "Get data code of the sfp."
    ::= { es2410cPortSFPInfoEntry 11 }

es2410cPortSFPTemperature    OBJECT-TYPE
    SYNTAX      DisplayString
    MAX-ACCESS      read-only
    STATUS      current
    DESCRIPTION
        "Get current temperature of the sfp."
    ::= { es2410cPortSFPInfoEntry 12 }

es2410cPortSFPVcc    OBJECT-TYPE
    SYNTAX      DisplayString
    MAX-ACCESS      read-only
    STATUS      current
    DESCRIPTION
        "Get current internal supply voltage of the sfp."
    ::= { es2410cPortSFPInfoEntry 13 }

es2410cPortSFPTxBias OBJECT-TYPE
    SYNTAX      DisplayString
    MAX-ACCESS      read-only
    STATUS      current
    DESCRIPTION
        "Get current TX Bias of the sfp."
    ::= { es2410cPortSFPInfoEntry 14 }

es2410cPortSFPTxPWR  OBJECT-TYPE
    SYNTAX      DisplayString
    MAX-ACCESS      read-only
    STATUS      current
    DESCRIPTION
        "Get current TX output power of the sfp."
    ::= { es2410cPortSFPInfoEntry 15 }

es2410cPortSFPRxPWR  OBJECT-TYPE
    SYNTAX      DisplayString
    MAX-ACCESS      read-only
    STATUS      current
    DESCRIPTION
        "Get current Received Power of the sfp."
    ::= { es2410cPortSFPInfoEntry 16 }

es2410cLoopDetectedConf              OBJECT IDENTIFIER ::= { es2410cProduces 10 }

es2410cLoopDetectedNumber OBJECT-TYPE
    SYNTAX      INTEGER(1..2147483647)
    MAX-ACCESS      read-only
    STATUS      current
    DESCRIPTION
        "Get the number of loop detected entry."
    ::= { es2410cLoopDetectedConf 1 }

es2410cLoopDetectedTable OBJECT-TYPE
    SYNTAX      SEQUENCE OF ES2410CLoopDetectedEntry
    MAX-ACCESS  not-accessible
    STATUS      current
    DESCRIPTION
        "This is a list of loop detected entry. The numbers of entries are given by the value of es2410cLoopDetectedNumber."
    ::= { es2410cLoopDetectedConf 2 }

es2410cLoopDetectedEntry OBJECT-TYPE
    SYNTAX      ES2410CLoopDetectedEntry
    MAX-ACCESS      not-accessible
    STATUS      current
    DESCRIPTION
        "Entry(s) for loop detected information."
    INDEX {es2410cLoopDetectedfIndex}
    ::= { es2410cLoopDetectedTable 1 }

ES2410CLoopDetectedEntry ::=
SEQUENCE {
    es2410cLoopDetectedfIndex           INTEGER,
    es2410cLoopDetectedStateEbl         INTEGER,
    es2410cLoopDetectedCurrentStatus    INTEGER,
    es2410cLoopDetectedResumed          INTEGER
}

es2410cLoopDetectedfIndex    OBJECT-TYPE
    SYNTAX      INTEGER(1..2147483647)
    MAX-ACCESS      read-only
    STATUS      current
    DESCRIPTION
        "This is the index of the loop detected entry."
    ::= { es2410cLoopDetectedEntry 1 }

es2410cLoopDetectedStateEbl  OBJECT-TYPE
    SYNTAX      INTEGER(0|1)
    MAX-ACCESS      read-write
    STATUS      current
    DESCRIPTION
        "The state of the loop detected entry.
         0 - disabled.
         1 - enabled. "
    ::= { es2410cLoopDetectedEntry 2 }

es2410cLoopDetectedCurrentStatus OBJECT-TYPE
    SYNTAX      INTEGER(0|1)
    MAX-ACCESS      read-only
    STATUS      current
    DESCRIPTION
        "The current status of the loop detected port.
         0 - unlocked
         1 - Locked due to the loop condition"
    ::= { es2410cLoopDetectedEntry 3 }

es2410cLoopDetectedResumed   OBJECT-TYPE
    SYNTAX      INTEGER(0|1)
    MAX-ACCESS      read-write
    STATUS      current
    DESCRIPTION
        "Unlock the port which is locked due to loop condition. Get this OID always return zero.
         1 - Unlock the port,
         0 - do nothing."
    ::= { es2410cLoopDetectedEntry 4 }

es2410cLoopDetectedAction OBJECT-TYPE
    SYNTAX      INTEGER(0|1)
    MAX-ACCESS      read-write
    STATUS      current
    DESCRIPTION
        "Set the corresponding action while loop is detected.
         1 - Lock the loop port,
         0 - do nothing."
    ::= { es2410cLoopDetectedConf 3 }

es2410cIpMacBind             OBJECT IDENTIFIER ::= { es2410cProduces 11 }

es2410cIpMacBindStatus           OBJECT IDENTIFIER ::= { es2410cIpMacBind 1 }

es2410cIpMacBindMode  OBJECT-TYPE
    SYNTAX      INTEGER(0|1)
    MAX-ACCESS      read-write
    STATUS      current
    DESCRIPTION
        "Set the IP-MAC Binding State.
         1 - Enable,
         0 - Disable."
    ::= { es2410cIpMacBindStatus 1 }

es2410cIpMacBindPort  OBJECT-TYPE
    SYNTAX      DisplayString
    MAX-ACCESS      read-write
    STATUS      current
    DESCRIPTION
        "Set the IP-MAC Binding Port.
         Syntax: 1,5-7, available from 1 to 10."
    ::= { es2410cIpMacBindStatus 2 }

es2410cIpMacBindCount  OBJECT-TYPE
    SYNTAX      INTEGER(0..2147483647)
    MAX-ACCESS      read-only
    STATUS      current
    DESCRIPTION
        "Get the current IP-MAC Binding user count."
    ::= { es2410cIpMacBindStatus 3 }

es2410cIpMacBindStatusTable  OBJECT-TYPE
    SYNTAX      SEQUENCE OF ES2410CIpMacBindStatusEntry
    MAX-ACCESS  not-accessible
    STATUS      current
    DESCRIPTION
        " "
    ::= { es2410cIpMacBindStatus 4 }

es2410cIpMacBindStatusEntry  OBJECT-TYPE
    SYNTAX      ES2410CIpMacBindStatusEntry
    MAX-ACCESS      not-accessible
    STATUS      current
    DESCRIPTION
        "Entry(s) for IP-MAC Binding Status."
    INDEX {es2410cIpMacBindStatusIndex}
    ::= { es2410cIpMacBindStatusTable 1 }

ES2410CIpMacBindStatusEntry ::=
SEQUENCE {
    es2410cIpMacBindStatusIndex      INTEGER,
    es2410cIpMacBindStatusName           DisplayString,
    es2410cIpMacBindStatusMac            DisplayString,
    es2410cIpMacBindStatusIp             IpAddress,
    es2410cIpMacBindStatusPort       DisplayString,
    es2410cIpMacBindStatusBindingMethod      INTEGER,
    es2410cIpMacBindStatusType       INTEGER
}

es2410cIpMacBindStatusIndex  OBJECT-TYPE
    SYNTAX      INTEGER(1..2147483647)
    MAX-ACCESS      read-only
    STATUS      current
    DESCRIPTION
        "The index of the IP-MAC Binding entry."
    ::= { es2410cIpMacBindStatusEntry 1 }

es2410cIpMacBindStatusName   OBJECT-TYPE
    SYNTAX      DisplayString
    MAX-ACCESS      read-only
    STATUS      current
    DESCRIPTION
        "Get the name of this IP-MAC binding entry."
    ::= { es2410cIpMacBindStatusEntry 2 }

es2410cIpMacBindStatusMac    OBJECT-TYPE
    SYNTAX      DisplayString
    MAX-ACCESS      read-only
    STATUS      current
    DESCRIPTION
        "Get the MAC address of this IP-MAC binding entry."
    ::= { es2410cIpMacBindStatusEntry 3 }

es2410cIpMacBindStatusIp     OBJECT-TYPE
    SYNTAX      IpAddress
    MAX-ACCESS      read-only
    STATUS      current
    DESCRIPTION
        "Get the IP address of this IP-MAC binding entry."
    ::= { es2410cIpMacBindStatusEntry 4 }

es2410cIpMacBindStatusPort   OBJECT-TYPE
    SYNTAX      DisplayString
    MAX-ACCESS      read-only
    STATUS      current
    DESCRIPTION
        "Get the binding port of this IP-MAC binding entry."
    ::= { es2410cIpMacBindStatusEntry 5 }

es2410cIpMacBindStatusBindingMethod   OBJECT-TYPE
    SYNTAX      INTEGER(0|1)
    MAX-ACCESS      read-only
    STATUS      current
    DESCRIPTION
        "Get the binding method of this IP-MAC binding entry.
         0 : IP-MAC,
         1 : IP,
         2 : MAC"
    ::= { es2410cIpMacBindStatusEntry 6 }

es2410cIpMacBindStatusType   OBJECT-TYPE
    SYNTAX      INTEGER(0|1)
    MAX-ACCESS      read-only
    STATUS      current
    DESCRIPTION
        "Get the status of this IP-MAC binding entry.
         0: Static
         1: Dynamic"
    ::= { es2410cIpMacBindStatusEntry 7 }

es2410cIpMacBindConf             OBJECT IDENTIFIER ::= { es2410cIpMacBind 2 }

es2410cIpMacBindConfName  OBJECT-TYPE
    SYNTAX      DisplayString
    MAX-ACCESS      read-write
    STATUS      current
    DESCRIPTION
        "Set the name of a IP-MAC binding entry."
    ::= { es2410cIpMacBindConf 1 }

es2410cIpMacBindConfMac  OBJECT-TYPE
    SYNTAX      DisplayString
    MAX-ACCESS      read-write
    STATUS      current
    DESCRIPTION
        "Set the MAC address of a IP-MAC binding entry."
    ::= { es2410cIpMacBindConf 2 }

es2410cIpMacBindConfIp  OBJECT-TYPE
    SYNTAX      IpAddress
    MAX-ACCESS      read-write
    STATUS      current
    DESCRIPTION
        "Set the IP address of a IP-MAC binding entry."
    ::= { es2410cIpMacBindConf 3 }

es2410cIpMacBindConfPort  OBJECT-TYPE
    SYNTAX      DisplayString
    MAX-ACCESS      read-write
    STATUS      current
    DESCRIPTION
        "Set the binding port of a IP-MAC binding entry.
         Port_range: range syntax: 1,5-7, available from 1 to 10
        "
    ::= { es2410cIpMacBindConf 4 }

es2410cIpMacBindBindingMethod  OBJECT-TYPE
    SYNTAX      INTEGER(0..2)
    MAX-ACCESS      read-write
    STATUS      current
    DESCRIPTION
        "Set the binding method of a IP-MAC binding entry.
         0 : IP-MAC,
         1 : IP,
         2 : MAC.
        "
    ::= { es2410cIpMacBindConf 5 }

es2410cAddIpMacBindConf  OBJECT-TYPE
    SYNTAX      INTEGER(0|1)
    MAX-ACCESS      read-write
    STATUS      current
    DESCRIPTION
        "Perform the operation of adding a IP-MAC binding entry.
         0 : None,
         1 : Add
        "
    ::= { es2410cIpMacBindConf 6 }

es2410cIpMacBindConfDelByIp  OBJECT-TYPE
    SYNTAX      IpAddress
    MAX-ACCESS      read-write
    STATUS      current
    DESCRIPTION
        "Delete the IP-MAC binding entry(s) by the specific IP address."
    ::= { es2410cIpMacBindConf 7 }


es2410cIpMacBindConfDelByMac  OBJECT-TYPE
    SYNTAX      DisplayString
    MAX-ACCESS      read-write
    STATUS      current
    DESCRIPTION
        "Delete the IP-MAC binding entry(s) by the specific MAC address."
    ::= { es2410cIpMacBindConf 8 }

es2410cIpMacBindConfDelByName  OBJECT-TYPE
    SYNTAX      DisplayString
    MAX-ACCESS      read-write
    STATUS      current
    DESCRIPTION
        "Delete the IP-MAC binding entry(s) by the specific entry name."
    ::= { es2410cIpMacBindConf 9 }

es2410cMacTableInfo          	OBJECT IDENTIFIER ::= { es2410cProduces 12 }

es2410cMacTableMaintenance       OBJECT IDENTIFIER ::= { es2410cMacTableInfo 1 }

es2410cMacTableAgingTime  OBJECT-TYPE
    SYNTAX      INTEGER(0|10..1000000)
    MAX-ACCESS  read-write
    STATUS      current
    DESCRIPTION
        "Set the Mac Table Aging Time (10~1000000 Secs).
         0 : Disable.
        "
    ::= { es2410cMacTableMaintenance 1 }

es2410cMacTableFlush  OBJECT-TYPE
    SYNTAX      INTEGER(0|1)
    MAX-ACCESS  read-write
    STATUS      current
    DESCRIPTION
        "1 : Flush Mac Table."
    ::= { es2410cMacTableMaintenance 2 }

es2410cMacTableLearnPortLimitTable  OBJECT-TYPE
    SYNTAX      SEQUENCE OF ES2410CMacTableLearnPortLimitEntry
    MAX-ACCESS  not-accessible
    STATUS      current
    DESCRIPTION
        " "
    ::= { es2410cMacTableMaintenance 3 }

es2410cMacTableLearnPortLimitEntry  OBJECT-TYPE
    SYNTAX      ES2410CMacTableLearnPortLimitEntry
    MAX-ACCESS  not-accessible
    STATUS      current
    DESCRIPTION
        "Entry(s) for Mac Table Port Learning Limit."
    INDEX {es2410cMacTableLearnPortLimitIndex}
    ::= { es2410cMacTableLearnPortLimitTable 1 }

ES2410CMacTableLearnPortLimitEntry ::=
SEQUENCE {
    es2410cMacTableLearnPortLimitIndex   INTEGER,
    es2410cMacTableLearnPortLimit       	INTEGER
}

es2410cMacTableLearnPortLimitIndex  OBJECT-TYPE
    SYNTAX      INTEGER(1..10)
    MAX-ACCESS      read-only
    STATUS      current
    DESCRIPTION
        "The index of the Mac Table Learning Limit entry."
    ::= { es2410cMacTableLearnPortLimitEntry 1 }

es2410cMacTableLearnPortLimit  OBJECT-TYPE
    SYNTAX      INTEGER(0..8191)
    MAX-ACCESS  read-write
    STATUS      current
    DESCRIPTION
        "Port Learning Limit (0~8191)."
    ::= { es2410cMacTableLearnPortLimitEntry 2 }

es2410cMacTableStaticMac      OBJECT IDENTIFIER ::= { es2410cMacTableInfo 2 }

es2410cMacTableStaticMacNumber  OBJECT-TYPE
    SYNTAX      INTEGER(0..1024)
    MAX-ACCESS  read-write
    STATUS      current
    DESCRIPTION
        "Static Mac Total Nnumber(0~1024)."
    ::= { es2410cMacTableStaticMac 1 }

es2410cMacTableStaticMacTable  OBJECT-TYPE
    SYNTAX      SEQUENCE OF ES2410CMacTableStaticMacEntry
    MAX-ACCESS  not-accessible
    STATUS      current
    DESCRIPTION
        " "
    ::= { es2410cMacTableStaticMac 2 }

es2410cMacTableStaticMacEntry  OBJECT-TYPE
    SYNTAX      ES2410CMacTableStaticMacEntry
    MAX-ACCESS  not-accessible
    STATUS      current
    DESCRIPTION
        "Entry(s) for Static Mac Table."
    INDEX {es2410cMacTableStaticMacIndex}
    ::= { es2410cMacTableStaticMacTable 1 }

ES2410CMacTableStaticMacEntry ::=
SEQUENCE {
    es2410cMacTableStaticMacIndex	INTEGER,
    es2410cMacTableStaticMacAddress   	MacAddress,
    es2410cMacTableStaticMacVid       	INTEGER,
    es2410cMacTableStaticMacRule       	INTEGER,
    es2410cMacTableStaticMacPort       	INTEGER
}

es2410cMacTableStaticMacIndex  OBJECT-TYPE
    SYNTAX      INTEGER(1..1024)
    MAX-ACCESS  not-accessible
    STATUS      current
    DESCRIPTION
        "The index of the static mac table entry."
    ::= { es2410cMacTableStaticMacEntry 1 }

es2410cMacTableStaticMacAddress  OBJECT-TYPE
    SYNTAX      MacAddress
    MAX-ACCESS  read-only
    STATUS      current
    DESCRIPTION
        "The mac address of the static mac table entry."
    ::= { es2410cMacTableStaticMacEntry 2 }

es2410cMacTableStaticMacVid  OBJECT-TYPE
    SYNTAX      INTEGER(1..4094)
    MAX-ACCESS  read-only
    STATUS      current
    DESCRIPTION
        "The vlan id of the static mac table entry."
    ::= { es2410cMacTableStaticMacEntry 3 }

es2410cMacTableStaticMacRule  OBJECT-TYPE
    SYNTAX      INTEGER(0..2)
    MAX-ACCESS  read-only
    STATUS      current
    DESCRIPTION
        "The forwarding rule of the static mac table entry.
         0 : static,
         1 : Static with Destination Drop,
         2 : Static with Source Drop
        "
    ::= { es2410cMacTableStaticMacEntry 4 }

es2410cMacTableStaticMacPort  OBJECT-TYPE
    SYNTAX      INTEGER(1..10)
    MAX-ACCESS  read-only
    STATUS      current
    DESCRIPTION
        "The port of the static mac table entry."
    ::= { es2410cMacTableStaticMacEntry 5 }


es2410cMacTableStaticMacConfig       OBJECT IDENTIFIER ::= { es2410cMacTableInfo 3 }

es2410cMacTableStaticMacAddMac  OBJECT-TYPE
    SYNTAX      DisplayString
    MAX-ACCESS  read-write
    STATUS      current
    DESCRIPTION
        "Add static mac address in temp."
    ::= { es2410cMacTableStaticMacConfig 1 }

es2410cMacTableStaticMacAddVid  OBJECT-TYPE
    SYNTAX      INTEGER(1..4094)
    MAX-ACCESS  read-write
    STATUS      current
    DESCRIPTION
        "Add vid in temp."
    ::= { es2410cMacTableStaticMacConfig 2 }

es2410cMacTableStaticMacAddRule  OBJECT-TYPE
    SYNTAX      INTEGER(0..2)
    MAX-ACCESS  read-write
    STATUS      current
    DESCRIPTION
        "Add forwarding rule in temp.
         0 : static,
         1 : Static with Destination Drop,
         2 : Static with Source Drop
        "
    ::= { es2410cMacTableStaticMacConfig 3 }

es2410cMacTableStaticMacAddPort  OBJECT-TYPE
    SYNTAX      INTEGER(1..10)
    MAX-ACCESS  read-write
    STATUS      current
    DESCRIPTION
        "Add port in temp."
    ::= { es2410cMacTableStaticMacConfig 4 }

es2410cMacTableStaticMacAddDo  OBJECT-TYPE
    SYNTAX      INTEGER(0|1)
    MAX-ACCESS  read-write
    STATUS      current
    DESCRIPTION
        "Add this temp in Static Mac Table."
    ::= { es2410cMacTableStaticMacConfig 5 }

es2410cMacTableStaticMacDeleteMac  OBJECT-TYPE
    SYNTAX      DisplayString
    MAX-ACCESS  read-write
    STATUS      current
    DESCRIPTION
        "Delete a static mac by mac address."
    ::= { es2410cMacTableStaticMacConfig 6 }

es2410cMacTableStaticMacDeleteDo  OBJECT-TYPE
    SYNTAX      INTEGER(0|1)
    MAX-ACCESS  read-write
    STATUS      current
    DESCRIPTION
        "Delete this mac entry"
    ::= { es2410cMacTableStaticMacConfig 7 }

es2410cMacTableMacAlias       OBJECT IDENTIFIER ::= { es2410cMacTableInfo 4 }

es2410cMacTableMacAliasNumber  OBJECT-TYPE
    SYNTAX      INTEGER(0..1024)
    MAX-ACCESS  read-write
    STATUS      current
    DESCRIPTION
        "Mac Alias Total Nnumber(0~1024)."
    ::= { es2410cMacTableMacAlias 1 }

es2410cMacTableMacAliasTable  OBJECT-TYPE
    SYNTAX      SEQUENCE OF ES2410CMacTableMacAliasEntry
    MAX-ACCESS  not-accessible
    STATUS      current
    DESCRIPTION
        " "
    ::= { es2410cMacTableMacAlias 2 }

es2410cMacTableMacAliasEntry OBJECT-TYPE
    SYNTAX      ES2410CMacTableMacAliasEntry
    MAX-ACCESS  not-accessible
    STATUS      current
    DESCRIPTION
        "Entry(s) for Mac Alias."
    INDEX {es2410cMacTableMacAliasIndex}
    ::= { es2410cMacTableMacAliasTable 1 }

ES2410CMacTableMacAliasEntry ::=
SEQUENCE {
    es2410cMacTableMacAliasIndex		INTEGER,
    es2410cMacTableMacAliasAddress   	MacAddress,
    es2410cMacTableMacAliasAlias       	DisplayString
}

es2410cMacTableMacAliasIndex  OBJECT-TYPE
    SYNTAX      INTEGER(1..1024)
    MAX-ACCESS  not-accessible
    STATUS      current
    DESCRIPTION
        "The index of the static mac alias entry."
    ::= { es2410cMacTableMacAliasEntry 1 }

es2410cMacTableMacAliasAddress  OBJECT-TYPE
    SYNTAX      MacAddress
    MAX-ACCESS  read-only
    STATUS      current
    DESCRIPTION
        "The mac address of the mac alias table entry."
    ::= { es2410cMacTableMacAliasEntry 2 }

es2410cMacTableMacAliasAlias  OBJECT-TYPE
    SYNTAX      DisplayString
    MAX-ACCESS  read-write
    STATUS      current
    DESCRIPTION
        "The alias of the mac alias table entry."
    ::= { es2410cMacTableMacAliasEntry 3 }

es2410cMacTableMacAliasAddAddress  OBJECT-TYPE
    SYNTAX      DisplayString
    MAX-ACCESS  read-write
    STATUS      current
    DESCRIPTION
        "Add address in mac alias temp entry"
    ::= { es2410cMacTableMacAlias 3 }

es2410cMacTableMacAliasAddAlias  OBJECT-TYPE
    SYNTAX      DisplayString
    MAX-ACCESS  read-write
    STATUS      current
    DESCRIPTION
        "Add alias in mac alias temp entry "
    ::= { es2410cMacTableMacAlias 4 }

es2410cMacTableMacAliasAddDo  OBJECT-TYPE
    SYNTAX      INTEGER(0|1)
    MAX-ACCESS  read-write
    STATUS      current
    DESCRIPTION
        "Add temp entry in mac alias table.
         0 : None
         1 : Add
        "
    ::= { es2410cMacTableMacAlias 5 }

es2410cMacTableMacAliasDeleteAddress  OBJECT-TYPE
    SYNTAX      DisplayString
    MAX-ACCESS  read-write
    STATUS      current
    DESCRIPTION
        "Set the address of mac alias table that you want to delete."
    ::= { es2410cMacTableMacAlias 6 }

es2410cMacTableMacAliasDeleteDo  OBJECT-TYPE
    SYNTAX      INTEGER(0|1)
    MAX-ACCESS  read-write
    STATUS      current
    DESCRIPTION
        "Delete the mac alias entry by es2410cMacTableMacAliasDeleteAddress
         0 : None
         1 : Delete
        "
    ::= { es2410cMacTableMacAlias 7 }

es2410cSecurity          	OBJECT IDENTIFIER ::= { es2410cProduces 13 }

es2410cMirror      OBJECT IDENTIFIER ::= { es2410cSecurity 1 }

es2410cMirrorMode  OBJECT-TYPE
    SYNTAX      INTEGER(0|1)
    MAX-ACCESS  read-write
    STATUS      current
    DESCRIPTION
        "Set the Mirror Enable/Disable Mode.
         0 : Mirror Disable,
         1 : Mirror Enable.
        "
    ::= { es2410cMirror 1 }

es2410cMonitoringPort  OBJECT-TYPE
    SYNTAX      INTEGER(0..10)
    MAX-ACCESS  read-write
    STATUS      current
    DESCRIPTION
        "Set the Mirror Monitoring Port.(1~10)"
    ::= { es2410cMirror 2 }

es2410cMonitoredIngressPort  OBJECT-TYPE
    SYNTAX      DisplayString
    MAX-ACCESS  read-write
    STATUS      current
    DESCRIPTION
        "Set monitored ingress port; range syntax: 1,5-7, available from 0 to 10.
         0 : Ingress Disable,
         1~10 : Ingress Enable.
        "
    ::= { es2410cMirror 3 }

es2410cMonitoredEgressPort  OBJECT-TYPE
    SYNTAX      DisplayString
    MAX-ACCESS  read-write
    STATUS      current
    DESCRIPTION
        "Set monitored egress port; range syntax: 1,5-7, available from 0 to 10.
         0 : Egress Disable,
         1~10 : Egress Enable.
        "
    ::= { es2410cMirror 4 }

es2410cIsolatedGroup      OBJECT IDENTIFIER ::= { es2410cSecurity 2 }

es2410cIsolatedPortGroup  OBJECT-TYPE
    SYNTAX      DisplayString
    MAX-ACCESS  read-write
    STATUS      current
    DESCRIPTION
        "Set the Isolated Group; range syntax: 1,5-7, available from 0 to 10.
         0 : Isolated Group Disable,
         1~10 : Isolated Group Enable
        "
    ::= { es2410cIsolatedGroup 1 }

es2410cVirtualStack        OBJECT IDENTIFIER ::= { es2410cProduces 14 }

es2410cVirtualStackState   OBJECT-TYPE
    SYNTAX      INTEGER(0|1)
    MAX-ACCESS  read-write
    STATUS      current
    DESCRIPTION
        "Set the Virtual Stack State.
         0 : disable,
         1 : enable
        "
    ::= { es2410cVirtualStack 1 }

es2410cVirtualStackRole   OBJECT-TYPE
    SYNTAX      INTEGER(0|1)
    MAX-ACCESS  read-write
    STATUS      current
    DESCRIPTION
        "Set the Virtual Stack Role.
         0 : slave,
         1 : master
        "
    ::= { es2410cVirtualStack 2 }

es2410cVirtualStackGroupID  OBJECT-TYPE
    SYNTAX      DisplayString
    MAX-ACCESS  read-write
    STATUS      current
    DESCRIPTION
        "Set the Virtual Stack Group ID."
    ::= { es2410cVirtualStack 3 }

es2410cManagementSecurity        OBJECT IDENTIFIER ::= { es2410cProduces 15 }

es2410cManagementSecurityNumber  OBJECT-TYPE
    SYNTAX      INTEGER(0..64)
    MAX-ACCESS  read-only
    STATUS      current
    DESCRIPTION
        "The Number of Management Security Entry."
    ::= { es2410cManagementSecurity 1 }

es2410cManagementSecurityTable  OBJECT-TYPE
    SYNTAX      SEQUENCE OF ES2410CManagementSecurityEntry
    MAX-ACCESS  not-accessible
    STATUS      current
    DESCRIPTION
        " "
    ::= { es2410cManagementSecurity 2 }

es2410cManagementSecurityEntry OBJECT-TYPE
    SYNTAX      ES2410CManagementSecurityEntry
    MAX-ACCESS  not-accessible
    STATUS      current
    DESCRIPTION
        "Entry(s) for Management Security."
    INDEX {es2410cManagementSecurityIndex}
    ::= { es2410cManagementSecurityTable 1 }

ES2410CManagementSecurityEntry ::=
SEQUENCE {
    es2410cManagementSecurityIndex		INTEGER,
    es2410cManagementSecurityName   		DisplayString,
    es2410cManagementSecurityVid       		INTEGER,
    es2410cManagementSecurityIpRange   		DisplayString,
    es2410cManagementSecurityIncomigPort   	DisplayString,
    es2410cManagementSecurityAccessType		DisplayString,
    es2410cManagementSecurityAction		INTEGER,
    es2410cManagementSecurityDelete		INTEGER
}

es2410cManagementSecurityIndex  OBJECT-TYPE
    SYNTAX      INTEGER(1..64)
    MAX-ACCESS  not-accessible
    STATUS      current
    DESCRIPTION
        "The index of management security entry."
    ::= { es2410cManagementSecurityEntry 1 }

es2410cManagementSecurityName  OBJECT-TYPE
    SYNTAX      DisplayString
    MAX-ACCESS  read-only
    STATUS      current
    DESCRIPTION
        "The name of management security entry."
    ::= { es2410cManagementSecurityEntry 2 }

es2410cManagementSecurityVid  OBJECT-TYPE
    SYNTAX      INTEGER(0..4094)
    MAX-ACCESS  read-write
    STATUS      current
    DESCRIPTION
        "The vid of management security entry.
         vid 0 : Any.
        "
    ::= { es2410cManagementSecurityEntry 3 }

es2410cManagementSecurityIpRange  OBJECT-TYPE
    SYNTAX      DisplayString
    MAX-ACCESS  read-write
    STATUS      current
    DESCRIPTION
        "The ip range of management security entry(StartIP-EndIP).
         ex : 192.168.1.1-192.168.1.255,
         0 : any.
        "
    ::= { es2410cManagementSecurityEntry 4 }

es2410cManagementSecurityIncomigPort  OBJECT-TYPE
    SYNTAX      DisplayString
    MAX-ACCESS  read-write
    STATUS      current
    DESCRIPTION
        "The incoming Port of management security entry.
         range syntax: 1,5-7, available from 0 to 10,
         0 : Any.
        "
    ::= { es2410cManagementSecurityEntry 5 }

es2410cManagementSecurityAccessType  OBJECT-TYPE
    SYNTAX      DisplayString
    MAX-ACCESS  read-write
    STATUS      current
    DESCRIPTION
        "The access type of management security entry.
         range syntax: 1,3 or 1-3, available from 0 to 3.
         0 : Any,
         1 : http,
         2 : telnet,
         3 : snmp
        "
    ::= { es2410cManagementSecurityEntry 6 }

es2410cManagementSecurityAction  OBJECT-TYPE
    SYNTAX      INTEGER(0|1)
    MAX-ACCESS  read-write
    STATUS      current
    DESCRIPTION
        "The action of management security entry.
         0 : deny,
         1 : accept.
        "
    ::= { es2410cManagementSecurityEntry 7 }

es2410cManagementSecurityDelete  OBJECT-TYPE
    SYNTAX      INTEGER(0|1)
    MAX-ACCESS  read-write
    STATUS      current
    DESCRIPTION
        "0 : None,
         1 : Delete this entry.
        "
    ::= { es2410cManagementSecurityEntry 8 }

es2410cManagementSecurityAddName  OBJECT-TYPE
    SYNTAX      DisplayString
    MAX-ACCESS  read-write
    STATUS      current
    DESCRIPTION
        "set name of management security new entry."
    ::= { es2410cManagementSecurity 3 }

es2410cManagementSecurityAddVid  OBJECT-TYPE
    SYNTAX      INTEGER(0..4094)
    MAX-ACCESS  read-write
    STATUS      current
    DESCRIPTION
        "set vid of management security new entry.
         vid 0 : Any.
        "
    ::= { es2410cManagementSecurity 4 }

es2410cManagementSecurityAddIpRange  OBJECT-TYPE
    SYNTAX      DisplayString
    MAX-ACCESS  read-write
    STATUS      current
    DESCRIPTION
         "Set ip range of management security new entry(StartIP-EndIP).
          ex : 192.168.1.1-192.168.1.255,
          0 : any.
         "
    ::= { es2410cManagementSecurity 5 }

es2410cManagementSecurityAddIncomigPort  OBJECT-TYPE
    SYNTAX      DisplayString
    MAX-ACCESS  read-write
    STATUS      current
    DESCRIPTION
        "Set incoming Port of management security new entry.
         range syntax: 1,5-7, available from 0 to 10,
         0 : Any.
        "
    ::= { es2410cManagementSecurity 6 }

es2410cManagementSecurityAddAccessType  OBJECT-TYPE
    SYNTAX      DisplayString
    MAX-ACCESS  read-write
    STATUS      current
    DESCRIPTION
        "Set access type of management security new entry.
         range syntax: 1,3 or 1-3, available from 0 to 3.
         0 : Any,
         1 : http,
         2 : telnet,
         3 : snmp
        "
    ::= { es2410cManagementSecurity 7 }

es2410cManagementSecurityAddAction  OBJECT-TYPE
    SYNTAX      INTEGER(0|1)
    MAX-ACCESS  read-write
    STATUS      current
    DESCRIPTION
        "Set action of management security new entry.
         0 : deny,
         1 : accept.
        "
    ::= { es2410cManagementSecurity 8 }

es2410cManagementSecurityAddDo  OBJECT-TYPE
    SYNTAX      INTEGER(0|1)
    MAX-ACCESS  read-write
    STATUS      current
    DESCRIPTION
        "Add management security new entry.
         0 : not add,
         1 : add.
        "
    ::= { es2410cManagementSecurity 9 }

es2410cQoS       OBJECT IDENTIFIER ::= { es2410cProduces 16 }

es2410cQoSGlobalConfig      OBJECT IDENTIFIER ::= { es2410cQoS 1 }

es2410cQoSMode OBJECT-TYPE
    SYNTAX      INTEGER(0|1)
    MAX-ACCESS  read-write
    STATUS      current
    DESCRIPTION
        "Set the Qos Mode Enable/Disable.
         0 : Disable,
         1 : Enable.
        "
    ::= { es2410cQoSGlobalConfig 1 }

es2410cQoS1PEnable OBJECT-TYPE
    SYNTAX      INTEGER(0|1)
    MAX-ACCESS  read-write
    STATUS      current
    DESCRIPTION
        "Set the Qos 802.1P Enable/Disable.
         0 : Disable,
         1 : Enable.
        "
    ::= { es2410cQoSGlobalConfig 2 }

es2410cQoSDSCPEnable OBJECT-TYPE
    SYNTAX      INTEGER(0|1)
    MAX-ACCESS  read-write
    STATUS      current
    DESCRIPTION
        "Set the Qos DSCP Enable/Disable.
         0 : Disable,
         1 : Enable.
        "
    ::= { es2410cQoSGlobalConfig 3 }

es2410cQoSSchedulingMethod OBJECT-TYPE
    SYNTAX      INTEGER(0..3)
    MAX-ACCESS  read-write
    STATUS      current
    DESCRIPTION
        "Set the Qos Scheduling Method(0~3).
	 0 : 4 WRR
	 1 : 1 Strict, 3 WRR
	 2 : 2 Strict, 2 WRR
	 3 : 4 Strict
        "
    ::= { es2410cQoSGlobalConfig 4 }

es2410cQoSWeightQ0 OBJECT-TYPE
    SYNTAX      INTEGER(1..55)
    MAX-ACCESS  read-write
    STATUS      current
    DESCRIPTION
        "Set the Qos Queue 0 Weight(1~55)."
    ::= { es2410cQoSGlobalConfig 5 }

es2410cQoSWeightQ1 OBJECT-TYPE
    SYNTAX      INTEGER(1..55)
    MAX-ACCESS  read-write
    STATUS      current
    DESCRIPTION
        "Set the Qos Queue 1 Weight(1~55)."
    ::= { es2410cQoSGlobalConfig 6 }

es2410cQoSWeightQ2 OBJECT-TYPE
    SYNTAX      INTEGER(1..55)
    MAX-ACCESS  read-write
    STATUS      current
    DESCRIPTION
        "Set the Qos Queue 2 Weight(1~55)."
    ::= { es2410cQoSGlobalConfig 7 }

es2410cQoSWeightQ3 OBJECT-TYPE
    SYNTAX      INTEGER(1..55)
    MAX-ACCESS  read-write
    STATUS      current
    DESCRIPTION
        "Set the Qos Queue 3 Weight(1~55)."
    ::= { es2410cQoSGlobalConfig 8 }

es2410cQoS1PPriority      OBJECT IDENTIFIER ::= { es2410cQoS 2 }

es2410cQoS1PPriorityTable  OBJECT-TYPE
    SYNTAX      SEQUENCE OF ES2410CQoS1PPriorityEntry
    MAX-ACCESS  not-accessible
    STATUS      current
    DESCRIPTION
        " "
    ::= { es2410cQoS1PPriority 1 }

es2410cQoS1PPriorityEntry OBJECT-TYPE
    SYNTAX      ES2410CQoS1PPriorityEntry
    MAX-ACCESS  not-accessible
    STATUS      current
    DESCRIPTION
        "Entry(s) for QoS 802.1P Priority."
    INDEX {es2410cQoS1PPriorityIndex}
    ::= { es2410cQoS1PPriorityTable 1 }

ES2410CQoS1PPriorityEntry ::=
SEQUENCE {
    es2410cQoS1PPriorityIndex		INTEGER,
    es2410cQoS1PPriorityValue		INTEGER,
    es2410cQoS1PPriorityQueue   		INTEGER
}

es2410cQoS1PPriorityIndex  OBJECT-TYPE
    SYNTAX      INTEGER(1..8)
    MAX-ACCESS  not-accessible
    STATUS      current
    DESCRIPTION
        "The Priority index of QoS 802.1P Priority entry."
    ::= { es2410cQoS1PPriorityEntry 1 }

es2410cQoS1PPriorityValue  OBJECT-TYPE
    SYNTAX      INTEGER(0..7)
    MAX-ACCESS  read-only
    STATUS      current
    DESCRIPTION
        "The Priority value of QoS 802.1P Priority entry."
    ::= { es2410cQoS1PPriorityEntry 2 }

es2410cQoS1PPriorityQueue  OBJECT-TYPE
    SYNTAX      INTEGER(0..3)
    MAX-ACCESS  read-write
    STATUS      current
    DESCRIPTION
        "The Queue(0~3) of QoS 802.1P Priority."
    ::= { es2410cQoS1PPriorityEntry 3 }

es2410cQoSDSCPPriority      OBJECT IDENTIFIER ::= { es2410cQoS 3 }

es2410cQoSDSCPPriorityTable  OBJECT-TYPE
    SYNTAX      SEQUENCE OF ES2410CQoSDSCPPriorityEntry
    MAX-ACCESS  not-accessible
    STATUS      current
    DESCRIPTION
        " "
    ::= { es2410cQoSDSCPPriority 1 }

es2410cQoSDSCPPriorityEntry OBJECT-TYPE
    SYNTAX      ES2410CQoSDSCPPriorityEntry
    MAX-ACCESS  not-accessible
    STATUS      current
    DESCRIPTION
        "Entry(s) for QoS DSCP Priority."
    INDEX {es2410cQoSDSCPPriorityIndex}
    ::= { es2410cQoSDSCPPriorityTable 1 }

ES2410CQoSDSCPPriorityEntry ::=
SEQUENCE {
    es2410cQoSDSCPPriorityIndex		INTEGER,
    es2410cQoSDSCPPriorityValue		INTEGER,
    es2410cQoSDSCPPriorityQueue   	INTEGER
}

es2410cQoSDSCPPriorityIndex  OBJECT-TYPE
    SYNTAX      INTEGER(1..64)
    MAX-ACCESS  not-accessible
    STATUS      current
    DESCRIPTION
        "The Priority index of QoS DSCP Priority entry."
    ::= { es2410cQoSDSCPPriorityEntry 1 }

es2410cQoSDSCPPriorityValue  OBJECT-TYPE
    SYNTAX      INTEGER(0..3)
    MAX-ACCESS  read-only
    STATUS      current
    DESCRIPTION
        "The Priority value of QoS DSCP Priority entry."
    ::= { es2410cQoSDSCPPriorityEntry 2 }

es2410cQoSDSCPPriorityQueue  OBJECT-TYPE
    SYNTAX      INTEGER(0..3)
    MAX-ACCESS  read-write
    STATUS      current
    DESCRIPTION
        "The Queue(0~3) of QoS DSCP Priority."
    ::= { es2410cQoSDSCPPriorityEntry 3 }

es2410cVlan      OBJECT IDENTIFIER ::= { es2410cProduces 17 }

es2410cVlanModeConfig      OBJECT IDENTIFIER ::= { es2410cVlan 1 }

es2410cVlanMode  OBJECT-TYPE
    SYNTAX      INTEGER(0..2)
    MAX-ACCESS  read-write
    STATUS      current
    DESCRIPTION
        "0:Tag-based, 1:Port-based, 2:Metro mode"
    ::= { es2410cVlanModeConfig 1 }

es2410cSymmetricVlan  OBJECT-TYPE
    SYNTAX      INTEGER(0|1)
    MAX-ACCESS  read-write
    STATUS      current
    DESCRIPTION
        "0:disable, 1:enable"
    ::= { es2410cVlanModeConfig 2 }

es2410cVlanSVL  OBJECT-TYPE
    SYNTAX      INTEGER(0|1)
    MAX-ACCESS  read-write
    STATUS      current
    DESCRIPTION
        "0:disable, 1:enable"
    ::= { es2410cVlanModeConfig 3 }

es2410cDoubleTag  OBJECT-TYPE
    SYNTAX      INTEGER(0..2)
    MAX-ACCESS  read-write
    STATUS      current
    DESCRIPTION
        "0 : disable,
         1 : enable SP-tag 0x88A8,
         2 : enable SP-tag 0x8100
        "
    ::= { es2410cVlanModeConfig 4 }

es2410cSpPortMember  OBJECT-TYPE
    SYNTAX      DisplayString
    MAX-ACCESS  read-write
    STATUS      current
    DESCRIPTION
        "The member of Service Provider Port.
         Port range syntax: 1,5-7, available from 1 to 10
        "
    ::= { es2410cVlanModeConfig 5 }

es2410cUpLinkPort  OBJECT-TYPE
    SYNTAX      INTEGER(0..2)
    MAX-ACCESS  read-write
    STATUS      current
    DESCRIPTION
        "0:Port 9, 1:Port 10, 2:Port 9 & 10"
    ::= { es2410cVlanModeConfig 6 }

es2410cVlanPvid      OBJECT IDENTIFIER ::= { es2410cVlan 2 }

es2410cVlanPvidTable  OBJECT-TYPE
    SYNTAX      SEQUENCE OF ES2410CVlanPvidEntry
    MAX-ACCESS  not-accessible
    STATUS      current
    DESCRIPTION
        " "
    ::= { es2410cVlanPvid 1 }

es2410cVlanPvidEntry OBJECT-TYPE
    SYNTAX      ES2410CVlanPvidEntry
    MAX-ACCESS  not-accessible
    STATUS      current
    DESCRIPTION
        "Entry(s) for Vlan Pvid."
    INDEX {es2410cVlanPvidPort}
    ::= { es2410cVlanPvidTable 1 }

ES2410CVlanPvidEntry ::=
SEQUENCE {
    es2410cVlanPvidPort				INTEGER,
    es2410cVlanPvidValue   			INTEGER,
    es2410cVlanPvidDefaultPriority      		INTEGER,
    es2410cVlanPvidDropUntag   			INTEGER
}

es2410cVlanPvidPort  OBJECT-TYPE
    SYNTAX      INTEGER(1..10)
    MAX-ACCESS  not-accessible
    STATUS      current
    DESCRIPTION
        "The port number of pvid entry."
    ::= { es2410cVlanPvidEntry 1 }

es2410cVlanPvidValue  OBJECT-TYPE
    SYNTAX      INTEGER(1..4094)
    MAX-ACCESS  read-write
    STATUS      current
    DESCRIPTION
        "The pvid value of port."
    ::= { es2410cVlanPvidEntry 2 }

es2410cVlanPvidDefaultPriority  OBJECT-TYPE
    SYNTAX      INTEGER(0..7)
    MAX-ACCESS  read-write
    STATUS      current
    DESCRIPTION
        "The default priority of port ."
    ::= { es2410cVlanPvidEntry 3 }

es2410cVlanPvidDropUntag  OBJECT-TYPE
    SYNTAX      INTEGER(0..7)
    MAX-ACCESS  read-write
    STATUS      current
    DESCRIPTION
        "The drop untag of port ."
    ::= { es2410cVlanPvidEntry 4 }

es2410cPortBasedVlanGroup      OBJECT IDENTIFIER ::= { es2410cVlan 3 }

es2410cPortBasedVlanNumbers  OBJECT-TYPE
    SYNTAX      INTEGER(1..10)
    MAX-ACCESS  read-only
    STATUS      current
    DESCRIPTION
        "Total numbers for tag-based vlan."
    ::= { es2410cPortBasedVlanGroup 1 }

es2410cPortBasedCreateStatus  OBJECT-TYPE
    SYNTAX      INTEGER(0|1)
    MAX-ACCESS  read-write
    STATUS      current
    DESCRIPTION
        "Creat a temp vlan in port-based vlan table.
         0 : none,
         1 : creat a new port-based vlan.
        "
    ::= { es2410cPortBasedVlanGroup 2 }

es2410cPortBasedVlanTable  OBJECT-TYPE
    SYNTAX      SEQUENCE OF ES2410CPortBasedVlanEntry
    MAX-ACCESS  not-accessible
    STATUS      current
    DESCRIPTION
        " "
    ::= { es2410cPortBasedVlanGroup 3 }

es2410cPortBasedVlanEntry OBJECT-TYPE
    SYNTAX      ES2410CPortBasedVlanEntry
    MAX-ACCESS  not-accessible
    STATUS      current
    DESCRIPTION
        "Entry(s) for port-based vlan table."
    INDEX {es2410cPortBasedVlanIndex}
    ::= { es2410cPortBasedVlanTable 1 }

ES2410CPortBasedVlanEntry ::=
SEQUENCE {
    es2410cPortBasedVlanIndex				INTEGER,
    es2410cPortBasedVlanName   				DisplayString,
    es2410cPortBasedVlanMember  				DisplayString,
    es2410cPortBasedVlanRowStatus			INTEGER
}

es2410cPortBasedVlanIndex  OBJECT-TYPE
    SYNTAX      INTEGER(1..10)
    MAX-ACCESS  not-accessible
    STATUS      current
    DESCRIPTION
        "The index of vlan."
    ::= { es2410cPortBasedVlanEntry 1 }

es2410cPortBasedVlanName  OBJECT-TYPE
    SYNTAX      DisplayString
    MAX-ACCESS  read-write
    STATUS      current
    DESCRIPTION
        "The name of vlan."
    ::= { es2410cPortBasedVlanEntry 2 }

es2410cPortBasedVlanMember  OBJECT-TYPE
    SYNTAX      DisplayString
    MAX-ACCESS  read-write
    STATUS      current
    DESCRIPTION
        "The member of vlan."
    ::= { es2410cPortBasedVlanEntry 3 }

es2410cPortBasedVlanRowStatus  OBJECT-TYPE
    SYNTAX      INTEGER(1..3)
    MAX-ACCESS  read-write
    STATUS      current
    DESCRIPTION
        "The row status of vlan.
         1 : active,
         2 : not-inService,
         3 : delete
        "
    ::= { es2410cPortBasedVlanEntry 4 }

es2410cManagementVlan      OBJECT IDENTIFIER ::= { es2410cVlan 4 }

es2410cManagementVlanState  OBJECT-TYPE
    SYNTAX      INTEGER(0|1)
    MAX-ACCESS  read-write
    STATUS      current
    DESCRIPTION
        "The stat of management vlan.
         0 : Disable,
         1 : Enable.
        "
    ::= { es2410cManagementVlan 1 }

es2410cManagementVlanVid  OBJECT-TYPE
    SYNTAX      INTEGER(1..4094)
    MAX-ACCESS  read-write
    STATUS      current
    DESCRIPTION
        "The vid value of management vlan."
    ::= { es2410cManagementVlan 2 }

es2410cDhcpSnooping        OBJECT IDENTIFIER ::= { es2410cProduces 18 }

es2410cDhcpSnoopingConf      OBJECT IDENTIFIER ::= { es2410cDhcpSnooping 1 }

es2410cDhcpSnoopingState OBJECT-TYPE
    SYNTAX         INTEGER(0|1)
    MAX-ACCESS     read-write
    STATUS         current
    DESCRIPTION
        "Set DHCP Snooping State.
         0 : Disable,
         1 : Enable.
         When DHCP Relay is already running. Please disable DHCP Relay first, and then enable DHCP Snooping again.
        "
    ::= { es2410cDhcpSnoopingConf 1 }

es2410cDhcpSnoopingPortCountSetupTable  OBJECT-TYPE
    SYNTAX      SEQUENCE OF ES2410CDhcpSnoopingPortCountSetupEntry
    MAX-ACCESS  not-accessible
    STATUS      current
    DESCRIPTION
        " "
    ::= { es2410cDhcpSnoopingConf 2 }

es2410cDhcpSnoopingPortCountSetupEntry OBJECT-TYPE
    SYNTAX      ES2410CDhcpSnoopingPortCountSetupEntry
    MAX-ACCESS  not-accessible
    STATUS      current
    DESCRIPTION
        "Entry(s) for DHCP snooping port count table."
    INDEX {es2410cDhcpSnoopingPortCountSetupPortIndex}
    ::= { es2410cDhcpSnoopingPortCountSetupTable 1 }

ES2410CDhcpSnoopingPortCountSetupEntry ::=
SEQUENCE {
    es2410cDhcpSnoopingPortCountSetupPortIndex		INTEGER,
    es2410cDhcpSnoopingPortCountSetupCount		INTEGER
}

es2410cDhcpSnoopingPortCountSetupPortIndex  OBJECT-TYPE
    SYNTAX      INTEGER(1..10)
    MAX-ACCESS  not-accessible
    STATUS      current
    DESCRIPTION
        "The port index of DHCP snooping port count table."
    ::= { es2410cDhcpSnoopingPortCountSetupEntry 1 }

es2410cDhcpSnoopingPortCountSetupCount OBJECT-TYPE
    SYNTAX         INTEGER(0..512)
    MAX-ACCESS     read-write
    STATUS         current
    DESCRIPTION
        "Set client-count. Limit range from 0 to 512. 0 for disable."
    ::= { es2410cDhcpSnoopingPortCountSetupEntry 2 }

es2410cDhcpSnoopingTrustGroupConf     OBJECT IDENTIFIER ::= { es2410cDhcpSnooping 2 }

es2410cDhcpSnoopingTrustGroupNumbers OBJECT-TYPE
    SYNTAX         INTEGER(0..128)
    MAX-ACCESS     read-only
    STATUS         current
    DESCRIPTION
        "Numbers of DHCP snooping trust group"
    ::= { es2410cDhcpSnoopingTrustGroupConf 1 }

es2410cDhcpSnoopingTrustGroupCreatStatus OBJECT-TYPE
    SYNTAX         INTEGER(1..4094)
    MAX-ACCESS     read-write
    STATUS         current
    DESCRIPTION
        "Creat a temp trust group in table.
         range : 1~4094"
    ::= { es2410cDhcpSnoopingTrustGroupConf 2 }

es2410cDhcpSnoopingTrustGroupTable  OBJECT-TYPE
    SYNTAX      SEQUENCE OF ES2410CDhcpSnoopingTrustGroupEntry
    MAX-ACCESS  not-accessible
    STATUS      current
    DESCRIPTION
        " "
    ::= { es2410cDhcpSnoopingTrustGroupConf 3 }

es2410cDhcpSnoopingTrustGroupEntry OBJECT-TYPE
    SYNTAX      ES2410CDhcpSnoopingTrustGroupEntry
    MAX-ACCESS  not-accessible
    STATUS      current
    DESCRIPTION
        "Entry(s) for DHCP snooping trust group table."
    INDEX {es2410cDhcpSnoopingTrustGroupIndex}
    ::= { es2410cDhcpSnoopingTrustGroupTable 1 }

ES2410CDhcpSnoopingTrustGroupEntry ::=
SEQUENCE {
    es2410cDhcpSnoopingTrustGroupIndex			INTEGER,
    es2410cDhcpSnoopingTrustGroupTrustVid		INTEGER,
    es2410cDhcpSnoopingTrustGroupOption82		INTEGER,
    es2410cDhcpSnoopingTrustGroupAction			INTEGER,
    es2410cDhcpSnoopingTrustGroupServerPort		DisplayString,
    es2410cDhcpSnoopingTrustGroupServerVid		INTEGER,
    es2410cDhcpSnoopingTrustGroupServerIp		IpAddress,
    es2410cDhcpSnoopingTrustGroupRowStatus		INTEGER
}

es2410cDhcpSnoopingTrustGroupIndex  OBJECT-TYPE
    SYNTAX      INTEGER(1..4095)
    MAX-ACCESS  not-accessible
    STATUS      current
    DESCRIPTION
        "The index of DHCP snooping trust group table."
    ::= { es2410cDhcpSnoopingTrustGroupEntry 1 }

es2410cDhcpSnoopingTrustGroupTrustVid OBJECT-TYPE
    SYNTAX         INTEGER(1..4094)
    MAX-ACCESS     read-write
    STATUS         current
    DESCRIPTION
        "Trust Vid in turst group.
         range : 1~4094."
    ::= { es2410cDhcpSnoopingTrustGroupEntry 2 }

es2410cDhcpSnoopingTrustGroupOption82 OBJECT-TYPE
    SYNTAX         INTEGER(0|1)
    MAX-ACCESS     read-write
    STATUS         current
    DESCRIPTION
        "Option82 state in turst group.
         0 : Disable,
         1 : Enable."
    ::= { es2410cDhcpSnoopingTrustGroupEntry 3 }

es2410cDhcpSnoopingTrustGroupAction OBJECT-TYPE
    SYNTAX         INTEGER(0..2)
    MAX-ACCESS     read-write
    STATUS         current
    DESCRIPTION
        "Action in turst group.
         0 : Replace,
         1 : Keep,
         2 : Drop."
    ::= { es2410cDhcpSnoopingTrustGroupEntry 4 }

es2410cDhcpSnoopingTrustGroupServerPort OBJECT-TYPE
    SYNTAX         DisplayString
    MAX-ACCESS     read-write
    STATUS         current
    DESCRIPTION
        "Trust port in turst group.
         Trust port with range format, max port 2 ports"
    ::= { es2410cDhcpSnoopingTrustGroupEntry 5 }

es2410cDhcpSnoopingTrustGroupServerVid OBJECT-TYPE
    SYNTAX         INTEGER(1..4094)
    MAX-ACCESS     read-write
    STATUS         current
    DESCRIPTION
        "Server Vid in turst group.
         range : 1~4094."
    ::= { es2410cDhcpSnoopingTrustGroupEntry 6 }

es2410cDhcpSnoopingTrustGroupServerIp OBJECT-TYPE
    SYNTAX         IpAddress
    MAX-ACCESS     read-write
    STATUS         current
    DESCRIPTION
        "Server ip in turst group."
    ::= { es2410cDhcpSnoopingTrustGroupEntry 7 }

es2410cDhcpSnoopingTrustGroupRowStatus  OBJECT-TYPE
    SYNTAX      INTEGER(1..3)
    MAX-ACCESS  read-write
    STATUS      current
    DESCRIPTION
        "The row status of trust group.
         1 : active,
         2 : not-inService,
         3 : delete
        "
    ::= { es2410cDhcpSnoopingTrustGroupEntry 8 }

es2410cDhcpSnoopingDefaultGroupConf     OBJECT IDENTIFIER ::= { es2410cDhcpSnooping 3 }

es2410cDhcpSnoopingDefaultGroupServerPort OBJECT-TYPE
    SYNTAX         DisplayString
    MAX-ACCESS     read-write
    STATUS         current
    DESCRIPTION
        "Server port in default turst group.
         Server port with range format, max port 2 ports, 0 for disabled"
    ::= { es2410cDhcpSnoopingDefaultGroupConf 1 }

es2410cDhcpSnoopingDefaultGroupServerVid OBJECT-TYPE
    SYNTAX         INTEGER(1..4094)
    MAX-ACCESS     read-write
    STATUS         current
    DESCRIPTION
        "Server Vid in default turst group.
         range : 1~4094."
    ::= { es2410cDhcpSnoopingDefaultGroupConf 2 }

es2410cDhcpSnoopingDefaultGroupOption82 OBJECT-TYPE
    SYNTAX         INTEGER(0|1)
    MAX-ACCESS     read-write
    STATUS         current
    DESCRIPTION
        "Option82 state in default turst group.
         0 : Disable,
         1 : Enable."
    ::= { es2410cDhcpSnoopingDefaultGroupConf 3 }

es2410cDhcpSnoopingDefaultGroupAction OBJECT-TYPE
    SYNTAX         INTEGER(0..2)
    MAX-ACCESS     read-write
    STATUS         current
    DESCRIPTION
        "Action in turst group.
         0 : Replace,
         1 : Keep,
         2 : Drop."
    ::= { es2410cDhcpSnoopingDefaultGroupConf 4 }

es2410cDhcpSnoopingDefaultGroupServerIp OBJECT-TYPE
    SYNTAX         IpAddress
    MAX-ACCESS     read-write
    STATUS         current
    DESCRIPTION
        "Server ip in default turst group."
    ::= { es2410cDhcpSnoopingDefaultGroupConf 5 }

es2410cDhcpSnoopingLeaseList     OBJECT IDENTIFIER ::= { es2410cDhcpSnooping 4 }

es2410cDhcpSnoopingLeaseListDeleteAll OBJECT-TYPE
    SYNTAX         INTEGER(0|1)
    MAX-ACCESS     read-write
    STATUS         current
    DESCRIPTION
        "Delete all lease list.
         0 : None,
         1 : Delete All."
    ::= { es2410cDhcpSnoopingLeaseList 1 }

es2410cDhcpSnoopingLeaseListNumbers OBJECT-TYPE
    SYNTAX         INTEGER(0..512)
    MAX-ACCESS     read-only
    STATUS         current
    DESCRIPTION
        "Numbers of lease list."
    ::= { es2410cDhcpSnoopingLeaseList 2 }

es2410cDhcpSnoopingLeaseListTable  OBJECT-TYPE
    SYNTAX      SEQUENCE OF ES2410CDhcpSnoopingLeaseListEntry
    MAX-ACCESS  not-accessible
    STATUS      current
    DESCRIPTION
        " "
    ::= { es2410cDhcpSnoopingLeaseList 3 }

es2410cDhcpSnoopingLeaseListEntry OBJECT-TYPE
    SYNTAX      ES2410CDhcpSnoopingLeaseListEntry
    MAX-ACCESS  not-accessible
    STATUS      current
    DESCRIPTION
        "Entry(s) for DHCP snooping lease list table."
    INDEX {es2410cDhcpSnoopingLeaseListIndex}
    ::= { es2410cDhcpSnoopingLeaseListTable 1 }

ES2410CDhcpSnoopingLeaseListEntry ::=
SEQUENCE {
    es2410cDhcpSnoopingLeaseListIndex			INTEGER,
    es2410cDhcpSnoopingLeaseListMac			DisplayString,
    es2410cDhcpSnoopingLeaseListIp			IpAddress,
    es2410cDhcpSnoopingLeaseListPort			INTEGER,
    es2410cDhcpSnoopingLeaseListVid			INTEGER,
    es2410cDhcpSnoopingLeaseListLease			DisplayString
}

es2410cDhcpSnoopingLeaseListIndex  OBJECT-TYPE
    SYNTAX      INTEGER(1..512)
    MAX-ACCESS  not-accessible
    STATUS      current
    DESCRIPTION
        "The index of DHCP snooping lease list table."
    ::= { es2410cDhcpSnoopingLeaseListEntry 1 }

es2410cDhcpSnoopingLeaseListMac  OBJECT-TYPE
    SYNTAX      DisplayString
    MAX-ACCESS  read-only
    STATUS      current
    DESCRIPTION
        "The MAC of DHCP snooping lease list entry."
    ::= { es2410cDhcpSnoopingLeaseListEntry 2 }

es2410cDhcpSnoopingLeaseListIp  OBJECT-TYPE
    SYNTAX      IpAddress
    MAX-ACCESS  read-only
    STATUS      current
    DESCRIPTION
        "The IP of DHCP snooping lease list entry."
    ::= { es2410cDhcpSnoopingLeaseListEntry 3 }

es2410cDhcpSnoopingLeaseListPort  OBJECT-TYPE
    SYNTAX      INTEGER(1..10)
    MAX-ACCESS  read-only
    STATUS      current
    DESCRIPTION
        "The port of DHCP snooping lease list entry."
    ::= { es2410cDhcpSnoopingLeaseListEntry 4 }

es2410cDhcpSnoopingLeaseListVid  OBJECT-TYPE
    SYNTAX      INTEGER(1..4094)
    MAX-ACCESS  read-only
    STATUS      current
    DESCRIPTION
        "The vid of DHCP snooping lease list entry."
    ::= { es2410cDhcpSnoopingLeaseListEntry 5 }

es2410cDhcpSnoopingLeaseListLease  OBJECT-TYPE
    SYNTAX      DisplayString
    MAX-ACCESS  read-only
    STATUS      current
    DESCRIPTION
        "The lease of DHCP snooping lease list entry.
         (Day:Hour:Min:Sec)"
    ::= { es2410cDhcpSnoopingLeaseListEntry 6 }

es2410cDhcpSnoopingCounter     OBJECT IDENTIFIER ::= { es2410cDhcpSnooping 5 }

es2410cDhcpSnoopingCounterReset OBJECT-TYPE
    SYNTAX         INTEGER(0|1)
    MAX-ACCESS     read-write
    STATUS         current
    DESCRIPTION
        "Reset dhcp snooptin port counter.
         0 : None,
         1 : reset."
    ::= { es2410cDhcpSnoopingCounter 1 }

es2410cDhcpSnoopingCounterTable  OBJECT-TYPE
    SYNTAX      SEQUENCE OF ES2410CDhcpSnoopingCounterEntry
    MAX-ACCESS  not-accessible
    STATUS      current
    DESCRIPTION
        " "
    ::= { es2410cDhcpSnoopingCounter 2 }

es2410cDhcpSnoopingCounterEntry OBJECT-TYPE
    SYNTAX      ES2410CDhcpSnoopingCounterEntry
    MAX-ACCESS  not-accessible
    STATUS      current
    DESCRIPTION
        "Entry(s) for DHCP snooping port counter table."
    INDEX {es2410cDhcpSnoopingCounterPortIndex}
    ::= { es2410cDhcpSnoopingCounterTable 1 }

ES2410CDhcpSnoopingCounterEntry ::=
SEQUENCE {
    es2410cDhcpSnoopingCounterPortIndex			INTEGER,
    es2410cDhcpSnoopingCounterDiscover			Counter32,
    es2410cDhcpSnoopingCounterOffer			Counter32,
    es2410cDhcpSnoopingCounterRequest			Counter32,
    es2410cDhcpSnoopingCounterDecline			Counter32,
    es2410cDhcpSnoopingCounterAck			Counter32,
    es2410cDhcpSnoopingCounterNack			Counter32,
    es2410cDhcpSnoopingCounterRelease			Counter32,
    es2410cDhcpSnoopingCounterInform			Counter32
}

es2410cDhcpSnoopingCounterPortIndex  OBJECT-TYPE
    SYNTAX      INTEGER(1..10)
    MAX-ACCESS  not-accessible
    STATUS      current
    DESCRIPTION
        "The port index of DHCP snooping port counter table."
    ::= { es2410cDhcpSnoopingCounterEntry 1 }

es2410cDhcpSnoopingCounterDiscover  OBJECT-TYPE
    SYNTAX      Counter32
    MAX-ACCESS  read-only
    STATUS      current
    DESCRIPTION
        "The discover of DHCP snooping port counter entry."
    ::= { es2410cDhcpSnoopingCounterEntry 2 }

es2410cDhcpSnoopingCounterOffer  OBJECT-TYPE
    SYNTAX      Counter32
    MAX-ACCESS  read-only
    STATUS      current
    DESCRIPTION
        "The offer of DHCP snooping port counter entry."
    ::= { es2410cDhcpSnoopingCounterEntry 3 }

es2410cDhcpSnoopingCounterRequest  OBJECT-TYPE
    SYNTAX      Counter32
    MAX-ACCESS  read-only
    STATUS      current
    DESCRIPTION
        "The request of DHCP snooping port counter entry."
    ::= { es2410cDhcpSnoopingCounterEntry 4 }

es2410cDhcpSnoopingCounterDecline  OBJECT-TYPE
    SYNTAX      Counter32
    MAX-ACCESS  read-only
    STATUS      current
    DESCRIPTION
        "The decline of DHCP snooping port counter entry."
    ::= { es2410cDhcpSnoopingCounterEntry 5 }

es2410cDhcpSnoopingCounterAck  OBJECT-TYPE
    SYNTAX      Counter32
    MAX-ACCESS  read-only
    STATUS      current
    DESCRIPTION
        "The ack of DHCP snooping port counter entry."
    ::= { es2410cDhcpSnoopingCounterEntry 6 }

es2410cDhcpSnoopingCounterNack  OBJECT-TYPE
    SYNTAX      Counter32
    MAX-ACCESS  read-only
    STATUS      current
    DESCRIPTION
        "The nack of DHCP snooping port counter entry."
    ::= { es2410cDhcpSnoopingCounterEntry 7 }

es2410cDhcpSnoopingCounterRelease  OBJECT-TYPE
    SYNTAX      Counter32
    MAX-ACCESS  read-only
    STATUS      current
    DESCRIPTION
        "The release of DHCP snooping port counter entry."
    ::= { es2410cDhcpSnoopingCounterEntry 8 }

es2410cDhcpSnoopingCounterInform  OBJECT-TYPE
    SYNTAX      Counter32
    MAX-ACCESS  read-only
    STATUS      current
    DESCRIPTION
        "The inform of DHCP snooping port counter entry."
    ::= { es2410cDhcpSnoopingCounterEntry 9 }

es2410cDot1X        OBJECT IDENTIFIER ::= { es2410cProduces 19 }

es2410cDot1XStateSetting      OBJECT IDENTIFIER ::= { es2410cDot1X 1 }

es2410cRadiusServer1 OBJECT-TYPE
    SYNTAX         IpAddress
    MAX-ACCESS     read-write
    STATUS         current
    DESCRIPTION
        "Set radius server 1 ip"
    ::= { es2410cDot1XStateSetting 1 }

es2410cDot1XPort1 OBJECT-TYPE
    SYNTAX         INTEGER(1..65535)
    MAX-ACCESS     read-write
    STATUS         current
    DESCRIPTION
        "Set 802.1X port number"
    ::= { es2410cDot1XStateSetting 2 }

es2410cRadiusServer2 OBJECT-TYPE
    SYNTAX         IpAddress
    MAX-ACCESS     read-write
    STATUS         current
    DESCRIPTION
        "Set radius server 2 ip"
    ::= { es2410cDot1XStateSetting 3 }

es2410cDot1XPort2 OBJECT-TYPE
    SYNTAX         INTEGER(1..65535)
    MAX-ACCESS     read-write
    STATUS         current
    DESCRIPTION
        "Set 802.1X port number"
    ::= { es2410cDot1XStateSetting 4 }

es2410cSecretKey1  OBJECT-TYPE
    SYNTAX         DisplayString
    MAX-ACCESS     read-write
    STATUS         current
    DESCRIPTION
        "Set 802.1X secret key"
    ::= { es2410cDot1XStateSetting 5 }

es2410cAccountingService  OBJECT-TYPE
    SYNTAX         INTEGER(0|1)
    MAX-ACCESS     read-write
    STATUS         current
    DESCRIPTION
        "Set 802.1X accounting service
         0 : disable
         1 : enable
        "
    ::= { es2410cDot1XStateSetting 6 }

es2410cAccountingServer1  OBJECT-TYPE
    SYNTAX         IpAddress
    MAX-ACCESS     read-write
    STATUS         current
    DESCRIPTION
        "Set 802.1X accounting server 1"
    ::= { es2410cDot1XStateSetting 7 }

es2410cAccountingPort1  OBJECT-TYPE
    SYNTAX         INTEGER(1..65535)
    MAX-ACCESS     read-write
    STATUS         current
    DESCRIPTION
        "Set 802.1X accounting port number"
    ::= { es2410cDot1XStateSetting 8 }

es2410cAccountingServer2  OBJECT-TYPE
    SYNTAX         IpAddress
    MAX-ACCESS     read-write
    STATUS         current
    DESCRIPTION
        "Set 802.1X accounting server 2"
    ::= { es2410cDot1XStateSetting 9 }

es2410cAccountingPort2  OBJECT-TYPE
    SYNTAX         INTEGER(1..65535)
    MAX-ACCESS     read-write
    STATUS         current
    DESCRIPTION
        "Set 802.1X accounting port number"
    ::= { es2410cDot1XStateSetting 10 }

es2410cSecretKey2  OBJECT-TYPE
    SYNTAX         DisplayString
    MAX-ACCESS     read-write
    STATUS         current
    DESCRIPTION
        "Set 802.1X secret key"
    ::= { es2410cDot1XStateSetting 11 }

es2410cDot1XPortSecurityManagement      OBJECT IDENTIFIER ::= { es2410cDot1X 2 }

es2410cDot1XPortSecurityTable  OBJECT-TYPE
    SYNTAX      SEQUENCE OF ES2410CDot1XPortSecurityEntry
    MAX-ACCESS  not-accessible
    STATUS      current
    DESCRIPTION
        " "
    ::= { es2410cDot1XPortSecurityManagement 1 }

es2410cDot1XPortSecurityEntry OBJECT-TYPE
    SYNTAX      ES2410CDot1XPortSecurityEntry
    MAX-ACCESS  not-accessible
    STATUS      current
    DESCRIPTION
        "Entry(s) for 802.1x port security management table."
    INDEX {es2410cDot1XPortSecurityPortIndex}
    ::= { es2410cDot1XPortSecurityTable 1 }

ES2410CDot1XPortSecurityEntry ::=
SEQUENCE {
    es2410cDot1XPortSecurityPortIndex				INTEGER,
    es2410cDot1XPortSecurityMode   				INTEGER,
    es2410cDot1XPortSecurityPortControl  			INTEGER,
    es2410cDot1XPortSecurityReAuthMax				INTEGER,
    es2410cDot1XPortSecurityTxPeriod				INTEGER,
    es2410cDot1XPortSecurityQuietPeriod				INTEGER,
    es2410cDot1XPortSecurityReAuthEnabled			INTEGER,
    es2410cDot1XPortSecurityReAuthPeriod				INTEGER,
    es2410cDot1XPortSecurityMaxRequest				INTEGER,
    es2410cDot1XPortSecuritySuppTimeout				INTEGER,
    es2410cDot1XPortSecurityServerTimeout			INTEGER,
    es2410cDot1XPortSecurityStatus				DisplayString
}

es2410cDot1XPortSecurityPortIndex  OBJECT-TYPE
    SYNTAX      INTEGER(1..10)
    MAX-ACCESS  not-accessible
    STATUS      current
    DESCRIPTION
        "The port index of 802.1x port security."
    ::= { es2410cDot1XPortSecurityEntry 1 }

es2410cDot1XPortSecurityMode  OBJECT-TYPE
    SYNTAX      INTEGER(0..2)
    MAX-ACCESS  read-write
    STATUS      current
    DESCRIPTION
        "The mode of 802.1x port security.
         0 : Disable,
         1 : Normal,
         2 : Advanced 802.1X
        "
    ::= { es2410cDot1XPortSecurityEntry 2 }

es2410cDot1XPortSecurityPortControl  OBJECT-TYPE
    SYNTAX      INTEGER(0..2)
    MAX-ACCESS  read-write
    STATUS      current
    DESCRIPTION
        "The port control of 802.1x port security.
	 0 : ForceUnauthorized,
	 1 : ForceAuthorized,
	 2 : Auto
        "
    ::= { es2410cDot1XPortSecurityEntry 3 }

es2410cDot1XPortSecurityReAuthMax  OBJECT-TYPE
    SYNTAX      INTEGER(1..10)
    MAX-ACCESS  read-write
    STATUS      current
    DESCRIPTION
        "The reAuthMax(1~10) of 802.1x port security."
    ::= { es2410cDot1XPortSecurityEntry 4 }

es2410cDot1XPortSecurityTxPeriod  OBJECT-TYPE
    SYNTAX      INTEGER(1..65535)
    MAX-ACCESS  read-write
    STATUS      current
    DESCRIPTION
        "The txPeriod(1~65535) of 802.1x port security."
    ::= { es2410cDot1XPortSecurityEntry 5 }

es2410cDot1XPortSecurityQuietPeriod  OBJECT-TYPE
    SYNTAX      INTEGER(0..65535)
    MAX-ACCESS  read-write
    STATUS      current
    DESCRIPTION
        "The quiet period(0~65535) of 802.1x port security."
    ::= { es2410cDot1XPortSecurityEntry 6 }

es2410cDot1XPortSecurityReAuthEnabled  OBJECT-TYPE
    SYNTAX      INTEGER(0|1)
    MAX-ACCESS  read-write
    STATUS      current
    DESCRIPTION
        "The reAuthEnabled of 802.1x port security.
         0 : off,
         1 : on.
        "
    ::= { es2410cDot1XPortSecurityEntry 7 }

es2410cDot1XPortSecurityReAuthPeriod  OBJECT-TYPE
    SYNTAX      INTEGER(1..65535)
    MAX-ACCESS  read-write
    STATUS      current
    DESCRIPTION
        "The reAuthPeriod(1~65535) of 802.1x port security."
    ::= { es2410cDot1XPortSecurityEntry 8 }

es2410cDot1XPortSecurityMaxRequest  OBJECT-TYPE
    SYNTAX      INTEGER(1..10)
    MAX-ACCESS  read-write
    STATUS      current
    DESCRIPTION
        "The max.request(1~10) of 802.1x port security."
    ::= { es2410cDot1XPortSecurityEntry 9 }

es2410cDot1XPortSecuritySuppTimeout  OBJECT-TYPE
    SYNTAX      INTEGER(1..255)
    MAX-ACCESS  read-write
    STATUS      current
    DESCRIPTION
        "The suppTimeout(1~255) of 802.1x port security."
    ::= { es2410cDot1XPortSecurityEntry 10 }

es2410cDot1XPortSecurityServerTimeout  OBJECT-TYPE
    SYNTAX      INTEGER(1..255)
    MAX-ACCESS  read-write
    STATUS      current
    DESCRIPTION
        "The server timeout(1~255) of 802.1x port security."
    ::= { es2410cDot1XPortSecurityEntry 11 }

es2410cDot1XPortSecurityStatus  OBJECT-TYPE
    SYNTAX      DisplayString
    MAX-ACCESS  read-only
    STATUS      current
    DESCRIPTION
        "The status of 802.1x port security."
    ::= { es2410cDot1XPortSecurityEntry 12 }

es2410cTrapEntry        OBJECT IDENTIFIER ::= { es2410cProduces 20 }

es2410cModuleInserted NOTIFICATION-TYPE
    OBJECTS { ifIndex }
    STATUS    current
    DESCRIPTION
        "Send the trap when a module is inserted to the system. The OID value means
         the port number."
    ::= { es2410cTrapEntry 1 }

es2410cModuleRemoved NOTIFICATION-TYPE
    OBJECTS { ifIndex }
    STATUS    current
    DESCRIPTION
        "Send the trap when a module is removed from the system. The OID value means
         the port number."
    ::= { es2410cTrapEntry 2 }

es2410cDualMediaSwapped NOTIFICATION-TYPE
    OBJECTS { ifIndex }
    STATUS    current
    DESCRIPTION
        "Send the trap when the dual media port changed. The OID value means the port number."
    ::= { es2410cTrapEntry 3 }

es2410cLoopDetected NOTIFICATION-TYPE
    OBJECTS { ifIndex }
    STATUS    current
    DESCRIPTION
        "Send the trap when loop condition has been detected. The OID value means the port number."
    ::= { es2410cTrapEntry 4 }

es2410cIpMacBindOffered NOTIFICATION-TYPE
    OBJECTS { ipmacbind }
    STATUS    current
    DESCRIPTION
        "Send the trap when a pair of IP-MAC binding is offered."
    ::= { es2410cTrapEntry 5 }

es2410cIpMacBindReleased NOTIFICATION-TYPE
    OBJECTS { ipmacbind }
    STATUS    current
    DESCRIPTION
        "Send the trap when a pair of IP-MAC binding is released."
    ::= { es2410cTrapEntry 6 }

es2410cARPInspectionDetected NOTIFICATION-TYPE
    OBJECTS { arpinspect }
    STATUS    current
    DESCRIPTION
        "Send the trap when ARP inspection detected."
    ::= { es2410cTrapEntry 7 }

es2410cStpStateDisabled NOTIFICATION-TYPE
    STATUS      current
    DESCRIPTION
       "Send the trap when the operational state of STP is from enabled to disabled. "
    ::= { es2410cTrapEntry 100 }

es2410cStpStateEnabled NOTIFICATION-TYPE
    STATUS      current
    DESCRIPTION
       "Send the trap when the operational state of STP is from disabled to enabled. "
    ::= { es2410cTrapEntry 101 }

es2410cStpTopologyChanged NOTIFICATION-TYPE
    OBJECTS { ifIndex }
    STATUS      current
    DESCRIPTION
       "Send the trap when RSTP determines a port should enter the FORWARDING state
        (a topology change occurs). The OID value is the ifIndex of the port that
        produces the topology change."
    ::= { es2410cTrapEntry 102 }

es2410cRmonRisingAlarm NOTIFICATION-TYPE
    STATUS      current
    DESCRIPTION
       "Send the trap when an RMON rising alarm happened. The OID value is the value
        of another OID variable sampled by the RMON Alarm Group that exceeds its
        own RisingThreshold "
    ::= { es2410cTrapEntry 110 }

es2410cRmonFallingAlarm NOTIFICATION-TYPE
    STATUS      current
    DESCRIPTION
           "Send the trap when an RMON falling alarm happened. The OID value is the value
        of another OID variable sampled by the RMON Alarm Group that is smaller than its
        own FallingThreshold "
    ::= { es2410cTrapEntry 111 }

es2410cLacpStateDisabled NOTIFICATION-TYPE
    OBJECTS {ifIndex, groupId}
    STATUS      current
    DESCRIPTION
       "Send the trap when the operational state of LACP is from enabled to disabled.
        The OID value means the disabled Group ID."
    ::= { es2410cTrapEntry 120 }

es2410cLacpStateEnabled NOTIFICATION-TYPE
    OBJECTS {ifIndex, groupId}
    STATUS      current
    DESCRIPTION
       "Send the trap when the operational state of LACP is from disabled to enabled.
        The OID value means the disabled Group ID."
    ::= { es2410cTrapEntry 121 }

es2410cLacpPortAdded NOTIFICATION-TYPE
    OBJECTS   { ifIndex, actorkey, partnerkey }
    STATUS      current
    DESCRIPTION
       "Send the trap when the state of port is in 'trunk ready'."
    ::= { es2410cTrapEntry 123 }

es2410cLacpPortTrunkFailure NOTIFICATION-TYPE
    OBJECTS   { ifIndex, actorkey, partnerkey}
    STATUS      current
    DESCRIPTION
       "Send the trap when one port is not able to be aggregated
        due to duplex-mode of the port. "
    ::= { es2410cTrapEntry 124 }

es2410cGvrpStateDisabled NOTIFICATION-TYPE
    STATUS      current
    DESCRIPTION
       "Send the trap when the operational state of GVRP is from enabled to disabled. "
    ::= { es2410cTrapEntry 140 }

es2410cGvrpStateEnabled NOTIFICATION-TYPE
    STATUS      current
    DESCRIPTION
       "Send the trap when the operational state of LACP is from disabled to enabled. "
    ::= { es2410cTrapEntry 141 }

es2410cVlanPortBaseEnabled NOTIFICATION-TYPE
    STATUS      current
    DESCRIPTION
       "Send the trap when the operational state of vlan is changed to port-based vlan."
    ::= { es2410cTrapEntry 151 }

es2410cVlanTagBaseEnabled NOTIFICATION-TYPE
    STATUS      current
    DESCRIPTION
       "Send the trap when the operational state of vlan is changed to tag-based vlan."
    ::= { es2410cTrapEntry 152 }

es2410cVlanMetroBaseEnabled NOTIFICATION-TYPE
    STATUS      current
    DESCRIPTION
       "Send the trap when the operational state of vlan is changed to metro-based vlan."
    ::= { es2410cTrapEntry 153 }

es2410cUserLogin NOTIFICATION-TYPE
    OBJECTS   {username}
    STATUS      current
    DESCRIPTION
       "Send the trap when one user logins the system."
    ::= { es2410cTrapEntry 200 }

es2410cUserLogout NOTIFICATION-TYPE
    OBJECTS   {username}
    STATUS      current
    DESCRIPTION
       "Send the trap when one user logouts the system."
    ::= { es2410cTrapEntry 201 }

es2410cTrapVariable  OBJECT IDENTIFIER ::= { es2410cProduces 21 }

username OBJECT-TYPE
    SYNTAX      DisplayString
    MAX-ACCESS  read-only
    STATUS      current
    DESCRIPTION
        "System account name."
    ::= { es2410cTrapVariable 1 }

groupId OBJECT-TYPE
    SYNTAX      INTEGER(1..8)
    MAX-ACCESS  read-only
    STATUS      current
    DESCRIPTION
        "The Trunk group ID of LACP."
    ::= { es2410cTrapVariable 2 }

actorkey OBJECT-TYPE
    SYNTAX  INTEGER(1..2147483647)
    MAX-ACCESS  read-only
    STATUS      current
    DESCRIPTION
        "This is the actor key information for LACP."
    ::= { es2410cTrapVariable 3 }

partnerkey OBJECT-TYPE
    SYNTAX  INTEGER(1..2147483647)
    MAX-ACCESS  read-only
    STATUS      current
    DESCRIPTION
        "This is the partner key information for LACP."
    ::= { es2410cTrapVariable 4 }

uplink OBJECT-TYPE
    SYNTAX  DisplayString
    MAX-ACCESS  read-only
    STATUS      current
    DESCRIPTION
        "Uplink port(s) in the metro-mode vlan."
    ::= { es2410cTrapVariable 5 }

ipmacbind OBJECT-TYPE
    SYNTAX      DisplayString
    MAX-ACCESS  read-only
    STATUS      current
    DESCRIPTION
        "IP-MAC Binding value. Format as mac:00:40:c7:00:00:01,ip:192.168.2.3,port:20
         00:40:c7:00:00:01 is the mac address;
         192.168.2.3 is the binding ip address;
         port:20 is the port, e.g 20"
    ::= { es2410cTrapVariable 6 }

arpinspect OBJECT-TYPE
    SYNTAX      DisplayString
    MAX-ACCESS  read-only
    STATUS      current
    DESCRIPTION
        "ARP Inspection detected.
         Format as mac:00:40:c7:00:00:01, port:20, Unknown Mac/IP."
    ::= { es2410cTrapVariable 7 }

es2410cAcl       OBJECT IDENTIFIER ::= { es2410cProduces 22 }

es2410cHighAcl      OBJECT IDENTIFIER ::= { es2410cAcl 1 }

es2410cHighAclCreatStatus OBJECT-TYPE
    SYNTAX         INTEGER(0|1)
    MAX-ACCESS     read-write
    STATUS         current
    DESCRIPTION
        "Create a new high-acl
         0 : None,
         1 : Create a high-acl temp entry
        "
    ::= { es2410cHighAcl 1 }

es2410cHighAclNumbers OBJECT-TYPE
    SYNTAX         INTEGER(0..128)
    MAX-ACCESS     read-only
    STATUS         current
    DESCRIPTION
        "Numbers of high-acl table."
    ::= { es2410cHighAcl 2 }

es2410cHighAclTable  OBJECT-TYPE
    SYNTAX      SEQUENCE OF ES2410CHighAclEntry
    MAX-ACCESS  not-accessible
    STATUS      current
    DESCRIPTION
        " "
    ::= { es2410cHighAcl 3 }

es2410cHighAclEntry OBJECT-TYPE
    SYNTAX      ES2410CHighAclEntry
    MAX-ACCESS  not-accessible
    STATUS      current
    DESCRIPTION
        "Entry(s) for high-acl table."
    INDEX {es2410cHighAclIndex}
    ::= { es2410cHighAclTable 1 }

ES2410CHighAclEntry ::=
SEQUENCE {
    es2410cHighAclIndex						INTEGER,
    es2410cHighAclName   					DisplayString,
    es2410cHighAclIngressPortMap		  			DisplayString,
    es2410cHighAclSMacFilter					DisplayString,
    es2410cHighAclDMacFilter					DisplayString,
    es2410cHighAclVlanType					INTEGER,
    es2410cHighAclTagVid						INTEGER,
    es2410cHighAclTagPriority					INTEGER,
    es2410cHighAclEthernetType					DisplayString,
    es2410cHighAclIPv4Protocol					INTEGER,
    es2410cHighAclIPv4ToS					DisplayString,
    es2410cHighAclIPv4TTLRange					INTEGER,
    es2410cHighAclIPv4DA						IpAddress,
    es2410cHighAclIPv4DAMask					IpAddress,
    es2410cHighAclIPv4SA						IpAddress,
    es2410cHighAclIPv4SAMask					IpAddress,
    es2410cHighAclL4DestinationPort				INTEGER,
    es2410cHighAclL4SourcePort					INTEGER,
    es2410cHighAclActionIBForwardDecision			INTEGER,
    es2410cHighAclActionIBForwardMap				INTEGER,
    es2410cHighAclActionIBModifyDSCPPacket			INTEGER,
    es2410cHighAclActionIBModifyDSCPValue			INTEGER,
    es2410cHighAclActionOBForwardDecision			INTEGER,
    es2410cHighAclActionOBForwardMap				INTEGER,
    es2410cHighAclActionOBModifyDSCPPacket			INTEGER,
    es2410cHighAclActionOBModifyDSCPValue			INTEGER,
    es2410cHighAclActionModifyDot1PPacket			INTEGER,
    es2410cHighAclActionModifyDot1PValue				INTEGER,
    es2410cHighAclActionModifyQoSPacket				INTEGER,
    es2410cHighAclActionModifyQoSValue				INTEGER,
    es2410cHighAclRateMeter					INTEGER,
    es2410cHighAclRowStatus					INTEGER
}

es2410cHighAclIndex  OBJECT-TYPE
    SYNTAX      INTEGER(1..128)
    MAX-ACCESS  not-accessible
    STATUS      current
    DESCRIPTION
        "The entry index of high-acl table."
    ::= { es2410cHighAclEntry 1 }

es2410cHighAclName OBJECT-TYPE
    SYNTAX         DisplayString
    MAX-ACCESS     read-write
    STATUS         current
    DESCRIPTION
        "The name of high-acl entry."
    ::= { es2410cHighAclEntry 2 }

es2410cHighAclIngressPortMap OBJECT-TYPE
    SYNTAX         DisplayString
    MAX-ACCESS     read-write
    STATUS         current
    DESCRIPTION
        "The ingress port map of high-acl entry.
         port range: syntax: 1,5-7, available from 1 to 10, 0 for any.
        "
    ::= { es2410cHighAclEntry 3 }

es2410cHighAclSMacFilter OBJECT-TYPE
    SYNTAX         DisplayString
    MAX-ACCESS     read-write
    STATUS         current
    DESCRIPTION
        "The source mac filter of high-acl entry."
    ::= { es2410cHighAclEntry 4 }

es2410cHighAclDMacFilter OBJECT-TYPE
    SYNTAX         DisplayString
    MAX-ACCESS     read-write
    STATUS         current
    DESCRIPTION
        "The destination mac filter of high-acl entry."
    ::= { es2410cHighAclEntry 5 }

es2410cHighAclVlanType OBJECT-TYPE
    SYNTAX         INTEGER(0|1)
    MAX-ACCESS     read-write
    STATUS         current
    DESCRIPTION
        "The vlan type of high-acl entry.
         0 : Any,
         1 : Tag-Based Vlan.
        "
    ::= { es2410cHighAclEntry 6 }

es2410cHighAclTagVid OBJECT-TYPE
    SYNTAX         INTEGER(0..4094)
    MAX-ACCESS     read-write
    STATUS         current
    DESCRIPTION
        "The tag-based vlan vid of high-acl entry.
         VLAN ID, form 1 to 4094, 0 for priority tag.
        "
    ::= { es2410cHighAclEntry 7 }


es2410cHighAclTagPriority OBJECT-TYPE
    SYNTAX         INTEGER(0..7)
    MAX-ACCESS     read-write
    STATUS         current
    DESCRIPTION
        "The tag priority(0~7) of high-acl entry."
    ::= { es2410cHighAclEntry 8 }

es2410cHighAclEthernetType OBJECT-TYPE
    SYNTAX         DisplayString(SIZE(0..4))
    MAX-ACCESS     read-write
    STATUS         current
    DESCRIPTION
        "The ethernet type of high-acl entry.
	 Ethernet type, format: 0806 (in hexadecimal format).
	 Example: IPv4 for 0800, ARP for 0806, Any for 0000.
        "
    ::= { es2410cHighAclEntry 9 }

es2410cHighAclIPv4Protocol OBJECT-TYPE
    SYNTAX         INTEGER(0..255)
    MAX-ACCESS     read-write
    STATUS         current
    DESCRIPTION
        "The IPv4 protocol of high-acl entry.
	 IPv4 protocol, from 0 to 255.
	 Example: ICMP for 1, UDP for 17, TCP for 6.
        "
    ::= { es2410cHighAclEntry 10 }

es2410cHighAclIPv4ToS OBJECT-TYPE
    SYNTAX         DisplayString(SIZE(0..2))
    MAX-ACCESS     read-write
    STATUS         current
    DESCRIPTION
        "The IPv4 ToS of high-acl entry.
         IPv4 TOS field, from 00 to ff (in hexadecimal format).
        "
    ::= { es2410cHighAclEntry 11 }

es2410cHighAclIPv4TTLRange OBJECT-TYPE
    SYNTAX         INTEGER(0..3)
    MAX-ACCESS     read-write
    STATUS         current
    DESCRIPTION
        "The IPv4 TTL Range of high-acl entry.
	 0 : 0,
	 1 : 1,
	 2 : 2~254,
	 3 : 255.
        "
    ::= { es2410cHighAclEntry 12 }

es2410cHighAclIPv4DA OBJECT-TYPE
    SYNTAX         IpAddress
    MAX-ACCESS     read-write
    STATUS         current
    DESCRIPTION
        "The IPv4 destination Address value of high-acl entry."
    ::= { es2410cHighAclEntry 13 }

es2410cHighAclIPv4DAMask OBJECT-TYPE
    SYNTAX         IpAddress
    MAX-ACCESS     read-write
    STATUS         current
    DESCRIPTION
        "The IPv4 destination Address mask value of high-acl entry."
    ::= { es2410cHighAclEntry 14 }

es2410cHighAclIPv4SA OBJECT-TYPE
    SYNTAX         IpAddress
    MAX-ACCESS     read-write
    STATUS         current
    DESCRIPTION
        "The IPv4 Source Address value of high-acl entry."
    ::= { es2410cHighAclEntry 15 }

es2410cHighAclIPv4SAMask OBJECT-TYPE
    SYNTAX         IpAddress
    MAX-ACCESS     read-write
    STATUS         current
    DESCRIPTION
        "The IPv4 Source Address mask value of high-acl entry."
    ::= { es2410cHighAclEntry 16 }

es2410cHighAclL4DestinationPort OBJECT-TYPE
    SYNTAX         INTEGER(0..65535)
    MAX-ACCESS     read-write
    STATUS         current
    DESCRIPTION
        "The L4 destination port number of high-acl entry.
         port: IPv4 L4 destination port, from 0 to 65535
        "
    ::= { es2410cHighAclEntry 17 }

es2410cHighAclL4SourcePort OBJECT-TYPE
    SYNTAX         INTEGER(0..65535)
    MAX-ACCESS     read-write
    STATUS         current
    DESCRIPTION
        "The L4 source port number of high-acl entry.
         port: IPv4 L4 source port, from 0 to 65535
        "
    ::= { es2410cHighAclEntry 18 }

es2410cHighAclActionIBForwardDecision OBJECT-TYPE
    SYNTAX         INTEGER(0..3)
    MAX-ACCESS     read-write
    STATUS         current
    DESCRIPTION
        "The forward decision in in-Band.
         0 : No change,
         1 : Use new forward map,
         2 : ORed with new map,
         3 : Explicit actions
        "
    ::= { es2410cHighAclEntry 19 }

es2410cHighAclActionIBForwardMap OBJECT-TYPE
    SYNTAX         INTEGER(0..10)
    MAX-ACCESS     read-write
    STATUS         current
    DESCRIPTION
        "If es2410cHighAclActionIBForwardDecision as 0 then
            0 : As ARL map.
         If es2410cHighAclActionIBForwardDecision as 1 or 2 then
	    0 : All Linked-Port,
	    1~10 : Port 1 ~ Port 10
	 If  es2410cHighAclActionIBForwardDecision as 3 then
	    0 : As ARL map,
	    1 : As ARL map and copy to mirror port,
	    2 : Drop,
	    3 : Forward to mirror port.
    	"
    ::= { es2410cHighAclEntry 20 }

es2410cHighAclActionIBModifyDSCPPacket OBJECT-TYPE
    SYNTAX         INTEGER(0|1)
    MAX-ACCESS     read-write
    STATUS         current
    DESCRIPTION
        "Modify DSCP packet value in in-Band.
         0 : Any,
         1 : Specific.
        "
    ::= { es2410cHighAclEntry 21 }

es2410cHighAclActionIBModifyDSCPValue OBJECT-TYPE
    SYNTAX         INTEGER(0..63)
    MAX-ACCESS     read-write
    STATUS         current
    DESCRIPTION
        "Be used by es2410cHighAclActionIBModifyDSCPPacket as 1.
         New DSCP field value, from 0 to 63"
    ::= { es2410cHighAclEntry 22 }

es2410cHighAclActionOBForwardDecision OBJECT-TYPE
    SYNTAX         INTEGER(0..3)
    MAX-ACCESS     read-write
    STATUS         current
    DESCRIPTION
        "The forward decision in out-Band.
         0 : No change,
         1 : Use new forward map,
         2 : ORed with new map,
         3 : Explicit actions
        "
    ::= { es2410cHighAclEntry 23 }

es2410cHighAclActionOBForwardMap OBJECT-TYPE
    SYNTAX         INTEGER(0..10)
    MAX-ACCESS     read-write
    STATUS         current
    DESCRIPTION
        "If es2410cHighAclActionOBForwardDecision as 0
            0 : As ARL map.
         If es2410cHighAclActionOBForwardDecision as 1 or 2 then
	    0 : All Linked-Port,
	    1~10 : Port 1 ~ Port 10
	 If es2410cHighAclActionOBForwardDecision as 3 then
	    0 : As ARL map,
	    1 : As ARL map and copy to mirror port ,
	    2 : Drop,
	    3 : Forward to mirror port.
    	"
    ::= { es2410cHighAclEntry 24 }

es2410cHighAclActionOBModifyDSCPPacket OBJECT-TYPE
    SYNTAX         INTEGER(0|1)
    MAX-ACCESS     read-write
    STATUS         current
    DESCRIPTION
        "Modify DSCP packet value in out-Band.
         0 : Any,
         1 : Specific.
        "
    ::= { es2410cHighAclEntry 25 }

es2410cHighAclActionOBModifyDSCPValue OBJECT-TYPE
    SYNTAX         INTEGER(0..63)
    MAX-ACCESS     read-write
    STATUS         current
    DESCRIPTION
        "Be used by es2410cHighAclActionOBModifyDSCPPacket as 1.
         New DSCP field value, from 0 to 63"
    ::= { es2410cHighAclEntry 26 }

es2410cHighAclActionModifyDot1PPacket OBJECT-TYPE
    SYNTAX         INTEGER(0|1)
    MAX-ACCESS     read-write
    STATUS         current
    DESCRIPTION
        "Modify 802.1P packet value.
         0 : Any,
         1 : Specific.
        "
    ::= { es2410cHighAclEntry 27 }

es2410cHighAclActionModifyDot1PValue OBJECT-TYPE
    SYNTAX         INTEGER(0..7)
    MAX-ACCESS     read-write
    STATUS         current
    DESCRIPTION
        "Be used by es2410cHighAclActionModifyDot1PPacket as 1.
         New 802.1P field value, from 0 to 7"
    ::= { es2410cHighAclEntry 28 }

es2410cHighAclActionModifyQoSPacket OBJECT-TYPE
    SYNTAX         INTEGER(0|1)
    MAX-ACCESS     read-write
    STATUS         current
    DESCRIPTION
        "Modify QoS packet value.
         0 : Any,
         1 : Specific.
        "
    ::= { es2410cHighAclEntry 29 }

es2410cHighAclActionModifyQoSValue OBJECT-TYPE
    SYNTAX         INTEGER(0..3)
    MAX-ACCESS     read-write
    STATUS         current
    DESCRIPTION
        "Be used by es2410cHighAclActionModifyQoSPacket as 1.
         New QoS field value, from 0 to 3"
    ::= { es2410cHighAclEntry 30 }

es2410cHighAclRateMeter OBJECT-TYPE
    SYNTAX         INTEGER(64..1024000)
    MAX-ACCESS     read-write
    STATUS         current
    DESCRIPTION
        "The rate meter(64..1024000) of high-acl entry."
    ::= { es2410cHighAclEntry 31 }

es2410cHighAclRowStatus  OBJECT-TYPE
    SYNTAX      INTEGER(1..3)
    MAX-ACCESS  read-write
    STATUS      current
    DESCRIPTION
        "The row status of high-acl entry.
         1 : active,
         2 : not-inService,
         3 : delete
        "
    ::= { es2410cHighAclEntry 32 }

es2410cLowAcl      OBJECT IDENTIFIER ::= { es2410cAcl 2 }

es2410cLowAclCreatStatus OBJECT-TYPE
    SYNTAX         INTEGER(0|1)
    MAX-ACCESS     read-write
    STATUS         current
    DESCRIPTION
        "Create a new low-acl
         0 : None,
         1 : Create a low-acl temp entry
        "
    ::= { es2410cLowAcl 1 }

es2410cLowAclNumbers OBJECT-TYPE
    SYNTAX         INTEGER(0..128)
    MAX-ACCESS     read-only
    STATUS         current
    DESCRIPTION
        "Numbers of low-acl table."
    ::= { es2410cLowAcl 2 }

es2410cLowAclTable  OBJECT-TYPE
    SYNTAX      SEQUENCE OF ES2410CLowAclEntry
    MAX-ACCESS  not-accessible
    STATUS      current
    DESCRIPTION
        " "
    ::= { es2410cLowAcl 3 }

es2410cLowAclEntry OBJECT-TYPE
    SYNTAX      ES2410CLowAclEntry
    MAX-ACCESS  not-accessible
    STATUS      current
    DESCRIPTION
        "Entry(s) for Low-acl table."
    INDEX {es2410cLowAclIndex}
    ::= { es2410cLowAclTable 1 }

ES2410CLowAclEntry ::=
SEQUENCE {
    es2410cLowAclIndex						INTEGER,
    es2410cLowAclName   						DisplayString,
    es2410cLowAclIngressPortMap		  			DisplayString,
    es2410cLowAclSMacFilter					DisplayString,
    es2410cLowAclDMacFilter					DisplayString,
    es2410cLowAclVlanType					INTEGER,
    es2410cLowAclTagVid						INTEGER,
    es2410cLowAclTagPriority					INTEGER,
    es2410cLowAclEthernetType					DisplayString,
    es2410cLowAclIPv4Protocol					INTEGER,
    es2410cLowAclIPv4ToS						DisplayString,
    es2410cLowAclIPv4TTLRange					INTEGER,
    es2410cLowAclIPv4DA						IpAddress,
    es2410cLowAclIPv4DAMask					IpAddress,
    es2410cLowAclIPv4SA						IpAddress,
    es2410cLowAclIPv4SAMask					IpAddress,
    es2410cLowAclL4DestinationPort				INTEGER,
    es2410cLowAclL4SourcePort					INTEGER,
    es2410cLowAclActionIBForwardDecision				INTEGER,
    es2410cLowAclActionIBForwardMap				INTEGER,
    es2410cLowAclActionIBModifyDSCPPacket			INTEGER,
    es2410cLowAclActionIBModifyDSCPValue				INTEGER,
    es2410cLowAclActionOBForwardDecision				INTEGER,
    es2410cLowAclActionOBForwardMap				INTEGER,
    es2410cLowAclActionOBModifyDSCPPacket			INTEGER,
    es2410cLowAclActionOBModifyDSCPValue				INTEGER,
    es2410cLowAclActionModifyDot1PPacket				INTEGER,
    es2410cLowAclActionModifyDot1PValue				INTEGER,
    es2410cLowAclActionModifyQoSPacket				INTEGER,
    es2410cLowAclActionModifyQoSValue				INTEGER,
    es2410cLowAclRateMeter					INTEGER,
    es2410cLowAclRowStatus					INTEGER
}

es2410cLowAclIndex  OBJECT-TYPE
    SYNTAX      INTEGER(1..128)
    MAX-ACCESS  not-accessible
    STATUS      current
    DESCRIPTION
        "The entry index of Low-acl table."
    ::= { es2410cLowAclEntry 1 }

es2410cLowAclName OBJECT-TYPE
    SYNTAX         DisplayString
    MAX-ACCESS     read-write
    STATUS         current
    DESCRIPTION
        "The name of low-acl entry."
    ::= { es2410cLowAclEntry 2 }

es2410cLowAclIngressPortMap OBJECT-TYPE
    SYNTAX         DisplayString
    MAX-ACCESS     read-write
    STATUS         current
    DESCRIPTION
        "The ingress port map of Low-acl entry.
         port range: syntax: 1,5-7, available from 1 to 10, 0 for any.
        "
    ::= { es2410cLowAclEntry 3 }

es2410cLowAclSMacFilter OBJECT-TYPE
    SYNTAX         DisplayString
    MAX-ACCESS     read-write
    STATUS         current
    DESCRIPTION
        "The source mac filter of low-acl entry."
    ::= { es2410cLowAclEntry 4 }

es2410cLowAclDMacFilter OBJECT-TYPE
    SYNTAX         DisplayString
    MAX-ACCESS     read-write
    STATUS         current
    DESCRIPTION
        "The destination mac filter of low-acl entry."
    ::= { es2410cLowAclEntry 5 }

es2410cLowAclVlanType OBJECT-TYPE
    SYNTAX         INTEGER(0|1)
    MAX-ACCESS     read-write
    STATUS         current
    DESCRIPTION
        "The vlan type of low-acl entry.
         0 : Any,
         1 : Tag-Based Vlan.
        "
    ::= { es2410cLowAclEntry 6 }

es2410cLowAclTagVid OBJECT-TYPE
    SYNTAX         INTEGER(0..4094)
    MAX-ACCESS     read-write
    STATUS         current
    DESCRIPTION
        "The tag-based vlan vid of low-acl entry.
         VLAN ID, form 1 to 4094, 0 for priority tag.
        "
    ::= { es2410cLowAclEntry 7 }


es2410cLowAclTagPriority OBJECT-TYPE
    SYNTAX         INTEGER(0..7)
    MAX-ACCESS     read-write
    STATUS         current
    DESCRIPTION
        "The tag priority(0~7) of low-acl entry."
    ::= { es2410cLowAclEntry 8 }

es2410cLowAclEthernetType OBJECT-TYPE
    SYNTAX         DisplayString(SIZE(0..4))
    MAX-ACCESS     read-write
    STATUS         current
    DESCRIPTION
        "The ethernet type of low-acl entry.
	 Ethernet type, format: 0806 (in hexadecimal format).
	 Example: IPv4 for 0800, ARP for 0806, Any for 0000.
        "
    ::= { es2410cLowAclEntry 9 }

es2410cLowAclIPv4Protocol OBJECT-TYPE
    SYNTAX         INTEGER(0..255)
    MAX-ACCESS     read-write
    STATUS         current
    DESCRIPTION
        "The IPv4 protocol of low-acl entry.
	 IPv4 protocol, from 0 to 255.
	 Example: ICMP for 1, UDP for 17, TCP for 6.
        "
    ::= { es2410cLowAclEntry 10 }

es2410cLowAclIPv4ToS OBJECT-TYPE
    SYNTAX         DisplayString(SIZE(0..2))
    MAX-ACCESS     read-write
    STATUS         current
    DESCRIPTION
        "The IPv4 ToS of low-acl entry.
         IPv4 TOS field, from 00 to ff (in hexadecimal format).
        "
    ::= { es2410cLowAclEntry 11 }

es2410cLowAclIPv4TTLRange OBJECT-TYPE
    SYNTAX         INTEGER(0..3)
    MAX-ACCESS     read-write
    STATUS         current
    DESCRIPTION
        "The IPv4 TTL Range of low-acl entry.
	 0 : 0,
	 1 : 1,
	 2 : 2~254,
	 3 : 255.
        "
    ::= { es2410cLowAclEntry 12 }

es2410cLowAclIPv4DA OBJECT-TYPE
    SYNTAX         IpAddress
    MAX-ACCESS     read-write
    STATUS         current
    DESCRIPTION
        "The IPv4 destination Address value of low-acl entry."
    ::= { es2410cLowAclEntry 13 }

es2410cLowAclIPv4DAMask OBJECT-TYPE
    SYNTAX         IpAddress
    MAX-ACCESS     read-write
    STATUS         current
    DESCRIPTION
        "The IPv4 destination Address mask value of low-acl entry."
    ::= { es2410cLowAclEntry 14 }

es2410cLowAclIPv4SA OBJECT-TYPE
    SYNTAX         IpAddress
    MAX-ACCESS     read-write
    STATUS         current
    DESCRIPTION
        "The IPv4 Source Address value of low-acl entry."
    ::= { es2410cLowAclEntry 15 }

es2410cLowAclIPv4SAMask OBJECT-TYPE
    SYNTAX         IpAddress
    MAX-ACCESS     read-write
    STATUS         current
    DESCRIPTION
        "The IPv4 Source Address mask value of low-acl entry."
    ::= { es2410cLowAclEntry 16 }

es2410cLowAclL4DestinationPort OBJECT-TYPE
    SYNTAX         INTEGER(0..65535)
    MAX-ACCESS     read-write
    STATUS         current
    DESCRIPTION
        "The L4 destination port number of low-acl entry.
         IPv4 L4 destination port, from 0 to 65535"
    ::= { es2410cLowAclEntry 17 }

es2410cLowAclL4SourcePort OBJECT-TYPE
    SYNTAX         INTEGER(0..65535)
    MAX-ACCESS     read-write
    STATUS         current
    DESCRIPTION
        "The L4 source port number of low-acl entry.
         IPv4 L4 source port, from 0 to 65535"
    ::= { es2410cLowAclEntry 18 }

es2410cLowAclActionIBForwardDecision OBJECT-TYPE
    SYNTAX         INTEGER(0..3)
    MAX-ACCESS     read-write
    STATUS         current
    DESCRIPTION
        "The forward decision in in-Band.
         0 : No change,
         1 : Use new forward map,
         2 : ORed with new map,
         3 : Explicit actions
        "
    ::= { es2410cLowAclEntry 19 }

es2410cLowAclActionIBForwardMap OBJECT-TYPE
    SYNTAX         INTEGER(0..10)
    MAX-ACCESS     read-write
    STATUS         current
    DESCRIPTION
        "If es2410cLowAclActionIBForwardDecision as 0 then
            0 : As ARL map.
         If es2410cLowAclActionIBForwardDecision as 1 or 2 then
	    0 : All Linked-Port,
	    1~10 : Port 1 ~ Port 10
	 If  es2410cLowAclActionIBForwardDecision as 3 then
	    0 : As ARL map,
	    1 : As ARL map and copy to mirror port,
	    2 : Drop,
	    3 : Forward to mirror port.
    	"
    ::= { es2410cLowAclEntry 20 }

es2410cLowAclActionIBModifyDSCPPacket OBJECT-TYPE
    SYNTAX         INTEGER(0|1)
    MAX-ACCESS     read-write
    STATUS         current
    DESCRIPTION
        "Modify DSCP packet value in in-Band.
         0 : Any,
         1 : Specific.
        "
    ::= { es2410cLowAclEntry 21 }

es2410cLowAclActionIBModifyDSCPValue OBJECT-TYPE
    SYNTAX         INTEGER(0..63)
    MAX-ACCESS     read-write
    STATUS         current
    DESCRIPTION
        "Be used by es2410cLowAclActionIBModifyDSCPPacket as 1.
         New DSCP field value, from 0 to 63"
    ::= { es2410cLowAclEntry 22 }

es2410cLowAclActionOBForwardDecision OBJECT-TYPE
    SYNTAX         INTEGER(0..3)
    MAX-ACCESS     read-write
    STATUS         current
    DESCRIPTION
        "The forward decision in out-Band.
         0 : No change,
         1 : Use new forward map,
         2 : ORed with new map,
         3 : Explicit actions
        "
    ::= { es2410cLowAclEntry 23 }

es2410cLowAclActionOBForwardMap OBJECT-TYPE
    SYNTAX         INTEGER(0..10)
    MAX-ACCESS     read-write
    STATUS         current
    DESCRIPTION
        "If es2410cLowAclActionOBForwardDecision as 0
            0 : As ARL map.
         If es2410cLowAclActionOBForwardDecision as 1 or 2 then
	    0 : All Linked-Port,
	    1~10 : Port 1 ~ Port 10
	 If es2410cLowAclActionOBForwardDecision as 3 then
	    0 : As ARL map,
	    1 : As ARL map and copy to mirror port ,
	    2 : Drop,
	    3 : Forward to mirror port.
    	"
    ::= { es2410cLowAclEntry 24 }

es2410cLowAclActionOBModifyDSCPPacket OBJECT-TYPE
    SYNTAX         INTEGER(0|1)
    MAX-ACCESS     read-write
    STATUS         current
    DESCRIPTION
        "Modify DSCP packet value in out-Band.
         0 : Any,
         1 : Specific.
        "
    ::= { es2410cLowAclEntry 25 }

es2410cLowAclActionOBModifyDSCPValue OBJECT-TYPE
    SYNTAX         INTEGER(0..63)
    MAX-ACCESS     read-write
    STATUS         current
    DESCRIPTION
        "Be used by es2410cLowAclActionOBModifyDSCPPacket as 1.
         New DSCP field value, from 0 to 63"
    ::= { es2410cLowAclEntry 26 }

es2410cLowAclActionModifyDot1PPacket OBJECT-TYPE
    SYNTAX         INTEGER(0|1)
    MAX-ACCESS     read-write
    STATUS         current
    DESCRIPTION
        "Modify 802.1P packet value.
         0 : Any,
         1 : Specific.
        "
    ::= { es2410cLowAclEntry 27 }

es2410cLowAclActionModifyDot1PValue OBJECT-TYPE
    SYNTAX         INTEGER(0..7)
    MAX-ACCESS     read-write
    STATUS         current
    DESCRIPTION
        "Be used by es2410cLowAclActionModifyDot1PPacket as 1.
         New 802.1p field value, from 0 to 7"
    ::= { es2410cLowAclEntry 28 }

es2410cLowAclActionModifyQoSPacket OBJECT-TYPE
    SYNTAX         INTEGER(0|1)
    MAX-ACCESS     read-write
    STATUS         current
    DESCRIPTION
        "Modify QoS packet value.
         0 : Any,
         1 : Specific.
        "
    ::= { es2410cLowAclEntry 29 }

es2410cLowAclActionModifyQoSValue OBJECT-TYPE
    SYNTAX         INTEGER(0..3)
    MAX-ACCESS     read-write
    STATUS         current
    DESCRIPTION
        "Be used by es2410cLowAclActionModifyQoSPacket as 1.
         New QoS field value, from 0 to 3"
    ::= { es2410cLowAclEntry 30 }

es2410cLowAclRateMeter OBJECT-TYPE
    SYNTAX         INTEGER(64..1024000)
    MAX-ACCESS     read-write
    STATUS         current
    DESCRIPTION
        "The rate meter(64..1024000) of low-acl entry."
    ::= { es2410cLowAclEntry 31 }

es2410cLowAclRowStatus  OBJECT-TYPE
    SYNTAX      INTEGER(1..3)
    MAX-ACCESS  read-write
    STATUS      current
    DESCRIPTION
        "The row status of low-acl entry.
         1 : active,
         2 : not-inService,
         3 : delete
        "
    ::= { es2410cLowAclEntry 32 }

es2410cTrunkInfo       OBJECT IDENTIFIER ::= { es2410cProduces 23 }

es2410cTrunkPort      OBJECT IDENTIFIER ::= { es2410cTrunkInfo 1 }

es2410cTrunkPortTable  OBJECT-TYPE
    SYNTAX      SEQUENCE OF ES2410CTrunkPortEntry
    MAX-ACCESS  not-accessible
    STATUS      current
    DESCRIPTION
        " "
    ::= { es2410cTrunkPort 1 }

es2410cTrunkPortEntry OBJECT-TYPE
    SYNTAX      ES2410CTrunkPortEntry
    MAX-ACCESS  not-accessible
    STATUS      current
    DESCRIPTION
        "Entry(s) for trunk table."
    INDEX {es2410cTrunkPortIndex}
    ::= { es2410cTrunkPortTable 1 }

ES2410CTrunkPortEntry ::=
SEQUENCE {
    es2410cTrunkPortIndex				INTEGER,
    es2410cTrunkPortMethod   				INTEGER,
    es2410cTrunkPortGroup 				INTEGER,
    es2410cTrunkPortActiveLacp				INTEGER,
    es2410cTrunkPortAggtr				INTEGER,
    es2410cTrunkPortStatus				INTEGER,
    es2410cTrunkPortCurrentMode				INTEGER
}

es2410cTrunkPortIndex  OBJECT-TYPE
    SYNTAX      INTEGER(1..10)
    MAX-ACCESS  not-accessible
    STATUS      current
    DESCRIPTION
        "The port index of trunk table."
    ::= { es2410cTrunkPortEntry 1 }

es2410cTrunkPortMethod  OBJECT-TYPE
    SYNTAX      INTEGER(0..2)
    MAX-ACCESS  read-write
    STATUS      current
    DESCRIPTION
        "The method of trunk port.
	 0 : None,
	 1 : LACP,
	 2 : Static.
        "
    ::= { es2410cTrunkPortEntry 2 }

es2410cTrunkPortGroup  OBJECT-TYPE
    SYNTAX      INTEGER(0..4)
    MAX-ACCESS  read-write
    STATUS      current
    DESCRIPTION
        "The group(0~4) of trunk port."
    ::= { es2410cTrunkPortEntry 3 }

es2410cTrunkPortActiveLacp  OBJECT-TYPE
    SYNTAX      INTEGER(0|1)
    MAX-ACCESS  read-write
    STATUS      current
    DESCRIPTION
        "The active lacp mode of trunk port.
	 0 : Passive,
	 1 : Active.
        "
    ::= { es2410cTrunkPortEntry 4 }

es2410cTrunkPortAggtr  OBJECT-TYPE
    SYNTAX      INTEGER(1..10)
    MAX-ACCESS  read-only
    STATUS      current
    DESCRIPTION
        "The Aggtr of trunk port."
    ::= { es2410cTrunkPortEntry 5 }

es2410cTrunkPortStatus  OBJECT-TYPE
    SYNTAX      INTEGER(0|1)
    MAX-ACCESS  read-only
    STATUS      current
    DESCRIPTION
        "The status of trunk port.
         0 : None,
         1 : Ready.
        "
    ::= { es2410cTrunkPortEntry 6 }

es2410cTrunkPortCurrentMode  OBJECT-TYPE
    SYNTAX      INTEGER(0..2)
    MAX-ACCESS  read-write
    STATUS      current
    DESCRIPTION
        "The current mode of trunk port entry.
	 0 : Active mode,
	 1 : Edit mode,
	 2 : Do edit.
        "
    ::= { es2410cTrunkPortEntry 7 }

es2410cAggregatorView      OBJECT IDENTIFIER ::= { es2410cTrunkInfo 2 }

es2410cAggregatorViewTable  OBJECT-TYPE
    SYNTAX      SEQUENCE OF ES2410CAggregatorViewEntry
    MAX-ACCESS  not-accessible
    STATUS      current
    DESCRIPTION
        " "
    ::= { es2410cAggregatorView 1 }

es2410cAggregatorViewEntry OBJECT-TYPE
    SYNTAX      ES2410CAggregatorViewEntry
    MAX-ACCESS  not-accessible
    STATUS      current
    DESCRIPTION
        "Entry(s) for aggregator view table."
    INDEX {es2410cAggregatorViewIndex}
    ::= { es2410cAggregatorViewTable 1 }

ES2410CAggregatorViewEntry ::=
SEQUENCE {
    es2410cAggregatorViewIndex				INTEGER,
    es2410cAggregatorViewMethod 				INTEGER,
    es2410cAggregatorViewMemberPorts 			DisplayString,
    es2410cAggregatorViewReadyPorts			DisplayString
}

es2410cAggregatorViewIndex  OBJECT-TYPE
    SYNTAX      INTEGER(1..10)
    MAX-ACCESS  not-accessible
    STATUS      current
    DESCRIPTION
        "The port index of aggregator view table."
    ::= { es2410cAggregatorViewEntry 1 }

es2410cAggregatorViewMethod  OBJECT-TYPE
    SYNTAX      INTEGER(0..2)
    MAX-ACCESS  read-only
    STATUS      current
    DESCRIPTION
        "The method of aggregator view table.
         0 : None,
	 1 : LACP,
	 2 : Static.
        "
    ::= { es2410cAggregatorViewEntry 2 }

es2410cAggregatorViewMemberPorts  OBJECT-TYPE
    SYNTAX      DisplayString
    MAX-ACCESS  read-only
    STATUS      current
    DESCRIPTION
        "The member ports of aggregator view table."
    ::= { es2410cAggregatorViewEntry 3 }

es2410cAggregatorViewReadyPorts  OBJECT-TYPE
    SYNTAX      DisplayString
    MAX-ACCESS  read-only
    STATUS      current
    DESCRIPTION
        "The ready ports of aggregator view table."
    ::= { es2410cAggregatorViewEntry 4 }

es2410cLacpSystemConfiguration     OBJECT IDENTIFIER ::= { es2410cTrunkInfo 3 }

es2410cLacpSystemPriority  OBJECT-TYPE
    SYNTAX      INTEGER(1..65535)
    MAX-ACCESS  read-write
    STATUS      current
    DESCRIPTION
        "The priority of LACP system."
    ::= { es2410cLacpSystemConfiguration 1 }

es2410cLacpSystemHashMethod  OBJECT-TYPE
    SYNTAX      INTEGER(0..5)
    MAX-ACCESS  read-write
    STATUS      current
    DESCRIPTION
        "The hash method of LACP system.
	 0 : DA and SA
         1 : SA
         2 : DA
         3 : IPv4 DIP
         4 : IPv4 SIP
         5 : DA, SA, IPv4 DIP and IPv4 SIP
        "
    ::= { es2410cLacpSystemConfiguration 2 }

es2410cDhcprelay            OBJECT IDENTIFIER ::= { es2410cProduces 25 }

es2410cDhcpRelayState OBJECT-TYPE
    SYNTAX      INTEGER(0|1)
    MAX-ACCESS  read-write
    STATUS      current
    DESCRIPTION
        "Set DHCP Relay State.
         0 : Disable,
         1 : Enable.
         When DHCP or DHCP Snooping is already running. Please disable DHCP or DHCP Snooping first, and then enable DHCP Relay again.
        "
    ::= { es2410cDhcprelay 1 }

es2410cDhcpRelayLifeTime OBJECT-TYPE
    SYNTAX      INTEGER(1..10)
    MAX-ACCESS  read-write
    STATUS      current
    DESCRIPTION
        "Set wait Server reply time.
         time: from 1 to 10 second(s)"
    ::= { es2410cDhcprelay 2 }

es2410cDhcpRelayOption82 OBJECT-TYPE
    SYNTAX      INTEGER(0|1)
    MAX-ACCESS  read-write
    STATUS      current
    DESCRIPTION
        "Option82 state in Dhcp Relay.
         0 : Disable,
         1 : Enable.
        "
    ::= { es2410cDhcprelay 3 }

es2410cDhcpRelayOption82Action OBJECT-TYPE
    SYNTAX      INTEGER(0..2)
    MAX-ACCESS  read-write
    STATUS      current
    DESCRIPTION
        "The action of the switch which is existing relay information in packets received from DHCP clients.
         0 : Replace,
         1 : Keep,
         2 : Drop."
    ::= { es2410cDhcprelay 4 }

es2410cDhcpRelayServerPort OBJECT-TYPE
    SYNTAX      DisplayString
    MAX-ACCESS  read-write
    STATUS      current
    DESCRIPTION
        "The Dhcp Relay Server Port.
         Server port cannot exceed more than two ports."
    ::= { es2410cDhcprelay 5 }

es2410cDhcpRelayServerIP OBJECT-TYPE
    SYNTAX      IpAddress
    MAX-ACCESS  read-write
    STATUS      current
    DESCRIPTION
        "Server ip"
    ::= { es2410cDhcprelay 6 }

es2410cMulticast        OBJECT IDENTIFIER ::= { es2410cProduces 26 }

es2410cIgmpSetting      OBJECT IDENTIFIER ::= { es2410cMulticast 1 }

es2410cIgmpSnoopingState OBJECT-TYPE
    SYNTAX         INTEGER(0|1)
    MAX-ACCESS     read-write
    STATUS         current
    DESCRIPTION
        "Set IGMP Snooping State.
         0 : Disable,
         1 : Enable.
        "
    ::= { es2410cIgmpSetting 1 }

es2410cIgmpSnoopingUnregisterMulticastFlooding OBJECT-TYPE
    SYNTAX         INTEGER(0|1)
    MAX-ACCESS     read-write
    STATUS         current
    DESCRIPTION
        "Set Unregister Multicast Flooding State.
         0 : Disable,
         1 : Enable.
        "
    ::= { es2410cIgmpSetting 2 }

es2410cIgmpSnoopingGeneralQueryInterval  OBJECT-TYPE
    SYNTAX      INTEGER(1..2000)
    MAX-ACCESS  read-write
    STATUS      current
    DESCRIPTION
        "Set general query interval.
         interval: from 1 to 2000 second(s)"
    ::= { es2410cIgmpSetting 3 }

es2410cIgmpSnoopingGeneralQueryMaxResponseTime  OBJECT-TYPE
    SYNTAX      INTEGER(1..10)
    MAX-ACCESS  read-write
    STATUS      current
    DESCRIPTION
        "Set general query max response time.
         time: from 1 to 10 second(s)"
    ::= { es2410cIgmpSetting 4 }

es2410cIgmpSnoopingGeneralQueryTimeout  OBJECT-TYPE
    SYNTAX      INTEGER(1..30)
    MAX-ACCESS  read-write
    STATUS      current
    DESCRIPTION
        "Set general query timeout.
         timeout: from 1 to 30 second(s)"
    ::= { es2410cIgmpSetting 5 }

es2410cIgmpSnoopingSpecificQueryCount  OBJECT-TYPE
    SYNTAX      INTEGER(1..10)
    MAX-ACCESS  read-write
    STATUS      current
    DESCRIPTION
        "Set specific query count.
         count: from 1 to 10"
    ::= { es2410cIgmpSetting 6 }

es2410cIgmpSnoopingSpecificQueryMaxResponseTime  OBJECT-TYPE
    SYNTAX      INTEGER(1..10)
    MAX-ACCESS  read-write
    STATUS      current
    DESCRIPTION
        "Set specific query max response time.
         time: from 1 to 10 second(s)"
    ::= { es2410cIgmpSetting 7 }

es2410cIgmpSnoopingSpecificQueryTimeout  OBJECT-TYPE
    SYNTAX      INTEGER(1..30)
    MAX-ACCESS  read-write
    STATUS      current
    DESCRIPTION
        "Set specific query timeout.
         timeout: from 1 to 30 second(s)"
    ::= { es2410cIgmpSetting 8 }

es2410cIgmpSnoopingSettingTable  OBJECT-TYPE
    SYNTAX      SEQUENCE OF ES2410CIgmpSnoopingSettingEntry
    MAX-ACCESS  not-accessible
    STATUS      current
    DESCRIPTION
        " "
    ::= { es2410cIgmpSetting 9 }

es2410cIgmpSnoopingSettingEntry OBJECT-TYPE
    SYNTAX      ES2410CIgmpSnoopingSettingEntry
    MAX-ACCESS  not-accessible
    STATUS      current
    DESCRIPTION
        "Entry(s) for IGMP snooping port setting table."
    INDEX {es2410cIgmpSnoopingSettingPortIndex}
    ::= { es2410cIgmpSnoopingSettingTable 1 }

ES2410CIgmpSnoopingSettingEntry ::=
SEQUENCE {
    es2410cIgmpSnoopingSettingPortIndex		INTEGER,
    es2410cIgmpSnoopingSettingMulticastGroupLimit		INTEGER,
    es2410cIgmpSnoopingSettingIGMPRouter		INTEGER
}

es2410cIgmpSnoopingSettingPortIndex  OBJECT-TYPE
    SYNTAX      INTEGER(1..26)
    MAX-ACCESS  not-accessible
    STATUS      current
    DESCRIPTION
        "The port index of IGMP snooping port setting table."
    ::= { es2410cIgmpSnoopingSettingEntry 1 }

es2410cIgmpSnoopingSettingMulticastGroupLimit OBJECT-TYPE
    SYNTAX         INTEGER(0..256)
    MAX-ACCESS     read-write
    STATUS         current
    DESCRIPTION
        "Set multicast group limit. Limit range from 0 to 256."
    ::= { es2410cIgmpSnoopingSettingEntry 2 }

es2410cIgmpSnoopingSettingIGMPRouter OBJECT-TYPE
    SYNTAX         INTEGER(0|1)
    MAX-ACCESS     read-write
    STATUS         current
    DESCRIPTION
        "Set IGMP router.
         0 : non-router,
         1 : router.
        "
    ::= { es2410cIgmpSnoopingSettingEntry 3 }

es2410cIgmpVlan      OBJECT IDENTIFIER ::= { es2410cMulticast 2 }

es2410cIgmpVlanNumbers  OBJECT-TYPE
    SYNTAX      INTEGER(1..256)
    MAX-ACCESS  read-only
    STATUS      current
    DESCRIPTION
        "Total numbers for igmp vlan."
    ::= { es2410cIgmpVlan 1 }

es2410cIgmpVlanCreatStatus OBJECT-TYPE
    SYNTAX         INTEGER(0..4094)
    MAX-ACCESS     read-write
    STATUS         current
    DESCRIPTION
        "Create IGMP Vlan Vid.
         Vid: from 1 to 4094"
    ::= { es2410cIgmpVlan 2 }

es2410cIgmpVlanTable  OBJECT-TYPE
    SYNTAX      SEQUENCE OF ES2410CIgmpVlanEntry
    MAX-ACCESS  not-accessible
    STATUS      current
    DESCRIPTION
        " "
    ::= { es2410cIgmpVlan 3 }

es2410cIgmpVlanEntry OBJECT-TYPE
    SYNTAX      ES2410CIgmpVlanEntry
    MAX-ACCESS  not-accessible
    STATUS      current
    DESCRIPTION
        "Entry(s) for Igmp Vlan table."
    INDEX {es2410cIgmpVlanIndex}
    ::= { es2410cIgmpVlanTable 1 }

ES2410CIgmpVlanEntry ::=
SEQUENCE {
    es2410cIgmpVlanIndex						INTEGER,
    es2410cIgmpVlanVid					    INTEGER,
    es2410cIgmpVlanRowStatus					INTEGER
}

es2410cIgmpVlanIndex  OBJECT-TYPE
    SYNTAX      INTEGER(1..64)
    MAX-ACCESS  not-accessible
    STATUS      current
    DESCRIPTION
        "The entry index of Igmp Vlan table."
    ::= { es2410cIgmpVlanEntry 1 }

es2410cIgmpVlanVid OBJECT-TYPE
    SYNTAX         INTEGER(1..4094)
    MAX-ACCESS     read-only
    STATUS         current
    DESCRIPTION
        "The vid of igmp vlan entry."
    ::= { es2410cIgmpVlanEntry 2 }

es2410cIgmpVlanRowStatus  OBJECT-TYPE
    SYNTAX      INTEGER(1..3)
    MAX-ACCESS  read-write
    STATUS      current
    DESCRIPTION
        "The row status of igmp vlan entry.
         1 : active,
         2 : not-inService,
         3 : delete
        "
    ::= { es2410cIgmpVlanEntry 3 }

es2410cIgmpVlanGroupAllow      OBJECT IDENTIFIER ::= { es2410cMulticast 3 }

es2410cIgmpVlanGroupAllowCreatStatus OBJECT-TYPE
    SYNTAX         INTEGER(0..4094)
    MAX-ACCESS     read-write
    STATUS         current
    DESCRIPTION
        "Create IGMP Group Allow Entry."
    ::= { es2410cIgmpVlanGroupAllow 1 }

es2410cIgmpVlanGroupAllowTable  OBJECT-TYPE
    SYNTAX      SEQUENCE OF ES2410CIgmpVlanGroupAllowEntry
    MAX-ACCESS  not-accessible
    STATUS      current
    DESCRIPTION
        " "
    ::= { es2410cIgmpVlanGroupAllow 2 }

es2410cIgmpVlanGroupAllowEntry OBJECT-TYPE
    SYNTAX      ES2410CIgmpVlanGroupAllowEntry
    MAX-ACCESS  not-accessible
    STATUS      current
    DESCRIPTION
        "Entry(s) for Igmp Group Allow table."
    INDEX {es2410cIgmpVlanGroupAllowIndex}
    ::= { es2410cIgmpVlanGroupAllowTable 1 }

ES2410CIgmpVlanGroupAllowEntry ::=
SEQUENCE {
    es2410cIgmpVlanGroupAllowIndex				    INTEGER,
    es2410cIgmpVlanGroupAllowStartAddress			IpAddress,
    es2410cIgmpVlanGroupAllowEndAddress				IpAddress,
    es2410cIgmpVlanGroupAllowVid				    INTEGER,
    es2410cIgmpVlanGroupAllowPortMember				DisplayString,
    es2410cIgmpVlanGroupAllowRowStatus				INTEGER
}

es2410cIgmpVlanGroupAllowIndex  OBJECT-TYPE
    SYNTAX      INTEGER(1..256)
    MAX-ACCESS  not-accessible
    STATUS      current
    DESCRIPTION
        "The entry index of Igmp Group Allow table."
    ::= { es2410cIgmpVlanGroupAllowEntry 1 }

es2410cIgmpVlanGroupAllowStartAddress OBJECT-TYPE
    SYNTAX      IpAddress
    MAX-ACCESS  read-write
    STATUS      current
    DESCRIPTION
        "Start address of Group Allow entry."
    ::= { es2410cIgmpVlanGroupAllowEntry 2 }

es2410cIgmpVlanGroupAllowEndAddress OBJECT-TYPE
    SYNTAX      IpAddress
    MAX-ACCESS  read-write
    STATUS      current
    DESCRIPTION
        "End address of Group Allow entry."
    ::= { es2410cIgmpVlanGroupAllowEntry 3 }

es2410cIgmpVlanGroupAllowVid  OBJECT-TYPE
    SYNTAX      INTEGER(0..4094)
    MAX-ACCESS  read-write
    STATUS      current
    DESCRIPTION
        "VLAN ID of Group Allow entry."
    ::= { es2410cIgmpVlanGroupAllowEntry 4 }

es2410cIgmpVlanGroupAllowPortMember  OBJECT-TYPE
    SYNTAX      DisplayString
    MAX-ACCESS  read-write
    STATUS      current
    DESCRIPTION
        "Port Member of Group Allow entry."
    ::= { es2410cIgmpVlanGroupAllowEntry 5 }

es2410cIgmpVlanGroupAllowRowStatus  OBJECT-TYPE
    SYNTAX      INTEGER(1..3)
    MAX-ACCESS  read-write
    STATUS      current
    DESCRIPTION
        "The row status of igmp group allow entry.
         1 : active,
         2 : not-inService,
         3 : delete
        "
    ::= { es2410cIgmpVlanGroupAllowEntry 6 }

es2410cMvrSetting      OBJECT IDENTIFIER ::= { es2410cMulticast 4 }

es2410cMvrSettingMulticastVlanRegistration OBJECT-TYPE
    SYNTAX         INTEGER(0|1)
    MAX-ACCESS     read-write
    STATUS         current
    DESCRIPTION
        "Set MVR State.
         0 : Disable,
         1 : Enable.
        "
    ::= { es2410cMvrSetting 1 }

es2410cMvrSettingMulticastVlanIdConf  OBJECT-TYPE
    SYNTAX      INTEGER(2..4094)
    MAX-ACCESS  read-write
    STATUS      current
    DESCRIPTION
        "Get/Set multicast vlan vid. This value whill be kept in buffer.
        Will be activity after enable Multicast Vlan Registration.
         vid: from 2 to 4094, 1: reserved for default vlan"
    ::= { es2410cMvrSetting 2 }

es2410cMvrSettingMulticastVlanIdShow  OBJECT-TYPE
    SYNTAX      INTEGER(0..4094)
    MAX-ACCESS  read-only
    STATUS      current
    DESCRIPTION
        "Get the multicast vlan vid real value.
         vid: from 2 to 4094"
    ::= { es2410cMvrSetting 3 }

es2410cMvrSettingTable  OBJECT-TYPE
    SYNTAX      SEQUENCE OF ES2410CMvrSettingEntry
    MAX-ACCESS  not-accessible
    STATUS      current
    DESCRIPTION
        " "
    ::= { es2410cMvrSetting 4 }

es2410cMvrSettingEntry OBJECT-TYPE
    SYNTAX      ES2410CMvrSettingEntry
    MAX-ACCESS  not-accessible
    STATUS      current
    DESCRIPTION
        "Entry(s) for MVR port setting table."
    INDEX {es2410cMvrSettingPort}
    ::= { es2410cMvrSettingTable 1 }

ES2410CMvrSettingEntry ::=
SEQUENCE {
    es2410cMvrSettingPort		    INTEGER,
    es2410cMvrSettingServerType		INTEGER,
    es2410cMvrSettingTagging		    INTEGER
}

es2410cMvrSettingPort  OBJECT-TYPE
    SYNTAX      INTEGER(1..26)
    MAX-ACCESS  not-accessible
    STATUS      current
    DESCRIPTION
        "The port index of MVR port setting table."
    ::= { es2410cMvrSettingEntry 1 }

es2410cMvrSettingServerType OBJECT-TYPE
    SYNTAX         INTEGER(0..2)
    MAX-ACCESS     read-write
    STATUS         current
    DESCRIPTION
        "Set mvr service type.
         type: 0(None), 1(Client), 2(Router).At least one clent or router port."
    ::= { es2410cMvrSettingEntry 2 }

es2410cMvrSettingTagging OBJECT-TYPE
    SYNTAX         INTEGER(0|1)
    MAX-ACCESS     read-write
    STATUS         current
    DESCRIPTION
        "Set mvr tagging.
         0 : untag-out,
         1 : tag-out.
        "
    ::= { es2410cMvrSettingEntry 3 }

es2410cMulticastStatus      OBJECT IDENTIFIER ::= { es2410cMulticast 5 }

es2410cMulticastStatusTable  OBJECT-TYPE
    SYNTAX      SEQUENCE OF ES2410CMulticastStatusEntry
    MAX-ACCESS  not-accessible
    STATUS      current
    DESCRIPTION
        " "
    ::= { es2410cMulticastStatus 1 }

es2410cMulticastStatusEntry OBJECT-TYPE
    SYNTAX      ES2410CMulticastStatusEntry
    MAX-ACCESS  not-accessible
    STATUS      current
    DESCRIPTION
        "Entry(s) for Multicast Status table."
    INDEX {es2410cMulticastStatusIndex}
    ::= { es2410cMulticastStatusTable 1 }

es2410cMulticastStatusEntry ::=
SEQUENCE {
    es2410cMulticastStatusIndex				INTEGER,
    es2410cMulticastStatusVid   				INTEGER,
    es2410cMulticastStatusMulticastGroup 				IpAddress,
    es2410cMulticastStatusPortMember				DisplayString
}

es2410cMulticastStatusIndex  OBJECT-TYPE
    SYNTAX      INTEGER(1..256)
    MAX-ACCESS  read-only
    STATUS      current
    DESCRIPTION
        "The port index of trunk table."
    ::= { es2410cMulticastStatusEntry 1 }

es2410cMulticastStatusVid OBJECT-TYPE
    SYNTAX         INTEGER(1..4094)
    MAX-ACCESS     read-only
    STATUS         current
    DESCRIPTION
        "The Vid of multicast status table."
    ::= { es2410cMulticastStatusEntry 2 }

es2410cMulticastStatusMulticastGroup OBJECT-TYPE
    SYNTAX      IpAddress
    MAX-ACCESS  read-only
    STATUS      current
    DESCRIPTION
        "The Multicast Group of multicast status table."
    ::= { es2410cMulticastStatusEntry 3 }

es2410cMulticastStatusPortMember  OBJECT-TYPE
    SYNTAX      DisplayString
    MAX-ACCESS  read-only
    STATUS      current
    DESCRIPTION
        "The Port Member of multicast status table."
    ::= { es2410cMulticastStatusEntry 4 }

es2410cRadiusIgmpSetting      OBJECT IDENTIFIER ::= { es2410cMulticast 6 }

es2410cRadiusIgmpServer1 OBJECT-TYPE
    SYNTAX      IpAddress
    MAX-ACCESS  read-write
    STATUS      current
    DESCRIPTION
        "Radius Igmp Server1"
    ::= { es2410cRadiusIgmpSetting 1 }

es2410cRadiusIgmpPortNumber1 OBJECT-TYPE
    SYNTAX      INTEGER(1..65535)
    MAX-ACCESS  read-write
    STATUS      current
    DESCRIPTION
        "Set Radius Igmp port number1.
         port number: from 1 to 65535"
    ::= { es2410cRadiusIgmpSetting 2 }

es2410cRadiusIgmpServer2 OBJECT-TYPE
    SYNTAX      IpAddress
    MAX-ACCESS  read-write
    STATUS      current
    DESCRIPTION
        "Radius Igmp Server2"
    ::= { es2410cRadiusIgmpSetting 3 }

es2410cRadiusIgmpPortNumber2 OBJECT-TYPE
    SYNTAX      INTEGER(1..65535)
    MAX-ACCESS  read-write
    STATUS      current
    DESCRIPTION
        "Set Radius Igmp port number2.
         port number: from 1 to 65535"
    ::= { es2410cRadiusIgmpSetting 4 }

es2410cRadiusIgmpSecretKey1  OBJECT-TYPE
    SYNTAX         DisplayString
    MAX-ACCESS     read-write
    STATUS         current
    DESCRIPTION
        "Set Radius Igmp secret key1"
    ::= { es2410cRadiusIgmpSetting 5 }

es2410cRadiusIgmpAccountingServer1 OBJECT-TYPE
    SYNTAX      IpAddress
    MAX-ACCESS  read-write
    STATUS      current
    DESCRIPTION
        "Radius Igmp Accounting Server1"
    ::= { es2410cRadiusIgmpSetting 6 }

es2410cRadiusIgmpAccountingPortNumber1 OBJECT-TYPE
    SYNTAX      INTEGER(1..65535)
    MAX-ACCESS  read-write
    STATUS      current
    DESCRIPTION
        "Set Radius Igmp Accounting port number1.
         port number: from 1 to 65535"
    ::= { es2410cRadiusIgmpSetting 7 }

es2410cRadiusIgmpAccountingServer2 OBJECT-TYPE
    SYNTAX      IpAddress
    MAX-ACCESS  read-write
    STATUS      current
    DESCRIPTION
        "Radius Igmp Accounting Server2"
    ::= { es2410cRadiusIgmpSetting 8 }

es2410cRadiusIgmpAccountingPortNumber2 OBJECT-TYPE
    SYNTAX      INTEGER(1..65535)
    MAX-ACCESS  read-write
    STATUS      current
    DESCRIPTION
        "Set Radius Igmp Accounting port number2.
         port number: from 1 to 65535"
    ::= { es2410cRadiusIgmpSetting 9 }

es2410cRadiusIgmpSecretKey2  OBJECT-TYPE
    SYNTAX         DisplayString
    MAX-ACCESS     read-write
    STATUS         current
    DESCRIPTION
        "Set Radius Igmp secret key2"
    ::= { es2410cRadiusIgmpSetting 10 }

es2410cRadiusIgmpResponseTimeout OBJECT-TYPE
    SYNTAX      INTEGER(2..60)
    MAX-ACCESS  read-write
    STATUS      current
    DESCRIPTION
        "Set radius-igmp timeout.
         time: 2 ~ 60 seconds"
    ::= { es2410cRadiusIgmpSetting 11 }

es2410cRadiusIgmpNumberOfRetry OBJECT-TYPE
    SYNTAX      INTEGER(0..10)
    MAX-ACCESS  read-write
    STATUS      current
    DESCRIPTION
        "Set radius-igmp number of retry.
         value: 0 ~ 10 times"
    ::= { es2410cRadiusIgmpSetting 12 }

es2410cRadiusIgmpPortMember  OBJECT-TYPE
    SYNTAX      DisplayString
    MAX-ACCESS  read-write
    STATUS      current
    DESCRIPTION
        "The Port Member of  Radius Igmp. 0: no port member"
    ::= { es2410cRadiusIgmpSetting 13 }

END
