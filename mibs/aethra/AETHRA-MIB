-- *****************************************************************
-- AETHRA-MIB: Aethra Telecommunications Enterprise MIB file
-- ATOS Compatible Version: 5.6 and previous, minimum version for all features is 5.6.14
--
-- Copyright (c) 2012 by
-- A TLC srl - Aethra Telecommunications
-- Legal Office: Via G.B. Martini,2 - 00198 ROMA - ITALY
-- Operating Office: Via 1° Maggio, 26 - 60131 ANCONA - ITALY
-- Phone: +39 071 250 651
-- E-Mail: info@aethra.com
--
-- All rights reserved.
--
-- *****************************************************************

AETHRA-MIB DEFINITIONS ::= BEGIN

    IMPORTS
      OBJECT-TYPE
        FROM RFC-1212
      TRAP-TYPE
        FROM RFC-1215
      enterprises, IpAddress, Counter, Gauge
        FROM RFC1155-SMI
      DisplayString, PhysAddress, ifDescr, ifIndex
        FROM RFC1213-MIB
      IANAifType
        FROM IANAifType-MIB;

--
-- Node definitions
--
-- Prefix: iso.org.dod.internet.private.enterprise (1.3.6.1.4.1)
--

  aethra OBJECT IDENTIFIER  ::= { enterprises 7745 }

  atosnt OBJECT IDENTIFIER  ::= { aethra 5 }

  tools  OBJECT IDENTIFIER  ::= { atosnt 1 }  -- Tools Node

  system OBJECT IDENTIFIER  ::= { atosnt 2 }  -- System Node

  dsl    OBJECT IDENTIFIER  ::= { atosnt 3 }  -- DSL Node

  voip   OBJECT IDENTIFIER  ::= { atosnt 4 }  -- Voip Node

  traps  OBJECT IDENTIFIER  ::= { atosnt 5 }  -- Traps Node

  ifc    OBJECT IDENTIFIER  ::= { atosnt 6 }  -- Interfaces Node



fileTransfer OBJECT IDENTIFIER ::= { tools 1 } -- fileTransfer Node

  fileTransferProtocol  OBJECT-TYPE
      SYNTAX    INTEGER {
						      tftp(1),
						      ftp(2),
						      http(3),
						      file(4),
						      scp(5)
					      }
      ACCESS    read-write
      STATUS      mandatory
      DESCRIPTION  "Set this parameter to configure the protocol for file transfer command.
      							The protocol file(4) reads from a local disk for download command,
      							writes to a local disk for upload.
                    OID: 1.3.6.1.4.1.7745.5.1.1.1"
      ::= { fileTransfer 1 }

  fileTransferFileName  OBJECT-TYPE
      SYNTAX    DisplayString
      ACCESS    read-write
      STATUS      mandatory
      DESCRIPTION  "Set this parameter to configure the name of the file to download or upload.
      							When using HTTP protocol set full url as fileTransferFileName.
                    OID: 1.3.6.1.4.1.7745.5.1.1.2"
      ::= { fileTransfer 2 }

  fileTransferServerName  OBJECT-TYPE
      SYNTAX    DisplayString
      ACCESS    read-write
      STATUS      mandatory
      DESCRIPTION  "Set this parameter to configure the name or IP address of remote server
      							when using TFTP or FTP protocol. When not configured systemDefaultTftpServer
      							or systemDefaultFtpServer is used for the respective protocols.
                    OID: 1.3.6.1.4.1.7745.5.1.1.3"
      ::= { fileTransfer 3 }

  fileTransferOption  OBJECT-TYPE
      SYNTAX    INTEGER {
						      firmware(1),
						      boot(2),
						      userconf(3),
						      logs(4),
						      package(5),
						      localfile(6),
						      welcome(7),
						      license(8),
						      certificate(9),
						      defaultconf(10),
						      bannerPre(11),
						      bannerPost(12)
     						 }
      ACCESS    read-write
      STATUS      mandatory
      DESCRIPTION  "Set this parameter to configure the type of file you are downloading or uploading.
      							When not configured firmware type is used.
      							firmware(1) is the operating system file,
      							boot(2) is the system boot,
      							userconf(3) is the current system configuration file,
      							logs(4) is the logs file and is available only for upload command,
      							package(5) is bundle is a package that contains boot and os in a single file,
      							localfile(6) is any file you want to download or upload in the system,
      							welcome(7) is a text message displayed before access to system console by telnet or ssh,
      							license(8) is a license file to enable advanced system features,
      							certificate(9) is the custom certificate file for the security protocol system (SSL),
      							defaultconf(10) is the custom default configuration file,
      							bannerPre(10) is available only from version 5.6.11, is a custom pre login banner file,
      							bannerPost(10)is available only from version 5.6.11, is a custom post login banner file.
                    OID: 1.3.6.1.4.1.7745.5.1.1.4"
      ::= { fileTransfer 4 }

  fileTransferStorageFileName  OBJECT-TYPE
      SYNTAX    DisplayString
      ACCESS    read-write
      STATUS      mandatory
      DESCRIPTION  "Set this parameter to configure the name of the local file when using file(4) protocol.
                    OID: 1.3.6.1.4.1.7745.5.1.1.5"
      ::= { fileTransfer 5 }

  fileTransferExec  OBJECT-TYPE
      SYNTAX    INTEGER {
						      noaction(0),
						      download(1),
						      upload(2)
					      }
      ACCESS    read-write
      STATUS      mandatory
      DESCRIPTION  "Set this parameter to start download or upload.
                    OID: 1.3.6.1.4.1.7745.5.1.1.6"
      ::= { fileTransfer 6 }

  fileTransferStatus  OBJECT-TYPE
      SYNTAX DisplayString
      ACCESS    read-only
      STATUS      mandatory
      DESCRIPTION  "Get this parameter to read the current status of file transfer command.
                    OID: 1.3.6.1.4.1.7745.5.1.1.7"
      ::= { fileTransfer 7 }


ping OBJECT IDENTIFIER ::= { tools 2 }   -- Ping Node

pingParameters OBJECT IDENTIFIER ::= { ping 1 }   -- Ping Parameters Node

  pingHost  OBJECT-TYPE
      SYNTAX    DisplayString
      ACCESS    read-write
      STATUS      mandatory
      DESCRIPTION  "Set this parameter to configure the host name or IP address to ping.
                    OID: 1.3.6.1.4.1.7745.5.1.2.1.1"
      ::= { pingParameters 1 }

  pingSize  OBJECT-TYPE
      SYNTAX    INTEGER (1..8192)
      ACCESS    read-write
      STATUS      mandatory
      DESCRIPTION  "Set this parameter to configure the size of ping packet.
                    OID: 1.3.6.1.4.1.7745.5.1.2.1.2"
      ::= { pingParameters 2 }

  pingTries  OBJECT-TYPE
      SYNTAX    INTEGER (1..65535)
      ACCESS    read-write
      STATUS      mandatory
      DESCRIPTION  "Set this parameter to configure the number of ping tries.
                    OID: 1.3.6.1.4.1.7745.5.1.2.1.3"
      ::= { pingParameters 3 }

  pingTTL  OBJECT-TYPE
      SYNTAX    INTEGER (1..255)
      ACCESS    read-write
      STATUS      mandatory
      DESCRIPTION  "Set this parameter to configure ping TTL option.
                    OID: 1.3.6.1.4.1.7745.5.1.2.1.4"
      ::= { pingParameters 4 }

  pingTimeOut  OBJECT-TYPE
      SYNTAX    INTEGER (1..65535)
      ACCESS    read-write
      STATUS      mandatory
      DESCRIPTION  "Set this parameter to configure ping response timeout (sec).
                    OID: 1.3.6.1.4.1.7745.5.1.2.1.5"
      ::= { pingParameters 5 }

  pingSource  OBJECT-TYPE
      SYNTAX    DisplayString
      ACCESS    read-write
      STATUS      mandatory
      DESCRIPTION  "Set this parameter to configure the name or IP address of the ping source.
                    OID: 1.3.6.1.4.1.7745.5.1.2.1.6"
      ::= { pingParameters 6 }

  pingStart  OBJECT-TYPE
      SYNTAX    INTEGER
      {
      noaction(0),
      start(1)
      }
      ACCESS    read-write
      STATUS      mandatory
      DESCRIPTION  "Set this parameter to start ping.
                    OID: 1.3.6.1.4.1.7745.5.1.2.1.7"
      ::= { pingParameters 7 }

  pingStatus  OBJECT-TYPE
      SYNTAX    DisplayString
      ACCESS    read-only
      STATUS      mandatory
      DESCRIPTION  "Get this parameter to read the current status of ping command.
                    OID: 1.3.6.1.4.1.7745.5.1.2.1.8"
      ::= { pingParameters 8 }

pingStatistics OBJECT IDENTIFIER ::= { ping 2 }   -- Ping Statistics Node

  pingTXpacket  OBJECT-TYPE
      SYNTAX    INTEGER
      ACCESS    read-only
      STATUS      mandatory
      DESCRIPTION  "Get this parameter to read the number of packets transmitted.
                    OID: 1.3.6.1.4.1.7745.5.1.2.2.1"
      ::= { pingStatistics 1 }

  pingRXpacket  OBJECT-TYPE
      SYNTAX    INTEGER
      ACCESS    read-only
      STATUS      mandatory
      DESCRIPTION  "Get this parameter to read the number of packets received.
                    OID: 1.3.6.1.4.1.7745.5.1.2.2.2"
      ::= { pingStatistics 2 }

  pingLOSTpacket  OBJECT-TYPE
      SYNTAX    INTEGER
      ACCESS    read-only
      STATUS      mandatory
      DESCRIPTION  "Get this parameter to read the number of packets losted.
                    OID: 1.3.6.1.4.1.7745.5.1.2.2.3"
      ::= { pingStatistics 3 }

  pingMinRTT  OBJECT-TYPE
      SYNTAX    INTEGER
      ACCESS    read-only
      STATUS      mandatory
      DESCRIPTION  "Get this parameter to read the minimum Round Trip Time (RTT) value.
                    OID: 1.3.6.1.4.1.7745.5.1.2.2.4"
      ::= { pingStatistics 4 }

  pingMaxRTT  OBJECT-TYPE
      SYNTAX    INTEGER
      ACCESS    read-only
      STATUS      mandatory
      DESCRIPTION  "Get this parameter to read the maximum Round Trip Time (RTT) value.
                    OID: 1.3.6.1.4.1.7745.5.1.2.2.5"
      ::= { pingStatistics 5 }

  pingAvgRTT  OBJECT-TYPE
      SYNTAX    INTEGER
      ACCESS    read-only
      STATUS      mandatory
      DESCRIPTION  "Get this parameter to read the average Round Trip Time (RTT) value.
                    OID: 1.3.6.1.4.1.7745.5.1.2.2.6"
      ::= { pingStatistics 6 }

-- System Parameters

  systemLoglevel  OBJECT-TYPE
      SYNTAX    INTEGER (1..5)
      ACCESS    read-write
      STATUS      mandatory
      DESCRIPTION  "Set this parameter to configure the log level of the node system.
      							OID: 1.3.6.1.4.1.7745.5.2.1"
      ::= { system 1 }

  systemDescription OBJECT-TYPE
      SYNTAX DisplayString
      ACCESS read-write
      STATUS mandatory
      DESCRIPTION  "Set this parameter to configure system description.
      							OID: 1.3.6.1.4.1.7745.5.2.2 "
      ::= { system 2 }

    systemName OBJECT-TYPE
      SYNTAX DisplayString
      ACCESS read-write
      STATUS mandatory
      DESCRIPTION  "Set this parameter to configure system name, it's also used as network hostname.
      							OID: 1.3.6.1.4.1.7745.5.2.3"
      ::= { system 3 }

    systemLocalDomain OBJECT-TYPE
      SYNTAX DisplayString
      ACCESS read-write
      STATUS mandatory
      DESCRIPTION  "Set this parameter to configure system local domain, it's also used as network workgroup.
      							OID: 1.3.6.1.4.1.7745.5.2.4"
      ::= { system 4 }

    systemDefaultTftpServer OBJECT-TYPE
      SYNTAX DisplayString
      ACCESS read-write
      STATUS mandatory
      DESCRIPTION  "Set this parameter to configure the name or IP address for the default remote TFTP server.
      							OID: 1.3.6.1.4.1.7745.5.2.5"
      ::= { system 5 }

    systemTftpLocalAdd OBJECT-TYPE
      SYNTAX IpAddress
      ACCESS read-write
      STATUS mandatory
      DESCRIPTION  "Set this parameter to configure the name or the local IP address used by the TFTP client.
      							OID: 1.3.6.1.4.1.7745.5.2.6"
      ::= { system 6 }

    systemDefaultFtpServer OBJECT-TYPE
      SYNTAX DisplayString
      ACCESS read-write
      STATUS mandatory
      DESCRIPTION  "Set this parameter to configure the name or IP address and port for the default remote FTP server.
      							OID: 1.3.6.1.4.1.7745.5.2.7"
      ::= { system 7 }

    systemFtpLocalAdd OBJECT-TYPE
      SYNTAX IpAddress
      ACCESS read-write
      STATUS mandatory
      DESCRIPTION  "Set this parameter to configure the name or the local IP address used by the FTP client.
      							OID: 1.3.6.1.4.1.7745.5.2.8"
      ::= { system 8 }

    systemFtpUsername OBJECT-TYPE
      SYNTAX DisplayString
      ACCESS read-write
      STATUS mandatory
      DESCRIPTION  "Set this parameter to configure the username for the default remote FTP server.
      							OID: 1.3.6.1.4.1.7745.5.2.9"
      ::= { system 9 }

    systemFtpPassword OBJECT-TYPE
      SYNTAX DisplayString
      ACCESS read-write
      STATUS mandatory
      DESCRIPTION  "Set this parameter to configure the password for the default remote FTP server.
      							OID: 1.3.6.1.4.1.7745.5.2.10"
      ::= { system 10 }

    systemAAAProfile OBJECT-TYPE
      SYNTAX DisplayString
      ACCESS read-write
      STATUS mandatory
      DESCRIPTION  "Set this parameter to configure the AAA profile used by the system.
      							OID: 1.3.6.1.4.1.7745.5.2.11 "
      ::= { system 11 }

   systemAAALogTimeout OBJECT-TYPE
      SYNTAX INTEGER (1..300)
      ACCESS read-write
      STATUS mandatory
      DESCRIPTION  "Set this parameter to configure the AAA login timeout.
      							OID: 1.3.6.1.4.1.7745.5.2.12"
      ::= { system 12 }

   systemBackupAuth OBJECT-TYPE
      SYNTAX    INTEGER {
	                off(0),
	                on(1)
                }
      ACCESS read-write
      STATUS mandatory
      DESCRIPTION  "Set this parameter to enable the backup authentication system.
      							OID: 1.3.6.1.4.1.7745.5.2.13"
      ::= { system 13 }

   systemScrollLine OBJECT-TYPE
      SYNTAX INTEGER (1..255)
      ACCESS read-write
      STATUS mandatory
      DESCRIPTION  "Set this parameter to enable the system scroll line.
      							OID: 1.3.6.1.4.1.7745.5.2.14"
      ::= { system 14 }

    systemKernelLogs OBJECT-TYPE
      SYNTAX    INTEGER {
	                off(0),
	                on(1)
                }
      ACCESS read-write
      STATUS mandatory
      DESCRIPTION  "Set this parameter to enable the system kernel logs
										OID: 1.3.6.1.4.1.7745.5.2.15"
      ::= { system 15 }

    systemCryptedPassword OBJECT-TYPE
      SYNTAX    INTEGER {
	                off(0),
	                on(1)
                }
      ACCESS read-write
      STATUS mandatory
      DESCRIPTION  "Set this parameter to enable the system crypted password.
      							OID: 1.3.6.1.4.1.7745.5.2.16"
      ::= { system 16 }

    systemSave  OBJECT-TYPE
      SYNTAX    INTEGER {
					      	noaction(0),
					      	save(1)
					      }
      ACCESS    read-write
      STATUS      mandatory
      DESCRIPTION  "Set this parameter to save current configuration.
                    OID: 1.3.6.1.4.1.7745.5.2.17"
      ::= { system 17 }

systemRestart OBJECT IDENTIFIER ::= { system 18 } -- Restart Node

  restartOption  OBJECT-TYPE
      SYNTAX    INTEGER {
						      saveConf(0),
						      notSaveConf(1),
						      restoreDefaultConf(2),
   						      restoreFactoryDefault(3)
					      }
      ACCESS    read-write
      STATUS      mandatory
      DESCRIPTION  "Set this parameter to choose restart command option.
					saveConf(0) saving configuration changes before restart the system,
			        notSaveConf(1) restart the system without saving configuration changes,
			        restoreDefaultConf(2) restart the system with the default configuration,
			        restoreFactoryDefault(3) available only from version 5.6.14,
			        restart the system with the factory default.
                    OID: 1.3.6.1.4.1.7745.5.2.18.1"
      ::= { systemRestart 1 }

  restartDelay  OBJECT-TYPE
      SYNTAX    INTEGER (0..30)
      ACCESS    read-write
      STATUS      mandatory
      DESCRIPTION  "Set this parameter to configure restart timeout (sec).
                    OID: 1.3.6.1.4.1.7745.5.2.18.2"
      ::= { systemRestart 2 }


  restartExec  OBJECT-TYPE
      SYNTAX    INTEGER {
						      noaction(0),
						      restart(1)
					      }
      ACCESS    read-write
      STATUS      mandatory
      DESCRIPTION  "Set this parameter to restart the system.
                    OID: 1.3.6.1.4.1.7745.5.2.18.3"
      ::= { systemRestart 3 }

   restartStatus  OBJECT-TYPE
      SYNTAX DisplayString
      ACCESS    read-only
      STATUS      mandatory
      DESCRIPTION  "Get this parameter to read the current status of restart command.
                    OID: OID: 1.3.6.1.4.1.7745.5.2.18.4"
      ::= { systemRestart 4 }

performance OBJECT IDENTIFIER ::= { system 19 } -- Performance Monitor Node

  performanceCpuAvg1min  OBJECT-TYPE
      SYNTAX    INTEGER
      ACCESS    read-only
      STATUS      mandatory
      DESCRIPTION  "Get this parameter to read the CPU average utilization in 1 minute (in %).
                    OID: 1.3.6.1.4.1.7745.5.2.19.1"
      ::= { performance 1 }

  performanceCpuAvg5min  OBJECT-TYPE
      SYNTAX    INTEGER
      ACCESS    read-only
      STATUS      mandatory
      DESCRIPTION  "Get this parameter to read the CPU average utilization in 5 minute (in %).
                    OID: 1.3.6.1.4.1.7745.5.2.19.2"
      ::= { performance 2 }

  performanceCpuAvg15min  OBJECT-TYPE
      SYNTAX    INTEGER
      ACCESS    read-only
      STATUS      mandatory
      DESCRIPTION  "Get this parameter to read the CPU average utilization in 15 minute (in %).
                    OID: 1.3.6.1.4.1.7745.5.2.19.3"
      ::= { performance 3 }

  performanceDynMemLoad  OBJECT-TYPE
      SYNTAX    INTEGER
      ACCESS    read-only
      STATUS      mandatory
      DESCRIPTION  "Get this parameter to read the usage of dynamic memory (in %).
                    OID: 1.3.6.1.4.1.7745.5.2.19.4"
      ::= { performance 4 }

  performanceDynMemTotal  OBJECT-TYPE
      SYNTAX    INTEGER
      ACCESS    read-only
      STATUS      mandatory
      DESCRIPTION  "Get this parameter to read the total dynamic memory (in KBytes).
                    OID: 1.3.6.1.4.1.7745.5.2.19.5"
      ::= { performance 5 }

  performanceDynMemFree  OBJECT-TYPE
      SYNTAX    INTEGER
      ACCESS    read-only
      STATUS      mandatory
      DESCRIPTION  "Get this parameter to read the free dynamic memory (in KBytes).
                    OID: 1.3.6.1.4.1.7745.5.2.19.6"
      ::= { performance 6 }

    systemDefaultScpServer OBJECT-TYPE
      SYNTAX DisplayString
      ACCESS read-write
      STATUS mandatory
      DESCRIPTION  "Set this parameter to configure the name or IP address and port for the default remote SCP server.
      							OID: 1.3.6.1.4.1.7745.5.2.20"
      ::= { system 20 }

    systemScpUsername OBJECT-TYPE
      SYNTAX DisplayString
      ACCESS read-write
      STATUS mandatory
      DESCRIPTION  "Set this parameter to configure the username for the default remote SCP server.
      							OID: 1.3.6.1.4.1.7745.5.2.21"
      ::= { system 21 }

    systemScpPassword OBJECT-TYPE
      SYNTAX DisplayString
      ACCESS read-write
      STATUS mandatory
      DESCRIPTION  "Set this parameter to configure the password for the default remote SCP server.
      							OID: 1.3.6.1.4.1.7745.5.2.22"
      ::= { system 22 }

    systemConsoleEnable OBJECT-TYPE
      SYNTAX    INTEGER {
	                off(0),
	                on(1)
                }
      ACCESS read-write
      STATUS mandatory
      DESCRIPTION  "Set this parameter to enable or disable serial console.
      							OID: 1.3.6.1.4.1.7745.5.2.23"
      ::= { system 23 }

     systemLogMsgRate OBJECT-TYPE
      SYNTAX INTEGER (0..2048)
      ACCESS read-write
      STATUS mandatory
      DESCRIPTION  "Set this parameter to configure the maximum number of log messages per minute.
      							A value set to 0 (zero) is equivalent to unlimited.
      							OID: 1.3.6.1.4.1.7745.5.2.24"
      ::= { system 24 }

xdsl  OBJECT IDENTIFIER  ::= { dsl 1 } -- xDSL Node

xdslTable OBJECT-TYPE
    SYNTAX  SEQUENCE OF XdslEntry
    ACCESS  not-accessible
    STATUS  mandatory
    DESCRIPTION
            "This is a table showing the list of xdsl interface entries.
             OID: 1.3.6.1.4.1.7745.5.3.1.1"
    ::= { xdsl 1 }

xdslEntry OBJECT-TYPE
    SYNTAX  XdslEntry
    ACCESS  not-accessible
    STATUS  mandatory
    DESCRIPTION
            "OID: 1.3.6.1.4.1.7745.5.3.1.1.1"
    INDEX   { xdslIndex }
    ::= { xdslTable 1 }

XdslEntry ::=
    SEQUENCE {
    xdslIndex
          INTEGER,
    xdslLinkStatus
          DisplayString,
    xdslTc
          DisplayString,
    xdslUsAttenuation
          INTEGER,
    xdslDsAttenuation
          INTEGER,
    xdslUsNoiseMargin
          INTEGER,
    xdslDsNoiseMargin
          INTEGER,
    xdslUsCurrRate
          INTEGER,
    xdslDsCurrRate
          INTEGER,
    xdslModulationType
          DisplayString,
    xdslUsMaxTheorRate
          INTEGER,
    xdslDsMaxTheorRate
          INTEGER,
    xdslUsTotBytes
          INTEGER,
    xdslDsTotBytes
          INTEGER,
    xdslNeTotCrcErr
          INTEGER,
    xdslNeShowtimeCrcErr
          INTEGER
    }

xdslIndex  OBJECT-TYPE
      SYNTAX    INTEGER (1..255)
      ACCESS    read-only
      STATUS      mandatory
      DESCRIPTION  "Get this parameter to read the index of the row.
                    OID: 1.3.6.1.4.1.7745.5.3.1.1.1.1"
      ::= { xdslEntry 1 }

xdslLinkStatus  OBJECT-TYPE
      SYNTAX    DisplayString
      ACCESS    read-only
      STATUS      mandatory
      DESCRIPTION  "Get this parameter to read the link status.
                    OID: 1.3.6.1.4.1.7745.5.3.1.1.1.2"
      ::= { xdslEntry 2 }

xdslTc  OBJECT-TYPE
      SYNTAX    DisplayString
      ACCESS    read-only
      STATUS      mandatory
      DESCRIPTION  "Get this parameter to read link transmission convergence.
                    OID: 1.3.6.1.4.1.7745.5.3.1.1.1.3"
      ::= { xdslEntry 3 }

xdslUsAttenuation  OBJECT-TYPE
      SYNTAX    INTEGER
      ACCESS    read-only
      STATUS      mandatory
      DESCRIPTION  "Get this parameter to read link upstream attenuation (0.1 dB steps).
                    OID: 1.3.6.1.4.1.7745.5.3.1.1.1.4"
      ::= { xdslEntry 4 }

xdslDsAttenuation  OBJECT-TYPE
      SYNTAX    INTEGER
      ACCESS    read-only
      STATUS      mandatory
      DESCRIPTION  "Get this parameter to read link downstream attenuation (0.1 dB steps).
                    OID: 1.3.6.1.4.1.7745.5.3.1.1.1.5"
      ::= { xdslEntry 5 }

xdslUsNoiseMargin  OBJECT-TYPE
      SYNTAX    INTEGER
      ACCESS    read-only
      STATUS      mandatory
      DESCRIPTION  "Get this parameter to read link upstream noise margin (0.1 dB steps).
                    OID: 1.3.6.1.4.1.7745.5.3.1.1.1.6"
      ::= { xdslEntry 6 }

xdslDsNoiseMargin  OBJECT-TYPE
      SYNTAX    INTEGER
      ACCESS    read-only
      STATUS      mandatory
      DESCRIPTION  "Get this parameter to read link downstream noise margin (0.1 dB steps).
                    OID: 1.3.6.1.4.1.7745.5.3.1.1.1.7"
      ::= { xdslEntry 7 }

xdslUsCurrRate  OBJECT-TYPE
      SYNTAX    INTEGER
      ACCESS    read-only
      STATUS      mandatory
      DESCRIPTION  "Get this parameter to read link upstream current rate (in Kbps).
                    OID: 1.3.6.1.4.1.7745.5.3.1.1.1.8"
      ::= { xdslEntry 8 }

xdslDsCurrRate  OBJECT-TYPE
      SYNTAX    INTEGER
      ACCESS    read-only
      STATUS      mandatory
      DESCRIPTION  "Get this parameter to read link downstream current rate (in Kbps).
                    OID: 1.3.6.1.4.1.7745.5.3.1.1.1.9"
      ::= { xdslEntry 9 }

xdslModulationType  OBJECT-TYPE
      SYNTAX    DisplayString
      ACCESS    read-only
      STATUS      mandatory
      DESCRIPTION  "Get this parameter to read link modulation type.
                    OID: 1.3.6.1.4.1.7745.5.3.1.1.1.10"
      ::= { xdslEntry 10 }

xdslUsMaxTheorRate  OBJECT-TYPE
      SYNTAX    INTEGER
      ACCESS    read-only
      STATUS      mandatory
      DESCRIPTION  "Get this parameter to read link upstream attainable max rate (in Kbps).
                    OID: 1.3.6.1.4.1.7745.5.3.1.1.1.11"
      ::= { xdslEntry 11 }

xdslDsMaxTheorRate  OBJECT-TYPE
      SYNTAX    INTEGER
      ACCESS    read-only
      STATUS      mandatory
      DESCRIPTION  "Get this parameter to read link downstream attainable max rate (in Kbps).
                    OID: 1.3.6.1.4.1.7745.5.3.1.1.1.12"
      ::= { xdslEntry 12 }

xdslUsTotBytes  OBJECT-TYPE
      SYNTAX    INTEGER
      ACCESS    read-only
      STATUS      mandatory
      DESCRIPTION  "Get this parameter to read link upstream total bytes.
                    OID: 1.3.6.1.4.1.7745.5.3.1.1.1.13"
      ::= { xdslEntry 13 }

xdslDsTotBytes  OBJECT-TYPE
      SYNTAX    INTEGER
      ACCESS    read-only
      STATUS      mandatory
      DESCRIPTION  "Get this parameter to read link downstream total bytes.
                    OID: 1.3.6.1.4.1.7745.5.3.1.1.1.14"
      ::= { xdslEntry 14 }

xdslNeTotCrcErr  OBJECT-TYPE
      SYNTAX    INTEGER
      ACCESS    read-only
      STATUS      mandatory
      DESCRIPTION  "Get this parameter to read link near-end total CRC errors.
                    OID: 1.3.6.1.4.1.7745.5.3.1.1.1.15"
      ::= { xdslEntry 15 }
xdslNeShowtimeCrcErr  OBJECT-TYPE
      SYNTAX    INTEGER
      ACCESS    read-only
      STATUS      mandatory
      DESCRIPTION  "Get this parameter to read link near-end last showtime CRC errors.
                    OID: 1.3.6.1.4.1.7745.5.3.1.1.1.16"
      ::= { xdslEntry 16 }

shdsl OBJECT IDENTIFIER  ::= { dsl 2 } -- SHDSL Node

shdslTable OBJECT-TYPE
    SYNTAX  SEQUENCE OF ShdslEntry
    ACCESS  not-accessible
    STATUS  mandatory
    DESCRIPTION
            "This is a table showing the list of shdsl physical interface entries.
             OID: 1.3.6.1.4.1.7745.5.3.2.1"
    ::= { shdsl 1 }

shdslEntry OBJECT-TYPE
    SYNTAX  ShdslEntry
    ACCESS  not-accessible
    STATUS  mandatory
    DESCRIPTION
            "OID: 1.3.6.1.4.1.7745.5.3.2.1.1"
    INDEX   { shdslIndex }
    ::= { shdslTable 1 }

ShdslEntry ::=
    SEQUENCE {
    shdslIndex
          INTEGER,
    shdslPhyStatus
          DisplayString,
    shdslTc
          DisplayString,
    shdslUsAttenuation
          INTEGER,
    shdslDsAttenuation
          INTEGER,
    shdslUsNoiseMargin
          INTEGER,
    shdslDsNoiseMargin
          INTEGER,
    shdslUsCurrRate
          INTEGER,
    shdslDsCurrRate
          INTEGER,
    shdslModulationType
          DisplayString,
    shdslUsMaxTheorRate
          INTEGER,
    shdslDsMaxTheorRate
          INTEGER,
    shdslUsTotBytes
          INTEGER,
    shdslDsTotBytes
          INTEGER,
    shdslNeTotCrcErr
          INTEGER,
    shdslNeShowtimeCrcErr
          INTEGER,
    shdslUsPower
          INTEGER,
    shdslDsPower
          INTEGER
    }

shdslIndex  OBJECT-TYPE
      SYNTAX    INTEGER (1..255)
      ACCESS    read-only
      STATUS      mandatory
      DESCRIPTION  "Get this parameter to read the index of the row.
                    OID: 1.3.6.1.4.1.7745.5.3.2.1.1.1"
      ::= { shdslEntry 1 }

shdslPhyStatus  OBJECT-TYPE
      SYNTAX    DisplayString
      ACCESS    read-only
      STATUS      mandatory
      DESCRIPTION  "Get this parameter to read physical status.
                    OID: 1.3.6.1.4.1.7745.5.3.2.1.1.2"
      ::= { shdslEntry 2 }

shdslTc  OBJECT-TYPE
      SYNTAX    DisplayString
      ACCESS    read-only
      STATUS      mandatory
      DESCRIPTION  "Get this parameter to read physical transmission convergence.
                    OID: 1.3.6.1.4.1.7745.5.3.2.1.1.3"
      ::= { shdslEntry 3 }

shdslUsAttenuation  OBJECT-TYPE
      SYNTAX    INTEGER
      ACCESS    read-only
      STATUS      mandatory
      DESCRIPTION  "Get this parameter to read physical upstream attenuation (0.1 dB steps).
                    OID: 1.3.6.1.4.1.7745.5.3.2.1.1.4"
      ::= { shdslEntry 4 }

shdslDsAttenuation  OBJECT-TYPE
      SYNTAX    INTEGER
      ACCESS    read-only
      STATUS      mandatory
      DESCRIPTION  "Get this parameter to read physical downstream attenuation (0.1 dB steps).
                    OID: 1.3.6.1.4.1.7745.5.3.2.1.1.5"
      ::= { shdslEntry 5 }

shdslUsNoiseMargin  OBJECT-TYPE
      SYNTAX    INTEGER
      ACCESS    read-only
      STATUS      mandatory
      DESCRIPTION  "Get this parameter to read physical upstream noise margin (0.1 dB steps).
                    OID: 1.3.6.1.4.1.7745.5.3.2.1.1.6"
      ::= { shdslEntry 6 }

shdslDsNoiseMargin  OBJECT-TYPE
      SYNTAX    INTEGER
      ACCESS    read-only
      STATUS      mandatory
      DESCRIPTION  "Get this parameter to read physical downstream noise margin (0.1 dB steps).
                    OID: 1.3.6.1.4.1.7745.5.3.2.1.1.7"
      ::= { shdslEntry 7 }

shdslUsCurrRate  OBJECT-TYPE
      SYNTAX    INTEGER
      ACCESS    read-only
      STATUS      mandatory
      DESCRIPTION  "Get this parameter to read physical upstream current rate (in Kbps).
                    OID: 1.3.6.1.4.1.7745.5.3.2.1.1.8"
      ::= { shdslEntry 8 }

shdslDsCurrRate  OBJECT-TYPE
      SYNTAX    INTEGER
      ACCESS    read-only
      STATUS      mandatory
      DESCRIPTION  "Get this parameter to read physical downstream current rate (in Kbps).
                    OID: 1.3.6.1.4.1.7745.5.3.2.1.1.9"
      ::= { shdslEntry 9 }

shdslModulationType  OBJECT-TYPE
      SYNTAX    DisplayString
      ACCESS    read-only
      STATUS      mandatory
      DESCRIPTION  "Get this parameter to read physical modulation type.
                    OID: 1.3.6.1.4.1.7745.5.3.2.1.1.10"
      ::= { shdslEntry 10 }

shdslUsMaxTheorRate  OBJECT-TYPE
      SYNTAX    INTEGER
      ACCESS    read-only
      STATUS      mandatory
      DESCRIPTION  "Get this parameter to read physical upstream attainable max rate (in Kbps).
                    OID: 1.3.6.1.4.1.7745.5.3.2.1.1.11"
      ::= { shdslEntry 11 }

shdslDsMaxTheorRate  OBJECT-TYPE
      SYNTAX    INTEGER
      ACCESS    read-only
      STATUS      mandatory
      DESCRIPTION  "Get this parameter to read physical downstream attainable max rate (in Kbps).
                    OID: 1.3.6.1.4.1.7745.5.3.2.1.1.12"
      ::= { shdslEntry 12 }

shdslUsTotBytes  OBJECT-TYPE
      SYNTAX    INTEGER
      ACCESS    read-only
      STATUS      mandatory
      DESCRIPTION  "Get this parameter to read physical upstream total bytes.
                    OID: 1.3.6.1.4.1.7745.5.3.2.1.1.13"
      ::= { shdslEntry 13 }

shdslDsTotBytes  OBJECT-TYPE
      SYNTAX    INTEGER
      ACCESS    read-only
      STATUS      mandatory
      DESCRIPTION  "Get this parameter to read physical downstream total bytes.
                    OID: 1.3.6.1.4.1.7745.5.3.2.1.1.14"
      ::= { shdslEntry 14 }

shdslNeTotCrcErr  OBJECT-TYPE
      SYNTAX    INTEGER
      ACCESS    read-only
      STATUS      mandatory
      DESCRIPTION  "Get this parameter to read physical near-end total CRC errors.
                    OID: 1.3.6.1.4.1.7745.5.3.2.1.1.15"
      ::= { shdslEntry 15 }

shdslNeShowtimeCrcErr  OBJECT-TYPE
      SYNTAX    INTEGER
      ACCESS    read-only
      STATUS      mandatory
      DESCRIPTION  "Get this parameter to read physical near-end last showtime CRC errors.
                    OID: 1.3.6.1.4.1.7745.5.3.2.1.1.16"
      ::= { shdslEntry 16 }

shdslUsPower  OBJECT-TYPE
      SYNTAX    INTEGER
      ACCESS    read-only
      STATUS      mandatory
      DESCRIPTION  "Get this parameter to read physical Us Power.
                    OID: 1.3.6.1.4.1.7745.5.3.2.1.1.17"
      ::= { shdslEntry 17 }

shdslDsPower  OBJECT-TYPE
      SYNTAX    INTEGER
      ACCESS    read-only
      STATUS      mandatory
      DESCRIPTION  "Get this parameter to read physical Ds Power.
                    OID: 1.3.6.1.4.1.7745.5.3.2.1.1.18"
      ::= { shdslEntry 18 }

trunk OBJECT IDENTIFIER ::= { voip 1 }   -- Voip Trunk

trunkTable OBJECT-TYPE
    SYNTAX  SEQUENCE OF TrunkEntry
    ACCESS  not-accessible
    STATUS  mandatory
    DESCRIPTION
            "This is a table showing the list of configured voip SIP trunk.
             OID: 1.3.6.1.4.1.7745.5.4.1.1"
    ::= { trunk 1 }

trunkEntry OBJECT-TYPE
    SYNTAX  TrunkEntry
    ACCESS  not-accessible
    STATUS  mandatory
    DESCRIPTION
            "OID: 1.3.6.1.4.1.7745.5.4.1.1.1"
    INDEX   { trunkIndex }
    ::= { trunkTable 1 }

TrunkEntry ::=
    SEQUENCE {
        trunkIndex
          INTEGER,
        trunkName
          DisplayString,
        trunkType
          DisplayString,
        trunkEnable
          INTEGER,
        trunkDescription
          DisplayString,
        trunkUserName
          DisplayString,
        trunkRegHost
          DisplayString,
        trunkProxyHost
          DisplayString,
        trunkIfcStatus
          DisplayString,
        trunkRegStatus
          DisplayString,
        trunkMsgWait
          DisplayString
              }

trunkIndex  OBJECT-TYPE
      SYNTAX    INTEGER (1..255)
      ACCESS    read-only
      STATUS      mandatory
      DESCRIPTION  "Get this parameter to read the index of the row.
                    OID: 1.3.6.1.4.1.7745.5.4.1.1.1.1"
      ::= { trunkEntry 1 }

trunkName OBJECT-TYPE
      SYNTAX    DisplayString
      ACCESS    read-only
      STATUS      mandatory
      DESCRIPTION  "Get this parameter to read trunk name.
                    OID: 1.3.6.1.4.1.7745.5.4.1.1.1.2"
      ::= { trunkEntry 2 }

trunkType OBJECT-TYPE
      SYNTAX    DisplayString
      ACCESS    read-only
      STATUS      mandatory
      DESCRIPTION  "Get this parameter to read trunk type.
                    OID: 1.3.6.1.4.1.7745.5.4.1.1.1.3"
      ::= { trunkEntry 3 }

trunkEnable  OBJECT-TYPE
      SYNTAX    INTEGER {
                registered(1),
                unregistered(2)
            }
      ACCESS    read-write
      STATUS      mandatory
      DESCRIPTION  "Get this parameter to read trunk registration enable.
                    OID: 1.3.6.1.4.1.7745.5.4.1.1.1.4"
      ::= { trunkEntry 4 }

trunkDescription  OBJECT-TYPE
      SYNTAX    DisplayString
      ACCESS    read-only
      STATUS      mandatory
      DESCRIPTION  "Get this parameter to read trunk description.
                    OID: 1.3.6.1.4.1.7745.5.4.1.1.1.5"
      ::= { trunkEntry 5 }

trunkUserName OBJECT-TYPE
      SYNTAX    DisplayString
      ACCESS    read-only
      STATUS      mandatory
      DESCRIPTION  "Get this parameter to read trunk username.
                    OID: 1.3.6.1.4.1.7745.5.4.1.1.1.6"
      ::= { trunkEntry 6 }

trunkRegHost OBJECT-TYPE
      SYNTAX    DisplayString
      ACCESS    read-only
      STATUS      mandatory
      DESCRIPTION  "Get this parameter to read trunk registar host.
                    OID: 1.3.6.1.4.1.7745.5.4.1.1.1.7"
      ::= { trunkEntry 7 }

trunkProxyHost OBJECT-TYPE
      SYNTAX    DisplayString
      ACCESS    read-only
      STATUS      mandatory
      DESCRIPTION  "Get this parameter to read trunk proxy host.
                    OID: 1.3.6.1.4.1.7745.5.4.1.1.1.8"
      ::= { trunkEntry 8 }

trunkIfcStatus OBJECT-TYPE
      SYNTAX    DisplayString
      ACCESS    read-only
      STATUS      mandatory
      DESCRIPTION  "Get this parameter to read trunk interface status.
                    OID: 1.3.6.1.4.1.7745.5.4.1.1.1.9"
      ::= { trunkEntry 9 }

trunkRegStatus OBJECT-TYPE
      SYNTAX    DisplayString
      ACCESS    read-only
      STATUS      mandatory
      DESCRIPTION  "Get this parameter to read trunk registration status.
                    OID: 1.3.6.1.4.1.7745.5.4.1.1.1.10"
      ::= { trunkEntry 10 }

trunkMsgWait OBJECT-TYPE
      SYNTAX    DisplayString
      ACCESS    read-only
      STATUS      mandatory
      DESCRIPTION  "Get this parameter to read trunk message wait status.
                    OID: 1.3.6.1.4.1.7745.5.4.1.1.1.11"
      ::= { trunkEntry 11 }


trunkIsdnTable OBJECT-TYPE
    SYNTAX  SEQUENCE OF TrunkIsdnEntry
    ACCESS  not-accessible
    STATUS  mandatory
    DESCRIPTION
            "This is a table showing the list of configured voip ISDN trunk.
             OID: 1.3.6.1.4.1.7745.5.4.1.2"
    ::= { trunk 2 }

trunkIsdnEntry OBJECT-TYPE
    SYNTAX  TrunkIsdnEntry
    ACCESS  not-accessible
    STATUS  mandatory
    DESCRIPTION
            "OID: 1.3.6.1.4.1.7745.5.4.1.2.1"
    INDEX   { trunkIsdnIndex }
    ::= { trunkIsdnTable 1 }

TrunkIsdnEntry ::=
    SEQUENCE {
        trunkIsdnIndex
          INTEGER,
        trunkIsdnName
          DisplayString,
        trunkIsdnType
          DisplayString,
        trunkIsdnEnable
          INTEGER,
        trunkIsdnDescription
          DisplayString,
        trunkIsdnB1Status
          DisplayString,
        trunkIsdnB2Status
          DisplayString
              }

trunkIsdnIndex  OBJECT-TYPE
      SYNTAX    INTEGER (1..255)
      ACCESS    read-only
      STATUS      mandatory
      DESCRIPTION  "Get this parameter to read the index of the row.
                    OID: 1.3.6.1.4.1.7745.5.4.1.2.1.1"
      ::= { trunkIsdnEntry 1 }

trunkIsdnName OBJECT-TYPE
      SYNTAX    DisplayString
      ACCESS    read-only
      STATUS      mandatory
      DESCRIPTION  "Get this parameter to read trunk name.
                    OID: 1.3.6.1.4.1.7745.5.4.1.2.1.2"
      ::= { trunkIsdnEntry 2 }

trunkIsdnType OBJECT-TYPE
      SYNTAX    DisplayString
      ACCESS    read-only
      STATUS      mandatory
      DESCRIPTION  "Get this parameter to read trunk type.
                    OID: 1.3.6.1.4.1.7745.5.4.1.2.1.3"
      ::= { trunkIsdnEntry 3 }

trunkIsdnEnable  OBJECT-TYPE
      SYNTAX    INTEGER {
                	enable(1),
                	disable(2)
                }
      ACCESS    read-write
      STATUS      mandatory
      DESCRIPTION  "Get this parameter to read trunk enable configuration.
                    OID: 1.3.6.1.4.1.7745.5.4.1.2.1.4"
      ::= { trunkIsdnEntry 4 }

trunkIsdnDescription  OBJECT-TYPE
      SYNTAX    DisplayString
      ACCESS    read-only
      STATUS      mandatory
      DESCRIPTION  "Get this parameter to read trunk description.
                    OID: 1.3.6.1.4.1.7745.5.4.1.2.1.5"
      ::= { trunkIsdnEntry 5 }

trunkIsdnB1Status OBJECT-TYPE
      SYNTAX    DisplayString
      ACCESS    read-only
      STATUS      mandatory
      DESCRIPTION  "Get this parameter to read trunk B1 status.
                    OID: 1.3.6.1.4.1.7745.5.4.1.2.1.6"
      ::= { trunkIsdnEntry 6 }

trunkIsdnB2Status OBJECT-TYPE
      SYNTAX    DisplayString
      ACCESS    read-only
      STATUS      mandatory
      DESCRIPTION  "Get this parameter to read trunk B2 status.
                    OID: 1.3.6.1.4.1.7745.5.4.1.2.1.7"
      ::= { trunkIsdnEntry 7 }

trunkFxoTable OBJECT-TYPE
    SYNTAX  SEQUENCE OF TrunkFxoEntry
    ACCESS  not-accessible
    STATUS  mandatory
    DESCRIPTION
            "This is a table showing the list of configured voip FXO trunk.
             OID: 1.3.6.1.4.1.7745.5.4.1.3"
    ::= { trunk 3 }

trunkFxoEntry OBJECT-TYPE
    SYNTAX  TrunkFxoEntry
    ACCESS  not-accessible
    STATUS  mandatory
    DESCRIPTION
            "OID: 1.3.6.1.4.1.7745.5.4.1.3.1"
    INDEX   { trunkFxoIndex }
    ::= { trunkFxoTable 1 }

TrunkFxoEntry ::=
    SEQUENCE {
        trunkFxoIndex
          INTEGER,
        trunkFxoName
          DisplayString,
        trunkFxoType
          DisplayString,
        trunkFxoEnable
          INTEGER,
        trunkFxoDescription
          DisplayString,
        trunkFxoStatus
          DisplayString
              }

trunkFxoIndex  OBJECT-TYPE
      SYNTAX    INTEGER (1..255)
      ACCESS    read-only
      STATUS      mandatory
      DESCRIPTION  "Get this parameter to read the index of the row.
                    OID: 1.3.6.1.4.1.7745.5.4.1.3.1.1"
      ::= { trunkFxoEntry 1 }

trunkFxoName OBJECT-TYPE
      SYNTAX    DisplayString
      ACCESS    read-only
      STATUS      mandatory
      DESCRIPTION  "Get this parameter to read trunk name.
                    OID: 1.3.6.1.4.1.7745.5.4.1.3.1.2"
      ::= { trunkFxoEntry 2 }

trunkFxoType OBJECT-TYPE
      SYNTAX    DisplayString
      ACCESS    read-only
      STATUS      mandatory
      DESCRIPTION  "Get this parameter to read trunk type.
                    OID: 1.3.6.1.4.1.7745.5.4.1.3.1.3"
      ::= { trunkFxoEntry 3 }

trunkFxoEnable  OBJECT-TYPE
      SYNTAX    INTEGER {
                	enable(1),
                  disable(2)
            		}
      ACCESS    read-write
      STATUS      mandatory
      DESCRIPTION  "Get this parameter to read trunk enable configuration.
                    OID: 1.3.6.1.4.1.7745.5.4.1.3.1.4"
      ::= { trunkFxoEntry 4 }

trunkFxoDescription  OBJECT-TYPE
      SYNTAX    DisplayString
      ACCESS    read-only
      STATUS      mandatory
      DESCRIPTION  "Get this parameter to read trunk description.
                    OID: 1.3.6.1.4.1.7745.5.4.1.3.1.5"
      ::= { trunkFxoEntry 5 }

trunkFxoStatus OBJECT-TYPE
      SYNTAX    DisplayString
      ACCESS    read-only
      STATUS      mandatory
      DESCRIPTION  "Get this parameter to read trunk status.
                    OID: 1.3.6.1.4.1.7745.5.4.1.3.1.6"
      ::= { trunkFxoEntry 6 }

userTerminal OBJECT IDENTIFIER ::= { voip 2 }   -- Voip User Terminal

usTermPotsTable OBJECT-TYPE
    SYNTAX  SEQUENCE OF UsTermPotsEntry
    ACCESS  not-accessible
    STATUS  mandatory
    DESCRIPTION
            "This is a table showing the list of configured voip POTS user terminal.
             OID: 1.3.6.1.4.1.7745.5.4.2.1"
    ::= { userTerminal 1 }

usTermPotsEntry OBJECT-TYPE
    SYNTAX  UsTermPotsEntry
    ACCESS  not-accessible
    STATUS  mandatory
    DESCRIPTION
            "OID: 1.3.6.1.4.1.7745.5.4.2.1.1"
    INDEX   { usTermPotsIndex }
    ::= { usTermPotsTable 1 }

UsTermPotsEntry ::=
    SEQUENCE {
        usTermPotsIndex
          INTEGER,
        usTermPotsEnable
          INTEGER,
        usTermPotsDescription
          DisplayString,
        usTermPotsStatus
          DisplayString,
        usTermPotsDspSlic
          DisplayString
              }

usTermPotsIndex  OBJECT-TYPE
      SYNTAX    INTEGER (1..255)
      ACCESS    read-only
      STATUS      mandatory
      DESCRIPTION  "Get this parameter to read the index of the row.
      							OID: 1.3.6.1.4.1.7745.5.4.2.1.1.1"
      ::= { usTermPotsEntry 1 }

usTermPotsEnable  OBJECT-TYPE
      SYNTAX    INTEGER {
                	enable(1),
                	disable(2)
                }
      ACCESS    read-write
      STATUS      mandatory
      DESCRIPTION  "Get this parameter to read user terminal enable configuration.
      							OID: 1.3.6.1.4.1.7745.5.4.2.1.1.2"
      ::= { usTermPotsEntry 2 }

usTermPotsDescription  OBJECT-TYPE
      SYNTAX    DisplayString
      ACCESS    read-only
      STATUS      mandatory
      DESCRIPTION  "Get this parameter to read user terminal description.
      							OID: 1.3.6.1.4.1.7745.5.4.2.1.1.3"
      ::= { usTermPotsEntry 3 }

usTermPotsStatus  OBJECT-TYPE
      SYNTAX    DisplayString
      ACCESS    read-only
      STATUS      mandatory
      DESCRIPTION  "Get this parameter to read user terminal status.
      							OID: 1.3.6.1.4.1.7745.5.4.2.1.1.4"
      ::= { usTermPotsEntry 4 }

usTermPotsDspSlic  OBJECT-TYPE
      SYNTAX    DisplayString
      ACCESS    read-only
      STATUS      mandatory
      DESCRIPTION  "Get this parameter to read user terminal DSP Slic.
      							OID: 1.3.6.1.4.1.7745.5.4.2.1.1.5"
      ::= { usTermPotsEntry 5 }

usTermISDNTable OBJECT-TYPE
    SYNTAX  SEQUENCE OF UsTermISDNEntry
    ACCESS  not-accessible
    STATUS  mandatory
    DESCRIPTION
            "This is a table showing the list of configured voip ISDN user terminal.
             OID: 1.3.6.1.4.1.7745.5.4.2.2"
    ::= { userTerminal 2 }

usTermISDNEntry OBJECT-TYPE
    SYNTAX  UsTermISDNEntry
    ACCESS  not-accessible
    STATUS  mandatory
    DESCRIPTION
            "OID: 1.3.6.1.4.1.7745.5.4.2.2.1"
    INDEX   { usTermISDNIndex }
    ::= { usTermISDNTable 1 }

UsTermISDNEntry ::=
    SEQUENCE {
        usTermISDNIndex
          INTEGER,
         usTermISDNEnable
          INTEGER,
        usTermISDNDescription
          DisplayString,
        usTermIsdnStatusB1
          DisplayString,
        usTermIsdnStatusB2
          DisplayString
              }

usTermISDNIndex  OBJECT-TYPE
      SYNTAX    INTEGER (1..255)
      ACCESS    read-only
      STATUS      mandatory
      DESCRIPTION  "Get this parameter to read the index of the row.
      							OID: 1.3.6.1.4.1.7745.5.4.2.2.1.1"
      ::= { usTermISDNEntry 1 }

usTermISDNEnable  OBJECT-TYPE
      SYNTAX    INTEGER {
	                enable(1),
	                disable(2)
                }
      ACCESS    read-write
      STATUS      mandatory
      DESCRIPTION  "Get this parameter to read user terminal enable configuration.
      							OID: 1.3.6.1.4.1.7745.5.4.2.2.1.2"
      ::= { usTermISDNEntry 2 }

usTermISDNDescription  OBJECT-TYPE
      SYNTAX    DisplayString
      ACCESS    read-only
      STATUS      mandatory
      DESCRIPTION  "Get this parameter to read user terminal description.
      							OID: 1.3.6.1.4.1.7745.5.4.2.2.1.3"
      ::= { usTermISDNEntry 3 }

usTermIsdnStatusB1  OBJECT-TYPE
      SYNTAX    DisplayString
      ACCESS    read-only
      STATUS      mandatory
      DESCRIPTION  "Get this parameter to read user terminal B1 status.
      							OID: 1.3.6.1.4.1.7745.5.4.2.2.1.4"
      ::= { usTermISDNEntry 4 }

usTermIsdnStatusB2  OBJECT-TYPE
      SYNTAX    DisplayString
      ACCESS    read-only
      STATUS      mandatory
      DESCRIPTION  "Get this parameter to read user terminal B2 status.
      							OID: 1.3.6.1.4.1.7745.5.4.2.2.1.5"
      ::= { usTermISDNEntry 5 }

usTermDectTable OBJECT-TYPE
    SYNTAX  SEQUENCE OF UsTermDectEntry
    ACCESS  not-accessible
    STATUS  mandatory
    DESCRIPTION
            "This is a table showing the list of configured voip DECT user terminal.
             OID: 1.3.6.1.4.1.7745.5.4.2.3"
    ::= { userTerminal 3 }

usTermDectEntry OBJECT-TYPE
    SYNTAX  UsTermDectEntry
    ACCESS  not-accessible
    STATUS  mandatory
    DESCRIPTION
            "OID: 1.3.6.1.4.1.7745.5.4.2.3.1"
    INDEX   { usTermDectIndex }
    ::= { usTermDectTable 1 }

UsTermDectEntry ::=
    SEQUENCE {
        usTermDectIndex
          INTEGER,
        usTermDectEnable
          INTEGER,
        usTermDectDescription
          DisplayString,
        usTermDectStatus
          DisplayString,
        usTermDectDspSlic
          DisplayString
              }

usTermDectIndex  OBJECT-TYPE
      SYNTAX    INTEGER (1..255)
      ACCESS    read-only
      STATUS      mandatory
      DESCRIPTION  "Get this parameter to read the index of the row.
      							OID: 1.3.6.1.4.1.7745.5.4.2.3.1.1"
      ::= { usTermDectEntry 1 }

usTermDectEnable  OBJECT-TYPE
      SYNTAX    INTEGER {
	                enable(1),
	                disable(2)
                }
      ACCESS    read-write
      STATUS      mandatory
      DESCRIPTION  "Get this parameter to read user terminal enable configuration.
      							OID: 1.3.6.1.4.1.7745.5.4.2.3.1.2"
      ::= { usTermDectEntry 2 }

usTermDectDescription  OBJECT-TYPE
      SYNTAX    DisplayString
      ACCESS    read-only
      STATUS      mandatory
      DESCRIPTION  "Get this parameter to read user terminal description.
      							OID: 1.3.6.1.4.1.7745.5.4.2.3.1.3"
      ::= { usTermDectEntry 3 }

usTermDectStatus  OBJECT-TYPE
      SYNTAX    DisplayString
      ACCESS    read-only
      STATUS      mandatory
      DESCRIPTION  "Get this parameter to read user terminal status.
      							OID: 1.3.6.1.4.1.7745.5.4.2.3.1.4"
      ::= { usTermDectEntry 4 }

usTermDectDspSlic  OBJECT-TYPE
      SYNTAX    DisplayString
      ACCESS    read-only
      STATUS      mandatory
      DESCRIPTION  "Get this parameter to read user terminal DSP Slic.
      							OID: 1.3.6.1.4.1.7745.5.4.2.3.1.5"
      ::= { usTermDectEntry 5 }

  voipMaxConnection  OBJECT-TYPE
      SYNTAX    INTEGER (1..16)
      ACCESS    read-write
      STATUS      mandatory
      DESCRIPTION  "Set this parameter to configure global voip max connections.
      							OID: 1.3.6.1.4.1.7745.5.4.3"
      ::= { voip 3 }

--
-- Traps v2c definitions
--

    genericTrap NOTIFICATION-TYPE
    OBJECTS { genericError }
      STATUS current
      DESCRIPTION
        "This trap is used to send generic string alarm messages to SNMP manager,
         when a particular condition occurs.
         OID: 1.3.6.1.4.1.7745.5.5.1"
      ::=  { traps 1 }

    genericError  OBJECT-TYPE
      SYNTAX    DisplayString
      ACCESS    read-only
      STATUS    mandatory
      DESCRIPTION  "Describe a generic error for generic trap.
                    OID: 1.3.6.1.4.1.7745.5.5.2"
      ::= { traps 2 }

    interfaceUp NOTIFICATION-TYPE
        OBJECTS { ifDescr }
      STATUS current
      DESCRIPTION
        "This trap is sent when a physical interface go up.
         OID: 1.3.6.1.4.1.7745.5.5.3"
      ::=  { traps 3 }

    interfaceDown NOTIFICATION-TYPE
        OBJECTS { ifDescr }
      STATUS current
      DESCRIPTION
        "This trap is sent when a physical interface go down.
         OID: 1.3.6.1.4.1.7745.5.5.4"
      ::=  { traps 4 }

    trunkRegistered NOTIFICATION-TYPE
        OBJECTS { trunkName }
      STATUS current
      DESCRIPTION
        "This trap is sent when a voip SIP Trunk registered.
         OID: 1.3.6.1.4.1.7745.5.5.5"
      ::=  { traps 5 }

    trunkUnregistered NOTIFICATION-TYPE
        OBJECTS { trunkName }
      STATUS current
      DESCRIPTION
        "This trap is sent when a voip SIP Trunk unregistered.
         OID: 1.3.6.1.4.1.7745.5.5.6"
      ::=  { traps 6 }

mgmtAccesses  OBJECT IDENTIFIER  ::= { traps 7 }  -- Management Access Traps

		mgmtUser OBJECT-TYPE
      SYNTAX  DisplayString (SIZE (0..255))
      ACCESS  read-only
      STATUS  mandatory
      DESCRIPTION
              "A textual string containing user name.
               OID: 1.3.6.1.4.1.7745.5.5.7.1"
      ::= { mgmtAccesses 1 }

    mgmtPrivilege OBJECT-TYPE
      SYNTAX  DisplayString (SIZE (0..255))
      ACCESS  read-only
      STATUS  mandatory
      DESCRIPTION
              "A textual string containing user privilege.
               OID: 1.3.6.1.4.1.7745.5.5.7.2"
      ::= { mgmtAccesses 2 }

    mgmtTime OBJECT-TYPE
      SYNTAX  DisplayString (SIZE (0..255))
      ACCESS  read-only
      STATUS  mandatory
      DESCRIPTION
              "A textual string containing time and date of event.
               OID: 1.3.6.1.4.1.7745.5.5.7.3"
      ::= { mgmtAccesses 3 }

    mgmtType OBJECT-TYPE
      SYNTAX    INTEGER {
				  console(1),
				  telnet(2),
				  web(3),
				  snmp(4),
				  ssh(5),
				  tr069(6),
				  unknown(7)
				}
      ACCESS  read-only
      STATUS  mandatory
      DESCRIPTION
              "A textual string containing user access type.
               OID: 1.3.6.1.4.1.7745.5.5.7.4"
      ::= { mgmtAccesses 4 }

    mgmtAddress OBJECT-TYPE
      SYNTAX  DisplayString (SIZE (0..255))
      ACCESS  read-only
      STATUS  mandatory
      DESCRIPTION
              "A textual string containing ip for remote access type.
               OID: 1.3.6.1.4.1.7745.5.5.7.5"
      ::= { mgmtAccesses 5 }

  mgmtLogin NOTIFICATION-TYPE
    OBJECTS { mgmtUser, mgmtPrivilege, mgmtTime, mgmtType, mgmtAddress }
    STATUS current
    DESCRIPTION
      "This trap is sent when a user login in the system console.
       OID: 1.3.6.1.4.1.7745.5.5.7.6"
    ::=  { mgmtAccesses 6 }

  mgmtLogout NOTIFICATION-TYPE
  	OBJECTS { mgmtUser, mgmtPrivilege, mgmtTime, mgmtType, mgmtAddress }
    STATUS current
    DESCRIPTION
      "This trap is sent when a user logout from the system console.
       OID: 1.3.6.1.4.1.7745.5.5.7.7"
    ::=  { mgmtAccesses 7 }

  mgmtChange NOTIFICATION-TYPE
  	OBJECTS { mgmtUser, mgmtTime, mgmtType, mgmtAddress }
    STATUS current
    DESCRIPTION
      "This trap is sent when a logged user change param in the system console.
       OID: 1.3.6.1.4.1.7745.5.5.7.8"
    ::=  { mgmtAccesses 8 }


  ifcTable OBJECT-TYPE
      SYNTAX  SEQUENCE OF IfcEntry
      ACCESS  not-accessible
      STATUS  mandatory
      DESCRIPTION
              "This is a table showing the list of interface entries.
               The number of entries is given by the value of mib-2 ifNumber.
               The indexes for the rows are equivalent to mib-2 ifIndex.
               OID: 1.3.6.1.4.1.7745.5.6.1"
      ::= { ifc 1 }

  ifcEntry OBJECT-TYPE
      SYNTAX  IfcEntry
      ACCESS  not-accessible
      STATUS  mandatory
      DESCRIPTION
              "
              OID: 1.3.6.1.4.1.7745.5.6.1.1"
      INDEX   { ifIndex }
      ::= { ifcTable 1 }

  IfcEntry ::=
      SEQUENCE {
          ifcName
              DisplayString,
          ifcDescr
              DisplayString,
          ifcType
              IANAifType,
          ifcPhysAddress
              PhysAddress,
          ifcMtu
              INTEGER,
          ifcSpeed
              Gauge,
          ifcRxRate
              Counter,
          ifcTxRate
              Counter
      }

ifcName OBJECT-TYPE
      SYNTAX  DisplayString (SIZE (0..255))
      ACCESS  read-only
      STATUS  mandatory
      DESCRIPTION
              "Get this parameter to read interface name.
               OID: 1.3.6.1.4.1.7745.5.6.1.1.1"
      ::= { ifcEntry 1 }

ifcDescr OBJECT-TYPE
      SYNTAX  DisplayString (SIZE (0..255))
      ACCESS  read-only
      STATUS  mandatory
      DESCRIPTION
              "Get this parameter to read interface description.
               OID: 1.3.6.1.4.1.7745.5.6.1.1.2"
      ::= { ifcEntry 2 }

ifcType OBJECT-TYPE
    SYNTAX    IANAifType
    ACCESS    read-only
    STATUS    mandatory
    DESCRIPTION
            "Get this parameter to read interface type.
             The types refer to those assigned by the Internet Assigned Numbers Authority (IANA).
             OID: 1.3.6.1.4.1.7745.5.6.1.1.3"
      ::= { ifcEntry 3 }

ifcPhysAddress OBJECT-TYPE
      SYNTAX  PhysAddress
      ACCESS  read-only
      STATUS  mandatory
      DESCRIPTION
              "Get this parameter to read interface physical address (mac address).
               OID: 1.3.6.1.4.1.7745.5.6.1.1.4"
      ::= { ifcEntry 4 }

ifcMtu OBJECT-TYPE
      SYNTAX  INTEGER
      ACCESS  read-only
      STATUS  mandatory
      DESCRIPTION
              "Get this parameter to read interface MTU,
               the size of the largest datagram which can be sent/received on the interface,
               specified in octets.
               OID: 1.3.6.1.4.1.7745.5.6.1.1.5"
      ::= { ifcEntry 5 }

ifcSpeed OBJECT-TYPE
      SYNTAX  Gauge
      ACCESS  read-only
      STATUS  mandatory
      DESCRIPTION
              "Get this parameter to read interface speed,
               an estimate of the interface's current bandwidth in bits per second.
               OID: 1.3.6.1.4.1.7745.5.6.1.1.6"
      ::= { ifcEntry 6 }

ifcRxRate OBJECT-TYPE
    SYNTAX      Counter
    ACCESS  read-only
    STATUS      mandatory
    DESCRIPTION
            "Get this parameter to read the current and effective RX rate in bit per second.
             OID: 1.3.6.1.4.1.7745.5.6.1.1.7"
    ::= { ifcEntry 7 }

ifcTxRate OBJECT-TYPE
    SYNTAX      Counter
    ACCESS  read-only
    STATUS      mandatory
    DESCRIPTION
            "Get this parameter to read the current and effective TX rate in bit per second.
             OID: 1.3.6.1.4.1.7745.5.6.1.1.8"
    ::= { ifcEntry 8 }

END
