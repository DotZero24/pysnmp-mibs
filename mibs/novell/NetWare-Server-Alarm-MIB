NetWare-Server-Alarm-MIB DEFINITIONS ::= BEGIN

IMPORTS
	enterprises
		FROM RFC1155-SMI

	InternationalDisplayString
		FROM HOST-RESOURCES-MIB

	TRAP-TYPE
		FROM RFC-1215

	OBJECT-TYPE
		FROM RFC-1212;


novell                  OBJECT IDENTIFIER ::= { enterprises 23 }

mibDoc                  OBJECT IDENTIFIER ::= { novell 2 }

nwalarm-mib              OBJECT IDENTIFIER ::= { mibDoc 10 }
trapinfo		OBJECT IDENTIFIER ::= { nwalarm-mib 1 }

NetNumber ::=		OCTET STRING (SIZE(4))

--trapinfo group
--These are used by 4.0 SNMP traps and are not accessible


memoryAddress           OBJECT-TYPE
			SYNTAX        INTEGER
			ACCESS        not-accessible
			STATUS        mandatory
                        DESCRIPTION   "An invalid memory address that an NLM
				tried to write to or read from."
			::= {trapinfo 1}

auditEventNumber	OBJECT-TYPE
			SYNTAX        INTEGER
			ACCESS        not-accessible
			STATUS        mandatory
                        DESCRIPTION   "An audit error code returned on an attempt
				to read an invalid volume."
			::= {trapinfo 2}

blockNumber 	        OBJECT-TYPE
			SYNTAX        INTEGER
			ACCESS        not-accessible
			STATUS        mandatory
                        DESCRIPTION   "The block number of a partition that
				needed to be redirected."
			::= {trapinfo 3}

numberOfBlocks 	        OBJECT-TYPE
			SYNTAX        INTEGER
			ACCESS        not-accessible
			STATUS        mandatory
                        DESCRIPTION   "The number of redirection blocks
				available."
			::= {trapinfo 4}

packetSize 	        OBJECT-TYPE
			SYNTAX        INTEGER
			ACCESS        not-accessible
			STATUS        mandatory
                        DESCRIPTION   "The maximum packet size the LAN driver
				can handle."
			::= {trapinfo 5}

boardNumber 	        OBJECT-TYPE
			SYNTAX        INTEGER
			ACCESS        not-accessible
			STATUS        mandatory
                        DESCRIPTION   "The number of the LAN board to which the protocol
                                    stack is bound."
			::= {trapinfo 6}

codeOffset	        OBJECT-TYPE
			SYNTAX        INTEGER
			ACCESS        not-accessible
			STATUS        mandatory
                        DESCRIPTION   "A code address, within an NLM, that is
				causing a problem."
			::= {trapinfo 7}

connectionNumber	OBJECT-TYPE
			SYNTAX        INTEGER
			ACCESS        not-accessible
			STATUS        mandatory
                        DESCRIPTION   "This could be either an NLM connection
				or a user connection."
			::= {trapinfo 8}

dataStreamNumber	OBJECT-TYPE
			SYNTAX        INTEGER
			ACCESS        not-accessible
			STATUS        mandatory
                        DESCRIPTION   ""
			::= {trapinfo 9}

diskSpace	        OBJECT-TYPE
			SYNTAX        INTEGER
			ACCESS        not-accessible
			STATUS        mandatory
                        DESCRIPTION   "An amount of volume disk space,
				measured in kilobytes."
			::= {trapinfo 10}

domainName 	        OBJECT-TYPE
			SYNTAX        InternationalDisplayString(SIZE(1..32))
			ACCESS        not-accessible
			STATUS        mandatory
                        DESCRIPTION   ""
			::= {trapinfo 11}


resourceDescription 	OBJECT-TYPE
			SYNTAX        InternationalDisplayString(SIZE(1..32))
			ACCESS        not-accessible
			STATUS        mandatory
                        DESCRIPTION   ""
			::= {trapinfo 12}

deviceName 	        OBJECT-TYPE
			SYNTAX        InternationalDisplayString(SIZE(1..64))
			ACCESS        not-accessible
			STATUS        mandatory
                        DESCRIPTION   ""
			::= {trapinfo 13}

dosType 	        OBJECT-TYPE
			SYNTAX        INTEGER
			ACCESS        not-accessible
			STATUS        mandatory
                        DESCRIPTION   ""
			::= {trapinfo 14}


errorNumber 	        OBJECT-TYPE
			SYNTAX        INTEGER
			ACCESS        not-accessible
			STATUS        mandatory
                        DESCRIPTION   "An unknown error returned during
				 decompression."
			::= {trapinfo 15}

exceptionName	        OBJECT-TYPE
			SYNTAX       InternationalDisplayString(SIZE(1..32))
			ACCESS        not-accessible
			STATUS        mandatory
                        DESCRIPTION   ""
			::= {trapinfo 16}

eipAddress		OBJECT-TYPE
			SYNTAX       INTEGER
			ACCESS        not-accessible
			STATUS        mandatory
                        DESCRIPTION   "An instruction pointer value causing
				an exception."
			::= {trapinfo 17}

fileName	        OBJECT-TYPE
			SYNTAX       InternationalDisplayString(SIZE(1..32))
			ACCESS        not-accessible
			STATUS        mandatory
                        DESCRIPTION   ""
			::= {trapinfo 18}

pathName	        OBJECT-TYPE
			SYNTAX       InternationalDisplayString(SIZE(2..124))
			ACCESS        not-accessible
			STATUS        mandatory
                        DESCRIPTION   ""
			::= {trapinfo 19}

fileOffset	        OBJECT-TYPE
			SYNTAX       INTEGER
			ACCESS        not-accessible
			STATUS        mandatory
                        DESCRIPTION   "An offset, in a file, that is causing
				a problem."
			::= {trapinfo 20}

ncpFunctionNumber	OBJECT-TYPE
			SYNTAX       INTEGER
			ACCESS        not-accessible
			STATUS        mandatory
                        DESCRIPTION   "Function number, in the workstation
				shell, that is causing a problem."
			::= {trapinfo 21}

fileSize	       	OBJECT-TYPE
			SYNTAX       INTEGER
			ACCESS        not-accessible
			STATUS        mandatory
                        DESCRIPTION   ""
			::= {trapinfo 22}

fileValue	       	OBJECT-TYPE
			SYNTAX       INTEGER
			ACCESS        not-accessible
			STATUS        mandatory
                        DESCRIPTION   "Contents of a file at a particular
				offset within the file."
			::= {trapinfo 23}

fileLength	       	OBJECT-TYPE
			SYNTAX       INTEGER
			ACCESS        not-accessible
			STATUS        mandatory
                        DESCRIPTION   "Length of temporary file created
				during file compression."
			::= {trapinfo 24}

interruptNumber		OBJECT-TYPE
			SYNTAX       INTEGER
			ACCESS        not-accessible
			STATUS        mandatory
                        DESCRIPTION   "Interrupt number for which there is
					no interrupt service routine
					registered with the OS."
			::= {trapinfo 25}

nlmName			OBJECT-TYPE
			SYNTAX       InternationalDisplayString(SIZE(1..128))
			ACCESS        not-accessible
			STATUS        mandatory
                        DESCRIPTION   ""
			::= {trapinfo 26}

mediaLabel		OBJECT-TYPE
			SYNTAX       InternationalDisplayString(SIZE(1..64))
			ACCESS        not-accessible
			STATUS        mandatory
                        DESCRIPTION   ""
			::= {trapinfo 27}


message			OBJECT-TYPE
			SYNTAX       InternationalDisplayString(SIZE(1..512))
			ACCESS        not-accessible
			STATUS        mandatory
                        DESCRIPTION   "This is a generic message containing
					all parameters substituted in the
					control string."
			::= {trapinfo 28}


numberOfFailedMemoryAllocAttempts  	OBJECT-TYPE
			SYNTAX       INTEGER
			ACCESS        not-accessible
			STATUS        mandatory
                        DESCRIPTION   "Number of failed memory requests."
			::= {trapinfo 29}

numberOfResources	OBJECT-TYPE
			SYNTAX       INTEGER
			ACCESS        not-accessible
			STATUS        mandatory
                        DESCRIPTION   "Number of resources not released by
				an NLM while unloading."
			::= {trapinfo 30}

networkAddress       	OBJECT-TYPE
			SYNTAX       NetNumber
			ACCESS        not-accessible
			STATUS        mandatory
                        DESCRIPTION   "An IPX network address."
			::= {trapinfo 31}


numberOfFailedFileLockRequests  OBJECT-TYPE
			SYNTAX       INTEGER
			ACCESS        not-accessible
			STATUS        mandatory
                        DESCRIPTION   "Number of open file lock requests
				that failed."
			::= {trapinfo 32}

processName         	OBJECT-TYPE
			SYNTAX       InternationalDisplayString(SIZE(1..16))
			ACCESS       not-accessible
			STATUS       mandatory
                        DESCRIPTION   "Name of an executing process."
			::= {trapinfo 33}

partitionNumber        	OBJECT-TYPE
			SYNTAX       INTEGER
			ACCESS       not-accessible
			STATUS       mandatory
                        DESCRIPTION   "A partition number."
			::= {trapinfo 34}

protocolName         	OBJECT-TYPE
			SYNTAX       InternationalDisplayString(SIZE(1..16))
			ACCESS       not-accessible
			STATUS       mandatory
                        DESCRIPTION   "Name of a protocol stack that is
				loaded and running."
			::= {trapinfo 35}

numberOfPackets        	OBJECT-TYPE
			SYNTAX       INTEGER
			ACCESS       not-accessible
			STATUS       mandatory
                        DESCRIPTION   "Number of incomplete packets received
				by IPX."
			::= {trapinfo 36}

resourceName          	OBJECT-TYPE
			SYNTAX       InternationalDisplayString(SIZE(1..32))
			ACCESS       not-accessible
			STATUS       mandatory
                        DESCRIPTION   ""
			::= {trapinfo 37}

numberOfFailedRecordLockRequests OBJECT-TYPE
			SYNTAX       INTEGER
			ACCESS       not-accessible
			STATUS       mandatory
                        DESCRIPTION   "Number of record lock requests that
					failed."
			::= {trapinfo 38}

serverName	       	OBJECT-TYPE
			SYNTAX       InternationalDisplayString(SIZE(1..48))
			ACCESS       not-accessible
			STATUS       mandatory
                        DESCRIPTION   ""
			::= {trapinfo 39}

stationNumber	       	OBJECT-TYPE
			SYNTAX       INTEGER
			ACCESS       not-accessible
			STATUS       mandatory
                        DESCRIPTION   "A station number."
			::= {trapinfo 40}


networkAddress1       	OBJECT-TYPE
			SYNTAX       NetNumber
			ACCESS        not-accessible
			STATUS        mandatory
                        DESCRIPTION   "An IPX network address."
			::= {trapinfo 41}


ncpSubFunctionNumber   	OBJECT-TYPE
			SYNTAX       INTEGER
			ACCESS       not-accessible
			STATUS       mandatory
                        DESCRIPTION   "Function number, in the workstation
				shell, that is causing a problem."
			::= {trapinfo 42}


nlmSeverity	       	OBJECT-TYPE
			SYNTAX       INTEGER{
						informational(1),
						warning(2),
						recoverable(3),
						critical(4),
						fatal(5),
						operationAborted(6)
                                             }
			ACCESS       not-accessible
			STATUS       mandatory
                        DESCRIPTION   "The severity of a generic alert."
			::= {trapinfo 43}


trapTime	       	OBJECT-TYPE
			SYNTAX       INTEGER
			ACCESS        not-accessible
			STATUS        mandatory
                        DESCRIPTION   "The number of seconds since midnight
				of January 1,1970 GMT."
			::= {trapinfo 44}


taskNumber		OBJECT-TYPE
			SYNTAX       INTEGER
			ACCESS        not-accessible
			STATUS        mandatory
                        DESCRIPTION   "A station task number."
			::= {trapinfo 45}

numberOfTransactions 	OBJECT-TYPE
			SYNTAX       INTEGER
			ACCESS        not-accessible
			STATUS        mandatory
                        DESCRIPTION   "Number of transactions delayed by TTS
				due to the maximum number of transactions
				being exceeded."
			::= {trapinfo 46}

serverTime	       	OBJECT-TYPE
			SYNTAX       INTEGER
			ACCESS        not-accessible
			STATUS        mandatory
                        DESCRIPTION   "The system time set at the server or workstation
                                    console."
			::= {trapinfo 47}


pathFileName	        OBJECT-TYPE
			SYNTAX       InternationalDisplayString(SIZE(2..124))
			ACCESS        not-accessible
			STATUS        mandatory
                        DESCRIPTION   ""
			::= {trapinfo 48}

userName       		OBJECT-TYPE
			SYNTAX       InternationalDisplayString(SIZE(1..48))
			ACCESS        not-accessible
			STATUS        mandatory
                        DESCRIPTION   ""
			::= {trapinfo 49}

volumeName           	OBJECT-TYPE
			SYNTAX       InternationalDisplayString(SIZE(1..16))
			ACCESS        not-accessible
			STATUS        mandatory
                        DESCRIPTION   ""
			::= {trapinfo 50}

volumeNumber           	OBJECT-TYPE
			SYNTAX       INTEGER
			ACCESS        not-accessible
			STATUS        mandatory
                        DESCRIPTION   "A volume number."
			::= {trapinfo 51}

lanDriverName            	OBJECT-TYPE
			SYNTAX       InternationalDisplayString(SIZE(1..256))
			ACCESS        not-accessible
			STATUS        mandatory
                        DESCRIPTION   "LAN driver name."
			::= {trapinfo 52}

routerName	       	OBJECT-TYPE
			SYNTAX       InternationalDisplayString(SIZE(1..48))
			ACCESS       not-accessible
			STATUS       mandatory
                        DESCRIPTION   ""
			::= {trapinfo 53}

macAddress       	OBJECT-TYPE
			SYNTAX       OCTET STRING(SIZE(6))
			ACCESS        not-accessible
			STATUS        mandatory
                        DESCRIPTION   "Six byte MAC address."
			::= {trapinfo 54}

macAddress1       	OBJECT-TYPE
			SYNTAX        OCTET STRING(SIZE(6))
			ACCESS        not-accessible
			STATUS        mandatory
                        DESCRIPTION   "Six byte MAC address."
			::= {trapinfo 55}

numberOfConnections     OBJECT-TYPE
			SYNTAX        INTEGER
			ACCESS        not-accessible
			STATUS        mandatory
                        DESCRIPTION   ""
			::= {trapinfo 56}

socketNumber		OBJECT-TYPE
			SYNTAX        INTEGER
			ACCESS        not-accessible
			STATUS        mandatory
                        DESCRIPTION   ""
			::= {trapinfo 57}

accountName       		OBJECT-TYPE
			SYNTAX       InternationalDisplayString(SIZE(1..48))
			ACCESS        not-accessible
			STATUS        mandatory
                        DESCRIPTION   ""
			::= {trapinfo 58}


fileMiscInfo		OBJECT-TYPE
			SYNTAX        INTEGER
			ACCESS        not-accessible
			STATUS        mandatory
                        DESCRIPTION   ""
			::= {trapinfo 59}


callBackNumber	        OBJECT-TYPE
			SYNTAX       InternationalDisplayString(SIZE(1..20))
			ACCESS        not-accessible
			STATUS        mandatory
                        DESCRIPTION   "Telephone number to call back."
			::= {trapinfo 60}

baudRate	        OBJECT-TYPE
			SYNTAX       InternationalDisplayString(SIZE(11))
			ACCESS        not-accessible
			STATUS        mandatory
                        DESCRIPTION   ""
			::= {trapinfo 61}

objectName 	        OBJECT-TYPE
			SYNTAX       InternationalDisplayString(SIZE(1..256))
			ACCESS        not-accessible
			STATUS        mandatory
                        DESCRIPTION   ""
			::= {trapinfo 62}


userName1      		OBJECT-TYPE
			SYNTAX       InternationalDisplayString(SIZE(1..48))
			ACCESS        not-accessible
			STATUS        mandatory
                        DESCRIPTION   ""
			::= {trapinfo 63}

dosType1 	        OBJECT-TYPE
			SYNTAX        INTEGER
			ACCESS        not-accessible
			STATUS        mandatory
                        DESCRIPTION   ""
			::= {trapinfo 64}



blockNumber1 	        OBJECT-TYPE
			SYNTAX        INTEGER
			ACCESS        not-accessible
			STATUS        mandatory
                        DESCRIPTION   "The block number of a partition that
				needed to be redirected."
			::= {trapinfo 65}

internalNetworkAddress  OBJECT-TYPE
			SYNTAX        NetNumber
			ACCESS        not-accessible
			STATUS        mandatory
                        DESCRIPTION   "Four byte internal network number."
			::= {trapinfo 66}

internalNetworkAddress1 OBJECT-TYPE
			SYNTAX        NetNumber
			ACCESS        not-accessible
			STATUS        mandatory
                        DESCRIPTION   "Four byte internal network number."
			::= {trapinfo 67}

macAddress2       	OBJECT-TYPE
			SYNTAX        OCTET STRING(SIZE(6))
			ACCESS        not-accessible
			STATUS        mandatory
                        DESCRIPTION   "Six byte MAC address."
			::= {trapinfo 68}

serverName1	       	OBJECT-TYPE
			SYNTAX       InternationalDisplayString(SIZE(1..48))
			ACCESS       not-accessible
			STATUS       mandatory
                        DESCRIPTION   ""
			::= {trapinfo 69}

socketNumber1		OBJECT-TYPE
			SYNTAX        INTEGER
			ACCESS        not-accessible
			STATUS        mandatory
                        DESCRIPTION   ""
			::= {trapinfo 70}

fileMiscInfo1		OBJECT-TYPE
			SYNTAX        INTEGER
			ACCESS        not-accessible
			STATUS        mandatory
                        DESCRIPTION   ""
			::= {trapinfo 71}

fileSize1	       	OBJECT-TYPE
			SYNTAX       INTEGER
			ACCESS        not-accessible
			STATUS        mandatory
                        DESCRIPTION   ""
			::= {trapinfo 72}

fileSize2	       	OBJECT-TYPE
			SYNTAX       INTEGER
			ACCESS        not-accessible
			STATUS        mandatory
                        DESCRIPTION   ""
			::= {trapinfo 73}

packetSize1	       	OBJECT-TYPE
			SYNTAX       INTEGER
			ACCESS        not-accessible
			STATUS        mandatory
                        DESCRIPTION   ""
			::= {trapinfo 74}

diskName 	        OBJECT-TYPE
			SYNTAX        InternationalDisplayString(SIZE(1..64))
			ACCESS        not-accessible
			STATUS        mandatory
                        DESCRIPTION   "Disk Name"
			::= {trapinfo 75}

reason	 	        OBJECT-TYPE
			SYNTAX        InternationalDisplayString(SIZE(1..35))
			ACCESS        not-accessible
			STATUS        mandatory
                        DESCRIPTION   "Reason why the disk was deactivated"
			::= {trapinfo 76}


maximumPercent 	        OBJECT-TYPE
			SYNTAX        INTEGER
			ACCESS        not-accessible
			STATUS        mandatory
                        DESCRIPTION   "Maximum percentage of volume space used"
			::= {trapinfo 77}

iRamLength	 	        OBJECT-TYPE
			SYNTAX        INTEGER
			ACCESS        not-accessible
			STATUS        mandatory
                        DESCRIPTION   "RAM length"
			::= {trapinfo 78}

iTimerTicks	 	        OBJECT-TYPE
			SYNTAX        INTEGER
			ACCESS        not-accessible
			STATUS        mandatory
                        DESCRIPTION   "Timer ticks"
			::= {trapinfo 79}

pollingLoops 	        OBJECT-TYPE
			SYNTAX        INTEGER
			ACCESS        not-accessible
			STATUS        mandatory
                        DESCRIPTION   "server polling loops"
			::= {trapinfo 80}

iHopsCount 	        OBJECT-TYPE
			SYNTAX        INTEGER
			ACCESS        not-accessible
			STATUS        mandatory
                        DESCRIPTION   "hop count"
			::= {trapinfo 81}

synchronizationRadius   OBJECT-TYPE
			SYNTAX        INTEGER
			ACCESS        not-accessible
			STATUS        mandatory
                        DESCRIPTION   "server polling loops"
			::= {trapinfo 82}

cmmndLnPrmtr            OBJECT-TYPE
			SYNTAX       InternationalDisplayString(SIZE(1..256))
			ACCESS       not-accessible
			STATUS       mandatory
                        DESCRIPTION   ""
			::= {trapinfo 83}

volumePercentage        OBJECT-TYPE
			SYNTAX        INTEGER
			ACCESS        not-accessible
			STATUS        mandatory
                        DESCRIPTION   "server polling loops"
			::= {trapinfo 84}

szReason	 	OBJECT-TYPE
			SYNTAX        InternationalDisplayString(SIZE(1..35))
			ACCESS        not-accessible
			STATUS        mandatory
                        DESCRIPTION   "Reason why SFT server failed"
			::= {trapinfo 85}


iRamStart	 	OBJECT-TYPE
			SYNTAX        INTEGER
			ACCESS        not-accessible
			STATUS        mandatory
                        DESCRIPTION   "RAM start address"
			::= {trapinfo 86}


-- alerts generated by OS using the function NetWareAlert

outOfShortTermMemoryRequestFailed  	TRAP-TYPE   --1.12.1.5.7/1.12.1.5.7
			ENTERPRISE      nwalarm-mib
			VARIABLES  {
                                        serverName,trapTime,
					numberOfFailedMemoryAllocAttempts
                                     }
			DESCRIPTION
                                "The system failed on one or more short-term
				memory requests."
                        --#TYPE "Memory: Short term alloc failed"
                        --#SUMMARY "%d requests for short term memory could "
			--#SUMMARY "not be granted on server %s."
 	                --#ARGUMENTS {2,0}
                        --#SEVERITY CRITICAL
                        --#TIMEINDEX 1
                        --#HELP "nwalarm.hlp"
                        --#HELPTAG 1
                        --#STATE  DEGRADED

	         ::= 1

errWritingToTheExtendedDirSpace 	TRAP-TYPE   --1.2.7.9/1.2.7.9
                        ENTERPRISE      nwalarm-mib
                        VARIABLES       {
                                        serverName,trapTime
                                        }
                        DESCRIPTION
                                "Error occurred while writing to hard disk. Data
				 may be	corrupted."
                        --#TYPE "FileSys: Directory write err (no vol)"
                        --#SUMMARY "Error occurred writing to "
			--#SUMMARY "extended directory space on server %s."
 	                --#ARGUMENTS {0}
                        --#SEVERITY CRITICAL
                        --#TIMEINDEX 1
                        --#HELP "nwalarm.hlp"
                        --#HELPTAG 2
                        --#STATE  DEGRADED

                    ::= 2

errWritingToFile 	TRAP-TYPE   --1.2.7.10/1.2.7.10
                        ENTERPRISE      nwalarm-mib
                        VARIABLES       {
                                        serverName,trapTime,dataStreamNumber
                                        }
                        DESCRIPTION
                                "An error occurred while writing to file
				(filename not accessible) data stream by
				server."
                        --#TYPE "FileSys: File write err, by server (no path)"
			--#SUMMARY "Error occurred writing to file "
			--#SUMMARY "data stream %d.  Error writing to "
			--#SUMMARY "extended directory space. Write "
			--#SUMMARY "requested by server %s."
 	                --#ARGUMENTS {2,0}
                        --#SEVERITY CRITICAL
                        --#TIMEINDEX 1
                        --#HELP "nwalarm.hlp"
                        --#HELPTAG 3
                        --#STATE  DEGRADED

                    ::= 3


errWritingToFileUsr 	TRAP-TYPE   --1.2.7.11/1.2.7.11
                        ENTERPRISE      nwalarm-mib
                        VARIABLES       {
                                        serverName,trapTime,dataStreamNumber,
					userName,stationNumber
                                       }
                        DESCRIPTION
                                "An error occurred while writing to file
				(filename not accessible) data stream
				by user."
                        --#TYPE "FileSys: File write err, by user (no path)"
                        --#SUMMARY "Error occurred writing to file "
			--#SUMMARY "(filename not accessible) data stream %d "
			--#SUMMARY "on server %s. Write requested by "
			--#SUMMARY "user %s on station %d."
 	                --#ARGUMENTS {2,0,3,4}
                        --#SEVERITY CRITICAL
                        --#TIMEINDEX 1
                        --#HELP "nwalarm.hlp"
                        --#HELPTAG 4
                        --#STATE  DEGRADED

                    ::= 4

errWritingToFileDataStream 	TRAP-TYPE   --1.2.7.12/1.2.7.12
                        ENTERPRISE      nwalarm-mib
                        VARIABLES       {
                                        serverName,trapTime,fileName,
					dataStreamNumber,volumeName,pathName
                                        }
                        DESCRIPTION
                                "Error occurred while writing to file
				 data stream by server."
                        --#TYPE "FileSys: File write err, by server (path)"
                        --#SUMMARY "Error writing to file "
			--#SUMMARY "%s data stream %d. Write requested "
			--#SUMMARY "by server %s. File path %s:%s."
 	                --#ARGUMENTS {2,3,0,4,5}
                        --#SEVERITY CRITICAL
                        --#TIMEINDEX 1
                        --#HELP "nwalarm.hlp"
                        --#HELPTAG 5
                        --#STATE  DEGRADED
                    ::= 5

errWritingToFileDataStreamUsr 	TRAP-TYPE   --1.2.7.13/1.2.7.13
                        ENTERPRISE      nwalarm-mib
                        VARIABLES       {
                                        serverName,trapTime,fileName,
					dataStreamNumber,userName,stationNumber,
					volumeName,pathName
                                        }
                        DESCRIPTION
                                "An error occurred while writing to file
				 data stream by user."
                        --#TYPE "FileSys: File write err, by user (path)"
			--#SUMMARY "Error writing to file %s "
			--#SUMMARY "data stream %d on server %s. Write "
			--#SUMMARY "requested by user %s on station %d. "
			--#SUMMARY "File path %s:%s."
 	                --#ARGUMENTS {2,3,0,4,5,6,7}
                        --#SEVERITY CRITICAL
                        --#TIMEINDEX 1
                        --#HELP "nwalarm.hlp"
                        --#HELPTAG 6
                        --#STATE  DEGRADED
                    ::= 6

fileReaderrSrvrNofileName 	TRAP-TYPE   --1.2.7.14/1.2.7.14
                        ENTERPRISE      nwalarm-mib
                        VARIABLES       {
                                        serverName,trapTime,fileOffset,
					dataStreamNumber
                                        }
                        DESCRIPTION
                                "File read Error. Error getting file name.
				Request	from server."
                        --#TYPE "FileSys: File read err, by server (no path)"
                        --#SUMMARY "File read err at offset %x in "
			--#SUMMARY "data stream %d on server %s. Error getting "
			--#SUMMARY "filename. Read requested by the server."
 	                --#ARGUMENTS {2,3,0}
                        --#SEVERITY CRITICAL
                        --#TIMEINDEX 1
                        --#HELP "nwalarm.hlp"
                        --#HELPTAG 7
                        --#STATE  DEGRADED

                    ::= 7

fileReaderrUsrNofileName 	TRAP-TYPE   --1.2.7.15/1.2.7.15
                        ENTERPRISE      nwalarm-mib
                        VARIABLES       {
                                        serverName,trapTime,fileOffset,
					dataStreamNumber,userName,stationNumber
                                        }
                        DESCRIPTION
                                "File read Error. Error getting file name.
				Request	from user."
                        --#TYPE "FileSys: File read err, by user (no path)"
                        --#SUMMARY "File read error at offset %x "
			--#SUMMARY "data stream %d on server %s.  Error "
			--#SUMMARY "getting filename. Read requested by "
			--#SUMMARY "user %s on station %d."
 	                --#ARGUMENTS {2,3,0,4,5}
                        --#SEVERITY CRITICAL
                        --#TIMEINDEX 1
                        --#HELP "nwalarm.hlp"
                        --#HELPTAG 8
                        --#STATE  DEGRADED

                    ::= 8

fileReaderrDSSrvr 	TRAP-TYPE   --1.2.7.16 /1.2.7.16
                        ENTERPRISE      nwalarm-mib
                        VARIABLES       {
                                        serverName,trapTime,fileName,fileOffset,
					dataStreamNumber,volumeName,pathName
                                        }
                        DESCRIPTION
                                "Error reading file data stream. Request
				from server."
                        --#TYPE "FileSys: File read err, by server (path)"
                        --#SUMMARY "Error reading file %s offset %x "
			--#SUMMARY "data stream %d.  Read requested by "
			--#SUMMARY "server %s. File path %s:%s."
 	                --#ARGUMENTS {2,3,4,0,5,6}
                        --#SEVERITY CRITICAL
                        --#TIMEINDEX 1
                        --#HELP "nwalarm.hlp"
                        --#HELPTAG 9
                        --#STATE  DEGRADED

                    ::= 9

fileReaderrDSUsr 	TRAP-TYPE   --1.2.7.17 /1.2.7.17
                        ENTERPRISE      nwalarm-mib
                        VARIABLES       {
                                        serverName,trapTime,fileName,fileOffset,
					dataStreamNumber,userName,stationNumber,
					volumeName,pathName
                                        }
                        DESCRIPTION
                                "Error reading file data stream. Request
				from user."
                        --#TYPE "FileSys: File read err, by user (path)"
                        --#SUMMARY "Error reading file %s offset %x "
			--#SUMMARY "data stream %d on server %s.  Read "
			--#SUMMARY "requested by user %s "
			--#SUMMARY "on station %d.  File path is %s:%s."
 	                --#ARGUMENTS {2,3,4,0,5,6,7,8}
                        --#SEVERITY CRITICAL
                        --#TIMEINDEX 1
                        --#HELP "nwalarm.hlp"
                        --#HELPTAG 10
                        --#STATE  DEGRADED

                    ::= 10

fileWritePreReaderrSrvr	TRAP-TYPE   --1.2.7.18/1.2.7.18
                        ENTERPRISE      nwalarm-mib
                        VARIABLES       {
                                        serverName,trapTime,fileOffset,
					dataStreamNumber
                                        }
                        DESCRIPTION
                                "File write (pre-read) error in a data stream.
				Error getting file name. Read was requested
				by the server."
                        --#TYPE "FileSys: File pre-read err, by server (no path)"
                        --#SUMMARY "File write (pre-read) error at "
			--#SUMMARY "offset %x data stream %d. Error getting "
			--#SUMMARY "file name. Read requested by server %s."
 	                --#ARGUMENTS {2,3,0}
                        --#SEVERITY CRITICAL
                        --#TIMEINDEX 1
                        --#HELP "nwalarm.hlp"
                        --#HELPTAG 11
                        --#STATE  DEGRADED

                    ::= 11

fileWritePreReaderrUsr 	TRAP-TYPE   --1.2.7.19/1.2.7.19
                        ENTERPRISE      nwalarm-mib
                        VARIABLES       {
                                        serverName,trapTime,fileOffset,
					dataStreamNumber,userName,stationNumber
                                        }
                        DESCRIPTION
                                "File write (pre-read) error in a data stream.
				Error getting file name. Read was requested by
				the user."
                        --#TYPE "FileSys: File pre-read err, by user (no path)"
                        --#SUMMARY "File write (pre-read) error at offset %x "
			--#SUMMARY "data stream %d on server %s.  Error  "
			--#SUMMARY "getting file name. Read requested by  "
               		--#SUMMARY "user %s on station %d."
 	                --#ARGUMENTS {2,3,0,4,5}
                        --#SEVERITY CRITICAL
                        --#TIMEINDEX 1
                        --#HELP "nwalarm.hlp"
                        --#HELPTAG 12
                        --#STATE  DEGRADED
                    ::= 12


fileWritePreReaderrDSSrvr 	TRAP-TYPE   --1.2.7.20 /1.2.7.20
                        ENTERPRISE      nwalarm-mib
                        VARIABLES       {
                                        serverName,trapTime,fileName,fileOffset,
					dataStreamNumber,volumeName,pathName
                                        }
                        DESCRIPTION
                                "File write (pre-read) error in a data stream.
				Read was requested by user."
                        --#TYPE "FileSys: File pre-read err, by server (path)"
                        --#SUMMARY "File %s write (pre-read) error at "
			--#SUMMARY "offset %x data stream %d. Error getting "
			--#SUMMARY " file name. Read requested by server %s. "
			--#SUMMARY " File path %s:%s."
 	                --#ARGUMENTS {2,3,4,0,5,6}
                        --#SEVERITY CRITICAL
                        --#TIMEINDEX 1
                        --#HELP "nwalarm.hlp"
                        --#HELPTAG 13
                        --#STATE  DEGRADED
                    ::= 13

fileWritePreReaderrDSUsr 	TRAP-TYPE   --1.2.7.21/1.2.7.21
                        ENTERPRISE      nwalarm-mib
                        VARIABLES       {
                                        serverName,trapTime,fileName,fileOffset,
					dataStreamNumber,userName,stationNumber,
					volumeName,pathName
                                        }
                        DESCRIPTION
                                "File write (pre-read) error in a data stream.
				Read requested by the user."
                        --#TYPE "FileSys: File pre-read err, by user (path)"
                        --#SUMMARY "File %s write (pre-read) error at "
			--#SUMMARY "offset %x data stream %d on server %s. "
			--#SUMMARY "Read requested by user %s on station %d. "
			--#SUMMARY "File path %s:%s."
	                --#ARGUMENTS {2,3,4,0,5,6,7,8}
                        --#SEVERITY CRITICAL
                        --#TIMEINDEX 1
                        --#HELP "nwalarm.hlp"
                        --#HELPTAG 14
                        --#STATE  DEGRADED

                    ::= 14

cacheMemAllocExceededMinLeftLimit	TRAP-TYPE   --1.2.3.5.26/1.12.5.7.3
                        ENTERPRISE      nwalarm-mib
                        VARIABLES       {
	                                  serverName,trapTime
                                        }
                        DESCRIPTION
                                "Cache memory allocator exceeded minimum
				 cache buffer limit."
                        --#TYPE "Memory: Cache buffer low limit exceeded"
                        --#SUMMARY "Cache memory allocator exceeded min. "
			--#SUMMARY "cache buffer left limit on server %s."
	                --#ARGUMENTS {0}
                        --#SEVERITY MINOR
                        --#TIMEINDEX 1
                        --#HELP "nwalarm.hlp"
                        --#HELPTAG 15
			--#STATE OPERATIONAL

                   ::= 15

cacheMemAllocOutOfMem	TRAP-TYPE   --1.2.3.5.27/1.12.5.7.4
                        ENTERPRISE      nwalarm-mib
                        VARIABLES       {
                                        serverName,trapTime
                                        }
                        DESCRIPTION
                                "Cache memory allocator out of available
				 memory."
                        --#TYPE "Memory: Cache buffers exhausted"
                        --#SUMMARY "Cache memory allocator out of available "
			--#SUMMARY "memory on server %s."
	                --#ARGUMENTS {0}
                        --#SEVERITY CRITICAL
                        --#TIMEINDEX 1
                        --#HELP "nwalarm.hlp"
                        --#HELPTAG 16
			--#STATE DEGRADED

                   ::= 16

numberOfCacheBuffersGettingLow	TRAP-TYPE   --1.2.3.5.28/1.12.5.7.5
                        ENTERPRISE      nwalarm-mib
                        VARIABLES       {
                                        serverName,trapTime
                                        }
                        DESCRIPTION
                                "The OS tried to allocate a cache buffer and
				the remaining number of buffers was less than
				the system limit."
                        --#TYPE "Memory: Cache buffers too low"
                        --#SUMMARY "No. of cache buffers getting too low "
			--#SUMMARY "on server %s."
	                --#ARGUMENTS {0}
                        --#SEVERITY CRITICAL
                        --#TIMEINDEX 1
                        --#HELP "nwalarm.hlp"
                        --#HELPTAG 17
			--#STATE DEGRADED

                   ::= 17

volOfDiskSpace		TRAP-TYPE   --1.6.1.5.19/1.2.5.5.12
                        ENTERPRISE      nwalarm-mib
                        VARIABLES       {
                                        serverName,trapTime,volumeName
                                        }
                        DESCRIPTION
                                "The indicated volume is out of disk space."
                        --#TYPE "FileSys: Vol out of space, no deleted files"
                        --#SUMMARY "Volume %s/%s: out of disk space. "
			--#SUMMARY  "No deleted files are occupying disk space."
 	                --#ARGUMENTS {0,2}
                        --#SEVERITY CRITICAL
                        --#TIMEINDEX 1
                        --#HELP "nwalarm.hlp"
                        --#HELPTAG 18
			--#STATE DEGRADED
                   ::= 18

volOfDiskSpaceNoPurge	TRAP-TYPE   --1.6.1.5.20/1.2.5.5.13
                        ENTERPRISE      nwalarm-mib
                        VARIABLES       {
					serverName,trapTime,volumeName,
					diskSpace
                                        }
                        DESCRIPTION
                                "The indicated volume is out of disk space.
				Space cannot be reclaimed by purging files."
                        --#TYPE "FileSys: Vol out of space, files not purgeable"
                        --#SUMMARY "Volume %s/%s: out of disk space. %dK "
			--#SUMMARY "of disk space in use by "
			--#SUMMARY "deleted files. No deleted files have been "
			--#SUMMARY "deleted long enough to be purged."
 	                --#ARGUMENTS {0,2,3}
                        --#SEVERITY CRITICAL
                        --#TIMEINDEX 1
                        --#HELP "nwalarm.hlp"
                        --#HELPTAG 19
			--#STATE DEGRADED

                   ::= 19

volAlmostOutOfDiskSpace	TRAP-TYPE   --1.6.1.7.21/1.2.5.7.14
                        ENTERPRISE      nwalarm-mib
                        VARIABLES       {
					serverName,trapTime,volumeName
                                        }
                        DESCRIPTION
                                "The available space on the volume has reached
				the SET parameter Volume Low MINOR Threshold
				value."
                        --#TYPE "FileSys: Vol low on space"
                        --#SUMMARY "Volume %s/%s: almost out of disk space."
 	                --#ARGUMENTS {0,2}
                        --#SEVERITY INFORMATIONAL
                        --#TIMEINDEX 1
                        --#HELP "nwalarm.hlp"
                        --#HELPTAG 20
			--#STATE OPERATIONAL
                   ::= 20


errWritingFatTables	TRAP-TYPE   --1.6.1.5.22/1.2.5.7.15
                        ENTERPRISE      nwalarm-mib
                        VARIABLES       {
                                        serverName,trapTime,volumeName
                                        }
                        DESCRIPTION
                                "An error has occurred while writing the FAT
				tables for a particular volume."
                        --#TYPE "FileSys: FAT write err"
                        --#SUMMARY "Error occurred writing the "
			--#SUMMARY "FAT table for volume %s/%s:."
 	                --#ARGUMENTS {0,2}
                        --#SEVERITY CRITICAL
                        --#TIMEINDEX 1
                        --#HELP "nwalarm.hlp"
                        --#HELPTAG 21
			--#STATE DEGRADED
                   ::= 21

errWritingDirectoryBlk	TRAP-TYPE   --1.6.1.5.23 /1.2.5.7.16
                        ENTERPRISE      nwalarm-mib
                        VARIABLES       {
                                        serverName,trapTime,volumeName
                                        }
                        DESCRIPTION
                                "An error has occurred while writing a
				directory block on a particular volume."
                        --#TYPE "FileSys: Directory write err (vol)"
                        --#SUMMARY "Error occurred writing to the "
			--#SUMMARY "directory on %s/%s:."
 	                --#ARGUMENTS {0,2}
                        --#SEVERITY CRITICAL
                        --#TIMEINDEX 1
                        --#HELP "nwalarm.hlp"
                        --#HELPTAG 22
			--#STATE NONOPERATIONAL

                   ::= 22


dirCopyReadErr		TRAP-TYPE   --1.6.1.5.24/1.2.5.7.17
                        ENTERPRISE      nwalarm-mib
                        VARIABLES       {
                                        serverName,trapTime,volumeName
                                        }
                        DESCRIPTION
                                "An error has occurred while reading one copy
				 of a directory on a particular volume."
                        --#TYPE "FileSys: Directory read err, one copy "
                        --#SUMMARY "Error reading one copy of "
			--#SUMMARY "a directory on %s/%s:."
 	                --#ARGUMENTS {0,2}
                        --#SEVERITY CRITICAL
                        --#TIMEINDEX 1
                        --#HELP "nwalarm.hlp"
                        --#HELPTAG 23
			--#STATE DEGRADED

                   ::= 23


errReadingBothCopiesofDir	TRAP-TYPE   --1.6.1.5.25/1.2.5.7.18
                        ENTERPRISE      nwalarm-mib
                        VARIABLES       {
                                        serverName,trapTime,volumeName
                                        }
                        DESCRIPTION
                                "An error has occurred while reading both
				copies of directory from a particular volume."
                        --#TYPE "FileSys: Directory read err, both copies"
                        --#SUMMARY "Error reading both copies of "
			--#SUMMARY "a directory on %s/%s:."
 	                --#ARGUMENTS {0,2}
                        --#SEVERITY CRITICAL
                        --#TIMEINDEX 1
                        --#HELP "nwalarm.hlp"
                        --#HELPTAG 24
			--#STATE NONOPERATIONAL
                   ::= 24

allocateDirEntryWriteError	TRAP-TYPE   --1.6.1.5.26/1.2.5.7.19
                        ENTERPRISE      nwalarm-mib
                        VARIABLES       {
                                        serverName,trapTime,volumeName
                                        }
                        DESCRIPTION
                                "A disk error occurred while
				 writing a newly allocated block on a volume.
				 HotFix could not correct it."
                        --#TYPE "Disk: Err writing new block"
                        --#SUMMARY "Error writing to a newly "
			--#SUMMARY "allocated directory block on %s/%s:."
 	                --#ARGUMENTS {0,2}
                        --#SEVERITY CRITICAL
                        --#TIMEINDEX 1
                        --#HELP "nwalarm.hlp"
                        --#HELPTAG 25
			--#STATE NONOPERATIONAL
                   ::= 25

errExpandingDirDuetoWriteErr	TRAP-TYPE   --1.6.1.5.27/1.2.5.7.28
                        ENTERPRISE      nwalarm-mib
                        VARIABLES       {
                                        serverName,trapTime,volumeName
                                        }
                        DESCRIPTION
                                "A disk error occurred on a volume while
				 expanding an existing directory. HotFix could
				 not correct it."
                        --#TYPE "Disk: Err expanding dir, write err"
                        --#SUMMARY "Error expanding a "
			--#SUMMARY "directory on %s/%s: due to disk write "
 	                --#SUMMARY "errors."
			--#ARGUMENTS {0,2}
                        --#SEVERITY CRITICAL
                        --#TIMEINDEX 1
                        --#HELP "nwalarm.hlp"
                        --#HELPTAG 26
			--#STATE DEGRADED

                   ::= 26

dirReachedItsLimit	TRAP-TYPE   --1.6.1.5.28/1.2.5.5.20
                        ENTERPRISE      nwalarm-mib
                        VARIABLES       {
                                        serverName,trapTime,volumeName
                                        }
                        DESCRIPTION
                                "A disk error occurred on a volume while
				 expanding an existing directory because the
				directory size reached its limit."
                        --#TYPE "Disk: Err expanding dir, size limit"
                        --#SUMMARY "Error expanding a directory "
			--#SUMMARY "on %s/%s: because the directory size "
			--#SUMMARY "limit was exceeded."
 	                --#ARGUMENTS {0,2}
                        --#SEVERITY CRITICAL
                        --#TIMEINDEX 1
                        --#HELP "nwalarm.hlp"
                        --#HELPTAG 27
			--#STATE DEGRADED

                   ::= 27

errExpandingNoDiskSpace	TRAP-TYPE   --1.6.1.5.29/1.2.5.7.21
                        ENTERPRISE      nwalarm-mib
                        VARIABLES       {
					serverName,trapTime,volumeName
                                        }
                        DESCRIPTION
                                "A disk error occurred on a volume while
				expanding an existing directory because no
				more disk space was available."
                        --#TYPE "Disk: Err expanding dir, no space"
                        --#SUMMARY "Error expanding a directory "
			--#SUMMARY " on %s/%s: because no more disk space was "
			--#SUMMARY "available."
	                --#ARGUMENTS {0,2}
                        --#SEVERITY CRITICAL
                        --#TIMEINDEX 1
                        --#HELP "nwalarm.hlp"
                        --#HELPTAG 28
			--#STATE DEGRADED
                   ::= 28

errExpandingNoMemSpace	TRAP-TYPE   --1.6.1.7.30/1.2.5.7.22
                        ENTERPRISE      nwalarm-mib
                        VARIABLES       {
                                        serverName,trapTime,volumeName
                                        }
                        DESCRIPTION
                                "A disk error occurred on a volume while
				expanding an existing directory because no
				more server memory was available to
				expand directory tables."
                        --#TYPE "Memory: Err expanding directory, no memory"
                        --#SUMMARY "Error expanding directory on %s/%s: "
			--#SUMMARY "because no more memory available "
			--#SUMMARY  "for directory tables."
	                --#ARGUMENTS {0,2}
                        --#SEVERITY CRITICAL
                        --#TIMEINDEX 1
                        --#HELP "nwalarm.hlp"
                        --#HELPTAG 29
			--#STATE DEGRADED
                   ::= 29



dirSizeGettingTooLrgeForMem	TRAP-TYPE   --1.6.1.7.31/1.2.5.5.23
                        ENTERPRISE      nwalarm-mib
                        VARIABLES       {
                                        serverName,trapTime,volumeName
                                        }
                        DESCRIPTION
                                "The volume directory table is getting too
				 large for server memory."
                        --#TYPE "Memory: Directory table too big for memory"
                        --#SUMMARY "Directory table on %s/%s: getting "
			--#SUMMARY "too large for available memory."
			--#SUMMARY "You may need to add more memory "
			--#SUMMARY "to the file server."
	                --#ARGUMENTS {0,2}
                        --#SEVERITY CRITICAL
                        --#TIMEINDEX 1
                        --#HELP "nwalarm.hlp"
                        --#HELPTAG 30
			--#STATE DEGRADED

                   ::= 30


lanReceiveBuffLimitReached	TRAP-TYPE   --1.9.5.13/1.7.12
                        ENTERPRISE      nwalarm-mib
                        VARIABLES       {
                                        serverName,trapTime
                                        }
                        DESCRIPTION
                                "No OS LAN buffers available for receiving
				packets."
                        --#TYPE "Network: LAN receive buffer limit reached"
                        --#SUMMARY "No OS LAN buffers are "
			--#SUMMARY  "available on server %s."
	                --#ARGUMENTS {0}
                        --#SEVERITY MAJOR
                        --#TIMEINDEX 1
                        --#HELP "nwalarm.hlp"
                        --#HELPTAG 31
			--#STATE DEGRADED
                   ::= 31


connTerminatedByWatchDog	TRAP-TYPE   --1.5.5.4/1.2.1.7.22
                        ENTERPRISE      nwalarm-mib
                        VARIABLES       {
                                        serverName,trapTime,userName,
                                        stationNumber
                                        }
                        DESCRIPTION
                                "Watchdog cleared the user connection"
                        --#TYPE "Connection: Cleared, by watchdog"
                        --#SUMMARY "User %s on station %d cleared by "
			--#SUMMARY "connection watchdog on server %s "
			--#SUMMARY "due to communication "
			--#SUMMARY " or station failure."
			--#ARGUMENTS {2,3,0}
                        --#SEVERITY CRITICAL
                        --#TIMEINDEX 1
                        --#HELP "nwalarm.hlp"
                        --#HELPTAG 32
			--#STATE   OPERATIONAL
                   ::= 32

copyrightViolation	TRAP-TYPE -- 1.5.11/1.5.11
			ENTERPRISE	nwalarm-mib
			VARIABLES 	{
                                        serverName,trapTime,networkAddress,
					macAddress
					}
			DESCRIPTION
				"Two NetWare servers on the network have
				 identical serial numbers. This is a
				 violation of NetWare's copyright and is
				illegal."

                        --#TYPE "System: Copyright violation"
                        --#SUMMARY "NetWare copyright violation on server %s! "
			--#SUMMARY "Call supervisor! Server at address %x:%x "
			--#SUMMARY "has the same serial number as this server."
                        --#ARGUMENTS {0,2,3}
                        --#SEVERITY CRITICAL
                        --#TIMEINDEX 1
                        --#HELP "nwalarm.hlp"
                        --#HELPTAG 33
                        --#STATE  OPERATIONAL

			::= 33

writeFault	  	TRAP-TYPE   --1.12.5.7
			ENTERPRISE      nwalarm-mib
			VARIABLES  {
                                        serverName,trapTime,processName,
					nlmName,codeOffset,memoryAddress
                                    }
			DESCRIPTION
                                "An NLM tried to write to a memory location
				 where it did not have write rights."
                        --#TYPE "OS: Write fault"
                        --#SUMMARY "Attempted write to protected or non-present "
			--#SUMMARY "page on server %s. Process: %s. Module: %s. "
			--#SUMMARY "Code offset in module: %x. Access address: "
			--#SUMMARY "%x."
 	                --#ARGUMENTS {0,2,3,4,5}
                        --#SEVERITY MINOR
                        --#TIMEINDEX 1
                        --#HELP "nwalarm.hlp"
                        --#HELPTAG 34
			--#STATE DEGRADED
	         ::= 34

readFault	  	TRAP-TYPE   --1.12.5.8
			ENTERPRISE      nwalarm-mib
			VARIABLES  {
                                        serverName,trapTime,processName,
					nlmName,codeOffset,memoryAddress
                                    }
			DESCRIPTION
                                "An NLM tried to read a memory location where
				it did not have read rights."
                        --#TYPE "OS: Read fault"
                        --#SUMMARY "Attempted read from protected or "
			--#SUMMARY "non-present page on server %s. Process:%s. "
			--#SUMMARY "Module: %s. Code offset in module: %x. Access "
 	                --#SUMMARY "address: %x."
			--#ARGUMENTS {0,2,3,4,5}
                        --#SEVERITY MINOR
                        --#TIMEINDEX 1
                        --#HELP "nwalarm.hlp"
                        --#HELPTAG 35
			--#STATE DEGRADED
	         ::= 35

ipxReceivedIncomPacket	TRAP-TYPE   --1.9.7.8/1.9.7.8
                        ENTERPRISE      nwalarm-mib
                        VARIABLES       {
                                        serverName,trapTime,networkAddress,
					macAddress,numberOfPackets
                                        }
                        DESCRIPTION
                                "IPX is receiving incomplete packets from a
				 node."
                        --#TYPE "Network: Bad IPX packet"
                        --#SUMMARY "IPX on server %s receiving incomplete "
			--#SUMMARY "packets from network:node %x:%x. %d "
			--#SUMMARY "incomplete packets received."
		        --#ARGUMENTS {0,2,3,4}
                        --#SEVERITY MINOR
                        --#TIMEINDEX 1
                        --#HELP "nwalarm.hlp"
                        --#HELPTAG 36
			--#STATE OPERATIONAL
                   ::= 36

unableToCreateVOLERR	TRAP-TYPE   --1.6.1.5.32/1.2.5.7.24
                        ENTERPRISE      nwalarm-mib
                        VARIABLES       {
                                        serverName,trapTime,volumeName
                                        }
                        DESCRIPTION
                                "The system error log file (VOL$LOG.ERR) could
				 not be created."
                        --#TYPE "FileSys: VOL$LOG.ERR create err, "
                        --#SUMMARY "Unable to create VOL$LOG.ERR on volume %s "
			--#SUMMARY "on server %s."
	                --#ARGUMENTS {2,0}
                        --#SEVERITY MINOR
                        --#TIMEINDEX 1
                        --#HELP "nwalarm.hlp"
                        --#HELPTAG 37
			--#STATE DEGRADED
                   ::= 37

unableToWriteVOLERR	TRAP-TYPE   --1.6.1.5.33/1.2.5.7.25
                        ENTERPRISE      nwalarm-mib
                        VARIABLES       {
                                        serverName,trapTime,volumeName
                                        }
                        DESCRIPTION
                                "The system error log file (VOL$LOG.ERR) could
				 not be written to."
                        --#TYPE "FileSys: VOL$LOG.ERR write err, "
                        --#SUMMARY "Unable to write to VOL$LOG.ERR "
			--#SUMMARY "on volume %s on server %s."
	                --#ARGUMENTS {2,0}
                        --#SEVERITY MINOR
                        --#TIMEINDEX 1
                        --#HELP "nwalarm.hlp"
                        --#HELPTAG 38
			--#STATE DEGRADED
                   ::= 38

volOprDespiteDeviceDriveDeact	TRAP-TYPE   --1.6.1.7.34/1.2.5.7.26
                        ENTERPRISE      nwalarm-mib
                        VARIABLES       {
                                        serverName,trapTime,volumeName
                                        }
                        DESCRIPTION
                                "The volume is still accessible although it is
				no longer fully mirrored."
                        --#TYPE "Disk: Deactivated, mirrored drive"
                        --#SUMMARY "Volume %s is still operational "
			--#SUMMARY "due to mirrored drive deactivation on "
			--#SUMMARY "server %s."
	                --#ARGUMENTS {2,0}
                        --#SEVERITY CRITICAL
                        --#TIMEINDEX 1
                        --#HELP "nwalarm.hlp"
                        --#HELPTAG 39
			--#STATE DEGRADED
                   ::= 39

loginDisabledByUser     TRAP-TYPE   --1.5.7.7/1.2.1.7.11
                        ENTERPRISE      nwalarm-mib
                        VARIABLES       {
                                        serverName,trapTime,userName,
					stationNumber
                                        }
                        DESCRIPTION
                                "A specified user issued a disable login
				 command."
                        --#TYPE "System: Login disabled, by user #1"
                        --#SUMMARY "Login disabled on server %s by user %s on "
			--#SUMMARY "station %d."
  	                --#ARGUMENTS {0,2,3}
                        --#SEVERITY INFORMATIONAL
                        --#TIMEINDEX 1
                        --#HELP "nwalarm.hlp"
                        --#HELPTAG 40
			--#STATE OPERATIONAL

                   ::= 40

loginEnabledByUser      TRAP-TYPE   --1.5.7.8/1.2.1.7.12
                        ENTERPRISE      nwalarm-mib
                        VARIABLES       {
                                        serverName,trapTime,userName,
					stationNumber
                                        }
                        DESCRIPTION
                                "A specified user issued an enable login
				 command."
                        --#TYPE "System: Login enabled, by user #2"
                        --#SUMMARY "Login enabled on server %s by user %s on "
			--#SUMMARY "station %d."
  	                --#ARGUMENTS {0,2,3}
                        --#SEVERITY INFORMATIONAL
                        --#TIMEINDEX 1
                        --#HELP "nwalarm.hlp"
                        --#HELPTAG 41
			--#STATE OPERATIONAL

                   ::= 41


clrStnByConsole		TRAP-TYPE   --1.5.7.14/1.2.1.7.13
                        ENTERPRISE      nwalarm-mib
                        VARIABLES       {
                                        serverName,trapTime,stationNumber
                                        }
                        DESCRIPTION
                                "A specified connection was cleared at the
				 server console."
                        --#TYPE "Connection: Cleared"
                        --#SUMMARY "Server %s cleared of station %d. "
			--#SUMMARY " Connection terminated on server %s."
  	                --#ARGUMENTS {0,2,0}
                        --#SEVERITY INFORMATIONAL
                        --#TIMEINDEX 1
                        --#HELP "nwalarm.hlp"
                        --#HELPTAG 42
			--#STATE OPERATIONAL
                   ::= 42

clrStnByUsr		TRAP-TYPE   --1.5.7.15/1.2.1.7.14
                        ENTERPRISE      nwalarm-mib
                        VARIABLES       {
                                        serverName,trapTime,userName,
					connectionNumber,userName1,stationNumber
                                        }
                        DESCRIPTION
                                "A specified connection was cleared from
				 a workstation."
                        --#TYPE "Connection: Cleared at user console"
                        --#SUMMARY "%s connection %d cleared by user %s on "
			--#SUMMARY "station %d on server %s."
  	                --#ARGUMENTS {2,3,4,5,0}
                        --#SEVERITY INFORMATIONAL
                        --#TIMEINDEX 1
                        --#HELP "nwalarm.hlp"
                        --#HELPTAG 43
			--#STATE  OPERATIONAL
                   ::= 43

fileServerDowned        TRAP-TYPE --1.7.10/1.7.10
                        ENTERPRISE      nwalarm-mib
                        VARIABLES       {
                                        serverName,trapTime,userName,
					stationNumber
                                        }
                        DESCRIPTION
                                "The file server was downed from a
				workstation console."
                        --#TYPE "System: Server downed, by user"
                        --#SUMMARY "File server %s was downed by user %s "
			--#SUMMARY "at station %d."
                        --#ARGUMENTS {0,2,3}
                        --#SEVERITY CRITICAL
                        --#TIMEINDEX 1
                        --#HELP "nwalarm.hlp"
                        --#HELPTAG 44
                        --#STATE  NONOPERATIONAL

                        ::= 44

errOpeningRIPSocket	TRAP-TYPE   --1.9.2.5.3
                        ENTERPRISE      nwalarm-mib
                        VARIABLES       {
                                        serverName,trapTime
                                        }
                        DESCRIPTION
                                "The server encountered an error while opening
				 a RIP socket."
                        --#TYPE "Router: Err opening RIP socket"
                        --#SUMMARY "RIP socket was already open when a router "
			--#SUMMARY "attempted to open it on "
			--#SUMMARY "server %s."
 	                --#ARGUMENTS {0}
                        --#SEVERITY CRITICAL
                        --#TIMEINDEX 1
                        --#HELP "nwalarm.hlp"
                        --#HELPTAG 45
			--#STATE OPERATIONAL

                   ::= 45

rtrConfigErr		TRAP-TYPE   --1.9.7.2/1.9.7.2
                        ENTERPRISE      nwalarm-mib
                        VARIABLES       {
                                        serverName,trapTime,macAddress,
					networkAddress,networkAddress1
                                        }
                        DESCRIPTION
                                "A router claims that a particular
				network address should actually be another
				address."
                        --#TYPE "Router: Config err #1"
                        --#SUMMARY "Server %s reports a router configuration "
			--#SUMMARY  "error. Router at node %x claims "
			--#SUMMARY  "network %x should be %x."
	                --#ARGUMENTS {0,2,3,4}
                        --#SEVERITY CRITICAL
                        --#TIMEINDEX 1
                        --#HELP "nwalarm.hlp"
                        --#HELPTAG 46
			--#STATE DEGRADED

                   ::= 46

lanDriverLoopBack	TRAP-TYPE   --1.9.7.3/1.9.7.3
                        ENTERPRISE      nwalarm-mib
                        VARIABLES       {
                                        serverName,trapTime,networkAddress
                                        }
                        DESCRIPTION
                                "A particular LAN driver received its own
				packet."
                        --#TYPE "Network: LAN driver loopback err"
                        --#SUMMARY "LAN driver loopback error detected. "
			--#SUMMARY "Driver for network %x received its own "
			--#SUMMARY "send packet on server %s."
	                --#ARGUMENTS {2,0}
                        --#SEVERITY MINOR
                        --#TIMEINDEX 1
                        --#HELP "nwalarm.hlp"
                        --#HELPTAG 47
			--#STATE DEGRADED

                   ::= 47

dupInternetAddr		TRAP-TYPE   --1.9.7.4/1.9.7.4
                        ENTERPRISE      nwalarm-mib
                        VARIABLES       {
                                        serverName,trapTime
                                        }
                        DESCRIPTION
                                "Two routers are claiming the same internet
				 address."
                        --#TYPE "Router: Duplicate internet address"
                        --#SUMMARY "Server %s reports a router configuration "
			--#SUMMARY "error. Another router claims "
			--#SUMMARY "the same internet address."
	                --#ARGUMENTS {0}
                        --#SEVERITY CRITICAL
                        --#TIMEINDEX 1
                        --#HELP "nwalarm.hlp"
                        --#HELPTAG 48
			--#STATE DEGRADED

                   ::= 48

lanBdUnreachable	TRAP-TYPE   --1.9.7.5/1.9.7.5
                        ENTERPRISE      nwalarm-mib
                        VARIABLES       {
                                        serverName,trapTime,networkAddress
                                        }
                        DESCRIPTION
                                "An IPX local network was removed because
				the LAN board was unreachable."
                        --#TYPE "Network: LAN board unreachable"
                        --#SUMMARY "IPX local network %x removed because LAN "
			--#SUMMARY "board unreachable on server %s."
	                --#ARGUMENTS {2,0}
                        --#SEVERITY CRITICAL
                        --#TIMEINDEX 1
                        --#HELP "nwalarm.hlp"
                        --#HELPTAG 49
			--#STATE DEGRADED

                   ::= 49

ipxUnbndRequest		TRAP-TYPE   --1.9.7.6/1.9.7.6
                        ENTERPRISE      nwalarm-mib
                        VARIABLES       {
                                        serverName,trapTime,networkAddress
                                        }
                        DESCRIPTION
                                "An IPX local network was removed because
				of an UNBIND request."
                        --#TYPE "Network: IPX unbound"
                        --#SUMMARY "IPX local network %x removed because "
			--#SUMMARY "of UNBIND request on server %s."
	                --#ARGUMENTS {2,0}
                        --#SEVERITY MINOR
                        --#TIMEINDEX 1
                        --#HELP "nwalarm.hlp"
                        --#HELPTAG 50
			--#STATE DEGRADED

                   ::= 50

errOpeningSAPSocket	TRAP-TYPE   --1.9.2.5.2
                        ENTERPRISE      nwalarm-mib
                        VARIABLES       {
                                        serverName,trapTime
                                        }
                        DESCRIPTION
                                "The server encountered an error while opening
				 a SAP socket."
                        --#TYPE "Router: Err opening SAP socket"
                        --#SUMMARY "SAP socket was already open when a router "
			--#SUMMARY "attempted to open it on server %s."
	                --#ARGUMENTS {0}
                        --#SEVERITY MINOR
                        --#TIMEINDEX 1
                        --#HELP "nwalarm.hlp"
                        --#HELPTAG 51
			--#STATE OPERATIONAL

                   ::= 51

rtrClaimingSameInterAddr	TRAP-TYPE   --1.9.7.1/1.9.7.1
                        ENTERPRISE      nwalarm-mib
                        VARIABLES       {
                                        serverName,trapTime,routerName
                                        }
                        DESCRIPTION
                                "Two routers are claiming the same
				 internet address."
                        --#TYPE "Router: Two routers claim same address"
                        --#SUMMARY "Server %s reports a router configuration "
			--#SUMMARY "error. Router %s claims my same "
			--#SUMMARY " internet address."
	                --#ARGUMENTS {0,2}
                        --#SEVERITY MINOR
                        --#TIMEINDEX 1
                        --#HELP "nwalarm.hlp"
                        --#HELPTAG 52
			--#STATE DEGRADED

                   ::= 52

spuriousInt	 	TRAP-TYPE   --1.13.5.14/1.5.14
			ENTERPRISE      nwalarm-mib
			VARIABLES  {
                                        serverName,trapTime,interruptNumber
                                    }
			DESCRIPTION
                                "No interrupt service routine was registered
				with this driver."
                        --#TYPE "OS: Spurious interrupt"
                        --#SUMMARY "Spurious hardware interrupt %d detected "
			--#SUMMARY "on server %s."
 	                --#ARGUMENTS {2,0}
                        --#SEVERITY MINOR
                        --#TIMEINDEX 1
                        --#HELP "nwalarm.hlp"
                        --#HELPTAG 53
			--#STATE OPERATIONAL

	         ::= 53

checksumInvalid		TRAP-TYPE   --1.1.5.23
                        ENTERPRISE      nwalarm-mib
                        VARIABLES       {
                                        serverName,trapTime,userName,
					networkAddress,macAddress
                                        }
                        DESCRIPTION
                                "An IPX NCP packet with invalid checksum was
				 received. Possible network corruption."
                        --#TYPE "Network: Invalid checksum"
                        --#SUMMARY "Server %s received an IPX NCP packet with "
			--#SUMMARY "invalid checksum from user %s at %x:%x. "
			--#SUMMARY "Possible network corruption."
                        --#ARGUMENTS {0,2,3,4}
                        --#SEVERITY MINOR
                        --#TIMEINDEX 1
                        --#HELP "nwalarm.hlp"
                        --#HELPTAG 54
                        --#STATE  OPERATIONAL

                        ::= 54

prmyPicLostInterrupt 	TRAP-TYPE   --1.13.5.15/1.5.15
			ENTERPRISE      nwalarm-mib
			VARIABLES  {
                                       serverName,trapTime
                                    }
			DESCRIPTION
                                "The hardware set an interrupt but when the
				CPU responded to it the interrupt was no longer
				available. The hardware interrupt controller
				that lost the interrupt was the primary
				interrupt controller."
                        --#TYPE "OS: Lost interrupt, primary controller"
                        --#SUMMARY "Primary interrupt controller detected a "
			--#SUMMARY "lost hardware interrupt on server %s."
 	                --#ARGUMENTS {0}
                        --#SEVERITY MINOR
                        --#TIMEINDEX 1
                        --#HELP "nwalarm.hlp"
                        --#HELPTAG 55
			--#STATE DEGRADED
	         ::= 55

scndryPicLostInterrupt 	TRAP-TYPE   --1.13.5.16/1.5.16
			ENTERPRISE      nwalarm-mib
			VARIABLES  {
                                        serverName,trapTime
                                    }
			DESCRIPTION
                                "The hardware set an interrupt but when the
				CPU responded to it the interrupt was no longer
				available. The hardware interrupt controller
				that lost the interrupt was the secondary
				interrupt controller."
                        --#TYPE "OS: Lost interrupt, secondary controller"
                        --#SUMMARY "Secondary interrupt controller detected "
			--#SUMMARY "a lost hardware interrupt on server %s."
 	                --#ARGUMENTS {0}
                        --#SEVERITY MINOR
                        --#TIMEINDEX 1
                        --#HELP "nwalarm.hlp"
                        --#HELPTAG 56
			--#STATE DEGRADED

	         ::= 56

--the following alert is not generated by the OS but it defined in nmevents.h
exception	 	TRAP-TYPE   --1.13.5.18
			ENTERPRISE      nwalarm-mib
			VARIABLES  {
                                       serverName,trapTime,domainName,
                                       processName,nlmName,codeOffset
                                    }
			DESCRIPTION
                                "An exception occurred due to an NLM
				writing to an invalid memory address."
                        --#TYPE "OS: Exception"
                        --#SUMMARY "Domain %s quarantined on server %s. "
			--#SUMMARY "Process: %s, module %s, code offset in "
			--#SUMMARY "module: %x caused an exception."
		        --#ARGUMENTS {2,0,3,4,5}
                        --#SEVERITY MINOR
                        --#TIMEINDEX 1
                        --#HELP "nwalarm.hlp"
                        --#HELPTAG 57
			--#STATE DEGRADED

	         ::= 57

invalidScreenID		TRAP-TYPE   --1.1.5.1.7.5
                        ENTERPRISE      nwalarm-mib
                        VARIABLES       {
                                        serverName,trapTime,nlmName,
					codeOffset
                                        }
                        DESCRIPTION
                                "An NLM passed an invalid screen ID to the
				 kernel."
                        --#TYPE "OS: Invalid screen ID"
                        --#SUMMARY "Invalid screen ID passed to screen "
			--#SUMMARY "manager on %s. Module: %s. "
			--#SUMMARY "Code offset in module: %x."
  	                --#ARGUMENTS {0,2,3}
                        --#SEVERITY CRITICAL
                        --#TIMEINDEX 1
                        --#HELP "nwalarm.hlp"
                        --#HELPTAG 58
                        --#STATE  DEGRADED

                    ::= 58


prssDidNotRelqhCntlFqtly TRAP-TYPE   --1.1.5.1.7.4/1.1.5.1.7.4
                        ENTERPRISE      nwalarm-mib
                        VARIABLES       {
                                        serverName,trapTime,processName,
					nlmName,codeOffset
                                        }
                        DESCRIPTION
                                "An NLM did not
				relinquish control within the system execution
				limit of .4 seconds."
                        --#TYPE "OS: Control not relinquished"
                        --#SUMMARY "%s process did not relinquish control "
			--#SUMMARY "in time on %s. Module: %s. "
			--#SUMMARY "Code offset in module: %x."
  	                --#ARGUMENTS {2,0,3,4}
                        --#SEVERITY MAJOR
                        --#TIMEINDEX 1
                        --#HELP "nwalarm.hlp"
                        --#HELPTAG 59
                        --#STATE  DEGRADED

                    ::= 59

fileSrvrUsrDeleted	TRAP-TYPE   --1.5.7.22/1.11.6.7.1
                        ENTERPRISE      nwalarm-mib
                        VARIABLES       {
                                        serverName,trapTime,userName
                                        }
                        DESCRIPTION
                                "A user account was deleted while the user
				 was logged in."
                        --#TYPE "User: Account deleted, by server"
			--#SUMMARY "User %s account deleted while "
			--#SUMMARY "user was logged into server %s."
 	                --#ARGUMENTS {2,0}
                        --#SEVERITY CRITICAL
                        --#TIMEINDEX 1
                        --#HELP "nwalarm.hlp"
                        --#HELPTAG 60
			--#STATE OPERATIONAL

                   ::= 60
--The following trap has an another alert similar to this, the only difference
--being the deletion of a single connection as compared to 'n' number of
-- active connections. The trap number is 233.

usrAcctDeletedByAUsr	TRAP-TYPE   --1.5.7.18/1.11.6.7.2 and 1.11.6.7.3
                        ENTERPRISE      nwalarm-mib
                        VARIABLES       {
                                        serverName,trapTime,accountName,
					userName,stationNumber,
					numberOfConnections
                                        }
                        DESCRIPTION
                                "User account deleted by another user while
				the deleted user was logged in."
                        --#TYPE "User: Account deleted, by user"
                        --#SUMMARY "Account %s deleted by user %s on station "
			--#SUMMARY "%d. %d active connections terminated on "
			--#SUMMARY "server %s."
	                --#ARGUMENTS {2,3,4,5,0}
                        --#SEVERITY CRITICAL
                        --#TIMEINDEX 1
                        --#HELP "nwalarm.hlp"
                        --#HELPTAG 61
			--#STATE OPERATIONAL
                   ::= 61


invalidResourceTag	TRAP-TYPE   --1.1.3.7.1/1.1.3.7.1
                        ENTERPRISE      nwalarm-mib
                        VARIABLES       {
                                        serverName,trapTime
                                        }
                        DESCRIPTION
                                "An invalid resource tag was passed to the OS."
                        --#TYPE "OS: Bad resrc tag passed to ParseDriverParms"
                        --#SUMMARY "Invalid resource tag passed to the "
			--#SUMMARY "OS function ParseDriverParameters "
			--#SUMMARY " on server %s."
                        --#ARGUMENTS {0}
                        --#SEVERITY CRITICAL
                        --#TIMEINDEX 1
                        --#HELP "nwalarm.hlp"
                        --#HELPTAG 62
                        --#STATE  DEGRADED

                        ::= 62

diskDeactivatedUnknownReason 	TRAP-TYPE   --1.13.7.2
			ENTERPRISE      nwalarm-mib
			VARIABLES  {
                                        serverName,trapTime,deviceName
                                    }
			DESCRIPTION
                                "A disk has been deactivated."
                        --#TYPE "Disk: Deactivated, cause unknown"
                        --#SUMMARY "%s deactivated for unknown reason on "
			--#SUMMARY "server %s."
 	                --#ARGUMENTS {2,0}
                        --#SEVERITY CRITICAL
                        --#TIMEINDEX 1
                        --#HELP "nwalarm.hlp"
                        --#HELPTAG 63
			--#STATE DEGRADED

	         ::= 63



diskDeactivatedDriverUnload 	TRAP-TYPE   --1.13.7.10
			ENTERPRISE      nwalarm-mib
			VARIABLES  {
                                        serverName,trapTime,deviceName
                                    }
			DESCRIPTION
                                "The system deactivated the specified disk
				because the associated driver was unloaded by
				a console operator command."
                        --#TYPE "Disk: Deactivated, driver unloaded"
                        --#SUMMARY "Disk %s deactivated due to driver unload "
			--#SUMMARY "on server %s."
 	                --#ARGUMENTS {2,0}
                        --#SEVERITY CRITICAL
                        --#TIMEINDEX 1
                        --#HELP "nwalarm.hlp"
                        --#HELPTAG 64
			--#STATE  DEGRADED

	         ::= 64


diskDeactivatedDeviceFailure 	TRAP-TYPE   --1.13.5.3
			ENTERPRISE      nwalarm-mib
			VARIABLES  {
                                        serverName,trapTime,deviceName
                                    }
			DESCRIPTION
                                "A disk has been deactivated by the
				disk driver due to device failure."
                        --#TYPE "Disk: Deactivated, device failure"
                        --#SUMMARY "Disk %s deactivated by driver due to "
			--#SUMMARY " device failure on server %s."
 	                --#ARGUMENTS {2,0}
                        --#SEVERITY CRITICAL
                        --#TIMEINDEX 1
                        --#HELP "nwalarm.hlp"
                        --#HELPTAG 65
			--#STATE DEGRADED

	         ::= 65

diskDeactivatedUsrRequest 	TRAP-TYPE   --1.13.7.19
			ENTERPRISE      nwalarm-mib
			VARIABLES  {
                                        serverName,trapTime,deviceName
                                    }
			DESCRIPTION
                                "The system deactivated the specified disk
				because the associated driver was unloaded by
				a user-initiated UNLOAD command."
                        --#TYPE "Disk: Deactivated, by user"
                        --#SUMMARY "Disk %s deactivated due to user request on "
			--#SUMMARY "server %s."
 	                --#ARGUMENTS {2,0}
                        --#SEVERITY CRITICAL
                        --#TIMEINDEX 1
                        --#HELP "nwalarm.hlp"
                        --#HELPTAG 66
			--#STATE DEGRADED
	         ::= 66

diskDeactivatedMediaDismount 	TRAP-TYPE   --1.13.5.6
			ENTERPRISE      nwalarm-mib
			VARIABLES  {
                                        serverName,trapTime,deviceName
                                    }
			DESCRIPTION
                                "The OS detected that a different medium
				was loaded in a drive and deactivated
				 the disk."
                        --#TYPE "Disk: Deactivated, media dismount"
                        --#SUMMARY "Disk %s deactivated due to media dismount "
			--#SUMMARY "on server %s."
 	                --#ARGUMENTS {2,0}
                        --#SEVERITY CRITICAL
                        --#TIMEINDEX 1
                        --#HELP "nwalarm.hlp"
                        --#HELPTAG 67
			--#STATE  DEGRADED

	         ::= 67

diskDeactivatedEOM 	TRAP-TYPE   --1.13.5.7
			ENTERPRISE      nwalarm-mib
			VARIABLES  {
                                        serverName,trapTime,deviceName
                                    }
			DESCRIPTION
                                "The system deactivated the specified disk
				because the end of the medium was reached."
                        --#TYPE "Disk: Deactivated, media eject"
                        --#SUMMARY "Disk %s deactivated due to medium eject on "
			--#SUMMARY "server %s."
 	                --#ARGUMENTS {2,0}
                        --#SEVERITY CRITICAL
                        --#TIMEINDEX 1
                        --#HELP "nwalarm.hlp"
                        --#HELPTAG 68
			--#STATE DEGRADED

	         ::= 68


diskDeactivatedServerDown 	TRAP-TYPE   --1.13.7.20
			ENTERPRISE      nwalarm-mib
			VARIABLES  {
                                        serverName,trapTime,deviceName
                                    }
			DESCRIPTION
                                "The system deactivated the specified disk
				because the associated driver was unloaded by
				a user-initiated DOWN server command."
                        --#TYPE "Disk: Deactivated, server downed"
                        --#SUMMARY "Disk %s deactivated due to down command on "
			--#SUMMARY "server %s."
 	                --#ARGUMENTS {2,0}
                        --#SEVERITY CRITICAL
                        --#TIMEINDEX 1
                        --#HELP "nwalarm.hlp"
                        --#HELPTAG 69
			--#STATE NONOPERATIONAL

	         ::= 69

diskDeactivatedServerFailure 	TRAP-TYPE   --1.13.5.5
			ENTERPRISE      nwalarm-mib
			VARIABLES  {
                                        serverName,trapTime,deviceName
                                    }
			DESCRIPTION
                                "The specified disk has been deactivated because
				the OS detected a failure in the file system."
                        --#TYPE "Disk: Deactivated, file system failure"
                        --#SUMMARY "Disk %s deactivated due to file system failure "
			--#SUMMARY " on server %s."
 	                --#ARGUMENTS {2,0}
                        --#SEVERITY CRITICAL
                        --#TIMEINDEX 1
                        --#HELP "nwalarm.hlp"
                        --#HELPTAG 70
			--#STATE NONOPERATIONAL

	         ::= 70

--The following trap has a similar trap for releasing 'n' number resources.
--The trap number is 199
moduleDidNotReleaseOneResource	TRAP-TYPE   --1.1.3.5.7
                        ENTERPRISE      nwalarm-mib
                        VARIABLES       {
                                        serverName,trapTime,
					nlmName,resourceName,resourceDescription
                                        }
                        DESCRIPTION
                                "An NLM did not release a resource."
                        --#TYPE "OS: NLM did not release resource."
                        --#SUMMARY "Module on server %s did not release "
			--#SUMMARY "a resource. Module: %s. Resource: %s. "
			--#SUMMARY "Description: %s."
                        --#ARGUMENTS {0,2,3,4}
                        --#SEVERITY CRITICAL
                        --#TIMEINDEX 1
                        --#HELP "nwalarm.hlp"
                        --#HELPTAG 71
                        --#STATE  DEGRADED
                        ::= 71

mirroredPartNotAllSync	TRAP-TYPE   --1.10.1.1.1.7.22
                        ENTERPRISE      nwalarm-mib
                        VARIABLES       {
                                        serverName,trapTime,partitionNumber
                                        }
                        DESCRIPTION
                                "The system has not mirrored all system
				 partitions that are designated as mirrored
				 partitions."
                        --#TYPE "Disk: Partition not remirrored"
                        --#SUMMARY "Mirrored partition %d "
			--#SUMMARY "cannot be remirrored on server %s."
 	                --#ARGUMENTS {2,0}
                        --#SEVERITY CRITICAL
                        --#TIMEINDEX 1
                        --#HELP "nwalarm.hlp"
                        --#HELPTAG 72
			--#STATE DEGRADED
	            ::= 72

allMirroredPartAreSync	TRAP-TYPE   --1.10.1.1.1.7.23 /1.2.7.29
                        ENTERPRISE      nwalarm-mib
                        VARIABLES       {
                                        serverName,trapTime
                                        }
                        DESCRIPTION
                                "The system has mirrored all system partitions
				that are designated as mirrored partitions."
                        --#TYPE "Disk: Partitions all synchronized"
                        --#SUMMARY "All mirrored partitions "
			--#SUMMARY "are synchronized on server %s."
 	                --#ARGUMENTS {0}
                        --#SEVERITY CRITICAL
                        --#TIMEINDEX 1
                        --#HELP "nwalarm.hlp"
                        --#HELPTAG 73
			--#STATE OPERATIONAL
	            ::= 73

partitionsSync		TRAP-TYPE   --1.10.1.1.1.7.24/1.13.1.1.7.12
                        ENTERPRISE      nwalarm-mib
                        VARIABLES       {
                                        serverName,trapTime,partitionNumber
                                        }
                        DESCRIPTION
                                "This mirrored partition is synchronized."
                        --#TYPE "Disk: Partition synchronized"
                        --#SUMMARY "Partition #%d on server %s synchronized."
 	                --#ARGUMENTS {2,0}
                        --#SEVERITY INFORMATIONAL
                        --#TIMEINDEX 1
                        --#HELP "nwalarm.hlp"
                        --#HELPTAG 74
			--#STATE OPERATIONAL

	            ::= 74

partitionsUnSync	TRAP-TYPE   --1.10.1.1.1.5.25 /1.13.1.1.7.13
                        ENTERPRISE      nwalarm-mib
                        VARIABLES       {
                                        serverName,trapTime,partitionNumber
                                        }
                        DESCRIPTION
                                "This logical partition is not synchronized."
                        --#TYPE "Disk: Partition not synchronized"
                        --#SUMMARY "Unsynchronized partition #%d "
			--#SUMMARY "on server %s"
 	                --#ARGUMENTS {2,0}
                        --#SEVERITY INFORMATIONAL
                        --#TIMEINDEX 1
                        --#HELP "nwalarm.hlp"
                        --#HELPTAG 75
			--#STATE DEGRADED

	            ::= 75


remirroringPart		TRAP-TYPE   --1.10.1.1.1.7.26 /1.13.1.1.7.11
                        ENTERPRISE      nwalarm-mib
                        VARIABLES       {
                                        serverName,trapTime,partitionNumber
                                        }
                        DESCRIPTION
                                "The system is remirroring this partition."
                        --#TYPE "Disk: Partition being remirrored"
                        --#SUMMARY "Remirroring partition #%d on server %s."
 	                --#ARGUMENTS {2,0}
                        --#SEVERITY CRITICAL
                        --#TIMEINDEX 1
                        --#HELP "nwalarm.hlp"
                        --#HELPTAG 76
			--#STATE OPERATIONAL

	            ::= 76

abortRemirrorPart	TRAP-TYPE   --1.10.1.1.1.5.27 /1.13.1.1.7.10
                        ENTERPRISE      nwalarm-mib
                        VARIABLES       {
                                        serverName,trapTime,partitionNumber
                                        }
                        DESCRIPTION
                                "System tried to remirror a partition to
				 another partition and failed."
                        --#TYPE "Disk: Partition remirror failed"
                        --#SUMMARY "Abort remirror of partition #%d on "
			--#SUMMARY "server %s."
 	                --#ARGUMENTS {2,0}
                        --#SEVERITY CRITICAL
                        --#TIMEINDEX 1
                        --#HELP "nwalarm.hlp"
                        --#HELPTAG 77
			--#STATE DEGRADED

	            ::= 77

mirrorInconsistencies	TRAP-TYPE   --1.10.1.1.1.5.28 /1.2.7.32
                        ENTERPRISE      nwalarm-mib
                        VARIABLES       {
                                        serverName,trapTime,partitionNumber
                                        }
                        DESCRIPTION
                                "This logical partition has certain
				inconsistencies."
                        --#TYPE "Disk: Partition inconsistent"
                        --#SUMMARY "Logical partition #%d has mirror "
			--#SUMMARY "inconsistencies on server %s."
 	                --#ARGUMENTS {2,0}
                        --#SEVERITY INFORMATIONAL
                        --#TIMEINDEX 1
                        --#HELP "nwalarm.hlp"
                        --#HELPTAG 78
			--#STATE DEGRADED
	            ::= 78

systemFileLockThresholdReached	TRAP-TYPE   --1.2.4.5.1/1.2.4.5.1
                        ENTERPRISE      nwalarm-mib
                        VARIABLES       {
                                        serverName,trapTime,
					numberOfFailedFileLockRequests
                                        }
                        DESCRIPTION
                                "System File lock threshold reached. New locks
                                 will fail."
                        --#TYPE "FileSys: Threshold, system file lock"
                        --#SUMMARY "System file lock threshold exceeded on "
			--#SUMMARY "server %s. %d file open or lock requests "
			--#SUMMARY "failed."
  	                --#ARGUMENTS {0,2}
                        --#SEVERITY MINOR
                        --#TIMEINDEX 1
                        --#HELP "nwalarm.hlp"
                        --#HELPTAG 79
			--#STATE DEGRADED

                    ::= 79

stationFileLockThresholdReached	TRAP-TYPE   --1.2.4.5.2/1.2.4.5.2
                        ENTERPRISE      nwalarm-mib
                        VARIABLES       {
                                        serverName,trapTime,stationNumber,
					numberOfFailedFileLockRequests
                                        }
                        DESCRIPTION
                                "Station file lock threshold reached."
                        --#TYPE "FileSys: Threshold, station file lock"
                        --#SUMMARY "Station %d file lock threshold exceeded "
			--#SUMMARY "on server %s. Total violations %d."
   	                --#ARGUMENTS {2,0,3}
                        --#SEVERITY INFORMATIONAL
                        --#TIMEINDEX 1
                        --#HELP "nwalarm.hlp"
                        --#HELPTAG 80
			--#STATE DEGRADED

                   ::= 80


systemRecordLockThresholdReached	TRAP-TYPE   --1.2.4.5.3/1.2.4.5.3
                        ENTERPRISE      nwalarm-mib
                        VARIABLES       {
                                        serverName,trapTime,
					numberOfFailedRecordLockRequests
                                        }
                        DESCRIPTION
                                "System record lock threshold reached."
                        --#TYPE "FileSys: Threshold, system record lock"
                        --#SUMMARY "System record lock threshold exceeded "
		        --#SUMMARY "on server %s. %d record lock requests "
    	                --#SUMMARY "failed."
			--#ARGUMENTS {0,2}
                        --#SEVERITY MINOR
                        --#TIMEINDEX 1
                        --#HELP "nwalarm.hlp"
                        --#HELPTAG 81
			--#STATE DEGRADED


                   ::= 81

stationRecordLockThresholdReached	TRAP-TYPE   --1.2.4.5.4/1.2.4.5.4
                        ENTERPRISE      nwalarm-mib
                        VARIABLES       {
                                        serverName,trapTime,stationNumber,
					numberOfFailedRecordLockRequests
                                        }
                        DESCRIPTION
                                "Station record lock threshold reached."
                        --#TYPE "FileSys: Threshold, station record lock"
                        --#SUMMARY "Station %d record lock threshold exceeded "
			--#SUMMARY "on server %s. Total violations %d."
     	                --#ARGUMENTS {2,0,3}
                        --#SEVERITY INFORMATIONAL
                        --#TIMEINDEX 1
                        --#HELP "nwalarm.hlp"
                        --#HELPTAG 82
			--#STATE DEGRADED

                   ::= 82

errorOpeningNetAcctData 	TRAP-TYPE   --1.2.7.24 /1.2.7.24
                        ENTERPRISE      nwalarm-mib
                        VARIABLES       {
                                        serverName,trapTime
                                        }
                        DESCRIPTION
                                "Cannot open file NET$ACCT.DAT to add audit
				 record."
                        --#TYPE "FileSys: NET$ACCT.DAT open err"
                        --#SUMMARY "Cannot open file NET$ACCT.DAT to add "
			--#SUMMARY "audit record on server %s."
 	                --#ARGUMENTS {0}
                        --#SEVERITY CRITICAL
                        --#TIMEINDEX 1
                        --#HELP "nwalarm.hlp"
                        --#HELPTAG 83
                        --#STATE  DEGRADED

                    ::= 83

ncpSearchLimitExecBySrvr	TRAP-TYPE   --1.4.7.5/1.2.1.2.7.3
                        ENTERPRISE      nwalarm-mib
                        VARIABLES       {
                                        serverName,trapTime,connectionNumber,
					userName
                                        }
                        DESCRIPTION
                                "A server requested an NCP directory search, and
				the limit for outstanding search was already
				 reached."
                        --#TYPE "NCP: Directory search limit exceeded, by server"
                        --#SUMMARY "Connection %d user %s exceeded "
			--#SUMMARY "outstanding NCP directory search limit on "
			--#SUMMARY "server %s."
 	                --#ARGUMENTS {2,3,0}
                        --#SEVERITY CRITICAL
                        --#TIMEINDEX 1
                        --#HELP "nwalarm.hlp"
                        --#HELPTAG 84
			--#STATE DEGRADED

                   ::= 84

ncpSearchLimitExecByStation	TRAP-TYPE   --1.4.7.2/1.4.7.2
                        ENTERPRISE      nwalarm-mib
                        VARIABLES       {
                                        serverName,trapTime
                                        }
                        DESCRIPTION
                                "A user requested an NCP directory search, and
				the limit for outstanding search was already
				 reached."
                        --#TYPE "NCP: Directory search limit exceeded, by user"
                        --#SUMMARY "Outstanding NCP directory search"
			--#SUMMARY "limit exceeded on server %s."
	                --#ARGUMENTS {0}
                        --#SEVERITY CRITICAL
                        --#TIMEINDEX 1
                        --#HELP "nwalarm.hlp"
                        --#HELPTAG 85
			--#STATE DEGRADED

                   ::= 85

insertMediaAck	 	TRAP-TYPE   --1.13.1.3.7.17
			ENTERPRISE      nwalarm-mib
			VARIABLES  {
                                      serverName,trapTime,deviceName
                                     }
			DESCRIPTION
                                "The insertion of a medium into a drive is
				acknowledged."
                        --#TYPE "MediaMgr: Media Insert ack'd"
                        --#SUMMARY  "Insert media request on device %s "
			--#SUMMARY  "acknowledged on server %s."
 	                --#ARGUMENTS {2,0}
                        --#SEVERITY INFORMATIONAL
                        --#TIMEINDEX 1
                        --#HELP "nwalarm.hlp"
                        --#HELPTAG 86
			--#STATE OPERATIONAL

	         ::= 86

insertMediaAborted 	TRAP-TYPE   --1.13.1.3.7.18
			ENTERPRISE      nwalarm-mib
			VARIABLES  {
                                      serverName,trapTime,deviceName
                                     }
			DESCRIPTION
                                "A previously requested insert media request
				is negated."
                        --#TYPE "MediaMgr: Media insert aborted"
                        --#SUMMARY  "Insert media request on device %s "
			--#SUMMARY  "aborted on server %s."
 	                --#ARGUMENTS {2,0}
                        --#SEVERITY INFORMATIONAL
                        --#TIMEINDEX 1
                        --#HELP "nwalarm.hlp"
                        --#HELPTAG 87
			--#STATE OPERATIONAL

	         ::= 87

remMediaAck	 	TRAP-TYPE   --1.13.1.3.7.19
			ENTERPRISE      nwalarm-mib
			VARIABLES  {
                                      serverName,trapTime,deviceName
                                    }
			DESCRIPTION
                                "The removal of a medium from a device is
				 acknowledged."
                        --#TYPE "MediaMgr: Media remove ack'd"
                        --#SUMMARY  "Remove media request on device %s "
			--#SUMMARY  "acknowledged on server %s."
 	                --#ARGUMENTS {2,0}
                        --#SEVERITY INFORMATIONAL
                        --#TIMEINDEX 1
                        --#HELP "nwalarm.hlp"
                        --#HELPTAG 88
			--#STATE OPERATIONAL

	         ::= 88

remMediaAborted 	TRAP-TYPE   --1.13.1.3.7.20
			ENTERPRISE      nwalarm-mib
			VARIABLES  {
                                      serverName,trapTime,deviceName
                                    }
			DESCRIPTION
                                "Previously issued remove media request
				aborted."
                        --#TYPE "MediaMgr: Media remove aborted"
                        --#SUMMARY  "Remove media request on device %s "
			--#SUMMARY  "aborted on server %s."
 	                --#ARGUMENTS {2,0}
                        --#SEVERITY INFORMATIONAL
                        --#TIMEINDEX 1
                        --#HELP "nwalarm.hlp"
                        --#HELPTAG 89
			--#STATE OPERATIONAL

	         ::= 89

insertDSMediaInto 	TRAP-TYPE   --1.13.1.3.7.31
			ENTERPRISE      nwalarm-mib
			VARIABLES  {
                                      serverName,trapTime,mediaLabel,deviceName
                                    }
			DESCRIPTION
                                "The media manager requires the double-sided
				 medium to be inserted into the device."
                        --#TYPE "MediaMgr: DS-media Insert req"
                        --#SUMMARY  "Insert double-sided medium %s into %s on "
			--#SUMMARY  "server %s. "
 	                --#ARGUMENTS {2,3,0}
                        --#SEVERITY INFORMATIONAL
                        --#TIMEINDEX 1
                        --#HELP "nwalarm.hlp"
                        --#HELPTAG 90
			--#STATE OPERATIONAL

	         ::= 90



removeMediaFrom 	TRAP-TYPE   --1.13.1.3.7.22
			ENTERPRISE      nwalarm-mib
			VARIABLES  {
                                      serverName,trapTime,deviceName
				}
			DESCRIPTION
                                "Media needs to be removed from device."
                        --#TYPE "MediaMgr: Media remove req"
                        --#SUMMARY  "Remove medium from %s on server %s."
 	                --#ARGUMENTS {2,0}
                        --#SEVERITY INFORMATIONAL
                        --#TIMEINDEX 1
                        --#HELP "nwalarm.hlp"
                        --#HELPTAG 91
			--#STATE OPERATIONAL

	         ::= 91

redirectBlk		TRAP-TYPE   --1.10.1.1.7.15/1.13.1.1.7.8
                        ENTERPRISE      nwalarm-mib
                        VARIABLES       {
                                        serverName,trapTime,blockNumber,
					blockNumber1,partitionNumber
                                        }
                        DESCRIPTION
                                "HotFix was able to redirect a block."
                        --#TYPE "Disk: Hotfix, block redirected"
                        --#SUMMARY "Redirected block number %x to %x on partition "
			--#SUMMARY "#%d on server %s."
 	                --#ARGUMENTS {2,3,4,0}
                        --#SEVERITY CRITICAL
                        --#TIMEINDEX 1
                        --#HELP "nwalarm.hlp"
                        --#HELPTAG 92
			--#STATE OPERATIONAL
                   ::= 92


couldNotRedirectBlk	TRAP-TYPE   --1.10.1.1.5.14 /1.13.1.1.7.9
                        ENTERPRISE      nwalarm-mib
                        VARIABLES       {
                                        serverName,trapTime,blockNumber,
					partitionNumber
                                        }
                        DESCRIPTION
                                "HotFix was unable to redirect a block."
                        --#TYPE "Disk: Hotfix, redirect failed"
                        --#SUMMARY "Could not redirect block %x on partition "
			--#SUMMARY "#%d on server %s."
 	                --#ARGUMENTS {2,3,0}
                        --#SEVERITY INFORMATIONAL
                        --#TIMEINDEX 1
                        --#HELP "nwalarm.hlp"
                        --#HELPTAG 93
			--#STATE DEGRADED

                   ::= 93

outOfHotFixBlks		TRAP-TYPE   --1.10.1.1.1.7.8/1.2.7.30
                        ENTERPRISE      nwalarm-mib
                        VARIABLES       {
                                        serverName,trapTime
                                        }
                        DESCRIPTION
                                "The redirection area set aside on a partition
				is exhausted."
                        --#TYPE "Disk: Hotfix, out of redirection blocks"
                        --#SUMMARY "Warning: No more redirection "
			--#SUMMARY "blocks on server %s."
 	                --#ARGUMENTS {0}
                        --#SEVERITY INFORMATIONAL
                        --#TIMEINDEX 1
                        --#HELP "nwalarm.hlp"
                        --#HELPTAG 94
			--#STATE DEGRADED

                   ::= 94


fewRedirectionBlks	TRAP-TYPE   --1.10.1.1.1.5.9 /1.2.7.31
                        ENTERPRISE      nwalarm-mib
                        VARIABLES       {
                                        serverName,trapTime,numberOfBlocks
                                        }
                        DESCRIPTION
                                "There are only few disk blocks available
				 for redirection."
                        --#TYPE "Disk: Hotfix, low on redirection blocks"
                        --#SUMMARY "Warning: Only %d redirection "
			--#SUMMARY "blocks left on server %s."
 	                --#ARGUMENTS {2,0}
                        --#SEVERITY INFORMATIONAL
                        --#TIMEINDEX 1
                        --#HELP "nwalarm.hlp"
                        --#HELPTAG 95
			--#STATE DEGRADED

	            ::= 95

redirectInconsistNoFix	TRAP-TYPE   --1.10.1.1.7.7
                        ENTERPRISE      nwalarm-mib
                        VARIABLES       {
                                        serverName,trapTime,partitionNumber
                                        }
                        DESCRIPTION
                                "The inconsistencies in the redirection tables
				found in the hotfix area could not be fixed
				by the media manager."
                        --#TYPE "Disk: Hotfix, inconsistencies not fixed"
                        --#SUMMARY "Redirection table inconsistencies on "
			--#SUMMARY "partition %d cannot be corrected on "
			--#SUMMARY "server %s."
 	                --#ARGUMENTS {2,0}
                        --#SEVERITY CRITICAL
                        --#TIMEINDEX 1
                        --#HELP "nwalarm.hlp"
                        --#HELPTAG 96
			--#STATE DEGRADED

                   ::= 96


redirectInconsistFix	TRAP-TYPE   --1.10.1.1.7.9
                        ENTERPRISE      nwalarm-mib
                        VARIABLES       {
                                        serverName,trapTime,partitionNumber
                                        }
                        DESCRIPTION
                                "The inconsistencies in the redirection tables
				found in the hotfix area were fixed by the
				media manager."
                        --#TYPE "Disk: Hotfix, inconsistencies fixed"
                        --#SUMMARY "Redirection table inconsistencies on "
			--#SUMMARY "partition %d were corrected on server %s."
 	                --#ARGUMENTS {2,0}
                        --#SEVERITY CRITICAL
                        --#TIMEINDEX 1
                        --#HELP "nwalarm.hlp"
                        --#HELPTAG 97
			--#STATE OPERATIONAL
                   ::= 97

invalidResourceTagPassed	TRAP-TYPE   --1.1.5.7.1/1.1.5.7.1
                        ENTERPRISE      nwalarm-mib
                        VARIABLES       {
                                        serverName,trapTime
                                        }
                        DESCRIPTION
                                "A loaded NLM tried to register hardware
				options with an invalid resource tag."
                        --#TYPE "OS: Bad resrc tag passed to RegisterHWOptions"
                        --#SUMMARY "Function RegisterHardwareOptions called "
			--#SUMMARY "with an invalid resource tag on server %s."
	                --#ARGUMENTS {0}
                        --#SEVERITY CRITICAL
                        --#TIMEINDEX 1
                        --#HELP "nwalarm.hlp"
                        --#HELPTAG 98
                        --#STATE  DEGRADED
                       ::= 98

checkAddHardware	TRAP-TYPE   --1.1.5.7.2/1.1.5.7.2
                        ENTERPRISE      nwalarm-mib
                        VARIABLES       {
                                        serverName,trapTime
                                        }
                        DESCRIPTION
                                "The NetWare OS tried to allocate memory for
				a system API and failed."
                        --#TYPE "OS: Resource tag allocation failure"
                        --#SUMMARY "Function CheckAndAddHardware could not "
			--#SUMMARY "allocate a resource tag on server %s."
	                --#ARGUMENTS {0}
                        --#SEVERITY CRITICAL
                        --#TIMEINDEX 1
                        --#HELP "nwalarm.hlp"
                        --#HELPTAG 99
                        --#STATE  DEGRADED

                       ::= 99

removeHardwareOptions	TRAP-TYPE   --1.1.5.7.3	/1.1.5.7.3
                        ENTERPRISE      nwalarm-mib
                        VARIABLES       {
                                        serverName,trapTime
                                        }
                        DESCRIPTION
                                "An executing NLM called the OS function
				RemoveHardwareOptions with an invalid pointer."
                        --#TYPE "OS: RemoveHardwareOptions failed "
			--#SUMMARY "OS function RemoveHardwareOptions called "
			--#SUMMARY "with an invalid pointer on file server %s."
	                --#ARGUMENTS {0}
                        --#SEVERITY CRITICAL
                        --#TIMEINDEX 1
                        --#HELP "nwalarm.hlp"
                        --#HELPTAG 100
                        --#STATE  DEGRADED

                    ::= 100


errUnloadKilledNlm	TRAP-TYPE   --1.1.3.7.4	/1.1.3.7.4
                        ENTERPRISE      nwalarm-mib
                        VARIABLES       {
                                        serverName,trapTime
                                        }
                        DESCRIPTION
                                "An NLM being unloaded has exported
				 variables that are in use
				 by other NLMs."
                        --#TYPE "OS: NLM unloaded with exported vars."
                        --#SUMMARY "Error unloading killed loadable module "
			--#SUMMARY "on server %s"
                        --#ARGUMENTS {0}
                        --#SEVERITY CRITICAL
                        --#TIMEINDEX 1
                        --#HELP "nwalarm.hlp"
                        --#HELPTAG 101
                        --#STATE  DEGRADED

                        ::= 101

invldRrceTagPsedToCreatePrss TRAP-TYPE   --1.1.5.1.7.3 /1.1.5.1.7.3
                        ENTERPRISE      nwalarm-mib
                        VARIABLES       {
                                        serverName,trapTime
                                        }
                        DESCRIPTION
                                "The system tried to start a new NLM or create
				 a process for an active NLM, but the NLM
				 did not allocate a resource tag or used an
				 invalid resource tag."
                        --#TYPE "OS: Bad resrc tag passed to CreateProcess"
			--#SUMMARY "OS function CreateProcess called with "
			--#SUMMARY "an invalid resource tag on file server %s."
 	                --#ARGUMENTS {0}
                        --#SEVERITY CRITICAL
                        --#TIMEINDEX 1
                        --#HELP "nwalarm.hlp"
                        --#HELPTAG 102
                        --#STATE  DEGRADED
                    ::= 102

createPrssReqtdStackTooSmall TRAP-TYPE   --1.1.5.1.7.2/1.1.5.1.7.2
                        ENTERPRISE      nwalarm-mib
                        VARIABLES       {
                                        serverName,trapTime
                                        }
                        DESCRIPTION
                                "The system tried to load an NLM that allocated
				insufficient stack for itself."
                        --#TYPE "OS: CreateProcess err, stack size too small"
                        --#SUMMARY "Function CreateProcess called with "
			--#SUMMARY "too small a stack size on file server %s."
	                --#ARGUMENTS {0}
                        --#SEVERITY CRITICAL
                        --#TIMEINDEX 1
                        --#HELP "nwalarm.hlp"
                        --#HELPTAG 103
                        --#STATE  DEGRADED

                    ::= 103

createPrssUnableToAllocPrssCntlBlk TRAP-TYPE   --1.1.5.1.7.1/1.1.5.1.7.1
                        ENTERPRISE      nwalarm-mib
                        VARIABLES       {
                                        serverName,trapTime
                                        }
                        DESCRIPTION
                                "The system tried to start a new NLM but there
				was not enough memory."
                        --#TYPE "OS: CreateProcess err, no memory"
                        --#SUMMARY "Function CreateProcess could not allocate "
			--#SUMMARY "a Process Control Block on server %s."
 	                --#ARGUMENTS {0}
                        --#SEVERITY CRITICAL
                        --#TIMEINDEX 1
                        --#HELP "nwalarm.hlp"
                        --#HELPTAG 104
                        --#STATE  DEGRADED

                    ::= 104


filePreservationErrorDuringErase 	TRAP-TYPE   --1.2.7.26/1.2.7.26
                        ENTERPRISE      nwalarm-mib
                        VARIABLES       {
                                        serverName,trapTime,volumeName,
					pathFileName
                                        }
                        DESCRIPTION
                                "An error prevented the preservation of a file
				during file deletion. The file is not
				salvageable."
                        --#TYPE "FileSys: File preservation err"
                        --#SUMMARY "Error prevented preservation of file "
			--#SUMMARY  "%s:%s during file deletion on file "
			--#SUMMARY "server %s."
 	                --#ARGUMENTS {2,3,0}
                        --#SEVERITY MINOR
                        --#TIMEINDEX 1
                        --#HELP "nwalarm.hlp"
                        --#HELPTAG 105
                        --#STATE  DEGRADED

                    ::= 105

filePreservationErrorInsuffSpace 	TRAP-TYPE   --1.2.7.27/1.2.7.27
                        ENTERPRISE      nwalarm-mib
                        VARIABLES       {
                                        serverName,trapTime,volumeName,
					pathFileName
                                        }
                        DESCRIPTION
                                "Insufficient directory table space or memory
				 available during file deletion. The file is
				 not salvageable."
                        --#TYPE "FileSys: File not salvageable, no dir space"
                        --#SUMMARY "Insufficient directory space (or memory) "
			--#SUMMARY "to preserve %s:%s during file deletion on "
			--#SUMMARY "file server %s."
		        --#ARGUMENTS {2,3,0}
                        --#SEVERITY MINOR
                        --#TIMEINDEX 1
                        --#HELP "nwalarm.hlp"
                        --#HELPTAG 106
                        --#STATE  DEGRADED

                    ::= 106


mlidResetLanBd		TRAP-TYPE   --1.9.2.1.3.7.6
                        ENTERPRISE      nwalarm-mib
                        VARIABLES       {
                                        serverName,trapTime,networkAddress,
					macAddress,socketNumber
                                        }
                        DESCRIPTION
                                "A bind command issued to an IPX LAN driver
				 with a wrong network number caused the MLID
				 to reset the LAN board."
                        --#TYPE "Network: MLID reset LAN board"
                        --#SUMMARY "%x:%x:%x has requested LAN board reset "
			--#SUMMARY "on file server %s."
 	                --#ARGUMENTS {2,3,4,0}
                        --#SEVERITY INFORMATIONAL
                        --#TIMEINDEX 1
                        --#HELP "nwalarm.hlp"
                        --#HELPTAG 107
                        --#STATE  OPERATIONAL

                   ::= 107

requestedRtrReset		TRAP-TYPE   --1.9.2.1.3.7.5
                        ENTERPRISE      nwalarm-mib
                        VARIABLES       {
                                        serverName,trapTime,networkAddress,
					macAddress,socketNumber
                                        }
                        DESCRIPTION
                                "A workstation issued a router reset command
				to a server."
                        --#TYPE "Router: Reset"
                        --#SUMMARY "%x:%x:%x has requested router reset "
			--#SUMMARY "on file server %s."
 	                --#ARGUMENTS {2,3,4,0}
                        --#SEVERITY INFORMATIONAL
                        --#TIMEINDEX 1
                        --#HELP "nwalarm.hlp"
                        --#HELPTAG 108
                        --#STATE  OPERATIONAL
                   ::= 108

volContainstheWrongDOSType	TRAP-TYPE   --1.6.7.4
                        ENTERPRISE      nwalarm-mib
                        VARIABLES       {
                                        serverName,trapTime,volumeName,
					dosType,dosType1
                                        }
                        DESCRIPTION
                                "The volume has a DOS TYPE different from
				that for which the server was configured."
                        --#TYPE "FileSys: Vol DOS type mismatch"
                        --#SUMMARY "Volume %s DOS type (%d) does not match "
			--#SUMMARY "the file server DOS type (%d) on "
			--#SUMMARY " file server %s."
 	                --#ARGUMENTS {2,3,4,0}
                        --#SEVERITY MINOR
                        --#TIMEINDEX 1
                        --#HELP "nwalarm.hlp"
                        --#HELPTAG 109
                        --#STATE  DEGRADED
                   ::= 109

originalNameSpaceNotFound 	TRAP-TYPE   --1.2.5.25/1.2.5.25
                        ENTERPRISE      nwalarm-mib
                        VARIABLES       {
                                        serverName,trapTime
                                        }
                        DESCRIPTION
                                "Function GetOriginalNameSpace could not
				find a name space. DOS name space was
				assumed."
                        --#TYPE "FileSys: Name space not found"
                        --#SUMMARY "GetOriginalNameSpace could not "
			--#SUMMARY "find the originating name space on"
			--#SUMMARY " %s. DOS name space assumed. Run VRepair to fix this"
 	                --#ARGUMENTS {0}
                        --#SEVERITY MAJOR
                        --#TIMEINDEX 1
                        --#HELP "nwalarm.hlp"
                        --#HELPTAG 110
                        --#STATE  DEGRADED

                    ::= 110

rdTimeDataMigratorModuleChanged	TRAP-TYPE   --1.2.8.7.5
                        ENTERPRISE      nwalarm-mib
                        VARIABLES       {
                                        serverName,trapTime
                                        }
                        DESCRIPTION
                                "A real-time data migrator default
				 support module	was changed by the
				application."

                        --#TYPE "FileSys: Migration support module changed"
                        --#SUMMARY "Real-time data migrator default read/write "
			--#SUMMARY "support module changed on server "
			--#SUMMARY "%s."
 	                --#ARGUMENTS {0}
                        --#SEVERITY INFORMATIONAL
                        --#TIMEINDEX 1
                        --#HELP "nwalarm.hlp"
                        --#HELPTAG 111
                        --#STATE  DEGRADED
                   ::= 111


errCreateOpenTTSLogFile	TRAP-TYPE   --1.2.6.5.1/1.2.2.1.5.1
                        ENTERPRISE      nwalarm-mib
                        VARIABLES       {
                                        serverName,trapTime
                                        }
                        DESCRIPTION
                                "The server could not open or create the
				TTS$LOG file. The volume may be out of disk
				space or the hard disk could have failed."

                        --#TYPE "FileSys: TTS$LOG.ERR create err"
                        --#SUMMARY "Error opening or creating TTS$LOG.ERR "
			--#SUMMARY "file on server %s."
	                --#ARGUMENTS {0}
                        --#SEVERITY INFORMATIONAL
                        --#TIMEINDEX 1
                        --#HELP "nwalarm.hlp"
                        --#HELPTAG 112
                        --#STATE  DEGRADED

                   ::= 112

errWriteOpenTTSLogFile	TRAP-TYPE   --1.2.6.5.2	/1.2.2.1.5.2
                        ENTERPRISE      nwalarm-mib
                        VARIABLES       {
                                        serverName,trapTime
                                        }
                        DESCRIPTION
                                "The server could not write to a
				TTS$LOG file. The volume may be out of disk
				space or the hard disk could have failed."

                        --#TYPE "FileSys: TTS$LOG.ERR write err"
                        --#SUMMARY "Error writing to TTS$LOG.ERR file on "
			--#SUMMARY "server %s."
	                --#ARGUMENTS {0}
                        --#SEVERITY INFORMATIONAL
                        --#TIMEINDEX 1
                        --#HELP "nwalarm.hlp"
                        --#HELPTAG 113
                        --#STATE  DEGRADED

                   ::= 113

ttsDownbyVolDismount	TRAP-TYPE   --1.2.6.7.3	/1.2.2.1.7.3
                        ENTERPRISE      nwalarm-mib
                        VARIABLES       {
                                        serverName,trapTime,volumeName
                                        }
                        DESCRIPTION
                                "Since the SYS volume was dismounted TTS is
				no longer available."
                        --#TYPE "TTS: Not available"
                        --#SUMMARY "%s TTS shut down because backout volume "
			--#SUMMARY "%s was dismounted."
	                --#ARGUMENTS {0,2}
                        --#SEVERITY CRITICAL
                        --#TIMEINDEX 1
                        --#HELP "nwalarm.hlp"
                        --#HELPTAG 114
                        --#STATE  DEGRADED

                   ::= 114

disableTTSbyUser	TRAP-TYPE   --1.2.6.7.4/1.2.2.1.7.4
                        ENTERPRISE      nwalarm-mib
                        VARIABLES       {
                                        serverName,trapTime,userName,
					stationNumber
                                        }
                        DESCRIPTION
                                "A disable TTS command was issued from a
				workstation."

                        --#TYPE "TTS: Disabled, by user"
                        --#SUMMARY "TTS disabled on server %s "
			--#SUMMARY "by user %s on station %d."
	                --#ARGUMENTS {0,2,3}
                        --#SEVERITY INFORMATIONAL
                        --#TIMEINDEX 1
                        --#HELP "nwalarm.hlp"
                        --#HELPTAG 115
                        --#STATE  DEGRADED

                   ::= 115

ttsDisabledByOperator	TRAP-TYPE   --1.2.6.7.14
                        ENTERPRISE      nwalarm-mib
                        VARIABLES       {
                                        serverName,trapTime
                                        }
                        DESCRIPTION
                                "TTS disabled by operator."
                        --#TYPE "TTS: Disabled, by server"
                        --#SUMMARY "TTS disabled by operator on server %s."
	                --#ARGUMENTS {0}
                        --#SEVERITY MINOR
                        --#TIMEINDEX 1
                        --#HELP "nwalarm.hlp"
                        --#HELPTAG 116
                        --#STATE  DEGRADED

                   ::= 116

ttsDisErrReadTTSduringBackout	TRAP-TYPE   --1.2.6.7.15
                        ENTERPRISE      nwalarm-mib
                        VARIABLES       {
                                        serverName,trapTime
                                        }
                        DESCRIPTION
                                "TTS disabled due to error reading
				backout file."
                        --#TYPE "TTS: Disabled, reading backout file"
                        --#SUMMARY "TTS disabled on server %s due to error "
			--#SUMMARY  "reading backout file. "
	                --#ARGUMENTS {0}
                        --#SEVERITY CRITICAL
                        --#TIMEINDEX 1
                        --#HELP "nwalarm.hlp"
                        --#HELPTAG 117
                        --#STATE  DEGRADED
                   ::= 117

ttsDisErrWritingTTSduringBackout	TRAP-TYPE   --1.2.6.7.5
                        ENTERPRISE      nwalarm-mib
                        VARIABLES       {
                                        serverName,trapTime
                                        }
                        DESCRIPTION
                                "TTS was disabled because there was an error
				writing to a file during transaction backout."
                        --#TYPE "TTS: Disabled, writing backout file"
                        --#SUMMARY "TTS disabled on server %s because of error "
			--#SUMMARY "writing to file during transaction backout."
	                --#ARGUMENTS {0}
                        --#SEVERITY CRITICAL
                        --#TIMEINDEX 1
                        --#HELP "nwalarm.hlp"
                        --#HELPTAG 118
                        --#STATE  DEGRADED

                   ::= 118


ttsDisErrTooManyDefInfo	TRAP-TYPE   --1.2.6.7.16
                        ENTERPRISE      nwalarm-mib
                        VARIABLES       {
                                        serverName,trapTime
                                        }
                        DESCRIPTION
                                "TTS was disabled because of too many defined
				 volumes."
		         --#TYPE "TTS: Disabled, too many volumes"
                        --#SUMMARY "TTS disabled on server %s because of too "
			--#SUMMARY "many defined volumes."
	                --#ARGUMENTS {0}
                        --#SEVERITY CRITICAL
                        --#TIMEINDEX 1
                        --#HELP "nwalarm.hlp"
                        --#HELPTAG 119
                        --#STATE  DEGRADED

                   ::= 119

ttsDisErrWritingVolDefInfo	TRAP-TYPE   --1.2.6.7.11
                        ENTERPRISE      nwalarm-mib
                        VARIABLES       {
                                        serverName,trapTime
                                        }
                        DESCRIPTION
                                "TTS was disabled due to an error writing volume
				 definition information."
		         --#TYPE "TTS: Disabled, volume information"
                        --#SUMMARY "TTS disabled on server %s because of error "
			--#SUMMARY "writing volume definition information."
	                --#ARGUMENTS {0}
                        --#SEVERITY CRITICAL
                        --#TIMEINDEX 1
                        --#HELP "nwalarm.hlp"
                        --#HELPTAG 120
                        --#STATE  DEGRADED

                   ::= 120

ttsDisErrRdBlkFlRecGen	TRAP-TYPE   --1.2.6.7.17
                        ENTERPRISE      nwalarm-mib
                        VARIABLES       {
                                        serverName,trapTime
                                        }
                        DESCRIPTION
                                "TTS was disabled due to error reading backout
				file during record generation"
		         --#TYPE "TTS: Disabled, record generation"
                        --#SUMMARY "TTS disabled on server %s because of error "
			--#SUMMARY "reading backout file during record "
	                --#SUMMARY "generation."
			--#ARGUMENTS {0}
                        --#SEVERITY CRITICAL
                        --#TIMEINDEX 1
                        --#HELP "nwalarm.hlp"
                        --#HELPTAG 121
                        --#STATE  DEGRADED

                   ::= 121

ttsDisGrowMemTables	TRAP-TYPE   --1.2.6.7.18
                        ENTERPRISE      nwalarm-mib
                        VARIABLES       {
                                        serverName,trapTime
                                        }
                        DESCRIPTION
                                "TTS was disabled because TTS tables were
				 getting too big."
		         --#TYPE "TTS: Disabled, growing TTS tables"
                        --#SUMMARY "TTS disabled on server %s because of error "
			--#SUMMARY "growing TTS memory tables."
	                --#ARGUMENTS {0}
                        --#SEVERITY CRITICAL
                        --#TIMEINDEX 1
                        --#HELP "nwalarm.hlp"
                        --#HELPTAG 122
                        --#STATE  DEGRADED

                   ::= 122

ttsDisErrAllDiskSpace	TRAP-TYPE   --1.2.6.7.19
                        ENTERPRISE      nwalarm-mib
                        VARIABLES       {
                                        serverName,trapTime
                                        }
                        DESCRIPTION
                                "TTS was disabled because of an error allocating
				 more disk space during backout."
		         --#TYPE "TTS: Disabled, no disk space"
                        --#SUMMARY "TTS disabled on server %s because of "
			--#SUMMARY "error allocating more disk space for the "
			--#SUMMARY "backout file."
	                --#ARGUMENTS {0}
                        --#SEVERITY CRITICAL
                        --#TIMEINDEX 1
                        --#HELP "nwalarm.hlp"
                        --#HELPTAG 123
                        --#STATE  DEGRADED

                   ::= 123

ttsDisDirErrOnBkFile	TRAP-TYPE   --1.2.6.7.20
                        ENTERPRISE      nwalarm-mib
                        VARIABLES       {
                                        serverName,trapTime
                                        }
                        DESCRIPTION
                                "TTS was disabled because of a directory error
				 on TTS backout file."
		         --#TYPE "TTS: Disabled, directory error"
                        --#SUMMARY "TTS disabled on server %s because of "
			--#SUMMARY "directory error on TTS backout file."
	                --#ARGUMENTS {0}
                        --#SEVERITY CRITICAL
                        --#TIMEINDEX 1
                        --#HELP "nwalarm.hlp"
                        --#HELPTAG 124
                        --#STATE  DEGRADED

                   ::= 124

enableTTSByUser		TRAP-TYPE   --1.2.6.7.6	/1.2.2.1.7.6
                        ENTERPRISE      nwalarm-mib
                        VARIABLES       {
                                        serverName,trapTime,userName,
					stationNumber
                                        }
                        DESCRIPTION
                                "TTS was enabled from a workstation."
                        --#TYPE "TTS: Enabled"
                        --#SUMMARY "TTS on server %s enabled by user %s on "
			--#SUMMARY "station %d."
 	                --#ARGUMENTS {0,2,3}
                        --#SEVERITY INFORMATIONAL
                        --#TIMEINDEX 1
                        --#HELP "nwalarm.hlp"
                        --#HELPTAG 125
                        --#STATE  OPERATIONAL

                   ::= 125


transactionAbortedForStation		TRAP-TYPE   --1.2.6.5.7/1.2.2.1.7.7
                        ENTERPRISE      nwalarm-mib
                        VARIABLES       {
                                        serverName,trapTime,stationNumber,
					taskNumber
                                        }
                        DESCRIPTION
                                "A transaction was not backed out due to
				a clear station command."
                        --#TYPE "TTS: Transaction aborted"
                        --#SUMMARY "Transaction aborted for station %d "
			--#SUMMARY "task %d on server %s."
	                --#ARGUMENTS {2,3,0}
                        --#SEVERITY INFORMATIONAL
                        --#TIMEINDEX 1
                        --#HELP "nwalarm.hlp"
                        --#HELPTAG 126
                        --#STATE  OPERATIONAL

                   ::= 126

ttsLimitExceeded	TRAP-TYPE   --1.2.6.7.8/1.2.2.1.7.8
                        ENTERPRISE      nwalarm-mib
                        VARIABLES       {
                                        serverName,trapTime,numberOfTransactions
                                        }
                        DESCRIPTION
                                "TTS has exceeded the maximum number of
				transactions."
                        --#TYPE "TTS: Hit active transaction limit"
                        --#SUMMARY "TTS exceeded max. "
			--#SUMMARY "active transactions limit on server "
			--#SUMMARY " %s. %d transactions delayed."
	                --#ARGUMENTS {0,2}
                        --#SEVERITY MINOR
                        --#TIMEINDEX 1
                        --#HELP "nwalarm.hlp"
                        --#HELPTAG 127
                        --#STATE  DEGRADED

                   ::= 127

ttsNoMemForExpandingTxNodeTables	TRAP-TYPE   --1.2.6.7.9/1.2.2.1.7.9
                        ENTERPRISE      nwalarm-mib
                        VARIABLES       {
                                        serverName,trapTime,
					numberOfFailedMemoryAllocAttempts
                                        }
                        DESCRIPTION
                                "TTS ran out of memory expanding transaction
				node tables."
                        --#TYPE "TTS: Ran out of memory"
                        --#SUMMARY "TTS ran out of memory expanding "
			--#SUMMARY "transaction node tables on server %s. "
			--#SUMMARY "%d memory allocation requests failed."
	                --#ARGUMENTS {0,2}
                        --#SEVERITY MINOR
                        --#TIMEINDEX 1
                        --#HELP "nwalarm.hlp"
                        --#HELPTAG 128
                        --#STATE  DEGRADED

                   ::= 128

auditEvent              TRAP-TYPE --1.7.11
                        ENTERPRISE      nwalarm-mib
                        VARIABLES       {
                                        serverName,trapTime,auditEventNumber,
					volumeNumber
                                        }
                        DESCRIPTION
                                "An audit request was made with an invalid
				volume number."
                        --#TYPE "Audit: Invalid req, volume #"
                        --#SUMMARY "Audit error on server %s. "
			--#SUMMARY "Audit event number = %d, invalid volume "
			--#SUMMARY "number = %d."
                        --#ARGUMENTS {0,2,3}
                        --#SEVERITY CRITICAL
                        --#TIMEINDEX 1
                        --#HELP "nwalarm.hlp"
                        --#HELPTAG 129
                        --#STATE  DEGRADED

                        ::= 129


auditAlertThresholdOverFlow    TRAP-TYPE  --1.5.23(msg.1258)
                        ENTERPRISE      nwalarm-mib
                        VARIABLES       {
                                        serverName,trapTime,volumeName
                                        }
                        DESCRIPTION
                                "There was an audit threshold overflow."

                        --#TYPE "Audit: Threshold overflow"
                        --#SUMMARY "Audit file threshold overflow on "
			--#SUMMARY "volume %s\%s:."
                        --#ARGUMENTS {0,2}
                        --#SEVERITY CRITICAL
                        --#TIMEINDEX 1
                        --#HELP "nwalarm.hlp"
                        --#HELPTAG 130
                        --#STATE  DEGRADED

                        ::= 130

auditAlertInvalidConfigFile    TRAP-TYPE  --1.5.14(msg.845)
                        ENTERPRISE      nwalarm-mib
                        VARIABLES       {
                                        serverName,trapTime,volumeName
                                        }
                        DESCRIPTION
                                "Auditing disabled -- invalid configuration
				file."
                        --#TYPE "Audit: Disabled, invalid config file"
                        --#SUMMARY "Auditing disabled, cannot open valid audit "
			--#SUMMARY "configuration file for volume %s\%s:."
                        --#ARGUMENTS {0,2}
                        --#SEVERITY CRITICAL
                        --#TIMEINDEX 1
                        --#HELP "nwalarm.hlp"
                        --#HELPTAG 131
                        --#STATE  DEGRADED

                        ::= 131

auditAlertNoMemory	TRAP-TYPE  --1.5.20(msg.1249)
                        ENTERPRISE      nwalarm-mib
                        VARIABLES       {
                                        serverName,trapTime,volumeName
                                        }
                        DESCRIPTION
                                "Memory for auditing cannot be allocated."

                        --#TYPE "Audit: Out of memory"
                        --#SUMMARY "Memory for auditing cannot be allocated. "
			--#SUMMARY "Volume %s\%s: is being dismounted."
                        --#ARGUMENTS {0,2}
                        --#SEVERITY CRITICAL
                        --#TIMEINDEX 1
                        --#HELP "nwalarm.hlp"
                        --#HELPTAG 132
                        --#STATE  DEGRADED

                        ::= 132

auditFileWriteError	TRAP-TYPE  --1.5.21(msg.1250)
                        ENTERPRISE      nwalarm-mib
                        VARIABLES       {
                                        serverName,trapTime,volumeName
                                        }
                        DESCRIPTION
                                "Audit-file write error."

                        --#TYPE "Audit: File write error"
                        --#SUMMARY "Audit file write error, volume %s\%s:."
                        --#ARGUMENTS {0,2}
                        --#SEVERITY CRITICAL
                        --#TIMEINDEX 1
                        --#HELP "nwalarm.hlp"
                        --#HELPTAG 133
                        --#STATE  DEGRADED

                        ::= 133

--the following trap covers two messages as they happen to be the same
auditFileFull		TRAP-TYPE  --1.5.22(msg.1251/1259)
                        ENTERPRISE      nwalarm-mib
                        VARIABLES       {
                                        serverName,trapTime,volumeName
                                        }
                        DESCRIPTION
                                "Audit file full."

                        --#TYPE "Audit: File full"
                        --#SUMMARY "Audit file full on volume %s\%s:."
                        --#ARGUMENTS {0,2}
                        --#SEVERITY CRITICAL
                        --#TIMEINDEX 1
                        --#HELP "nwalarm.hlp"
                        --#HELPTAG 134
                        --#STATE  DEGRADED

                        ::= 134

invalidConnTypetoAllocConn	TRAP-TYPE   --1.5.7.9/1.2.1.7.18
                        ENTERPRISE      nwalarm-mib
                        VARIABLES       {
                                        serverName,trapTime
                                        }
                        DESCRIPTION
                                "An executing NLM tried to allocate a connection
				number but an invalid connection type was
				 passed as a parameter."
                        --#TYPE "OS: Invalid connection type"
                        --#SUMMARY "Function AllocateConnectionNumber called "
			--#SUMMARY "with invalid connection type on server "
  	                --#SUMMARY "%s."
			--#ARGUMENTS {0}
                        --#SEVERITY CRITICAL
                        --#TIMEINDEX 1
                        --#HELP "nwalarm.hlp"
                        --#HELPTAG 135
                        --#STATE  DEGRADED

                   ::= 135

invalidRsrcTagPassedtoAllocConn	TRAP-TYPE   --1.5.7.10 /1.2.1.7.19
                        ENTERPRISE      nwalarm-mib
                        VARIABLES       {
                                        serverName,trapTime
                                        }
                        DESCRIPTION
                                "An executing NLM tried to allocate a connection
				number but an invalid resource tag was passed
				as a parameter."
                        --#TYPE "OS: Bad resrc tag passed to AllocConnNumber"
                        --#SUMMARY "Function AllocateConnectionNumber called "
			--#SUMMARY "with invalid resource tag on server %s."
  	                --#ARGUMENTS {0}
                        --#SEVERITY CRITICAL
                        --#TIMEINDEX 1
                        --#HELP "nwalarm.hlp"
                        --#HELPTAG 136
                        --#STATE  DEGRADED

                   ::= 136

outOfServerConn		TRAP-TYPE   --1.5.7.11/1.2.1.7.20
                        ENTERPRISE      nwalarm-mib
                        VARIABLES       {
                                        serverName,trapTime
                                        }
                        DESCRIPTION
                                "A request to allocate a connection number for a
				workstation could not be granted because the
				maximum number of connections had
				been allocated."

                        --#TYPE "System: Server out of connections"
                        --#SUMMARY "Server %s out of connections. User "
			--#SUMMARY "connect request failed."
  	                --#ARGUMENTS {0}
                        --#SEVERITY CRITICAL
                        --#TIMEINDEX 1
                        --#HELP "nwalarm.hlp"
                        --#HELPTAG 137
                        --#STATE  NONOPERATIONAL

                   ::= 137


connTerminated5MinNotice	TRAP-TYPE   --1.5.7.17/1.2.1.7.21
                        ENTERPRISE      nwalarm-mib
                        VARIABLES       {
                                        serverName,trapTime,userName,
					stationNumber
                                        }
                        DESCRIPTION
                                "Server watchdog logged out the connection
				since the user did not log in for five minutes."

                        --#TYPE "Connection: Cleared, 5-min notice"
                        --#SUMMARY "User %s at station %d connection "
			--#SUMMARY "terminated on server %s. User did not "
		        --#SUMMARY "logout within five min. after security "
			--#SUMMARY "watchdog notice."
  	                --#ARGUMENTS {2,3,0}
                        --#SEVERITY CRITICAL
                        --#TIMEINDEX 1
                        --#HELP "nwalarm.hlp"
                        --#HELPTAG 138
                        --#STATE  OPERATIONAL
                   ::= 138

usrAcctDisabledByAUsr	TRAP-TYPE   --1.5.7.16/1.2.1.7.15
                        ENTERPRISE      nwalarm-mib
                        VARIABLES       {
                                        serverName,trapTime,accountName,
					userName,stationNumber,
					numberOfConnections
                                        }
                        DESCRIPTION
                                "A user account was disabled by another user.
				 The user whose account was disabled was logged
				 in at the time."
                        --#TYPE "User: Account disabled"
                        --#SUMMARY "User account %s on server %s disabled by "
			--#SUMMARY "user %s on station %d.  %d active "
			--#SUMMARY "connections have been requested to log out."
  	                --#ARGUMENTS {2,0,3,4,5}
                        --#SEVERITY CRITICAL
                        --#TIMEINDEX 1
                        --#HELP "nwalarm.hlp"
                        --#HELPTAG 139
			--#STATE  OPERATIONAL

                   ::= 139

useOfUnEncryptedPwd	TRAP-TYPE   --1.5.5.3/1.2.1.5.24
                        ENTERPRISE      nwalarm-mib
                        VARIABLES       {
                                        serverName,trapTime,stationNumber
                                        }
                        DESCRIPTION
                                "An application or utility tried to log in
				or change a password using an unencrypted
				password.The server accepts only encrypted
				passwords."
                        --#TYPE "Security: Unencrypted password"
                        --#SUMMARY "Station %d tried to use an unencrypted "
			--#SUMMARY "password call to login into server %s."
  	                --#ARGUMENTS {2,0}
                        --#SEVERITY CRITICAL
                        --#TIMEINDEX 1
                        --#HELP "nwalarm.hlp"
                        --#HELPTAG 140
			--#STATE  OPERATIONAL

                   ::= 140

supAcctLockoutClrdByConsole	TRAP-TYPE   --1.5.7.5/1.2.1.7.17
                        ENTERPRISE      nwalarm-mib
                        VARIABLES       {
                                        serverName,trapTime
                                        }
                        DESCRIPTION
                                "An account locked by a supervisor is now
				cleared. The account was locked because
				someone tried to login with an
				incorrect password."
                        --#TYPE "Security: Supervisor lockout cleared"
                        --#SUMMARY "SUPERVISOR account lockout cleared from "
			--#SUMMARY "server console on server %s."
  	                --#ARGUMENTS {0}
                        --#SEVERITY MINOR
                        --#TIMEINDEX 1
                        --#HELP "nwalarm.hlp"
                        --#HELPTAG 141
			--#STATE  OPERATIONAL

                   ::= 141

systemTimeChangedByConsole	TRAP-TYPE   --1.1.6.7.3/1.1.6.7.1
                        ENTERPRISE      nwalarm-mib
                        VARIABLES       {
                                        serverName,trapTime,userName
                                        }
                        DESCRIPTION
                                "The system time was changed from the
				 server console."
                        --#TYPE "System: Time changed, by server"
                        --#SUMMARY "System time changed from server "
			--#SUMMARY "console on server %s. New time is %s."
                        --#ARGUMENTS {0,2}
                        --#SEVERITY INFORMATIONAL
                        --#TIMEINDEX 1
                        --#HELP "nwalarm.hlp"
                        --#HELPTAG 142
                        --#STATE  OPERATIONAL

                       ::= 142

systemTimeChangedByUser	TRAP-TYPE   --1.1.6.7.4/1.1.6.7.2
                        ENTERPRISE      nwalarm-mib
                        VARIABLES       {
                                        serverName,trapTime,stationNumber,
					userName
                                        }
                        DESCRIPTION
                                "The system time was changed from a user
				 console."
                        --#TYPE "System: Time changed, by user"
                        --#SUMMARY "System time changed by station %d on "
			--#SUMMARY "server %s. New time is %s."
	                --#ARGUMENTS {2,0,3}
                        --#SEVERITY INFORMATIONAL
                        --#TIMEINDEX 1
                        --#HELP "nwalarm.hlp"
                        --#HELPTAG 143
                        --#STATE  OPERATIONAL

                       ::= 143



volDismountedDueToDriveDeact	TRAP-TYPE   --1.6.1.7.35/1.2.5.7.27
                        ENTERPRISE      nwalarm-mib
                        VARIABLES       {
                                        serverName,trapTime,volumeName
                                        }
                        DESCRIPTION
                                "The volume dismounted due to driver
				unload, disk failure, or OS-initiated
				driver unload."
                        --#TYPE "FileSys: Vol dismounted, drive deactivation"
                        --#SUMMARY "Volume %s dismounted due to drive "
			--#SUMMARY "deactivation on server %s."
	                --#ARGUMENTS {2,0}
                        --#SEVERITY CRITICAL
                        --#TIMEINDEX 1
                        --#HELP "nwalarm.hlp"
                        --#HELPTAG 144
                        --#STATE  DEGRADED

                   ::= 144

rtrFalsehood		TRAP-TYPE   --1.9.5.10
                        ENTERPRISE      nwalarm-mib
                        VARIABLES       {
                                        serverName,trapTime,
					internalNetworkAddress,
					macAddress,
					internalNetworkAddress1,macAddress1,
					macAddress2
                                        }
                        DESCRIPTION
                                "A router is falsely claiming that a particular
				network address has been changed to a different
				address."
                        --#TYPE "Router: Reporting wrong addresses"
                        --#SUMMARY "Server %s reports a router is falsely "
			--#SUMMARY "claiming its internal network no. has "
			--#SUMMARY "changed from %x:%x to %x:%x. "
			--#SUMMARY "Information from router %x."
	                --#ARGUMENTS {0,2,3,4,5,6}
                        --#SEVERITY CRITICAL
                        --#TIMEINDEX 1
                        --#HELP "nwalarm.hlp"
                        --#HELPTAG 145
                        --#STATE  DEGRADED

                   ::= 145

srvrAddrChanged		TRAP-TYPE   --1.9.5.11
                        ENTERPRISE      nwalarm-mib
                        VARIABLES       {
                                        serverName,trapTime,serverName1,
					networkAddress,macAddress,
					socketNumber,networkAddress1,macAddress1,
					socketNumber1,macAddress2
                                        }
                        DESCRIPTION
                                "A particular server address has been changed."
                        --#TYPE "Router: Server address changed"
                        --#SUMMARY "%s reports that the address of "
			--#SUMMARY "%s changed from %x:%x:%x "
			--#SUMMARY "to %x:%x:%x. Information from router "
	                --#SUMMARY "at %x."
			--#ARGUMENTS {0,2,3,4,5,6,7,8,9}
                        --#SEVERITY CRITICAL
                        --#TIMEINDEX 1
                        --#HELP "nwalarm.hlp"
                        --#HELPTAG 146
                        --#STATE  OPERATIONAL
                   ::= 146


extendFileHasNoOwnerToCharge 	TRAP-TYPE   --1.2.5.35
                        ENTERPRISE      nwalarm-mib
                        VARIABLES       {
                                        serverName,trapTime,userName,
					connectionNumber,pathFileName
                                        }
                        DESCRIPTION
                                "A file occupying a certain percentage of
				disk space has no owner to charge."
                        --#TYPE "FileSys: File extend err, no owner"
                        --#SUMMARY "User %s on connection %d attempted to "
			--#SUMMARY "extend the length of a file with no owner "
			--#SUMMARY "on server %s. File name %s."
 	                --#ARGUMENTS {2,3,0,4}
                        --#SEVERITY CRITICAL
                        --#TIMEINDEX 1
                        --#HELP "nwalarm.hlp"
                        --#HELPTAG 147
                        --#STATE  DEGRADED
                    ::= 147

rtrConfigErr3		TRAP-TYPE   --1.9.5.12
                        ENTERPRISE      nwalarm-mib
                        VARIABLES       {
                                        serverName,trapTime,macAddress,
					networkAddress,networkAddress1
                                        }
                        DESCRIPTION
                                "A router claims that a particular network
				 address should actually be another address."
                        --#TYPE "Router: Config err #3"
                        --#SUMMARY "Server %s reports a router configuration "
			--#SUMMARY "error. Router at node %x claims network "
			--#SUMMARY "%x should be %x."
	                --#ARGUMENTS {0,2,3,4}
                        --#SEVERITY MINOR
                        --#TIMEINDEX 1
                        --#HELP "nwalarm.hlp"
                        --#HELPTAG 148
                        --#STATE  DEGRADED

                   ::= 148

rtrConfigErr2		TRAP-TYPE   --1.9.5.9
                        ENTERPRISE      nwalarm-mib
                        VARIABLES       {
                                        serverName,trapTime,macAddress,
					routerName,networkAddress,
					networkAddress1
                                        }
                        DESCRIPTION
                                "A router claims that a particular network
				 address should actually be another address."
                        --#TYPE "Router: Config err #2"
                        --#SUMMARY "Server %s reports a router configuration "
			--#SUMMARY "error. Node %x (%s) claims network %x "
			--#SUMMARY "should be %x."
	                --#ARGUMENTS {0,2,3,4,5}
                        --#SEVERITY MINOR
                        --#TIMEINDEX 1
                        --#HELP "nwalarm.hlp"
                        --#HELPTAG 149
                        --#STATE  DEGRADED

                   ::= 149

dataMgrtrNotLoadedWhenRequested	TRAP-TYPE   --1.2.8.5.6
                        ENTERPRISE      nwalarm-mib
                        VARIABLES       {
                                        serverName,trapTime,volumeName
                                        }
                        DESCRIPTION
                                "A read/write request was made to the
				real-time data migration module, but the
				module was not loaded."
                        --#TYPE "FileSys: Migration NLM not loaded"
                        --#SUMMARY "Volume %s on server %s mounted with "
			--#SUMMARY "no Migration NLM loaded, some files may be "
			--#SUMMARY "inaccessible. "
 	                --#ARGUMENTS {2,0}
                        --#SEVERITY INFORMATIONAL
                        --#TIMEINDEX 1
                        --#HELP "nwalarm.hlp"
                        --#HELPTAG 150
                        --#STATE  DEGRADED

                   ::= 150

noSpecificSupportModulesLoaded	TRAP-TYPE   --1.2.8.5.4
                        ENTERPRISE      nwalarm-mib
                        VARIABLES       {
                                        serverName,trapTime,volumeName
                                        }
                        DESCRIPTION
                                "A read/write request was made to the real-time
				data migration module, but the required data
				migration support module was not loaded."
                        --#TYPE "FileSys: Migration support NLM not loaded"
                        --#SUMMARY "Volume %s on server %s mounted "
			--#SUMMARY "without a specified Migration Support NLM, "
			--#SUMMARY "some files may be inaccessible."
 	                --#ARGUMENTS {2,0}
                        --#SEVERITY INFORMATIONAL
                        --#TIMEINDEX 1
                        --#HELP "nwalarm.hlp"
                        --#HELPTAG 151
                        --#STATE  DEGRADED

                   ::= 151

notEnoughRAMForComp 	TRAP-TYPE   --1.2.5.36
                        ENTERPRISE      nwalarm-mib
                        VARIABLES       {
                                        serverName,trapTime
                                        }
                        DESCRIPTION
                                "Insufficient RAM to compress file."
                        --#TYPE "FileSys: Compression err, no memory"
                        --#SUMMARY "Server %s has insufficient RAM to "
			--#SUMMARY "compress file. "
 	                --#ARGUMENTS {0}
                        --#SEVERITY MAJOR
                        --#TIMEINDEX 1
                        --#HELP "nwalarm.hlp"
                        --#HELPTAG 152
                        --#STATE  DEGRADED

                    ::= 152

diskErrorCompression 	TRAP-TYPE   --1.2.5.37(msg.3004)
                        ENTERPRISE      nwalarm-mib
                        VARIABLES       {
                                        serverName,trapTime
                                        }
                        DESCRIPTION
                                "Disk I/O error compressing file."
                        --#TYPE "FileSys: Compression err, disk I/O"
                        --#SUMMARY "Disk I/O error compressing file on "
			--#SUMMARY "server %s."
 	                --#ARGUMENTS {0}
                        --#SEVERITY CRITICAL
                        --#TIMEINDEX 1
                        --#HELP "nwalarm.hlp"
                        --#HELPTAG 153
                        --#STATE  DEGRADED

                    ::= 153

compressErrorHoleCountMismatch 	TRAP-TYPE   --1.2.5.59(msg.3285)
                        ENTERPRISE      nwalarm-mib
                        VARIABLES       {
                                        serverName,trapTime,pathFileName,
					volumeNumber,
					fileSize,fileMiscInfo,fileMiscInfo1
                                        }
                        DESCRIPTION
                                "There was an internal compression error
				on the sparse count found on the linked list
				maintained by the compression executables."
                        --#TYPE "FileSys: Compression err, sparse count"
                        --#SUMMARY "Compress error file %s, volume %d, "
			--#SUMMARY "size %d on server %s. Original sparse "
			--#SUMMARY "count of %d, internal linked list shows "
			--#SUMMARY "sparse count %d."
 	                --#ARGUMENTS {2,3,4,0,5,6}
                        --#SEVERITY CRITICAL
                        --#TIMEINDEX 1
                        --#HELP "nwalarm.hlp"
                        --#HELPTAG 154
                        --#STATE  DEGRADED

                    ::= 154


unknownErrorCompression 	TRAP-TYPE   --1.2.5.38
                        ENTERPRISE      nwalarm-mib
                        VARIABLES       {
                                        serverName,trapTime,errorNumber
                                        }
                        DESCRIPTION
                                "There was an unknown error during file
                                 compression."
                        --#TYPE "FileSys: Compression err, disk write"
                        --#SUMMARY "Disk I/O error %d writing "
			--#SUMMARY "a compressed file to disk on server %s. If "
			--#SUMMARY "redirection is off, the data is not "
			--#SUMMARY "redirected to the hotfix area."
 	                --#ARGUMENTS {2,0}
                        --#SEVERITY CRITICAL
                        --#TIMEINDEX 1
                        --#HELP "nwalarm.hlp"
                        --#HELPTAG 155
                        --#STATE  DEGRADED

                    ::= 155

insufficientSpaceForDecompression 	TRAP-TYPE   --1.2.5.39
                        ENTERPRISE      nwalarm-mib
                        VARIABLES       {
                                        serverName,trapTime,pathFileName,
					stationNumber
                                        }
                        DESCRIPTION
                                "Insufficient disk space to decompress file."
                        --#TYPE "FileSys: Decompression err, no disk space"
                        --#SUMMARY "Server %s has insufficient disk space to "
			--#SUMMARY "decompress file %s for station %d."
  	                --#ARGUMENTS {0,2,3}
                        --#SEVERITY CRITICAL
                        --#TIMEINDEX 1
                        --#HELP "nwalarm.hlp"
                        --#HELPTAG 156
                        --#STATE  DEGRADED

                    ::= 156

decompUnknownCompVersion 	TRAP-TYPE   --1.2.5.40
                        ENTERPRISE      nwalarm-mib
                        VARIABLES       {
                                        serverName,trapTime,pathFileName,
					stationNumber
                                        }
                        DESCRIPTION
                                "File being decompressed has
				 unknown compression format."
                        --#TYPE "FileSys: Decompression err, unknown format "
                        --#SUMMARY "Compressed file %s being decompressed on "
			--#SUMMARY "server %s for station %d has unknown "
			--#SUMMARY "compression format."
  	                --#ARGUMENTS {2,0,3}
                        --#SEVERITY CRITICAL
                        --#TIMEINDEX 1
                        --#HELP "nwalarm.hlp"
                        --#HELPTAG 157
                        --#STATE  DEGRADED

                    ::= 157

unknownErrorDecomp 	TRAP-TYPE   --1.2.5.41
                        ENTERPRISE      nwalarm-mib
                        VARIABLES       {
                                        serverName,trapTime,errorNumber
                                        }
                        DESCRIPTION
                                "Unknown error returned from file decompress."
                        --#TYPE "FileSys: Decompression err, unknown (no path)"
                        --#SUMMARY "Unknown error %d returned from file "
			--#SUMMARY "decompress on server %s. "
	                --#ARGUMENTS {2,0}
                        --#SEVERITY CRITICAL
                        --#TIMEINDEX 1
                        --#HELP "nwalarm.hlp"
                        --#HELPTAG 158
                        --#STATE  DEGRADED

                    ::= 158



insufficientDecompError	TRAP-TYPE   --1.2.5.42
                        ENTERPRISE      nwalarm-mib
                        VARIABLES       {
                                        serverName,trapTime
                                        }
                        DESCRIPTION
                                "Insufficient RAM to decompress file."
                        --#TYPE "FileSys: Decompression err, no RAM (no path)"
                        --#SUMMARY "Server %s has insufficient RAM to "
			--#SUMMARY "decompress file."
	                --#ARGUMENTS {0}
                        --#SEVERITY MAJOR
                        --#TIMEINDEX 1
                        --#HELP "nwalarm.hlp"
                        --#HELPTAG 159
                        --#STATE  DEGRADED

                    ::= 159

compFileCorrupted	TRAP-TYPE   --1.2.5.43
                        ENTERPRISE      nwalarm-mib
                        VARIABLES       {
                                        serverName,trapTime
                                        }
                        DESCRIPTION
                                "Compressed file is corrupt and
				unrecoverable."
                        --#TYPE "FileSys: Compressed file corrupt (no path)"
                        --#SUMMARY "Compressed file found on server %s "
			--#SUMMARY "is corrupt and unrecoverable."
	                --#ARGUMENTS {0}
                        --#SEVERITY CRITICAL
                        --#TIMEINDEX 1
                        --#HELP "nwalarm.hlp"
                        --#HELPTAG 160
                        --#STATE  DEGRADED

                    ::= 160

rejectedIncompleteNCP	TRAP-TYPE   --1.4.7.9
                        ENTERPRISE      nwalarm-mib
                        VARIABLES       {
                                        serverName,trapTime,stationNumber,
					ncpFunctionNumber,ncpSubFunctionNumber
                                        }
                        DESCRIPTION
                                "A server received an incomplete NCP packet from
				a workstation and rejected the packet."
                        --#TYPE "NCP: Rejected incomplete NCP packet"
                        --#SUMMARY "Server %s rejected an incomplete NCP "
			--#SUMMARY "packet from station %d (NCP %d %d)."
 	                --#ARGUMENTS {0,2,3,4}
                        --#SEVERITY CRITICAL
                        --#TIMEINDEX 1
                        --#HELP "nwalarm.hlp"
                        --#HELPTAG 161
                        --#STATE  OPERATIONAL

                   ::= 161

stationUsedABadPacket	TRAP-TYPE   --1.4.7.6
                        ENTERPRISE      nwalarm-mib
                        VARIABLES       {
                                        serverName,trapTime,stationNumber,
					ncpFunctionNumber,ncpSubFunctionNumber
                                        }
                        DESCRIPTION
                                "A server received an incomplete NCP packet from
				a workstation and processed it."
                        --#TYPE "NCP: Processed incomplete NCP packet"
                        --#SUMMARY "Server %s processed an incomplete NCP from "
			--#SUMMARY "station %d (NCP %d %d)."
 	                --#ARGUMENTS {0,2,3,4}
                        --#SEVERITY MINOR
                        --#TIMEINDEX 1
                        --#HELP "nwalarm.hlp"
                        --#HELPTAG 162
                        --#STATE  OPERATIONAL

                   ::= 162


rejectedNCPBadSubfunctionLngth	TRAP-TYPE   --1.4.7.10
                        ENTERPRISE      nwalarm-mib
                        VARIABLES       {
                                        serverName,trapTime,stationNumber,
					ncpFunctionNumber,ncpSubFunctionNumber
                                        }
                        DESCRIPTION
                                "A server received an NCP with the length field
				improperly initialized and rejected it."
                        --#TYPE "NCP: Rejected bad NCP packet"
                        --#SUMMARY "Server %s rejected an NCP with a bad "
			--#SUMMARY "subfunction length, station %d "
			--#SUMMARY "(NCP %d %d)."
 	                --#ARGUMENTS {0,2,3,4}
                        --#SEVERITY CRITICAL
                        --#TIMEINDEX 1
                        --#HELP "nwalarm.hlp"
                        --#HELPTAG 163
                        --#STATE  OPERATIONAL

                   ::= 163

processedNCPBadSubfunctionLngth	TRAP-TYPE   --1.4.7.11
                        ENTERPRISE      nwalarm-mib
                        VARIABLES       {
                                        serverName,trapTime,stationNumber,
					ncpFunctionNumber,ncpSubFunctionNumber
                                        }
                        DESCRIPTION
                                "A server received an NCP with the length field
				improperly initialized and processed it."
                        --#TYPE "NCP: Processed bad NCP packet"
                        --#SUMMARY "Server %s processed an NCP with a bad "
			--#SUMMARY "subfunction length, station %d "
			--#SUMMARY "(NCP %d %d)."
  	                --#ARGUMENTS {0,2,3,4}
                        --#SEVERITY MINOR
                        --#TIMEINDEX 1
                        --#HELP "nwalarm.hlp"
                        --#HELPTAG 164
                        --#STATE  OPERATIONAL

                   ::= 164

compFilePathCorrupted	TRAP-TYPE   --1.2.5.44
                        ENTERPRISE      nwalarm-mib
                        VARIABLES       {
                                        serverName,trapTime,pathFileName
                                        }
                        DESCRIPTION
                                "Compressed file with path is corrupted and
				 unrecoverable."
                        --#TYPE "FileSys: Compressed file corrupt (path)"
                        --#SUMMARY "Compressed file %s on server %s is "
			--#SUMMARY "corrupt and unrecoverable."
	                --#ARGUMENTS {2,0}
                        --#SEVERITY CRITICAL
                        --#TIMEINDEX 1
                        --#HELP "nwalarm.hlp"
                        --#HELPTAG 165
                        --#STATE  DEGRADED

                    ::= 165

compFileInUse		TRAP-TYPE   --1.2.5.45
                        ENTERPRISE      nwalarm-mib
                        VARIABLES       {
                                        serverName,trapTime,pathFileName,
					stationNumber
                                        }
                        DESCRIPTION
                                "Compressed file in use is corrupt and
				unrecoverable."

                        --#TYPE "FileSys: Compressed file corrupt, in use"
                        --#SUMMARY "Compressed file %s found on server %s and "
			--#SUMMARY "in use by station %d is corrupt and "
			--#SUMMARY "unrecoverable."
	                --#ARGUMENTS {2,0,3}
                        --#SEVERITY CRITICAL
                        --#TIMEINDEX 1
                        --#HELP "nwalarm.hlp"
                        --#HELPTAG 166
                        --#STATE  DEGRADED

                    ::= 166

nlmNoPriority		TRAP-TYPE   --1.1.3.7.5
                        ENTERPRISE      nwalarm-mib
                        VARIABLES       {
                                        serverName,trapTime
                                        }
                        DESCRIPTION
                                "A loaded NLM is not allowing other low-priority
				threads to run."
                        --#TYPE "OS: NLM not letting other threads run"
                        --#SUMMARY "NLM executing on server %s is not "
			--#SUMMARY "allowing low-priority threads to run."
	                --#ARGUMENTS {0}
                        --#SEVERITY INFORMATIONAL
                        --#TIMEINDEX 1
                        --#HELP "nwalarm.hlp"
                        --#HELPTAG 167
                        --#STATE  DEGRADED
                       ::= 167

workToDo		TRAP-TYPE   --1.1.3.7.6
                        ENTERPRISE      nwalarm-mib
                        VARIABLES       {
                                        serverName,trapTime
                                        }
                        DESCRIPTION
                                "A Work-to-do thread took more than a minute of
				 CPU time."
                        --#TYPE "OS: Work-to-do took too much CPU"
                        --#SUMMARY "A kernel Work-to-do on server %s took "
			--#SUMMARY "more than one minute to run."
		        --#ARGUMENTS {0}
                        --#SEVERITY INFORMATIONAL
                        --#TIMEINDEX 1
                        --#HELP "nwalarm.hlp"
                        --#HELPTAG 168
                        --#STATE  DEGRADED

                       ::= 168

compErrTempFileErr	TRAP-TYPE   --1.2.5.46
                        ENTERPRISE      nwalarm-mib
                        VARIABLES       {
                                        serverName,trapTime,pathFileName,
					volumeNumber,fileSize,fileOffset,
					fileValue
                                        }
                        DESCRIPTION
                                "There was an invalid byte in the temporary file
				created during file compression."

                        --#TYPE "FileSys: Compression err, inconsistent temp file "
                        --#SUMMARY "Internal compression error on server %s "
			--#SUMMARY "file %s volume %d size %d. Intermediate "
			--#SUMMARY "file inconsistency at offset %x: value %x "
			--#SUMMARY "should be 31h or 30h."
	                --#ARGUMENTS {0,2,3,4,5,6}
                        --#SEVERITY CRITICAL
                        --#TIMEINDEX 1
                        --#HELP "nwalarm.hlp"
                        --#HELPTAG 169
                        --#STATE  DEGRADED

                    ::= 169

compErrLngthTotMismatch	TRAP-TYPE   --1.2.5.47
                        ENTERPRISE      nwalarm-mib
                        VARIABLES       {
                                        serverName,trapTime,pathFileName,
					volumeNumber,fileSize,fileMiscInfo,
					fileMiscInfo1
                                        }
                        DESCRIPTION
                                "This is an internal consistency check done by
				compression to guarantee the integrity of the
				data being compressed. During the file
				compression, an intermediate file is created
				that describes the compressed version of the
				file. The file contains code describing what
				should be encoded in the compressed version of
				the file. The totals from processing the
				original file do not match the totals from
				processing the intermediate file."

                        --#TYPE "FileSys: Compression err, length totals"
                        --#SUMMARY "Internal compression error on server %s "
			--#SUMMARY "file %s, volume %d, intermediate size %d. "
			--#SUMMARY "Length totals from intermediate file "
			--#SUMMARY "generation %x and intermediate file "
			--#SUMMARY " processing %x mismatch invalidating "
			--#SUMMARY "intermediate file."
	                --#ARGUMENTS {0,2,3,4,5,6}
                        --#SEVERITY CRITICAL
                        --#TIMEINDEX 1
                        --#HELP "nwalarm.hlp"
                        --#HELPTAG 170
                        --#STATE  DEGRADED

                    ::= 170


compErrOffsetTotalsMismatch	TRAP-TYPE   --1.2.5.48
                        ENTERPRISE      nwalarm-mib
                        VARIABLES       {
                                        serverName,trapTime,pathFileName,
					volumeNumber,
					fileSize,fileMiscInfo,fileMiscInfo1
                                        }
                        DESCRIPTION
                                "This is an internal consistency check done by
				compression to guarantee the integrity of the
				data being compressed. During the file
				compression, an intermediate file is created
				that describes the compressed version of the
				file. The file contains code describing what
				should be encoded in the compressed version
				of the file. The totals from processing the
				original file do not match the totals from
				processing the intermediate file."

                        --#TYPE "FileSys: Compression err, offset totals"
                        --#SUMMARY "Internal compression error on server %s "
			--#SUMMARY "file %s,volume %d,intermediate size %ld. "
			--#SUMMARY "Offset totals from intermediate file "
			--#SUMMARY "generation (%x) and intermediate file "
			--#SUMMARY "processing (%x) mismatch invalidating "
			--#SUMMARY "intermediate file."
	                --#ARGUMENTS {0,2,3,4,5,6}
                        --#SEVERITY CRITICAL
                        --#TIMEINDEX 1
                        --#HELP "nwalarm.hlp"
                        --#HELPTAG 171
                        --#STATE  DEGRADED

                    ::= 171


compErrDataCodeCountMismatch	TRAP-TYPE   --1.2.5.49
                        ENTERPRISE      nwalarm-mib
                        VARIABLES       {
                                        serverName,trapTime,pathFileName,
					volumeNumber,fileSize,fileMiscInfo,
					fileMiscInfo1
                                        }
                        DESCRIPTION
                                "This is an internal consistency check done by
				compression to guarantee the integrity of the
				data being compressed. During the file compression,
				an intermediate file is created that describes
				the compressed version of the file. The file
				contains code describing what should be encoded
				in the compressed version of the file. The totals
				from processing the original file do not match the
				totals from processing the intermediate file."

                        --#TYPE "FileSys: Compression err, data encode counts"
                        --#SUMMARY "Internal compression error on server %s "
			--#SUMMARY "file %s volume %d intermediate size %ld. Data "
			--#SUMMARY "encode counts from intermediate file "
			--#SUMMARY "generation (%ld) and intermediate file "
			--#SUMMARY "processing (%ld) mismatch invalidating "
			--#SUMMARY "intermediate file. "
	                --#ARGUMENTS {0,2,3,4,5,6}
                        --#SEVERITY CRITICAL
                        --#TIMEINDEX 1
                        --#HELP "nwalarm.hlp"
                        --#HELPTAG 172
                        --#STATE  DEGRADED

                    ::= 172

compErrLthOffsetCodeCountMismatch	TRAP-TYPE   --1.2.5.50
                        ENTERPRISE      nwalarm-mib
                        VARIABLES       {
                                        serverName,trapTime,pathFileName,
					volumeNumber,
					fileSize,fileMiscInfo,fileMiscInfo1
                                        }
                        DESCRIPTION
                                "This is an internal consistency check done by
				compression to guarantee the integrity of the
				data being compressed. During the file compression,
				an intermediate file is created that describes
				the compressed version of the file. The file
				contains code describing what should be encoded
				in the compressed version of the file. The totals
				from processing the original file do not match the
				totals from processing the intermediate file."
                        --#TYPE "FileSys: Compression err, length/offset counts"
                        --#SUMMARY "Internal compression error on server %s "
			--#SUMMARY "file %s volume %d intermediate size %d. "
			--#SUMMARY "Length/offset code counts from "
			--#SUMMARY "intermediate generation (%d) and "
			--#SUMMARY "intermediate file processing (%d) mismatch "
			--#SUMMARY "invalidating intermediate file."
	                --#ARGUMENTS {0,2,3,4,5,6}
                        --#SEVERITY CRITICAL
                        --#TIMEINDEX 1
                        --#HELP "nwalarm.hlp"
                        --#HELPTAG 173
                        --#STATE  DEGRADED

                    ::= 173

compErrLgrLngthCodeCountMismatch	TRAP-TYPE   --1.2.5.51
                        ENTERPRISE      nwalarm-mib
                        VARIABLES       {
                                        serverName,trapTime,message
                                        }
                        DESCRIPTION
                                "License File in error"
                        --#TYPE "FileSys: Compression err, large length/offset"
			--#SUMMARY "%s reports that %s"
	                --#ARGUMENTS {0,2}
                        --#SEVERITY CRITICAL
                        --#TIMEINDEX 1
                        --#HELP "nwalarm.hlp"
                        --#HELPTAG 174
                        --#STATE  DEGRADED

                    ::= 174
--There is another trap similar to the following trap. The trap no.234.
--The only difference is on intermediate file in the following trap while
--in trap 234, it is on original file

compErrReadZeroBytesInt	TRAP-TYPE   --1.2.5.52
                        ENTERPRISE      nwalarm-mib
                        VARIABLES       {
                                        serverName,trapTime,volumeNumber,
					fileSize,pathFileName,fileOffset
                                        }
                        DESCRIPTION
				"The disk has returned 0 bytes for a
				compression read request and there is
				still more data to read."
                        --#TYPE "FileSys: Compression err, EOF on intermediate"
                        --#SUMMARY "Compress error intermediate, volume %d, "
			--#SUMMARY "size %d. Read beyond end of file %s at "
			--#SUMMARY "offset %d. Error occurred on server %s."
	                --#ARGUMENTS {2,3,4,5,0}
                        --#SEVERITY CRITICAL
                        --#TIMEINDEX 1
                        --#HELP "nwalarm.hlp"
                        --#HELPTAG 175
                        --#STATE  DEGRADED

                    ::= 175

compErrTreeTooBig	TRAP-TYPE   --1.2.5.53
                        ENTERPRISE      nwalarm-mib
                        VARIABLES       {
                                        serverName,trapTime,pathFileName,
					volumeNumber,fileSize
                                        }
                        DESCRIPTION
                                "This is an internal consistency check done by
				compression to guarantee the integrity of the
				data being compressed. During the file
				compression, an intermediate file is created
				that describes the compressed version of the
				file. The file contains code describing what
				should be encoded in the compressed version of
				the file. The totals from processing the
				original file do not match the totals from
				processing the intermediate file."

                        --#TYPE "FileSys: Compression err, Shannon tree depth"
                        --#SUMMARY "Internal compression error on server %s "
			--#SUMMARY "file %s volume %d size %d. Shannon tree "
			--#SUMMARY "depth exceeded 32 generating bit codes "
			--#SUMMARY "not containable in a single LONG."
	                --#ARGUMENTS {0,2,3,4}
                        --#SEVERITY CRITICAL
                        --#TIMEINDEX 1
                        --#HELP "nwalarm.hlp"
                        --#HELPTAG 176
                        --#STATE  DEGRADED

                    ::= 176


compErrMatchSizeFail	TRAP-TYPE   --1.2.5.54
                        ENTERPRISE      nwalarm-mib
                        VARIABLES       {
                                        serverName,trapTime,pathFileName,
					volumeNumber,
					fileSize,fileSize1,fileSize2

                                        }
                        DESCRIPTION
                                "This is an internal consistency check done by
				compression to guarantee the integrity of the data
				being compressed. During the file compression,
				an intermediate file is created that describes
				the compressed version of the file. The file contains
				code describing what should be encoded in the
				compressed version of the file. The totals from
				processing the original file do not match the
				totals from processing the intermediate file."

                        --#TYPE "FileSys: Compression err, projected size"
                        --#SUMMARY "Internal compression error on server %s "
			--#SUMMARY "file %s volume %d size %d. Projected size "
			--#SUMMARY "of the compressed file (%d) did not match "
			--#SUMMARY " byte size of the compressed file (%d)."
	                --#ARGUMENTS {0,2,3,4,5,6}
                        --#SEVERITY CRITICAL
                        --#TIMEINDEX 1
                        --#HELP "nwalarm.hlp"
                        --#HELPTAG 177
                        --#STATE  DEGRADED

                    ::= 177

signatureInvalid	TRAP-TYPE   --1.1.5.22
                        ENTERPRISE      nwalarm-mib
                        VARIABLES       {
                                        serverName,trapTime,userName,
					networkAddress,	macAddress
                                        }
                        DESCRIPTION
                                "NCP packet with invalid signature was received.
				Possible packet forgery."
                        --#TYPE "Security: Invalid signature #1"
                        --#SUMMARY "Server %s received an NCP request with an "
			--#SUMMARY "invalid security signature from user %s at "
			--#SUMMARY "%x:%x. Possible intruder or network "
			--#SUMMARY "corruption."
                        --#ARGUMENTS {0,2,3,4}
                        --#SEVERITY MINOR
                        --#TIMEINDEX 1
                        --#HELP "nwalarm.hlp"
                        --#HELPTAG 178
                        --#STATE  OPERATIONAL

                        ::= 178

licenseInvalid		TRAP-TYPE   --1.1.5.24
                        ENTERPRISE      nwalarm-mib
                        VARIABLES       {
                                        serverName,trapTime,message
                                        }
                        DESCRIPTION
                                "The server license is invalid. Maximum
				 connections reduced to one."
                        --#TYPE "System: License invalid"
                        --#SUMMARY "Server license invalid. %s "
			--#SUMMARY "on server %s. Possible network corruption."
                        --#ARGUMENTS {2,0}
                        --#SEVERITY MINOR
                        --#TIMEINDEX 1
                        --#HELP "nwalarm.hlp"
                        --#HELPTAG 179
                        --#STATE  DEGRADED

                        ::= 179

deactHotFix	 	TRAP-TYPE   --1.13.5.56
			ENTERPRISE      nwalarm-mib
			VARIABLES  {
                                      serverName,trapTime,deviceName
                                    }
			DESCRIPTION
                                "There was a media failure and hotfix could not
				fix it. The device was deactivated."
                        --#TYPE "Disk: Deactivated, hotfix failure"
                        --#SUMMARY  "%s deactivated due to hotfix failure on "
			--#SUMMARY  "server %s."
 	                --#ARGUMENTS {2,0}
                        --#SEVERITY CRITICAL
                        --#TIMEINDEX 1
                        --#HELP "nwalarm.hlp"
                        --#HELPTAG 180
                        --#STATE  DEGRADED

	         ::= 180

unknownDecompressErrorWithName	TRAP-TYPE   --1.2.5.55
                        ENTERPRISE      nwalarm-mib
                        VARIABLES       {
                                        serverName,trapTime,errorNumber,
					pathFileName
                                        }
                        DESCRIPTION
                                "A unknown error was returned from file
				decompression."
                        --#TYPE "FileSys: Decompression err, unknown (path)"
                        --#SUMMARY "Unknown error (%d) returned from "
			--#SUMMARY "decompression for file %s on server %s."
 	                --#ARGUMENTS {2,3,0}
                        --#SEVERITY CRITICAL
                        --#TIMEINDEX 1
                        --#HELP "nwalarm.hlp"
                        --#HELPTAG 181
                        --#STATE  DEGRADED

                    ::= 181

insufficientRamToDecompWithName	TRAP-TYPE   --1.2.5.56
                        ENTERPRISE      nwalarm-mib
                        VARIABLES       {
                                        serverName,trapTime,pathFileName
                                        }
                        DESCRIPTION
                                "Insufficient RAM to decompress file."
                        --#TYPE "FileSys: Decompression err, no RAM (path)"
                        --#SUMMARY "Insufficient RAM to decompress file %s "
			--#SUMMARY "on server %s."
 	                --#ARGUMENTS {2,0}
                        --#SEVERITY MAJOR
                        --#TIMEINDEX 1
                        --#HELP "nwalarm.hlp"
                        --#HELPTAG 182
                        --#STATE  DEGRADED

                    ::= 182

decompressUnderFreePercentage	TRAP-TYPE   --1.2.5.57
                        ENTERPRISE      nwalarm-mib
                        VARIABLES       {
                                        serverName,trapTime,volumeName
                                        }
                        DESCRIPTION
                                "Compressed files are not being committed as
				decompressed due to lack of disk space."
                        --#TYPE "FileSys: Decompression err, not committed"
                        --#SUMMARY "Compressed files are not being committed "
			--#SUMMARY "decompressed on volume %s due to lack of "
			--#SUMMARY "disk space on server %s."
 	                --#ARGUMENTS {2,0}
                        --#SEVERITY MINOR
                        --#TIMEINDEX 1
                        --#HELP "nwalarm.hlp"
                        --#HELPTAG 183
                        --#STATE  DEGRADED

                    ::= 183

negPktLargeBuffer	TRAP-TYPE   --1.4.7.12
                        ENTERPRISE      nwalarm-mib
                        VARIABLES       {
                                        serverName,trapTime,connectionNumber,
					packetSize, packetSize1
                                        }
                        DESCRIPTION
                                "An NCP negotiation packet tried to negotiate a
				connection request packet that was larger than
				the driver could handle. The request was rejected
				by IPX."
                        --#TYPE "NCP: Rejected large packet req."
                        --#SUMMARY "%s: Connection %d, negotiate packet request "
			--#SUMMARY "failed using buffer size = %d, which was "
			--#SUMMARY "larger than max. buffer size of %d. "
  	                --#ARGUMENTS {0, 2,3,4}
                        --#SEVERITY MAJOR
                        --#TIMEINDEX 1
                        --#HELP "nwalarm.hlp"
                        --#HELPTAG 184
                        --#STATE  DEGRADED

                   ::= 184

loginDisabledByConsole	TRAP-TYPE   --1.5.7.28
                        ENTERPRISE      nwalarm-mib
                        VARIABLES       {
                                        serverName,trapTime
                                        }
                        DESCRIPTION
                                "A disable login command was issued at
				the server console."
                        --#TYPE "System: Login disabled, by server"
                        --#SUMMARY "Login is now disabled on server %s."
 	                --#ARGUMENTS {0}
                        --#SEVERITY INFORMATIONAL
                        --#TIMEINDEX 1
                        --#HELP "nwalarm.hlp"
                        --#HELPTAG 185
                        --#STATE  OPERATIONAL

                   ::= 185

loginEnabledByConsole	TRAP-TYPE   --1.5.7.29
                        ENTERPRISE      nwalarm-mib
                        VARIABLES       {
                                        serverName,trapTime
                                        }
                        DESCRIPTION
                                "An enable login command was issued at
				the server console."
                        --#TYPE "System: Login enabled, by server"
                        --#SUMMARY "Login is now enabled on server %s."
 	                --#ARGUMENTS {0}
                        --#SEVERITY INFORMATIONAL
                        --#TIMEINDEX 1
                        --#HELP "nwalarm.hlp"
                        --#HELPTAG 186
                        --#STATE  OPERATIONAL

                   ::= 186

growableStackNotAllocated	TRAP-TYPE   --1.1.5.1.5.6
                        ENTERPRISE      nwalarm-mib
                        VARIABLES       {
                                        serverName,trapTime
                                        }
                        DESCRIPTION
                                "A loaded NLM tried to create a stack and failed."
                        --#TYPE "OS: Stack creation failed."
                        --#SUMMARY "Executing NLM on server %s "
			--#SUMMARY  "requested growable stack but failed."
 	                --#ARGUMENTS {0}
                        --#SEVERITY CRITICAL
                        --#TIMEINDEX 1
                        --#HELP "nwalarm.hlp"
                        --#HELPTAG 187
                        --#STATE  DEGRADED

                    ::= 187
--***********************************************************************
-- the following alerts share the same unique ids as some of the earlier
-- alerts but is distinguished by the OS from the message num.
--***********************************************************************

-- the following two are same as trap 86 but have different message numbers

insertDSMediaAck 	TRAP-TYPE   --1.13.1.3.7.23
			ENTERPRISE      nwalarm-mib
			VARIABLES  {
                                      serverName,trapTime,deviceName
                                    }
			DESCRIPTION
                                "The insertion of a double-sided medium into a
				 drive is acknowledged."
                        --#TYPE "MediaMgr: DS-media insert ack'd"
                        --#SUMMARY  "Insert double-sided media request on "
			--#SUMMARY  "device %s acknowledged on server %s."
 	                --#ARGUMENTS {2,0}
                        --#SEVERITY INFORMATIONAL
                        --#TIMEINDEX 1
                        --#HELP "nwalarm.hlp"
                        --#HELPTAG 188
			--#STATE OPERATIONAL

	         ::= 188

insertMagazineAck 	TRAP-TYPE   --1.13.1.3.7.24
			ENTERPRISE      nwalarm-mib
			VARIABLES  {
                                      serverName,trapTime,deviceName
                                    }
			DESCRIPTION
                                "The insertion of a magazine into a drive is
				acknowledged."
                        --#TYPE "MediaMgr: Magazine insert ack'd"
                        --#SUMMARY  "Insert magazine request on device %s "
			--#SUMMARY  "acknowledged on server %s."
 	                --#ARGUMENTS {2,0}
                        --#SEVERITY INFORMATIONAL
                        --#TIMEINDEX 1
                        --#HELP "nwalarm.hlp"
                        --#HELPTAG 189
			--#STATE OPERATIONAL

	         ::= 189

-- the following two are same as trap 87 but have different message numbers


insertDSMediaAborted 	TRAP-TYPE   --1.13.1.3.7.25
			ENTERPRISE      nwalarm-mib
			VARIABLES  {
                                      serverName,trapTime,deviceName
                                    }
			DESCRIPTION
                                "Previously requested insert double-sided
				media request is withdrawn."
                        --#TYPE "MediaMgr: DS-media insert aborted"
                        --#SUMMARY  "Insert double-sided media request on "
			--#SUMMARY  "device %s aborted on server %s."
 	                --#ARGUMENTS {2,0}
                        --#SEVERITY INFORMATIONAL
                        --#TIMEINDEX 1
                        --#HELP "nwalarm.hlp"
                        --#HELPTAG 190
			--#STATE OPERATIONAL

	         ::= 190

insertMagazineAborted 	TRAP-TYPE   --1.13.1.3.7.26
			ENTERPRISE      nwalarm-mib
			VARIABLES  {
                                      serverName,trapTime,deviceName
                                    }
			DESCRIPTION
                                "Previously requested insert magazine request
				 is withdrawn."
                        --#TYPE "MediaMgr: Magazine insert aborted"
                        --#SUMMARY  "Insert magazine request on device %s "
			--#SUMMARY  "aborted on server %s."
 	                --#ARGUMENTS {2,0}
                        --#SEVERITY INFORMATIONAL
                        --#TIMEINDEX 1
                        --#HELP "nwalarm.hlp"
                        --#HELPTAG 191
			--#STATE OPERATIONAL

	         ::= 191

-- the following two are same as trap 88 but have different message numbers


remDSMediaAck	 	TRAP-TYPE   --1.13.1.3.7.27
			ENTERPRISE      nwalarm-mib
			VARIABLES  {
                                      serverName,trapTime,deviceName
                                     }
			DESCRIPTION
                                "Removal of a double-sided medium from a device
				 is acknowledged."
                        --#TYPE "MediaMgr: DS-media remove ack'd"
                        --#SUMMARY  "Remove double-sided media request on "
			--#SUMMARY  "device %s acknowledged on server %s."
 	                --#ARGUMENTS {2,0}
                        --#SEVERITY INFORMATIONAL
                        --#TIMEINDEX 1
                        --#HELP "nwalarm.hlp"
                        --#HELPTAG 192
			--#STATE OPERATIONAL

	         ::= 192

remMagazineAck	 	TRAP-TYPE   --1.13.1.3.7.28
			ENTERPRISE      nwalarm-mib
			VARIABLES  {
                                      serverName,trapTime,deviceName
                                    }
			DESCRIPTION
                                "Removal of a magazine from a device is
				 acknowledged."
                        --#TYPE "MediaMgr: Magazine remove ack'd"
                        --#SUMMARY  "Remove magazine request on device %s "
			--#SUMMARY  "acknowledged on server %s."
 	                --#ARGUMENTS {2,0}
                        --#SEVERITY INFORMATIONAL
                        --#TIMEINDEX 1
                        --#HELP "nwalarm.hlp"
                        --#HELPTAG 193
			--#STATE OPERATIONAL

	         ::= 193

-- the following two are same as trap 89 but have different message numbers


remDSMediaAborted 	TRAP-TYPE   --1.13.1.3.7.29
			ENTERPRISE      nwalarm-mib
			VARIABLES  {
                                      serverName,trapTime,deviceName
                                    }
			DESCRIPTION
                                "Previously requested remove double-sided
				 media request aborted."
                        --#TYPE "MediaMgr: DS-media remove aborted"
                        --#SUMMARY  "Remove double-sided media request on "
			--#SUMMARY  "device %s aborted on server %s."
 	                --#ARGUMENTS {2,0}
                        --#SEVERITY INFORMATIONAL
                        --#TIMEINDEX 1
                        --#HELP "nwalarm.hlp"
                        --#HELPTAG 194
			--#STATE OPERATIONAL

	         ::= 194


remMagazineAborted 	TRAP-TYPE   --1.13.1.3.7.30
			ENTERPRISE      nwalarm-mib
			VARIABLES  {
                                      serverName,trapTime,deviceName
                                    }
			DESCRIPTION
                                "Previously requested remove magazine request
				 aborted."
                        --#TYPE "MediaMgr: Magazine remove aborted"
                        --#SUMMARY  "Remove magazine request on device %s "
			--#SUMMARY  "aborted on server %s."
 	                --#ARGUMENTS {2,0}
                        --#SEVERITY INFORMATIONAL
                        --#TIMEINDEX 1
                        --#HELP "nwalarm.hlp"
                        --#HELPTAG 195
			--#STATE OPERATIONAL

	         ::= 195

-- the following two are same as trap 90 but have different message numbers


insertMagazineInto 	TRAP-TYPE   --1.13.1.3.7.32
			ENTERPRISE      nwalarm-mib
			VARIABLES  {
                                      serverName,trapTime,mediaLabel,
					deviceName
                                    }
			DESCRIPTION
                                "The media manager requires a magazine to be
				inserted into the device."
                        --#TYPE "MediaMgr: Magazine insert req"
                        --#SUMMARY  "Insert magazine %s into %s on server %s."
 	                --#ARGUMENTS {2,3,0}
                        --#SEVERITY INFORMATIONAL
                        --#TIMEINDEX 1
                        --#HELP "nwalarm.hlp"
                        --#HELPTAG 196
			--#STATE OPERATIONAL

	         ::= 196

-- the following two are same as trap 91 but have different message numbers

removeDSMediaFrom 	TRAP-TYPE   --1.13.1.3.7.33
			ENTERPRISE      nwalarm-mib
			VARIABLES  {
                                      serverName,trapTime,deviceName
                                    }
			DESCRIPTION
                                "The media manager requires a double-sided
				 medium to be removed from a device."
                        --#TYPE "MediaMgr: DS-media remove req"
                        --#SUMMARY  "Remove double-sided medium from %s "
			--#SUMMARY  "on server %s."
 	                --#ARGUMENTS {2,0}
                        --#SEVERITY INFORMATIONAL
                        --#TIMEINDEX 1
                        --#HELP "nwalarm.hlp"
                        --#HELPTAG 197
			--#STATE OPERATIONAL

	         ::= 197

removeMagazineFrom 	TRAP-TYPE   --1.13.1.3.7.34
			ENTERPRISE      nwalarm-mib
			VARIABLES  {
                                      serverName,trapTime,deviceName
                                   }
			DESCRIPTION
                                "The media manager requires a magazine
				to be removed from a device."
                        --#TYPE "MediaMgr: Remove magazine from server"
                        --#SUMMARY  "Remove magazine from %s on server %s."
 	                --#ARGUMENTS {2,0}
                        --#SEVERITY INFORMATIONAL
                        --#TIMEINDEX 1
                        --#HELP "nwalarm.hlp"
                        --#HELPTAG 198
			--#STATE OPERATIONAL

	         ::= 198

-- the following is same as trap 71 but has different message number

moduleDidNotReleaseResources	TRAP-TYPE   --1.1.3.7.2/1.1.3.7.2
                        ENTERPRISE      nwalarm-mib
                        VARIABLES       {
                                        serverName,trapTime,numberOfResources,
					nlmName,resourceName,resourceDescription
                                        }
                        DESCRIPTION "An NLM did not release
				 resources."
                        --#TYPE "OS: NLM did not release resources"
                        --#SUMMARY "Module executing on %s did not "
			--#SUMMARY "release %d resources. Module: %s."
			--#SUMMARY " Resource: %s. Description: %s."
                        --#ARGUMENTS {0,2,3,4,5}
                        --#SEVERITY CRITICAL
                        --#TIMEINDEX 1
                        --#HELP "nwalarm.hlp"
                        --#HELPTAG 199
                        --#STATE  DEGRADED

                        ::= 199

--**************************************bindery alerts**********************

opnBinderyFailSinceVolNotMounted  TRAP-TYPE   --1.11.5.4/1.11.6.5.4
			ENTERPRISE      nwalarm-mib
			VARIABLES  {
                                        serverName,trapTime
                                    }
			DESCRIPTION
                                "Server failed to open the bindery. Request
				 failed because the SYS volume was not mounted."
                        --#TYPE "System: Bindery did not open, server"
                        --#SUMMARY "OS failed to open the bindery. "
			--#SUMMARY "Volume SYS is not mounted on "
			--#SUMMARY "server %s."
 	                --#ARGUMENTS {0}
                        --#SEVERITY INFORMATIONAL
                        --#TIMEINDEX 1
                        --#HELP "nwalarm.hlp"
                        --#HELPTAG 200
                        --#STATE  NONOPERATIONAL

	            ::= 200

binderyOpnReqtdByUsrFailed  TRAP-TYPE   --1.11.5.5/1.11.6.5.5
			ENTERPRISE      nwalarm-mib
			VARIABLES  {
                                        serverName,trapTime,userName,
					stationNumber
                                    }
			DESCRIPTION
                                "A user tried to open the bindery and failed
				 since the SYS volume was not mounted."
                        --#TYPE "System: Bindery did not open, user"
                        --#SUMMARY "Open bindery request by user %s on "
			--#SUMMARY "station %d failed because volume SYS is "
			--#SUMMARY " not mounted on server %s."
 	                --#ARGUMENTS {2,3,0}
                        --#SEVERITY INFORMATIONAL
                        --#TIMEINDEX 1
                        --#HELP "nwalarm.hlp"
                        --#HELPTAG 201
                        --#STATE  NONOPERATIONAL

	            ::= 201

binderyOpnReqtdBySrvr  TRAP-TYPE   --1.11.7.6/1.11.6.7.6
			ENTERPRISE      nwalarm-mib
			VARIABLES  {
                                        serverName,trapTime
                                    }
			DESCRIPTION
                                "The server has opened the bindery."
                        --#TYPE "System: Bindery opened, by server"
                        --#SUMMARY "Bindery open requested by server %s."
 	                --#ARGUMENTS {0}
                        --#SEVERITY MINOR
                        --#TIMEINDEX 1
                        --#HELP "nwalarm.hlp"
                        --#HELPTAG 202
                        --#STATE  OPERATIONAL

	            ::= 202

binderyOpnReqtdByUsR  	TRAP-TYPE   --1.11.7.7/1.11.6.7.7
			ENTERPRISE      nwalarm-mib
			VARIABLES  {
                                        serverName,trapTime,userName,
					stationNumber
                                    }
			DESCRIPTION
                                "The user tried to open the bindery and
				 succeeded."
                        --#TYPE "System: Bindery opened, by user"
                        --#SUMMARY "Bindery open requested by user %s on "
			--#SUMMARY "station %d. Server %s opened bindery."
 	                --#ARGUMENTS {2,3,0}
                        --#SEVERITY INFORMATIONAL
                        --#TIMEINDEX 1
                        --#HELP "nwalarm.hlp"
                        --#HELPTAG 203
                        --#STATE  OPERATIONAL

	            ::= 203

binderyClosedBySrvr  	TRAP-TYPE   --1.11.7.8/1.11.6.7.8
			ENTERPRISE      nwalarm-mib
			VARIABLES  {
                                        serverName,trapTime
                                    }
			DESCRIPTION
                                "The server has closed the bindery."
                        --#TYPE "System: Bindery closed, by server"
                        --#SUMMARY "Bindery close requested by server %s."
 	                --#ARGUMENTS {0}
                        --#SEVERITY INFORMATIONAL
                        --#TIMEINDEX 1
                        --#HELP "nwalarm.hlp"
                        --#HELPTAG 204
                        --#STATE  NONOPERATIONAL

	         ::= 204

binderyClosedByUsr  	TRAP-TYPE   --1.11.7.9/1.11.6.7.9
			ENTERPRISE      nwalarm-mib
			VARIABLES  {
                                        serverName,trapTime,userName,
					stationNumber
                                    }
			DESCRIPTION
                                "The user has requested a bindery to be closed."
                        --#TYPE "System: Bindery closed, by user"
                        --#SUMMARY "Bindery close requested by user %s on "
			--#SUMMARY "station %d. Bindery was closed on server "
			--#SUMMARY "%s."
	                --#ARGUMENTS {2,3,0}
                        --#SEVERITY MINOR
                        --#TIMEINDEX 1
                        --#HELP "nwalarm.hlp"
                        --#HELPTAG 205
                        --#STATE  NONOPERATIONAL

	         ::= 205

--Bindery alert (un-encrypted passwd), use trap 140 of os

intruderLockout		TRAP-TYPE   --1.5.7.19/1.2.1.7.16
                        ENTERPRISE      nwalarm-mib
                        VARIABLES       {
                                        serverName,trapTime,accountName,
					networkAddress,macAddress
                                        }
                        DESCRIPTION
                                "User account temporarily disabled due to
				repeated login attempt with wrong password."
                        --#TYPE "User: Account disabled, temporarily"
                        --#SUMMARY "Server %s temporarily disabled "
			--#SUMMARY "account %s at address (%x:%x)."
 	                --#ARGUMENTS {0,2,3,4}
                        --#SEVERITY MINOR
                        --#TIMEINDEX 1
                        --#HELP "nwalarm.hlp"
                        --#HELPTAG 206
                        --#STATE  OPERATIONAL

                   ::= 206


--**************************Directory Services*****************************

dsOpenFailed  	TRAP-TYPE   --1.15.5.1
			ENTERPRISE      nwalarm-mib
			VARIABLES  {
                                      serverName,trapTime
                                    }
			DESCRIPTION
                                "Directory services database did not open."
                        --#TYPE "DS: Database open failed"
                        --#SUMMARY  "Directory services: Could not "
			--#SUMMARY  "open local database on server %s."
 	                --#ARGUMENTS {0}
                        --#SEVERITY MINOR
                        --#TIMEINDEX 1
                        --#HELP "nwalarm.hlp"
                        --#HELPTAG 207
                        --#STATE  NONOPERATIONAL

	         ::= 207

dsOpenFailedInconsistentDatabase TRAP-TYPE   --1.15.5.2
			ENTERPRISE      nwalarm-mib
			VARIABLES  {
                                      serverName,trapTime
                                     }
			DESCRIPTION
                                "Directory services database did not open due
				to inconsistent database."
                        --#TYPE "DS: Database inconsistent"
                        --#SUMMARY  "Directory services: Could not open local "
			--#SUMMARY  "database because it is inconsistent on "
			--#SUMMARY  "server %s. Try to correct with "
			--#SUMMARY "DSREPAIR.NLM."
 	                --#ARGUMENTS {0}
                        --#SEVERITY MINOR
                        --#TIMEINDEX 1
                        --#HELP "nwalarm.hlp"
                        --#HELPTAG 208
                        --#STATE  NONOPERATIONAL

	         ::= 208

dsopenSucceeded  	TRAP-TYPE   --1.15.7.4
			ENTERPRISE      nwalarm-mib
			VARIABLES  {
                                      serverName,trapTime
                                    }
			DESCRIPTION
                                "The directory services database was
				 successfully opened."
                        --#TYPE "DS: Database open"
                        --#SUMMARY  "Directory services: Local database is "
			--#SUMMARY  "open on server %s."
 	                --#ARGUMENTS {0}
                        --#SEVERITY MINOR
                        --#TIMEINDEX 1
                        --#HELP "nwalarm.hlp"
                        --#HELPTAG 209
                        --#STATE  OPERATIONAL

	         ::= 209

dsCloseSucceeded  	TRAP-TYPE   --1.15.7.5
			ENTERPRISE      nwalarm-mib
			VARIABLES  {
                                      serverName,trapTime
                                    }
			DESCRIPTION
                                "The directory services database was
				 successfully closed."
                        --#TYPE "DS: Database closed"
                        --#SUMMARY  "Directory services: Local database has "
			--#SUMMARY  "been closed on server %s."
 	                --#ARGUMENTS {0}
                        --#SEVERITY MINOR
                        --#TIMEINDEX 1
                        --#HELP "nwalarm.hlp"
                        --#HELPTAG 210
                        --#STATE  NONOPERATIONAL

	         ::= 210

--skulking Error covers ds alert on skulks 1-4.Pass the message string
--as parameter

skulkingError	  	TRAP-TYPE   --1.15.5.3
			ENTERPRISE      nwalarm-mib
			VARIABLES  {
                                      serverName,trapTime,errorNumber
                                    }
			DESCRIPTION
                                "Skulking error."
                        --#TYPE "DS: Skulking err"
                        --#SUMMARY  "Skulking error: %d on server %s."
 	                --#ARGUMENTS {2,0}
                        --#SEVERITY MINOR
                        --#TIMEINDEX 1
                        --#HELP "nwalarm.hlp"
                        --#HELPTAG 211
                        --#STATE  DEGRADED

	         ::= 211

--ds alert Server Open bindery, use bindery trap no.198
--ds alert User Open bindery, use bindery trap no.199
--ds alert Server Close bindery, use bindery trap no.200
--ds alert User Close bindery, use bindery trap no.201
--ds alert Intruder-lockout, use bindery trap no.202

dsIntruderNoAddr  	TRAP-TYPE   --1.15.5.5
			ENTERPRISE      nwalarm-mib
			VARIABLES  {
                                      serverName,trapTime,accountName
                                    }
			DESCRIPTION
                                "A user repeatedly tried to log in with an
				invalid password and the user's account was
				temporarily disabled by the supervisor.
				The address of the user was non-IPX."
                        --#TYPE "Security: Intruder lockout"
                        --#SUMMARY  "Server %s temporarily disabled account %s "
			--#SUMMARY  "due to repeated attempts to "
			--#SUMMARY  " login with a wrong password."
 	                --#ARGUMENTS {0,2}
                        --#SEVERITY MINOR
                        --#TIMEINDEX 1
                        --#HELP "nwalarm.hlp"
                        --#HELPTAG 212
                        --#STATE  OPERATIONAL
	         ::= 212

--*************************domain alerts*********************************

domainQuarantined	TRAP-TYPE   --1.1.3.5.8
                        ENTERPRISE      nwalarm-mib
                        VARIABLES       {
                                        serverName,trapTime,exceptionName,
					domainName,processName,nlmName,
					eipAddress
                                        }
                        DESCRIPTION
		       		"There was a protection violation in one of
				the NLMs in the OSP domain during execution.
				The NLM is quarantined."
                        --#TYPE "OS: Domain quarantined"
                        --#SUMMARY "Unhandled exception caused a "
			--#SUMMARY "domain to be quarantined on server %s. "
			--#SUMMARY "Exception: %s. Domain: %s. Process: %s. "
			--#SUMMARY "Module %s. EIP: %x."
	                --#ARGUMENTS {0,2,3,4,5,6}
                        --#SEVERITY MINOR
                        --#TIMEINDEX 1
                        --#HELP "nwalarm.hlp"
                        --#HELPTAG 213
                        --#STATE  DEGRADED
                       ::= 213

commandProcess		TRAP-TYPE   --1.1.3.5.9
                        ENTERPRISE      nwalarm-mib
                        VARIABLES       {
                                        serverName,trapTime
                                        }
                        DESCRIPTION
                                "The command processor faulted while loading
				 an NLM."
                        --#TYPE "System: Command processor faulted."
                        --#SUMMARY "Console Command Processor "
			--#SUMMARY "restarted after recovery on server %s."
                        --#ARGUMENTS {0}
                        --#SEVERITY MINOR
                        --#TIMEINDEX 1
                        --#HELP "nwalarm.hlp"
                        --#HELPTAG 214
                        --#STATE  DEGRADED
                       ::= 214

--*************************RSPX alerts*********************************

remoteConnGranted	TRAP-TYPE   --1.5.7.25
                        ENTERPRISE      nwalarm-mib
                        VARIABLES       {
                                        serverName,trapTime,networkAddress,
					macAddress
                                        }
                        DESCRIPTION
                                "A request to use a workstation console as a
				 file server console was granted."
                        --#TYPE "System: RCONSOLE connection granted"
                        --#SUMMARY "Server %s granted remote console "
			--#SUMMARY " connection for workstation %x:%x."
 	                --#ARGUMENTS {0,2,3}
                        --#SEVERITY INFORMATIONAL
                        --#TIMEINDEX 1
                        --#HELP "nwalarm.hlp"
                        --#HELPTAG 215
                        --#STATE  OPERATIONAL

                   ::= 215


remoteConnCleared	TRAP-TYPE   --1.5.7.26
                        ENTERPRISE      nwalarm-mib
                        VARIABLES       {
                                        serverName,trapTime,networkAddress,
					macAddress
                                        }
                        DESCRIPTION
                                "A request to clear the use of a workstation
				  console as a file server console was granted."
                        --#TYPE "System: RCONSOLE connection cleared"
                        --#SUMMARY "Server %s cleared remote console "
			--#SUMMARY " connection for workstation %x:%x."
 	                --#ARGUMENTS {0,2,3}
                        --#SEVERITY INFORMATIONAL
                        --#TIMEINDEX 1
                        --#HELP "nwalarm.hlp"
                        --#HELPTAG 216
                        --#STATE  OPERATIONAL

                   ::= 216

remoteConnRefused	TRAP-TYPE   --1.5.7.27
                        ENTERPRISE      nwalarm-mib
                        VARIABLES       {
                                        serverName,trapTime,networkAddress,
					macAddress
                                        }
                        DESCRIPTION
                                "A request to use the workstation console as a
				file server console was refused."
                        --#TYPE "System: RCONSOLE connection refused"
                        --#SUMMARY "Server %s refused remote connection "
			--#SUMMARY "request for workstation %x:%x."
 	                --#ARGUMENTS {0,2,3}
                        --#SEVERITY MINOR
                        --#TIMEINDEX 1
                        --#HELP "nwalarm.hlp"
                        --#HELPTAG 217
                        --#STATE  OPERATIONAL

                   ::= 217

--Alerts to indentify if the trap.nlm is loaded or not (probably
--generated by the SNMP agent


translatorUp            TRAP-TYPE
                        ENTERPRISE      nwalarm-mib
                        VARIABLES       {
	                                   serverName,trapTime
                                        }
                        DESCRIPTION
                                "The Trap NLM is loaded."
                        --#TYPE "System: Trap NLM loaded"
                        --#SUMMARY "Trap NLM loaded on server %s."
                        --#ARGUMENTS {0}
                        --#SEVERITY INFORMATIONAL
                        --#TIMEINDEX 1
                        --#HELP "nwalarm.hlp"
                        --#HELPTAG 218
                        --#STATE  OPERATIONAL
                        ::= 218

translatorDown          TRAP-TYPE
                        ENTERPRISE      nwalarm-mib
                        VARIABLES       {
	                                   serverName,trapTime
                                        }
                        DESCRIPTION
                                "The Trap NLM is being unloaded."

                        --#TYPE "System: Trap NLM unloaded"
                        --#SUMMARY "Trap NLM going down on server %s."
                        --#ARGUMENTS {0}
                        --#SEVERITY MINOR
                        --#TIMEINDEX 1
                        --#HELP "nwalarm.hlp"
                        --#HELPTAG 219
                        --#STATE  NONOPERATIONAL

                        ::= 219



--the following are alerts generated by OS using event report function


volAnyMounted		TRAP-TYPE   --1.6.1.7.18/1.2.5.7.36
                        ENTERPRISE      nwalarm-mib
                        VARIABLES       {
                                        serverName,trapTime,volumeName
                                        }
                        DESCRIPTION
                                "The server mounted the indicated volume
				 in response to a MOUNT command."
                        --#TYPE "FileSys: Vol mounted"
                        --#SUMMARY "Volume %s mounted on server %s."
 	                --#ARGUMENTS {2,0}
                        --#SEVERITY INFORMATIONAL
                        --#TIMEINDEX 1
                        --#HELP "nwalarm.hlp"
                        --#HELPTAG 220
                        --#STATE  OPERATIONAL

                   ::= 220


volAnyDismounted		TRAP-TYPE   --1.6.1.7.17/1.2.5.7.35
                        ENTERPRISE      nwalarm-mib
                        VARIABLES       {
                                        serverName,trapTime,volumeName
                                        }
                        DESCRIPTION
                                "The server dismounted the indicated volume
				 in response to a DISMOUNT command."
                        --#TYPE "FileSys: Vol dismounted"
                        --#SUMMARY "Volume %s dismounted on "
			--#SUMMARY "server %s."
 	                --#ARGUMENTS {2,0}
                        --#SEVERITY INFORMATIONAL
                        --#TIMEINDEX 1
                        --#HELP "nwalarm.hlp"
                        --#HELPTAG 221
                        --#STATE  DEGRADED

                   ::= 221


serverDownatServer	TRAP-TYPE  --1.7.13
			ENTERPRISE	nwalarm-mib
			VARIABLES 	{
                                        serverName,trapTime
					}
			DESCRIPTION
				"The server was downed at the server console."

                        --#TYPE "System: Server downed, at server console"
                        --#SUMMARY "File server %s is down. "
			--#SUMMARY "Connection terminated."
                        --#ARGUMENTS {0}
                        --#SEVERITY INFORMATIONAL
                        --#TIMEINDEX 1
                        --#HELP "nwalarm.hlp"
                        --#HELPTAG 222
                        --#STATE  NONOPERATIONAL

			::= 222


protocolBound		TRAP-TYPE   --1.9.2.7.4
                        ENTERPRISE      nwalarm-mib
                        VARIABLES       {
                                        serverName,trapTime,lanDriverName,
					boardNumber,protocolName
                                        }
                        DESCRIPTION
                                "A protocol stack has been bound to a
				LAN driver."
                        --#TYPE "Network: Protocol bound to driver"
                        --#SUMMARY "LAN driver %s (board # %d) is now bound "
			--#SUMMARY "to protocol %s stack on server %s."
 	                --#ARGUMENTS {2,3,4,0}
                        --#SEVERITY INFORMATIONAL
                        --#TIMEINDEX 1
                        --#HELP "nwalarm.hlp"
                        --#HELPTAG 223
			--#STATE OPERATIONAL

                   ::= 223

protocolUnBound		TRAP-TYPE   --1.9.2.7.5
                        ENTERPRISE      nwalarm-mib
                        VARIABLES       {
                                        serverName,trapTime,lanDriverName,
					boardNumber,protocolName
                                        }
                        DESCRIPTION
                                "A protocol stack has been unbound from
				 a LAN driver."
                        --#TYPE "Network: Protocol unbound from driver"
                        --#SUMMARY "LAN driver %s (board # %d) is now unbound "
			--#SUMMARY "from protocol %s stack on server %s."
 	                --#ARGUMENTS {2,3,4,0}
                        --#SEVERITY INFORMATIONAL
                        --#TIMEINDEX 1
                        --#HELP "nwalarm.hlp"
                        --#HELPTAG 224
			--#STATE NONOPERATIONAL

                   ::= 224



moduleLoad		TRAP-TYPE
                        ENTERPRISE      nwalarm-mib
                        VARIABLES       {
                                        serverName,trapTime,nlmName
                                        }
                        DESCRIPTION
                                "An NLM has been loaded."
                        --#TYPE "System: NLM loaded"
                        --#SUMMARY "%s NLM loaded on server %s."
 	                --#ARGUMENTS {2,0}
                        --#SEVERITY MINOR
                        --#TIMEINDEX 1
                        --#HELP "nwalarm.hlp"
                        --#HELPTAG 225
			--#STATE OPERATIONAL

                   ::= 225


moduleUnLoad		TRAP-TYPE
                        ENTERPRISE      nwalarm-mib
                        VARIABLES       {
                                        serverName,trapTime,nlmName
                                        }
                        DESCRIPTION
                                "An NLM has been unloaded."
                        --#TYPE "System: NLM unloaded"
                        --#SUMMARY "%s NLM unloaded on server %s."
 	                --#ARGUMENTS {2,0}
                        --#SEVERITY MINOR
                        --#TIMEINDEX 1
                        --#HELP "nwalarm.hlp"
                        --#HELPTAG 226
			--#STATE OPERATIONAL

                   ::= 226

mlidRegister		TRAP-TYPE
                        ENTERPRISE      nwalarm-mib
                        VARIABLES       {
                                        serverName,trapTime,boardNumber,
					lanDriverName
                                        }
                        DESCRIPTION
                                "MLID has registered a board."
                        --#TYPE "Network: MLID registered board"
                        --#SUMMARY "LAN board number %d registered "
			--#SUMMARY " with LAN driver %s on server %s."
 	                --#ARGUMENTS {2,3,0}
                        --#SEVERITY INFORMATIONAL
                        --#TIMEINDEX 1
                        --#HELP "nwalarm.hlp"
                        --#HELPTAG 227
			--#STATE OPERATIONAL

                   ::= 227

mlidUnRegister		TRAP-TYPE
                        ENTERPRISE      nwalarm-mib
                        VARIABLES       {
                                        serverName,trapTime,boardNumber,
					lanDriverName
                                        }
                        DESCRIPTION
                                "MLID has de-registered a board."
                        --#TYPE "Network: MLID de-registered"
                        --#SUMMARY "LAN board number %d de-registered "
			--#SUMMARY "from LAN driver %s on server %s."
 	                --#ARGUMENTS {2,3,0}
                        --#SEVERITY INFORMATIONAL
                        --#TIMEINDEX 1
                        --#HELP "nwalarm.hlp"
                        --#HELPTAG 228
			--#STATE NONOPERATIONAL

                   ::= 228

clearConnection		TRAP-TYPE
                        ENTERPRISE      nwalarm-mib
                        VARIABLES       {
                                        serverName,trapTime,userName,
					connectionNumber
                                        }
                        DESCRIPTION
                                "A user connection has been cleared."
                        --#TYPE "Connection: User connection cleared"
                        --#SUMMARY "User %s (connection #%d) "
			--#SUMMARY "logged out from server %s."
 	                --#ARGUMENTS {2,3,0}
                        --#SEVERITY INFORMATIONAL
                        --#TIMEINDEX 1
                        --#HELP "nwalarm.hlp"
                        --#HELPTAG 229
			--#STATE OPERATIONAL

                   ::= 229



loginConnection		TRAP-TYPE
                        ENTERPRISE      nwalarm-mib
                        VARIABLES       {
                                        serverName,trapTime,userName,
					connectionNumber
                                        }
                        DESCRIPTION
                                "A user has logged in."
                        --#TYPE "Connection: User logged in"
                        --#SUMMARY "User %s (connection #%d) "
			--#SUMMARY "logged into server %s."
 	                --#ARGUMENTS {2,3,0}
                        --#SEVERITY INFORMATIONAL
                        --#TIMEINDEX 1
                        --#HELP "nwalarm.hlp"
                        --#HELPTAG 230
			--#STATE OPERATIONAL

                   ::= 230


nlmAlertCritical                TRAP-TYPE  --1.5.18
                        ENTERPRISE      nwalarm-mib
                        VARIABLES       {
                                        serverName,trapTime,nlmName,
					nlmSeverity,message
                                        }
                        DESCRIPTION
                                "This trap will handle all traps being
				 generated by third-party NLMs and the
				 traps generated by driver NLMs written
				 by NOVELL or third party."

                        --#TYPE "NLM: Critical alert"
			--#SUMMARY "%s: '%s', severity=%d, server %s"
			--#ARGUMENTS {2,4,3,0}
                        --#SEVERITY CRITICAL
                        --#TIMEINDEX 1
                        --#HELP "nwalarm.hlp"
                        --#HELPTAG 231
                        --#STATE  OPERATIONAL

                        ::= 231


logoutConnection		TRAP-TYPE
                        ENTERPRISE      nwalarm-mib
                        VARIABLES       {
                                        serverName,trapTime,userName,
					connectionNumber
                                        }
                        DESCRIPTION
                                "A user has logged out."
                        --#TYPE "Connection: User logged out"
                        --#SUMMARY "User %s (connection #%d) "
			--#SUMMARY "logged out of server %s."
 	                --#ARGUMENTS {2,3,0}
                        --#SEVERITY INFORMATIONAL
                        --#TIMEINDEX 1
                        --#HELP "nwalarm.hlp"
                        --#HELPTAG 232
			--#STATE OPERATIONAL

                   ::= 232

usrAcctDeletedByAUsrSingleConn	TRAP-TYPE   --1.5.7.18
                        ENTERPRISE      nwalarm-mib
                        VARIABLES       {
                                        serverName,trapTime,accountName,
					userName,stationNumber
                                        }
                        DESCRIPTION
                                "A user account was deleted by another user.
				The deleted user was logged in at the time. "
                        --#TYPE "User: Account deleted, single connection"
                        --#SUMMARY "Account %s deleted by user %s on station "
			--#SUMMARY "%d. One active connection terminated on "
			--#SUMMARY "server %s."
	                --#ARGUMENTS {2,3,4,0}
                        --#SEVERITY CRITICAL
                        --#TIMEINDEX 1
                        --#HELP "nwalarm.hlp"
                        --#HELPTAG 233
			--#STATE OPERATIONAL
                   ::= 233



compErrReadZeroBytesOrig	TRAP-TYPE   --1.2.5.58
                        ENTERPRISE      nwalarm-mib
                        VARIABLES       {
                                        serverName,trapTime,volumeNumber,
					fileSize,fileName,fileOffset
                                        }
                        DESCRIPTION
				"The disk has returned 0 bytes for a
				compression read request and there is
				still more data to read."
                        --#TYPE "FileSys: Compression err, EOF on original"
                        --#SUMMARY "Compress error original, volume %d, "
			--#SUMMARY "size %d. Read beyond end of file %s at "
			--#SUMMARY "offset %d. Error occurred on server %s."
	                --#ARGUMENTS {2,3,4,5,0}
                        --#SEVERITY CRITICAL
                        --#TIMEINDEX 1
                        --#HELP "nwalarm.hlp"
                        --#HELPTAG 234
                        --#STATE  DEGRADED

                    ::= 234
--one more trap may be added for queue action
--Some of the traps in 3.11 and not covered by 4.00.


--In 4.0, there are many alerts concerning disk deactivation. The OS generates
--separate alert in each case. In 3.11, all the disk deactivation alerts are
--grouped into one and reason for each case is imbedded as a parameter in
-- the control string


diskDeactivated		TRAP-TYPE  --1.13.1.5.19/20/21/22/23/24/25/26/27/28/31
                        ENTERPRISE      nwalarm-mib
                        VARIABLES       {
                                        serverName,trapTime,diskName,
					reason
			  }
                        DESCRIPTION
                                "The specified disk was deactivated. Any
				of the following is a possible cause:
				a: deactivated by a console command.
				b: disk drive failure.
				c: driver unload.
				d: file system failure.
				e: wrong medium.
				f: end-of-medium.
				g: end-of-medium MINOR.
				h: unload command.
				i: dismount command.
				j: down command.   "

                        --#TYPE "Disk: Deactivated, cause specified"
                        --#SUMMARY "Disk %s deactivated due to %s on server %s."
                        --#ARGUMENTS {2,3,0}
                        --#SEVERITY CRITICAL
                        --#TIMEINDEX 1
                        --#HELP "nwalarm.hlp"
                        --#HELPTAG 235
                        --#STATE  DEGRADED
                        ::= 235

diskMounted		TRAP-TYPE  --1.13.1.7.30
                        ENTERPRISE      nwalarm-mib
                        VARIABLES       {
                                        serverName,trapTime,diskName
			  }
                        DESCRIPTION
				"The system mounted the specified
				removable disk at the user's request."
                        --#TYPE "Disk: Mounted"
                        --#SUMMARY "Disk %s mounted on server %s."
                        --#ARGUMENTS {2,0}
                        --#SEVERITY INFORMATIONAL
                        --#TIMEINDEX 1
                        --#HELP "nwalarm.hlp"
                        --#HELPTAG 236
                        --#STATE  OPERATIONAL
                        ::= 236

--following entry common between 3.11(os id nos 80,81)

redirectBlockMismatch	TRAP-TYPE  --1.13.1.7.29
                        ENTERPRISE      nwalarm-mib
                        VARIABLES       {
                                        serverName,trapTime,partitionNumber,
                                        numberOfPackets
                        		}
                        DESCRIPTION
				"The system detected a redirection block
				mismatch."
                        --#TYPE "Disk: Hotfix, redirection block mismatch"
                        --#SUMMARY "Redirection block mismatch detected "
			--#SUMMARY "on partition #%d device #%d on server %s."
                        --#ARGUMENTS {2,3,0}
                        --#SEVERITY INFORMATIONAL
                        --#TIMEINDEX 1
                        --#HELP "nwalarm.hlp"
                        --#HELPTAG 237
                        --#STATE  OPERATIONAL
                        ::= 237

shortTermMemoryLimitExceeded  	TRAP-TYPE   --1.12.1.5.8
			ENTERPRISE      nwalarm-mib
			VARIABLES  {
                                        serverName,trapTime,
					numberOfFailedMemoryAllocAttempts
                                     }
			DESCRIPTION
                                "Short-term memory requests are failing."
                        --#TYPE "Memory: Short term limit exceeded"
                        --#SUMMARY "Allocatable short-term requests exceeded "
			--#SUMMARY "configuration limit. %d short-term "
			--#SUMMARY "memory allocation requests failed on "
			--#SUMMARY "server %s."
 	                --#ARGUMENTS {2,0}
                        --#SEVERITY CRITICAL
                        --#TIMEINDEX 1
                        --#HELP "nwalarm.hlp"
                        --#HELPTAG 238
                        --#STATE  DEGRADED
	         	::= 238

semipermanentMemoryExhausted  	TRAP-TYPE   --1.12.2.5.1
			ENTERPRISE      nwalarm-mib
			VARIABLES  {
                                        serverName,trapTime
                                     }
			DESCRIPTION
                                "Semi-permanent memory exhausted."
                        --#TYPE "Memory: Semi-permanent memory exhausted"
                        --#SUMMARY "Semi-permanent memory exhausted "
			--#SUMMARY "on server %s."
 	                --#ARGUMENTS {0}
                        --#SEVERITY CRITICAL
                        --#TIMEINDEX 1
                        --#HELP "nwalarm.hlp"
                        --#HELPTAG 239
                        --#STATE  DEGRADED
	         	::= 239

diskDismounted		TRAP-TYPE  --1.13.1.7.31
                        ENTERPRISE      nwalarm-mib
                        VARIABLES       {
                                        serverName,trapTime,diskName
			  }
                        DESCRIPTION
				"The system mounted the specified
				removable disk at the user's request."
                        --#TYPE "Disk: Dismounted"
                        --#SUMMARY "Disk %s dismounted on server %s."
                        --#ARGUMENTS {2,0}
                        --#SEVERITY INFORMATIONAL
                        --#TIMEINDEX 1
                        --#HELP "nwalarm.hlp"
                        --#HELPTAG 240
                        --#STATE  OPERATIONAL
                        ::= 240

--following trap entry is common for 3.11(OS id nos 9,11)


diskAdded		TRAP-TYPE  --1.13.7.4
                        ENTERPRISE      nwalarm-mib
                        VARIABLES       {
                                        serverName,trapTime,diskName
				  }
                        DESCRIPTION
				"The specified hard disk has been added to the
				operating system"
                        --#TYPE "Disk: Added"
                        --#SUMMARY "Hard disk %s added on server %s."
                        --#ARGUMENTS {2,0}
                        --#SEVERITY INFORMATIONAL
                        --#TIMEINDEX 1
                        --#HELP "nwalarm.hlp"
                        --#HELPTAG 241
                        --#STATE  OPERATIONAL
                        ::= 241

diskActivated		TRAP-TYPE  --1.13.1.7.2
                        ENTERPRISE      nwalarm-mib
                        VARIABLES       {
                                        serverName,trapTime,diskName
				  }
                        DESCRIPTION
				"The specified hard disk has been activated at
				the user's request."
                        --#TYPE "Disk: Activated"
                        --#SUMMARY "Hard disk %s activated on server %s."
                        --#ARGUMENTS {2,0}
                        --#SEVERITY INFORMATIONAL
                        --#TIMEINDEX 1
                        --#HELP "nwalarm.hlp"
                        --#HELPTAG 242
                        --#STATE  OPERATIONAL
                        ::= 242


generalTTSfailures   	TRAP-TYPE  --1.2.2.1.7.11/1.2.2.1.7.5
                        ENTERPRISE      nwalarm-mib
                        VARIABLES       {
                                        serverName,trapTime,message
				  }
                        DESCRIPTION
				"TTS was disabled due to one of the
				following reasons:
				- disabled by operator,
				- error reading TTS file during backout,
				- error writing to file during backout,
				- too many defined volumes,
				- error writing volume information to TTS file,
				- error reading TTS file during record
				generation,
				- error growing TTS tables,
				- error allocating new space for the TTS
				backout file,
				- error writing directory information for the
				 TTS backout file.
                                "
                        --#TYPE "TTS: Disabled, for reason"
                        --#SUMMARY "%s: %s."
                        --#ARGUMENTS {0,2}
                        --#SEVERITY CRITICAL
                        --#TIMEINDEX 1
                        --#HELP "nwalarm.hlp"
                        --#HELPTAG 243
                        --#STATE  DEGRADED
                        ::= 243

mirroredPartNotAllSynced TRAP-TYPE   --1.2.7.28
                        ENTERPRISE      nwalarm-mib
                        VARIABLES       {
                                        serverName,trapTime
                                        }
                        DESCRIPTION
                                "The system has not mirrored all system
				 partitions that are designated as mirrored
				 partitions."
                        --#TYPE "Disk: Partitions not synchronized"
                        --#SUMMARY "Mirrored partitions on this system "
			--#SUMMARY "are not all synchronized on server %s."
 	                --#ARGUMENTS {0}
                        --#SEVERITY CRITICAL
                        --#TIMEINDEX 1
                        --#HELP "nwalarm.hlp"
                        --#HELPTAG 244
			--#STATE DEGRADED
	            ::= 244

reqtdRtrReset311	TRAP-TYPE   --1.9.7.7
                        ENTERPRISE      nwalarm-mib
                        VARIABLES       {
                                        serverName,trapTime
                                        }
                        DESCRIPTION
                                "A workstation issued a router reset command
				  to a server."
                        --#TYPE "Router: Reset, dynamic"
                        --#SUMMARY "Dynamic router reset requested "
			--#SUMMARY "on file server %s."
 	                --#ARGUMENTS {0}
                        --#SEVERITY INFORMATIONAL
                        --#TIMEINDEX 1
                        --#HELP "nwalarm.hlp"
                        --#HELPTAG 245
                        --#STATE  OPERATIONAL
                   ::= 245




invalidSignatureString	 TRAP-TYPE  --1.5.7
                        ENTERPRISE      nwalarm-mib
                        VARIABLES       {
                                        serverName,trapTime,userName,
					networkAddress,macAddress
			  }
                        DESCRIPTION
				"The system detected an NCP packet with
				 invalid signature."
                        --#TYPE "Security: Invalid signature #2"
                        --#SUMMARY "NCP request with an invalid security "
			--#SUMMARY "signature received from user %s at "
			--#SUMMARY "%x:%x by server %s. "
			--#SUMMARY "Possible intruder or network corruption."
                        --#ARGUMENTS {2,3,4,0}
                        --#SEVERITY MINOR
                        --#TIMEINDEX 1
                        --#HELP "nwalarm.hlp"
                        --#HELPTAG 246
                        --#STATE  OPERATIONAL
                        ::= 246

invalidDuplicateSignature	 TRAP-TYPE  --1.5.8
                        ENTERPRISE      nwalarm-mib
                        VARIABLES       {
                                        serverName,trapTime,userName,
					networkAddress,macAddress
			  }
                        DESCRIPTION
				"The system detected a duplicate NCP packet
				 that was different from the original packet."
                        --#TYPE "Security: Duplicate but different NCP received"
                        --#SUMMARY "Server %s received a duplicate NCP request "
			--#SUMMARY "different from the original request from "
			--#SUMMARY " user %s at address %x:%x. Possible "
			--#SUMMARY "intruder or request corruption at client."
                        --#ARGUMENTS {0,2,3,4}
                        --#SEVERITY MINOR
                        --#TIMEINDEX 1
                        --#HELP "nwalarm.hlp"
                        --#HELPTAG 247
                        --#STATE  OPERATIONAL
                        ::= 247

invalidPburstSignature	 TRAP-TYPE  --1.5.9
                        ENTERPRISE      nwalarm-mib
                        VARIABLES       {
                                        serverName,trapTime,userName,
					networkAddress,macAddress
			  }
                        DESCRIPTION
				"The system received an NCP packet burst
				request with an invalid security signature."
                        --#TYPE "Security: Invalid packet burst signature"
                        --#SUMMARY "Server %s received an NCP packet burst "
			--#SUMMARY "request with invalid signature from "
			--#SUMMARY "user %s at address %x:%x. Possible "
			--#SUMMARY "intruder or network corruption."
                        --#ARGUMENTS {0,2,3,4}
                        --#SEVERITY MINOR
                        --#TIMEINDEX 1
                        --#HELP "nwalarm.hlp"
                        --#HELPTAG 248
                        --#STATE  OPERATIONAL
                        ::= 248

--Some of 4.00 alerts not included in the earlier trap mib


failedToDeleteMigrateFile	TRAP-TYPE   --1.2.8.5.7
                        ENTERPRISE      nwalarm-mib
                        VARIABLES       {
                                        serverName,trapTime,volumeName,
					pathFileName
                                        }
                        DESCRIPTION
				"The system tried to delete a migrated file
				but failed because it was unable to obtain
				directory table space or memory."
                        --#TYPE "FileSys: Failed to delete migrated file"
                        --#SUMMARY "DeleteFileToLimbo failed, unable to save "
			--#SUMMARY "migrated file (%s:%s) on server %s."
	                --#ARGUMENTS {2,3,0}
                        --#SEVERITY CRITICAL
                        --#TIMEINDEX 1
                        --#HELP "nwalarm.hlp"
                        --#HELPTAG 249
                        --#STATE  DEGRADED

                    ::= 249

--RSPX alerts


unsignedRemoteConnectionRefused		TRAP-TYPE   --1.5.7.30
                        ENTERPRISE      nwalarm-mib
                        VARIABLES       {
                                        serverName,trapTime,networkAddress,
					macAddress
                                        }
                        DESCRIPTION
				"A request to use the workstation console as a
				file server console was refused. The packet
				did not have a signature."
                        --#TYPE "Security: Unsigned remote connection refused"
                        --#SUMMARY "Unsigned remote console connection "
			--#SUMMARY "refused for %x:%x by server %s."
	                --#ARGUMENTS {2,3,0}
                        --#SEVERITY INFORMATIONAL
                        --#TIMEINDEX 1
                        --#HELP "nwalarm.hlp"
                        --#HELPTAG 250
                        --#STATE  OPERATIONAL

                    ::= 250

unsignedRemoteConnectionGranted		TRAP-TYPE   --1.5.7.31
                        ENTERPRISE      nwalarm-mib
                        VARIABLES       {
                                        serverName,trapTime,networkAddress,
					macAddress
                                        }
                        DESCRIPTION
				"A request to use the workstation console as a
				file server console was granted. The packet
				did not have a signature."
                        --#TYPE "Security: Unsigned remote connection granted"
                        --#SUMMARY "Unsigned remote console connection "
			--#SUMMARY "granted for %x:%x by server %s."
	                --#ARGUMENTS {2,3,0}
                        --#SEVERITY INFORMATIONAL
                        --#TIMEINDEX 1
                        --#HELP "nwalarm.hlp"
                        --#HELPTAG 251
                        --#STATE  OPERATIONAL

                    ::= 251

--Remote alerts

responsePacketNotAllocated	TRAP-TYPE   --1.5.7.32
                        ENTERPRISE      nwalarm-mib
                        VARIABLES       {
                                        serverName,trapTime
                                        }
                        DESCRIPTION
				"More responses were present from
				workstations than there were buffers
				to hold them. "
                        --#TYPE "Network: Response packet dropped"
                        --#SUMMARY "Response buffer could not be found "
			--#SUMMARY "for workstation response delivery by "
			--#SUMMARY "server %s."
	                --#ARGUMENTS {0}
                        --#SEVERITY INFORMATIONAL
                        --#TIMEINDEX 1
                        --#HELP "nwalarm.hlp"
                        --#HELPTAG 252
                        --#STATE  OPERATIONAL

                    ::= 252

wsNotLocated		TRAP-TYPE   --1.5.7.33
                        ENTERPRISE      nwalarm-mib
                        VARIABLES       {
                                        serverName,trapTime
                                        }
                        DESCRIPTION
				"A response was received from a remote
				 workstation, but it did not apply to
				this connection. "
                        --#TYPE "Network: Workstation not located"
                        --#SUMMARY "Workstation response could not be "
			--#SUMMARY "located on server %s."
	                --#ARGUMENTS {0}
                        --#SEVERITY INFORMATIONAL
                        --#TIMEINDEX 1
                        --#HELP "nwalarm.hlp"
                        --#HELPTAG 253
                        --#STATE  OPERATIONAL

                    ::= 253

--RS232 alerts

remoteConnectionTimedOut	TRAP-TYPE   --1.5.7.34
                        ENTERPRISE      nwalarm-mib
                        VARIABLES       {
                                        serverName,trapTime,userName
                                        }
                        DESCRIPTION
				"The system watchdog timed out the remote
				 connection."
                        --#TYPE "Async: Connection timed-out"
                        --#SUMMARY "Remote console connection timed out "
			--#SUMMARY "for %s on server %s."
	                --#ARGUMENTS {2,0}
                        --#SEVERITY INFORMATIONAL
                        --#TIMEINDEX 1
                        --#HELP "nwalarm.hlp"
                        --#HELPTAG 254
                        --#STATE  OPERATIONAL

                    ::= 254

modemConnectionCleared	TRAP-TYPE   --1.5.7.35
                        ENTERPRISE      nwalarm-mib
                        VARIABLES       {
                                        serverName,trapTime
                                        }
                        DESCRIPTION
				"Since the remote partner was gone,
				 the modem connection was cleared. "
                        --#TYPE "Async: Modem connection cleared"
                        --#SUMMARY "Modem connection cleared on server %s. "
	                --#ARGUMENTS {0}
                        --#SEVERITY INFORMATIONAL
                        --#TIMEINDEX 1
                        --#HELP "nwalarm.hlp"
                        --#HELPTAG 255
                        --#STATE  OPERATIONAL

                    ::= 255

remoteConnectionClearedNameKnown	TRAP-TYPE   --1.5.7.36
                        ENTERPRISE      nwalarm-mib
                        VARIABLES       {
                                        serverName,trapTime,userName
                                        }
                        DESCRIPTION
				"The remote connection permission granted
				 earlier has been cleared."
                        --#TYPE "Async: Connection cleared"
                        --#SUMMARY "Remote connection cleared for %s "
			--#SUMMARY "on server %s."
	                --#ARGUMENTS {2,0}
                        --#SEVERITY INFORMATIONAL
                        --#TIMEINDEX 1
                        --#HELP "nwalarm.hlp"
                        --#HELPTAG 256
                        --#STATE  OPERATIONAL

                    ::= 256


callBackNumberNotReceived	TRAP-TYPE   --1.5.7.37
                        ENTERPRISE      nwalarm-mib
                        VARIABLES       {
                                        serverName,trapTime
                                        }
                        DESCRIPTION
				"A workstation tried to connect to a server
				 through a modem but failed. "
                        --#TYPE "Async: Call-back # not received"
                        --#SUMMARY "Call-back # not received. "
			--#SUMMARY "NLM unable to reconnect to server "
			--#SUMMARY "%s. "
	                --#ARGUMENTS {0}
                        --#SEVERITY INFORMATIONAL
                        --#TIMEINDEX 1
                        --#HELP "nwalarm.hlp"
                        --#HELPTAG 257
                        --#STATE  OPERATIONAL

                    ::= 257

nlmUnableToOpenListFile	TRAP-TYPE   --1.5.7.38
                        ENTERPRISE      nwalarm-mib
                        VARIABLES       {
                                        serverName,trapTime
                                        }
                        DESCRIPTION
				"The call-back option has been enabled, but
				 the call-back list file,
				 SYS:SYSTEM\CALLBACK.LST, could not be opened."
                        --#TYPE "Async: Call-back file open err"
                        --#SUMMARY "NLM unable to open the "
			--#SUMMARY "call-back list file on server %s. "
	                --#ARGUMENTS {0}
                        --#SEVERITY INFORMATIONAL
                        --#TIMEINDEX 1
                        --#HELP "nwalarm.hlp"
                        --#HELPTAG 258
                        --#STATE  OPERATIONAL

                    ::= 258

nlmUnableToReadListFile	TRAP-TYPE   --1.5.7.39
                        ENTERPRISE      nwalarm-mib
                        VARIABLES       {
                                        serverName,trapTime
                                        }
                        DESCRIPTION
				"The call-back option has been enabled, but
				 the call-back list file,
				 SYS:SYSTEM\CALLBACK.LST, could not be read."
                        --#TYPE "Async: Call-back file read err"
                        --#SUMMARY "NLM unable to read the "
			--#SUMMARY "call-back list file on server %s. "
	                --#ARGUMENTS {0}
                        --#SEVERITY INFORMATIONAL
                        --#TIMEINDEX 1
                        --#HELP "nwalarm.hlp"
                        --#HELPTAG 259
                        --#STATE  OPERATIONAL

                    ::= 259

unauthorizedCallBackNumber	TRAP-TYPE   --1.5.7.40
                        ENTERPRISE      nwalarm-mib
                        VARIABLES       {
                                        serverName,trapTime,callBackNumber
                                        }
                        DESCRIPTION
				"The call-back option has been enabled,
				 but the call-back list file,
				SYS:SYSTEM\CALLBACK.LST, does not contain
				 the number that was sent from the remote
				 workstation. "
                        --#TYPE "Async: Call-back # unauthorized"
                        --#SUMMARY "Number %s is an unauthorized "
			--#SUMMARY "call-back number on server %s."
	                --#ARGUMENTS {2,0}
                        --#SEVERITY INFORMATIONAL
                        --#TIMEINDEX 1
                        --#HELP "nwalarm.hlp"
                        --#HELPTAG 260
                        --#STATE  OPERATIONAL

                    ::= 260

modemClearedAndCallBackAttempted	TRAP-TYPE   --1.5.7.41
                        ENTERPRISE      nwalarm-mib
                        VARIABLES       {
                                        serverName,trapTime
                                        }
                        DESCRIPTION
				"The connection with modem has been cleared.
				 The server will now attempt to call back the
				 number."
                        --#TYPE "Async: Modem cleared, call-back attempted"
                        --#SUMMARY "Modem connection cleared and call-back "
			--#SUMMARY "now attempted on server %s."
	                --#ARGUMENTS {0}
                        --#SEVERITY INFORMATIONAL
                        --#TIMEINDEX 1
                        --#HELP "nwalarm.hlp"
                        --#HELPTAG 261
                        --#STATE  OPERATIONAL

                    ::= 261

attmptngToEstblshCallBckConnectn	TRAP-TYPE   --1.5.7.42
                        ENTERPRISE      nwalarm-mib
                        VARIABLES       {
                                        serverName,trapTime,callBackNumber
                                        }
                        DESCRIPTION
				"The server is trying to call-back the number
				 given to it during the modem connection
				 process."
                        --#TYPE "Async: Call-back attempted"
                        --#SUMMARY "Attempting to establish call-back "
			--#SUMMARY "connection %s on server %s."
	                --#ARGUMENTS {2,0}
                        --#SEVERITY INFORMATIONAL
                        --#TIMEINDEX 1
                        --#HELP "nwalarm.hlp"
                        --#HELPTAG 262
                        --#STATE  OPERATIONAL

                    ::= 262

remoteConnectionRefusedNameKnown	TRAP-TYPE   --1.5.7.43
                        ENTERPRISE      nwalarm-mib
                        VARIABLES       {
                                        serverName,trapTime,userName
                                        }
                        DESCRIPTION
				"Request for a remote connection was refused. "
                        --#TYPE "Async: Connection refused"
                        --#SUMMARY "Remote connection refused for %s "
			--#SUMMARY "on server %s."
	                --#ARGUMENTS {2,0}
                        --#SEVERITY INFORMATIONAL
                        --#TIMEINDEX 1
                        --#HELP "nwalarm.hlp"
                        --#HELPTAG 263
                        --#STATE  OPERATIONAL

                    ::= 263

remoteConnectionGrantedNameKnown	TRAP-TYPE   --1.5.7.44
                        ENTERPRISE      nwalarm-mib
                        VARIABLES       {
                                        serverName,trapTime,userName
                                        }
                        DESCRIPTION
				"Request for a remote connection was granted. "
                        --#TYPE "Async: Connection granted"
                        --#SUMMARY "Remote connection granted for %s "
			--#SUMMARY "on server %s."
	                --#ARGUMENTS {2,0}
                        --#SEVERITY INFORMATIONAL
                        --#TIMEINDEX 1
                        --#HELP "nwalarm.hlp"
                        --#HELPTAG 264
                        --#STATE  OPERATIONAL

                    ::= 264

modemConnectionEstablished	TRAP-TYPE   --1.5.7.45
                        ENTERPRISE      nwalarm-mib
                        VARIABLES       {
                                        serverName,trapTime,baudRate
                                        }
                        DESCRIPTION
				"The modem connection has been established
				 at a particular baud rate."
                        --#TYPE "Async: Modem connection established"
                        --#SUMMARY "Modem connection established at %s baud "
			--#SUMMARY "on server %s."
	                --#ARGUMENTS {2,0}
                        --#SEVERITY INFORMATIONAL
                        --#TIMEINDEX 1
                        --#HELP "nwalarm.hlp"
                        --#HELPTAG 265
                        --#STATE  OPERATIONAL

                    ::= 265

--ds audit alerts

dsAuditFileWriteError	TRAP-TYPE   --1.15.5.9
                        ENTERPRISE      nwalarm-mib
                        VARIABLES       {
                                        serverName,trapTime,objectName
                                        }
                        DESCRIPTION
				"The operating system encountered an error
				when attempting to write to the audit file."
                        --#TYPE "AuditDS: File write error"
                        --#SUMMARY "DS audit file write error, %s on server %s."
	                --#ARGUMENTS {2,0}
                        --#SEVERITY MINOR
                        --#TIMEINDEX 1
                        --#HELP "nwalarm.hlp"
                        --#HELPTAG 266
                        --#STATE  OPERATIONAL

                    ::= 266

dsAuditFileFull		TRAP-TYPE   --1.15.5.10
                        ENTERPRISE      nwalarm-mib
                        VARIABLES       {
                                        serverName,trapTime,objectName
                                        }
                        DESCRIPTION
				"The operating system filled up the audit
				file when it wrote an audit record."
			--#TYPE "AuditDS: File full"
                        --#SUMMARY "DS audit file full, %s on server %s. "
	                --#ARGUMENTS {2,0}
                        --#SEVERITY MINOR
                        --#TIMEINDEX 1
                        --#HELP "nwalarm.hlp"
                        --#HELPTAG 267
                        --#STATE  OPERATIONAL

                    ::= 267

dsAuditFileThresholdOverflow	TRAP-TYPE   --1.15.5.11
                        ENTERPRISE      nwalarm-mib
                        VARIABLES       {
                                        serverName,trapTime,objectName
                                        }
                        DESCRIPTION
				"The operating system encountered a MINOR
				threshold level for the volume when writing
				an audit record."
			--#TYPE "AuditDS: Threshold overflow"
                        --#SUMMARY "DS audit file threshold overflow, %s "
			--#SUMMARY "on server %s."
	                --#ARGUMENTS {2,0}
                        --#SEVERITY MINOR
                        --#TIMEINDEX 1
                        --#HELP "nwalarm.hlp"
                        --#HELPTAG 268
                        --#STATE  OPERATIONAL

                    ::= 268


dsAuditMemoryAllocation	TRAP-TYPE   --1.15.5.12
                        ENTERPRISE      nwalarm-mib
                        VARIABLES       {
                                        serverName,trapTime
                                        }
                        DESCRIPTION
				"The operating system ran out of memory when
				it started up auditing while mounting a
				volume."
			--#TYPE "AuditDS: Out of memory"
                        --#SUMMARY "DS auditing memory allocation error "
			--#SUMMARY "on server %s."
	                --#ARGUMENTS {0}
                        --#SEVERITY MINOR
                        --#TIMEINDEX 1
                        --#HELP "nwalarm.hlp"
                        --#HELPTAG 269
                        --#STATE  OPERATIONAL

                    ::= 269
serverUp		TRAP-TYPE
                        ENTERPRISE      nwalarm-mib
                        VARIABLES       {
                                        serverName,trapTime
                                        }
                        DESCRIPTION
                      		"NetWare Server up."
                  	--#TYPE "System: Server up"
                  	--#SUMMARY "NetWare server %s has just been brought up."
	                --#ARGUMENTS {0}
                        --#SEVERITY INFORMATIONAL
                        --#TIMEINDEX 1
                        --#HELP "nwalarm.hlp"
                        --#HELPTAG 270
                        --#STATE  OPERATIONAL

                    ::= 270

-- os alert

volRestrictedSpace	TRAP-TYPE
                        ENTERPRISE      nwalarm-mib
                        VARIABLES       {
                                        serverName,trapTime,volumeName,
                                        volumePercentage
                                        }
                        DESCRIPTION
                      		"EA restricted space limit was reached
                                on a particualr volume"
                  	--#TYPE "FileSys: EA restricted space limit"
                  	--#SUMMARY "Volume %s, EA restricted space limit reached"
                        --#SUMMARY " (%d%%) on NetWare server %s."
	                --#ARGUMENTS {2,3,0}
                        --#SEVERITY INFORMATIONAL
                        --#TIMEINDEX 1
                        --#HELP "nwalarm.hlp"
                        --#HELPTAG 271
                        --#STATE  OPERATIONAL

                    ::= 271

-- timesync alerts

cannotInitialize	TRAP-TYPE
                        ENTERPRISE      nwalarm-mib
                        VARIABLES       {
                                        serverName,trapTime
                                        }
                        DESCRIPTION
                      		"Time synchronization not initialized"
                  	--#TYPE "TimeSync: Not initialized"
                  	--#SUMMARY "TIMESYNC NLM:  Cannot initialize time"
                        --#SUMMARY " synchronization on NetWare server %s."
	                --#ARGUMENTS {0}
                        --#SEVERITY CRITICAL
                        --#TIMEINDEX 1
                        --#HELP "nwalarm.hlp"
                        --#HELPTAG 272
                        --#STATE  OPERATIONAL

                    ::= 272

cannotStart     	TRAP-TYPE
                        ENTERPRISE      nwalarm-mib
                        VARIABLES       {
                                        serverName,trapTime
                                        }
                        DESCRIPTION
                      		"Time synchronization not started"
                  	--#TYPE "TimeSync: Not started"
                  	--#SUMMARY "TIMESYNC NLM:  Cannot start time"
                        --#SUMMARY "synchronization on NetWare server %s."
	                --#ARGUMENTS {0}
                        --#SEVERITY CRITICAL
                        --#TIMEINDEX 1
                        --#HELP "nwalarm.hlp"
                        --#HELPTAG 273
                        --#STATE  OPERATIONAL

                    ::= 273

noSAPSocketTag     	TRAP-TYPE
                        ENTERPRISE      nwalarm-mib
                        VARIABLES       {
                                        serverName,trapTime
                                        }
                        DESCRIPTION
                      		"SAP socket tag not allocated"
                  	--#TYPE "TimeSync: No SAP socket tag"
                  	--#SUMMARY "Cannot allocate SAP Socket tag"
                        --#SUMMARY "on NetWare server %s."
	                --#ARGUMENTS {0}
                        --#SEVERITY INFORMATIONAL
                        --#TIMEINDEX 1
                        --#HELP "nwalarm.hlp"
                        --#HELPTAG 274
                        --#STATE  OPERATIONAL

                    ::= 274

noSAPSocket     	TRAP-TYPE
                        ENTERPRISE      nwalarm-mib
                        VARIABLES       {
                                        serverName,trapTime
                                        }
                        DESCRIPTION
                      		"SAP socket not opened"
                  	--#TYPE "TimeSync: No SAP socket"
                  	--#SUMMARY "TIMESYNC NLM:  Cannot open SAP"
                        --#SUMMARY "socket on NetWare server %s."
	                --#ARGUMENTS {0}
                        --#SEVERITY INFORMATIONAL
                        --#TIMEINDEX 1
                        --#HELP "nwalarm.hlp"
                        --#HELPTAG 275
                        --#STATE  OPERATIONAL

                    ::= 275

noSetableParameterTag     	TRAP-TYPE
                        ENTERPRISE      nwalarm-mib
                        VARIABLES       {
                                        serverName,trapTime
                                        }
                        DESCRIPTION
                      		"Settable parameter tag not allocated"
                  	--#TYPE "TimeSync: No settable parameter tag"
                  	--#SUMMARY "TIMESYNC NLM:  Cannot allocate setable "
                        --#SUMMARY "parameters tag on NetWare server %s."
	                --#ARGUMENTS {0}
                        --#SEVERITY INFORMATIONAL
                        --#TIMEINDEX 1
                        --#HELP "nwalarm.hlp"
                        --#HELPTAG 276
                        --#STATE  OPERATIONAL

                    ::= 276

noTimerTag           	TRAP-TYPE
                        ENTERPRISE      nwalarm-mib
                        VARIABLES       {
                                        serverName,trapTime
                                        }
                        DESCRIPTION
                      		"Time tag not allocated"
                  	--#TYPE "TimeSync: No timer tag"
                  	--#SUMMARY "TIMESYNC NLM:  Cannot allocate timer"
                        --#SUMMARY "tag on NetWare server %s."
	                --#ARGUMENTS {0}
                        --#SEVERITY INFORMATIONAL
                        --#TIMEINDEX 1
                        --#HELP "nwalarm.hlp"
                        --#HELPTAG 277
                        --#STATE  OPERATIONAL

                    ::= 277

noAllocTag           	TRAP-TYPE
                        ENTERPRISE      nwalarm-mib
                        VARIABLES       {
                                        serverName,trapTime
                                        }
                        DESCRIPTION
                      		"Alloc tag not allocated"
                  	--#TYPE "TimeSync: No alloc tag"
                  	--#SUMMARY "TIMESYNC NLM: Cannot allocate alloc"
                        --#SUMMARY "tag on NetWare server %s."
	                --#ARGUMENTS {0}
                        --#SEVERITY INFORMATIONAL
                        --#TIMEINDEX 1
                        --#HELP "nwalarm.hlp"
                        --#HELPTAG 278
                        --#STATE  OPERATIONAL

                    ::= 278

noResourceTag     	TRAP-TYPE
                        ENTERPRISE      nwalarm-mib
                        VARIABLES       {
                                        serverName,trapTime
                                        }
                        DESCRIPTION
                      		"Resource Tag not allocated"
                  	--#TYPE "TimeSync: No resource tag"
                  	--#SUMMARY "TIMESYNC NLM:  Cannot allocate NCP"
                        --#SUMMARY "resource tag on NetWare server %s."
	                --#ARGUMENTS {0}
                        --#SEVERITY INFORMATIONAL
                        --#TIMEINDEX 1
                        --#HELP "nwalarm.hlp"
                        --#HELPTAG 279
                        --#STATE  OPERATIONAL

                    ::= 279

noProcessTag     	TRAP-TYPE
                        ENTERPRISE      nwalarm-mib
                        VARIABLES       {
                                        serverName,trapTime
                                        }
                        DESCRIPTION
                      		"Process Tag not allocated"
                  	--#TYPE "TimeSync: No process tag"
                  	--#SUMMARY "TIMESYNC NLM:  Cannot allocate process"
                        --#SUMMARY "tag on NetWare server %s."
	                --#ARGUMENTS {0}
                        --#SEVERITY INFORMATIONAL
                        --#TIMEINDEX 1
                        --#HELP "nwalarm.hlp"
                        --#HELPTAG 280
                        --#STATE  OPERATIONAL

                    ::= 280

noEventTag           	TRAP-TYPE
                        ENTERPRISE      nwalarm-mib
                        VARIABLES       {
                                        serverName,trapTime
                                        }
                        DESCRIPTION
                      		"Event tag not allocated"
                  	--#TYPE "TimeSync: No event tag"
                  	--#SUMMARY "TIMESYNC NLM: Cannot allocate event"
                        --#SUMMARY "tag on NetWare server %s."
	                --#ARGUMENTS {0}
                        --#SEVERITY INFORMATIONAL
                        --#TIMEINDEX 1
                        --#HELP "nwalarm.hlp"
                        --#HELPTAG 281
                        --#STATE  OPERATIONAL

                    ::= 281


noGlobalInfo           	TRAP-TYPE
                        ENTERPRISE      nwalarm-mib
                        VARIABLES       {
                                        serverName,trapTime
                                        }
                        DESCRIPTION
                      		"Global information not initialized"
                  	--#TYPE "TimeSync: No global information"
                  	--#SUMMARY "TIMESYNC NLM: Cannot initialize global"
                        --#SUMMARY "information on NetWare server %s."
	                --#ARGUMENTS {0}
                        --#SEVERITY INFORMATIONAL
                        --#TIMEINDEX 1
                        --#HELP "nwalarm.hlp"
                        --#HELPTAG 282
                        --#STATE  OPERATIONAL

                    ::= 282

noParseCommandLine        	TRAP-TYPE
                        ENTERPRISE      nwalarm-mib
                        VARIABLES       {
                                        serverName,trapTime
                                        }
                        DESCRIPTION
                      		"Command line arguments not parsed"
                  	--#TYPE "TimeSync: No command line"
                  	--#SUMMARY "TIMESYNC NLM: Cannot parse load command"
                        --#SUMMARY " line arguments on NetWare server %s."
	                --#ARGUMENTS {0}
                        --#SEVERITY INFORMATIONAL
                        --#TIMEINDEX 1
                        --#HELP "nwalarm.hlp"
                        --#HELPTAG 283
                        --#STATE  OPERATIONAL

                    ::= 283

noTimeSyncNCPVariable         TRAP-TYPE
                        ENTERPRISE      nwalarm-mib
                        VARIABLES       {
                                        serverName,trapTime
                                        }
                        DESCRIPTION
                      		"Timesync NCP verb not hooked"
                  	--#TYPE "TimeSync: No timesync NCP verb"
                  	--#SUMMARY "TIMESYNC NLM: Cannot hook TimeSync "
                        --#SUMMARY "NCP verb on NetWare server %s."
	                --#ARGUMENTS {0}
                        --#SEVERITY INFORMATIONAL
                        --#TIMEINDEX 1
                        --#HELP "nwalarm.hlp"
                        --#HELPTAG 284
                        --#STATE  OPERATIONAL

                    ::= 284

cantAllocateMainStack   TRAP-TYPE
                        ENTERPRISE      nwalarm-mib
                        VARIABLES       {
                                        serverName,trapTime
                                        }
                        DESCRIPTION
                      		"Could not allocate main stack"
                  	--#TYPE "TimeSync: No main stack"
                  	--#SUMMARY "TIMESYNC NLM: Couldn't allocate "
                        --#SUMMARY "main stack on NetWare server %s."
	                --#ARGUMENTS {0}
                        --#SEVERITY INFORMATIONAL
                        --#TIMEINDEX 1
                        --#HELP "nwalarm.hlp"
                        --#HELPTAG 285
                        --#STATE  OPERATIONAL

                    ::= 285

cantCreateMainProcess  	TRAP-TYPE
                        ENTERPRISE      nwalarm-mib
                        VARIABLES       {
                                        serverName,trapTime
                                        }
                        DESCRIPTION
                      		"Could not create main process"
                  	--#TYPE "TimeSync: Could not create main process"
                  	--#SUMMARY "TIMESYNC NLM: Couldn't create main"
                        --#SUMMARY "process on NetWare server %s."
	                --#ARGUMENTS {0}
                        --#SEVERITY INFORMATIONAL
                        --#TIMEINDEX 1
                        --#HELP "nwalarm.hlp"
                        --#HELPTAG 286
                        --#STATE  OPERATIONAL

                    ::= 286

syncRadiusLess        	TRAP-TYPE
                        ENTERPRISE      nwalarm-mib
                        VARIABLES       {
                                        serverName,trapTime,
                                        synchronizationRadius
                                        }
                        DESCRIPTION
                      		"Synchronization radius will prevent
                                 synchronization"
                  	--#TYPE "TimeSync: Synchronization radius"
                  	--#SUMMARY "TIMESYNC NLM: Synchronization Radius"
                        --#SUMMARY "less than %d on NetWare server %s"
                        --#SUMMARY "will prevent synchronization"
	                --#ARGUMENTS {2,0}
                        --#SEVERITY MINOR
                        --#TIMEINDEX 1
                        --#HELP "nwalarm.hlp"
                        --#HELPTAG 287
                        --#STATE  OPERATIONAL

                    ::= 287

unrecognizedCommandLinePrmtr     TRAP-TYPE
                        ENTERPRISE      nwalarm-mib
                        VARIABLES       {
                                        serverName,trapTime,
                                        cmmndLnPrmtr
                                        }
                        DESCRIPTION
                      		"Unrecognized command line parameter"
                  	--#TYPE "TimeSync: Unrecognized parameter"
                  	--#SUMMARY "TIMESYNC NLM: Unrecognized command "
                        --#SUMMARY "line parameter: %s on NetWare server %s."
	                --#ARGUMENTS {2,0}
                        --#SEVERITY MINOR
                        --#TIMEINDEX 1
                        --#HELP "nwalarm.hlp"
                        --#HELPTAG 288
                        --#STATE  OPERATIONAL

                    ::= 288

unrecognizedCommandLineOption  	TRAP-TYPE
                        ENTERPRISE      nwalarm-mib
                        VARIABLES       {
                                        serverName,trapTime,
                                        cmmndLnPrmtr
                                        }
                        DESCRIPTION
                      		"Unrecognized command line option"
                  	--#TYPE "TimeSync: Unrecognized config option"
                  	--#SUMMARY "TIMESYNC NLM: Unrecognized command "
                        --#SUMMARY "line parameter: %s in configuration file"
                        --#SUMMARY "on NetWare server %s."
	                --#ARGUMENTS {2,0}
                        --#SEVERITY MINOR
                        --#TIMEINDEX 1
                        --#HELP "nwalarm.hlp"
                        --#HELPTAG 289
                        --#STATE  OPERATIONAL

                    ::= 289

serverPolled            TRAP-TYPE
                        ENTERPRISE      nwalarm-mib
                        VARIABLES       {
                                        serverName,trapTime,serverName1
                                        }
                        DESCRIPTION
                      		"Primary reference and single servers
                                 should not follow a secondary server"
                  	--#TYPE "TimeSync: Server polled"
                  	--#SUMMARY "Primary, reference and single servers "
                        --#SUMMARY "should not follow a secondary server. "
                        --#SUMMARY "This server %s, polled: %s. "
                        --#SUMMARY "The time exchange was ignored. "
	                --#ARGUMENTS {0,2}
                        --#SEVERITY MINOR
                        --#TIMEINDEX 1
                        --#HELP "nwalarm.hlp"
                        --#HELPTAG 290
                        --#STATE  OPERATIONAL

                    ::= 290

singleSrvrIncompatible  TRAP-TYPE
                        ENTERPRISE      nwalarm-mib
                        VARIABLES       {
                                        serverName,trapTime,serverName1
                                        }
                        DESCRIPTION
                      		"SINGLE servers are incompatible with
                                 REFERENCE and PRIMARY servers."
                  	--#TYPE "TimeSync: Servers incompatible"
                  	--#SUMMARY "Single servers are incompatible with"
                        --#SUMMARY "Reference and Primary servers"
                        --#SUMMARY "and should not follow secondary servers."
                        --#SUMMARY "This server %s, polled: %s."
                        --#SUMMARY "The time exchange was ignored!"
	                --#ARGUMENTS {0,2}
                        --#SEVERITY MINOR
                        --#TIMEINDEX 1
                        --#HELP "nwalarm.hlp"
                        --#HELPTAG 291
                        --#STATE  OPERATIONAL

                    ::= 291

timeSyncLost            TRAP-TYPE
                        ENTERPRISE      nwalarm-mib
                        VARIABLES       {
                                        serverName,trapTime,pollingLoops
                                        }
                        DESCRIPTION
                      		"Time synchronization lost after successful
                                 polling loops"
                  	--#TYPE "TimeSync: Time synchronization lost"
                  	--#SUMMARY "Time synchronization lost after"
                        --#SUMMARY "%d successful polling loops on NetWare"
                        --#SUMMARY "server %s"
	                --#ARGUMENTS {2,0}
                        --#SEVERITY MINOR
                        --#TIMEINDEX 1
                        --#HELP "nwalarm.hlp"
                        --#HELPTAG 292
                        --#STATE  OPERATIONAL

                    ::= 292

timeSyncEstablished     TRAP-TYPE
                        ENTERPRISE      nwalarm-mib
                        VARIABLES       {
                                        serverName,trapTime
                                        }
                        DESCRIPTION
                      		"Time synchronization has been established"
                  	--#TYPE "TimeSync: Time synchronization established"
                  	--#SUMMARY "Time synchronization established"
                        --#SUMMARY "on NetWare server %s"
	                --#ARGUMENTS {0}
                        --#SEVERITY INFORMATIONAL
                        --#TIMEINDEX 1
                        --#HELP "nwalarm.hlp"
                        --#HELPTAG 293
                        --#STATE  OPERATIONAL

                    ::= 293

connTerminated          TRAP-TYPE
                        ENTERPRISE      nwalarm-mib
                        VARIABLES       {
                                        serverName,trapTime,connectionNumber
                                        }
                        DESCRIPTION
                      		"Connection cleared and terminated"
                  	--#TYPE "Connection: Terminated"
                  	--#SUMMARY "Connection %u on %s cleared"
                        --#SUMMARY "and terminated."
	                --#ARGUMENTS {2,0}
                        --#SEVERITY INFORMATIONAL
                        --#TIMEINDEX 1
                        --#HELP "nwalarm.hlp"
                        --#HELPTAG 294
                        --#STATE  OPERATIONAL

                    ::= 294

connClearedByUsr        TRAP-TYPE
                        ENTERPRISE      nwalarm-mib
                        VARIABLES       {
                                        serverName,trapTime,connectionNumber,
                                        stationNumber, userName
                                        }
                        DESCRIPTION
                      		"Connection cleared by user"
                  	--#TYPE "Connection: Cleared by user"
                  	--#SUMMARY "Connection %u cleared by user %s\\%s"
                        --#SUMMARY " on station %u."
	                --#ARGUMENTS {2,4,0,3}
                        --#SEVERITY INFORMATIONAL
                        --#TIMEINDEX 1
                        --#HELP "nwalarm.hlp"
                        --#HELPTAG 295
                        --#STATE  OPERATIONAL

                    ::= 295


loginDisabled           TRAP-TYPE
                        ENTERPRISE      nwalarm-mib
                        VARIABLES       {
                                        serverName,trapTime,connectionNumber,
                                        userName
                                        }
                        DESCRIPTION
                      		"Login disabled by user on a connection"
                  	--#TYPE "System: Login disabled, by user #2"
                  	--#SUMMARY "Login disabled on connection %u"
                        --#SUMMARY "by user %s on NetWare server %s."
	                --#ARGUMENTS {2,3,0}
                        --#SEVERITY INFORMATIONAL
                        --#TIMEINDEX 1
                        --#HELP "nwalarm.hlp"
                        --#HELPTAG 296
                        --#STATE  OPERATIONAL

                    ::= 296

downFileServer          TRAP-TYPE
                        ENTERPRISE      nwalarm-mib
                        VARIABLES       {
                                        serverName,trapTime,stationNumber,
                                        userName
                                        }
                        DESCRIPTION
                      		"Down file server requested by an user"
                  	--#TYPE "System: Server down req, by user"
                  	--#SUMMARY "Down file server (%s) requested by"
                        --#SUMMARY "user %s on station %u."
	                --#ARGUMENTS {0,3,2}
                        --#SEVERITY INFORMATIONAL
                        --#TIMEINDEX 1
                        --#HELP "nwalarm.hlp"
                        --#HELPTAG 297
                        --#STATE  OPERATIONAL

                    ::= 297

loginEnabled            TRAP-TYPE
                        ENTERPRISE      nwalarm-mib
                        VARIABLES       {
                                        serverName,trapTime,connectionNumber,
                                        userName
                                        }
                        DESCRIPTION
                      		"Login enabled by user"
                  	--#TYPE "System: Login enabled, by user #1"
                  	--#SUMMARY "Login enabled on connection %u by"
                        --#SUMMARY "user %s on NetWare server %s."
	                --#ARGUMENTS {2,3,0}
                        --#SEVERITY INFORMATIONAL
                        --#TIMEINDEX 1
                        --#HELP "nwalarm.hlp"
                        --#HELPTAG 298
                        --#STATE  OPERATIONAL

                    ::= 298

-- new SFT and PIN alerts

errLogTransferErr       TRAP-TYPE
                        ENTERPRISE      nwalarm-mib
                        VARIABLES       {
                                        serverName,trapTime
                                        }
                        DESCRIPTION
                      		"Error transferring IOEngine error log to
                                 MSEngine"
                  	--#TYPE "SFT-III: Err transferring IOEngine err log"
                  	--#SUMMARY "Error transfering IOEngine error log to"
                        --#SUMMARY "MSEngine on NetWare server %s."
                        --#SUMMARY "Error log remaining in DOS file."
	                --#ARGUMENTS {0}
                        --#SEVERITY CRITICAL
                        --#TIMEINDEX 1
                        --#HELP "nwalarm.hlp"
                        --#HELPTAG 299
                        --#STATE  OPERATIONAL

                    ::= 299


faultInConsoleCommandHandler     TRAP-TYPE
                        ENTERPRISE      nwalarm-mib
                        VARIABLES       {
                                        serverName,trapTime
                                        }
                        DESCRIPTION
                      		"Fault in console command handler"
                  	--#TYPE "System: Command handler fault"
                  	--#SUMMARY "Fault occurred in a registered console"
                        --#SUMMARY "command handler on NetWare server %s."
	                --#ARGUMENTS {0}
                        --#SEVERITY CRITICAL
                        --#TIMEINDEX 1
                        --#HELP "nwalarm.hlp"
                        --#HELPTAG 300
                        --#STATE  OPERATIONAL

                    ::= 300

commLinkActivated       TRAP-TYPE
                        ENTERPRISE      nwalarm-mib
                        VARIABLES       {
                                        serverName,trapTime
                                        }
                        DESCRIPTION
                      		"Mirrored comm link activated"
                  	--#TYPE "SFT-III: MSL activated"
                  	--#SUMMARY "Mirrored server to server comm link"
                        --#SUMMARY "activated on NetWare server %s."
	                --#ARGUMENTS {0}
                        --#SEVERITY INFORMATIONAL
                        --#TIMEINDEX 1
                        --#HELP "nwalarm.hlp"
                        --#HELPTAG 301
                        --#STATE  OPERATIONAL

                    ::= 301

commLinkFailure         TRAP-TYPE
                        ENTERPRISE      nwalarm-mib
                        VARIABLES       {
                                        serverName,trapTime
                                        }
                        DESCRIPTION
                      		"Mirrored comm link failure"
                  	--#TYPE "SFT-III: MSL failure"
                  	--#SUMMARY "Mirrored server to server comm link"
                        --#SUMMARY "failure on all MSLs on NetWare server %s."
	                --#ARGUMENTS {0}
                        --#SEVERITY INFORMATIONAL
                        --#TIMEINDEX 1
                        --#HELP "nwalarm.hlp"
                        --#HELPTAG 302
                        --#STATE  OPERATIONAL

                    ::= 302

commLinkDeactivated     TRAP-TYPE
                        ENTERPRISE      nwalarm-mib
                        VARIABLES       {
                                        serverName,trapTime
                                        }
                        DESCRIPTION
                      		"Mirrored comm link de-activated"
                  	--#TYPE "SFT-III: MSL de-activated"
                  	--#SUMMARY "Mirrored server to server comm link"
                        --#SUMMARY "de-activated on NetWare server %s."
	                --#ARGUMENTS {0}
                        --#SEVERITY INFORMATIONAL
                        --#TIMEINDEX 1
                        --#HELP "nwalarm.hlp"
                        --#HELPTAG 303
                        --#STATE  OPERATIONAL

                    ::= 303

srvrAttemptedToSync     TRAP-TYPE
                        ENTERPRISE      nwalarm-mib
                        VARIABLES       {
                                        serverName,trapTime
                                        }
                        DESCRIPTION
                      		"Server attempted to synchronize"
                  	--#TYPE "SFT-III: Synchronization attempt"
                  	--#SUMMARY "Other server attempted to synchronize"
                        --#SUMMARY "with server %s but server is down."
	                --#ARGUMENTS {0}
                        --#SEVERITY INFORMATIONAL
                        --#TIMEINDEX 1
                        --#HELP "nwalarm.hlp"
                        --#HELPTAG 304
                        --#STATE  OPERATIONAL

                    ::= 304

commLinkBrokeOK         TRAP-TYPE
                        ENTERPRISE      nwalarm-mib
                        VARIABLES       {
                                        serverName,trapTime
                                        }
                        DESCRIPTION
                      		"Comm Link broke and re-established"
                  	--#TYPE "SFT-III: MSL comm. re-established"
                  	--#SUMMARY "Mirrored server to server comm link"
                        --#SUMMARY "broken then re-established with other"
                        --#SUMMARY "server from NetWare server %s."
	                --#ARGUMENTS {0}
                        --#SEVERITY INFORMATIONAL
                        --#TIMEINDEX 1
                        --#HELP "nwalarm.hlp"
                        --#HELPTAG 305
                        --#STATE  OPERATIONAL

                    ::= 305

syncStartingAmSecondarySrvr   TRAP-TYPE
                        ENTERPRISE      nwalarm-mib
                        VARIABLES       {
                                        serverName,trapTime
                                        }
                        DESCRIPTION
                      		"Secondary server starting synchronization"
                  	--#TYPE "SFT-III: Synchronization starting"
                  	--#SUMMARY "Mirrored server synchronization beginning"
                        --#SUMMARY "on %s (this will be the secondary server)."
	                --#ARGUMENTS {0}
                        --#SEVERITY INFORMATIONAL
                        --#TIMEINDEX 1
                        --#HELP "nwalarm.hlp"
                        --#HELPTAG 306
                        --#STATE  OPERATIONAL

                    ::= 306

badSrvrInitMsg           TRAP-TYPE
                        ENTERPRISE      nwalarm-mib
                        VARIABLES       {
                                        serverName,trapTime
                                        }
                        DESCRIPTION
                      		"Invalid mirrored server initialization"
                  	--#TYPE "SFT-III: Invalid initialization message"
                  	--#SUMMARY "Invalid mirrored server initialization"
                        --#SUMMARY "message received on NetWare server %s"
                        --#SUMMARY "from the other server."
	                --#ARGUMENTS {0}
                        --#SEVERITY INFORMATIONAL
                        --#TIMEINDEX 1
                        --#HELP "nwalarm.hlp"
                        --#HELPTAG 307
                        --#STATE  OPERATIONAL

                    ::= 307

commLinkInitFailed      TRAP-TYPE
                        ENTERPRISE      nwalarm-mib
                        VARIABLES       {
                                        serverName,trapTime
                                        }
                        DESCRIPTION
                      		"Comm Link init failed"
                  	--#TYPE "SFT-III: MSL failure, initialization"
                  	--#SUMMARY "Mirrored server to server comm link"
                        --#SUMMARY "failure during initialization on NetWare"
                        --#SUMMARY "server %s."
	                --#ARGUMENTS {0}
                        --#SEVERITY INFORMATIONAL
                        --#TIMEINDEX 1
                        --#HELP "nwalarm.hlp"
                        --#HELPTAG 308
                        --#STATE  OPERATIONAL

                    ::= 308

failedDuringSync        TRAP-TYPE
                        ENTERPRISE      nwalarm-mib
                        VARIABLES       {
                                        serverName,trapTime,szReason
                                        }
                        DESCRIPTION
                      		"Synchronization failure"
                  	--#TYPE "SFT-III: Synchronization failure"
                  	--#SUMMARY "%s failure during synchronization"
                        --#SUMMARY "on NetWare server %s."
	                --#ARGUMENTS {2,0}
                        --#SEVERITY MAJOR
                        --#TIMEINDEX 1
                        --#HELP "nwalarm.hlp"
                        --#HELPTAG 309
                        --#STATE  OPERATIONAL

                    ::= 309

commDriverLoadedDuringActivate TRAP-TYPE
                        ENTERPRISE      nwalarm-mib
                        VARIABLES       {
                                        serverName,trapTime
                                        }
                        DESCRIPTION
                      		"Comm driver loaded during an activate server"
                  	--#TYPE "SFT-III: MSL driver loaded during activate"
                  	--#SUMMARY "Mirrored server to server comm driver"
                        --#SUMMARY " loaded during ACTIVATE SERVER on %s ..."
                        --#SUMMARY "will wait till activate is done."
	                --#ARGUMENTS {0}
                        --#SEVERITY MAJOR
                        --#TIMEINDEX 1
                        --#HELP "nwalarm.hlp"
                        --#HELPTAG 310
                        --#STATE  OPERATIONAL

                    ::= 310

errWritingStatusDump    TRAP-TYPE
                        ENTERPRISE      nwalarm-mib
                        VARIABLES       {
                                        serverName,trapTime
                                        }
                        DESCRIPTION
                      		"Error writing status dump"
                  	--#TYPE "SFT-III: Err writing status dump"
                  	--#SUMMARY "Error writing out status dump on NetWare"
                        --#SUMMARY "server %s."
	                --#ARGUMENTS {0}
                        --#SEVERITY MINOR
                        --#TIMEINDEX 1
                        --#HELP "nwalarm.hlp"
                        --#HELPTAG 311
                        --#STATE  OPERATIONAL

                    ::= 311

commDriverFailureOnPrimary      TRAP-TYPE
                        ENTERPRISE      nwalarm-mib
                        VARIABLES       {
                                        serverName,trapTime
                                        }
                        DESCRIPTION
                      		"Comm driver on primary server"
                  	--#TYPE "SFT-III: MSL driver on primary server"
                        --#SUMMARY "MSL failure notification during hold off..."
                        --#SUMMARY "this causes no problem, since this is the"
                        --#SUMMARY "primary server (%s) but get a newer driver"
                        --#SUMMARY "with this problem fixed"
	                --#ARGUMENTS {0}
                        --#SEVERITY MINOR
                        --#TIMEINDEX 1
                        --#HELP "nwalarm.hlp"
                        --#HELPTAG 312
                        --#STATE  OPERATIONAL

                    ::= 312

commDriverFailureOnSecondary      TRAP-TYPE
                        ENTERPRISE      nwalarm-mib
                        VARIABLES       {
                                        serverName,trapTime
                                        }
                        DESCRIPTION
                      		"Comm Link init failed"
                  	--#TYPE "SFT-III: MSL failure, hold off"
                        --#SUMMARY "MSL failure during hold off."
			--#SUMMARY "This is the secondary server (%s),"
                        --#SUMMARY "there is a potential for clients to hang"
                        --#SUMMARY "or lose state...the server is still OK"
                        --#SUMMARY "but get a newer driver with this problem"
                        --#SUMMARY "fixed"
	                --#ARGUMENTS {0}
                        --#SEVERITY MINOR
                        --#TIMEINDEX 1
                        --#HELP "nwalarm.hlp"
                        --#HELPTAG 313
                        --#STATE  OPERATIONAL

                    ::= 313

errFinishingGeneratingStatusDump     TRAP-TYPE
                        ENTERPRISE      nwalarm-mib
                        VARIABLES       {
                                        serverName,trapTime
                                        }
                        DESCRIPTION
                      		"Error finishing generating status dump"
                  	--#TYPE "SFT-III: Err finishing status dump"
                  	--#SUMMARY "Error finishing generating status dump"
                        --#SUMMARY "on NetWare server %s."
	                --#ARGUMENTS {0}
                        --#SEVERITY MINOR
                        --#TIMEINDEX 1
                        --#HELP "nwalarm.hlp"
                        --#HELPTAG 314
                        --#STATE  OPERATIONAL

                    ::= 314

sFTIIWhatToDoReasonString  TRAP-TYPE
                        ENTERPRISE      nwalarm-mib
                        VARIABLES       {
                                        serverName,trapTime
                                        }
                        DESCRIPTION
                      		"SFTIII what to do with reason string"
                  	--#TYPE "SFT-III: Reason string"
                  	--#SUMMARY "server %s SFTIII reason string"
	                --#ARGUMENTS {0}
                        --#SEVERITY CRITICAL
                        --#TIMEINDEX 1
                        --#HELP "nwalarm.hlp"
                        --#HELPTAG 315
                        --#STATE  OPERATIONAL

                    ::= 315

sFTIIErrorUnexpected    TRAP-TYPE
                        ENTERPRISE      nwalarm-mib
                        VARIABLES       {
                                        serverName,trapTime
                                        }
                        DESCRIPTION
                      		"Unexpected SFTIII error"
                  	--#TYPE "SFT-III: Unexpected error"
                  	--#SUMMARY "Unexpected error on NetWare"
                        --#SUMMARY "server %s (not generated by server test)"
	                --#ARGUMENTS {0}
                        --#SEVERITY CRITICAL
                        --#TIMEINDEX 1
                        --#HELP "nwalarm.hlp"
                        --#HELPTAG 316
                        --#STATE  OPERATIONAL

                    ::= 316

syncErrorGeneratedFromCustomSrvr    TRAP-TYPE
                        ENTERPRISE      nwalarm-mib
                        VARIABLES       {
                                        serverName,trapTime
                                        }
                        DESCRIPTION
                      		"Sync error generated by custom server"
                  	--#TYPE "SFT-III: Sync error generated by custom MSL"
                  	--#SUMMARY "Synchronization error generated on"
                        --#SUMMARY "NetWare server %s by custom mirrored "
                        --#SUMMARY "server NLM"
	                --#ARGUMENTS {0}
                        --#SEVERITY MAJOR
                        --#TIMEINDEX 1
                        --#HELP "nwalarm.hlp"
                        --#HELPTAG 317
                        --#STATE  OPERATIONAL

                    ::= 317

srvrLinkHasPluggedPacket       TRAP-TYPE
                        ENTERPRISE      nwalarm-mib
                        VARIABLES       {
                                        serverName,trapTime
                                        }
                        DESCRIPTION
                      		"Server link has plugged packet"
                  	--#TYPE "SFT-III: Server link has plugged packet"
                  	--#SUMMARY "Server (%s) discovered a"
                        --#SUMMARY " 'stuck' LAN packet, which precludes"
                        --#SUMMARY "server synchronization"
	                --#ARGUMENTS {0}
                        --#SEVERITY MAJOR
                        --#TIMEINDEX 1
                        --#HELP "nwalarm.hlp"
                        --#HELPTAG 318
                        --#STATE  OPERATIONAL

                    ::= 318

srvrToBeRevived          TRAP-TYPE
                        ENTERPRISE      nwalarm-mib
                        VARIABLES       {
                                        serverName,trapTime
                                        }
                        DESCRIPTION
                      		"Mirrored Server will be revived"
                  	--#TYPE "SFT-III: Mirrored Server will be revived"
                  	--#SUMMARY "Mirrored server for NetWare server %s"
                        --#SUMMARY "will be revived since the other server"
                        --#SUMMARY "seems to be halted"
	                --#ARGUMENTS {0}
                        --#SEVERITY MINOR
                        --#TIMEINDEX 1
                        --#HELP "nwalarm.hlp"
                        --#HELPTAG 319
                        --#STATE  OPERATIONAL

                    ::= 319

srvrsAreSyncedThisIsThePrimary       TRAP-TYPE
                        ENTERPRISE      nwalarm-mib
                        VARIABLES       {
                                        serverName,trapTime
                                        }
                        DESCRIPTION
                      		"Mirrored servers are synchronized"
                  	--#TYPE "SFT-III: Mirrored servers are synchronized"
                  	--#SUMMARY "Mirrored servers now synchronized"
                        --#SUMMARY "(this is the primary server on server %s)"
	                --#ARGUMENTS {0}
                        --#SEVERITY INFORMATIONAL
                        --#TIMEINDEX 1
                        --#HELP "nwalarm.hlp"
                        --#HELPTAG 320
                        --#STATE  OPERATIONAL

                    ::= 320

srvrCantRouteViaIPXToSecondary      TRAP-TYPE
                        ENTERPRISE      nwalarm-mib
                        VARIABLES       {
                                        serverName,trapTime
                                        }
                        DESCRIPTION
                      		"Server does not know how to route via IPX"
                  	--#TYPE "SFT-III: Unable to route to secondary via IPX"
                  	--#SUMMARY "Server %s does not know how to route"
                        --#SUMMARY "via IPX to the secondary server"
	                --#ARGUMENTS {0}
                        --#SEVERITY INFORMATIONAL
                        --#TIMEINDEX 1
                        --#HELP "nwalarm.hlp"
                        --#HELPTAG 318
                        --#STATE  OPERATIONAL

                    ::= 321

srvrIPXRouteInfoToSecondary      TRAP-TYPE
                        ENTERPRISE      nwalarm-mib
                        VARIABLES       {
                                        serverName,trapTime,boardNumber,
                                        iHopsCount,macAddress
                                        }
                        DESCRIPTION
                      		"IPX route to secondary server"
                  	--#TYPE "SFT-III: IPX route to secondary"
                  	--#SUMMARY "IPX route from %s to secondary server:"
                        --#SUMMARY "Board #%d, Hops %d,"
                        --#SUMMARY "Immediate Router = %x"
	                --#ARGUMENTS {0,2,3,4}
                        --#SEVERITY INFORMATIONAL
                        --#TIMEINDEX 1
                        --#HELP "nwalarm.hlp"
                        --#HELPTAG 322
                        --#STATE  OPERATIONAL

                    ::= 322

errGivingRAMtoMSEngine  TRAP-TYPE
                        ENTERPRISE      nwalarm-mib
                        VARIABLES       {
                                        serverName,trapTime
                                        }
                        DESCRIPTION
                      		"Error giving additional RAM to MSEngine"
                  	--#TYPE "SFT-III: MSEngine, err adding RAM"
                  	--#SUMMARY "Error giving additional RAM to MSEngine"
                        --#SUMMARY "on server %s"
	                --#ARGUMENTS {0}
                        --#SEVERITY INFORMATIONAL
                        --#TIMEINDEX 1
                        --#HELP "nwalarm.hlp"
                        --#HELPTAG 323
                        --#STATE  OPERATIONAL

                    ::= 323

moreRAMgivenToMSEngine  TRAP-TYPE
                        ENTERPRISE      nwalarm-mib
                        VARIABLES       {
                                        serverName,trapTime,iRamStart,
                                        iRamLength
                                        }
                        DESCRIPTION
                      		"More RAM given to MSEngine"
                  	--#TYPE "SFT-III: MSEngine, more RAM added"
                  	--#SUMMARY "More RAM given to MSEngine at 0x%x"
                        --#SUMMARY "length 0x%x on server %s"
	                --#ARGUMENTS {2,3,0}
                        --#SEVERITY INFORMATIONAL
                        --#TIMEINDEX 1
                        --#HELP "nwalarm.hlp"
                        --#HELPTAG 324
                        --#STATE  OPERATIONAL

                    ::= 324

srvrsAreSyncedThisIsTheSecondary       TRAP-TYPE
                        ENTERPRISE      nwalarm-mib
                        VARIABLES       {
                                        serverName,trapTime
                                        }
                        DESCRIPTION
                      		"Mirrored servers now synchronized"
                  	--#TYPE "SFT-III: Mirrored servers now synchronized"
                  	--#SUMMARY "Mirrored servers now synchronized"
                        --#SUMMARY "(this server, %s, is the secondary"
                        --#SUMMARY " server)"
	                --#ARGUMENTS {0}
                        --#SEVERITY INFORMATIONAL
                        --#TIMEINDEX 1
                        --#HELP "nwalarm.hlp"
                        --#HELPTAG 325
                        --#STATE  OPERATIONAL

                    ::= 325

srvrCantRouteViaIPXToPrimary      TRAP-TYPE
                        ENTERPRISE      nwalarm-mib
                        VARIABLES       {
                                        serverName,trapTime
                                        }
                        DESCRIPTION
                      		"This server does not know how to route
                                 via IPX"
                  	--#TYPE "SFT-III: Unable to route to primary via IPX"
                  	--#SUMMARY "This server (%s) does not know how to"
                        --#SUMMARY "route via IPX to the primary server"
	                --#ARGUMENTS {0}
                        --#SEVERITY INFORMATIONAL
                        --#TIMEINDEX 1
                        --#HELP "nwalarm.hlp"
                        --#HELPTAG 326
                        --#STATE  OPERATIONAL

                    ::= 326

srvrIPXRouteInfoToPrimary      TRAP-TYPE
                        ENTERPRISE      nwalarm-mib
                        VARIABLES       {
                                        serverName,trapTime,boardNumber,
                                        iHopsCount,macAddress
                                        }
                        DESCRIPTION
                      		"IPX route to primary server"
                  	--#TYPE "SFT-III: IPX route to primary"
                  	--#SUMMARY "IPX route to primary server %s: Board #%d,"
                        --#SUMMARY "Hops %d,"
                        --#SUMMARY "Immediate Router = %x"
	                --#ARGUMENTS {0,2,3,4}
                        --#SEVERITY INFORMATIONAL
                        --#TIMEINDEX 1
                        --#HELP "nwalarm.hlp"
                        --#HELPTAG 327
                        --#STATE  OPERATIONAL

                    ::= 327

priSrvrFailedButSecDown  TRAP-TYPE
                        ENTERPRISE      nwalarm-mib
                        VARIABLES       {
                                        serverName,trapTime,szReason
                                        }
                        DESCRIPTION
                      		"Primary server failed"
                  	--#TYPE "SFT-III: Primary failed, secondary down"
                  	--#SUMMARY "Primary server %s failed due to %s..."
                        --#SUMMARY "this server is becoming the primary but"
                        --#SUMMARY "the server has been downed"
	                --#ARGUMENTS {0,2}
                        --#SEVERITY MAJOR
                        --#TIMEINDEX 1
                        --#HELP "nwalarm.hlp"
                        --#HELPTAG 328
                        --#STATE  OPERATIONAL

                    ::= 328

priSrvrFailedNewPri      TRAP-TYPE
                        ENTERPRISE      nwalarm-mib
                        VARIABLES       {
                                        serverName,trapTime,szReason
                                        }
                        DESCRIPTION
                      		"Primary server failed"
                  	--#TYPE "SFT-III: Primary failed, secondary up"
                  	--#SUMMARY "Primary server %s failed due to %s..."
                        --#SUMMARY "this server is becoming the primary"
                        --#SUMMARY "server"
	                --#ARGUMENTS {0,2}
                        --#SEVERITY MAJOR
                        --#TIMEINDEX 1
                        --#HELP "nwalarm.hlp"
                        --#HELPTAG 329
                        --#STATE  OPERATIONAL

                    ::= 329

numMemSegsExceedLimit   TRAP-TYPE
                        ENTERPRISE      nwalarm-mib
                        VARIABLES       {
                                        serverName,trapTime
                                        }
                        DESCRIPTION
                      		"Number of memory segments exceeds limits"
                  	--#TYPE "SFT-III: Memory segments exceeds limits"
                  	--#SUMMARY "No. of memory segments exceeds"
                        --#SUMMARY "synchronization record limit on server %s"
	                --#ARGUMENTS {0}
                        --#SEVERITY MAJOR
                        --#TIMEINDEX 1
                        --#HELP "nwalarm.hlp"
                        --#HELPTAG 330
                        --#STATE  OPERATIONAL

                    ::= 330

numScreenExceedsLimit   TRAP-TYPE
                        ENTERPRISE      nwalarm-mib
                        VARIABLES       {
                                        serverName,trapTime
                                        }
                        DESCRIPTION
                      		"Number of screen modes exceeds limits"
                  	--#TYPE "SFT-III: Screen modes exceeds limits"
                  	--#SUMMARY "No. of screen modes exceeds"
                        --#SUMMARY "synchronization record limit on server %s"
	                --#ARGUMENTS {0}
                        --#SEVERITY MAJOR
                        --#TIMEINDEX 1
                        --#HELP "nwalarm.hlp"
                        --#HELPTAG 331
                        --#STATE  OPERATIONAL

                    ::= 331

iOVersionMismatch       TRAP-TYPE
                        ENTERPRISE      nwalarm-mib
                        VARIABLES       {
                                        serverName,trapTime
                                        }
                        DESCRIPTION
                      		"Other server's IOEngine software version
                                 does not match"
                  	--#TYPE "SFT-III: Mismatch, IOEngine software version"
                  	--#SUMMARY "Other server's IOEngine software version"
                        --#SUMMARY "does not match this server (i.e. %s)."
	                --#ARGUMENTS {0}
                        --#SEVERITY MAJOR
                        --#TIMEINDEX 1
                        --#HELP "nwalarm.hlp"
                        --#HELPTAG 332
                        --#STATE  OPERATIONAL

                    ::= 332

srvrProtectLevelNoMatch    TRAP-TYPE
                        ENTERPRISE      nwalarm-mib
                        VARIABLES       {
                                        serverName,trapTime
                                        }
                        DESCRIPTION
                      		"Server's protection level does not match"
                  	--#TYPE "SFT-III: Mismatch, Protection level"
                  	--#SUMMARY "%s: Other server's protection level does not"
                        --#SUMMARY "match"
	                --#ARGUMENTS {0}
                        --#SEVERITY MAJOR
                        --#TIMEINDEX 1
                        --#HELP "nwalarm.hlp"
                        --#HELPTAG 333
                        --#STATE  OPERATIONAL

                    ::= 333

srvrScreenAddressMismatch      TRAP-TYPE
                        ENTERPRISE      nwalarm-mib
                        VARIABLES       {
                                        serverName,trapTime
                                        }
                        DESCRIPTION
                      		"Server's screen address does not match"
                  	--#TYPE "SFT-III: Mismatch, Screen address"
                  	--#SUMMARY "Other server's screen address does not"
                        --#SUMMARY "match this server's (%s) (cannot mirror"
                        --#SUMMARY "monochrome to color screen)"
	                --#ARGUMENTS {0}
                        --#SEVERITY MAJOR
                        --#TIMEINDEX 1
                        --#HELP "nwalarm.hlp"
                        --#HELPTAG 334
                        --#STATE  OPERATIONAL

                    ::= 334
iOEngineNotLoadedAtSameAddress      TRAP-TYPE
                        ENTERPRISE      nwalarm-mib
                        VARIABLES       {
                                        serverName,trapTime,iRamStart,
                                        iRamLength
                                        }
                        DESCRIPTION
                      		"Server's IOEngine not loaded at the same
                                 location"
                  	--#TYPE "SFT-III: Mismatch, IOEngine address"
                  	--#SUMMARY "Other server's IOEngine not loaded at the"
                        --#SUMMARY "same location in memory (this server:%s"
                        --#SUMMARY "at 0x%x, other server at 0x%x)"
	                --#ARGUMENTS {0,2,3}
                        --#SEVERITY MAJOR
                        --#TIMEINDEX 1
                        --#HELP "nwalarm.hlp"
                        --#HELPTAG 335
                        --#STATE  OPERATIONAL

                    ::= 335

bothSrvrHaveActiveMSEngines        TRAP-TYPE
                        ENTERPRISE      nwalarm-mib
                        VARIABLES       {
                                        serverName,trapTime
                                        }
                        DESCRIPTION
                      		"Both servers have active MSEngines"
                  	--#TYPE "SFT-III: MSEngine, active on both servers"
                  	--#SUMMARY "%s: Both servers have active MSEngines"
	                --#ARGUMENTS {0}
                        --#SEVERITY MAJOR
                        --#TIMEINDEX 1
                        --#HELP "nwalarm.hlp"
                        --#HELPTAG 336
                        --#STATE  OPERATIONAL

                    ::= 336

noActiveMSEngineOnServers        TRAP-TYPE
                        ENTERPRISE      nwalarm-mib
                        VARIABLES       {
                                        serverName,trapTime
                                        }
                        DESCRIPTION
                      		"Neither server has an active MSEngine"
                  	--#TYPE "SFT-III: MSEngine, not active on either server"
                  	--#SUMMARY "%s: Neither server has an active"
                        --#SUMMARY "MSEngine...will auto synchronize when"
                        --#SUMMARY "one is activated"
	                --#ARGUMENTS {0}
                        --#SEVERITY MAJOR
                        --#TIMEINDEX 1
                        --#HELP "nwalarm.hlp"
                        --#HELPTAG 337
                        --#STATE  OPERATIONAL

                    ::= 337

secSrvrMissingRAM        TRAP-TYPE
                        ENTERPRISE      nwalarm-mib
                        VARIABLES       {
                                        serverName,trapTime,iRamStart,
                                        iRamLength
                                        }
                        DESCRIPTION
                      		"Secondary server is missing RAM"
                  	--#TYPE "SFT-III: Secondary is missing RAM"
                  	--#SUMMARY "%s: Secondary server is missing RAM"
                        --#SUMMARY "at 0x%x length 0x%x"
	                --#ARGUMENTS {0,2,3}
                        --#SEVERITY MAJOR
                        --#TIMEINDEX 1
                        --#HELP "nwalarm.hlp"
                        --#HELPTAG 338
                        --#STATE  OPERATIONAL

                    ::= 338

bothSrvrHaveSameIPXAddr  TRAP-TYPE
                        ENTERPRISE      nwalarm-mib
                        VARIABLES       {
                                        serverName,trapTime
                                        }
                        DESCRIPTION
                      		"Server's IOEngines have the same IPX
                                 internal network number"
                  	--#TYPE "SFT-III: Duplicate internal net#, IO & IO"
                  	--#SUMMARY "%s: Both server's IOEngines have the same"
                        --#SUMMARY "IPX internal network number"
	                --#ARGUMENTS {0}
                        --#SEVERITY MAJOR
                        --#TIMEINDEX 1
                        --#HELP "nwalarm.hlp"
                        --#HELPTAG 339
                        --#STATE  OPERATIONAL

                    ::= 339

iOEngIPXAddrMatchesMSEngine  TRAP-TYPE
                        ENTERPRISE      nwalarm-mib
                        VARIABLES       {
                                        serverName,trapTime
                                        }
                        DESCRIPTION
                      		"IOEngine IPX internal net number matches
			         the MSEngine's IPX internal net number"
                  	--#TYPE "SFT-III: Duplicate internal net#, MS & IO"
                  	--#SUMMARY "Secondary IOEngine IPX internal net"
                        --#SUMMARY "number matches the MSEngine's IPX"
                        --#SUMMARY "internal net number on %s"
	                --#ARGUMENTS {0}
                        --#SEVERITY MAJOR
                        --#TIMEINDEX 1
                        --#HELP "nwalarm.hlp"
                        --#HELPTAG 340
                        --#STATE  OPERATIONAL

                    ::= 340

iOEnginesMismatchLANRxBufferSize   TRAP-TYPE
                        ENTERPRISE      nwalarm-mib
                        VARIABLES       {
                                        serverName,trapTime,iRamStart,
                                        iRamLength
                                        }
                        DESCRIPTION
                      		"IOEngines have different lan receive buffer
                                 sizes"
                  	--#TYPE "SFT-III: Mismatch, IOEngine LAN recv buffers"
                  	--#SUMMARY "IOEngines have different LAN receive"
                        --#SUMMARY "buffer sizes (this server, %s has %d,"
                        --#SUMMARY "other server %d)"
	                --#ARGUMENTS {0,2,3}
                        --#SEVERITY MAJOR
                        --#TIMEINDEX 1
                        --#HELP "nwalarm.hlp"
                        --#HELPTAG 341
                        --#STATE  OPERATIONAL

                    ::= 341

iOEnginesHaveSameName      TRAP-TYPE
                        ENTERPRISE      nwalarm-mib
                        VARIABLES       {
                                        serverName,trapTime
                                        }
                        DESCRIPTION
                      		"IOEngines have the same names"
                  	--#TYPE "SFT-III: Duplicate IOEngine names"
                  	--#SUMMARY "%s: IOEngines have the same names"
                        --#SUMMARY "(give the secondary a different name)"
	                --#ARGUMENTS {0}
                        --#SEVERITY MAJOR
                        --#TIMEINDEX 1
                        --#HELP "nwalarm.hlp"
                        --#HELPTAG 342
                        --#STATE  OPERATIONAL

                    ::= 342

noMemoryForIOEngineName       TRAP-TYPE
                        ENTERPRISE      nwalarm-mib
                        VARIABLES       {
                                        serverName,trapTime
                                        }
                        DESCRIPTION
                      		"Insufficient memory to store other
                                 IOEngine's name"
                  	--#TYPE "SFT-III: No memory to store IOEngine name"
                  	--#SUMMARY "Insufficient memory to store other"
                        --#SUMMARY " IOEngine's name on NetWare server %s"
	                --#ARGUMENTS {0}
                        --#SEVERITY MAJOR
                        --#TIMEINDEX 1
                        --#HELP "nwalarm.hlp"
                        --#HELPTAG 343
                        --#STATE  OPERATIONAL

                    ::= 343

srvrToSrvrLinkBeginSync   TRAP-TYPE
                        ENTERPRISE      nwalarm-mib
                        VARIABLES       {
                                        serverName,trapTime
                                        }
                        DESCRIPTION
                      		"Mirrored server to server comm link
				  connection beginning synchronization"
                  	--#TYPE "SFT-III: MSL beginning synchronization"
                  	--#SUMMARY "Mirrored server to server comm link"
                        --#SUMMARY "connection established with other server"
                        --#SUMMARY "...beginning synchronization on %s"
	                --#ARGUMENTS {0}
                        --#SEVERITY INFORMATIONAL
                        --#TIMEINDEX 1
                        --#HELP "nwalarm.hlp"
                        --#HELPTAG 344
                        --#STATE  OPERATIONAL

                    ::= 344

mSEngineActivated          TRAP-TYPE
                        ENTERPRISE      nwalarm-mib
                        VARIABLES       {
                                        serverName,trapTime
                                        }
                        DESCRIPTION
                      		"MSEngine activated"
                  	--#TYPE "SFT-III: MSEngine, activated"
                  	--#SUMMARY "MSEngine activated on NetWare server %s"
	                --#ARGUMENTS {0}
                        --#SEVERITY INFORMATIONAL
                        --#TIMEINDEX 1
                        --#HELP "nwalarm.hlp"
                        --#HELPTAG 345
                        --#STATE  OPERATIONAL

                    ::= 345

mSEngActivatedWillSyncWithOther    TRAP-TYPE
                        ENTERPRISE      nwalarm-mib
                        VARIABLES       {
                                        serverName,trapTime
                                        }
                        DESCRIPTION
                      		"MSEngine activated...will synchronize
                                 with other server if it's there"
                  	--#TYPE "SFT-III: MSEngine, activated...will synchronize"
                  	--#SUMMARY "%s: MSEngine activated and will synchronize"
                        --#SUMMARY "with other server if it's there"
	                --#ARGUMENTS {0}
                        --#SEVERITY INFORMATIONAL
                        --#TIMEINDEX 1
                        --#HELP "nwalarm.hlp"
                        --#HELPTAG 346
                        --#STATE  OPERATIONAL

                    ::= 346

iOtoMSCommBeingUnloaded TRAP-TYPE
                        ENTERPRISE      nwalarm-mib
                        VARIABLES       {
                                        serverName,trapTime
                                        }
                        DESCRIPTION
                      		"IOEngine to MSEngine communications being
                                 unloaded"
                  	--#TYPE "SFT-III: IOEngine to MSEngine comm. unloaded"
                  	--#SUMMARY "SFT III IOEngine to MSEngine"
                        --#SUMMARY "comm being unloaded on "
                        --#SUMMARY "%s, on the IOEngine before it is"
                        --#SUMMARY "being unloaded on the MSEngine. Unload"
                        --#SUMMARY "the MSEngine handler so the IOEngine"
                        --#SUMMARY " handler can finish unloading"
	                --#ARGUMENTS {0}
                        --#SEVERITY INFORMATIONAL
                        --#TIMEINDEX 1
                        --#HELP "nwalarm.hlp"
                        --#HELPTAG 347
                        --#STATE  OPERATIONAL

                    ::= 347

sFTIIIOutOfMsgCodes     TRAP-TYPE
                        ENTERPRISE      nwalarm-mib
                        VARIABLES       {
                                        serverName,trapTime
                                        }
                        DESCRIPTION
                      		"Out of communications message codes"
                  	--#TYPE "SFT-III: Out of comm. message codes"
                  	--#SUMMARY "SFT III out of comm message"
                        --#SUMMARY "codes on NetWare server %s"
	                --#ARGUMENTS {0}
                        --#SEVERITY INFORMATIONAL
                        --#TIMEINDEX 1
                        --#HELP "nwalarm.hlp"
                        --#HELPTAG 348
                        --#STATE  OPERATIONAL

                    ::= 348

secIOEngSupportModulesNotLoaded     TRAP-TYPE
                        ENTERPRISE      nwalarm-mib
                        VARIABLES       {
                                        serverName,trapTime
                                        }
                        DESCRIPTION
                      		"Secondary IOEngine doesn't have appropriate
                                 support modules loaded"
                  	--#TYPE "SFT-III: Secondary IOEngine no support modules"
                  	--#SUMMARY "SFT III secondary IOEngine on NetWare"
                        --#SUMMARY "server %s doesn't have appropriate"
                        --#SUMMARY "support modules loaded"
	                --#ARGUMENTS {0}
                        --#SEVERITY INFORMATIONAL
                        --#TIMEINDEX 1
                        --#HELP "nwalarm.hlp"
                        --#HELPTAG 349
                        --#STATE  OPERATIONAL

                    ::= 349

errXferDumpToSystem     TRAP-TYPE
                        ENTERPRISE      nwalarm-mib
                        VARIABLES       {
                                        serverName,trapTime
                                        }
                        DESCRIPTION
                      		"Unable to transfer mirrored server status
                                 dumps"
                  	--#TYPE "SFT-III: Unable to transfer status dumps"
                  	--#SUMMARY "Unable to transfer mirrored server status"
                        --#SUMMARY "dumps from DOS to %s\SYS:SYSTEM"
	                --#ARGUMENTS {0}
                        --#SEVERITY INFORMATIONAL
                        --#TIMEINDEX 1
                        --#HELP "nwalarm.hlp"
                        --#HELPTAG 350
                        --#STATE  OPERATIONAL

                    ::= 350

failureCheckingPrimarySrvr       TRAP-TYPE
                        ENTERPRISE      nwalarm-mib
                        VARIABLES       {
                                        serverName,trapTime,szReason
                                        }
                        DESCRIPTION
                      		"Failure checking if the primary server is
                                 alive over the IPX internet"
                  	--#TYPE "SFT-III: Failure checking primary via IPX"
                  	--#SUMMARY "%s failure...checking if the primary"
                        --#SUMMARY "server is alive over the IPX internet"
                        --#SUMMARY "from server %s"
	                --#ARGUMENTS {2,0}
                        --#SEVERITY MAJOR
                        --#TIMEINDEX 1
                        --#HELP "nwalarm.hlp"
                        --#HELPTAG 351
                        --#STATE  OPERATIONAL

                    ::= 351

errStarting2ndProcessor      TRAP-TYPE
                        ENTERPRISE      nwalarm-mib
                        VARIABLES       {
                                        serverName,trapTime
                                        }
                        DESCRIPTION
                      		"Error starting the 2nd processor"
                  	--#TYPE "SFT-III: Err starting 2nd processor"
                  	--#SUMMARY "server %s Error starting the 2nd processor"
	                --#ARGUMENTS {0}
                        --#SEVERITY MINOR
                        --#TIMEINDEX 1
                        --#HELP "nwalarm.hlp"
                        --#HELPTAG 352
                        --#STATE  OPERATIONAL

                    ::= 352

srvrFailure              TRAP-TYPE
                        ENTERPRISE      nwalarm-mib
                        VARIABLES       {
                                        serverName,trapTime
                                        }
                        DESCRIPTION
                      		"Server Failure message"
                  	--#TYPE "SFT-III: Server Failed"
                  	--#SUMMARY "Server %s failed"
	                --#ARGUMENTS {0}
                        --#SEVERITY INFORMATIONAL
                        --#TIMEINDEX 1
                        --#HELP "nwalarm.hlp"
                        --#HELPTAG 353
                        --#STATE  OPERATIONAL

                    ::= 353

srvsSyncing             TRAP-TYPE
                        ENTERPRISE      nwalarm-mib
                        VARIABLES       {
                                        serverName,trapTime
                                        }
                        DESCRIPTION
                                "Mirrored server synchronizing"
                  	--#TYPE "SFT-III: Mirrored server synchronizing"
                  	--#SUMMARY "Mirrored server %s synchronizing..."
                        --#SUMMARY "expect a short delay."
	                --#ARGUMENTS {0}
                        --#SEVERITY INFORMATIONAL
                        --#TIMEINDEX 1
                        --#HELP "nwalarm.hlp"
                        --#HELPTAG 354
                        --#STATE  OPERATIONAL

                    ::= 354

mSLBoardNumberConnEstablished         TRAP-TYPE
                        ENTERPRISE      nwalarm-mib
                        VARIABLES       {
                                        serverName,trapTime,boardNumber
                                        }
                        DESCRIPTION
                      		"MSL Board Number has established a
                                 connection"
                  	--#TYPE "SFT-III: MSL connection established"
                  	--#SUMMARY "MSL Board Number %d established a"
                        --#SUMMARY "connection on server %s"
	                --#ARGUMENTS {2,0}
                        --#SEVERITY INFORMATIONAL
                        --#TIMEINDEX 1
                        --#HELP "nwalarm.hlp"
                        --#HELPTAG 355
                        --#STATE  OPERATIONAL

                    ::= 355

secSrvrLANIsBetter       TRAP-TYPE
                        ENTERPRISE      nwalarm-mib
                        VARIABLES       {
                                        serverName,trapTime
                                        }
                        DESCRIPTION
                      		"The secondary server's LAN more functional
                                 than primary server's"
                  	--#TYPE "SFT-III: Secondary's LAN more functional"
                  	--#SUMMARY "%s: Secondary server's LAN adapters"
                        --#SUMMARY "are more functional than the primary"
                        --#SUMMARY "server's; the primary will restart"
	                --#ARGUMENTS {0}
                        --#SEVERITY INFORMATIONAL
                        --#TIMEINDEX 1
                        --#HELP "nwalarm.hlp"
                        --#HELPTAG 356
                        --#STATE  OPERATIONAL

                    ::= 356

iPXreturningStatusPackets       TRAP-TYPE
                        ENTERPRISE      nwalarm-mib
                        VARIABLES       {
                                        serverName,trapTime,networkAddress
                                        }
                        DESCRIPTION
                      		"IPX Network is now returning status check
                                 packets"
                  	--#TYPE "SFT-III: IPX net now returning status checks"
                  	--#SUMMARY "IPX Network %x is returning status"
                        --#SUMMARY "check packets on server %s"
	                --#ARGUMENTS {2,0}
                        --#SEVERITY INFORMATIONAL
                        --#TIMEINDEX 1
                        --#HELP "nwalarm.hlp"
                        --#HELPTAG 357
                        --#STATE  OPERATIONAL

                    ::= 357

iPXnotReturningStatCheckPackets   TRAP-TYPE
                        ENTERPRISE      nwalarm-mib
                        VARIABLES       {
                                        serverName,trapTime,networkAddress
                                        }
                        DESCRIPTION
                      		"IPX Network is no longer returning status
                                 check packets"
                  	--#TYPE "SFT-III: IPX net not returning status checks"
                  	--#SUMMARY "IPX Network %x is no longer returning"
                        --#SUMMARY "status check packets on server %s"
	                --#ARGUMENTS {2,0}
                        --#SEVERITY INFORMATIONAL
                        --#TIMEINDEX 1
                        --#HELP "nwalarm.hlp"
                        --#HELPTAG 358
                        --#STATE  OPERATIONAL

                    ::= 358

iPXnotReturningStatPcktLANJammed     TRAP-TYPE
                        ENTERPRISE      nwalarm-mib
                        VARIABLES       {
                                        serverName,trapTime,networkAddress
                                        }
                        DESCRIPTION
                      		"IPX Network is no longer returning
                                 status check packets and the LAN adapter
                                 is jammed transmitting packets"
                  	--#TYPE "SFT-III: IPX net LAN adapter jammed"
                  	--#SUMMARY "IPX Network %x is no longer returning"
                        --#SUMMARY "status check packets and the LAN adapter"
                        --#SUMMARY "is jammed transmitting packets on NetWare"
                        --#SUMMARY "server %s"
	                --#ARGUMENTS {2,0}
                        --#SEVERITY INFORMATIONAL
                        --#TIMEINDEX 1
                        --#HELP "nwalarm.hlp"
                        --#HELPTAG 359
                        --#STATE  OPERATIONAL

                    ::= 359

failReasonByOtherSrvr    TRAP-TYPE
                        ENTERPRISE      nwalarm-mib
                        VARIABLES       {
                                        serverName,trapTime,serverName1
                                        }
                        DESCRIPTION
                      		"Failure reason as detected by other server"
                  	--#TYPE "SFT-III: Failure detected by other server"
                  	--#SUMMARY "%s: Failure reason as detected by"
                        --#SUMMARY "other server: %s"
	                --#ARGUMENTS {0,2}
                        --#SEVERITY INFORMATIONAL
                        --#TIMEINDEX 1
                        --#HELP "nwalarm.hlp"
                        --#HELPTAG 360
                        --#STATE  OPERATIONAL

                    ::= 360

iPXInternetIsJammed     TRAP-TYPE
                        ENTERPRISE      nwalarm-mib
                        VARIABLES       {
                                        serverName,trapTime
                                        }
                        DESCRIPTION
                      		"The IPX Internet is back up"
                  	--#TYPE "SFT-III: IPX Internet is back up"
                  	--#SUMMARY "%s: IPX Internet is back up"
	                --#ARGUMENTS {0}
                        --#SEVERITY MAJOR
                        --#TIMEINDEX 1
                        --#HELP "nwalarm.hlp"
                        --#HELPTAG 361
                        --#STATE  OPERATIONAL

                    ::= 361

iPXTooSlowForSecSrvr     TRAP-TYPE
                        ENTERPRISE      nwalarm-mib
                        VARIABLES       {
                                        serverName,trapTime
                                        }
                        DESCRIPTION
                      		"The IPX internet may be too slow to notify
                                 the secondary server if the MSL fails...
                                 increase the 'Secondary Take Over Delay
                                 Amount'"
                  	--#TYPE "SFT-III: IPX internet too slow"
                  	--#SUMMARY "%s: IPX internet may be too slow to"
                        --#SUMMARY "notify the secondary server if the MSL"
                        --#SUMMARY "fails; increase the 'Secondary Take Over"
                        --#SUMMARY "Wait Time'"
	                --#ARGUMENTS {0}
                        --#SEVERITY INFORMATIONAL
                        --#TIMEINDEX 1
                        --#HELP "nwalarm.hlp"
                        --#HELPTAG 362
                        --#STATE  OPERATIONAL

                    ::= 362

otherSrvrTooManyHops     TRAP-TYPE
                        ENTERPRISE      nwalarm-mib
                        VARIABLES       {
                                        serverName,trapTime
                                        }
                        DESCRIPTION
                      		"The IPX internet path to the other server
                                 has been detected as being greater than the
                                 'Maximum Pseudo Hop Count'"
                  	--#TYPE "SFT-III: IPX internet path Hop Count large"
                  	--#SUMMARY "IPX internet path to the other server"
                        --#SUMMARY "detected as being greater than"
                        --#SUMMARY "the 'Maximum Pseudo Hop Count'; this may"
                        --#SUMMARY "cause some IPX routers to delay on a"
                        --#SUMMARY "primary server (%s) switch over."
	                --#ARGUMENTS {0}
                        --#SEVERITY INFORMATIONAL
                        --#TIMEINDEX 1
                        --#HELP "nwalarm.hlp"
                        --#HELPTAG 363
                        --#STATE  OPERATIONAL

                    ::= 363

iPXappearsDown          TRAP-TYPE
                        ENTERPRISE      nwalarm-mib
                        VARIABLES       {
                                        serverName,trapTime
                                        }
                        DESCRIPTION
                      		"The IPX Internet appears to be down"
                  	--#TYPE "SFT-III: IPX Internet appears down"
                  	--#SUMMARY "server %s IPX Internet appears to be down"
                        --#SUMMARY "(no 'I'm alive' packets received for"
                        --#SUMMARY "a second)"
	                --#ARGUMENTS {0}
                        --#SEVERITY MAJOR
                        --#TIMEINDEX 1
                        --#HELP "nwalarm.hlp"
                        --#HELPTAG 364
                        --#STATE  OPERATIONAL

                    ::= 364

iPXFoundRouteToOtherSrvr TRAP-TYPE
                        ENTERPRISE      nwalarm-mib
                        VARIABLES       {
                                        serverName,trapTime
                                        }
                        DESCRIPTION
                      		"IPX route to the other server has been
                                 discovered"
                  	--#TYPE "SFT-III: IPX route discovered"
                  	--#SUMMARY "IPX route to the other server"
                        --#SUMMARY "discovered on NetWare server %s"
	                --#ARGUMENTS {0}
                        --#SEVERITY INFORMATIONAL
                        --#TIMEINDEX 1
                        --#HELP "nwalarm.hlp"
                        --#HELPTAG 365
                        --#STATE  OPERATIONAL

                    ::= 365

iPXNewRouteToSecSrvr    TRAP-TYPE
                        ENTERPRISE      nwalarm-mib
                        VARIABLES       {
                                        serverName,trapTime,boardNumber,
                                        iHopsCount,macAddress
                                        }
                        DESCRIPTION
                      		"New IPX route to other server"
                  	--#TYPE "SFT-III: IPX route to other server new"
                  	--#SUMMARY "New IPX route from %s to other server ="
                        --#SUMMARY "Board #%d, Hops %d,"
                        --#SUMMARY "Immediate Router = %x"
	                --#ARGUMENTS {0,2,3,4}
                        --#SEVERITY INFORMATIONAL
                        --#TIMEINDEX 1
                        --#HELP "nwalarm.hlp"
                        --#HELPTAG 366
                        --#STATE  OPERATIONAL

                    ::= 366

iPXLostRoute            TRAP-TYPE
                        ENTERPRISE      nwalarm-mib
                        VARIABLES       {
                                        serverName,trapTime
                                        }
                        DESCRIPTION
                      		"IPX route to the other server has been lost"
                  	--#TYPE "SFT-III: IPX route to the other server lost"
                  	--#SUMMARY "IPX route from NetWare server %s to the"
                        --#SUMMARY "other server lost"
	                --#ARGUMENTS {0}
                        --#SEVERITY INFORMATIONAL
                        --#TIMEINDEX 1
                        --#HELP "nwalarm.hlp"
                        --#HELPTAG 367
                        --#STATE  OPERATIONAL

                    ::= 367

secSrvrGoingToDie        TRAP-TYPE
                        ENTERPRISE      nwalarm-mib
                        VARIABLES       {
                                        serverName,trapTime,szReason,
                                        iTimerTicks
                                        }
                        DESCRIPTION
                      		"Secondary server will initiate error"
                  	--#TYPE "SFT-III: Secondary will initiate error"
                  	--#SUMMARY "%s: Secondary server will initiate error"
                        --#SUMMARY "by doing a %s after %d timer ticks"
	                --#ARGUMENTS {0,2,3}
                        --#SEVERITY INFORMATIONAL
                        --#TIMEINDEX 1
                        --#HELP "nwalarm.hlp"
                        --#HELPTAG 368
                        --#STATE  OPERATIONAL

                    ::= 368

priSrvrDyingTimerReStart   TRAP-TYPE
                        ENTERPRISE      nwalarm-mib
                        VARIABLES       {
                                        serverName,trapTime,szReason,
                                        iTimerTicks
                                        }
                        DESCRIPTION
                      		"Primary server will initiate error"
                  	--#TYPE "SFT-III: Primary will initiate err, after sync"
                  	--#SUMMARY "Primary server (%s) will initiate error"
                        --#SUMMARY "by doing a %s after %d timer ticks"
			--#SUMMARY "(but timer won't start until secondary"
                        --#SUMMARY "is fully synchronized)"
	                --#ARGUMENTS {0,2,3}
                        --#SEVERITY INFORMATIONAL
                        --#TIMEINDEX 1
                        --#HELP "nwalarm.hlp"
                        --#HELPTAG 369
                        --#STATE  OPERATIONAL

                    ::= 369

priSrvrDying             TRAP-TYPE
                        ENTERPRISE      nwalarm-mib
                        VARIABLES       {
                                        serverName,trapTime,szReason,
                                        iTimerTicks
                                        }
                        DESCRIPTION
                      		"Primary server will initiate error...dying"
                  	--#TYPE "SFT-III: Primary will initiate err"
                  	--#SUMMARY "Primary server (%s) will initiate error"
                        --#SUMMARY "by doing a %s after %d timer ticks"
	                --#ARGUMENTS {0,2,3}
                        --#SEVERITY INFORMATIONAL
                        --#TIMEINDEX 1
                        --#HELP "nwalarm.hlp"
                        --#HELPTAG 370
                        --#STATE  OPERATIONAL

                    ::= 370

noMemForOtherIOEngScreen   TRAP-TYPE
                        ENTERPRISE      nwalarm-mib
                        VARIABLES       {
                                        serverName,trapTime
                                        }
                        DESCRIPTION
                      		"Allocate memory for other IOEngine screen"
                  	--#TYPE "SFT-III: IOEngine screen mem alloc fail"
                  	--#SUMMARY "Unable to allocate memory for other "
                        --#SUMMARY "IOEngine screen on %s"
	                --#ARGUMENTS {0}
                        --#SEVERITY INFORMATIONAL
                        --#TIMEINDEX 1
                        --#HELP "nwalarm.hlp"
                        --#HELPTAG 371
                        --#STATE  OPERATIONAL

                    ::= 371

timesyncErrorMsg        TRAP-TYPE
                        ENTERPRISE      nwalarm-mib
                        VARIABLES       {
                                        serverName,trapTime
                                        }
                        DESCRIPTION
                      		"Timesync error"
                  	--#TYPE "TimeSync: Error"
                  	--#SUMMARY "server %s TIMESYNC: Error occurred."
	                --#ARGUMENTS {0}
                        --#SEVERITY CRITICAL
                        --#TIMEINDEX 1
                        --#HELP "nwalarm.hlp"
                        --#HELPTAG 372
                        --#STATE  OPERATIONAL

                    ::= 372
-- new DS alerts
dsAlertSetServerDown    TRAP-TYPE
                        ENTERPRISE      nwalarm-mib
                        VARIABLES       {
                                        serverName,trapTime,serverName1
                                        }
                        DESCRIPTION
                      		"Unable to communicate with server"
                  	--#TYPE "DS: Unable to communicate with server"
                  	--#SUMMARY "%s unable to communicate with server %s"
	                --#ARGUMENTS {0,2}
                        --#SEVERITY WARNING
                        --#TIMEINDEX 1
                        --#HELP "nwalarm.hlp"
                        --#HELPTAG 373
                        --#STATE  OPERATIONAL

                    ::= 373

dsAlertSetServerUp      TRAP-TYPE
                        ENTERPRISE      nwalarm-mib
                        VARIABLES       {
                                        serverName,trapTime,serverName1
                                        }
                        DESCRIPTION
                      		"Re-established communication with server"
                  	--#TYPE "DS: Re-established communication with server"
                  	--#SUMMARY "%s re-established comm with server %s"
	                --#ARGUMENTS {0,2}
                        --#SEVERITY WARNING
                        --#TIMEINDEX 1
                        --#HELP "nwalarm.hlp"
                        --#HELPTAG 374
                        --#STATE  OPERATIONAL

                    ::= 374

redirectTableMismatch	TRAP-TYPE
                        ENTERPRISE      nwalarm-mib
                        VARIABLES       {
                                        serverName,trapTime,partitionNumber,
                                        numberOfPackets
                        		}
                        DESCRIPTION
				"The system detected a redirection error table
				mismatch."
                        --#TYPE "Disk: Hotfix, redirection err table mismatch"
                        --#SUMMARY "Redirection error table mismatch detected "
			--#SUMMARY "on partition #%d device #%d on server %s."
                        --#ARGUMENTS {2,3,0}
                        --#SEVERITY INFORMATIONAL
                        --#TIMEINDEX 1
                        --#HELP "nwalarm.hlp"
                        --#HELPTAG 375
                        --#STATE  OPERATIONAL
                        ::= 375


nlmAlertMajor                   TRAP-TYPE  --1.5.18
                        ENTERPRISE      nwalarm-mib
                        VARIABLES       {
                                        serverName,trapTime,nlmName,
					nlmSeverity,message
                                        }
                        DESCRIPTION
                                "This trap will handle major traps being
				 generated by third-party NLMs and the
				 traps generated by driver NLMs written
				 by NOVELL or third party."

                        --#TYPE "NLM: Major alert"
			--#SUMMARY "%s: '%s', severity=%d, server %s"
			--#ARGUMENTS {2,4,3,0}
                        --#SEVERITY MAJOR
                        --#TIMEINDEX 1
                        --#HELP "nwalarm.hlp"
                        --#HELPTAG 376
                        --#STATE  OPERATIONAL

                        ::= 376

nlmAlertMinor                   TRAP-TYPE  --1.5.18
                        ENTERPRISE      nwalarm-mib
                        VARIABLES       {
                                        serverName,trapTime,nlmName,
					nlmSeverity,message
                                        }
                        DESCRIPTION
                                "This trap will handle minor traps being
				 generated by third-party NLMs and the
				 traps generated by driver NLMs written
				 by NOVELL or third party."

                        --#TYPE "NLM: Minor alert"
			--#SUMMARY "%s: '%s', severity=%d, server %s"
			--#ARGUMENTS {2,4,3,0}
                        --#SEVERITY MINOR
                        --#TIMEINDEX 1
                        --#HELP "nwalarm.hlp"
                        --#HELPTAG 377
                        --#STATE  OPERATIONAL

                        ::= 377

nlmAlertInformational           TRAP-TYPE  --1.5.18
                        ENTERPRISE      nwalarm-mib
                        VARIABLES       {
                                        serverName,trapTime,nlmName,
					nlmSeverity,message
                                        }
                        DESCRIPTION
                                "This trap will handle info traps being
				 generated by third-party NLMs and the
				 traps generated by driver NLMs written
				 by NOVELL or third party."

                        --#TYPE "NLM: Informational alert"
			--#SUMMARY "%s: '%s', severity=%d, server %s"
			--#ARGUMENTS {2,4,3,0}
                        --#SEVERITY INFORMATIONAL
                        --#TIMEINDEX 1
                        --#HELP "nwalarm.hlp"
                        --#HELPTAG 378
                        --#STATE  OPERATIONAL

                        ::= 378

END
