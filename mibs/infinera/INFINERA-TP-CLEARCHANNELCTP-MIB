-- *****************************************************************
-- INFINERA-TP-CLEARCHANNELCTP-MIB
--
-- October 2008, Sharfuddin Syed / Narendra Gupta
--
--
-- Copyright (c) 2008-2012 by Infinera Inc.
-- All rights reserved.
-- ****************************************************************

INFINERA-TP-CLEARCHANNELCTP-MIB DEFINITIONS ::= BEGIN

IMPORTS
    MODULE-IDENTITY, OBJECT-TYPE,
    Integer32                                   FROM SNMPv2-SMI
    MODULE-COMPLIANCE, OBJECT-GROUP             FROM SNMPv2-CONF
    DisplayString, TruthValue                   FROM SNMPv2-TC
    ifIndex                                     FROM IF-MIB
    FloatTenths, InfnServiceType,
    InfnServiceMode,InfnSMQ			FROM INFINERA-TC-MIB
    terminationPoint                            FROM INFINERA-REG-MIB;

clearChannelCtpMIB MODULE-IDENTITY
    LAST-UPDATED "200802180000Z"
    ORGANIZATION
        "Infinera"
    CONTACT-INFO
        "Infinera
                1322 Bordeaux Drive
                Sunnyvale, CA - 94089

                Contact : Technical Support
                Email   : support@infinera.com
                Phone   : 1-877-INF-5288"
    DESCRIPTION
        " "

    REVISION "200802180000Z"
    DESCRIPTION
        "First Version"
::= { terminationPoint 9 }


-- Conformance Statements

clearChannelCtpConformance  OBJECT IDENTIFIER ::= { clearChannelCtpMIB 3 }
clearChannelCtpCompliances  OBJECT IDENTIFIER ::= { clearChannelCtpConformance 1 }
clearChannelCtpGroups  OBJECT IDENTIFIER ::= { clearChannelCtpConformance 2 }

-- February 18, 2008
-- February 18, 2008

clearChannelCtpTable  OBJECT-TYPE
    SYNTAX SEQUENCE OF ClearChannelCtpEntry
    MAX-ACCESS not-accessible
    STATUS     current
    DESCRIPTION
        "A list of clearChannelCtp entries. Each entry is uniquely identified by the value of ifIndex."
    ::= { clearChannelCtpMIB 1 }

clearChannelCtpEntry  OBJECT-TYPE
    SYNTAX     ClearChannelCtpEntry
    MAX-ACCESS not-accessible
    STATUS     current
    DESCRIPTION
        "A clearChannelCtp entry containing information pertaining to Infinera clearChannelCtp interfaces.
                This table is a subclass of IfCommon. Entries will exist in this table only for interfaces of
                type clearChannelCtp."
    INDEX { ifIndex }
    ::= { clearChannelCtpTable 1 }

ClearChannelCtpEntry  ::= SEQUENCE {
    clearChannelCtpSupportingCircuitIdList    DisplayString,
    clearChannelCtpLoopback                   INTEGER,
    clearChannelCtpPmHistStatsEnable          INTEGER,
    clearChannelCtpConfiguredServiceType      InfnServiceType,
    clearChannelCtpServiceMode 			InfnServiceMode,
    clearChannelCtpServiceModeQualifier	      	InfnSMQ
}

clearChannelCtpSupportingCircuitIdList  OBJECT-TYPE
    SYNTAX     DisplayString
    MAX-ACCESS read-only
    STATUS     current
    DESCRIPTION
        "An unordered list of the Circuit Id's which support this entry.
         This string contains the string representation of each supporting
          CircuitId, separated by a ',' (comma) if there is more than one."
    ::= { clearChannelCtpEntry 1 }

clearChannelCtpLoopback  OBJECT-TYPE
    SYNTAX     INTEGER {
        none (1),
        terminal (2),
        facility (3)
    }
    MAX-ACCESS read-write
    STATUS     current
    DESCRIPTION
        "Flag that indicates if loopback is enabled or disabled."
    DEFVAL  { none }
    ::= { clearChannelCtpEntry 2 }

clearChannelCtpPmHistStatsEnable  OBJECT-TYPE
    SYNTAX     INTEGER {
        enabled (1),
        disabled (2)
    }
    MAX-ACCESS read-write
    STATUS     obsolete
    DESCRIPTION
        "Flag to enable or disable PM collection."
    DEFVAL  { enabled }
    ::= { clearChannelCtpEntry 3 }

clearChannelCtpConfiguredServiceType  OBJECT-TYPE
    SYNTAX     InfnServiceType
    MAX-ACCESS read-only
    STATUS     current
    DESCRIPTION
        "The configured service type."
    ::= { clearChannelCtpEntry 4 }

clearChannelCtpServiceMode OBJECT-TYPE
    SYNTAX  InfnServiceMode
    MAX-ACCESS  read-only
    STATUS      current
    DESCRIPTION "ServiceMode of ClearChannel client CTP."
    DEFVAL      { none }
    ::= { clearChannelCtpEntry  5 }

clearChannelCtpServiceModeQualifier  OBJECT-TYPE
    SYNTAX      InfnSMQ
    MAX-ACCESS  read-only
    STATUS      current
    DESCRIPTION "The Service Mode Qualifier (SMQ) of the ClearChannel client CTP (i.e., the mode/type of service in which
        this ClearChannel client CTP is being used,). None’ is the default value indicated for the ClearChannel client CTP when it is initially created."
    DEFVAL      { none }
    ::= { clearChannelCtpEntry  6 }

clearChannelCtpCompliance  MODULE-COMPLIANCE
    STATUS     current
    DESCRIPTION
        "Describes the requirements for conformance to the CLEARCHANNELCTP-MIB"
    MODULE
        MANDATORY-GROUPS { clearChannelCtpGroup }
    ::= { clearChannelCtpCompliances 1 }

clearChannelCtpGroup  OBJECT-GROUP
    OBJECTS { clearChannelCtpSupportingCircuitIdList,
        clearChannelCtpLoopback,
        clearChannelCtpPmHistStatsEnable,
        clearChannelCtpConfiguredServiceType,
        clearChannelCtpServiceMode,
        clearChannelCtpServiceModeQualifier }
    STATUS     current
    DESCRIPTION
        " A collection of objects for managing the clearChannelCtp"
    ::= { clearChannelCtpGroups 1 }
END
