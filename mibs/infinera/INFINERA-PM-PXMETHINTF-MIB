-- *****************************************************************
-- INFINERA-PM-PXMETHINTF-MIB
--
-- February 2015, Mithun Murthy / Narendra Gupta
--
--
-- Copyright (c) 2008-2012 by Infinera Inc.
-- All rights reserved.
-- ****************************************************************

INFINERA-PM-PXMETHINTF-MIB DEFINITIONS ::= BEGIN

IMPORTS
MODULE-IDENTITY, OBJECT-TYPE,
    Integer32, Counter64                        FROM SNMPv2-SMI
    MODULE-COMPLIANCE, OBJECT-GROUP             FROM SNMPv2-CONF
    DisplayString, TruthValue                   FROM SNMPv2-TC
    ifIndex                                     FROM IF-MIB
    HCPerfIntervalCount                         FROM HC-PerfHist-TC-MIB
    FloatHundredths,InfnServiceType             FROM INFINERA-TC-MIB
    perfMon                                     FROM INFINERA-REG-MIB;

pxmEthIntfPmMIB MODULE-IDENTITY
    LAST-UPDATED  "201402190000Z"
    ORGANIZATION  "Infinera"
    CONTACT-INFO
        "Infinera
        1322 Bordeaux Drive
        Sunnyvale, CA - 94089

        Contact : Technical Support
        Email   : support@infinera.com
        Phone   : 1-877-INF-5288"
    DESCRIPTION
    " "
    REVISION      "201402190000Z"
    DESCRIPTION
        "First Version"
    ::= { perfMon 97}

pxmEthIntfRmonPm      OBJECT IDENTIFIER ::= { pxmEthIntfPmMIB 1 }

pxmEthIntfPmTable OBJECT-TYPE
    SYNTAX      SEQUENCE OF PxmEthIntfPmEntry
    MAX-ACCESS  not-accessible
    STATUS      current
    DESCRIPTION
    "A list of PxmEthIntfPm entries. Each entry is uniquely identified by the value of ifIndex, sampleDuration and
    pxmEthIntfPmTimestamp."
    ::= { pxmEthIntfRmonPm 2 }

pxmEthIntfPmEntry  OBJECT-TYPE
    SYNTAX      PxmEthIntfPmEntry
    MAX-ACCESS  not-accessible
    STATUS      current
    DESCRIPTION
    "A PxmEthIntf entry containing historical performance information pertaining to Infinera
    PxmEthIntf interfaces. This table is a subclass of IfCommon. Entries will exist in this
    table only for interfaces of type PxmEthIntf.
    Each interface may have a number of entries in this table, each with a different combination
    of timestamp and sample duration."
    INDEX { ifIndex, pxmEthIntfPmSampleDuration, pxmEthIntfPmTimestamp }
    ::= { pxmEthIntfPmTable 1 }

PxmEthIntfPmEntry  ::= SEQUENCE {
    pxmEthIntfPmTimestamp           Integer32,
    pxmEthIntfPmSampleDuration      INTEGER,
    pxmEthIntfPmValidity            TruthValue,
    pxmEthIntfPmRxPackets           HCPerfIntervalCount,
    pxmEthIntfPmRxOctets            HCPerfIntervalCount,
    pxmEthIntfPmRxCrcAlignedErr     Integer32,
    pxmEthIntfPmRxUndersized        HCPerfIntervalCount,
    pxmEthIntfPmRxOversized         HCPerfIntervalCount,
    pxmEthIntfPmRxUnicastPkts       HCPerfIntervalCount,
    pxmEthIntfPmRxBroadcastPkts     HCPerfIntervalCount,
    pxmEthIntfPmRxMulticastPkts     HCPerfIntervalCount,
    pxmEthIntfPmRxPktErrors         HCPerfIntervalCount,
    pxmEthIntfPmRxSize64            HCPerfIntervalCount,
    pxmEthIntfPmRxSize65to127       HCPerfIntervalCount,
    pxmEthIntfPmRxSize128to255      HCPerfIntervalCount,
    pxmEthIntfPmRxSize256to511      HCPerfIntervalCount,
    pxmEthIntfPmRxSize512to1023     HCPerfIntervalCount,
    pxmEthIntfPmRxSize1024to1518    HCPerfIntervalCount,
    pxmEthIntfPmTxPackets           HCPerfIntervalCount,
    pxmEthIntfPmTxOctets            HCPerfIntervalCount,
    pxmEthIntfPmTxUnicastPkts       HCPerfIntervalCount,
    pxmEthIntfPmTxBroadcastPkts     HCPerfIntervalCount,
    pxmEthIntfPmTxMulticastPkts     HCPerfIntervalCount,
    pxmEthIntfPmTxPktErrors         HCPerfIntervalCount
}

pxmEthIntfPmTimestamp OBJECT-TYPE
    SYNTAX      Integer32 (0..2147483647)
    MAX-ACCESS  not-accessible
    STATUS      current
    DESCRIPTION
    "End Time stamp for this interval. If this time is later than the current time,
    then the data for this bucket is currently being collected."
    ::= { pxmEthIntfPmEntry  1 }


pxmEthIntfPmSampleDuration OBJECT-TYPE
    SYNTAX      INTEGER {
        fifteenMinutes(1),
        day(2)
        }
    MAX-ACCESS  not-accessible
    STATUS      current
    DESCRIPTION
        "The duration of this sample."
    ::= { pxmEthIntfPmEntry  2 }

pxmEthIntfPmValidity OBJECT-TYPE
    SYNTAX      TruthValue
    MAX-ACCESS  read-only
    STATUS      current
    DESCRIPTION "Flag indicating if data was valid for the entire interval"
    ::= { pxmEthIntfPmEntry  3 }

pxmEthIntfPmRxPackets OBJECT-TYPE
    SYNTAX      HCPerfIntervalCount
    MAX-ACCESS  read-only
    STATUS      current
    DESCRIPTION "Number of received data packets."
    ::= { pxmEthIntfPmEntry  4 }

pxmEthIntfPmRxOctets OBJECT-TYPE
    SYNTAX      HCPerfIntervalCount
    MAX-ACCESS  read-only
    STATUS      current
    DESCRIPTION "Number of received data octets."
    ::= { pxmEthIntfPmEntry  5 }

pxmEthIntfPmRxCrcAlignedErr OBJECT-TYPE
    SYNTAX      Integer32
    MAX-ACCESS  read-only
    STATUS      current
    DESCRIPTION "Cyclical redundancy check align error count. Number of packets received that have a length
        (excluding framing bits, but including FCS octets) of between 64 and MaxFrameLength octets, inclusive,
        but have either a bad FCS with   an integral number of octets (FCS Error) or a bad FCS with a non-
        integral number of octets (Alignment Error), on the receive client interface."
    ::= { pxmEthIntfPmEntry  6 }

pxmEthIntfPmRxUndersized OBJECT-TYPE
    SYNTAX      HCPerfIntervalCount
    MAX-ACCESS  read-only
    STATUS      current
    DESCRIPTION "Undersize packet count. Number of received packets that are less than 64 octets long (excluding
        framing bits, but including FCS octets) and are otherwise well formed, on the receive client interface."
    ::= { pxmEthIntfPmEntry  7 }


pxmEthIntfPmRxOversized OBJECT-TYPE
    SYNTAX      HCPerfIntervalCount
    MAX-ACCESS  read-only
    STATUS      current
    DESCRIPTION "Oversize packet count. Number of received packets that are longer than the maximum frame length
        (excluding  framing bits, but including FCS octets) and are otherwise well formed, on the receive client
        interface."
    ::= { pxmEthIntfPmEntry  8 }

pxmEthIntfPmRxUnicastPkts OBJECT-TYPE
    SYNTAX      HCPerfIntervalCount
    MAX-ACCESS  read-only
    STATUS      current
    DESCRIPTION "A count of frames that are successfully received and are directed to the unicast address. This
        does not include frames received with frame-too-long, FCS, length, or alignment errors, or frames lost due to
        internal MAC sublayer error."
    ::= { pxmEthIntfPmEntry  9 }

pxmEthIntfPmRxBroadcastPkts OBJECT-TYPE
    SYNTAX      HCPerfIntervalCount
    MAX-ACCESS  read-only
    STATUS      current
    DESCRIPTION "A count of frames that are successfully received and are directed to the broadcast group address. This
        does not include frames received with frame-too-long, FCS, length, or alignment errors, or frames lost due to
        internal MAC sublayer error."
    ::= { pxmEthIntfPmEntry  10 }

pxmEthIntfPmRxMulticastPkts OBJECT-TYPE
    SYNTAX      HCPerfIntervalCount
    MAX-ACCESS  read-only
    STATUS      current
    DESCRIPTION "A count of frames that are successfully received and are directed to an active nonbroadcast group
        address.  This does not include frames received with frame-too-long, FCS, length, or alignment errors, or frames
        lost due to internal  MAC sublayer error."
    ::= { pxmEthIntfPmEntry  11 }


pxmEthIntfPmRxPktErrors OBJECT-TYPE
    SYNTAX      HCPerfIntervalCount
    MAX-ACCESS  read-only
    STATUS      current
    DESCRIPTION "Number of data packets that are part of an Errored Packet (i.e., the FCS is in
        error, resulting in incrementing the Fragment counter, the Jabber counter, or the CRCAlignError counter), at the
        signal de-encapsulation point before the client-side transmit interface."
    ::= { pxmEthIntfPmEntry  12 }


pxmEthIntfPmRxSize64 OBJECT-TYPE
    SYNTAX      HCPerfIntervalCount
    MAX-ACCESS  read-only
    STATUS      current
    DESCRIPTION "Received packets (including bad packets) of 64 or less octets."
    ::= { pxmEthIntfPmEntry  13 }

pxmEthIntfPmRxSize65to127 OBJECT-TYPE
    SYNTAX      HCPerfIntervalCount
    MAX-ACCESS  read-only
    STATUS      current
    DESCRIPTION "Received packets (including bad packets) from 65 to 127 octets."
    ::= { pxmEthIntfPmEntry 14 }


pxmEthIntfPmRxSize128to255 OBJECT-TYPE
    SYNTAX      HCPerfIntervalCount
    MAX-ACCESS  read-only
    STATUS      current
    DESCRIPTION "Received packets (including bad packets) from 128 to 255 octets."
    ::= { pxmEthIntfPmEntry  15 }


pxmEthIntfPmRxSize256to511 OBJECT-TYPE
    SYNTAX      HCPerfIntervalCount
    MAX-ACCESS  read-only
    STATUS      current
    DESCRIPTION "Received packets (including bad packets) from 256 to 511 octets."
    ::= { pxmEthIntfPmEntry  16 }


pxmEthIntfPmRxSize512to1023 OBJECT-TYPE
    SYNTAX      HCPerfIntervalCount
    MAX-ACCESS  read-only
    STATUS      current
    DESCRIPTION "Received packets (including bad packets) from 512 to 1023 octets."
    ::= { pxmEthIntfPmEntry  17 }

pxmEthIntfPmRxSize1024to1518 OBJECT-TYPE
    SYNTAX      HCPerfIntervalCount
    MAX-ACCESS  read-only
    STATUS      current
    DESCRIPTION "Received packets (including bad packets) from 1024 to 1518 octets."
    ::= { pxmEthIntfPmEntry  18 }

pxmEthIntfPmTxPackets OBJECT-TYPE
    SYNTAX      HCPerfIntervalCount
    MAX-ACCESS  read-only
    STATUS      current
    DESCRIPTION "Number of transmitted data packets."
    ::= { pxmEthIntfPmEntry  19 }

pxmEthIntfPmTxOctets OBJECT-TYPE
    SYNTAX      HCPerfIntervalCount
    MAX-ACCESS  read-only
    STATUS      current
    DESCRIPTION "Number of transmitted data octets."
    ::= { pxmEthIntfPmEntry  20 }

pxmEthIntfPmTxUnicastPkts OBJECT-TYPE
    SYNTAX      HCPerfIntervalCount
    MAX-ACCESS  read-only
    STATUS      current
    DESCRIPTION "A count of the frames that were successfully transmitted, as indicated by the transmit status
        <93>transmit  OK<94>, to the broadcast address. Frames transmitted to multicast addresses are not broadcast
        frames and are excluded."
    ::= { pxmEthIntfPmEntry  21 }

pxmEthIntfPmTxBroadcastPkts OBJECT-TYPE
    SYNTAX      HCPerfIntervalCount
    MAX-ACCESS  read-only
    STATUS      current
    DESCRIPTION "A count of the frames that were successfully transmitted, as indicated by the transmit status
                <93>transmit  OK<94>, to the broadcast address. Frames transmitted to multicast addresses are
                 not broadcast frames and are excluded."
    ::= { pxmEthIntfPmEntry  22 }


pxmEthIntfPmTxMulticastPkts OBJECT-TYPE
    SYNTAX      HCPerfIntervalCount
    MAX-ACCESS  read-only
    STATUS      current
    DESCRIPTION "A count of frames that are successfully transmitted, as indicated by the status value
                <93>transmit OK<94>,  to a group destination address other than broadcast."
    ::= { pxmEthIntfPmEntry  23 }


pxmEthIntfPmTxPktErrors OBJECT-TYPE
    SYNTAX      HCPerfIntervalCount
    MAX-ACCESS  read-only
    STATUS      current
    DESCRIPTION "Number of data octets that are part of an Errored Packet (i.e., the FCS is in error,
                 resulting in incrementing the Fragment counter, the Jabber counter, or the CRCAlignError
                 counter), at the signal de-encapsulation point before the client-side transmit interface."
    ::= { pxmEthIntfPmEntry  24 }

--Real Time entries

pxmEthIntfPmRealTable OBJECT-TYPE
    SYNTAX      SEQUENCE OF PxmEthIntfPmRealEntry
    MAX-ACCESS  not-accessible
    STATUS      current
    DESCRIPTION
        "A list of PxmEthIntfPmReal entries. Each entry is uniquely identified by the value of ifIndex."
    ::= { pxmEthIntfRmonPm 1 }

pxmEthIntfPmRealEntry  OBJECT-TYPE
    SYNTAX      PxmEthIntfPmRealEntry
    MAX-ACCESS  not-accessible
    STATUS      current
    DESCRIPTION
    "A PxmEthIntf entry containing real-time performance information pertaining to Infinera PxmEthIntf
    interfaces.This table is a subclass of IfCommon. Entries will exist in this table only for interfaces of
    type PxmEthIntf."
    INDEX { ifIndex }
    ::= { pxmEthIntfPmRealTable 1 }

PxmEthIntfPmRealEntry  ::= SEQUENCE {
        pxmEthIntfPmRealRxPackets           Counter64,
        pxmEthIntfPmRealRxOctets            Counter64,
        pxmEthIntfPmRealRxCrcAlignedErr     Integer32,
        pxmEthIntfPmRealRxUndersized        Counter64,
        pxmEthIntfPmRealRxOversized         Counter64,
        pxmEthIntfPmRealRxUnicastPkts       Counter64,
        pxmEthIntfPmRealRxBroadcastPkts     Counter64,
        pxmEthIntfPmRealRxMulticastPkts     Counter64,
        pxmEthIntfPmRealRxPktErrors         Counter64,
        pxmEthIntfPmRealRxSize64            Counter64,
        pxmEthIntfPmRealRxSize65to127       Counter64,
        pxmEthIntfPmRealRxSize128to255      Counter64,
        pxmEthIntfPmRealRxSize256to511      Counter64,
        pxmEthIntfPmRealRxSize512to1023     Counter64,
        pxmEthIntfPmRealRxSize1024to1518    Counter64,
        pxmEthIntfPmRealRxLU                FloatHundredths,
        pxmEthIntfPmRealTxPackets           Counter64,
        pxmEthIntfPmRealTxOctets            Counter64,
        pxmEthIntfPmRealTxUnicastPkts       Counter64,
        pxmEthIntfPmRealTxBroadcastPkts     Counter64,
        pxmEthIntfPmRealTxMulticastPkts     Counter64,
        pxmEthIntfPmRealTxPktErrors         Counter64,
        pxmEthIntfPmRealTxLU                FloatHundredths
}

pxmEthIntfPmRealRxPackets OBJECT-TYPE
    SYNTAX      Counter64
    MAX-ACCESS  read-only
    STATUS      current
    DESCRIPTION "Number of received data packets."
    ::= { pxmEthIntfPmRealEntry  1 }


pxmEthIntfPmRealRxOctets OBJECT-TYPE
    SYNTAX      Counter64
    MAX-ACCESS  read-only
    STATUS      current
    DESCRIPTION "Number of received data octets."
    ::= { pxmEthIntfPmRealEntry  2 }

pxmEthIntfPmRealRxCrcAlignedErr OBJECT-TYPE
    SYNTAX      Integer32
    MAX-ACCESS  read-only
    STATUS      current
    DESCRIPTION "Cyclical redundancy check align error count. Number of packets received that have a length (excluding       framing bits, but including FCS octets) of between 64 and MaxFrameLength octets, inclusive, but have either a bad FCS with   an integral number of octets (FCS Error) or a bad FCS with a non-integral number of octets (Alignment Error), on the receive client interface."
    ::= { pxmEthIntfPmRealEntry  3 }


pxmEthIntfPmRealRxUndersized OBJECT-TYPE
    SYNTAX      Counter64
    MAX-ACCESS  read-only
    STATUS      current
    DESCRIPTION "Undersize packet count. Number of received packets that are less than 64 octets long (excluding framing     bits, but including FCS octets) and are otherwise well formed, on the receive client interface."
    ::= { pxmEthIntfPmRealEntry  4 }


pxmEthIntfPmRealRxOversized OBJECT-TYPE
    SYNTAX      Counter64
    MAX-ACCESS  read-only
    STATUS      current
    DESCRIPTION "Oversize packet count. Number of received packets that are longer than the maximum frame length (excluding  framing bits, but including FCS octets) and are otherwise well formed, on the receive client interface."
    ::= { pxmEthIntfPmRealEntry  5 }


pxmEthIntfPmRealRxUnicastPkts OBJECT-TYPE
    SYNTAX      Counter64
    MAX-ACCESS  read-only
    STATUS      current
    DESCRIPTION "A count of frames that are successfully received and are directed to the
                 broadcast group address. This does not include frames received with frame-too-long,
                 FCS, length, or alignment errors, or frames lost due to internal MAC sublayer error."
    ::= { pxmEthIntfPmRealEntry  6 }

pxmEthIntfPmRealRxBroadcastPkts OBJECT-TYPE
    SYNTAX      Counter64
    MAX-ACCESS  read-only
    STATUS      current
    DESCRIPTION "A count of frames that are successfully received and are directed to the broadcast
                 group address. This does not include frames received with frame-too-long, FCS,
                 length, or alignment errors, or frames lost due to internal MAC sublayer error."
    ::= { pxmEthIntfPmRealEntry  7 }

pxmEthIntfPmRealRxMulticastPkts OBJECT-TYPE
    SYNTAX      Counter64
    MAX-ACCESS  read-only
    STATUS      current
    DESCRIPTION "A count of frames that are successfully received and are directed to an active
                 nonbroadcast group address.  This does not include frames received with frame-too-long,
                 FCS, length, or alignment errors, or frames lost due to internal  MAC sublayer error."
    ::= { pxmEthIntfPmRealEntry  8 }

pxmEthIntfPmRealRxPktErrors OBJECT-TYPE
    SYNTAX      Counter64
    MAX-ACCESS  read-only
    STATUS      current
    DESCRIPTION "Errored octet. Number of data octets that are part of an Errored Packet
                (i.e., the FCS is in error, resulting in incrementing the Fragment counter,
                the Jabber counter, or the CRCAlignError counter), at the signal
                de-encapsulation point before the client-side transmit interface."
    ::= { pxmEthIntfPmRealEntry  9 }

pxmEthIntfPmRealRxSize64 OBJECT-TYPE
    SYNTAX      Counter64
    MAX-ACCESS  read-only
    STATUS      current
    DESCRIPTION "Received packets (including bad packets) of 64 or less octets."
    ::= { pxmEthIntfPmRealEntry  10 }

pxmEthIntfPmRealRxSize65to127 OBJECT-TYPE
    SYNTAX      Counter64
    MAX-ACCESS  read-only
    STATUS      current
    DESCRIPTION "Received packets (including bad packets) from 65 to 127 octets."
    ::= { pxmEthIntfPmRealEntry  11 }

pxmEthIntfPmRealRxSize128to255 OBJECT-TYPE
    SYNTAX      Counter64
    MAX-ACCESS  read-only
    STATUS      current
    DESCRIPTION "Received packets (including bad packets) from 128 to 255 octets."
    ::= { pxmEthIntfPmRealEntry  12 }

pxmEthIntfPmRealRxSize256to511 OBJECT-TYPE
    SYNTAX      Counter64
    MAX-ACCESS  read-only
    STATUS      current
    DESCRIPTION "Received packets (including bad packets) from 256 to 511 octets."
    ::= { pxmEthIntfPmRealEntry  13 }

pxmEthIntfPmRealRxSize512to1023 OBJECT-TYPE
    SYNTAX      Counter64
    MAX-ACCESS  read-only
    STATUS      current
    DESCRIPTION "Received packets (including bad packets) from 512 to 1023 octets."
    ::= { pxmEthIntfPmRealEntry  14 }

pxmEthIntfPmRealRxSize1024to1518 OBJECT-TYPE
    SYNTAX      Counter64
    MAX-ACCESS  read-only
    STATUS      current
    DESCRIPTION "Received packets (including bad packets) from 1024 to 1518 octets."
    ::= { pxmEthIntfPmRealEntry  15 }

pxmEthIntfPmRealRxLU OBJECT-TYPE
    SYNTAX      FloatHundredths
    MAX-ACCESS  read-only
    STATUS      current
    DESCRIPTION "Receive Link utilization."
    ::= { pxmEthIntfPmRealEntry  16 }

pxmEthIntfPmRealTxPackets OBJECT-TYPE
    SYNTAX      Counter64
    MAX-ACCESS  read-only
    STATUS      current
    DESCRIPTION "Number of transmitted data packets."
    ::= { pxmEthIntfPmRealEntry  17 }

pxmEthIntfPmRealTxOctets OBJECT-TYPE
    SYNTAX      Counter64
    MAX-ACCESS  read-only
    STATUS      current
    DESCRIPTION "Number of transmitted data octets."
    ::= { pxmEthIntfPmRealEntry  18 }

pxmEthIntfPmRealTxUnicastPkts OBJECT-TYPE
    SYNTAX      Counter64
    MAX-ACCESS  read-only
    STATUS      current
    DESCRIPTION "A count of the frames that were successfully transmitted, as indicated by the
                transmit status <93>transmit  OK<94>, to the broadcast address.
                Frames transmitted to multicast addresses are not broadcast frames and are excluded."
    ::= { pxmEthIntfPmRealEntry  19 }

pxmEthIntfPmRealTxBroadcastPkts OBJECT-TYPE
    SYNTAX      Counter64
    MAX-ACCESS  read-only
    STATUS      current
    DESCRIPTION "A count of the frames that were successfully transmitted, as indicated by the
                 transmit status <93>transmit  OK<94>, to the broadcast address. Frames transmitted
                 to multicast addresses are not broadcast frames and are excluded."
    ::= { pxmEthIntfPmRealEntry  20 }

pxmEthIntfPmRealTxMulticastPkts OBJECT-TYPE
    SYNTAX      Counter64
    MAX-ACCESS  read-only
    STATUS      current
    DESCRIPTION "A count of frames that are successfully transmitted, as indicated by the status
                 value <93>transmit OK<94>,  to a group destination address other than broadcast."
    ::= { pxmEthIntfPmRealEntry  21 }

pxmEthIntfPmRealTxPktErrors OBJECT-TYPE
    SYNTAX      Counter64
    MAX-ACCESS  read-only
    STATUS      current
    DESCRIPTION "Number of data octets that are part of an Errored Packet (i.e., the FCS is in error,
                 resulting in incrementing the Fragment counter, the Jabber counter, or the CRCAlignError
                 counter), at the signal de-encapsulation point before the client-side transmit interface."
    ::= { pxmEthIntfPmRealEntry  22 }

pxmEthIntfPmRealTxLU OBJECT-TYPE
    SYNTAX      FloatHundredths
    MAX-ACCESS  read-only
    STATUS      current
    DESCRIPTION "Transmit Link utilization."
    ::= { pxmEthIntfPmRealEntry  23 }

-- BWP PMs
pxmEthIntfBwpPm      OBJECT IDENTIFIER ::= { pxmEthIntfPmMIB 2 }

pxmBwpEthIntfPmTable OBJECT-TYPE
    SYNTAX      SEQUENCE OF PxmBwpEthIntfPmEntry
    MAX-ACCESS  not-accessible
    STATUS      current
    DESCRIPTION
        "A list of PxmBwpEthIntfPm entries. Each entry is uniquely identified by the value of ifIndex, sampleDuration and pxmEthIntfPmTimestamp."
    ::= { pxmEthIntfBwpPm 2 }

pxmBwpEthIntfPmEntry  OBJECT-TYPE
    SYNTAX      PxmBwpEthIntfPmEntry
    MAX-ACCESS  not-accessible
    STATUS      current
    DESCRIPTION
        "A PxmBwpEthIntf entry containing historical performance information pertaining to Infinera
        PxmEthIntf interfaces. This table is a subclass of IfCommon. Entries will exist in this
        table only for interfaces of type PxmEthIntf.
        Each interface may have a number of entries in this table, each with a different combination
        of timestamp and sample duration."
    INDEX { ifIndex, pxmBwpEthIntfPmSampleDuration, pxmBwpEthIntfPmTimestamp }
    ::= { pxmBwpEthIntfPmTable 1 }

PxmBwpEthIntfPmEntry  ::= SEQUENCE {
    pxmBwpEthIntfPmTimestamp            Integer32,
    pxmBwpEthIntfPmSampleDuration       INTEGER,
    pxmBwpEthIntfPmValidity             TruthValue,
    pxmBwpEthIntfPmPolicerConformedPkts         HCPerfIntervalCount,
    pxmBwpEthIntfPmPolicerConformedOctets       HCPerfIntervalCount,
    pxmBwpEthIntfPmPolicerExceededPkts          HCPerfIntervalCount,
    pxmBwpEthIntfPmPolicerExceededOctets        HCPerfIntervalCount,
    pxmBwpEthIntfPmPolicerViolatedPkts          HCPerfIntervalCount,
    pxmBwpEthIntfPmPolicerViolatedOctets        HCPerfIntervalCount
}

pxmBwpEthIntfPmTimestamp OBJECT-TYPE
    SYNTAX      Integer32 (0..2147483647)
    MAX-ACCESS  not-accessible
    STATUS      current
    DESCRIPTION
        "End Time stamp for this interval. If this time is later than the current time,
        then the data for this bucket is currently being collected."
    ::= { pxmBwpEthIntfPmEntry  1 }

pxmBwpEthIntfPmSampleDuration OBJECT-TYPE
    SYNTAX      INTEGER {
                    fifteenMinutes(1),
                    day(2)
                }
    MAX-ACCESS  not-accessible
    STATUS      current
    DESCRIPTION
        "The duration of this sample."
    ::= { pxmBwpEthIntfPmEntry  2 }

pxmBwpEthIntfPmValidity OBJECT-TYPE
    SYNTAX      TruthValue
    MAX-ACCESS  read-only
    STATUS      current
    DESCRIPTION "Flag indicating if data was valid for the entire interval"
    ::= { pxmBwpEthIntfPmEntry  3 }

pxmBwpEthIntfPmPolicerConformedPkts OBJECT-TYPE
    SYNTAX      HCPerfIntervalCount
    MAX-ACCESS  read-only
    STATUS      current
    DESCRIPTION ""
    ::= { pxmBwpEthIntfPmEntry  4 }

pxmBwpEthIntfPmPolicerConformedOctets OBJECT-TYPE
    SYNTAX      HCPerfIntervalCount
    MAX-ACCESS  read-only
    STATUS      current
    DESCRIPTION ""
    ::= { pxmBwpEthIntfPmEntry  5 }

pxmBwpEthIntfPmPolicerExceededPkts OBJECT-TYPE
    SYNTAX      HCPerfIntervalCount
    MAX-ACCESS  read-only
    STATUS      current
    DESCRIPTION ""
    ::= { pxmBwpEthIntfPmEntry  6 }

pxmBwpEthIntfPmPolicerExceededOctets OBJECT-TYPE
    SYNTAX      HCPerfIntervalCount
    MAX-ACCESS  read-only
    STATUS      current
    DESCRIPTION ""
    ::= { pxmBwpEthIntfPmEntry  7 }

pxmBwpEthIntfPmPolicerViolatedPkts OBJECT-TYPE
    SYNTAX      HCPerfIntervalCount
    MAX-ACCESS  read-only
    STATUS      current
    DESCRIPTION ""
    ::= { pxmBwpEthIntfPmEntry  8 }

pxmBwpEthIntfPmPolicerViolatedOctets OBJECT-TYPE
    SYNTAX      HCPerfIntervalCount
    MAX-ACCESS  read-only
    STATUS      current
    DESCRIPTION ""
    ::= { pxmBwpEthIntfPmEntry  9 }

-- BWP Real
pxmBwpEthIntfPmRealTable OBJECT-TYPE
    SYNTAX      SEQUENCE OF PxmBwpEthIntfPmRealEntry
    MAX-ACCESS  not-accessible
    STATUS      current
    DESCRIPTION
        "A list of PxmBwpEthIntfPmReal entries. Each entry is uniquely identified by the value of ifIndex."
    ::= { pxmEthIntfBwpPm 1 }

pxmBwpEthIntfPmRealEntry  OBJECT-TYPE
    SYNTAX      PxmBwpEthIntfPmRealEntry
    MAX-ACCESS  not-accessible
    STATUS      current
    DESCRIPTION
        "A PxmBwpEthIntfPm entry containing real-time performance information pertaining to Infinera
        PxmEthIntfPm interfaces.This table is a subclass of IfCommon. Entries will exist in this table
        only for interfaces of type PxmEthIntfPm."
    INDEX { ifIndex }
    ::= { pxmBwpEthIntfPmRealTable 1 }

PxmBwpEthIntfPmRealEntry  ::= SEQUENCE {
    pxmBwpEthIntfPmRealPolicerConformedPkts    Counter64,
    pxmBwpEthIntfPmRealPolicerConformedOctets  Counter64,
    pxmBwpEthIntfPmRealPolicerExceededPkts     Counter64,
    pxmBwpEthIntfPmRealPolicerExceededOctets   Counter64,
    pxmBwpEthIntfPmRealPolicerViolatedPkts     Counter64,
    pxmBwpEthIntfPmRealPolicerViolatedOctets   Counter64
}

pxmBwpEthIntfPmRealPolicerConformedPkts OBJECT-TYPE
    SYNTAX      Counter64
    MAX-ACCESS  read-only
    STATUS      current
    DESCRIPTION ""
    ::= { pxmBwpEthIntfPmRealEntry  1 }

pxmBwpEthIntfPmRealPolicerConformedOctets OBJECT-TYPE
    SYNTAX      Counter64
    MAX-ACCESS  read-only
    STATUS      current
    DESCRIPTION ""
    ::= { pxmBwpEthIntfPmRealEntry  2 }

pxmBwpEthIntfPmRealPolicerExceededPkts OBJECT-TYPE
    SYNTAX      Counter64
    MAX-ACCESS  read-only
    STATUS      current
    DESCRIPTION ""
    ::= { pxmBwpEthIntfPmRealEntry  3 }

pxmBwpEthIntfPmRealPolicerExceededOctets OBJECT-TYPE
    SYNTAX      Counter64
    MAX-ACCESS  read-only
    STATUS      current
    DESCRIPTION ""
    ::= { pxmBwpEthIntfPmRealEntry  4 }

pxmBwpEthIntfPmRealPolicerViolatedPkts OBJECT-TYPE
    SYNTAX      Counter64
    MAX-ACCESS  read-only
    STATUS      current
    DESCRIPTION ""
    ::= { pxmBwpEthIntfPmRealEntry  5 }

pxmBwpEthIntfPmRealPolicerViolatedOctets OBJECT-TYPE
    SYNTAX      Counter64
    MAX-ACCESS  read-only
    STATUS      current
    DESCRIPTION ""
    ::= { pxmBwpEthIntfPmRealEntry  6 }

-- Congestion Mgmt PMs
pxmCmEthIntfPmObjects      OBJECT IDENTIFIER ::= { pxmEthIntfPmMIB 3 }

pxmCmEthIntfRealPm         OBJECT IDENTIFIER ::= { pxmCmEthIntfPmObjects 1 }

pxmCmEthIntfPm             OBJECT IDENTIFIER ::= { pxmCmEthIntfPmObjects 2 }

-- CM - TC0, TC2, TC4, TC6, TC7
-- TC0 Real

pxmTC0EthIntfPmRealTable OBJECT-TYPE
    SYNTAX      SEQUENCE OF PxmTC0EthIntfPmRealEntry
    MAX-ACCESS  not-accessible
    STATUS      current
    DESCRIPTION
        "A list of PxmTC0EthIntfPmReal entries. Each entry is uniquely identified by the value of ifIndex."
    ::= { pxmCmEthIntfRealPm 1 }

pxmTC0EthIntfPmRealEntry  OBJECT-TYPE
    SYNTAX      PxmTC0EthIntfPmRealEntry
    MAX-ACCESS  not-accessible
    STATUS      current
    DESCRIPTION
        "A PxmTC0EthIntfPm entry containing real-time performance information pertaining to Infinera
        PxmEthIntfPm interfaces. This table is a subclass of IfCommon. Entries will exist in this table
        only for interfaces of type PxmEthIntfPm."
    INDEX { ifIndex }
    ::= { pxmTC0EthIntfPmRealTable 1 }

PxmTC0EthIntfPmRealEntry  ::= SEQUENCE {
    pxmTC0EthIntfPmRealTCNum                     Integer32,
    pxmTC0EthIntfPmRealTDQueuingCurrentQDepth    Integer32,
    pxmTC0EthIntfPmRealQueueingDiscardOctets     Counter64,
    pxmTC0EthIntfPmRealQueueingDiscardPkts       Integer32,
    pxmTC0EthIntfPmRealRandomGreenDropPkts       Counter64,
    pxmTC0EthIntfPmRealRandomGreenDropOctets     Counter64,
    pxmTC0EthIntfPmRealRandomYellowDropPkts      Counter64,
    pxmTC0EthIntfPmRealRandomYellowDropOctets    Counter64,
    pxmTC0EthIntfPmRealQueueingTransmitPkts      Counter64,
    pxmTC0EthIntfPmRealQueueingTransmitOctets    Counter64,
    pxmTC0EthIntfPmRealQueueingMeanQSizeUnit     Integer32,
    pxmTC0EthIntfPmRealMeanQSize                 Integer32
}

pxmTC0EthIntfPmRealTCNum OBJECT-TYPE
    SYNTAX      Integer32
    MAX-ACCESS  read-only
    STATUS      current
    DESCRIPTION "TCNum Real PM of traffic class - 0 (TC0) on PxmEthIntf"
    ::= { pxmTC0EthIntfPmRealEntry  1 }

pxmTC0EthIntfPmRealTDQueuingCurrentQDepth OBJECT-TYPE
    SYNTAX      Integer32
    MAX-ACCESS  read-only
    STATUS      current
    DESCRIPTION "TDQueuingCurrentQDepth Real PM of traffic class - 0 (TC0) on PxmEthIntf"
    ::= { pxmTC0EthIntfPmRealEntry  2 }

pxmTC0EthIntfPmRealQueueingDiscardOctets OBJECT-TYPE
    SYNTAX      Counter64
    MAX-ACCESS  read-only
    STATUS      current
    DESCRIPTION "QueueingDiscardOctets Real PM of traffic class - 0 (TC0) on PxmEthIntf"
    ::= { pxmTC0EthIntfPmRealEntry  3 }

pxmTC0EthIntfPmRealQueueingDiscardPkts OBJECT-TYPE
    SYNTAX      Integer32
    MAX-ACCESS  read-only
    STATUS      current
    DESCRIPTION "QueueingDiscardPkts Real PM of traffic class - 0 (TC0) on PxmEthIntf"
    ::= { pxmTC0EthIntfPmRealEntry  4 }

pxmTC0EthIntfPmRealRandomGreenDropPkts OBJECT-TYPE
    SYNTAX      Counter64
    MAX-ACCESS  read-only
    STATUS      current
    DESCRIPTION "RandomGreenDropPkts Real PM of traffic class - 0 (TC0) on PxmEthIntf"
    ::= { pxmTC0EthIntfPmRealEntry  5 }

pxmTC0EthIntfPmRealRandomGreenDropOctets OBJECT-TYPE
    SYNTAX      Counter64
    MAX-ACCESS  read-only
    STATUS      current
    DESCRIPTION "RandomGreenDropOctets Real PM of traffic class - 0 (TC0) on PxmEthIntf"
    ::= { pxmTC0EthIntfPmRealEntry  6 }

pxmTC0EthIntfPmRealRandomYellowDropPkts OBJECT-TYPE
    SYNTAX      Counter64
    MAX-ACCESS  read-only
    STATUS      current
    DESCRIPTION "RandomYellowDropPkts Real PM of traffic class - 0 (TC0) on PxmEthIntf"
    ::= { pxmTC0EthIntfPmRealEntry  7 }

pxmTC0EthIntfPmRealRandomYellowDropOctets OBJECT-TYPE
    SYNTAX      Counter64
    MAX-ACCESS  read-only
    STATUS      current
    DESCRIPTION "RandomYellowDropOctets Real PM of traffic class - 0 (TC0) on PxmEthIntf"
    ::= { pxmTC0EthIntfPmRealEntry  8 }

pxmTC0EthIntfPmRealQueueingTransmitPkts OBJECT-TYPE
    SYNTAX      Counter64
    MAX-ACCESS  read-only
    STATUS      current
    DESCRIPTION "QueueingTransmitPkts Real PM of traffic class - 0 (TC0) on PxmEthIntf"
    ::= { pxmTC0EthIntfPmRealEntry  9 }

pxmTC0EthIntfPmRealQueueingTransmitOctets OBJECT-TYPE
    SYNTAX      Counter64
    MAX-ACCESS  read-only
    STATUS      current
    DESCRIPTION "QueueingTransmitOctets Real PM of traffic class - 0 (TC0) on PxmEthIntf"
    ::= { pxmTC0EthIntfPmRealEntry  10 }

pxmTC0EthIntfPmRealQueueingMeanQSizeUnit OBJECT-TYPE
    SYNTAX      Integer32
    MAX-ACCESS  read-only
    STATUS      current
    DESCRIPTION "QueueingMeanQSizeUnit Real PM of traffic class - 0 (TC0) on PxmEthIntf"
    ::= { pxmTC0EthIntfPmRealEntry  11 }

pxmTC0EthIntfPmRealMeanQSize OBJECT-TYPE
    SYNTAX      Integer32
    MAX-ACCESS  read-only
    STATUS      current
    DESCRIPTION "MeanQSize Real PM of traffic class - 0 (TC0) on PxmEthIntf"
    ::= { pxmTC0EthIntfPmRealEntry  12 }

-- TC0 Historical
pxmTC0EthIntfPmTable OBJECT-TYPE
    SYNTAX      SEQUENCE OF PxmTC0EthIntfPmEntry
    MAX-ACCESS  not-accessible
    STATUS      current
    DESCRIPTION
        "A list of PxmTC0EthIntfPm entries. Each entry is uniquely identified by the value of ifIndex."
    ::= { pxmCmEthIntfPm 1 }

pxmTC0EthIntfPmEntry  OBJECT-TYPE
    SYNTAX      PxmTC0EthIntfPmEntry
    MAX-ACCESS  not-accessible
    STATUS      current
    DESCRIPTION "A PxmTC0EthIntf entry containing historical performance information pertaining to Infinera
            PxmEthIntf interfaces. This table is a subclass of IfCommon. Entries will exist in this
            table only for interfaces of type PxmEthIntf.
            Each interface may have a number of entries in this table, each with a different combination
            of timestamp and sample duration."
    INDEX { ifIndex, pxmTC0EthIntfPmSampleDuration, pxmTC0EthIntfPmTimestamp }
    ::= { pxmTC0EthIntfPmTable 1 }

PxmTC0EthIntfPmEntry  ::= SEQUENCE {
    pxmTC0EthIntfPmTimestamp                 Integer32,
    pxmTC0EthIntfPmSampleDuration            INTEGER,
    pxmTC0EthIntfPmValidity                  TruthValue,
    pxmTC0EthIntfPmTCNum                     Integer32,
    pxmTC0EthIntfPmQueueingDiscardOctets     Counter64,
    pxmTC0EthIntfPmQueueingDiscardPkts       Integer32,
    pxmTC0EthIntfPmRandomGreenDropPkts       Counter64,
    pxmTC0EthIntfPmRandomGreenDropOctets     Counter64,
    pxmTC0EthIntfPmRandomYellowDropPkts      Counter64,
    pxmTC0EthIntfPmRandomYellowDropOctets    Counter64,
    pxmTC0EthIntfPmQueueingTransmitPkts      Counter64,
    pxmTC0EthIntfPmQueueingTransmitOctets    Counter64
}

pxmTC0EthIntfPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTC0EthIntfPmEntry  1 }

pxmTC0EthIntfPmSampleDuration OBJECT-TYPE
    SYNTAX      INTEGER {
                    fifteenMinutes(1),
                    day(2)
                }
    MAX-ACCESS  not-accessible
    STATUS      current
    DESCRIPTION "The duration of this sample."
    ::= { pxmTC0EthIntfPmEntry  2 }

pxmTC0EthIntfPmValidity OBJECT-TYPE
    SYNTAX      TruthValue
    MAX-ACCESS  read-only
    STATUS      current
    DESCRIPTION "Flag indicating if data was valid for the entire interval"
    ::= { pxmTC0EthIntfPmEntry  3 }

pxmTC0EthIntfPmTCNum OBJECT-TYPE
    SYNTAX      Integer32
    MAX-ACCESS  read-only
    STATUS      current
    DESCRIPTION "TCNum Historical PM of traffic class - 0 (TC0) on PxmEthIntf"
    ::= { pxmTC0EthIntfPmEntry  4 }

pxmTC0EthIntfPmQueueingDiscardOctets OBJECT-TYPE
    SYNTAX      Counter64
    MAX-ACCESS  read-only
    STATUS      current
    DESCRIPTION "QueueingDiscardOctets Historical PM of traffic class - 0 (TC0) on PxmEthIntf"
    ::= { pxmTC0EthIntfPmEntry  5 }

pxmTC0EthIntfPmQueueingDiscardPkts OBJECT-TYPE
    SYNTAX      Integer32
    MAX-ACCESS  read-only
    STATUS      current
    DESCRIPTION "QueueingDiscardPkts Historical PM of traffic class - 0 (TC0) on PxmEthIntf"
    ::= { pxmTC0EthIntfPmEntry  6 }

pxmTC0EthIntfPmRandomGreenDropPkts OBJECT-TYPE
    SYNTAX      Counter64
    MAX-ACCESS  read-only
    STATUS      current
    DESCRIPTION "RandomGreenDropPkts Historical PM of traffic class - 0 (TC0) on PxmEthIntf"
    ::= { pxmTC0EthIntfPmEntry  7 }

pxmTC0EthIntfPmRandomGreenDropOctets OBJECT-TYPE
    SYNTAX      Counter64
    MAX-ACCESS  read-only
    STATUS      current
    DESCRIPTION "RandomGreenDropOctets Historical PM of traffic class - 0 (TC0) on PxmEthIntf"
    ::= { pxmTC0EthIntfPmEntry  8 }

pxmTC0EthIntfPmRandomYellowDropPkts OBJECT-TYPE
    SYNTAX      Counter64
    MAX-ACCESS  read-only
    STATUS      current
    DESCRIPTION "RandomYellowDropPkts Historical PM of traffic class - 0 (TC0) on PxmEthIntf"
    ::= { pxmTC0EthIntfPmEntry  9 }

pxmTC0EthIntfPmRandomYellowDropOctets OBJECT-TYPE
    SYNTAX      Counter64
    MAX-ACCESS  read-only
    STATUS      current
    DESCRIPTION "RandomYellowDropOctets Historical PM of traffic class - 0 (TC0) on PxmEthIntf"
    ::= { pxmTC0EthIntfPmEntry  10 }

pxmTC0EthIntfPmQueueingTransmitPkts OBJECT-TYPE
    SYNTAX      Counter64
    MAX-ACCESS  read-only
    STATUS      current
    DESCRIPTION "QueueingTransmitPkts Historical PM of traffic class - 0 (TC0) on PxmEthIntf"
    ::= { pxmTC0EthIntfPmEntry  11 }

pxmTC0EthIntfPmQueueingTransmitOctets OBJECT-TYPE
    SYNTAX      Counter64
    MAX-ACCESS  read-only
    STATUS      current
    DESCRIPTION "QueueingTransmitOctets Historical PM of traffic class - 0 (TC0) on PxmEthIntf"
    ::= { pxmTC0EthIntfPmEntry  12 }

-- TC2 Real
pxmTC2EthIntfPmRealTable OBJECT-TYPE
    SYNTAX      SEQUENCE OF PxmTC2EthIntfPmRealEntry
    MAX-ACCESS  not-accessible
    STATUS      current
    DESCRIPTION
        "A list of PxmBwpEthIntfPmReal entries. Each entry is uniquely identified by the value of ifIndex."
    ::= { pxmCmEthIntfRealPm 2 }

pxmTC2EthIntfPmRealEntry  OBJECT-TYPE
    SYNTAX      PxmTC2EthIntfPmRealEntry
    MAX-ACCESS  not-accessible
    STATUS      current
    DESCRIPTION
        "A PxmTC0EthIntfPm entry containing real-time performance information pertaining to Infinera
        PxmEthIntfPm interfaces.  This table is a subclass of IfCommon. Entries will exist in this table
        only for interfaces of type PxmEthIntfPm."
    INDEX { ifIndex }
    ::= { pxmTC2EthIntfPmRealTable 1 }

PxmTC2EthIntfPmRealEntry  ::= SEQUENCE {
    pxmTC2EthIntfPmRealTCNum                     Integer32,
    pxmTC2EthIntfPmRealTDQueuingCurrentQDepth    Integer32,
    pxmTC2EthIntfPmRealQueueingDiscardOctets     Counter64,
    pxmTC2EthIntfPmRealQueueingDiscardPkts       Integer32,
    pxmTC2EthIntfPmRealRandomGreenDropPkts       Counter64,
    pxmTC2EthIntfPmRealRandomGreenDropOctets     Counter64,
    pxmTC2EthIntfPmRealRandomYellowDropPkts      Counter64,
    pxmTC2EthIntfPmRealRandomYellowDropOctets    Counter64,
    pxmTC2EthIntfPmRealQueueingTransmitPkts      Counter64,
    pxmTC2EthIntfPmRealQueueingTransmitOctets    Counter64,
    pxmTC2EthIntfPmRealQueueingMeanQSizeUnit     Integer32,
    pxmTC2EthIntfPmRealMeanQSize                 Integer32
}

pxmTC2EthIntfPmRealTCNum OBJECT-TYPE
    SYNTAX      Integer32
    MAX-ACCESS  read-only
    STATUS      current
    DESCRIPTION "TCNum Real PM of traffic class - 2 (TC2) on PxmEthIntf"
    ::= { pxmTC2EthIntfPmRealEntry  1 }

pxmTC2EthIntfPmRealTDQueuingCurrentQDepth OBJECT-TYPE
    SYNTAX      Integer32
    MAX-ACCESS  read-only
    STATUS      current
    DESCRIPTION "TDQueuingCurrentQDepth Real PM of traffic class - 2 (TC2) on PxmEthIntf"
    ::= { pxmTC2EthIntfPmRealEntry  2 }

pxmTC2EthIntfPmRealQueueingDiscardOctets OBJECT-TYPE
    SYNTAX      Counter64
    MAX-ACCESS  read-only
    STATUS      current
    DESCRIPTION "QueueingDiscardOctets Real PM of traffic class - 2 (TC2) on PxmEthIntf"
    ::= { pxmTC2EthIntfPmRealEntry  3 }

pxmTC2EthIntfPmRealQueueingDiscardPkts OBJECT-TYPE
    SYNTAX      Integer32
    MAX-ACCESS  read-only
    STATUS      current
    DESCRIPTION "QueueingDiscardPkts Real PM of traffic class - 2 (TC2) on PxmEthIntf"
    ::= { pxmTC2EthIntfPmRealEntry  4 }

pxmTC2EthIntfPmRealRandomGreenDropPkts OBJECT-TYPE
    SYNTAX      Counter64
    MAX-ACCESS  read-only
    STATUS      current
    DESCRIPTION "RandomGreenDropPkts Real PM of traffic class - 2 (TC2) on PxmEthIntf"
    ::= { pxmTC2EthIntfPmRealEntry  5 }

pxmTC2EthIntfPmRealRandomGreenDropOctets OBJECT-TYPE
    SYNTAX      Counter64
    MAX-ACCESS  read-only
    STATUS      current
    DESCRIPTION "RandomGreenDropOctets Real PM of traffic class - 2 (TC2) on PxmEthIntf"
    ::= { pxmTC2EthIntfPmRealEntry  6 }

pxmTC2EthIntfPmRealRandomYellowDropPkts OBJECT-TYPE
    SYNTAX      Counter64
    MAX-ACCESS  read-only
    STATUS      current
    DESCRIPTION "RandomYellowDropPkts Real PM of traffic class - 2 (TC2) on PxmEthIntf"
    ::= { pxmTC2EthIntfPmRealEntry  7 }

pxmTC2EthIntfPmRealRandomYellowDropOctets OBJECT-TYPE
    SYNTAX      Counter64
    MAX-ACCESS  read-only
    STATUS      current
    DESCRIPTION "RandomYellowDropOctets Real PM of traffic class - 2 (TC2) on PxmEthIntf"
    ::= { pxmTC2EthIntfPmRealEntry  8 }

pxmTC2EthIntfPmRealQueueingTransmitPkts OBJECT-TYPE
    SYNTAX      Counter64
    MAX-ACCESS  read-only
    STATUS      current
    DESCRIPTION "QueueingTransmitPkts Real PM of traffic class - 2 (TC2) on PxmEthIntf"
    ::= { pxmTC2EthIntfPmRealEntry  9 }

pxmTC2EthIntfPmRealQueueingTransmitOctets OBJECT-TYPE
    SYNTAX      Counter64
    MAX-ACCESS  read-only
    STATUS      current
    DESCRIPTION "QueueingTransmitOctets Real PM of traffic class - 2 (TC2) on PxmEthIntf"
    ::= { pxmTC2EthIntfPmRealEntry  10 }

pxmTC2EthIntfPmRealQueueingMeanQSizeUnit OBJECT-TYPE
    SYNTAX      Integer32
    MAX-ACCESS  read-only
    STATUS      current
    DESCRIPTION "QueueingMeanQSizeUnit Real PM of traffic class - 2 (TC2) on PxmEthIntf"
    ::= { pxmTC2EthIntfPmRealEntry  11 }

pxmTC2EthIntfPmRealMeanQSize OBJECT-TYPE
    SYNTAX      Integer32
    MAX-ACCESS  read-only
    STATUS      current
    DESCRIPTION "MeanQSize Real PM of traffic class - 2 (TC2) on PxmEthIntf"
    ::= { pxmTC2EthIntfPmRealEntry  12 }

-- TC2 Historical
pxmTC2EthIntfPmTable OBJECT-TYPE
    SYNTAX      SEQUENCE OF PxmTC2EthIntfPmEntry
    MAX-ACCESS  not-accessible
    STATUS      current
    DESCRIPTION
        "A list of PxmBwpEthIntfPmReal entries. Each entry is uniquely identified by the value of ifIndex."
    ::= { pxmCmEthIntfPm 2 }

pxmTC2EthIntfPmEntry  OBJECT-TYPE
    SYNTAX      PxmTC2EthIntfPmEntry
    MAX-ACCESS  not-accessible
    STATUS      current
    DESCRIPTION "A PxmTC2EthIntf entry containing historical performance information pertaining to Infinera
            PxmEthIntf interfaces. This table is a subclass of IfCommon. Entries will exist in this
            table only for interfaces of type PxmEthIntf.
            Each interface may have a number of entries in this table, each with a different combination
            of timestamp and sample duration."
    INDEX { ifIndex, pxmTC2EthIntfPmSampleDuration, pxmTC2EthIntfPmTimestamp }
    ::= { pxmTC2EthIntfPmTable 1 }

PxmTC2EthIntfPmEntry  ::= SEQUENCE {
    pxmTC2EthIntfPmTimestamp                 Integer32,
    pxmTC2EthIntfPmSampleDuration            INTEGER,
    pxmTC2EthIntfPmValidity                  TruthValue,
    pxmTC2EthIntfPmTCNum                     Integer32,
    pxmTC2EthIntfPmQueueingDiscardOctets     Counter64,
    pxmTC2EthIntfPmQueueingDiscardPkts       Integer32,
    pxmTC2EthIntfPmRandomGreenDropPkts       Counter64,
    pxmTC2EthIntfPmRandomGreenDropOctets     Counter64,
    pxmTC2EthIntfPmRandomYellowDropPkts      Counter64,
    pxmTC2EthIntfPmRandomYellowDropOctets    Counter64,
    pxmTC2EthIntfPmQueueingTransmitPkts      Counter64,
    pxmTC2EthIntfPmQueueingTransmitOctets    Counter64
}

pxmTC2EthIntfPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTC2EthIntfPmEntry  1 }

pxmTC2EthIntfPmSampleDuration OBJECT-TYPE
    SYNTAX      INTEGER {
                    fifteenMinutes(1),
                    day(2)
                }
    MAX-ACCESS  not-accessible
    STATUS      current
    DESCRIPTION
        "The duration of this sample."
    ::= { pxmTC2EthIntfPmEntry  2 }

pxmTC2EthIntfPmValidity OBJECT-TYPE
    SYNTAX      TruthValue
    MAX-ACCESS  read-only
    STATUS      current
    DESCRIPTION "Flag indicating if data was valid for the entire interval"
    ::= { pxmTC2EthIntfPmEntry  3 }

pxmTC2EthIntfPmTCNum OBJECT-TYPE
    SYNTAX      Integer32
    MAX-ACCESS  read-only
    STATUS      current
    DESCRIPTION "TCNum Historical PM of traffic class - 2 (TC2) on PxmEthIntf"
    ::= { pxmTC2EthIntfPmEntry  4 }

pxmTC2EthIntfPmQueueingDiscardOctets OBJECT-TYPE
    SYNTAX      Counter64
    MAX-ACCESS  read-only
    STATUS      current
    DESCRIPTION "QueueingDiscardOctets Historical PM of traffic class - 2 (TC2) on PxmEthIntf"
    ::= { pxmTC2EthIntfPmEntry  5 }

pxmTC2EthIntfPmQueueingDiscardPkts OBJECT-TYPE
    SYNTAX      Integer32
    MAX-ACCESS  read-only
    STATUS      current
    DESCRIPTION "QueueingDiscardPkts Historical PM of traffic class - 2 (TC2) on PxmEthIntf"
    ::= { pxmTC2EthIntfPmEntry  6 }

pxmTC2EthIntfPmRandomGreenDropPkts OBJECT-TYPE
    SYNTAX      Counter64
    MAX-ACCESS  read-only
    STATUS      current
    DESCRIPTION "RandomGreenDropPkts Historical PM of traffic class - 2 (TC2) on PxmEthIntf"
    ::= { pxmTC2EthIntfPmEntry  7 }

pxmTC2EthIntfPmRandomGreenDropOctets OBJECT-TYPE
    SYNTAX      Counter64
    MAX-ACCESS  read-only
    STATUS      current
    DESCRIPTION "RandomGreenDropOctets Historical PM of traffic class - 2 (TC2) on PxmEthIntf"
    ::= { pxmTC2EthIntfPmEntry  8 }

pxmTC2EthIntfPmRandomYellowDropPkts OBJECT-TYPE
    SYNTAX      Counter64
    MAX-ACCESS  read-only
    STATUS      current
    DESCRIPTION "RandomYellowDropPkts Historical PM of traffic class - 2 (TC2) on PxmEthIntf"
    ::= { pxmTC2EthIntfPmEntry  9 }

pxmTC2EthIntfPmRandomYellowDropOctets OBJECT-TYPE
    SYNTAX      Counter64
    MAX-ACCESS  read-only
    STATUS      current
    DESCRIPTION "RandomYellowDropOctets Historical PM of traffic class - 2 (TC2) on PxmEthIntf"
    ::= { pxmTC2EthIntfPmEntry  10 }

pxmTC2EthIntfPmQueueingTransmitPkts OBJECT-TYPE
    SYNTAX      Counter64
    MAX-ACCESS  read-only
    STATUS      current
    DESCRIPTION "QueueingTransmitPkts Historical PM of traffic class - 2 (TC2) on PxmEthIntf"
    ::= { pxmTC2EthIntfPmEntry  11 }

pxmTC2EthIntfPmQueueingTransmitOctets OBJECT-TYPE
    SYNTAX      Counter64
    MAX-ACCESS  read-only
    STATUS      current
    DESCRIPTION "QueueingTransmitOctets Historical PM of traffic class - 2 (TC2) on PxmEthIntf"
    ::= { pxmTC2EthIntfPmEntry  12 }

-- TC4 Real
pxmTC4EthIntfPmRealTable OBJECT-TYPE
    SYNTAX      SEQUENCE OF PxmTC4EthIntfPmRealEntry
    MAX-ACCESS  not-accessible
    STATUS      current
    DESCRIPTION
        "A list of PxmBwpEthIntfPmReal entries. Each entry is uniquely identified by the value of ifIndex."
    ::= { pxmCmEthIntfRealPm 3 }

pxmTC4EthIntfPmRealEntry  OBJECT-TYPE
    SYNTAX      PxmTC4EthIntfPmRealEntry
    MAX-ACCESS  not-accessible
    STATUS      current
    DESCRIPTION
        "A PxmTC0EthIntfPm entry containing real-time performance information pertaining to Infinera
        PxmEthIntfPm interfaces. This table is a subclass of IfCommon. Entries will exist in this table
        only for interfaces of type PxmEthIntfPm."
    INDEX { ifIndex }
    ::= { pxmTC4EthIntfPmRealTable 1 }

PxmTC4EthIntfPmRealEntry  ::= SEQUENCE {
    pxmTC4EthIntfPmRealTCNum                     Integer32,
    pxmTC4EthIntfPmRealTDQueuingCurrentQDepth    Integer32,
    pxmTC4EthIntfPmRealQueueingDiscardOctets     Counter64,
    pxmTC4EthIntfPmRealQueueingDiscardPkts       Integer32,
    pxmTC4EthIntfPmRealRandomGreenDropPkts       Counter64,
    pxmTC4EthIntfPmRealRandomGreenDropOctets     Counter64,
    pxmTC4EthIntfPmRealRandomYellowDropPkts      Counter64,
    pxmTC4EthIntfPmRealRandomYellowDropOctets    Counter64,
    pxmTC4EthIntfPmRealQueueingTransmitPkts      Counter64,
    pxmTC4EthIntfPmRealQueueingTransmitOctets    Counter64,
    pxmTC4EthIntfPmRealQueueingMeanQSizeUnit     Integer32,
    pxmTC4EthIntfPmRealMeanQSize                 Integer32
}

pxmTC4EthIntfPmRealTCNum OBJECT-TYPE
    SYNTAX      Integer32
    MAX-ACCESS  read-only
    STATUS      current
    DESCRIPTION "TCNum Real PM of traffic class - 4 (TC4) on PxmEthInt"
    ::= { pxmTC4EthIntfPmRealEntry  1 }

pxmTC4EthIntfPmRealTDQueuingCurrentQDepth OBJECT-TYPE
    SYNTAX      Integer32
    MAX-ACCESS  read-only
    STATUS      current
    DESCRIPTION "TDQueuingCurrentQDepth Real PM of traffic class - 4 (TC4) on PxmEthInt"
    ::= { pxmTC4EthIntfPmRealEntry  2 }

pxmTC4EthIntfPmRealQueueingDiscardOctets OBJECT-TYPE
    SYNTAX      Counter64
    MAX-ACCESS  read-only
    STATUS      current
    DESCRIPTION "QueueingDiscardOctets Real PM of traffic class - 4 (TC4) on PxmEthInt"
    ::= { pxmTC4EthIntfPmRealEntry  3 }

pxmTC4EthIntfPmRealQueueingDiscardPkts OBJECT-TYPE
    SYNTAX      Integer32
    MAX-ACCESS  read-only
    STATUS      current
    DESCRIPTION "QueueingDiscardPkts Real PM of traffic class - 4 (TC4) on PxmEthInt"
    ::= { pxmTC4EthIntfPmRealEntry  4 }

pxmTC4EthIntfPmRealRandomGreenDropPkts OBJECT-TYPE
    SYNTAX      Counter64
    MAX-ACCESS  read-only
    STATUS      current
    DESCRIPTION "RandomGreenDropPkts Real PM of traffic class - 4 (TC4) on PxmEthInt"
    ::= { pxmTC4EthIntfPmRealEntry  5 }

pxmTC4EthIntfPmRealRandomGreenDropOctets OBJECT-TYPE
    SYNTAX      Counter64
    MAX-ACCESS  read-only
    STATUS      current
    DESCRIPTION "RandomGreenDropOctets Real PM of traffic class - 4 (TC4) on PxmEthInt"
    ::= { pxmTC4EthIntfPmRealEntry  6 }

pxmTC4EthIntfPmRealRandomYellowDropPkts OBJECT-TYPE
    SYNTAX      Counter64
    MAX-ACCESS  read-only
    STATUS      current
    DESCRIPTION "RandomYellowDropPkts Real PM of traffic class - 4 (TC4) on PxmEthInt"
    ::= { pxmTC4EthIntfPmRealEntry  7 }

pxmTC4EthIntfPmRealRandomYellowDropOctets OBJECT-TYPE
    SYNTAX      Counter64
    MAX-ACCESS  read-only
    STATUS      current
    DESCRIPTION "iRandomYellowDropOctets Real PM of traffic class - 4 (TC4) on PxmEthInt"
    ::= { pxmTC4EthIntfPmRealEntry  8 }

pxmTC4EthIntfPmRealQueueingTransmitPkts OBJECT-TYPE
    SYNTAX      Counter64
    MAX-ACCESS  read-only
    STATUS      current
    DESCRIPTION "QueueingTransmitPkts Real PM of traffic class - 4 (TC4) on PxmEthInt"
    ::= { pxmTC4EthIntfPmRealEntry  9 }

pxmTC4EthIntfPmRealQueueingTransmitOctets OBJECT-TYPE
    SYNTAX      Counter64
    MAX-ACCESS  read-only
    STATUS      current
    DESCRIPTION "QueueingTransmitOctets Real PM of traffic class - 4 (TC4) on PxmEthInt"
    ::= { pxmTC4EthIntfPmRealEntry  10 }

pxmTC4EthIntfPmRealQueueingMeanQSizeUnit OBJECT-TYPE
    SYNTAX      Integer32
    MAX-ACCESS  read-only
    STATUS      current
    DESCRIPTION "QueueingMeanQSizeUnit Real PM of traffic class - 4 (TC4) on PxmEthInt"
    ::= { pxmTC4EthIntfPmRealEntry  11 }

pxmTC4EthIntfPmRealMeanQSize OBJECT-TYPE
    SYNTAX      Integer32
    MAX-ACCESS  read-only
    STATUS      current
    DESCRIPTION "MeanQSize Real PM of traffic class - 4 (TC4) on PxmEthInt"
    ::= { pxmTC4EthIntfPmRealEntry  12 }

-- TC4 Historical
pxmTC4EthIntfPmTable OBJECT-TYPE
    SYNTAX      SEQUENCE OF PxmTC4EthIntfPmEntry
    MAX-ACCESS  not-accessible
    STATUS      current
    DESCRIPTION
        "A list of PxmBwpEthIntfPmReal entries. Each entry is uniquely identified by the value of ifIndex."
    ::= { pxmCmEthIntfPm 3 }

pxmTC4EthIntfPmEntry  OBJECT-TYPE
    SYNTAX      PxmTC4EthIntfPmEntry
    MAX-ACCESS  not-accessible
    STATUS      current
    DESCRIPTION "A PxmTC4EthIntf entry containing historical performance information pertaining to Infinera
            PxmEthIntf interfaces. This table is a subclass of IfCommon. Entries will exist in this
            table only for interfaces of type PxmEthIntf.
            Each interface may have a number of entries in this table, each with a different combination
            of timestamp and sample duration."
    INDEX { ifIndex, pxmTC4EthIntfPmSampleDuration, pxmTC4EthIntfPmTimestamp }
    ::= { pxmTC4EthIntfPmTable 1 }

PxmTC4EthIntfPmEntry  ::= SEQUENCE {
    pxmTC4EthIntfPmTimestamp                 Integer32,
    pxmTC4EthIntfPmSampleDuration            INTEGER,
    pxmTC4EthIntfPmValidity                  TruthValue,
    pxmTC4EthIntfPmTCNum                     Integer32,
    pxmTC4EthIntfPmQueueingDiscardOctets     Counter64,
    pxmTC4EthIntfPmQueueingDiscardPkts       Integer32,
    pxmTC4EthIntfPmRandomGreenDropPkts       Counter64,
    pxmTC4EthIntfPmRandomGreenDropOctets     Counter64,
    pxmTC4EthIntfPmRandomYellowDropPkts      Counter64,
    pxmTC4EthIntfPmRandomYellowDropOctets    Counter64,
    pxmTC4EthIntfPmQueueingTransmitPkts      Counter64,
    pxmTC4EthIntfPmQueueingTransmitOctets    Counter64
}

pxmTC4EthIntfPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTC4EthIntfPmEntry  1 }

pxmTC4EthIntfPmSampleDuration OBJECT-TYPE
    SYNTAX      INTEGER {
                    fifteenMinutes(1),
                    day(2)
                }
    MAX-ACCESS  not-accessible
    STATUS      current
    DESCRIPTION "The duration of this sample."
    ::= { pxmTC4EthIntfPmEntry  2 }

pxmTC4EthIntfPmValidity OBJECT-TYPE
    SYNTAX      TruthValue
    MAX-ACCESS  read-only
    STATUS      current
    DESCRIPTION "Flag indicating if data was valid for the entire interval"
    ::= { pxmTC4EthIntfPmEntry  3 }

pxmTC4EthIntfPmTCNum OBJECT-TYPE
    SYNTAX      Integer32
    MAX-ACCESS  read-only
    STATUS      current
    DESCRIPTION "TCNum Historical PM of traffic class - 4 (TC4) on PxmEthIntf"
    ::= { pxmTC4EthIntfPmEntry  4 }

pxmTC4EthIntfPmQueueingDiscardOctets OBJECT-TYPE
    SYNTAX      Counter64
    MAX-ACCESS  read-only
    STATUS      current
    DESCRIPTION "QueueingDiscardOctets Historical PM of traffic class - 4 (TC4) on PxmEthIntf"
    ::= { pxmTC4EthIntfPmEntry  5 }

pxmTC4EthIntfPmQueueingDiscardPkts OBJECT-TYPE
    SYNTAX      Integer32
    MAX-ACCESS  read-only
    STATUS      current
    DESCRIPTION "QueueingDiscardPkts Historical PM of traffic class - 4 (TC4) on PxmEthIntf"
    ::= { pxmTC4EthIntfPmEntry  6 }

pxmTC4EthIntfPmRandomGreenDropPkts OBJECT-TYPE
    SYNTAX      Counter64
    MAX-ACCESS  read-only
    STATUS      current
    DESCRIPTION "RandomGreenDropPkts Historical PM of traffic class - 4 (TC4) on PxmEthIntf"
    ::= { pxmTC4EthIntfPmEntry  7 }

pxmTC4EthIntfPmRandomGreenDropOctets OBJECT-TYPE
    SYNTAX      Counter64
    MAX-ACCESS  read-only
    STATUS      current
    DESCRIPTION "RandomGreenDropOctets Historical PM of traffic class - 4 (TC4) on PxmEthIntf"
    ::= { pxmTC4EthIntfPmEntry  8 }

pxmTC4EthIntfPmRandomYellowDropPkts OBJECT-TYPE
    SYNTAX      Counter64
    MAX-ACCESS  read-only
    STATUS      current
    DESCRIPTION "RandomYellowDropPkts Historical PM of traffic class - 4 (TC4) on PxmEthIntf"
    ::= { pxmTC4EthIntfPmEntry  9 }

pxmTC4EthIntfPmRandomYellowDropOctets OBJECT-TYPE
    SYNTAX      Counter64
    MAX-ACCESS  read-only
    STATUS      current
    DESCRIPTION "RandomYellowDropOctets Historical PM of traffic class - 4 (TC4) on PxmEthIntf"
    ::= { pxmTC4EthIntfPmEntry  10 }

pxmTC4EthIntfPmQueueingTransmitPkts OBJECT-TYPE
    SYNTAX      Counter64
    MAX-ACCESS  read-only
    STATUS      current
    DESCRIPTION "TransmitPkts Historical PM of traffic class - 4 (TC4) on PxmEthIntf"
    ::= { pxmTC4EthIntfPmEntry  11 }

pxmTC4EthIntfPmQueueingTransmitOctets OBJECT-TYPE
    SYNTAX      Counter64
    MAX-ACCESS  read-only
    STATUS      current
    DESCRIPTION "QueueingTransmitOctets Historical PM of traffic class - 4 (TC4) on PxmEthIntf"
    ::= { pxmTC4EthIntfPmEntry  12 }

-- TC6 Real
pxmTC6EthIntfPmRealTable OBJECT-TYPE
    SYNTAX      SEQUENCE OF PxmTC6EthIntfPmRealEntry
    MAX-ACCESS  not-accessible
    STATUS      current
    DESCRIPTION
        "A list of PxmBwpEthIntfPmReal entries. Each entry is uniquely identified by the value of ifIndex."
    ::= { pxmCmEthIntfRealPm 4 }

pxmTC6EthIntfPmRealEntry  OBJECT-TYPE
    SYNTAX      PxmTC6EthIntfPmRealEntry
    MAX-ACCESS  not-accessible
    STATUS      current
    DESCRIPTION
        "A PxmTC0EthIntfPm entry containing real-time performance information pertaining to Infinera PxmEthIntfPm interfaces.
        This table is a subclass of IfCommon. Entries will exist in this table only for interfaces of
        type PxmEthIntfPm."
    INDEX { ifIndex }
    ::= { pxmTC6EthIntfPmRealTable 1 }

PxmTC6EthIntfPmRealEntry  ::= SEQUENCE {
    pxmTC6EthIntfPmRealTCNum                     Integer32,
    pxmTC6EthIntfPmRealTDQueuingCurrentQDepth    Integer32,
    pxmTC6EthIntfPmRealQueueingDiscardOctets     Counter64,
    pxmTC6EthIntfPmRealQueueingDiscardPkts       Integer32,
    pxmTC6EthIntfPmRealRandomGreenDropPkts       Counter64,
    pxmTC6EthIntfPmRealRandomGreenDropOctets     Counter64,
    pxmTC6EthIntfPmRealRandomYellowDropPkts      Counter64,
    pxmTC6EthIntfPmRealRandomYellowDropOctets    Counter64,
    pxmTC6EthIntfPmRealQueueingTransmitPkts      Counter64,
    pxmTC6EthIntfPmRealQueueingTransmitOctets    Counter64,
    pxmTC6EthIntfPmRealQueueingMeanQSizeUnit     Integer32,
    pxmTC6EthIntfPmRealMeanQSize                 Integer32
}

pxmTC6EthIntfPmRealTCNum OBJECT-TYPE
    SYNTAX      Integer32
    MAX-ACCESS  read-only
    STATUS      current
    DESCRIPTION "TCNum Real PM of traffic class - 6 (TC6) on PxmEthIntf"
    ::= { pxmTC6EthIntfPmRealEntry  1 }

pxmTC6EthIntfPmRealTDQueuingCurrentQDepth OBJECT-TYPE
    SYNTAX      Integer32
    MAX-ACCESS  read-only
    STATUS      current
    DESCRIPTION "TDQueuingCurrentQDepth Real PM of traffic class - 6 (TC6) on PxmEthIntf"
    ::= { pxmTC6EthIntfPmRealEntry  2 }

pxmTC6EthIntfPmRealQueueingDiscardOctets OBJECT-TYPE
    SYNTAX      Counter64
    MAX-ACCESS  read-only
    STATUS      current
    DESCRIPTION "QueueingDiscardOctets Real PM of traffic class - 6 (TC6) on PxmEthIntf"
    ::= { pxmTC6EthIntfPmRealEntry  3 }

pxmTC6EthIntfPmRealQueueingDiscardPkts OBJECT-TYPE
    SYNTAX      Integer32
    MAX-ACCESS  read-only
    STATUS      current
    DESCRIPTION "QueueingDiscardPkts Real PM of traffic class - 6 (TC6) on PxmEthIntf"
    ::= { pxmTC6EthIntfPmRealEntry  4 }

pxmTC6EthIntfPmRealRandomGreenDropPkts OBJECT-TYPE
    SYNTAX      Counter64
    MAX-ACCESS  read-only
    STATUS      current
    DESCRIPTION "RandomGreenDropPkts Real PM of traffic class - 6 (TC6) on PxmEthIntf"
    ::= { pxmTC6EthIntfPmRealEntry  5 }

pxmTC6EthIntfPmRealRandomGreenDropOctets OBJECT-TYPE
    SYNTAX      Counter64
    MAX-ACCESS  read-only
    STATUS      current
    DESCRIPTION "RandomGreenDropOctets Real PM of traffic class - 6 (TC6) on PxmEthIntf"
    ::= { pxmTC6EthIntfPmRealEntry  6 }

pxmTC6EthIntfPmRealRandomYellowDropPkts OBJECT-TYPE
    SYNTAX      Counter64
    MAX-ACCESS  read-only
    STATUS      current
    DESCRIPTION "RandomYellowDropPkts Real PM of traffic class - 6 (TC6) on PxmEthIntf"
    ::= { pxmTC6EthIntfPmRealEntry  7 }

pxmTC6EthIntfPmRealRandomYellowDropOctets OBJECT-TYPE
    SYNTAX      Counter64
    MAX-ACCESS  read-only
    STATUS      current
    DESCRIPTION "RandomYellowDropOctets Real PM of traffic class - 6 (TC6) on PxmEthIntf"
    ::= { pxmTC6EthIntfPmRealEntry  8 }

pxmTC6EthIntfPmRealQueueingTransmitPkts OBJECT-TYPE
    SYNTAX      Counter64
    MAX-ACCESS  read-only
    STATUS      current
    DESCRIPTION "QueueingTransmitPkts Real PM of traffic class - 6 (TC6) on PxmEthIntf"
    ::= { pxmTC6EthIntfPmRealEntry  9 }

pxmTC6EthIntfPmRealQueueingTransmitOctets OBJECT-TYPE
    SYNTAX      Counter64
    MAX-ACCESS  read-only
    STATUS      current
    DESCRIPTION "QueueingTransmitOctets Real PM of traffic class - 6 (TC6) on PxmEthIntf"
    ::= { pxmTC6EthIntfPmRealEntry  10 }

pxmTC6EthIntfPmRealQueueingMeanQSizeUnit OBJECT-TYPE
    SYNTAX      Integer32
    MAX-ACCESS  read-only
    STATUS      current
    DESCRIPTION "QueueingMeanQSizeUnit Real PM of traffic class - 6 (TC6) on PxmEthIntf"
    ::= { pxmTC6EthIntfPmRealEntry  11 }

pxmTC6EthIntfPmRealMeanQSize OBJECT-TYPE
    SYNTAX      Integer32
    MAX-ACCESS  read-only
    STATUS      current
    DESCRIPTION "MeanQSize Real PM of traffic class - 6 (TC6) on PxmEthIntf"
    ::= { pxmTC6EthIntfPmRealEntry  12 }

-- TC6 Historical
pxmTC6EthIntfPmTable OBJECT-TYPE
    SYNTAX      SEQUENCE OF PxmTC6EthIntfPmEntry
    MAX-ACCESS  not-accessible
    STATUS      current
    DESCRIPTION
        "A list of PxmBwpEthIntfPmReal entries. Each entry is uniquely identified by the value of ifIndex."
    ::= { pxmCmEthIntfPm 4 }

pxmTC6EthIntfPmEntry  OBJECT-TYPE
    SYNTAX      PxmTC6EthIntfPmEntry
    MAX-ACCESS  not-accessible
    STATUS      current
    DESCRIPTION "A PxmTC6EthIntf entry containing historical performance information pertaining to Infinera
            PxmEthIntf interfaces. This table is a subclass of IfCommon. Entries will exist in this
            table only for interfaces of type PxmEthIntf.
            Each interface may have a number of entries in this table, each with a different combination
            of timestamp and sample duration."
    INDEX { ifIndex, pxmTC6EthIntfPmSampleDuration, pxmTC6EthIntfPmTimestamp }
    ::= { pxmTC6EthIntfPmTable 1 }

PxmTC6EthIntfPmEntry  ::= SEQUENCE {
    pxmTC6EthIntfPmTimestamp                 Integer32,
    pxmTC6EthIntfPmSampleDuration            INTEGER,
    pxmTC6EthIntfPmValidity                  TruthValue,
    pxmTC6EthIntfPmTCNum                     Integer32,
    pxmTC6EthIntfPmQueueingDiscardOctets     Counter64,
    pxmTC6EthIntfPmQueueingDiscardPkts       Integer32,
    pxmTC6EthIntfPmRandomGreenDropPkts       Counter64,
    pxmTC6EthIntfPmRandomGreenDropOctets     Counter64,
    pxmTC6EthIntfPmRandomYellowDropPkts      Counter64,
    pxmTC6EthIntfPmRandomYellowDropOctets    Counter64,
    pxmTC6EthIntfPmQueueingTransmitPkts      Counter64,
    pxmTC6EthIntfPmQueueingTransmitOctets    Counter64
}

pxmTC6EthIntfPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTC6EthIntfPmEntry  1 }

pxmTC6EthIntfPmSampleDuration OBJECT-TYPE
    SYNTAX      INTEGER {
                    fifteenMinutes(1),
                    day(2)
                }
    MAX-ACCESS  not-accessible
    STATUS      current
    DESCRIPTION "The duration of this sample."
    ::= { pxmTC6EthIntfPmEntry  2 }

pxmTC6EthIntfPmValidity OBJECT-TYPE
    SYNTAX      TruthValue
    MAX-ACCESS  read-only
    STATUS      current
    DESCRIPTION "Flag indicating if data was valid for the entire interval"
    ::= { pxmTC6EthIntfPmEntry  3 }

pxmTC6EthIntfPmTCNum OBJECT-TYPE
    SYNTAX      Integer32
    MAX-ACCESS  read-only
    STATUS      current
    DESCRIPTION "TCNum Historical PM of traffic class - 6 (TC6) on PxmEthIntf"
    ::= { pxmTC6EthIntfPmEntry  4 }

pxmTC6EthIntfPmQueueingDiscardOctets OBJECT-TYPE
    SYNTAX      Counter64
    MAX-ACCESS  read-only
    STATUS      current
    DESCRIPTION "QueueingDiscardOctets Historical PM of traffic class - 6 (TC6) on PxmEthIntf"
    ::= { pxmTC6EthIntfPmEntry  5 }

pxmTC6EthIntfPmQueueingDiscardPkts OBJECT-TYPE
    SYNTAX      Integer32
    MAX-ACCESS  read-only
    STATUS      current
    DESCRIPTION "QueueingDiscardPkts Historical PM of traffic class - 6 (TC6) on PxmEthIntf"
    ::= { pxmTC6EthIntfPmEntry  6 }

pxmTC6EthIntfPmRandomGreenDropPkts OBJECT-TYPE
    SYNTAX      Counter64
    MAX-ACCESS  read-only
    STATUS      current
    DESCRIPTION "RandomGreenDropPkts Historical PM of traffic class - 6 (TC6) on PxmEthIntf"
    ::= { pxmTC6EthIntfPmEntry  7 }

pxmTC6EthIntfPmRandomGreenDropOctets OBJECT-TYPE
    SYNTAX      Counter64
    MAX-ACCESS  read-only
    STATUS      current
    DESCRIPTION "RandomGreenDropOctets Historical PM of traffic class - 6 (TC6) on PxmEthIntf"
    ::= { pxmTC6EthIntfPmEntry  8 }

pxmTC6EthIntfPmRandomYellowDropPkts OBJECT-TYPE
    SYNTAX      Counter64
    MAX-ACCESS  read-only
    STATUS      current
    DESCRIPTION "RandomYellowDropPkts Historical PM of traffic class - 6 (TC6) on PxmEthIntf"
    ::= { pxmTC6EthIntfPmEntry  9 }

pxmTC6EthIntfPmRandomYellowDropOctets OBJECT-TYPE
    SYNTAX      Counter64
    MAX-ACCESS  read-only
    STATUS      current
    DESCRIPTION "RandomYellowDropOctets Historical PM of traffic class - 6 (TC6) on PxmEthIntf"
    ::= { pxmTC6EthIntfPmEntry  10 }

pxmTC6EthIntfPmQueueingTransmitPkts OBJECT-TYPE
    SYNTAX      Counter64
    MAX-ACCESS  read-only
    STATUS      current
    DESCRIPTION "QueueingTransmitPkts Historical PM of traffic class - 6 (TC6) on PxmEthIntf"
    ::= { pxmTC6EthIntfPmEntry  11 }

pxmTC6EthIntfPmQueueingTransmitOctets OBJECT-TYPE
    SYNTAX      Counter64
    MAX-ACCESS  read-only
    STATUS      current
    DESCRIPTION "QueueingTransmitOctets Historical PM of traffic class - 6 (TC6) on PxmEthIntf"
    ::= { pxmTC6EthIntfPmEntry  12 }

-- TC7 Real
pxmTC7EthIntfPmRealTable OBJECT-TYPE
    SYNTAX      SEQUENCE OF PxmTC7EthIntfPmRealEntry
    MAX-ACCESS  not-accessible
    STATUS      current
    DESCRIPTION
        "A list of PxmBwpEthIntfPmReal entries. Each entry is uniquely identified by the value of ifIndex."
    ::= { pxmCmEthIntfRealPm 5 }

pxmTC7EthIntfPmRealEntry  OBJECT-TYPE
    SYNTAX      PxmTC7EthIntfPmRealEntry
    MAX-ACCESS  not-accessible
    STATUS      current
    DESCRIPTION
        "A PxmTC7EthIntfPm entry containing real-time performance information pertaining to Infinera PxmEthIntfPm interfaces.
        This table is a subclass of IfCommon. Entries will exist in this table only for interfaces of
        type PxmEthIntfPm."
    INDEX { ifIndex }
    ::= { pxmTC7EthIntfPmRealTable 1 }

PxmTC7EthIntfPmRealEntry  ::= SEQUENCE {
    pxmTC7EthIntfPmRealTCNum                     Integer32,
    pxmTC7EthIntfPmRealTDQueuingCurrentQDepth    Integer32,
    pxmTC7EthIntfPmRealQueueingDiscardOctets     Counter64,
    pxmTC7EthIntfPmRealQueueingDiscardPkts       Integer32,
    pxmTC7EthIntfPmRealRandomGreenDropPkts       Counter64,
    pxmTC7EthIntfPmRealRandomGreenDropOctets     Counter64,
    pxmTC7EthIntfPmRealRandomYellowDropPkts      Counter64,
    pxmTC7EthIntfPmRealRandomYellowDropOctets    Counter64,
    pxmTC7EthIntfPmRealQueueingTransmitPkts      Counter64,
    pxmTC7EthIntfPmRealQueueingTransmitOctets    Counter64,
    pxmTC7EthIntfPmRealQueueingMeanQSizeUnit     Integer32,
    pxmTC7EthIntfPmRealMeanQSize                 Integer32
}

pxmTC7EthIntfPmRealTCNum OBJECT-TYPE
    SYNTAX      Integer32
    MAX-ACCESS  read-only
    STATUS      current
    DESCRIPTION "TCNum Real PM of traffic class - 7 (TC7) on PxmEthIntf"
    ::= { pxmTC7EthIntfPmRealEntry  1 }

pxmTC7EthIntfPmRealTDQueuingCurrentQDepth OBJECT-TYPE
    SYNTAX      Integer32
    MAX-ACCESS  read-only
    STATUS      current
    DESCRIPTION "TDQueuingCurrentQDepth Real PM of traffic class - 7 (TC7) on PxmEthIntf"
    ::= { pxmTC7EthIntfPmRealEntry  2 }

pxmTC7EthIntfPmRealQueueingDiscardOctets OBJECT-TYPE
    SYNTAX      Counter64
    MAX-ACCESS  read-only
    STATUS      current
    DESCRIPTION "QueueingDiscardOctets Real PM of traffic class - 7 (TC7) on PxmEthIntf"
    ::= { pxmTC7EthIntfPmRealEntry  3 }

pxmTC7EthIntfPmRealQueueingDiscardPkts OBJECT-TYPE
    SYNTAX      Integer32
    MAX-ACCESS  read-only
    STATUS      current
    DESCRIPTION "QueueingDiscardPkts Real PM of traffic class - 7 (TC7) on PxmEthIntf"
    ::= { pxmTC7EthIntfPmRealEntry  4 }

pxmTC7EthIntfPmRealRandomGreenDropPkts OBJECT-TYPE
    SYNTAX      Counter64
    MAX-ACCESS  read-only
    STATUS      current
    DESCRIPTION "RandomGreenDropPkts Real PM of traffic class - 7 (TC7) on PxmEthIntf"
    ::= { pxmTC7EthIntfPmRealEntry  5 }

pxmTC7EthIntfPmRealRandomGreenDropOctets OBJECT-TYPE
    SYNTAX      Counter64
    MAX-ACCESS  read-only
    STATUS      current
    DESCRIPTION "RandomGreenDropOctets Real PM of traffic class - 7 (TC7) on PxmEthIntf"
    ::= { pxmTC7EthIntfPmRealEntry  6 }

pxmTC7EthIntfPmRealRandomYellowDropPkts OBJECT-TYPE
    SYNTAX      Counter64
    MAX-ACCESS  read-only
    STATUS      current
    DESCRIPTION "RandomYellowDropPkts Real PM of traffic class - 7 (TC7) on PxmEthIntf"
    ::= { pxmTC7EthIntfPmRealEntry  7 }

pxmTC7EthIntfPmRealRandomYellowDropOctets OBJECT-TYPE
    SYNTAX      Counter64
    MAX-ACCESS  read-only
    STATUS      current
    DESCRIPTION "RandomYellowDropOctets Real PM of traffic class - 7 (TC7) on PxmEthIntf"
    ::= { pxmTC7EthIntfPmRealEntry  8 }

pxmTC7EthIntfPmRealQueueingTransmitPkts OBJECT-TYPE
    SYNTAX      Counter64
    MAX-ACCESS  read-only
    STATUS      current
    DESCRIPTION "QueueingTransmitPkts Real PM of traffic class - 7 (TC7) on PxmEthIntf"
    ::= { pxmTC7EthIntfPmRealEntry  9 }

pxmTC7EthIntfPmRealQueueingTransmitOctets OBJECT-TYPE
    SYNTAX      Counter64
    MAX-ACCESS  read-only
    STATUS      current
    DESCRIPTION "QueueingTransmitOctets Real PM of traffic class - 7 (TC7) on PxmEthIntf"
    ::= { pxmTC7EthIntfPmRealEntry  10 }

pxmTC7EthIntfPmRealQueueingMeanQSizeUnit OBJECT-TYPE
    SYNTAX      Integer32
    MAX-ACCESS  read-only
    STATUS      current
    DESCRIPTION "QueueingMeanQSizeUnit Real PM of traffic class - 7 (TC7) on PxmEthIntf"
    ::= { pxmTC7EthIntfPmRealEntry  11 }

pxmTC7EthIntfPmRealMeanQSize OBJECT-TYPE
    SYNTAX      Integer32
    MAX-ACCESS  read-only
    STATUS      current
    DESCRIPTION "MeanQSize Real PM of traffic class - 7 (TC7) on PxmEthIntf"
    ::= { pxmTC7EthIntfPmRealEntry  12 }

-- TC7 Historical
pxmTC7EthIntfPmTable OBJECT-TYPE
    SYNTAX      SEQUENCE OF PxmTC7EthIntfPmEntry
    MAX-ACCESS  not-accessible
    STATUS      current
    DESCRIPTION
        "A list of PxmBwpEthIntfPmReal entries. Each entry is uniquely identified by the value of ifIndex."
    ::= { pxmCmEthIntfPm 5 }

pxmTC7EthIntfPmEntry  OBJECT-TYPE
    SYNTAX      PxmTC7EthIntfPmEntry
    MAX-ACCESS  not-accessible
    STATUS      current
    DESCRIPTION "A PxmTC7EthIntf entry containing historical performance information pertaining to Infinera
            PxmEthIntf interfaces. This table is a subclass of IfCommon. Entries will exist in this
            table only for interfaces of type PxmEthIntf.
            Each interface may have a number of entries in this table, each with a different combination
            of timestamp and sample duration."
    INDEX { ifIndex, pxmTC7EthIntfPmSampleDuration, pxmTC7EthIntfPmTimestamp }
    ::= { pxmTC7EthIntfPmTable 1 }

PxmTC7EthIntfPmEntry  ::= SEQUENCE {
    pxmTC7EthIntfPmTimestamp                 Integer32,
    pxmTC7EthIntfPmSampleDuration            INTEGER,
    pxmTC7EthIntfPmValidity                  TruthValue,
    pxmTC7EthIntfPmTCNum                     Integer32,
    pxmTC7EthIntfPmQueueingDiscardOctets     Counter64,
    pxmTC7EthIntfPmQueueingDiscardPkts       Integer32,
    pxmTC7EthIntfPmRandomGreenDropPkts       Counter64,
    pxmTC7EthIntfPmRandomGreenDropOctets     Counter64,
    pxmTC7EthIntfPmRandomYellowDropPkts      Counter64,
    pxmTC7EthIntfPmRandomYellowDropOctets    Counter64,
    pxmTC7EthIntfPmQueueingTransmitPkts      Counter64,
    pxmTC7EthIntfPmQueueingTransmitOctets    Counter64
}

pxmTC7EthIntfPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTC7EthIntfPmEntry  1 }

pxmTC7EthIntfPmSampleDuration OBJECT-TYPE
    SYNTAX      INTEGER {
                    fifteenMinutes(1),
                    day(2)
                }
    MAX-ACCESS  not-accessible
    STATUS      current
    DESCRIPTION
        "The duration of this sample."
    ::= { pxmTC7EthIntfPmEntry  2 }

pxmTC7EthIntfPmValidity OBJECT-TYPE
    SYNTAX      TruthValue
    MAX-ACCESS  read-only
    STATUS      current
    DESCRIPTION "Flag indicating if data was valid for the entire interval"
    ::= { pxmTC7EthIntfPmEntry  3 }

pxmTC7EthIntfPmTCNum OBJECT-TYPE
    SYNTAX      Integer32
    MAX-ACCESS  read-only
    STATUS      current
    DESCRIPTION "TCNum Historical PM of traffic class - 7 (TC7) on PxmEthIntf"
    ::= { pxmTC7EthIntfPmEntry  4 }

pxmTC7EthIntfPmQueueingDiscardOctets OBJECT-TYPE
    SYNTAX      Counter64
    MAX-ACCESS  read-only
    STATUS      current
    DESCRIPTION "QueueingDiscardOctets Historical PM of traffic class - 7 (TC7) on PxmEthIntf"
    ::= { pxmTC7EthIntfPmEntry  5 }

pxmTC7EthIntfPmQueueingDiscardPkts OBJECT-TYPE
    SYNTAX      Integer32
    MAX-ACCESS  read-only
    STATUS      current
    DESCRIPTION "QueueingDiscardPkts Historical PM of traffic class - 7 (TC7) on PxmEthIntf"
    ::= { pxmTC7EthIntfPmEntry  6 }

pxmTC7EthIntfPmRandomGreenDropPkts OBJECT-TYPE
    SYNTAX      Counter64
    MAX-ACCESS  read-only
    STATUS      current
    DESCRIPTION "RandomGreenDropPkts Historical PM of traffic class - 7 (TC7) on PxmEthIntf"
    ::= { pxmTC7EthIntfPmEntry  7 }

pxmTC7EthIntfPmRandomGreenDropOctets OBJECT-TYPE
    SYNTAX      Counter64
    MAX-ACCESS  read-only
    STATUS      current
    DESCRIPTION "RandomGreenDropOctets Historical PM of traffic class - 7 (TC7) on PxmEthIntf"
    ::= { pxmTC7EthIntfPmEntry  8 }

pxmTC7EthIntfPmRandomYellowDropPkts OBJECT-TYPE
    SYNTAX      Counter64
    MAX-ACCESS  read-only
    STATUS      current
    DESCRIPTION "RandomYellowDropPkts Historical PM of traffic class - 7 (TC7) on PxmEthIntf"
    ::= { pxmTC7EthIntfPmEntry  9 }

pxmTC7EthIntfPmRandomYellowDropOctets OBJECT-TYPE
    SYNTAX      Counter64
    MAX-ACCESS  read-only
    STATUS      current
    DESCRIPTION "RandomYellowDropOctets Historical PM of traffic class - 7 (TC7) on PxmEthIntf"
    ::= { pxmTC7EthIntfPmEntry  10 }

pxmTC7EthIntfPmQueueingTransmitPkts OBJECT-TYPE
    SYNTAX      Counter64
    MAX-ACCESS  read-only
    STATUS      current
    DESCRIPTION "QueueingTransmitPkts Historical PM of traffic class - 7 (TC7) on PxmEthIntf"
    ::= { pxmTC7EthIntfPmEntry  11 }

pxmTC7EthIntfPmQueueingTransmitOctets OBJECT-TYPE
    SYNTAX      Counter64
    MAX-ACCESS  read-only
    STATUS      current
    DESCRIPTION "QueueingTransmitOctets Historical PM of traffic class - 7 (TC7) on PxmEthIntf"
    ::= { pxmTC7EthIntfPmEntry  12 }

-- TCANY Real
pxmTCANYEthIntfPmRealTable OBJECT-TYPE
    SYNTAX      SEQUENCE OF PxmTCANYEthIntfPmRealEntry
    MAX-ACCESS  not-accessible
    STATUS      current
    DESCRIPTION
        "A list of PxmBwpEthIntfPmReal entries. Each entry is uniquely identified by the value of ifIndex."
    ::= { pxmCmEthIntfRealPm 6 }

pxmTCANYEthIntfPmRealEntry  OBJECT-TYPE
    SYNTAX      PxmTCANYEthIntfPmRealEntry
    MAX-ACCESS  not-accessible
    STATUS      current
    DESCRIPTION
        "A PxmTC0EthIntfPm entry containing real-time performance information pertaining to Infinera PxmEthIntfPm interfaces.
        This table is a subclass of IfCommon. Entries will exist in this table only for interfaces of
        type PxmEthIntfPm."
    INDEX { ifIndex }
    ::= { pxmTCANYEthIntfPmRealTable 1 }

PxmTCANYEthIntfPmRealEntry  ::= SEQUENCE {
    pxmTCANYEthIntfPmRealTCNum                     Integer32,
    pxmTCANYEthIntfPmRealTDQueuingCurrentQDepth    Integer32,
    pxmTCANYEthIntfPmRealQueueingDiscardOctets     Counter64,
    pxmTCANYEthIntfPmRealQueueingDiscardPkts       Integer32,
    pxmTCANYEthIntfPmRealRandomGreenDropPkts       Counter64,
    pxmTCANYEthIntfPmRealRandomGreenDropOctets     Counter64,
    pxmTCANYEthIntfPmRealRandomYellowDropPkts      Counter64,
    pxmTCANYEthIntfPmRealRandomYellowDropOctets    Counter64,
    pxmTCANYEthIntfPmRealQueueingTransmitPkts      Counter64,
    pxmTCANYEthIntfPmRealQueueingTransmitOctets    Counter64,
    pxmTCANYEthIntfPmRealQueueingMeanQSizeUnit     Integer32,
    pxmTCANYEthIntfPmRealMeanQSize                 Integer32
}

pxmTCANYEthIntfPmRealTCNum OBJECT-TYPE
    SYNTAX      Integer32
    MAX-ACCESS  read-only
    STATUS      current
    DESCRIPTION "TCNum Real PM of traffic class - ANY (TCANY) on PxmEthIntf"
    ::= { pxmTCANYEthIntfPmRealEntry  1 }

pxmTCANYEthIntfPmRealTDQueuingCurrentQDepth OBJECT-TYPE
    SYNTAX      Integer32
    MAX-ACCESS  read-only
    STATUS      current
    DESCRIPTION "TDQueuingCurrentQDepth Real PM of traffic class - ANY (TCANY) on PxmEthIntf"
    ::= { pxmTCANYEthIntfPmRealEntry  2 }

pxmTCANYEthIntfPmRealQueueingDiscardOctets OBJECT-TYPE
    SYNTAX      Counter64
    MAX-ACCESS  read-only
    STATUS      current
    DESCRIPTION "QueueingDiscardOctets Real PM of traffic class - ANY (TCANY) on PxmEthIntf"
    ::= { pxmTCANYEthIntfPmRealEntry  3 }

pxmTCANYEthIntfPmRealQueueingDiscardPkts OBJECT-TYPE
    SYNTAX      Integer32
    MAX-ACCESS  read-only
    STATUS      current
    DESCRIPTION "QueueingDiscardPkts Real PM of traffic class - ANY (TCANY) on PxmEthIntf"
    ::= { pxmTCANYEthIntfPmRealEntry  4 }

pxmTCANYEthIntfPmRealRandomGreenDropPkts OBJECT-TYPE
    SYNTAX      Counter64
    MAX-ACCESS  read-only
    STATUS      current
    DESCRIPTION "RandomGreenDropPkts Real PM of traffic class - ANY (TCANY) on PxmEthIntf"
    ::= { pxmTCANYEthIntfPmRealEntry  5 }

pxmTCANYEthIntfPmRealRandomGreenDropOctets OBJECT-TYPE
    SYNTAX      Counter64
    MAX-ACCESS  read-only
    STATUS      current
    DESCRIPTION "RandomGreenDropOctets Real PM of traffic class - ANY (TCANY) on PxmEthIntf"
    ::= { pxmTCANYEthIntfPmRealEntry  6 }

pxmTCANYEthIntfPmRealRandomYellowDropPkts OBJECT-TYPE
    SYNTAX      Counter64
    MAX-ACCESS  read-only
    STATUS      current
    DESCRIPTION "RandomYellowDropPkts Real PM of traffic class - ANY (TCANY) on PxmEthIntf"
    ::= { pxmTCANYEthIntfPmRealEntry  7 }

pxmTCANYEthIntfPmRealRandomYellowDropOctets OBJECT-TYPE
    SYNTAX      Counter64
    MAX-ACCESS  read-only
    STATUS      current
    DESCRIPTION "RandomYellowDropOctets Real PM of traffic class - ANY (TCANY) on PxmEthIntf"
    ::= { pxmTCANYEthIntfPmRealEntry  8 }

pxmTCANYEthIntfPmRealQueueingTransmitPkts OBJECT-TYPE
    SYNTAX      Counter64
    MAX-ACCESS  read-only
    STATUS      current
    DESCRIPTION "QueueingTransmitPkts Real PM of traffic class - ANY (TCANY) on PxmEthIntf"
    ::= { pxmTCANYEthIntfPmRealEntry  9 }

pxmTCANYEthIntfPmRealQueueingTransmitOctets OBJECT-TYPE
    SYNTAX      Counter64
    MAX-ACCESS  read-only
    STATUS      current
    DESCRIPTION "QueueingTransmitOctets Real PM of traffic class - ANY (TCANY) on PxmEthIntf"
    ::= { pxmTCANYEthIntfPmRealEntry  10 }

pxmTCANYEthIntfPmRealQueueingMeanQSizeUnit OBJECT-TYPE
    SYNTAX      Integer32
    MAX-ACCESS  read-only
    STATUS      current
    DESCRIPTION "QueueingMeanQSizeUnit Real PM of traffic class - ANY (TCANY) on PxmEthIntf"
    ::= { pxmTCANYEthIntfPmRealEntry  11 }

pxmTCANYEthIntfPmRealMeanQSize OBJECT-TYPE
    SYNTAX      Integer32
    MAX-ACCESS  read-only
    STATUS      current
    DESCRIPTION "MeanQSize Real PM of traffic class - ANY (TCANY) on PxmEthIntf"
    ::= { pxmTCANYEthIntfPmRealEntry  12 }

-- TCANY Historical
pxmTCANYEthIntfPmTable OBJECT-TYPE
    SYNTAX      SEQUENCE OF PxmTCANYEthIntfPmEntry
    MAX-ACCESS  not-accessible
    STATUS      current
    DESCRIPTION
        "A list of PxmBwpEthIntfPmReal entries. Each entry is uniquely identified by the value of ifIndex."
    ::= { pxmCmEthIntfPm 6 }

pxmTCANYEthIntfPmEntry  OBJECT-TYPE
    SYNTAX      PxmTCANYEthIntfPmEntry
    MAX-ACCESS  not-accessible
    STATUS      current
    DESCRIPTION "A PxmTCANYEthIntf entry containing historical performance information pertaining to Infinera
            PxmEthIntf interfaces. This table is a subclass of IfCommon. Entries will exist in this
            table only for interfaces of type PxmEthIntf.
            Each interface may have a number of entries in this table, each with a different combination
            of timestamp and sample duration."
    INDEX { ifIndex, pxmTCANYEthIntfPmSampleDuration, pxmTCANYEthIntfPmTimestamp }
    ::= { pxmTCANYEthIntfPmTable 1 }

PxmTCANYEthIntfPmEntry  ::= SEQUENCE {
    pxmTCANYEthIntfPmTimestamp                 Integer32,
    pxmTCANYEthIntfPmSampleDuration            INTEGER,
    pxmTCANYEthIntfPmValidity                  TruthValue,
    pxmTCANYEthIntfPmTCNum                     Integer32,
    pxmTCANYEthIntfPmQueueingDiscardOctets     Counter64,
    pxmTCANYEthIntfPmQueueingDiscardPkts       Integer32,
    pxmTCANYEthIntfPmRandomGreenDropPkts       Counter64,
    pxmTCANYEthIntfPmRandomGreenDropOctets     Counter64,
    pxmTCANYEthIntfPmRandomYellowDropPkts      Counter64,
    pxmTCANYEthIntfPmRandomYellowDropOctets    Counter64,
    pxmTCANYEthIntfPmQueueingTransmitPkts      Counter64,
    pxmTCANYEthIntfPmQueueingTransmitOctets    Counter64
}

pxmTCANYEthIntfPmTimestamp OBJECT-TYPE
    SYNTAX      Integer32 (0..2147483647)
    MAX-ACCESS  not-accessible
    STATUS      current
    DESCRIPTION
        "End Time stamp for this interval. If this time is later than the current time,
        then the data for this bucket is currently being collected."
    ::= { pxmTCANYEthIntfPmEntry  1 }

pxmTCANYEthIntfPmSampleDuration OBJECT-TYPE
    SYNTAX      INTEGER {
                    fifteenMinutes(1),
                    day(2)
                }
    MAX-ACCESS  not-accessible
    STATUS      current
    DESCRIPTION
        "The duration of this sample."
    ::= { pxmTCANYEthIntfPmEntry  2 }

pxmTCANYEthIntfPmValidity OBJECT-TYPE
    SYNTAX      TruthValue
    MAX-ACCESS  read-only
    STATUS      current
    DESCRIPTION "Flag indicating if data was valid for the entire interval"
    ::= { pxmTCANYEthIntfPmEntry  3 }

pxmTCANYEthIntfPmTCNum OBJECT-TYPE
    SYNTAX      Integer32
    MAX-ACCESS  read-only
    STATUS      current
    DESCRIPTION "TCNum Historical PM of traffic class - ANY (TCANY) on PxmEthIntf"
    ::= { pxmTCANYEthIntfPmEntry  4 }

pxmTCANYEthIntfPmQueueingDiscardOctets OBJECT-TYPE
    SYNTAX      Counter64
    MAX-ACCESS  read-only
    STATUS      current
    DESCRIPTION "QueueingDiscardOctets Historical PM of traffic class - ANY (TCANY) on PxmEthIntf"
    ::= { pxmTCANYEthIntfPmEntry  5 }

pxmTCANYEthIntfPmQueueingDiscardPkts OBJECT-TYPE
    SYNTAX      Integer32
    MAX-ACCESS  read-only
    STATUS      current
    DESCRIPTION "QueueingDiscardPkts Historical PM of traffic class - ANY (TCANY) on PxmEthIntf"
    ::= { pxmTCANYEthIntfPmEntry  6 }

pxmTCANYEthIntfPmRandomGreenDropPkts OBJECT-TYPE
    SYNTAX      Counter64
    MAX-ACCESS  read-only
    STATUS      current
    DESCRIPTION "RandomGreenDropPkts Historical PM of traffic class - ANY (TCANY) on PxmEthIntf"
    ::= { pxmTCANYEthIntfPmEntry  7 }

pxmTCANYEthIntfPmRandomGreenDropOctets OBJECT-TYPE
    SYNTAX      Counter64
    MAX-ACCESS  read-only
    STATUS      current
    DESCRIPTION "RandomGreenDropOctets Historical PM of traffic class - ANY (TCANY) on PxmEthIntf"
    ::= { pxmTCANYEthIntfPmEntry  8 }

pxmTCANYEthIntfPmRandomYellowDropPkts OBJECT-TYPE
    SYNTAX      Counter64
    MAX-ACCESS  read-only
    STATUS      current
    DESCRIPTION "RandomYellowDropPkts Historical PM of traffic class - ANY (TCANY) on PxmEthIntf"
    ::= { pxmTCANYEthIntfPmEntry  9 }

pxmTCANYEthIntfPmRandomYellowDropOctets OBJECT-TYPE
    SYNTAX      Counter64
    MAX-ACCESS  read-only
    STATUS      current
    DESCRIPTION "RandomYellowDropOctets Historical PM of traffic class - ANY (TCANY) on PxmEthIntf"
    ::= { pxmTCANYEthIntfPmEntry  10 }

pxmTCANYEthIntfPmQueueingTransmitPkts OBJECT-TYPE
    SYNTAX      Counter64
    MAX-ACCESS  read-only
    STATUS      current
    DESCRIPTION "QueueingTransmitPkts Historical PM of traffic class - ANY (TCANY) on PxmEthIntf"
    ::= { pxmTCANYEthIntfPmEntry  11 }

pxmTCANYEthIntfPmQueueingTransmitOctets OBJECT-TYPE
    SYNTAX      Counter64
    MAX-ACCESS  read-only
    STATUS      current
    DESCRIPTION "QueueingTransmitOctets Historical PM of traffic class - ANY (TCANY) on PxmEthIntf"
    ::= { pxmTCANYEthIntfPmEntry  12 }

-- End of CM PMs

-- Conformance Statements
pxmEthIntfPmConformance    OBJECT IDENTIFIER ::= { pxmEthIntfPmMIB 4 }
pxmEthIntfPmCompliances    OBJECT IDENTIFIER ::= { pxmEthIntfPmConformance 1 }
pxmEthIntfPmGroups         OBJECT IDENTIFIER ::= { pxmEthIntfPmConformance 2 }

pxmEthIntfPmCompliance MODULE-COMPLIANCE
    STATUS current
    DESCRIPTION
        "Describes the requirements for conformance to the PM-PXMETHINTF-MIB"
    MODULE
    MANDATORY-GROUPS { pxmEthIntfPmGroup }
    ::= { pxmEthIntfPmCompliances 1 }

pxmEthIntfPmRealCompliance MODULE-COMPLIANCE
    STATUS current
    DESCRIPTION
        "Describes the requirements for conformance to the pxmEthIntfPmReal-MIB"
    MODULE
    MANDATORY-GROUPS { pxmEthIntfPmRealGroup }
    ::= { pxmEthIntfPmCompliances 2 }

pxmEthIntfPmGroup OBJECT-GROUP
    OBJECTS {
        pxmEthIntfPmValidity,
        pxmEthIntfPmRxPackets,
        pxmEthIntfPmRxOctets,
        pxmEthIntfPmRxCrcAlignedErr,
        pxmEthIntfPmRxUndersized,
        pxmEthIntfPmRxOversized,
        pxmEthIntfPmRxUnicastPkts,
        pxmEthIntfPmRxBroadcastPkts,
        pxmEthIntfPmRxMulticastPkts,
        pxmEthIntfPmRxPktErrors,
        pxmEthIntfPmRxSize64,
        pxmEthIntfPmRxSize65to127,
        pxmEthIntfPmRxSize128to255,
        pxmEthIntfPmRxSize256to511,
        pxmEthIntfPmRxSize512to1023,
        pxmEthIntfPmRxSize1024to1518,
        pxmEthIntfPmTxPackets,
        pxmEthIntfPmTxOctets,
        pxmEthIntfPmTxUnicastPkts,
        pxmEthIntfPmTxBroadcastPkts,
        pxmEthIntfPmTxMulticastPkts,
        pxmEthIntfPmTxPktErrors
}
    STATUS current
    DESCRIPTION
        " A collection of objects for reading the performance of the pxmEthIntf."
    ::= { pxmEthIntfPmGroups 1 }


pxmEthIntfPmRealGroup OBJECT-GROUP
    OBJECTS {
        pxmEthIntfPmRealRxPackets,
        pxmEthIntfPmRealRxOctets,
        pxmEthIntfPmRealRxCrcAlignedErr,
        pxmEthIntfPmRealRxUndersized,
        pxmEthIntfPmRealRxOversized,
        pxmEthIntfPmRealRxUnicastPkts,
        pxmEthIntfPmRealRxBroadcastPkts,
        pxmEthIntfPmRealRxMulticastPkts,
        pxmEthIntfPmRealRxPktErrors,
        pxmEthIntfPmRealRxSize64,
        pxmEthIntfPmRealRxSize65to127,
        pxmEthIntfPmRealRxSize128to255,
        pxmEthIntfPmRealRxSize256to511,
        pxmEthIntfPmRealRxSize512to1023,
        pxmEthIntfPmRealRxSize1024to1518,
        pxmEthIntfPmRealRxLU,
        pxmEthIntfPmRealTxPackets,
        pxmEthIntfPmRealTxOctets,
        pxmEthIntfPmRealTxUnicastPkts,
        pxmEthIntfPmRealTxBroadcastPkts,
        pxmEthIntfPmRealTxMulticastPkts,
        pxmEthIntfPmRealTxPktErrors,
        pxmEthIntfPmRealTxLU
}
    STATUS current
    DESCRIPTION
    " A collection of objects for reading the real-time performance of the pxmEthIntf."
    ::= { pxmEthIntfPmGroups 2 }

pxmBwpEthIntfPmGroup  OBJECT-GROUP
    OBJECTS {
        pxmBwpEthIntfPmTimestamp,
        pxmBwpEthIntfPmSampleDuration,
        pxmBwpEthIntfPmValidity,
        pxmBwpEthIntfPmPolicerConformedPkts,
        pxmBwpEthIntfPmPolicerConformedOctets,
        pxmBwpEthIntfPmPolicerExceededPkts,
        pxmBwpEthIntfPmPolicerExceededOctets,
        pxmBwpEthIntfPmPolicerViolatedPkts,
        pxmBwpEthIntfPmPolicerViolatedOctets
    }
    STATUS current
    DESCRIPTION
        " A collection of objects for reading the metering counters of pxmEthIntf."
    ::= { pxmEthIntfPmGroups 3 }

pxmBwpEthIntfPmRealGroup  OBJECT-GROUP
    OBJECTS {
        pxmBwpEthIntfPmRealPolicerConformedPkts,
        pxmBwpEthIntfPmRealPolicerConformedOctets,
        pxmBwpEthIntfPmRealPolicerExceededPkts,
        pxmBwpEthIntfPmRealPolicerExceededOctets,
        pxmBwpEthIntfPmRealPolicerViolatedPkts,
        pxmBwpEthIntfPmRealPolicerViolatedOctets
    }
    STATUS current
    DESCRIPTION
        " A collection of objects for reading the metering counters of pxmEthIntf."
    ::= { pxmEthIntfPmGroups 4 }

pxmTC0EthIntfPmRealGroup OBJECT-GROUP
    OBJECTS {
        pxmTC0EthIntfPmRealTCNum,
        pxmTC0EthIntfPmRealTDQueuingCurrentQDepth,
        pxmTC0EthIntfPmRealQueueingDiscardOctets,
        pxmTC0EthIntfPmRealQueueingDiscardPkts,
        pxmTC0EthIntfPmRealRandomGreenDropPkts,
        pxmTC0EthIntfPmRealRandomGreenDropOctets,
        pxmTC0EthIntfPmRealRandomYellowDropPkts,
        pxmTC0EthIntfPmRealRandomYellowDropOctets,
        pxmTC0EthIntfPmRealQueueingTransmitPkts,
        pxmTC0EthIntfPmRealQueueingTransmitOctets,
        pxmTC0EthIntfPmRealQueueingMeanQSizeUnit,
        pxmTC0EthIntfPmRealMeanQSize
    }
    STATUS current
    DESCRIPTION
        " A collection of objects for reading the real-time performance of the pxmEthIntf."
    ::= { pxmEthIntfPmGroups 5 }

pxmTC0EthIntfPmGroup OBJECT-GROUP
    OBJECTS {
        pxmTC0EthIntfPmValidity,
        pxmTC0EthIntfPmTCNum,
        pxmTC0EthIntfPmQueueingDiscardOctets,
        pxmTC0EthIntfPmQueueingDiscardPkts,
        pxmTC0EthIntfPmRandomGreenDropPkts,
        pxmTC0EthIntfPmRandomGreenDropOctets,
        pxmTC0EthIntfPmRandomYellowDropPkts,
        pxmTC0EthIntfPmRandomYellowDropOctets,
        pxmTC0EthIntfPmQueueingTransmitPkts,
        pxmTC0EthIntfPmQueueingTransmitOctets
    }
    STATUS current
    DESCRIPTION
        " A collection of objects for reading the real-time performance of the pxmEthIntf."
    ::= { pxmEthIntfPmGroups 6 }

pxmTC2EthIntfPmRealGroup OBJECT-GROUP
    OBJECTS {
        pxmTC2EthIntfPmRealTCNum,
        pxmTC2EthIntfPmRealTDQueuingCurrentQDepth,
        pxmTC2EthIntfPmRealQueueingDiscardOctets,
        pxmTC2EthIntfPmRealQueueingDiscardPkts,
        pxmTC2EthIntfPmRealRandomGreenDropPkts,
        pxmTC2EthIntfPmRealRandomGreenDropOctets,
        pxmTC2EthIntfPmRealRandomYellowDropPkts,
        pxmTC2EthIntfPmRealRandomYellowDropOctets,
        pxmTC2EthIntfPmRealQueueingTransmitPkts,
        pxmTC2EthIntfPmRealQueueingTransmitOctets,
        pxmTC2EthIntfPmRealQueueingMeanQSizeUnit,
        pxmTC2EthIntfPmRealMeanQSize
    }
    STATUS current
    DESCRIPTION
        " A collection of objects for reading the real-time performance of the pxmEthIntf."
    ::= { pxmEthIntfPmGroups 7 }

pxmTC2EthIntfPmGroup OBJECT-GROUP
    OBJECTS {
        pxmTC2EthIntfPmValidity,
        pxmTC2EthIntfPmTCNum,
        pxmTC2EthIntfPmQueueingDiscardOctets,
        pxmTC2EthIntfPmQueueingDiscardPkts,
        pxmTC2EthIntfPmRandomGreenDropPkts,
        pxmTC2EthIntfPmRandomGreenDropOctets,
        pxmTC2EthIntfPmRandomYellowDropPkts,
        pxmTC2EthIntfPmRandomYellowDropOctets,
        pxmTC2EthIntfPmQueueingTransmitPkts,
        pxmTC2EthIntfPmQueueingTransmitOctets
    }
    STATUS current
    DESCRIPTION
        " A collection of objects for reading the real-time performance of the pxmEthIntf."
    ::= { pxmEthIntfPmGroups 8 }

pxmTC4EthIntfPmRealGroup OBJECT-GROUP
    OBJECTS {
        pxmTC4EthIntfPmRealTCNum,
        pxmTC4EthIntfPmRealTDQueuingCurrentQDepth,
        pxmTC4EthIntfPmRealQueueingDiscardOctets,
        pxmTC4EthIntfPmRealQueueingDiscardPkts,
        pxmTC4EthIntfPmRealRandomGreenDropPkts,
        pxmTC4EthIntfPmRealRandomGreenDropOctets,
        pxmTC4EthIntfPmRealRandomYellowDropPkts,
        pxmTC4EthIntfPmRealRandomYellowDropOctets,
        pxmTC4EthIntfPmRealQueueingTransmitPkts,
        pxmTC4EthIntfPmRealQueueingTransmitOctets,
        pxmTC4EthIntfPmRealQueueingMeanQSizeUnit,
        pxmTC4EthIntfPmRealMeanQSize
    }
    STATUS current
    DESCRIPTION
        " A collection of objects for reading the real-time performance of the pxmEthIntf."
    ::= { pxmEthIntfPmGroups 9 }

pxmTC4EthIntfPmGroup OBJECT-GROUP
    OBJECTS {
        pxmTC4EthIntfPmValidity,
        pxmTC4EthIntfPmTCNum,
        pxmTC4EthIntfPmQueueingDiscardOctets,
        pxmTC4EthIntfPmQueueingDiscardPkts,
        pxmTC4EthIntfPmRandomGreenDropPkts,
        pxmTC4EthIntfPmRandomGreenDropOctets,
        pxmTC4EthIntfPmRandomYellowDropPkts,
        pxmTC4EthIntfPmRandomYellowDropOctets,
        pxmTC4EthIntfPmQueueingTransmitPkts,
        pxmTC4EthIntfPmQueueingTransmitOctets
    }
    STATUS current
    DESCRIPTION
        " A collection of objects for reading the real-time performance of the pxmEthIntf."
    ::= { pxmEthIntfPmGroups 10 }

pxmTC6EthIntfPmRealGroup OBJECT-GROUP
    OBJECTS {
        pxmTC6EthIntfPmRealTCNum,
        pxmTC6EthIntfPmRealTDQueuingCurrentQDepth,
        pxmTC6EthIntfPmRealQueueingDiscardOctets,
        pxmTC6EthIntfPmRealQueueingDiscardPkts,
        pxmTC6EthIntfPmRealRandomGreenDropPkts,
        pxmTC6EthIntfPmRealRandomGreenDropOctets,
        pxmTC6EthIntfPmRealRandomYellowDropPkts,
        pxmTC6EthIntfPmRealRandomYellowDropOctets,
        pxmTC6EthIntfPmRealQueueingTransmitPkts,
        pxmTC6EthIntfPmRealQueueingTransmitOctets,
        pxmTC6EthIntfPmRealQueueingMeanQSizeUnit,
        pxmTC6EthIntfPmRealMeanQSize
    }
    STATUS current
    DESCRIPTION
        " A collection of objects for reading the real-time performance of the pxmEthIntf."
    ::= { pxmEthIntfPmGroups 11 }

pxmTC6EthIntfPmGroup OBJECT-GROUP
    OBJECTS {
        pxmTC6EthIntfPmValidity,
        pxmTC6EthIntfPmTCNum,
        pxmTC6EthIntfPmQueueingDiscardOctets,
        pxmTC6EthIntfPmQueueingDiscardPkts,
        pxmTC6EthIntfPmRandomGreenDropPkts,
        pxmTC6EthIntfPmRandomGreenDropOctets,
        pxmTC6EthIntfPmRandomYellowDropPkts,
        pxmTC6EthIntfPmRandomYellowDropOctets,
        pxmTC6EthIntfPmQueueingTransmitPkts,
        pxmTC6EthIntfPmQueueingTransmitOctets
    }
    STATUS current
    DESCRIPTION
        " A collection of objects for reading the real-time performance of the pxmEthIntf."
    ::= { pxmEthIntfPmGroups 12 }

pxmTC7EthIntfPmRealGroup OBJECT-GROUP
    OBJECTS {
        pxmTC7EthIntfPmRealTCNum,
        pxmTC7EthIntfPmRealTDQueuingCurrentQDepth,
        pxmTC7EthIntfPmRealQueueingDiscardOctets,
        pxmTC7EthIntfPmRealQueueingDiscardPkts,
        pxmTC7EthIntfPmRealRandomGreenDropPkts,
        pxmTC7EthIntfPmRealRandomGreenDropOctets,
        pxmTC7EthIntfPmRealRandomYellowDropPkts,
        pxmTC7EthIntfPmRealRandomYellowDropOctets,
        pxmTC7EthIntfPmRealQueueingTransmitPkts,
        pxmTC7EthIntfPmRealQueueingTransmitOctets,
        pxmTC7EthIntfPmRealQueueingMeanQSizeUnit,
        pxmTC7EthIntfPmRealMeanQSize
    }
    STATUS current
    DESCRIPTION
        " A collection of objects for reading the real-time performance of the pxmEthIntf."
    ::= { pxmEthIntfPmGroups 13 }

pxmTC7EthIntfPmGroup OBJECT-GROUP
    OBJECTS {
        pxmTC7EthIntfPmValidity,
        pxmTC7EthIntfPmTCNum,
        pxmTC7EthIntfPmQueueingDiscardOctets,
        pxmTC7EthIntfPmQueueingDiscardPkts,
        pxmTC7EthIntfPmRandomGreenDropPkts,
        pxmTC7EthIntfPmRandomGreenDropOctets,
        pxmTC7EthIntfPmRandomYellowDropPkts,
        pxmTC7EthIntfPmRandomYellowDropOctets,
        pxmTC7EthIntfPmQueueingTransmitPkts,
        pxmTC7EthIntfPmQueueingTransmitOctets
    }
    STATUS current
    DESCRIPTION
        " A collection of objects for reading the real-time performance of the pxmEthIntf."
    ::= { pxmEthIntfPmGroups 14 }

pxmTCANYEthIntfPmRealGroup OBJECT-GROUP
    OBJECTS {
        pxmTCANYEthIntfPmRealTCNum,
        pxmTCANYEthIntfPmRealTDQueuingCurrentQDepth,
        pxmTCANYEthIntfPmRealQueueingDiscardOctets,
        pxmTCANYEthIntfPmRealQueueingDiscardPkts,
        pxmTCANYEthIntfPmRealRandomGreenDropPkts,
        pxmTCANYEthIntfPmRealRandomGreenDropOctets,
        pxmTCANYEthIntfPmRealRandomYellowDropPkts,
        pxmTCANYEthIntfPmRealRandomYellowDropOctets,
        pxmTCANYEthIntfPmRealQueueingTransmitPkts,
        pxmTCANYEthIntfPmRealQueueingTransmitOctets,
        pxmTCANYEthIntfPmRealQueueingMeanQSizeUnit,
        pxmTCANYEthIntfPmRealMeanQSize
    }
    STATUS current
    DESCRIPTION
        " A collection of objects for reading the real-time performance of the pxmEthIntf."
    ::= { pxmEthIntfPmGroups 15 }

pxmTCANYEthIntfPmGroup OBJECT-GROUP
    OBJECTS {
        pxmTCANYEthIntfPmValidity,
        pxmTCANYEthIntfPmTCNum,
        pxmTCANYEthIntfPmQueueingDiscardOctets,
        pxmTCANYEthIntfPmQueueingDiscardPkts,
        pxmTCANYEthIntfPmRandomGreenDropPkts,
        pxmTCANYEthIntfPmRandomGreenDropOctets,
        pxmTCANYEthIntfPmRandomYellowDropPkts,
        pxmTCANYEthIntfPmRandomYellowDropOctets,
        pxmTCANYEthIntfPmQueueingTransmitPkts,
        pxmTCANYEthIntfPmQueueingTransmitOctets
    }
    STATUS current
    DESCRIPTION
        " A collection of objects for reading the real-time performance of the pxmEthIntf."
    ::= { pxmEthIntfPmGroups 16 }

END
