-- *****************************************************************
-- INFINERA-TP-ODUICLIENTCTP-MIB
-- Copyright (c) 2011-2012 by Infinera Inc.
-- All rights reserved.
-- ****************************************************************

INFINERA-TP-ODUICLIENTCTP-MIB DEFINITIONS ::= BEGIN

IMPORTS
    MODULE-IDENTITY, OBJECT-TYPE,
    Integer32, Counter64                        FROM SNMPv2-SMI
    MODULE-COMPLIANCE, OBJECT-GROUP             FROM SNMPv2-CONF
    DisplayString, TruthValue                   FROM SNMPv2-TC
    ifIndex                                     FROM IF-MIB
    InfnServiceType,InfnEqptType,InfnArc,
    InfnEnableDisable, InfnOtuBitRateK,
    InfnTcmList, InfnServiceMode,
    InfnMonitoringMode, InfnSMQ,
    InfnRate,InfnXconType, InfnTsgType		    FROM INFINERA-TC-MIB
    terminationPoint                            FROM INFINERA-REG-MIB;


oduiClientCtpMIB MODULE-IDENTITY
    LAST-UPDATED  "200907200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "200907200000Z"
    DESCRIPTION
        "First Version"
    ::= { terminationPoint 30 }

oduiClientCtpTable OBJECT-TYPE
    SYNTAX      SEQUENCE OF OduiClientCtpEntry
    MAX-ACCESS  not-accessible
    STATUS      current
    DESCRIPTION
        "A list of OduiClientCtp entries. Each entry is uniquely identified by the value of ifIndex."
    ::= { oduiClientCtpMIB 1 }

oduiClientCtpEntry  OBJECT-TYPE
    SYNTAX      OduiClientCtpEntry
    MAX-ACCESS  not-accessible
    STATUS      current
    DESCRIPTION
        "A OduiClientCtp entry containing information pertaining to Infinera OduiClientCtp interfaces. Entries will exist in this table for interfaces of type 		oduiclientCtp."
    INDEX { ifIndex }
    ::= { oduiClientCtpTable 1 }


OduiClientCtpEntry  ::= SEQUENCE {
    oduiClientCtpServiceMode                     InfnServiceMode,
    oduiClientCtpServiceModeQualifier            InfnSMQ,
    oduiClientCtpFacMonitoringMode               InfnMonitoringMode,
    oduiClientCtpFacTxTTI                        DisplayString,
    oduiClientCtpFacExpectedSAPI                 DisplayString,
    oduiClientCtpFacExpectedDAPI                 DisplayString,
    oduiClientCtpTermTxTTI                       DisplayString,
    oduiClientCtpTermExpectedSAPI                DisplayString,
    oduiClientCtpTermExpectedDAPI                DisplayString,
    oduiClientCtpFacReceivedTTI                  DisplayString,
    oduiClientCtpTermReceivedTTI                 DisplayString,
    oduiClientCtpRxDs15MinutesTce                Integer32,
    oduiClientCtpRxDsDayTce                      Integer32,
    oduiClientCtpRxDsDayTceReporting             TruthValue,
    oduiClientCtpRxDs15MinutesTceReporting       TruthValue,
    oduiClientCtpFacTimDetMode                   INTEGER,
    oduiClientCtpTermTimDetMode                  INTEGER,
    oduiClientCtpTcmList                         BITS,
    oduiClientCtpConfiguredServiceType           InfnServiceType,
    oduiClientCtpFacPmHistStatsEnable            InfnEnableDisable,
    oduiClientCtpTermPmHistStatsEnable           InfnEnableDisable,
    oduiClientCtpAlarmReportControl              InfnArc,
    oduiClientCtpSupportingCircuitIdList         DisplayString,
    oduiClientCtpFacDSThreshold                  Integer32,
    oduiClientCtpTermDSThreshold                 Integer32,
    oduiClientCtpTermMonitoringMode              InfnMonitoringMode,
    oduiClientCtpTSCount			             Integer32,
    oduiClientCtprate				             DisplayString,
    oduiClientCtpTributaryPortNumber		     Integer32,
    oduiClientCtpExpectedTPNs			         Integer32,
    oduiClientCtpDetectedTPNs			         Integer32,
    oduiClientCtpsupportingOPUTributarySlots	 DisplayString,
    oduiClientCtpavailableOPUTributarySlots	     DisplayString,
    oduiClientCtpdatarate 			             InfnRate,
    oduiClientCtpCrossConnectType		         InfnXconType,
    oduiClientCtpSupportingTP			         DisplayString,
    oduiClientCtpTsg				             InfnTsgType,
    oduiClientCtpExpectedPayload		         InfnServiceType,
    oduiClientCtpLoopBack			             INTEGER,
    oduiClientCtpFacSDThreshold                  Integer32,
    oduiClientCtpRxDsF15MinutesTce               Integer32,
    oduiClientCtpRxDsF15MinutesTceReporting      TruthValue,
    oduiClientCtpRxDsFDayTce                     Integer32,
    oduiClientCtpRxDsFDayTceReporting            TruthValue,
    oduiClientCtpRxBei15MinutesTce               Integer32,
    oduiClientCtpRxBei15MinutesTceReporting      TruthValue,
    oduiClientCtpRxBeiDayTce                     Integer32,
    oduiClientCtpRxBeiDayTceReporting            TruthValue,
	oduiClientCtpBitRateK						 InfnOtuBitRateK
}

oduiClientCtpServiceMode  OBJECT-TYPE
    SYNTAX      InfnServiceMode
    MAX-ACCESS  read-only
    STATUS      current
    DESCRIPTION "The Service Mode (SM) of the ODU client CTP (i.e., the mode/type of service in which
        this ODU client CTP is being used,)."
    DEFVAL      {none}
    ::= { oduiClientCtpEntry  1 }

oduiClientCtpServiceModeQualifier  OBJECT-TYPE
    SYNTAX      InfnSMQ
    MAX-ACCESS  read-only
    STATUS      current
    DESCRIPTION "The Service Mode Qualifier (SMQ) of the ODU client CTP
    (i.e., the mode/type of service in which this ODU client CTP is being used,)."
    DEFVAL      {none}
    ::= { oduiClientCtpEntry  2 }

oduiClientCtpFacMonitoringMode OBJECT-TYPE
    SYNTAX  InfnMonitoringMode
    MAX-ACCESS  read-write
    STATUS      current
    DESCRIPTION "Allowed Section Monitoring / Path  Monitoring / TCM Attribute Value(s)
        (For side corresponding to MonitoringMode) (Fac-Side/Term-Side)."
    ::= { oduiClientCtpEntry 3 }


oduiClientCtpFacTxTTI OBJECT-TYPE
    SYNTAX      DisplayString  (SIZE(1..64))
    MAX-ACCESS  read-write
    STATUS      current
    DESCRIPTION  "The TTI message that needs to be transmitted in the Facility direction (e.g., from  Line to Trib direction).
    This message is inserted based on appropriate setting of FacMonitoringMode"
    ::= { oduiClientCtpEntry  4 }

oduiClientCtpFacExpectedSAPI OBJECT-TYPE
    SYNTAX      DisplayString  (SIZE(1..16))
    MAX-ACCESS  read-write
    STATUS      current
    DESCRIPTION "The Source Access Point Identifier that is expected from the Facility side (e.g., Trib to Line direction). "
    ::= { oduiClientCtpEntry  5 }

oduiClientCtpFacExpectedDAPI OBJECT-TYPE
    SYNTAX      DisplayString (SIZE(1..16))
    MAX-ACCESS  read-write
    STATUS      current
    DESCRIPTION "The Destination Access Point Identifier that is expected from the Facility side(e.g., Trib to Line direction)."
    ::= { oduiClientCtpEntry  6 }


oduiClientCtpTermTxTTI OBJECT-TYPE
    SYNTAX      DisplayString (SIZE(1..64))
    MAX-ACCESS  read-write
    STATUS      current
    DESCRIPTION "The TTI message that needs to be transmitted in the Terminal direction (e.g., from Trib to Line direction). This message
    is inserted based on appropriate setting of TermMonitoringMode"
    ::= { oduiClientCtpEntry  7 }

oduiClientCtpTermExpectedSAPI OBJECT-TYPE
    SYNTAX      DisplayString (SIZE(1..16))
    MAX-ACCESS  read-write
    STATUS      current
    DESCRIPTION "The Source Access Point Identifier that is expected from the Terminal side (e.g., in the Line to Trib direction)."
    ::= { oduiClientCtpEntry  8 }

oduiClientCtpTermExpectedDAPI OBJECT-TYPE
    SYNTAX      DisplayString (SIZE(1..16))
    MAX-ACCESS  read-write
    STATUS      current
    DESCRIPTION "The Destination Access Point Identifier that is expected from the Terminal side (e.g., in the Line to Trib direction)."
    ::= { oduiClientCtpEntry  9 }

oduiClientCtpFacReceivedTTI  OBJECT-TYPE
    SYNTAX      DisplayString (SIZE(1..64))
    MAX-ACCESS  read-only
    STATUS      current
    DESCRIPTION "The TTI message received from the Facility side (e.g., in the Trib to Term direction) of an OTU Trib Interface."
    ::= { oduiClientCtpEntry  10 }

oduiClientCtpTermReceivedTTI  OBJECT-TYPE
    SYNTAX      DisplayString (SIZE(1..64))
    MAX-ACCESS  read-only
    STATUS      current
    DESCRIPTION    "The TTI message received from the Terminal side (e.g., in the Line to Trib direction) of an ODU Trib Interface."
    ::= { oduiClientCtpEntry  11 }


oduiClientCtpRxDs15MinutesTce  OBJECT-TYPE
    SYNTAX      Integer32
    MAX-ACCESS  read-write
    STATUS      current
    DESCRIPTION "Number of Defect Seconds in received direction during 15 minutes interval."
    DEFVAL      { 120 }
    ::= { oduiClientCtpEntry  12 }

oduiClientCtpRxDsDayTce OBJECT-TYPE
    SYNTAX      Integer32
    MAX-ACCESS  read-write
    STATUS      current
    DESCRIPTION "Number of Defect Seconds in received direction during 24 hours interval."
    DEFVAL      { 1200 }
    ::= { oduiClientCtpEntry  13 }

oduiClientCtpRxDsDayTceReporting OBJECT-TYPE
    SYNTAX      TruthValue
    MAX-ACCESS  read-write
    STATUS      current
    DESCRIPTION " Flag that enables/disables the reporting of RxDsDayTce threshold crossing."
    DEFVAL      { false }
    ::= { oduiClientCtpEntry  14 }

oduiClientCtpRxDs15MinutesTceReporting OBJECT-TYPE
    SYNTAX      TruthValue
    MAX-ACCESS  read-write
    STATUS      current
    DESCRIPTION " Flag that enables/disables the reporting of RxDs15MinutesTce threshold crossing."
    DEFVAL      { false }
    ::= { oduiClientCtpEntry  15 }

oduiClientCtpFacTimDetMode  OBJECT-TYPE
    SYNTAX  INTEGER {
    off(1),
    sapi(2),
    dapi(3),
    sapidapi(4)
    }
    MAX-ACCESS  read-write
    STATUS      current
    DESCRIPTION "This attribute is used to configure if the TIM-S alarm shall be reported on mismatch of Expected and Received TTI message. The following are the values and their meaning:
        OFF: TIM-S is not reported.
        DAPI: TIM-S is reported only if the DAPI message mismatch occurs.
        SAPI: TIM-S is reported only if the SAPI message mismatch occurs.
        DAPISAPI: Either the DAPI or    the SAPI messages are in a mis- match state."
    DEFVAL      { off }
    ::= { oduiClientCtpEntry 16 }

oduiClientCtpTermTimDetMode  OBJECT-TYPE
    SYNTAX  INTEGER {
    off(1),
    sapi(2),
    dapi(3),
    sapidapi(4)
    }
    MAX-ACCESS  read-write
    STATUS      current
    DESCRIPTION "This attribute is used to configure if the TIM-S alarm shall be reported on mismatch of Expected and Received TTI
        message (on Terminal side). The following are the values and their meaning:
        OFF: TIM-S is not reported.
        DAPI: TIM-S is reported only if the DAPI message mismatch occurs.
        SAPI: TIM-S is reported only if the SAPI message mismatch occurs.
        DAPI_SAPI: Either the DAPI or the SAPI messages are in a mismatch state. "
    DEFVAL      { off }
    ::= { oduiClientCtpEntry 17 }

oduiClientCtpTcmList OBJECT-TYPE
    SYNTAX  InfnTcmList
    MAX-ACCESS  read-only
    STATUS      current
    DESCRIPTION "List of active tandem connection monitoring points (list of (contained) ODUkT
        CTP objects). The default of NONE(BITS 0) implies that none of the TCM fields are in use
        no contained ODUkT CTP objects). Note that a maximum of 3 TCM IDs can be active at any given time,
        each with one or both sides (facility and/or terminal) active (e.g., there can be up to 6 ODUkT
        CTP object instances, but only for 3 TCM IDs).
        Each entry in the TCMList is active and will have a corresponding ODUkT client CTP created.
        For OTUk-based adaptation, TCMs can only be enabled on the Facility-side."
    ::= { oduiClientCtpEntry  18 }

oduiClientCtpConfiguredServiceType  OBJECT-TYPE
    SYNTAX  InfnServiceType
    MAX-ACCESS  read-only
    STATUS      current
    DESCRIPTION "The ODU Service type that is configured on this generic OduiClientCtp managed object. "
      ::= { oduiClientCtpEntry 19 }

oduiClientCtpFacPmHistStatsEnable OBJECT-TYPE
    SYNTAX  InfnEnableDisable
    MAX-ACCESS  read-write
    STATUS      current
    DESCRIPTION " Flag to enable or disable the collection of PMs on the Facility side of ODU Clients"
    DEFVAL      { enabled }
    ::= { oduiClientCtpEntry  20 }

oduiClientCtpTermPmHistStatsEnable OBJECT-TYPE
    SYNTAX  InfnEnableDisable
    MAX-ACCESS  read-write
    STATUS      current
    DESCRIPTION "Flag to enable or disable the collection of PMs on the Terminal side of ODU Clients."
    DEFVAL      { enabled }
    ::= { oduiClientCtpEntry  21 }

oduiClientCtpAlarmReportControl OBJECT-TYPE
    SYNTAX InfnArc
    MAX-ACCESS  read-write
    STATUS      current
    DESCRIPTION " The Alarm Reporting Control Flag for the ODU Clients."
    DEFVAL      { allowed }
    ::= { oduiClientCtpEntry  22 }

oduiClientCtpSupportingCircuitIdList  OBJECT-TYPE
    SYNTAX      DisplayString
    MAX-ACCESS  read-only
    STATUS      current
    DESCRIPTION "The Supporting Circuit ID List that is this client is using. "
    ::= { oduiClientCtpEntry   23 }


oduiClientCtpFacDSThreshold OBJECT-TYPE
    SYNTAX      Integer32 (1..100)
    MAX-ACCESS  read-write
    STATUS      current
    DESCRIPTION "This attribute indicates the Facility-side threshold level for declaring a performance monitoring (PM)
        Second to be bad. A PM Second is declared bad if the percentage of detected errored blocks in that second is
        greater than or equal to the specified threshold level. This attribute maps to the DEGThr MIB of RFC-3591"
    DEFVAL      { 30 }
    ::= { oduiClientCtpEntry  24 }


oduiClientCtpTermDSThreshold OBJECT-TYPE
    SYNTAX      Integer32 (1..100)
    MAX-ACCESS  read-write
    STATUS      current
    DESCRIPTION "This attribute indicates the Terminal side (e.g., Line side) threshold level for declaring a
    performance monitoring (PM) Second to be bad. A PM Second is  declared bad if the percentage of detected  errored blocks in that second is greater than or equal to
    the specified threshold level. This attribute maps to the DEGThr MIB of RFC-3591"
    DEFVAL      { 30 }
    ::= { oduiClientCtpEntry  25 }

oduiClientCtpTermMonitoringMode OBJECT-TYPE
    SYNTAX  InfnMonitoringMode
    MAX-ACCESS  read-write
    STATUS      current
    DESCRIPTION "Allowed Section Monitoring / Path  Monitoring / TCM Attribute Value(s)
        (For side corresponding to MonitoringMode) (Fac-Side/Term-Side)."
    ::= { oduiClientCtpEntry 26 }

oduiClientCtpTSCount OBJECT-TYPE
    SYNTAX  Integer32
    MAX-ACCESS  read-only
    STATUS      current
    DESCRIPTION ""
    ::= { oduiClientCtpEntry 28 }

oduiClientCtprate 	 OBJECT-TYPE
    SYNTAX  DisplayString
    MAX-ACCESS  read-only
    STATUS      current
    DESCRIPTION "."
    ::= { oduiClientCtpEntry 29 }

oduiClientCtpTributaryPortNumber OBJECT-TYPE
    SYNTAX  Integer32
    MAX-ACCESS  read-only
    STATUS      current
    DESCRIPTION ""
    ::= { oduiClientCtpEntry 30 }

oduiClientCtpExpectedTPNs  OBJECT-TYPE
    SYNTAX  Integer32
    MAX-ACCESS  read-only
    STATUS      current
    DESCRIPTION ""
    ::= { oduiClientCtpEntry 31 }

oduiClientCtpDetectedTPNs   OBJECT-TYPE
    SYNTAX  Integer32
    MAX-ACCESS  read-only
    STATUS      current
    DESCRIPTION ""
    ::= { oduiClientCtpEntry 32 }


oduiClientCtpsupportingOPUTributarySlots  OBJECT-TYPE
    SYNTAX  DisplayString
    MAX-ACCESS  read-write
    STATUS      current
    DESCRIPTION ""
    ::= { oduiClientCtpEntry 33 }

oduiClientCtpavailableOPUTributarySlots  OBJECT-TYPE
    SYNTAX  DisplayString
    MAX-ACCESS  read-only
    STATUS      current
    DESCRIPTION ""
    ::= { oduiClientCtpEntry 34 }

oduiClientCtpdatarate 	 OBJECT-TYPE
    SYNTAX  InfnRate
    MAX-ACCESS  read-only
    STATUS      current
    DESCRIPTION ""
    ::= { oduiClientCtpEntry 35 }

oduiClientCtpCrossConnectType  OBJECT-TYPE
    SYNTAX  InfnXconType
    MAX-ACCESS  read-only
    STATUS      current
    DESCRIPTION ""
    ::= { oduiClientCtpEntry 36 }


oduiClientCtpSupportingTP    OBJECT-TYPE
    SYNTAX  DisplayString
    MAX-ACCESS  read-write
    STATUS      current
    DESCRIPTION ""
    ::= { oduiClientCtpEntry 37 }

oduiClientCtpTsg   OBJECT-TYPE
    SYNTAX  InfnTsgType
    MAX-ACCESS  read-write
    STATUS      current
    DESCRIPTION ""
    ::= { oduiClientCtpEntry 38 }

oduiClientCtpExpectedPayload   OBJECT-TYPE
    SYNTAX  InfnServiceType
    MAX-ACCESS  read-only
    STATUS      current
    DESCRIPTION ""
    ::= { oduiClientCtpEntry 39 }

oduiClientCtpLoopBack OBJECT-TYPE
    SYNTAX  INTEGER {
        none(1),
        terminal(2),
        facility(3)
    }
    MAX-ACCESS  read-write
    STATUS      current
    DESCRIPTION "Flag to enable the loopback."
    DEFVAL      { none }
    ::= {oduiClientCtpEntry   40 }

oduiClientCtpFacSDThreshold  OBJECT-TYPE
    SYNTAX      Integer32 (2..10)
    MAX-ACCESS  read-write
    STATUS      current
    DESCRIPTION "This attribute indicates the Facility-side (e.g., Trib-side/Client-side) threshold level for declaring a
        Degraded Signal defect. A Degraded Signal defect shall be declared if SDThreshold consecutive bad PM Seconds are detected.
        This attribute maps to the DEGM MIB of RFC-3591"
    DEFVAL      { 7 }
    ::= { oduiClientCtpEntry  41 }

oduiClientCtpRxDsF15MinutesTce  OBJECT-TYPE
    SYNTAX      Integer32
    MAX-ACCESS  read-write
    STATUS      current
    DESCRIPTION ""
    ::= { oduiClientCtpEntry 42 }

oduiClientCtpRxDsF15MinutesTceReporting OBJECT-TYPE
    SYNTAX      TruthValue
    MAX-ACCESS  read-write
    STATUS      current
    DESCRIPTION ""
    ::= { oduiClientCtpEntry 43 }

oduiClientCtpRxDsFDayTce        OBJECT-TYPE
    SYNTAX      Integer32
    MAX-ACCESS  read-write
    STATUS      current
    DESCRIPTION ""
    ::= { oduiClientCtpEntry 44 }

oduiClientCtpRxDsFDayTceReporting   OBJECT-TYPE
    SYNTAX      TruthValue
    MAX-ACCESS  read-write
    STATUS      current
    DESCRIPTION ""
    ::= { oduiClientCtpEntry 45 }

oduiClientCtpRxBei15MinutesTce      OBJECT-TYPE
    SYNTAX      Integer32
    MAX-ACCESS  read-write
    STATUS      current
    DESCRIPTION ""
    ::= { oduiClientCtpEntry 46 }

oduiClientCtpRxBei15MinutesTceReporting OBJECT-TYPE
    SYNTAX      TruthValue
    MAX-ACCESS  read-write
    STATUS      current
    DESCRIPTION ""
    ::= { oduiClientCtpEntry 47 }

oduiClientCtpRxBeiDayTce    OBJECT-TYPE
    SYNTAX      Integer32
    MAX-ACCESS  read-write
    STATUS      current
    DESCRIPTION ""
    ::= { oduiClientCtpEntry 48 }

oduiClientCtpRxBeiDayTceReporting   OBJECT-TYPE
    SYNTAX      TruthValue
    MAX-ACCESS  read-write
    STATUS      current
    DESCRIPTION ""
    ::= { oduiClientCtpEntry 49 }

oduiClientCtpBitRateK OBJECT-TYPE
    SYNTAX      InfnOtuBitRateK
    MAX-ACCESS  read-only
    STATUS      current
    DESCRIPTION ""
    ::= { oduiClientCtpEntry 50 }


-- Conformance Statements
oduiClientCtpConformance    OBJECT IDENTIFIER ::= { oduiClientCtpMIB 3 }
oduiClientCtpCompliances    OBJECT IDENTIFIER ::= { oduiClientCtpConformance 1 }
oduiClientCtpGroups         OBJECT IDENTIFIER ::= { oduiClientCtpConformance 2 }

oduiClientCtpCompliance MODULE-COMPLIANCE
    STATUS current
    DESCRIPTION
    "Describes the requirements for conformance to the ODUICLIENTCTP-MIB"

    MODULE
        MANDATORY-GROUPS { oduiClientCtpGroup }
    ::= { oduiClientCtpCompliances 1 }

oduiClientCtpGroup OBJECT-GROUP
    OBJECTS {
    oduiClientCtpServiceMode,
    oduiClientCtpFacMonitoringMode,
    oduiClientCtpFacTxTTI,
    oduiClientCtpFacExpectedSAPI,
    oduiClientCtpFacExpectedDAPI,
    oduiClientCtpTermTxTTI,
    oduiClientCtpTermExpectedSAPI,
    oduiClientCtpTermExpectedDAPI,
    oduiClientCtpFacReceivedTTI,
    oduiClientCtpTermReceivedTTI,
    oduiClientCtpRxDs15MinutesTce,
    oduiClientCtpRxDsDayTce,
    oduiClientCtpRxDsDayTceReporting,
    oduiClientCtpRxDs15MinutesTceReporting,
    oduiClientCtpFacTimDetMode,
    oduiClientCtpTermTimDetMode,
    oduiClientCtpTcmList,
    oduiClientCtpConfiguredServiceType,
    oduiClientCtpFacPmHistStatsEnable,
    oduiClientCtpTermPmHistStatsEnable,
    oduiClientCtpAlarmReportControl,
    oduiClientCtpSupportingCircuitIdList,
    oduiClientCtpFacDSThreshold,
    oduiClientCtpTermDSThreshold,
    oduiClientCtpTermMonitoringMode,
    oduiClientCtpTSCount,
    oduiClientCtprate,
    oduiClientCtpTributaryPortNumber,
    oduiClientCtpExpectedTPNs,
    oduiClientCtpDetectedTPNs,
    oduiClientCtpsupportingOPUTributarySlots,
    oduiClientCtpavailableOPUTributarySlots,
    oduiClientCtpdatarate,
    oduiClientCtpCrossConnectType,
    oduiClientCtpSupportingTP,
    oduiClientCtpTsg,
    oduiClientCtpExpectedPayload,
    oduiClientCtpLoopBack,
    oduiClientCtpFacSDThreshold,
    oduiClientCtpRxDsF15MinutesTce,
    oduiClientCtpRxDsF15MinutesTceReporting,
    oduiClientCtpRxDsFDayTce,
    oduiClientCtpRxDsFDayTceReporting,
    oduiClientCtpRxBei15MinutesTce,
    oduiClientCtpRxBei15MinutesTceReporting,
    oduiClientCtpRxBeiDayTce,
    oduiClientCtpRxBeiDayTceReporting,
	oduiClientCtpBitRateK
    }
    STATUS current
    DESCRIPTION
        " A collection of objects for managing the oduiClientCtp"
    ::= { oduiClientCtpGroups 1 }
END
