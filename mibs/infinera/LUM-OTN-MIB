LUM-OTN-MIB DEFINITIONS ::= BEGIN

IMPORTS
    MODULE-IDENTITY, OBJECT-TYPE, Unsigned32
        FROM SNMPv2-SMI
    OBJECT-GROUP, MODULE-COMPLIANCE
        FROM SNMPv2-CONF
    TestAndIncr, DisplayString, DateAndTime
        FROM SNMPv2-TC
    lumModules, lumOtnMIB
        FROM LUM-REG
    FaultStatus, MgmtNameString, SubrackNumber, SlotNumber, PortNumber,
    BoardOrInterfaceAdminStatus, BoardOrInterfaceOperStatus, CommandString,
    ObjectProperty, OtnMonitorType, OtnMonitorConfig, OtnTIMDetMode
        FROM LUM-TC;

lumOtnMIBModule MODULE-IDENTITY
    LAST-UPDATED
        "201706150000Z" -- June 15th 2017
    ORGANIZATION
        "Infinera Corporation"
    CONTACT-INFO
        "techsupport@infinera.com"
    DESCRIPTION
        "The OTN interface and protection group MIB.

        - General

        - SMTCMPM interfaces
"
    REVISION
        "201706150000Z" -- June 15th 2017
    DESCRIPTION
        "Changes made for release r29.0:
         - Changed ORGANIZATION and CONTACT-INFO"
    REVISION
        "201601110000Z" -- Jan 11th 2016
    DESCRIPTION
        "Added default value notPresent for operStatus."
    REVISION
        "201203300000Z" -- March 30th 2012
    DESCRIPTION
        "Added iae and biae alarms."
    REVISION
        "200906150000Z" -- June 15th 2009
    DESCRIPTION
        "The initial revision of this module."
    ::= { lumModules 34 }


-- ----------------------------------------------------
-- Conformance area, containing groups and complicance
-- specifications.
-- ----------------------------------------------------

lumOtnConfs OBJECT IDENTIFIER ::= { lumOtnMIB 1 }
lumOtnGroups OBJECT IDENTIFIER ::= { lumOtnConfs 1 }
lumOtnCompl OBJECT IDENTIFIER ::= { lumOtnConfs 2 }
lumOtnMinimalGroups OBJECT IDENTIFIER ::= { lumOtnConfs 3 }
lumOtnMinimalCompl OBJECT IDENTIFIER ::= { lumOtnConfs 4 }


-- ----------------------------------------------------
-- Root for objects in the otn MIB
-- ----------------------------------------------------

lumOtnMIBObjects OBJECT IDENTIFIER ::= { lumOtnMIB 2 }


-- ----------------------------------------------------
-- This MIB contains the following groups:
-- ----------------------------------------------------

otnGeneral OBJECT IDENTIFIER ::= { lumOtnMIBObjects 1 }
otnSmTcmPmList OBJECT IDENTIFIER ::= { lumOtnMIBObjects 2}

-- ----------------------------------------------------
-- Textual Conventions
-- ----------------------------------------------------

-- ----------------------------------------------------
-- General group
-- ----------------------------------------------------

otnGeneralTestAndIncr OBJECT-TYPE
    SYNTAX      TestAndIncr
    MAX-ACCESS  read-write
    STATUS      current
    DESCRIPTION
        "Protection against simultaneous access from
        multiple managers. See SNMPv2-TC.

"
    ::= { otnGeneral 1 }

otnGeneralMibSpecVersion OBJECT-TYPE
    SYNTAX      DisplayString
    MAX-ACCESS  read-write
    STATUS      current
    DESCRIPTION
        "The MIB specification version.

        tbd: persistent?
"
    DEFVAL { "" }
    ::= { otnGeneral 2 }

otnGeneralMibImplVersion OBJECT-TYPE
    SYNTAX      DisplayString
    MAX-ACCESS  read-write
    STATUS      current
    DESCRIPTION
        "The MIB implementation version.

        tbd: persistent?
"
    DEFVAL { "" }
    ::= { otnGeneral 3 }

otnGeneralLastChangeTime OBJECT-TYPE
    SYNTAX      DateAndTime
    MAX-ACCESS  read-only
    STATUS      current
    DESCRIPTION
        "The time when the configuration of the MIB was
        last changed.

"
    ::= { otnGeneral 4 }

otnGeneralStateLastChangeTime OBJECT-TYPE
    SYNTAX      DateAndTime
    MAX-ACCESS  read-only
    STATUS      current
    DESCRIPTION
        "The time when the state of the MIB was last
        changed.

"
    ::= { otnGeneral 5 }

otnGeneralSmTcmPmTableSize OBJECT-TYPE
    SYNTAX      Unsigned32
    MAX-ACCESS  read-only
    STATUS      current
    DESCRIPTION
        "Size of table

"
    ::= { otnGeneral 6 }

-- ----------------------------------------------------
-- Otn definitions
-- ----------------------------------------------------

otnSmTcmPmTable  OBJECT-TYPE
    SYNTAX      SEQUENCE OF OtnSmTcmPmEntry
    MAX-ACCESS  not-accessible
    STATUS      current
    DESCRIPTION
        "The OTN table."
    ::= { otnSmTcmPmList 1 }

otnSmTcmPmEntry OBJECT-TYPE
    SYNTAX      OtnSmTcmPmEntry
    MAX-ACCESS  not-accessible
    STATUS      current
    DESCRIPTION
        "An entry in the OTN table.
"
    INDEX { otnSmTcmPmIndex }
    ::= { otnSmTcmPmTable 1 }

OtnSmTcmPmEntry ::=
    SEQUENCE {
    otnSmTcmPmIndex			  Unsigned32,
    otnSmTcmPmName  		          MgmtNameString,
    otnSmTcmPmType                        OtnMonitorType,
    otnSmTcmPmMonitorConfig               OtnMonitorConfig,
    otnSmTcmPmTerminatedTcm               INTEGER,
    otnSmTcmPmDescr			  DisplayString,
    otnSmTcmPmSubrack 		          SubrackNumber,
    otnSmTcmPmSlot		          SlotNumber,
    otnSmTcmPmTxPort	  	          PortNumber,
    otnSmTcmPmAdminStatus		  INTEGER,
    otnSmTcmPmOperStatus		  INTEGER,
    otnSmTcmPmSapiTraceTransmitted        DisplayString,
    otnSmTcmPmSapiTraceReceivedByte0      Unsigned32,
    otnSmTcmPmSapiTraceReceived           DisplayString,
    otnSmTcmPmSapiTraceExpected           DisplayString,
    otnSmTcmPmDapiTraceTransmitted        DisplayString,
    otnSmTcmPmDapiTraceReceivedByte0      Unsigned32,
    otnSmTcmPmDapiTraceReceived           DisplayString,
    otnSmTcmPmDapiTraceExpected           DisplayString,
    otnSmTcmPmOpSpecificTraceTransmitted  DisplayString,
    otnSmTcmPmOpSpecificTraceReceived     DisplayString,
    otnSmTcmPmTraceIdMMDetectionMode      OtnTIMDetMode,
    otnSmTcmPmTraceAlarmMode              INTEGER,
    otnSmTcmPmObjectProperty              ObjectProperty,
    otnSmTcmPmTraceMismatch               FaultStatus,
    otnSmTcmPmBackwardDefectIndication    FaultStatus,
    otnSmTcmPmAlarmIndicationSignal       FaultStatus,
    otnSmTcmPmOpenConnectionIndication    FaultStatus,
    otnSmTcmPmClientMaintenanceIndication FaultStatus,
    otnSmTcmPmLockedDefectIndication      FaultStatus,
    otnSmTcmPmSetTerminatedTcmCommand     CommandString,
    otnSmTcmPmNoRemoteTerminatedTcm       FaultStatus,
    otnSmTcmPmIncomingAlignmentError      FaultStatus,
    otnSmTcmPmBackwardIncomingAlignmentError FaultStatus}

otnSmTcmPmIndex OBJECT-TYPE
    SYNTAX      Unsigned32 (1..2147483647)
    MAX-ACCESS  read-only
    STATUS      current
    DESCRIPTION
        "An arbitrary index assigned to each entry.

"
    ::= { otnSmTcmPmEntry 1 }

otnSmTcmPmName OBJECT-TYPE
    SYNTAX      MgmtNameString
    MAX-ACCESS  read-only
    STATUS      current
    DESCRIPTION
	"The name of the object, for example
	'sm:1:2:1-2', where the numbers indicate the
	subrack, slot and port numbers.

"
    DEFVAL { "" }
    ::= { otnSmTcmPmEntry 2 }

otnSmTcmPmType OBJECT-TYPE
    SYNTAX      OtnMonitorType
    MAX-ACCESS  read-only
    STATUS      current
    DESCRIPTION
	"The type of object, SM, TCM or PM.

"
    ::= { otnSmTcmPmEntry 3 }

otnSmTcmPmMonitorConfig OBJECT-TYPE
    SYNTAX      OtnMonitorConfig
    MAX-ACCESS  read-only
    STATUS      current
    DESCRIPTION
	"MontorConfig tells if monitor is terminated or not.

"
    DEFVAL { transparent }
    ::= { otnSmTcmPmEntry 4 }

otnSmTcmPmTerminatedTcm OBJECT-TYPE
    SYNTAX          INTEGER {
                    none (0),
                    tcm1 (1),
                    tcm2 (2),
                    tcm3 (3),
                    tcm4 (4),
                    tcm5 (5),
                    tcm6 (6) }
    MAX-ACCESS      read-create
    STATUS          current
    DESCRIPTION
        "Tcm that will be terminated in this node. This is none
         or tcm1, tcm2, tcm3, tcm4, tcm5, tcm6. If one tcm is selected
         the alarms on this tcm will also be used as protection criteria.

"
    DEFVAL { none }
    ::= { otnSmTcmPmEntry 5 }

otnSmTcmPmDescr OBJECT-TYPE
    SYNTAX      DisplayString
    MAX-ACCESS  read-write
    STATUS      current
    DESCRIPTION
        "User configurable label.

"
    DEFVAL { "" }
    ::= { otnSmTcmPmEntry 6 }

otnSmTcmPmSubrack OBJECT-TYPE
    SYNTAX      SubrackNumber
    MAX-ACCESS  read-only
    STATUS      current
    DESCRIPTION
        "The subrack number for this protected
        interface.

"
    DEFVAL { 0 }
    ::= { otnSmTcmPmEntry 7 }

otnSmTcmPmSlot OBJECT-TYPE
    SYNTAX      SlotNumber
    MAX-ACCESS  read-only
    STATUS      current
    DESCRIPTION
        "The slot number for this protected
        interface.

"
    DEFVAL { 0 }
    ::= { otnSmTcmPmEntry 8 }

otnSmTcmPmTxPort OBJECT-TYPE
    SYNTAX      PortNumber
    MAX-ACCESS  read-only
    STATUS      current
    DESCRIPTION
        "The number of the port where the interface is
        located.

"
    DEFVAL { 0 }
    ::= { otnSmTcmPmEntry 9 }

otnSmTcmPmAdminStatus OBJECT-TYPE
    SYNTAX      BoardOrInterfaceAdminStatus
    MAX-ACCESS  read-write
    STATUS      current
    DESCRIPTION
        "The administrative state for the interface.

        down - The interface should be inactive.

        service - The object is activated but alarms
        are suppressed. Intended for use during service
        or re-configuration. When service is concluded
        adminStatus should be set to 'up' again. Note that
        there is no difference between 'up' and 'service',
        if no alarms can be raised from this object.

        up - The interface should be activated when
        it becomes available. Alarms are not suppressed.

"
    DEFVAL { up }
    ::= { otnSmTcmPmEntry 10 }

otnSmTcmPmOperStatus OBJECT-TYPE
    SYNTAX      BoardOrInterfaceOperStatus
    MAX-ACCESS  read-only
    STATUS      current
    DESCRIPTION
        "The operational state for the interface.

        notPresent - The interface is not available.

        down - The interface is de-activated or there are
        faults preventing it from going to the 'up'-state.

        up - The interface is active.

"
    DEFVAL { notPresent }
    ::= { otnSmTcmPmEntry 11 }

otnSmTcmPmSapiTraceTransmitted   OBJECT-TYPE
    SYNTAX      DisplayString (SIZE(0..15))
    MAX-ACCESS  read-write
    STATUS      current
    DESCRIPTION
        "The Source Destination Access Point Identifier to be
         transmitted from this interface.

         Note, it is only possible to enter 15 characters since first
         character is added automatically according to standard.

"
    DEFVAL { "" }
    ::= { otnSmTcmPmEntry 12 }

otnSmTcmPmSapiTraceReceivedByte0 OBJECT-TYPE
    SYNTAX      Unsigned32 (1..2147483647)
    MAX-ACCESS  read-only
    STATUS      current
    DESCRIPTION
        "The received Source Access Point Identifier for this interface.

"
    ::= { otnSmTcmPmEntry 13 }

otnSmTcmPmSapiTraceReceived OBJECT-TYPE
    SYNTAX      DisplayString (SIZE(0..15))
    MAX-ACCESS  read-only
    STATUS      current
    DESCRIPTION
        "The received Source Access Point Identifier for this interface.

"
    ::= { otnSmTcmPmEntry 14 }

otnSmTcmPmSapiTraceExpected OBJECT-TYPE
    SYNTAX      DisplayString (SIZE(0..15))
    MAX-ACCESS  read-write
    STATUS      current
    DESCRIPTION
        "SAPI used for matching against the received SAPI.

         Note, it is only possible to enter 15 characters since first
         character is added automatically according to standard.

"
    DEFVAL { "" }
    ::= { otnSmTcmPmEntry 15 }

otnSmTcmPmDapiTraceTransmitted   OBJECT-TYPE
    SYNTAX      DisplayString (SIZE(0..15))
    MAX-ACCESS  read-write
    STATUS      current
    DESCRIPTION
        "The Destination Access Point Identifier to be transmitted from this
        interface.

        Note, it is only possible to enter 15 characters since first
        character is added automatically according to standard.

"
    DEFVAL { "" }
    ::= { otnSmTcmPmEntry 16 }

otnSmTcmPmDapiTraceReceivedByte0 OBJECT-TYPE
    SYNTAX      Unsigned32 (1..2147483647)
    MAX-ACCESS  read-only
    STATUS      current
    DESCRIPTION
        "The received Destination Access Point Identifier for this interface.

"
    ::= { otnSmTcmPmEntry 17 }

otnSmTcmPmDapiTraceReceived OBJECT-TYPE
    SYNTAX      DisplayString (SIZE(0..15))
    MAX-ACCESS  read-only
    STATUS      current
    DESCRIPTION
        "The received Destination Access Point Identifier for this interface.

"
    ::= { otnSmTcmPmEntry 18 }

otnSmTcmPmDapiTraceExpected OBJECT-TYPE
    SYNTAX      DisplayString (SIZE(0..15))
    MAX-ACCESS  read-write
    STATUS      current
    DESCRIPTION
        "DAPI used for matching against the received DAPI.

         Note, it is only possible to enter 15 characters since first
         character is added automatically according to standard.

"
    DEFVAL { "" }
    ::= { otnSmTcmPmEntry 19 }

otnSmTcmPmOpSpecificTraceTransmitted   OBJECT-TYPE
    SYNTAX      DisplayString (SIZE(0..31))
    MAX-ACCESS  read-write
    STATUS      current
    DESCRIPTION
        "The operator specific trace identifier to be transmitted
         from this interface.

		Set to empty string for default value.

		<IP address>:<subrack>:<slot>:<port>

		Note that only the last part of the address
		is used.

"
    DEFVAL { "" }
    ::= { otnSmTcmPmEntry 20 }

otnSmTcmPmOpSpecificTraceReceived OBJECT-TYPE
    SYNTAX      DisplayString (SIZE(0..31))
    MAX-ACCESS  read-only
    STATUS      current
    DESCRIPTION
        "The received operator specific trace identifier for this
         interface.

"
    ::= { otnSmTcmPmEntry 21 }

otnSmTcmPmTraceIdMMDetectionMode OBJECT-TYPE
    SYNTAX          OtnTIMDetMode
    MAX-ACCESS      read-write
    STATUS          current
    DESCRIPTION
        "The method to detect a TTI identifier mismatch value.

"
    DEFVAL { sapi }
    ::= { otnSmTcmPmEntry 22 }

otnSmTcmPmTraceAlarmMode OBJECT-TYPE
    SYNTAX      INTEGER {
                    disabled (1),
                    enabled (2) }
    MAX-ACCESS  read-write
    STATUS      current
    DESCRIPTION
        "Controls if the trace identifier mismatch alarm
        should be raised. If trace alarm mode is enabled, BDI is sent
        in backward direction if received trace and expected trace
        differs.

        disabled - The alarm is disabled.

        enabled - The alarm is raised if expected trace
        identifier differs from the received trace
        identifier.

"
    DEFVAL { disabled }
    ::= { otnSmTcmPmEntry 23 }

otnSmTcmPmObjectProperty OBJECT-TYPE
    SYNTAX      ObjectProperty
    MAX-ACCESS  read-only
    STATUS      current
    DESCRIPTION
        "Property mask.

"
    ::= { otnSmTcmPmEntry 24 }

otnSmTcmPmTraceMismatch OBJECT-TYPE
    SYNTAX      FaultStatus
    MAX-ACCESS  read-only
    STATUS      current
    DESCRIPTION
        "Indicates if the expected SM/PM/TCMtrace identifier (SAPI+DAPI)
        differs from the received trace identifier.

        A: The received trace identifier differs from
        the expected trace identifier.

        D: The identifiers match.

"
    ::= { otnSmTcmPmEntry 25 }

otnSmTcmPmBackwardDefectIndication OBJECT-TYPE
    SYNTAX      FaultStatus
    MAX-ACCESS  read-only
    STATUS      current
    DESCRIPTION
        "Indicates if backward defect indication (BDI) alarm
         exists or not.

        A: BDI is active.

        D: BDI is inactive.

"
    ::= { otnSmTcmPmEntry 26 }

otnSmTcmPmAlarmIndicationSignal OBJECT-TYPE
    SYNTAX      FaultStatus
    MAX-ACCESS  read-only
    STATUS      current
    DESCRIPTION
        "Alarm indication signal.

        A: An 'all ones' PM/TCM signal is detected.

        D: PM/TCM signal recovered.

"
    ::= { otnSmTcmPmEntry 27 }

otnSmTcmPmOpenConnectionIndication OBJECT-TYPE
    SYNTAX      FaultStatus
    MAX-ACCESS  read-only
    STATUS      current
    DESCRIPTION
        "Open connection Indication.

        A: A 'open connection' PM/TCM signal is detected.

        D: PM/TCM signal recovered.

"
    ::= { otnSmTcmPmEntry 28 }

otnSmTcmPmClientMaintenanceIndication OBJECT-TYPE
    SYNTAX      FaultStatus
    MAX-ACCESS  read-only
    STATUS      deprecated
    DESCRIPTION
        "Client Maintenance Indication.

        A: A 'client maintenance' PM signal is detected.

        D: PM/TCM signal recovered.

"
    ::= { otnSmTcmPmEntry 29 }

otnSmTcmPmLockedDefectIndication OBJECT-TYPE
    SYNTAX      FaultStatus
    MAX-ACCESS  read-only
    STATUS      current
    DESCRIPTION
        "Locked Defect Indication.

        A: A 'Locked Defect' PM/TCM signal is detected.

        D: PM/TCM signal recovered.

"
    ::= { otnSmTcmPmEntry 30 }

otnSmTcmPmSetTerminatedTcmCommand OBJECT-TYPE
    SYNTAX      CommandString
    MAX-ACCESS  read-only
    STATUS      current
    DESCRIPTION
        "Command to change which TCM that is terminated.

"
    ::= { otnSmTcmPmEntry 31 }

otnSmTcmPmNoRemoteTerminatedTcm OBJECT-TYPE
    SYNTAX      FaultStatus
    MAX-ACCESS  read-only
    STATUS      current
    DESCRIPTION
        "No terminated TCM.

        A: The TCM is not terminated anywhere.

        D: The TCM is terminated somewhere.

"
    ::= { otnSmTcmPmEntry 32 }

otnSmTcmPmIncomingAlignmentError OBJECT-TYPE
    SYNTAX      FaultStatus
    MAX-ACCESS  read-only
    STATUS      current
    DESCRIPTION
        "Indicates an incoming frame alignment error.

        A: IAE is active

        D: IAE is inactive

"
    ::= { otnSmTcmPmEntry 33 }

otnSmTcmPmBackwardIncomingAlignmentError OBJECT-TYPE
    SYNTAX      FaultStatus
    MAX-ACCESS  read-only
    STATUS      current
    DESCRIPTION
        "Indicates a backward incoming alignment error.

        A: BIAE is active

        D: BIAE is inactive

"
    ::= { otnSmTcmPmEntry 34 }



-- ----------------------------------------------------
-- Object and event groups
-- ----------------------------------------------------

otnGeneralGroup OBJECT-GROUP
    OBJECTS {
        otnGeneralTestAndIncr,
        otnGeneralMibSpecVersion,
        otnGeneralMibImplVersion,
        otnGeneralLastChangeTime }
    STATUS      current
    DESCRIPTION
        "The general objects."
    ::= { lumOtnGroups 1 }

otnSmTcmPmGroup OBJECT-GROUP
    OBJECTS {
        otnSmTcmPmIndex,
        otnSmTcmPmName,
        otnSmTcmPmType,
        otnSmTcmPmMonitorConfig,
        otnSmTcmPmTerminatedTcm,
        otnSmTcmPmDescr,
        otnSmTcmPmSubrack,
        otnSmTcmPmSlot,
        otnSmTcmPmTxPort,
        otnSmTcmPmAdminStatus,
	otnSmTcmPmOperStatus,
        otnSmTcmPmSapiTraceTransmitted,
        otnSmTcmPmSapiTraceReceivedByte0,
        otnSmTcmPmSapiTraceReceived,
        otnSmTcmPmSapiTraceExpected,
        otnSmTcmPmDapiTraceTransmitted,
        otnSmTcmPmDapiTraceReceivedByte0,
        otnSmTcmPmDapiTraceReceived,
        otnSmTcmPmDapiTraceExpected,
        otnSmTcmPmOpSpecificTraceTransmitted,
        otnSmTcmPmOpSpecificTraceReceived,
        otnSmTcmPmTraceIdMMDetectionMode,
        otnSmTcmPmTraceAlarmMode,
        otnSmTcmPmObjectProperty,
        otnSmTcmPmTraceMismatch,
        otnSmTcmPmBackwardDefectIndication,
        otnSmTcmPmAlarmIndicationSignal,
        otnSmTcmPmOpenConnectionIndication,
        otnSmTcmPmClientMaintenanceIndication,
        otnSmTcmPmLockedDefectIndication }
    STATUS      deprecated
    DESCRIPTION
        "The OTN SM, TCM and PM objects. (14.0) "
    ::= { lumOtnGroups 2 }

    otnSmTcmPmGroupV2 OBJECT-GROUP
    OBJECTS {
        otnSmTcmPmIndex,
        otnSmTcmPmName,
        otnSmTcmPmType,
        otnSmTcmPmMonitorConfig,
        otnSmTcmPmTerminatedTcm,
        otnSmTcmPmDescr,
        otnSmTcmPmSubrack,
        otnSmTcmPmSlot,
        otnSmTcmPmTxPort,
	otnSmTcmPmAdminStatus,
	otnSmTcmPmOperStatus,
        otnSmTcmPmSapiTraceTransmitted,
        otnSmTcmPmSapiTraceReceivedByte0,
        otnSmTcmPmSapiTraceReceived,
        otnSmTcmPmSapiTraceExpected,
        otnSmTcmPmDapiTraceTransmitted,
        otnSmTcmPmDapiTraceReceivedByte0,
        otnSmTcmPmDapiTraceReceived,
        otnSmTcmPmDapiTraceExpected,
        otnSmTcmPmOpSpecificTraceTransmitted,
        otnSmTcmPmOpSpecificTraceReceived,
        otnSmTcmPmTraceIdMMDetectionMode,
        otnSmTcmPmTraceAlarmMode,
        otnSmTcmPmObjectProperty,
        otnSmTcmPmTraceMismatch,
        otnSmTcmPmBackwardDefectIndication,
        otnSmTcmPmAlarmIndicationSignal,
        otnSmTcmPmOpenConnectionIndication,
        otnSmTcmPmLockedDefectIndication,
        otnSmTcmPmSetTerminatedTcmCommand,
        otnSmTcmPmNoRemoteTerminatedTcm }
    STATUS      deprecated
    DESCRIPTION
        "The OTN SM, TCM and PM objects. (15.0) "
    ::= { lumOtnGroups 3 }

    otnSmTcmPmGroupV3 OBJECT-GROUP
    OBJECTS {
        otnSmTcmPmIndex,
        otnSmTcmPmName,
        otnSmTcmPmType,
        otnSmTcmPmMonitorConfig,
        otnSmTcmPmTerminatedTcm,
        otnSmTcmPmDescr,
        otnSmTcmPmSubrack,
        otnSmTcmPmSlot,
        otnSmTcmPmTxPort,
	otnSmTcmPmAdminStatus,
	otnSmTcmPmOperStatus,
        otnSmTcmPmSapiTraceTransmitted,
        otnSmTcmPmSapiTraceReceivedByte0,
        otnSmTcmPmSapiTraceReceived,
        otnSmTcmPmSapiTraceExpected,
        otnSmTcmPmDapiTraceTransmitted,
        otnSmTcmPmDapiTraceReceivedByte0,
        otnSmTcmPmDapiTraceReceived,
        otnSmTcmPmDapiTraceExpected,
        otnSmTcmPmOpSpecificTraceTransmitted,
        otnSmTcmPmOpSpecificTraceReceived,
        otnSmTcmPmTraceIdMMDetectionMode,
        otnSmTcmPmTraceAlarmMode,
        otnSmTcmPmObjectProperty,
        otnSmTcmPmTraceMismatch,
        otnSmTcmPmBackwardDefectIndication,
        otnSmTcmPmAlarmIndicationSignal,
        otnSmTcmPmOpenConnectionIndication,
        otnSmTcmPmLockedDefectIndication,
        otnSmTcmPmSetTerminatedTcmCommand,
        otnSmTcmPmNoRemoteTerminatedTcm,
        otnSmTcmPmIncomingAlignmentError,
        otnSmTcmPmBackwardIncomingAlignmentError }
    STATUS      current
    DESCRIPTION
        "The OTN SM, TCM and PM objects. (19.0) "
    ::= { lumOtnGroups 4 }

-- ----------------------------------------------------
-- Compliance
-- ----------------------------------------------------

lumOtnBasicCompl1 MODULE-COMPLIANCE
    STATUS     deprecated
    DESCRIPTION
        "Basic implementation requirements for the OTN MIB V1. (14.0)"
    MODULE
        MANDATORY-GROUPS {
	    otnGeneralGroup,
            otnSmTcmPmGroup
 }
    ::= { lumOtnCompl 1 }

lumOtnBasicCompl2 MODULE-COMPLIANCE
    STATUS     deprecated
    DESCRIPTION
        "Basic implementation requirements for the OTN MIB V1. (14.0)"
    MODULE
        MANDATORY-GROUPS {
	    otnGeneralGroup,
        otnSmTcmPmGroupV2
 }
    ::= { lumOtnCompl 2 }

lumOtnBasicCompl3 MODULE-COMPLIANCE
    STATUS     current
    DESCRIPTION
        "Basic implementation requirements for the OTN MIB V3. (19.0)"
    MODULE
        MANDATORY-GROUPS {
	    otnGeneralGroup,
            otnSmTcmPmGroupV3
 }
    ::= { lumOtnCompl 3 }

-- ----------------------------------------------------
-- Minimal object and event groups
-- ----------------------------------------------------

otnGeneralMinimalGroupV1 OBJECT-GROUP
    OBJECTS {
        otnGeneralLastChangeTime,
        otnGeneralSmTcmPmTableSize }
    STATUS      current
    DESCRIPTION
        "The minimal general otn objects.
"
    ::= { lumOtnMinimalGroups 1 }

otnSmTcmPmMinimalGroupV1 OBJECT-GROUP
    OBJECTS {
        otnSmTcmPmIndex,
        otnSmTcmPmName,
        otnSmTcmPmType,
        otnSmTcmPmMonitorConfig,
        otnSmTcmPmTerminatedTcm,
        otnSmTcmPmDescr,
        otnSmTcmPmSubrack,
        otnSmTcmPmSlot,
        otnSmTcmPmTxPort,
	otnSmTcmPmAdminStatus,
	otnSmTcmPmOperStatus,
        otnSmTcmPmTraceIdMMDetectionMode,
        otnSmTcmPmSapiTraceTransmitted,
        otnSmTcmPmDapiTraceTransmitted,
        otnSmTcmPmOpSpecificTraceTransmitted,
        otnSmTcmPmSapiTraceReceivedByte0,
        otnSmTcmPmSapiTraceReceived,
        otnSmTcmPmDapiTraceReceivedByte0,
        otnSmTcmPmDapiTraceReceived,
        otnSmTcmPmOpSpecificTraceReceived,
        otnSmTcmPmSapiTraceExpected,
        otnSmTcmPmDapiTraceExpected,
        otnSmTcmPmTraceAlarmMode,
        otnSmTcmPmObjectProperty,
        otnSmTcmPmTraceMismatch,
        otnSmTcmPmBackwardDefectIndication,
        otnSmTcmPmAlarmIndicationSignal,
        otnSmTcmPmOpenConnectionIndication,
        otnSmTcmPmClientMaintenanceIndication,
        otnSmTcmPmLockedDefectIndication }

    STATUS      deprecated
    DESCRIPTION
        "The otn interface minimal objects."
    ::= { lumOtnMinimalGroups 2 }

otnSmTcmPmMinimalGroupV2 OBJECT-GROUP
    OBJECTS {
        otnSmTcmPmIndex,
        otnSmTcmPmName,
        otnSmTcmPmType,
        otnSmTcmPmMonitorConfig,
        otnSmTcmPmTerminatedTcm,
        otnSmTcmPmDescr,
        otnSmTcmPmSubrack,
        otnSmTcmPmSlot,
        otnSmTcmPmTxPort,
	otnSmTcmPmAdminStatus,
	otnSmTcmPmOperStatus,
        otnSmTcmPmTraceIdMMDetectionMode,
        otnSmTcmPmSapiTraceTransmitted,
        otnSmTcmPmDapiTraceTransmitted,
        otnSmTcmPmOpSpecificTraceTransmitted,
        otnSmTcmPmSapiTraceReceivedByte0,
        otnSmTcmPmSapiTraceReceived,
        otnSmTcmPmDapiTraceReceivedByte0,
        otnSmTcmPmDapiTraceReceived,
        otnSmTcmPmOpSpecificTraceReceived,
        otnSmTcmPmSapiTraceExpected,
        otnSmTcmPmDapiTraceExpected,
        otnSmTcmPmTraceAlarmMode,
        otnSmTcmPmObjectProperty,
        otnSmTcmPmTraceMismatch,
        otnSmTcmPmBackwardDefectIndication,
        otnSmTcmPmAlarmIndicationSignal,
        otnSmTcmPmOpenConnectionIndication,
        otnSmTcmPmLockedDefectIndication,
        otnSmTcmPmSetTerminatedTcmCommand }
    STATUS      current
    DESCRIPTION
        "The otn interface minimal objects."
    ::= { lumOtnMinimalGroups 3 }

-- ----------------------------------------------------
-- Minimal Compliance
-- ----------------------------------------------------

lumOtmMinimalComplV1 MODULE-COMPLIANCE
    STATUS      deprecated
    DESCRIPTION
        "Minimal implementation requirements for the otn MIB v1."
    MODULE
        MANDATORY-GROUPS {
            otnGeneralMinimalGroupV1,
            otnSmTcmPmMinimalGroupV1 }
    ::= { lumOtnMinimalCompl 1 }

lumOtmMinimalComplV2 MODULE-COMPLIANCE
    STATUS      current
    DESCRIPTION
        "Minimal implementation requirements for the otn MIB v2."
    MODULE
        MANDATORY-GROUPS {
            otnGeneralMinimalGroupV1,
            otnSmTcmPmMinimalGroupV2 }
    ::= { lumOtnMinimalCompl 2 }

END
