-- *****************************************************************
-- INFINERA-PM-FSMSCGPTP-MIB
--
-- October 2013, Rishab Joshi
--
--
-- Copyright (c) 2008-2013 by Infinera Inc.
-- All rights reserved.
-- ****************************************************************

INFINERA-PM-FSMSCGPTP-MIB DEFINITIONS ::= BEGIN

IMPORTS
    MODULE-IDENTITY, OBJECT-TYPE,
    Integer32                                   FROM SNMPv2-SMI
    MODULE-COMPLIANCE, OBJECT-GROUP             FROM SNMPv2-CONF
    TruthValue                                  FROM SNMPv2-TC
    ifIndex                                     FROM IF-MIB
    FloatHundredths, InfnSampleDuration         FROM INFINERA-TC-MIB
    perfMon                                     FROM INFINERA-REG-MIB;


fsmScgPtpPmMIB MODULE-IDENTITY
    LAST-UPDATED  "201310080000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION      "201310080000Z"
    DESCRIPTION
        "First Version"
    ::= { perfMon 40 }


fsmScgPtpPmTable OBJECT-TYPE
    SYNTAX      SEQUENCE OF FsmScgPtpPmEntry
    MAX-ACCESS  not-accessible
    STATUS      current
    DESCRIPTION
        "A list of FsmScgPtpPm entries. Each entry is uniquely identified by the value of ifIndex."
    ::= { fsmScgPtpPmMIB 2 }

fsmScgPtpPmEntry  OBJECT-TYPE
    SYNTAX      FsmScgPtpPmEntry
    MAX-ACCESS  not-accessible
    STATUS      current
    DESCRIPTION
        "A FsmScgPtp entry containing historical performance information pertaining to Infinera OFXSCGPTP.
        This table is a subclass of IfCommon. Entries will exist in this table only for interfaces
        of type OFXSCGPTP."
    INDEX { ifIndex, fsmScgPtpPmSampleDuration, fsmScgPtpPmTimestamp}
    ::= { fsmScgPtpPmTable 1 }


FsmScgPtpPmEntry  ::= SEQUENCE {
   fsmScgPtpPmTimestamp        Integer32,
   fsmScgPtpPmSampleDuration   InfnSampleDuration,
   fsmScgPtpPmValidity         TruthValue,
   fsmScgPtpPmCmnScgOptMin     FloatHundredths,
   fsmScgPtpPmCmnScgOptMax     FloatHundredths,
   fsmScgPtpPmCmnScgOptAve     FloatHundredths,
   fsmScgPtpPmCmnScgOprMin     FloatHundredths,
   fsmScgPtpPmCmnScgOprMax     FloatHundredths,
   fsmScgPtpPmCmnScgOprAve     FloatHundredths
}


fsmScgPtpPmTimestamp OBJECT-TYPE
    SYNTAX      Integer32 (0..2147483647)
    MAX-ACCESS  not-accessible
    STATUS      current
    DESCRIPTION
        "End Time stamp for this interval. If this time is later than the current time,then the data for this bucket is currently being collected."
    ::= { fsmScgPtpPmEntry  1 }


fsmScgPtpPmSampleDuration OBJECT-TYPE
    SYNTAX      InfnSampleDuration
    MAX-ACCESS  not-accessible
    STATUS      current
    DESCRIPTION
        "The duration of this sample."
    ::= { fsmScgPtpPmEntry  2 }

fsmScgPtpPmValidity OBJECT-TYPE
    SYNTAX      TruthValue
    MAX-ACCESS  read-only
    STATUS      current
    DESCRIPTION "Flag indicating if data was valid for the entire interval"
    ::= { fsmScgPtpPmEntry  3 }


fsmScgPtpPmCmnScgOptMin OBJECT-TYPE
    SYNTAX      FloatHundredths
    MAX-ACCESS  read-only
    STATUS      current
    DESCRIPTION "Minimum FsmScg optical power min."
    ::= { fsmScgPtpPmEntry  4 }


fsmScgPtpPmCmnScgOptMax OBJECT-TYPE
    SYNTAX      FloatHundredths
    MAX-ACCESS  read-only
    STATUS      current
    DESCRIPTION "Maximum FsmScg optical power max."
    ::= { fsmScgPtpPmEntry  5 }


fsmScgPtpPmCmnScgOptAve OBJECT-TYPE
    SYNTAX      FloatHundredths
    MAX-ACCESS  read-only
    STATUS      current
    DESCRIPTION "Average FsmScg optical power ave."
    ::= { fsmScgPtpPmEntry  6 }


fsmScgPtpPmCmnScgOprMin OBJECT-TYPE
    SYNTAX      FloatHundredths
    MAX-ACCESS  read-only
    STATUS      current
    DESCRIPTION "Minimum FsmScg optical power min."
    ::= { fsmScgPtpPmEntry  7}


fsmScgPtpPmCmnScgOprMax OBJECT-TYPE
    SYNTAX      FloatHundredths
    MAX-ACCESS  read-only
    STATUS      current
    DESCRIPTION "Maximum FsmScg optical power max."
    ::= { fsmScgPtpPmEntry  8}


fsmScgPtpPmCmnScgOprAve OBJECT-TYPE
    SYNTAX      FloatHundredths
    MAX-ACCESS  read-only
    STATUS      current
    DESCRIPTION "Average FsmScg optical power ave."
    ::= { fsmScgPtpPmEntry  9}




fsmScgPtpPmRealTable OBJECT-TYPE
    SYNTAX      SEQUENCE OF FsmScgPtpPmRealEntry
    MAX-ACCESS  not-accessible
    STATUS      current
    DESCRIPTION
        "A list of FsmScgPtpPmReal entries. Each entry is uniquely identified by the value of ifIndex."
    ::= { fsmScgPtpPmMIB 1 }

fsmScgPtpPmRealEntry  OBJECT-TYPE
    SYNTAX      FsmScgPtpPmRealEntry
    MAX-ACCESS  not-accessible
    STATUS      current
    DESCRIPTION
        "A  fsmScgPtp entry containing real-time performance information pertaining to Infinera
         fsmScgPtp interfaces. This table is a subclass of IfCommon."
    INDEX { ifIndex }
    ::= { fsmScgPtpPmRealTable 1 }


FsmScgPtpPmRealEntry  ::= SEQUENCE {
    fsmScgPtpPmRealCmnScgOpt       FloatHundredths,
    fsmScgPtpPmRealCmnScgOpr       FloatHundredths
}

fsmScgPtpPmRealCmnScgOpt OBJECT-TYPE
    SYNTAX      FloatHundredths
    MAX-ACCESS  read-only
    STATUS      current
    DESCRIPTION "Total FsmScg optical power trasmit."
    ::= { fsmScgPtpPmRealEntry  1 }


fsmScgPtpPmRealCmnScgOpr OBJECT-TYPE
    SYNTAX      FloatHundredths
    MAX-ACCESS  read-only
    STATUS      current
    DESCRIPTION "Total FsmScg optical power receive."
    ::= { fsmScgPtpPmRealEntry  2 }



-- Conformance Statements
fsmScgPtpPmConformance    OBJECT IDENTIFIER ::= { fsmScgPtpPmMIB 3 }
fsmScgPtpPmCompliances    OBJECT IDENTIFIER ::= { fsmScgPtpPmConformance 1 }
fsmScgPtpPmGroups         OBJECT IDENTIFIER ::= { fsmScgPtpPmConformance 2 }

fsmScgPtpPmCompliance MODULE-COMPLIANCE
    STATUS current
    DESCRIPTION
    "Describes the requirements for conformance to the  fsmScgPtp-MIB"
    MODULE
        MANDATORY-GROUPS { fsmScgPtpPmGroup }
    ::= { fsmScgPtpPmCompliances 1 }

fsmScgPtpPmRealCompliance MODULE-COMPLIANCE
    STATUS current
    DESCRIPTION
    "Describes the requirements for conformance to the FsmScgPtpPmReal-MIB"
    MODULE
        MANDATORY-GROUPS { fsmScgPtpPmRealGroup }
    ::= { fsmScgPtpPmCompliances 2 }

fsmScgPtpPmGroup OBJECT-GROUP
    OBJECTS {
        fsmScgPtpPmTimestamp,
        fsmScgPtpPmSampleDuration,
        fsmScgPtpPmValidity,
        fsmScgPtpPmCmnScgOptMin,
        fsmScgPtpPmCmnScgOptMax,
        fsmScgPtpPmCmnScgOptAve,
        fsmScgPtpPmCmnScgOprMin,
        fsmScgPtpPmCmnScgOprMax,
        fsmScgPtpPmCmnScgOprAve
    }
    STATUS current
    DESCRIPTION
        " A collection of objects for reading the historical performance of the  fsmScgPtp."
    ::= { fsmScgPtpPmGroups 1 }

fsmScgPtpPmRealGroup OBJECT-GROUP
    OBJECTS {
        fsmScgPtpPmRealCmnScgOpt,
        fsmScgPtpPmRealCmnScgOpr
    }
    STATUS current
    DESCRIPTION
        " A collection of objects for reading the real-time performance of the  fsmScgPtp."
    ::= { fsmScgPtpPmGroups 2 }

END
