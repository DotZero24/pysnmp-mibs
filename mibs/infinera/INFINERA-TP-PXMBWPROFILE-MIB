-- *****************************************************************
-- INFINERA-TP-PXMBWPROFILE-MIB
--
-- Mithun Murthy/ Divyank Rastogi
--
--
-- Copyright (c) 2008-2016 by Infinera Inc.
-- All rights reserved.
-- ****************************************************************

INFINERA-TP-PXMBWPROFILE-MIB DEFINITIONS ::= BEGIN

IMPORTS
    MODULE-IDENTITY, OBJECT-TYPE, Integer32     FROM SNMPv2-SMI
    MODULE-COMPLIANCE, OBJECT-GROUP             FROM SNMPv2-CONF
    DisplayString, TruthValue                   FROM SNMPv2-TC
    ifIndex                                     FROM IF-MIB
	InfnEnableDisable,InfnColorMode,InfnMeterType,
	InfnSharedMeterInstance,InfnMeterAction,
	InfnBwRateUnit								FROM INFINERA-TC-MIB
    commonProfile								FROM INFINERA-REG-MIB;

pxmBwProfileMIB MODULE-IDENTITY
    LAST-UPDATED  "201605200000Z"
    ORGANIZATION
        "Infinera"
    CONTACT-INFO
        "Infinera
                1322 Bordeaux Drive
                Sunnyvale, CA - 94089

                Contact : Technical Support
                Email   : support@infinera.com
                Phone   : 1-877-INF-5288"
    DESCRIPTION
        " "

    REVISION  "201605200000Z"
    DESCRIPTION
        " "
::= { commonProfile 3 }


pxmBwProfileConformance   OBJECT IDENTIFIER ::= { pxmBwProfileMIB 3 }
pxmBwProfileCompliances   OBJECT IDENTIFIER ::= { pxmBwProfileConformance 1 }
pxmBwProfileGroups        OBJECT IDENTIFIER ::= { pxmBwProfileConformance 2 }

pxmBwProfileTable  OBJECT-TYPE
    SYNTAX SEQUENCE OF PxmBwProfileEntry
    MAX-ACCESS not-accessible
    STATUS     current
    DESCRIPTION
        "A list of PxmBwProfile entries. Each entry is uniquely identified by
                the value of ifIndex."
    ::= { pxmBwProfileMIB 1 }

pxmBwProfileEntry  OBJECT-TYPE
    SYNTAX     PxmBwProfileEntry
    MAX-ACCESS not-accessible
    STATUS     current
    DESCRIPTION
        "A PxmBwProfile entry containing information pertaining to
                Infinera PxmBwProfile interfaces. This table is a subclass of IfCommon.
                Entries will exist in this table only for interfaces of type PxmBwProfile."
    INDEX { ifIndex }
    ::= { pxmBwProfileTable 1 }

PxmBwProfileEntry  ::= SEQUENCE {
    pxmBwProfileCouplingFlag	InfnEnableDisable,
    pxmBwProfileColorMode		InfnColorMode,
    pxmBwProfileMeterType		InfnMeterType,
    pxmBwProfileSharedMeterInstance	InfnSharedMeterInstance,
    pxmBwProfileMeterAction		InfnMeterAction,
    pxmBwProfileRateUnit		InfnBwRateUnit,
	pxmBwProfileInUse			TruthValue
}

pxmBwProfileCouplingFlag 	OBJECT-TYPE
    SYNTAX     InfnEnableDisable
    MAX-ACCESS read-write
    STATUS     current
    DESCRIPTION
        ""
    ::= { pxmBwProfileEntry 1 }

pxmBwProfileColorMode	OBJECT-TYPE
    SYNTAX     InfnColorMode
    MAX-ACCESS read-write
    STATUS     current
    DESCRIPTION
        ""
    ::= { pxmBwProfileEntry 2 }

pxmBwProfileMeterType	OBJECT-TYPE
    SYNTAX     InfnMeterType
    MAX-ACCESS read-write
    STATUS     current
    DESCRIPTION
        ""
    ::= { pxmBwProfileEntry 3 }

pxmBwProfileSharedMeterInstance	OBJECT-TYPE
    SYNTAX     InfnSharedMeterInstance
    MAX-ACCESS read-write
    STATUS     current
    DESCRIPTION
        ""
    ::= { pxmBwProfileEntry 4 }

pxmBwProfileMeterAction		OBJECT-TYPE
    SYNTAX     InfnMeterAction
    MAX-ACCESS read-write
    STATUS     current
    DESCRIPTION
        ""
    ::= { pxmBwProfileEntry 5 }

pxmBwProfileRateUnit	OBJECT-TYPE
    SYNTAX     InfnBwRateUnit
    MAX-ACCESS read-write
    STATUS     current
    DESCRIPTION
        ""
    ::= { pxmBwProfileEntry 6 }

pxmBwProfileInUse	OBJECT-TYPE
    SYNTAX    	TruthValue
    MAX-ACCESS read-only
    STATUS     current
    DESCRIPTION
        ""
    ::= { pxmBwProfileEntry 7 }


pxmBwProfileCompliance  MODULE-COMPLIANCE
    STATUS     current
    DESCRIPTION
        "Describes the requirements for conformance to the TRIBPTP-MIB"
    MODULE
        MANDATORY-GROUPS { pxmBwProfileGroup }
    ::= { pxmBwProfileCompliances 1 }

pxmBwProfileGroup  OBJECT-GROUP
    OBJECTS {
		pxmBwProfileCouplingFlag,
		pxmBwProfileColorMode,
		pxmBwProfileMeterType,
		pxmBwProfileSharedMeterInstance,
		pxmBwProfileMeterAction,
		pxmBwProfileRateUnit,
		pxmBwProfileInUse
    }
    STATUS     current
    DESCRIPTION
        " A collection of objects for managing pxmBwProfile interfaces."
    ::= { pxmBwProfileGroups 1 }
END
