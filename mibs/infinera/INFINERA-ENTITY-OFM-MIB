-- ***************************************************************
-- INFINERA-ENTITY-OFM-MIB
--
--
-- Copyright (c) 2011-2012 by Infinera Inc.
-- All rights reserved.
-- ****************************************************************

INFINERA-ENTITY-OFM-MIB DEFINITIONS ::= BEGIN

IMPORTS
    OBJECT-TYPE, MODULE-IDENTITY        	FROM SNMPv2-SMI
    OBJECT-GROUP, MODULE-COMPLIANCE     	FROM SNMPv2-CONF
    DisplayString            	            FROM SNMPv2-TC
    entLPPhysicalIndex                  	FROM ENTITY-MIB
    equipment                           	FROM INFINERA-REG-MIB
    InfnEqptType, FloatTenths           FROM INFINERA-TC-MIB;

ofmMIB MODULE-IDENTITY
    LAST-UPDATED  "201110200000Z"
    ORGANIZATION "INFINERA"
    CONTACT-INFO
        "Infinera
        169 Java Drive
        Sunnyvale, CA - 94089

        Contact : Technical Support
        Email   : support@infinera.com
        Phone   : 1-877-INF-5288 "
        DESCRIPTION
        "This MIB is modeling for OFM equipment table"

::= { equipment 40 }

ofmConformance       OBJECT IDENTIFIER ::= { ofmMIB 3 }
ofmCompliances       OBJECT IDENTIFIER ::= { ofmConformance 1 }
ofmGroups            OBJECT IDENTIFIER ::= { ofmConformance 2 }

ofmTable  OBJECT-TYPE
    SYNTAX SEQUENCE OF OfmEntry
    MAX-ACCESS not-accessible
    STATUS     current
    DESCRIPTION
        "This table contains all OFM modules that are currently present in a network element.
        "
    ::= { ofmMIB 1 }

ofmEntry  OBJECT-TYPE
    SYNTAX     OfmEntry
    MAX-ACCESS not-accessible
    STATUS     current
    DESCRIPTION
        "A row in the OFM table. Each row in the table is identified with a unique entPhysicalIndexID."
    INDEX { entLPPhysicalIndex }
    ::= { ofmTable 1 }

OfmEntry ::= SEQUENCE {
   ofmMoId                                  DisplayString,
   ofmProvEqptType                          InfnEqptType,
   ofmOTNContainerRepresentation            INTEGER,
   ofmActvTimingSource						DisplayString,
   ofmPicDspVer                             DisplayString,
   ofmMaxFruGain                            FloatTenths,
   ofmRxEdfaOutputPowerTarget               FloatTenths,
   ofmRxEdfaGain                            FloatTenths,
   ofmRecommendedGain                       FloatTenths,
   ofmBwQmax                                FloatTenths,
   ofmBwQused                               FloatTenths,
   ofmBwQlicensed                           FloatTenths,
   ofmBwBmax                                FloatTenths,
   ofmBwBused                               FloatTenths,
   ofmBwBlicensed                           FloatTenths,
   ofmLicensedServicesDisabled              Integer32,
   ofmLicenseEnforced                       INTEGER,
   ofmDefFlexLicModFormat                   INTEGER,
   ofmBwUsgWaterMarkGranularity             FloatTenths,
   ofmAvailableTunableSuperChNumbers        DisplayString
}

ofmMoId     OBJECT-TYPE
    SYNTAX      DisplayString
    MAX-ACCESS  read-write
    STATUS      current
    DESCRIPTION ""
    ::= { ofmEntry 1 }

ofmProvEqptType     OBJECT-TYPE
    SYNTAX      InfnEqptType
    MAX-ACCESS  read-write
    STATUS      current
    DESCRIPTION ""
    ::= { ofmEntry 2 }

ofmOTNContainerRepresentation OBJECT-TYPE
    SYNTAX      INTEGER{
        otuKi(1),
        otuAdapti(2)
    }
    MAX-ACCESS  read-write
    STATUS      current
    DESCRIPTION ""
    ::= { ofmEntry  3 }


ofmActvTimingSource OBJECT-TYPE
	SYNTAX     DisplayString
    MAX-ACCESS read-only
    STATUS     current
    DESCRIPTION ""
    ::= { ofmEntry 4 }

ofmPicDspVer    OBJECT-TYPE
    SYNTAX      DisplayString
    MAX-ACCESS  read-only
    STATUS      current
    DESCRIPTION ""
    ::= { ofmEntry  5 }

ofmMaxFruGain   OBJECT-TYPE
    SYNTAX      FloatTenths
    MAX-ACCESS  read-only
    STATUS      current
    DESCRIPTION ""
    ::= { ofmEntry  6 }

ofmRecommendedGain OBJECT-TYPE
    SYNTAX          FloatTenths
    MAX-ACCESS      read-only
    STATUS          current
    DESCRIPTION     ""
    ::= { ofmEntry 7 }

ofmRxEdfaOutputPowerTarget  OBJECT-TYPE
    SYNTAX      FloatTenths
    MAX-ACCESS  read-only
    STATUS      current
    DESCRIPTION ""
    ::= { ofmEntry  8 }

ofmRxEdfaGain   OBJECT-TYPE
    SYNTAX      FloatTenths
    MAX-ACCESS  read-write
    STATUS      current
    DESCRIPTION ""
    ::= { ofmEntry  9 }

ofmBwQmax   OBJECT-TYPE
    SYNTAX      FloatTenths
    MAX-ACCESS  read-write
    STATUS      current
    DESCRIPTION ""
    ::= { ofmEntry 10 }

ofmBwQused      OBJECT-TYPE
    SYNTAX      FloatTenths
    MAX-ACCESS  read-write
    STATUS      current
    DESCRIPTION ""
    ::= { ofmEntry 11 }

ofmBwQlicensed  OBJECT-TYPE
    SYNTAX      FloatTenths
    MAX-ACCESS  read-write
    STATUS      current
    DESCRIPTION ""
    ::= { ofmEntry 12 }


ofmBwBmax       OBJECT-TYPE
    SYNTAX      FloatTenths
    MAX-ACCESS  read-write
    STATUS      current
    DESCRIPTION ""
    ::= { ofmEntry 13 }

ofmBwBused      OBJECT-TYPE
    SYNTAX      FloatTenths
    MAX-ACCESS  read-write
    STATUS      current
    DESCRIPTION ""
    ::= { ofmEntry 14 }

ofmBwBlicensed      OBJECT-TYPE
    SYNTAX      FloatTenths
    MAX-ACCESS  read-write
    STATUS      current
    DESCRIPTION ""
    ::=  { ofmEntry 15 }


ofmLicensedServicesDisabled OBJECT-TYPE
    SYNTAX      Integer32
    MAX-ACCESS  read-only
    STATUS      current
    DESCRIPTION ""
    ::= { ofmEntry 16 }

ofmLicenseEnforced      OBJECT-TYPE
    SYNTAX      INTEGER {
        unknown (1),
        notEnforced (2),
        enforced (3)
    }
    MAX-ACCESS  read-only
    STATUS      current
    DESCRIPTION ""
    ::= { ofmEntry 17 }

ofmDefFlexLicModFormat      OBJECT-TYPE
    SYNTAX      INTEGER {
        unknown(1),
        qpsk(2),
        bpsk(3),
        pm3qam(4)
    }
    MAX-ACCESS  read-write
    STATUS      current
    DESCRIPTION ""
    ::= { ofmEntry 18 }

ofmBwUsgWaterMarkGranularity    OBJECT-TYPE
    SYNTAX      FloatTenths
    MAX-ACCESS  read-write
    STATUS      current
    DESCRIPTION ""
    ::= { ofmEntry 19 }

ofmAvailableTunableSuperChNumbers OBJECT-TYPE
    SYNTAX      DisplayString
    MAX-ACCESS  read-only
    STATUS      current
    DESCRIPTION ""
    ::= { ofmEntry  20 }

ofmCompliance  MODULE-COMPLIANCE
    STATUS      current
    DESCRIPTION ""
    MODULE
        MANDATORY-GROUPS { ofmGroup }
    ::= { ofmCompliances 1 }

ofmGroup  OBJECT-GROUP
    OBJECTS {
        ofmMoId,
        ofmProvEqptType,
   	    ofmActvTimingSource,
        ofmPicDspVer,
        ofmMaxFruGain,
        ofmRxEdfaOutputPowerTarget,
        ofmRxEdfaGain,
        ofmOTNContainerRepresentation,
        ofmRecommendedGain,
        ofmBwQmax,
        ofmBwQused,
        ofmBwQlicensed,
        ofmBwBmax,
        ofmBwBused,
        ofmBwBlicensed,
        ofmLicensedServicesDisabled,
        ofmLicenseEnforced,
        ofmDefFlexLicModFormat,
        ofmBwUsgWaterMarkGranularity,
        ofmAvailableTunableSuperChNumbers
    }
    STATUS     current
    DESCRIPTION
        ""
    ::= { ofmGroups 1 }
END
