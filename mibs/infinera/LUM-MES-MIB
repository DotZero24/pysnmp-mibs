LUM-MES-MIB DEFINITIONS ::= BEGIN

IMPORTS
    MODULE-IDENTITY, OBJECT-TYPE, Unsigned32, Integer32, IpAddress,
    Counter64
        FROM SNMPv2-SMI
    OBJECT-GROUP, MODULE-COMPLIANCE
        FROM SNMPv2-CONF
    DisplayString, DateAndTime, RowStatus, MacAddress, TEXTUAL-CONVENTION
        FROM SNMPv2-TC
    lumModules, lumMesMIB
        FROM LUM-REG
    MgmtNameString, SubrackNumber, SlotNumber, PortNumber,
    BoardOrInterfaceOperStatus, BoardOrInterfaceAdminStatus, ObjectProperty,
    CommandString, FaultStatus, ServiceIdWithNotUsed
        FROM LUM-TC;

lumMesMIBModule MODULE-IDENTITY
    LAST-UPDATED
        "201812210000Z" -- Dec 2018
    ORGANIZATION
        "Infinera Corporation"
    CONTACT-INFO
        "techsupport@infinera.se"
    DESCRIPTION
        "The Metro Ethernet Services MIB.

"
    REVISION
        "201812210000Z" -- Dec 2018
    DESCRIPTION
        "Changes for r32.0.0:
        - Added mesVlanMapMacLearningLimit in vlanMap."
    REVISION
        "201805310000Z" -- May 2018
    DESCRIPTION
        "Changes for r28.0.6:
        - Changed mesErpHoldOffTime to read-create and updated its description."
    REVISION
        "201802060000Z" -- February 6th 2018
    DESCRIPTION
        "Changes for r31.0:
        - Added the HDEA1600 board"
    REVISION
        "201712150000Z" -- December 15th 2017
    DESCRIPTION
        "Changes for r30.0:
        - Added the emxp440 board
        - added mesVlanMapPortmaskIf9-16
        - added subrack and slot attributes in VlanMap
        - added mesMirroringDestInterface
        - added mesMiscAssociateClassAdvanced
        - added mesClassAssociateActionAdvanced"
    REVISION
        "201706150000Z" -- June 15th 2017
    DESCRIPTION
        "Changes for r29.0:
        - Added mesPortAutoNegMasterSlaveCfg.
        - Added mesPortAutoNegMasterSlaveStatus.
        - Added StateLastChangeTime and ConfigLastChangeTime in the general group for all tables
        - Changed ORGANIZATION and CONTACT-INFO"
    REVISION
        "201611170000Z" -- Nov 2016
    DESCRIPTION
        "Changes for r28.0:
        - Added mesCfmMepLocalId."
    REVISION
        "201610310000Z" -- OCT 2016
    DESCRIPTION
        "Changes for r27.0.2:
        - Added mesPolicingId."
    REVISION
        "201604300000Z" -- April 2016
    DESCRIPTION
        "Changes for r27.0:
        - Added mesActionRedirectIfNo and mesActionRedirectTxPort.
        - Added mesClassIfNo and mesClassTxPort."
    REVISION
        "201601110000Z" -- Jan 11th 2016
    DESCRIPTION
        "Added default value notPresent/down for operStatus."
    REVISION
        "201512150000Z" -- Dec 2015
    DESCRIPTION
        "Changes for r26.0:
        - Added larger portmask in mesPort for LAG ports, mesPortLagPortmaskIf1-8.
        - Added idx port reference for mesPort,  mesPortIdx.
        - Added interface number for mesPort, mesPortIfNo.
        - Added idx L1 client port reference for mesPort, mesPortClientIdx.
        - Added TU port reference for mesPort, mesPortUpPortId.
        - Changed access type from 'read-only' to 'read-create' on:
            mesPortIndex, mesPortName, mesPortSubrack, mesPortSlot,
            mesPortTxPort, mesPortRxPort
        - Added larger portmasks for VLAN Map, mesVlanMapPortmaskIf1-8
        - Added mesCfmMepIfNo
        - Added mesMgmtVlanIfNo
        - Added larger portmasks for COS profile mesCosProfilePortmaskIf1-8
        - Added larger portmasks for LAGs mesLagPortmaskIf1-8
        - Added mesLagMasterIfNo, mesLagMasterTxPort and mesLagLocalId for LAGs.
        - Increased range for mesPolicingRate to support 100G
        - Added mesLacpIfNo, mesLacpTxPort, and mesLacpUpPortId in LACP table.
        - Added mesVlanTagRuleInterfaceName for vlanTagRule table."
    REVISION
        "201504150000Z" -- April 2015
    DESCRIPTION
        "Added mesLagAdminStatus and mesLagOperStatus in r25"
    REVISION
       "201502110000Z" -- Feb 2015
    DESCRIPTION
        "Added alarm mesErpProvisioningMismatch in r25
         - hidden=yes for mesErpUnexpectedMegLevel -not used
         - added mesClassEthertype"
    REVISION
        "201501150000Z" -- Jan 2015
    DESCRIPTION
        "Added emxp240iie in r25"
    REVISION
        "201410290000Z" -- Oct 2014
    DESCRIPTION
        "Changed LAG minimumActiveOfLinks and maximumActiveOfLinks to 0"
    REVISION
        "201408160000Z" -- Aug 16th 2014
        DESCRIPTION
        "Changes made for release r23.1:
        - Added mesLagLacpMaxNumberOfActiveLinks.
        - Added mesLagLacpMinNumberOfActiveLinks.
        - Added mesMiscEnablePtp1588.
        - Added mesMiscEnableStpMgmtVlan."
    REVISION
        "201405160000Z" -- May 16th 2014
    DESCRIPTION
        "Changes made for release r23:
        - Added transmitLmr status for meps, e.g LM responder status.
        - Added transmitDmr status for meps, e.g DM responder status.
        - Addes CoS awareness for LM Responder.
        - Added service ID for vlanMap, action, classification and MEF policer.
        - Added fhmxp10g board
        - Added attributes to the LAG table for LACP
            mesLagLacpEnabled
            mesLagLacpSystemPriority
            mesLagLacpPeriod
            mesLagLacpLinkProtection
            mesLagDegraded
            mesLagFailure
        - Added LACP table"
    REVISION
        "201311010000Z" -- Nov 1st 2013
    DESCRIPTION
        "Changes made for release r22:
        - Added 'undefined' state to, mesErpStatusLeft, mesErpStatusRight, mesErpProtState, mesErpActiveEvent, mesErpRapsReqState
        - Added attributes in mesMisc table for ERP v2
            mesMiscNoOfErpV2s
            mesMiscAssociateErpV2
        - Added attributes in Erp table for ERP v2
            mesErpRowStatus
            mesErpNodeType
            mesErpProtectionMode
            mesErpVersion
            mesErpMajorName
            mesErpRingId
            mesErpRingIndex
            mesErpOperatorCommand
            mesErpGroupId
            mesErpSwitchInformation
            mesErpTopologyChangePropagation
            mesErpSubRings
        - Added VLAN Protection group table
        - Added attribute in VLAN Map table
            mesVlanMapRings
        - Added attribute in mgmtVlan table
            mesMgmtVlanRings
        - Added to mesClass table
            mesClassInternalClassId"
    REVISION
        "201305010000Z" -- May 1st 2013
    DESCRIPTION
        "Changes made for release r21:
        - Added tpq10gfeci board.
        - Added error propagation.
        - Added portdevice info in mesMaid and mesCfmMep.
        - Added additional alarms mesCfmMepRemoteCsfLos, mesCfmMepRemoteCsfRdi, mesCfmMepRemoteCsfFdi, mesCfmMepLocalCsfLos."
    REVISION
        "201212200000Z" --  Dec 20th 2012
    DESCRIPTION
        "Changes made for release r20:
        - Added msTp40G, msMxp40G board."
    REVISION
        "201203300000Z" -- March 30th 2012
    DESCRIPTION
        "Changes made for release r19:
        -Attribute forceMgmtVlan added on board tpq10Gfec."
    REVISION
        "201112200000Z" --  December 20th 2011
    DESCRIPTION
        "Changes made for release r18:
        - High BER alarm added for mesPortTable.
        - Added counter for up-MEPs.
        - Added support for control of CCM sequence number, mesCfmMepCcmSeqNumStatus.
        - Added 1gbE port usage current and next for emxp40Gii.
        - Added mesCfmMepDirection, The direction in which the MEP faces on the Bridge port.
        - mesMiscSfpPortUsage updated.
        - Added OAM counters for ethClassPm. Updated help texts for classifications in MES MIB.
        - Added mesClassDirection attribute to enable egress policies.
        - Added MES class inner/outer VLAN CFI classification attributes.
        - Updated MIB MES classification with MAC address mask."
    REVISION
        "201107040000Z" --  July 4th 2011"
    DESCRIPTION
        "The Metro Ethernet services MIB."
    REVISION
        "201104210000Z" --  April 21th 2011
    DESCRIPTION
        "Layer2 updates."
    REVISION
        "200802260000Z" --  February 26th 2008
    DESCRIPTION
        "Added provider tag transparancy."
    REVISION
        "200802210000Z" --  February 21st 2008
    DESCRIPTION
        "Added MEG configuration."
    REVISION
        "200801300000Z" --  January 30th 2008
    DESCRIPTION
        "Added OAM protocol configuration."
    REVISION
        "200711150000Z" --  November 15th 2007
    DESCRIPTION
        "Revised layer 2 processing."
    REVISION
        "200711090000Z" --  November 9th 2007
    DESCRIPTION
        "Added queue profiles."
    REVISION
        "200710250000Z" --  October 25th 2007
    DESCRIPTION
        "Added default priority on UNI.
        Added protocol specific layer 2 control protocol
        processing directives on UNI."
    REVISION
        "200704170000Z" --  April 17th 2007
    DESCRIPTION
        "The initial revision of this module."
    ::= { lumModules 32 }


-- ----------------------------------------------------
-- Conformance area, containing groups and complicance
-- specifications.
-- ----------------------------------------------------

lumMesConfs OBJECT IDENTIFIER ::= { lumMesMIB 1 }
lumMesGroups OBJECT IDENTIFIER ::= { lumMesConfs 1 }
lumMesCompl OBJECT IDENTIFIER ::= { lumMesConfs 2 }


-- ----------------------------------------------------
-- Root for objects in the mes MIB
-- ----------------------------------------------------

lumMesMIBObjects OBJECT IDENTIFIER ::= { lumMesMIB 2 }


-- ----------------------------------------------------
-- This MIB contains the following groups:
-- ----------------------------------------------------

mesGeneral OBJECT IDENTIFIER ::= { lumMesMIBObjects 1 }
mesUniList OBJECT IDENTIFIER ::= { lumMesMIBObjects 2 }
mesNniList OBJECT IDENTIFIER ::= { lumMesMIBObjects 3 }
mesEvcList OBJECT IDENTIFIER ::= { lumMesMIBObjects 4 }
mesCeEvcMapList OBJECT IDENTIFIER ::= { lumMesMIBObjects 5 }
mesBwpList OBJECT IDENTIFIER ::= { lumMesMIBObjects 6 }
mesQProfileList OBJECT IDENTIFIER ::= { lumMesMIBObjects 7 }
mesMepList OBJECT IDENTIFIER ::= { lumMesMIBObjects 8 }
mesMegList OBJECT IDENTIFIER ::= { lumMesMIBObjects 9 }
mesMiscList OBJECT IDENTIFIER ::= { lumMesMIBObjects 10 }
mesEvcBwpMapList OBJECT IDENTIFIER ::= { lumMesMIBObjects 11 }
mesPortList OBJECT IDENTIFIER ::= { lumMesMIBObjects 12 }
mesVlanMapList OBJECT IDENTIFIER ::= { lumMesMIBObjects 13 }
mesMgmtVlanList OBJECT IDENTIFIER ::= { lumMesMIBObjects 14 }
mesLagList OBJECT IDENTIFIER ::= { lumMesMIBObjects 15 }
mesPolicingList OBJECT IDENTIFIER ::= { lumMesMIBObjects 16 }
mesShapingList OBJECT IDENTIFIER ::= { lumMesMIBObjects 17 }
mesCosList OBJECT IDENTIFIER ::= { lumMesMIBObjects 18 }
mesBwpMapList OBJECT IDENTIFIER ::= { lumMesMIBObjects 19 }
mesMirroringList OBJECT IDENTIFIER ::= { lumMesMIBObjects 20 }
mesVlanTagRuleList OBJECT IDENTIFIER ::= { lumMesMIBObjects 21 }
mesVlanTagClassVlanList OBJECT IDENTIFIER ::= { lumMesMIBObjects 22 }
mesCosProfileList OBJECT IDENTIFIER ::= { lumMesMIBObjects 23 }
mesMaidList OBJECT IDENTIFIER ::= { lumMesMIBObjects 24 }
mesCfmMepList OBJECT IDENTIFIER ::= { lumMesMIBObjects 25 }
mesErpList OBJECT IDENTIFIER ::= { lumMesMIBObjects 26 }
mesClassList OBJECT IDENTIFIER ::= { lumMesMIBObjects 27 }
mesActionList OBJECT IDENTIFIER ::= { lumMesMIBObjects 28 }
mesPolicyList OBJECT IDENTIFIER ::= { lumMesMIBObjects 29 }
mesErrorPropList OBJECT IDENTIFIER ::= { lumMesMIBObjects 30 }
mesVlanProtList OBJECT IDENTIFIER ::= { lumMesMIBObjects 31 }
mesLacpList OBJECT IDENTIFIER ::= { lumMesMIBObjects 32 }
-- lumentisMesNotifications  OBJECT IDENTIFIER ::= { lumMesMIBObjects n }


-- ----------------------------------------------------
-- Textual Conventions
-- ----------------------------------------------------

MesQProfileId ::= TEXTUAL-CONVENTION
    STATUS current
    DESCRIPTION
        "Queue profile identity."
    SYNTAX INTEGER {
        -- undefined (0),
        strict1 (1),
        strict2 (2),
        strict3 (3),
        strict4 (4),
        strict5 (5),
        strict6 (6),
        wrr1 (7),
        wrr2 (8),
        wrr3 (9),
        wrr4 (10),
        wrr5 (11),
        wrr6 (12),
        wrr7 (13),
        wrr8 (14) }

Dot1agCfmMaintDomainNameType ::= TEXTUAL-CONVENTION
    STATUS current
    DESCRIPTION
       "A value that represents a type (and thereby the format)
        of a Dot1agCfmMaintDomainName. The value can be one of
        the following:
        ieeeReserved(0)   Reserved for definition by IEEE 802.1
                          recommend to not use zero unless
                          absolutely needed.
        none(1)           No format specified, usually because
                          there is not (yet) a Maintenance
                          Domain Name. In this case, a zero
                          length OCTET STRING for the Domain
                          Name field is acceptable.
        dnsLikeName(2)    Domain Name like string, globally unique
                          text string derived from a DNS name.
        macAddrAndUint(3) MAC address + 2-octet (unsigned) integer.
        charString(4)     RFC2579 DisplayString, except that the
                          character codes 0-31 (decimal) are not
                          used.
        ieeeReserved(xx)  Reserved for definition by IEEE 802.1
                          xx values can be [5..31] and [64..255]
        ituReserved(xx)   Reserved for definition by ITU-T Y.1731
                          xx values range from [32..63]
        To support future extensions, the Dot1agCfmMaintDomainNameType
        textual convention SHOULD NOT be sub-typed in object type
        definitions. It MAY be sub-typed in compliance statements in
        order to require only a subset of these address types for a
        compliant implementation.
        Implementations must ensure that Dot1agCfmMaintDomainNameType
        objects and any dependent objects (e.g.,
        Dot1agCfmMaintDomainName objects) are consistent. An
        inconsistentValue error must be generated if an attempt to
        change an Dot1agCfmMaintDomainNameType object would, for
        example, lead to an undefined Dot1agCfmMaintDomainName value.
        In particular,
        Dot1agCfmMaintDomainNameType/Dot1agCfmMaintDomainName pairs
        must be changed together if the nameType changes.
       "
    REFERENCE
       "802.1ag clause 21.6.5, Table 21-19"
    SYNTAX INTEGER {
             none (1),
             dnsLikeName (2),
             macAddressAndUint (3),
             charString (4)
           }

Dot1agCfmMaintDomainName ::= TEXTUAL-CONVENTION
    DISPLAY-HINT "43a"
    STATUS current
    DESCRIPTION
       "Denotes a generic Maintenance Domain Name.

        A Dot1agCfmMaintDomainName value is always interpreted within
        the context of a Dot1agCfmMaintDomainNameType value. Every
        usage of the Dot1agCfmMaintDomainName textual convention is
        required to specify the Dot1agCfmMaintDomainNameType object
        that provides the context. It is suggested that the
        Dot1agCfmMaintDomainNameType object be logically registered
        before the object(s) that use the Dot1agCfmMaintDomainName
        textual convention, if they appear in the same logical row.

        The value of a Dot1agCfmMaintDomainName object must always
        be consistent with the value of the associated
        Dot1agCfmMaintDomainNameType object. Attempts to set
        an Dot1agCfmMaintDomainName object to a value inconsistent
        with the associated Dot1agCfmMaintDomainNameType must fail
        with an inconsistentValue error.

        When this textual convention is used as the syntax of an
        index object, there may be issues with the limit of 128
        sub-identifiers specified in SMIv2, IETF STD 58. In this
        case, the object definition MUST include a 'SIZE' clause
        to limit the number of potential instance sub-identifiers;
        otherwise the applicable constraints MUST be stated in
        the appropriate conceptual row DESCRIPTION clauses, or
        in the surrounding documentation if there is no single
        DESCRIPTION clause that is appropriate.

        A value of none(1) in the associated
        Dot1agCfmMaintDomainNameType object means that no Maintenance
        Domain name is present, and the contents of the
        Dot1agCfmMaintDomainName object are meaningless.
        See the DESCRIPTION of the Dot1agCfmMaintAssocNameType
        TEXTUAL-CONVENTION for a discussion of the length limits on
        the Maintenance Domain name and Maintenance Association name.
       "
    REFERENCE
       "802.1ag clause 21.6.5"
    SYNTAX OCTET STRING (SIZE(1..43))

Dot1agCfmMaintAssocNameType ::= TEXTUAL-CONVENTION
    STATUS current
    DESCRIPTION
       "A value that represents a type (and thereby the format)
        of a Dot1agCfmMaintAssocName. The value can be one of
        the following:

        ieeeReserved(0)   Reserved for definition by IEEE 802.1
                          recommend to not use zero unless
                          absolutely needed.
        primaryVid(1)     Primary VLAN ID.
                          12 bits represented in a 2-octet integer:
                          - 4 least significant bits of the first
                            byte contains the 4 most significant
                            bits of the 12 bits primary VID
                          - second byte contains the 8 least
                            significant bits of the primary VID

                                 0 1 2 3 4 5 6 7 8
                                 +-+-+-+-+-+-+-+-+
                                 |0 0 0 0| (MSB) |
                                 +-+-+-+-+-+-+-+-+
                                 | VID LSB |
                                 +-+-+-+-+-+-+-+-+
        charString(2)     RFC2579 DisplayString, except that the
                          character codes 0-31 (decimal) are not
                          used. (1..45) octets
        unsignedInt16 (3) 2-octet integer/big endian
        rfc2685VpnId(4)   RFC 2685 VPN ID
                          3 octet VPN authority Organizationally
                          Unique Identifier followed by 4 octet VPN
                          index identifying VPN according to the OUI:
                                 0 1 2 3 4 5 6 7 8
                                 +-+-+-+-+-+-+-+-+
                                 | VPN OUI (MSB) |
                                 +-+-+-+-+-+-+-+-+
                                 | VPN OUI |
                                 +-+-+-+-+-+-+-+-+
                                 | VPN OUI (LSB) |
                                 +-+-+-+-+-+-+-+-+
                                 |VPN Index (MSB)|
                                 +-+-+-+-+-+-+-+-+
                                 | VPN Index |
                                 +-+-+-+-+-+-+-+-+
                                 | VPN Index |
                                 +-+-+-+-+-+-+-+-+
                                 |VPN Index (LSB)|
                                 +-+-+-+-+-+-+-+-+

        ieeeReserved(xx)  Reserved for definition by IEEE 802.1
                          xx values can be [5..31] and [64..255]
        ituReserved(xx)   Reserved for definition by ITU-T Y.1731
                          xx values range from [32..63]

        icc               According to ITU recommendation Y.1731, the
                          ICC-based MEG ID is an ASCII string (A to Z
                          or 0 to 9) of up to thirteen characters. It
                          consists of two subfields, the ITU carrier
                          code (one to six character) followed by a
                          unique MEG ID code.

        To support future extensions, the Dot1agCfmMaintAssocNameType
        textual convention SHOULD NOT be sub-typed in object type
        definitions. It MAY be sub-typed in compliance statements in
        order to require only a subset of these address types for a
        compliant implementation.

        Implementations must ensure that Dot1agCfmMaintAssocNameType
        objects and any dependent objects (e.g.,
        Dot1agCfmMaintAssocName objects) are consistent. An
        inconsistentValue error must be generated if an attempt to
        change an Dot1agCfmMaintAssocNameType object would, for
        example, lead to an undefined Dot1agCfmMaintAssocName value.
        In particular,
        Dot1agCfmMaintAssocNameType/Dot1agCfmMaintAssocName pairs
        must be changed together if the nameType changes.

        The Maintenance Domain name and Maintenance Association name,
        when put together into the CCM PDU, MUST total 48 octets or
        less. If the Dot1agCfmMaintDomainNameType object contains
        none(1), then the Dot1agCfmMaintAssocName object MUST be
        45 octets or less in length. Otherwise, the length of
        the Dot1agCfmMaintDomainName object plus the length of the
        Dot1agCfmMaintAssocName object, added together, MUST total
        less than or equal to 44 octets.
       "
    REFERENCE
       "802.1ag clause 21.6.5.4, Table 21-20"
    SYNTAX INTEGER {
             primaryVid (1),
             charString (2),
             unsignedInt16 (3),
             rfc2685VpnId (4),
             icc (32)
           }

Dot1agCfmMaintAssocName ::= TEXTUAL-CONVENTION
    DISPLAY-HINT "45a"
    STATUS current
    DESCRIPTION
      "Denotes a generic Maintenance Association Name. It is the
       part of the Maintenance Association Identifier which is
       unique within the Maintenance Domain Name and is appended
       to the Maintenance Domain Name to form the Maintenance
       Association Identifier (MAID).

       A Dot1agCfmMaintAssocName value is always interpreted within
       the context of a Dot1agCfmMaintAssocNameType value. Every
       usage of the Dot1agCfmMaintAssocName textual convention is
       required to specify the Dot1agCfmMaintAssocNameType object
       that provides the context. It is suggested that the
       Dot1agCfmMaintAssocNameType object be logically registered
       before the object(s) that use the Dot1agCfmMaintAssocName
       textual convention, if they appear in the same logical row.

       The value of a Dot1agCfmMaintAssocName object must
       always be consistent with the value of the associated
       Dot1agCfmMaintAssocNameType object. Attempts to set
       an Dot1agCfmMaintAssocName object to a value inconsistent
       with the associated Dot1agCfmMaintAssocNameType must fail
       with an inconsistentValue error.

       When this textual convention is used as the syntax of an
       index object, there may be issues with the limit of 128
       sub-identifiers specified in SMIv2, IETF STD 58. In this
       case, the object definition MUST include a 'SIZE' clause
       to limit the number of potential instance sub-identifiers;
       otherwise the applicable constraints MUST be stated in
       the appropriate conceptual row DESCRIPTION clauses, or
       in the surrounding documentation if there is no single
       DESCRIPTION clause that is appropriate.
      "
    REFERENCE
      "802.1ag clauses 21.6.5.4, 21.6.5.5, 21.6.5.6"
    SYNTAX OCTET STRING (SIZE(1..45))

Dot1agCfmMDLevel ::= TEXTUAL-CONVENTION
    DISPLAY-HINT "d"
    STATUS current
    DESCRIPTION
       "Integer identifying the Maintenance Domain Level (MD Level).
        Higher numbers correspond to higher Maintenance Domains,
        those with the greatest physical reach, with the highest
        values for customers' CFM PDUs. Lower numbers correspond
        to lower Maintenance Domains, those with more limited
        physical reach, with the lowest values for CFM PDUs
        protecting single bridges or physical links.
       "
    REFERENCE
       "802.1ag clauses 18.3, 21.4.1"
    SYNTAX Integer32 (0..7)

Dot1agCfmMDLevelOrNone ::= TEXTUAL-CONVENTION
    DISPLAY-HINT "d"
    STATUS current
    DESCRIPTION
       "Integer identifying the Maintenance Domain Level (MD Level).
        Higher numbers correspond to higher Maintenance Domains,
        those with the greatest physical reach, with the highest
        values for customers' CFM packets. Lower numbers correspond
        to lower Maintenance Domains, those with more limited
        physical reach, with the lowest values for CFM PDUs
        protecting single bridges or physical links.

        The value (-1) is reserved to indicate that no MA Level has
        been assigned.
       "
    REFERENCE
       "802.1ag clauses 18.3, 12.14.3.1.3:c"
    SYNTAX Integer32 (-1 | 0..7)

Dot1agCfmMpDirection ::= TEXTUAL-CONVENTION
    STATUS current
    DESCRIPTION
       "Indicates the direction in which the Maintenance
        association (MEP or MIP) faces on the bridge port:

        down(1)    Sends Continuity Check Messages away from the
                   MAC Relay Entity.
        up(2)      Sends Continuity Check Messages towards the
                   MAC Relay Entity.
       "
    REFERENCE
       "802.1ag clauses 12.14.6.3.2:c"
    SYNTAX INTEGER {
             down (1),
             up (2)
           }

Dot1agCfmCcmInterval ::= TEXTUAL-CONVENTION
    STATUS current
    DESCRIPTION
       "Indicates the interval at which CCMs are sent by a MEP.
        The possible values are:
        intervalInvalid(0) No CCMs are sent (disabled).
        interval300Hz(1)   CCMs are sent every 3 1/3 milliseconds
                           (300Hz).
        interval10ms(2)    CCMs are sent every 10 milliseconds.
        interval100ms(3)   CCMs are sent every 100 milliseconds.
        interval1s(4)      CCMs are sent every 1 second.
        interval10s(5)     CCMs are sent every 10 seconds.
        interval1min(6)    CCMs are sent every minute.
        interval10min(7)   CCMs are sent every 10 minutes.

        Note: enumerations start at zero to match the 'CCM Interval
        field' protocol field.
       "
    REFERENCE
       "802.1ag clauses 12.14.6.1.3:e, 20.8.1 and 21.6.1.3"
    SYNTAX INTEGER {
             intervalInvalid (0),
             interval300Hz (1),
             interval10ms (2),
             interval100ms (3),
             interval1s (4),
             interval10s (5),
             interval1min (6),
             interval10min (7)
           }

Dot1agCfmMepId ::= TEXTUAL-CONVENTION
    DISPLAY-HINT "d"
    STATUS current
    DESCRIPTION
       "Maintenance association End Point Identifier (MEPID): A small
        integer, unique over a given Maintenance Association,
        identifying a specific MEP.
       "
    REFERENCE
       "802.1ag clauses 3.19 and 19.2.1"
    SYNTAX Unsigned32 (1..8191)



MesLacpLinkProtectionValue ::= TEXTUAL-CONVENTION
    STATUS current
    DESCRIPTION
        "LACP link protection

        normal - The load is distributed on all links in the LAG.
        onePlusOne - All traffic is carried by the primary link while the other is used as a standby link in case of failure on the primary link."
    SYNTAX INTEGER {
        -- undefined (0),
        normal (0),
        onePlusOne (1) }



-- ----------------------------------------------------
-- General group
-- ----------------------------------------------------

mesGeneralConfigLastChangeTime OBJECT-TYPE
    SYNTAX      DateAndTime
    MAX-ACCESS  read-only
    STATUS      current
    DESCRIPTION
        "The time when the configuration of the MIB was
        last changed.

"
    ::= { mesGeneral 1 }

mesGeneralStateLastChangeTime OBJECT-TYPE
    SYNTAX      DateAndTime
    MAX-ACCESS  read-only
    STATUS      current
    DESCRIPTION
        "The time when the state and/or configuration of
        the MIB was last changed.

"
    ::= { mesGeneral 2 }

mesGeneralUniTableSize OBJECT-TYPE
    SYNTAX      Unsigned32
    MAX-ACCESS  read-only
    STATUS      obsolete
    DESCRIPTION
        "Size of UNI table

"
    ::= { mesGeneral 3 }

mesGeneralNniTableSize OBJECT-TYPE
    SYNTAX      Unsigned32
    MAX-ACCESS  read-only
    STATUS      obsolete
    DESCRIPTION
        "Size of NNI table

"
    ::= { mesGeneral 4 }

mesGeneralEvcTableSize OBJECT-TYPE
    SYNTAX      Unsigned32
    MAX-ACCESS  read-only
    STATUS      obsolete
    DESCRIPTION
        "Size of EVC table

"
    ::= { mesGeneral 5 }

mesGeneralBwpTableSize OBJECT-TYPE
    SYNTAX      Unsigned32
    MAX-ACCESS  read-only
    STATUS      current
    DESCRIPTION
        "Size of band width profile table

"
    ::= { mesGeneral 6 }

mesGeneralCeEvcMapTableSize OBJECT-TYPE
    SYNTAX      Unsigned32
    MAX-ACCESS  read-only
    STATUS      obsolete
    DESCRIPTION
        "Size of CE EVC map table

"
    ::= { mesGeneral 7 }

mesGeneralMepTableSize OBJECT-TYPE
    SYNTAX      Unsigned32
    MAX-ACCESS  read-only
    STATUS      obsolete
    DESCRIPTION
        "Size of MEP table

"
    ::= { mesGeneral 8 }

mesGeneralMegTableSize OBJECT-TYPE
    SYNTAX      Unsigned32
    MAX-ACCESS  read-only
    STATUS      obsolete
    DESCRIPTION
        "Size of MEG table

"
    ::= { mesGeneral 9 }

mesGeneralEvcBwpMapTableSize OBJECT-TYPE
    SYNTAX      Unsigned32
    MAX-ACCESS  read-only
    STATUS      obsolete
    DESCRIPTION
        "Size of EVC BWP map table

"
    ::= { mesGeneral 10 }

mesGeneralPortTableSize OBJECT-TYPE
    SYNTAX      Unsigned32
    MAX-ACCESS  read-only
    STATUS      current
    DESCRIPTION
        "Size of Port table

"
    ::= { mesGeneral 11 }

mesGeneralVlanMapTableSize OBJECT-TYPE
    SYNTAX      Unsigned32
    MAX-ACCESS  read-only
    STATUS      current
    DESCRIPTION
        "Size of VLAN map table

"
    ::= { mesGeneral 12 }

mesGeneralMgmtVlanTableSize OBJECT-TYPE
    SYNTAX      Unsigned32
    MAX-ACCESS  read-only
    STATUS      current
    DESCRIPTION
        "Size of MGMT VLAN table


"
    ::= { mesGeneral 13 }

mesGeneralLagTableSize OBJECT-TYPE
    SYNTAX      Unsigned32
    MAX-ACCESS  read-only
    STATUS      current
    DESCRIPTION
        "Size of LAG table


"
    ::= { mesGeneral 14 }

mesGeneralPolicingTableSize OBJECT-TYPE
    SYNTAX      Unsigned32
    MAX-ACCESS  read-only
    STATUS      current
    DESCRIPTION
        "Size of policing table


"
    ::= { mesGeneral 15 }

mesGeneralShapingTableSize OBJECT-TYPE
    SYNTAX      Unsigned32
    MAX-ACCESS  read-only
    STATUS      current
    DESCRIPTION
        "Size of shaping table


"
    ::= { mesGeneral 16 }

mesGeneralBwpMapTableSize OBJECT-TYPE
    SYNTAX      Unsigned32
    MAX-ACCESS  read-only
    STATUS      current
    DESCRIPTION
        "Size of BWP map table

"
    ::= { mesGeneral 17 }

mesGeneralCosTableSize OBJECT-TYPE
    SYNTAX      Unsigned32
    MAX-ACCESS  read-only
    STATUS      current
    DESCRIPTION
        "Size of COS table

"
    ::= { mesGeneral 18 }

mesGeneralMirroringTableSize OBJECT-TYPE
    SYNTAX      Unsigned32
    MAX-ACCESS  read-only
    STATUS      current
    DESCRIPTION
        "Size of mirroring table

"
    ::= { mesGeneral 19 }

mesGeneralVlanTagRuleTableSize OBJECT-TYPE
    SYNTAX      Unsigned32
    MAX-ACCESS  read-only
    STATUS      current
    DESCRIPTION
        "Size of VLAN tag rule table

"
    ::= { mesGeneral 20 }

mesGeneralVlanTagClassVlanTableSize OBJECT-TYPE
    SYNTAX      Unsigned32
    MAX-ACCESS  read-only
    STATUS      current
    DESCRIPTION
        "Size of VLAN tag classification VLAN table

"
    ::= { mesGeneral 21 }

mesGeneralCosProfileTableSize OBJECT-TYPE
    SYNTAX      Unsigned32
    MAX-ACCESS  read-only
    STATUS      current
    DESCRIPTION
        "Size of COS Profile table

"
    ::= { mesGeneral 22 }

mesGeneralMaidTableSize OBJECT-TYPE
    SYNTAX      Unsigned32
    MAX-ACCESS  read-only
    STATUS      current
    DESCRIPTION
        "Size of Maintainance Domain table

"
    ::= { mesGeneral 23 }

mesGeneralCfmMepTableSize OBJECT-TYPE
    SYNTAX      Unsigned32
    MAX-ACCESS  read-only
    STATUS      current
    DESCRIPTION
        "Size of CFM MEP table

"
    ::= { mesGeneral 24 }

mesGeneralErpTableSize OBJECT-TYPE
    SYNTAX      Unsigned32
    MAX-ACCESS  read-only
    STATUS      current
    DESCRIPTION
        "Size of ERP (Ethernet Ring Protection) table

"
    ::= { mesGeneral 25 }

mesGeneralClassTableSize OBJECT-TYPE
    SYNTAX      Unsigned32
    MAX-ACCESS  read-only
    STATUS      current
    DESCRIPTION
        "Size of Classification table

"
    ::= { mesGeneral 26 }

mesGeneralActionTableSize OBJECT-TYPE
    SYNTAX      Unsigned32
    MAX-ACCESS  read-only
    STATUS      current
    DESCRIPTION
        "Size of Action table

"
    ::= { mesGeneral 27 }

mesGeneralPolicyTableSize OBJECT-TYPE
    SYNTAX      Unsigned32
    MAX-ACCESS  read-only
    STATUS      current
    DESCRIPTION
        "Size of Policy table

"
    ::= { mesGeneral 28 }

mesGeneralErrorPropTableSize OBJECT-TYPE
    SYNTAX      Unsigned32
    MAX-ACCESS  read-only
    STATUS      current
    DESCRIPTION
        "Size of Error Propagation rule table.

"
    ::= { mesGeneral 29 }

mesGeneralVlanProtTableSize OBJECT-TYPE
    SYNTAX      Unsigned32
    MAX-ACCESS  read-only
    STATUS      current
    DESCRIPTION
        "Size of ERP VLAN table.

"
    ::= { mesGeneral 30 }

mesGeneralLacpTableSize OBJECT-TYPE
    SYNTAX      Unsigned32
    MAX-ACCESS  read-only
    STATUS      current
    DESCRIPTION
        "Size of LACP table.

"
    ::= { mesGeneral 31 }

mesGeneralLagStateLastChangeTime OBJECT-TYPE
    SYNTAX      DateAndTime
    MAX-ACCESS  read-only
    STATUS      current
    DESCRIPTION
         "The time when the state and/or configuration of
         the table was last changed.

"
    ::= { mesGeneral 32 }

mesGeneralLagConfigLastChangeTime OBJECT-TYPE
    SYNTAX      DateAndTime
    MAX-ACCESS  read-only
    STATUS      current
    DESCRIPTION
         "The time when the configuration of the table was
          last changed.

"
    ::= { mesGeneral 33 }

mesGeneralErpStateLastChangeTime OBJECT-TYPE
    SYNTAX      DateAndTime
    MAX-ACCESS  read-only
    STATUS      current
    DESCRIPTION
         "The time when the state and/or configuration of
          the table was last changed.

"
    ::= { mesGeneral 34 }

mesGeneralErpConfigLastChangeTime OBJECT-TYPE
    SYNTAX      DateAndTime
    MAX-ACCESS  read-only
    STATUS      current
    DESCRIPTION
         "The time when the configuration of the table was
          last changed.

"
    ::= { mesGeneral 35 }

mesGeneralMaidStateLastChangeTime OBJECT-TYPE
    SYNTAX      DateAndTime
    MAX-ACCESS  read-only
    STATUS      current
    DESCRIPTION
         "The time when the state and/or configuration of
          the table was last changed.

"
    ::= { mesGeneral 36 }

mesGeneralMaidConfigLastChangeTime OBJECT-TYPE
    SYNTAX      DateAndTime
    MAX-ACCESS  read-only
    STATUS      current
    DESCRIPTION
         "The time when the configuration of the table was
          last changed.

"
    ::= { mesGeneral 37 }

mesGeneralCfmMepStateLastChangeTime OBJECT-TYPE
    SYNTAX      DateAndTime
    MAX-ACCESS  read-only
    STATUS      current
    DESCRIPTION
         "The time when the state and/or configuration of
          the table was last changed.

"
    ::= { mesGeneral 38 }

mesGeneralCfmMepConfigLastChangeTime OBJECT-TYPE
    SYNTAX      DateAndTime
    MAX-ACCESS  read-only
    STATUS      current
    DESCRIPTION
         "The time when the configuration of the table was
          last changed.

"
    ::= { mesGeneral 39 }

mesGeneralVlanMapStateLastChangeTime OBJECT-TYPE
    SYNTAX      DateAndTime
    MAX-ACCESS  read-only
    STATUS      current
    DESCRIPTION
         "The time when the state and/or configuration of
          the table was last changed.

"
    ::= { mesGeneral 40 }

mesGeneralVlanMapConfigLastChangeTime OBJECT-TYPE
    SYNTAX      DateAndTime
    MAX-ACCESS  read-only
    STATUS      current
    DESCRIPTION
         "The time when the configuration of the table was
          last changed.

"
    ::= { mesGeneral 41 }

mesGeneralMgmtVlanStateLastChangeTime OBJECT-TYPE
    SYNTAX      DateAndTime
    MAX-ACCESS  read-only
    STATUS      current
    DESCRIPTION
         "The time when the state and/or configuration of
          the table was last changed.

"
    ::= { mesGeneral 42 }

mesGeneralMgmtVlanConfigLastChangeTime OBJECT-TYPE
    SYNTAX      DateAndTime
    MAX-ACCESS  read-only
    STATUS      current
    DESCRIPTION
         "The time when the configuration of the table was
          last changed.

"
    ::= { mesGeneral 43 }

mesGeneralClassStateLastChangeTime OBJECT-TYPE
    SYNTAX      DateAndTime
    MAX-ACCESS  read-only
    STATUS      current
    DESCRIPTION
         "The time when the state and/or configuration of
          the table was last changed.

"
    ::= { mesGeneral 44 }

mesGeneralClassConfigLastChangeTime OBJECT-TYPE
    SYNTAX      DateAndTime
    MAX-ACCESS  read-only
    STATUS      current
    DESCRIPTION
         "The time when the configuration of the table was
          last changed.

"
    ::= { mesGeneral 45 }

mesGeneralActionStateLastChangeTime OBJECT-TYPE
    SYNTAX      DateAndTime
    MAX-ACCESS  read-only
    STATUS      current
    DESCRIPTION
         "The time when the state and/or configuration of
          the table was last changed.

"
    ::= { mesGeneral 46 }

mesGeneralActionConfigLastChangeTime OBJECT-TYPE
    SYNTAX      DateAndTime
    MAX-ACCESS  read-only
    STATUS      current
    DESCRIPTION
         "The time when the configuration of the table was
          last changed.

"
    ::= { mesGeneral 47 }

mesGeneralPolicyStateLastChangeTime OBJECT-TYPE
    SYNTAX      DateAndTime
    MAX-ACCESS  read-only
    STATUS      current
    DESCRIPTION
         "The time when the state and/or configuration of
          the table was last changed.

"
    ::= { mesGeneral 48 }

mesGeneralPolicyConfigLastChangeTime OBJECT-TYPE
    SYNTAX      DateAndTime
    MAX-ACCESS  read-only
    STATUS      current
    DESCRIPTION
         "The time when the configuration of the table was
          last changed.

"
    ::= { mesGeneral 49 }

mesGeneralErrorPropStateLastChangeTime OBJECT-TYPE
    SYNTAX      DateAndTime
    MAX-ACCESS  read-only
    STATUS      current
    DESCRIPTION
         "The time when the state and/or configuration of
          the table was last changed.

"
    ::= { mesGeneral 50 }

mesGeneralErrorPropConfigLastChangeTime OBJECT-TYPE
    SYNTAX      DateAndTime
    MAX-ACCESS  read-only
    STATUS      current
    DESCRIPTION
         "The time when the configuration of the table was
          last changed.

"
    ::= { mesGeneral 51 }

mesGeneralVlanProtStateLastChangeTime OBJECT-TYPE
    SYNTAX      DateAndTime
    MAX-ACCESS  read-only
    STATUS      current
    DESCRIPTION
         "The time when the state and/or configuration of
          the table was last changed.

"
    ::= { mesGeneral 52 }

mesGeneralVlanProtConfigLastChangeTime OBJECT-TYPE
    SYNTAX      DateAndTime
    MAX-ACCESS  read-only
    STATUS      current
    DESCRIPTION
         "The time when the configuration of the table was
          last changed.

"
    ::= { mesGeneral 53 }

mesGeneralLacpStateLastChangeTime OBJECT-TYPE
    SYNTAX      DateAndTime
    MAX-ACCESS  read-only
    STATUS      current
    DESCRIPTION
         "The time when the state and/or configuration of
          the table was last changed.

"
    ::= { mesGeneral 54 }

mesGeneralLacpConfigLastChangeTime OBJECT-TYPE
    SYNTAX      DateAndTime
    MAX-ACCESS  read-only
    STATUS      current
    DESCRIPTION
         "The time when the configuration of the table was
          last changed.

"
    ::= { mesGeneral 55 }

mesGeneralPolicingStateLastChangeTime OBJECT-TYPE
    SYNTAX      DateAndTime
    MAX-ACCESS  read-only
    STATUS      current
    DESCRIPTION
         "The time when the state and/or configuration of
          the table was last changed.

"
    ::= { mesGeneral 56 }

mesGeneralPolicingConfigLastChangeTime OBJECT-TYPE
    SYNTAX      DateAndTime
    MAX-ACCESS  read-only
    STATUS      current
    DESCRIPTION
         "The time when the configuration of the table was
          last changed.

"
    ::= { mesGeneral 57 }

mesGeneralShapingStateLastChangeTime OBJECT-TYPE
    SYNTAX      DateAndTime
    MAX-ACCESS  read-only
    STATUS      current
    DESCRIPTION
         "The time when the state and/or configuration of
          the table was last changed.

"
    ::= { mesGeneral 58 }

mesGeneralShapingConfigLastChangeTime OBJECT-TYPE
    SYNTAX      DateAndTime
    MAX-ACCESS  read-only
    STATUS      current
    DESCRIPTION
         "The time when the configuration of the table was
          last changed.

"
    ::= { mesGeneral 59 }

mesGeneralCosStateLastChangeTime OBJECT-TYPE
    SYNTAX      DateAndTime
    MAX-ACCESS  read-only
    STATUS      current
    DESCRIPTION
         "The time when the state and/or configuration of
          the table was last changed.

"
    ::= { mesGeneral 60 }

mesGeneralCosConfigLastChangeTime OBJECT-TYPE
    SYNTAX      DateAndTime
    MAX-ACCESS  read-only
    STATUS      current
    DESCRIPTION
         "The time when the configuration of the table was
          last changed.

"
    ::= { mesGeneral 61 }

mesGeneralBwpMapStateLastChangeTime OBJECT-TYPE
    SYNTAX      DateAndTime
    MAX-ACCESS  read-only
    STATUS      current
    DESCRIPTION
         "The time when the state and/or configuration of
          the table was last changed.

"
    ::= { mesGeneral 62 }

mesGeneralBwpMapConfigLastChangeTime OBJECT-TYPE
    SYNTAX      DateAndTime
    MAX-ACCESS  read-only
    STATUS      current
    DESCRIPTION
         "The time when the configuration of the table was
          last changed.

"
    ::= { mesGeneral 63 }

mesGeneralMirroringStateLastChangeTime OBJECT-TYPE
    SYNTAX      DateAndTime
    MAX-ACCESS  read-only
    STATUS      current
    DESCRIPTION
         "The time when the state and/or configuration of
          the table was last changed.

"
    ::= { mesGeneral 64 }

mesGeneralMirroringConfigLastChangeTime OBJECT-TYPE
    SYNTAX      DateAndTime
    MAX-ACCESS  read-only
    STATUS      current
    DESCRIPTION
         "The time when the configuration of the table was
          last changed.

"
    ::= { mesGeneral 65 }

mesGeneralVlanTagRuleStateLastChangeTime OBJECT-TYPE
    SYNTAX      DateAndTime
    MAX-ACCESS  read-only
    STATUS      current
    DESCRIPTION
         "The time when the state and/or configuration of
          the table was last changed.

"
    ::= { mesGeneral 66 }

mesGeneralVlanTagRuleConfigLastChangeTime OBJECT-TYPE
    SYNTAX      DateAndTime
    MAX-ACCESS  read-only
    STATUS      current
    DESCRIPTION
         "The time when the configuration of the table was
          last changed.

"
    ::= { mesGeneral 67 }

mesGeneralVlanTagClassVlanStateLastChangeTime OBJECT-TYPE
    SYNTAX      DateAndTime
    MAX-ACCESS  read-only
    STATUS      current
    DESCRIPTION
         "The time when the state and/or configuration of
          the table was last changed.

"
    ::= { mesGeneral 68 }

mesGeneralVlanTagClassVlanConfigLastChangeTime OBJECT-TYPE
    SYNTAX      DateAndTime
    MAX-ACCESS  read-only
    STATUS      current
    DESCRIPTION
         "The time when the configuration of the table was
          last changed.

"
    ::= { mesGeneral 69 }

mesGeneralCosProfileStateLastChangeTime OBJECT-TYPE
    SYNTAX      DateAndTime
    MAX-ACCESS  read-only
    STATUS      current
    DESCRIPTION
         "The time when the state and/or configuration of
          the table was last changed.

"
    ::= { mesGeneral 70 }

mesGeneralCosProfileConfigLastChangeTime OBJECT-TYPE
    SYNTAX      DateAndTime
    MAX-ACCESS  read-only
    STATUS      current
    DESCRIPTION
         "The time when the configuration of the table was
          last changed.

"
    ::= { mesGeneral 71 }

mesGeneralBwpStateLastChangeTime OBJECT-TYPE
    SYNTAX      DateAndTime
    MAX-ACCESS  read-only
    STATUS      current
    DESCRIPTION
         "The time when the state and/or configuration of
          the table was last changed.

"
    ::= { mesGeneral 72 }

mesGeneralBwpConfigLastChangeTime OBJECT-TYPE
    SYNTAX      DateAndTime
    MAX-ACCESS  read-only
    STATUS      current
    DESCRIPTION
         "The time when the configuration of the table was
          last changed.

"
    ::= { mesGeneral 73 }

mesGeneralMiscStateLastChangeTime OBJECT-TYPE
    SYNTAX      DateAndTime
    MAX-ACCESS  read-only
    STATUS      current
    DESCRIPTION
         "The time when the state and/or configuration of
          the table was last changed.

"
    ::= { mesGeneral 74 }

mesGeneralMiscConfigLastChangeTime OBJECT-TYPE
    SYNTAX      DateAndTime
    MAX-ACCESS  read-only
    STATUS      current
    DESCRIPTION
         "The time when the configuration of the table was
          last changed.

"
    ::= { mesGeneral 75 }

mesGeneralPortStateLastChangeTime OBJECT-TYPE
    SYNTAX      DateAndTime
    MAX-ACCESS  read-only
    STATUS      current
    DESCRIPTION
         "The time when the state and/or configuration of
          the table was last changed.

"
    ::= { mesGeneral 76 }

mesGeneralPortConfigLastChangeTime OBJECT-TYPE
    SYNTAX      DateAndTime
    MAX-ACCESS  read-only
    STATUS      current
    DESCRIPTION
         "The time when the configuration of the table was
          last changed.

"
    ::= { mesGeneral 77 }

-- ----------------------------------------------------
-- UNI
-- ----------------------------------------------------

mesUniTable  OBJECT-TYPE
    SYNTAX      SEQUENCE OF MesUniEntry
    MAX-ACCESS  not-accessible
    STATUS      obsolete
    DESCRIPTION
        "The UNI list."
    ::= { mesUniList 1 }

mesUniEntry OBJECT-TYPE
    SYNTAX      MesUniEntry
    MAX-ACCESS  not-accessible
    STATUS      current
    DESCRIPTION
        "An entry in the UNI list.
"
    INDEX { mesUniIndex }
    ::= { mesUniTable 1 }

MesUniEntry ::=
    SEQUENCE {
        mesUniIndex                      Unsigned32,
        mesUniName                       MgmtNameString,
        mesUniDescr                      DisplayString,
        mesUniSubrack                    SubrackNumber,
        mesUniSlot                       SlotNumber,
        mesUniTxPort                     PortNumber,
        mesUniRxPort                     PortNumber,
        mesUniObjectProperty             ObjectProperty,
        mesUniAdminStatus                BoardOrInterfaceAdminStatus,
        mesUniOperStatus                 BoardOrInterfaceOperStatus,
        mesUniIdentifier                 DisplayString,
        mesUniMtuSize                    Unsigned32,
        mesUniMaxNoOfEvcs                Unsigned32,
        mesUniCurrentNoOfEvcs            Unsigned32,
        mesUniAvailableCapacity          Unsigned32,
        mesUniServiceMultiplexing        INTEGER,
        mesUniBundling                   INTEGER,
        mesUniAllToOneBundling           INTEGER,
        mesUniUntaggedCeVlanIdAssignment Unsigned32,
        mesUniAssociateBwp               CommandString,
        mesUniReleaseBwp                 CommandString,
        mesUniIngressBwProfilePerUni     INTEGER,
        mesUniIngressBwp                 DisplayString,
        mesUniEgressBwProfilePerUni      INTEGER,
        mesUniEgressBwp                  DisplayString,
        mesUniL2ControlProtocolProcessing INTEGER,
        mesUniSetupCommand               CommandString,
        mesUniCreateEvcCommand           CommandString,
        mesUniListCeVlanIdsCommand       CommandString,
        mesUniTaggingOfUntaggedFrames    INTEGER,
        mesUniCeVlanIdAssignmentCommand  CommandString,
        mesUniL2SpanningTreeProcessing   INTEGER,
        mesUniL2PauseProcessing          INTEGER,
        mesUniL2SlowProtocolsProcessing  INTEGER,
        mesUniL2PortAuthenticationProcessing INTEGER,
        mesUniL2OtherBridgeBlockProcessing INTEGER,
        mesUniL2AllLANsBridgeMgmtProcessing INTEGER,
        mesUniL2GarpProcessing          INTEGER,
        mesUniL2OamUniMeProcessing      INTEGER,
        mesUniTagTransparency           INTEGER,
        mesUniMgmtVlan                  INTEGER,
        mesUniDefineMgmtVlan            CommandString,
        mesUniMgmtVlanTagType           INTEGER,
        mesUniMgmtVlanEtherType         Unsigned32,
        mesUniMgmtVlanVlanId            Unsigned32,
        mesUniMgmtVlanPriority          Unsigned32,
        mesUniMgmtVlanMacAddress        MacAddress,
        mesUniMacInMac                   INTEGER,
        mesUniMacInMacIsid               Unsigned32,
        mesUniMacInMacDa                 DisplayString,
        mesUniDefineMac                  CommandString,
        mesUniLagStatus                  INTEGER,
        mesUniLagPortmask                Unsigned32,
        mesUniAssociateLag               CommandString }


mesUniIndex OBJECT-TYPE
    SYNTAX      Unsigned32 (1..2147483647)
    MAX-ACCESS  read-only
    STATUS      current
    DESCRIPTION
        "An arbitrary index assigned to each if entry.
"
    ::= { mesUniEntry 1 }

mesUniName OBJECT-TYPE
    SYNTAX      MgmtNameString
    MAX-ACCESS  read-only
    STATUS      current
    DESCRIPTION
        "The management name of the interface, for example
        'uni:1:2:1-2'.

"
    ::= { mesUniEntry 2 }

mesUniDescr OBJECT-TYPE
    SYNTAX      DisplayString
    MAX-ACCESS  read-write
    STATUS      current
    DESCRIPTION
        "User configurable label.

"
    DEFVAL { "" }
    ::= { mesUniEntry 3 }

mesUniSubrack OBJECT-TYPE
    SYNTAX      SubrackNumber
    MAX-ACCESS  read-only
    STATUS      current
    DESCRIPTION
        "The number of the subrack where the interface
        is located.

"
    ::= { mesUniEntry 4 }

mesUniSlot OBJECT-TYPE
    SYNTAX      SlotNumber
    MAX-ACCESS  read-only
    STATUS      current
    DESCRIPTION
        "The number of the slot where the interface is
        located.

"
    ::= { mesUniEntry 5 }

mesUniTxPort OBJECT-TYPE
    SYNTAX      PortNumber
    MAX-ACCESS  read-only
    STATUS      current
    DESCRIPTION
        "The TX-port of the interface corresponding to the
        UNI.

"
    ::= { mesUniEntry 6 }

mesUniRxPort OBJECT-TYPE
    SYNTAX      PortNumber
    MAX-ACCESS  read-only
    STATUS      current
    DESCRIPTION
        "The RX-port of the interface corresponding to the
        UNI.

"
    ::= { mesUniEntry 7 }

mesUniObjectProperty  OBJECT-TYPE
    SYNTAX      ObjectProperty
    MAX-ACCESS  read-only
    STATUS      current
    DESCRIPTION
        "Property mask.

"
    ::= { mesUniEntry 8 }

mesUniAdminStatus OBJECT-TYPE
    SYNTAX      BoardOrInterfaceAdminStatus
    MAX-ACCESS  read-write
    STATUS      current
    DESCRIPTION
        "The administrative state for the object.

        down - The object is de-activated.

        service - The object is activated but alarms
        are suppressed. Intended for use during service
        or re-configuration. When service is concluded
        adminStatus should be set to 'up' again. Note that
        there is no difference between 'up' and 'service',
        if no alarms can be raised from this object.

        up - The object will be activated when
        available. Alarms are not suppressed.

"
    DEFVAL { up }
    ::= { mesUniEntry 9 }

mesUniOperStatus OBJECT-TYPE
    SYNTAX      BoardOrInterfaceOperStatus
    MAX-ACCESS  read-only
    STATUS      current
    DESCRIPTION
        "The operational state for the object.

        notPresent - The object is not available.

        down - The object is de-activated or there are
        faults preventing its transition to the 'up' state.

        up - The object is active.

"
    DEFVAL { notPresent }
    ::= { mesUniEntry 10 }

mesUniIdentifier OBJECT-TYPE
    SYNTAX      DisplayString
    MAX-ACCESS  read-create
    STATUS      current
    DESCRIPTION
        "Unique identifier for the UNI.

"
    DEFVAL { "" }
    ::= { mesUniEntry 11 }

mesUniMtuSize OBJECT-TYPE
    SYNTAX      Unsigned32(1518..9600)
    MAX-ACCESS  read-write
    STATUS      current
    DESCRIPTION
        "The Max Transmission Unit (MTU) Size for the UNI.

"
    DEFVAL { 1518 }
    ::= { mesUniEntry 12 }

mesUniMaxNoOfEvcs OBJECT-TYPE
    SYNTAX      Unsigned32 (0..4094)
    MAX-ACCESS  read-only
    STATUS      current
    DESCRIPTION
        "The remaining number of EVCs that
        can be created on this UNI.

"
    ::= { mesUniEntry 13 }

mesUniCurrentNoOfEvcs OBJECT-TYPE
    SYNTAX      Unsigned32
    MAX-ACCESS  read-only
    STATUS      current
    DESCRIPTION
        "The current number of EVCs associated
        with this UNI.

"
    ::= { mesUniEntry 14 }

mesUniAvailableCapacity OBJECT-TYPE
    SYNTAX      Unsigned32
    MAX-ACCESS  read-only
    STATUS      current
    DESCRIPTION
        "Available (unused) bandwidth capacity at the UNI.

"
    ::= { mesUniEntry 15 }

mesUniServiceMultiplexing OBJECT-TYPE
    SYNTAX      INTEGER {
                    no (1),
                    yes (2) }
    MAX-ACCESS  read-create
    STATUS      current
    DESCRIPTION
        "Defines whether several EVCs may be associated with
         the UNI.

        no - Only one EVC can be associated with the UNI.

        yes  - Several EVCs can be associated with the UNI.

"
    DEFVAL { no }
    ::= { mesUniEntry 16 }

mesUniBundling OBJECT-TYPE
    SYNTAX      INTEGER {
                    no (1),
                    yes (2) }
    MAX-ACCESS  read-create
    STATUS      current
    DESCRIPTION
        "Defines whether several CE-VLAN IDs may be mapped to
         the same EVC.

        no - Only one CE-VLAN ID may be mapped to any given
        EVC.

        yes - Several CE-VLAN IDs may be mapped to any given
        EVC.

"
    DEFVAL { no }
    ::= { mesUniEntry 17 }

mesUniAllToOneBundling OBJECT-TYPE
    SYNTAX      INTEGER {
                    no (1),
                    yes (2) }
    MAX-ACCESS  read-create
    STATUS      current
    DESCRIPTION
        "Defines whether all CE-VLAN IDs will be mapped to
         the same EVC.

        no - Different CE-VLAN IDs may be mapped to
        different EVCs.

        yes - All CE-VLAN IDs will be mapped to the same
        EVC.

"
    DEFVAL { yes }
    ::= { mesUniEntry 18 }

mesUniUntaggedCeVlanIdAssignment OBJECT-TYPE
    SYNTAX      Unsigned32(1..4094)
    MAX-ACCESS  read-create
    STATUS      current
    DESCRIPTION
        "CE-VLAN ID assigned to untagged and priority
         tagged Service Frames.

"
    DEFVAL { 1 }
    ::= { mesUniEntry 19 }

mesUniAssociateBwp OBJECT-TYPE
    SYNTAX      CommandString
    MAX-ACCESS  read-only
    STATUS      current
    DESCRIPTION
        "Create and associate ingress or egress BW profile
        for the UNI.

         The following must be selected:
         - Direction (ingress or egress)
         - Class of Service indentifer
         - Commited Information Rate
         - Commited Burst Rate
         - Excess Information Rate
         - Excess Burst Rate

         This will create an entry in the BWP table, unless
         it already exists.

         The values must be set within certain ranges, see
         below:

         CIR+EIR          Max of CBS+EBS
         (bits/s)         (bytes)
         -------          --------------
         > 125M           4.13M
         125M - 7.81M     2.09M
         7.80M - 3.91M    1.39M
         3.90M - 1.95M    697K
         1.95M - 977K     348K
         976K - 7.63K     65.5K
         7.62K - 3.81K    43.6K
         3.81K - 1.91K    21.8K
         1.91K - 0.954K   10.8K

"
    ::= { mesUniEntry 20 }

mesUniReleaseBwp OBJECT-TYPE
    SYNTAX      CommandString
    MAX-ACCESS  read-only
    STATUS      current
    DESCRIPTION
        "Release relationship to BW profile.

"
    ::= { mesUniEntry 21 }

mesUniIngressBwProfilePerUni OBJECT-TYPE
    SYNTAX      INTEGER {
                    disabled (1),
                    enabled (2) }
    MAX-ACCESS  read-create
    STATUS      current
    DESCRIPTION
        "Defines whether the ingress BW profile is applied
         at the UNI level (instead of at the EVC level).

        disabled - BW profiling is done per EVC (or CoS).

        enabled  - BW profiling is done at UNI level.

"
    DEFVAL { disabled }
    ::= { mesUniEntry 22 }

mesUniIngressBwp OBJECT-TYPE
    SYNTAX      DisplayString
    MAX-ACCESS  read-create
    STATUS      current
    DESCRIPTION
        "The CoS Identifier for the ingress BW profile.

"
    DEFVAL { "" }
    ::= { mesUniEntry 23 }

mesUniEgressBwProfilePerUni OBJECT-TYPE
    SYNTAX      INTEGER {
                    disabled (1),
                    enabled (2) }
    MAX-ACCESS  read-create
    STATUS      current
    DESCRIPTION
        "Defines whether the egress BW profile is applied
         at the UNI level (instead of at the EVC level).

        disabled - BW profiling is done per EVC (or CoS).

        enabled  - BW profiling is done at UNI level
        Not available in this release.
"
    DEFVAL { disabled }
    ::= { mesUniEntry 24 }

mesUniEgressBwp OBJECT-TYPE
    SYNTAX      DisplayString
    MAX-ACCESS  read-create
    STATUS      current
    DESCRIPTION
        "The CoS Identifier for the egress BW profile.

        Not available in this release.
"
    DEFVAL { "" }
    ::= { mesUniEntry 25 }

mesUniL2ControlProtocolProcessing OBJECT-TYPE
    SYNTAX      INTEGER {
                    discard (1),
                    peer (2),
                    passToEvc (3),
                    peerAndPassToEvc (4) }
    MAX-ACCESS  read-write
    STATUS      deprecated
    DESCRIPTION
        "Defines how the L2-protocols shall be handled
         at the UNI.

         discard - discard all ingress frames carrying
                   L2 Control Protocols.

         passToEvc - Let the EVC decide how to handle this
                     See EVC attribute

"
    DEFVAL { passToEvc }
    ::= { mesUniEntry 26 }


mesUniSetupCommand OBJECT-TYPE
    SYNTAX      CommandString
    MAX-ACCESS  read-only
    STATUS      current
    DESCRIPTION
        "Do basic settings of the UNI.

         Identifier, type of multiplexing and type of
         bundling can be selected.

"
    ::= { mesUniEntry 27 }

mesUniCreateEvcCommand OBJECT-TYPE
    SYNTAX      CommandString
    MAX-ACCESS  read-only
    STATUS      current
    DESCRIPTION
        "Create a new EVC terminating on the UNI.

        A unique identifier, NNI to connect to, and VLAN-ID
        must be selected.

        This will create an entry in the EVC table.

"
    ::= { mesUniEntry 28 }

mesUniListCeVlanIdsCommand OBJECT-TYPE
    SYNTAX      CommandString
    MAX-ACCESS  read-only
    STATUS      current
    DESCRIPTION
        "List all used and unused CE-VLAN IDs at the UNI.

"
    ::= { mesUniEntry 29 }

mesUniTaggingOfUntaggedFrames OBJECT-TYPE
    SYNTAX      INTEGER {
                    disabled (1),
                    enabled (2) }
    MAX-ACCESS  read-create
    STATUS      current
    DESCRIPTION
        "Defines whether CE-VLAN ID may be assigned to
         untagged and priority tagged Service Frames.

        disabled - tagging is disabled.

        enabled - tagging is enabled. CE-VLAN ID is assigned
                   to untagged and priority tagged Service
                   Frames

"
    DEFVAL { disabled }
    ::= { mesUniEntry 30 }

mesUniCeVlanIdAssignmentCommand OBJECT-TYPE
    SYNTAX      CommandString
    MAX-ACCESS  read-only
    STATUS      current
    DESCRIPTION
        "Assigns CE-VLAN ID to untagged and priority
         tagged Service Frames.
         params
              Assignment enabled or disabled.
              Default CE VLAN id.
              Default CE VLAN priority.

"
    ::= { mesUniEntry 31 }

mesUniL2SpanningTreeProcessing OBJECT-TYPE
    SYNTAX      INTEGER {
                    discard (1),
                    peer (2),
                    passToEvc (3),
                    peerAndPassToEvc (4) }
    MAX-ACCESS  read-write
    STATUS      current
    DESCRIPTION
        "Defines how the L2-protocols shall be handled
         at the UNI.

         MAC dest. address: 01-80-C2-00-00-00

         discard - discard all ingress frames carrying
                   L2 Control Protocols.

         passToEvc - Let the EVC decide how to handle this
                     See EVC attribute

"
    DEFVAL { discard }
    ::= { mesUniEntry 32 }

mesUniL2PauseProcessing OBJECT-TYPE
    SYNTAX      INTEGER {
                    discard (1),
                    peer (2),
                    passToEvc (3),
                    peerAndPassToEvc (4) }
    MAX-ACCESS  read-write
    STATUS      current
    DESCRIPTION
        "Defines how the L2-protocols shall be handled
         at the UNI.

         MAC dest. address: 01-80-C2-00-00-01

         discard - discard all ingress frames carrying
                   L2 Control Protocols.

         passToEvc - Let the EVC decide how to handle this
                     See EVC attribute

"
    DEFVAL { discard }
    ::= { mesUniEntry 33 }

mesUniL2SlowProtocolsProcessing OBJECT-TYPE
    SYNTAX      INTEGER {
                    discard (1),
                    peer (2),
                    passToEvc (3),
                    peerAndPassToEvc (4) }
    MAX-ACCESS  read-write
    STATUS      current
    DESCRIPTION
        "Defines how the L2-protocols shall be handled
         at the UNI.

         MAC dest. address: 01-80-C2-00-00-02

         discard - discard all ingress frames carrying
                   L2 Control Protocols.

         passToEvc - Let the EVC decide how to handle this
                     See EVC attribute

"
    DEFVAL { discard }
    ::= { mesUniEntry 34 }

mesUniL2PortAuthenticationProcessing OBJECT-TYPE
    SYNTAX      INTEGER {
                    discard (1),
                    peer (2),
                    passToEvc (3),
                    peerAndPassToEvc (4) }
    MAX-ACCESS  read-write
    STATUS      current
    DESCRIPTION
        "Defines how the L2-protocols shall be handled
         at the UNI.

         MAC dest. address: 01-80-C2-00-00-03

         discard - discard all ingress frames carrying
                   L2 Control Protocols.

         passToEvc - Let the EVC decide how to handle this
                     See EVC attribute

"
    DEFVAL { discard }
    ::= { mesUniEntry 35 }

mesUniL2OtherBridgeBlockProcessing OBJECT-TYPE
    SYNTAX      INTEGER {
                    discard (1),
                    peer (2),
                    passToEvc (3),
                    peerAndPassToEvc (4) }
    MAX-ACCESS  read-write
    STATUS      current
    DESCRIPTION
        "Defines how the L2-protocols shall be handled
         at the UNI.

         MAC dest. address: 01-80-C2-00-00-04 -> 0F

         discard - discard all ingress frames carrying
                   L2 Control Protocols.

         passToEvc - Let the EVC decide how to handle this
                     See EVC attribute

"
    DEFVAL { discard }
    ::= { mesUniEntry 36 }

mesUniL2AllLANsBridgeMgmtProcessing OBJECT-TYPE
    SYNTAX      INTEGER {
                    discard (1),
                    peer (2),
                    passToEvc (3),
                    peerAndPassToEvc (4) }
    MAX-ACCESS  read-write
    STATUS      current
    DESCRIPTION
        "Defines how the L2-protocols shall be handled
         at the UNI.

         MAC dest. address: 01-80-C2-00-00-10

         discard - discard all ingress frames carrying
                   L2 Control Protocols.

         passToEvc - Let the EVC decide how to handle this
                     See EVC attribute

"
    DEFVAL { discard }
    ::= { mesUniEntry 37 }

mesUniL2GarpProcessing OBJECT-TYPE
    SYNTAX      INTEGER {
                    discard (1),
                    peer (2),
                    passToEvc (3),
                    peerAndPassToEvc (4) }
    MAX-ACCESS  read-write
    STATUS      current
    DESCRIPTION
        "Defines how the L2-protocols shall be handled
         at the UNI.

         MAC dest. address: 01-80-C2-00-00-20 -> 2F

         discard - discard all ingress frames carrying
                   L2 Control Protocols.

         passToEvc - Let the EVC decide how to handle this
                     See EVC attribute

"
    DEFVAL { discard }
    ::= { mesUniEntry 38 }

mesUniL2OamUniMeProcessing OBJECT-TYPE
    SYNTAX      INTEGER {
                    discard (1),
                    peer (2),
                    passToEvc (3),
                    peerAndPassToEvc (4) }
    MAX-ACCESS  read-write
    STATUS      current
    DESCRIPTION
        "Defines how the L2-protocols shall be handled
         at the UNI.

         MAC dest. address: 01-80-C2-00-00-30 -> 3F

         discard - discard all ingress frames carrying
                   L2 Control Protocols.

         passToEvc - Let the EVC decide how to handle this
                     See EVC attribute

"
    DEFVAL { discard }
    ::= { mesUniEntry 39 }

mesUniTagTransparency OBJECT-TYPE
    SYNTAX      INTEGER {
                    disabled (1),
                    enabled (2) }
    MAX-ACCESS  read-create
    STATUS      current
    DESCRIPTION
        "Defines if it should be assumed that service frames
         already have a provider tag at the UNI.
         When enabled no provider-tag is added/removed from
         the service frames.

         disabled - Provider tag is not present at the UNI.

         enabled - Provider tag exists a the UNI.

"
    DEFVAL { disabled }
    ::= { mesUniEntry 40 }

mesUniMgmtVlan OBJECT-TYPE
    SYNTAX      INTEGER {
                    disabled (1),
                    enabled (2) }
    MAX-ACCESS  read-write
    STATUS      current
    DESCRIPTION
        "Defines whether the management VLAN is enabled or
         disabled on the client port.

        disabled - Management VLAN on port is disabled.

        enabled  - Management VLAN on port is enabled.

"
    DEFVAL { disabled }
    ::= { mesUniEntry 41 }

mesUniDefineMgmtVlan OBJECT-TYPE
    SYNTAX      CommandString
    MAX-ACCESS  read-only
    STATUS      current
    DESCRIPTION
        "Procedure to define how the management
        frames shall be tagged.

        Sets tag type, ether type,
        VLAN id and priority to be used for the
        management frames.

"
    ::= { mesUniEntry 42 }

mesUniMgmtVlanTagType OBJECT-TYPE
    SYNTAX      INTEGER {
                    noTag (0),
                    qTag0x8100 (1),
                    sTag0x88a8 (2),
                    tag0x9100 (3),
                    macInMac    (4),
                    other (5)}
    MAX-ACCESS  read-create
    STATUS      current
    DESCRIPTION
        "Defines what Ether Type the tag applied
         to the mgmt VLAN shall have.

        noTag           - No mgmt VLAN is active
        qTag0x8100      - 802.1Q
        sTag0x88a8      - 802.1ad Service tag
        tag0x9100       - Proprietary, deprecated by 802.1ad
        other           - Select your own ether type

"
    DEFVAL { noTag }
    ::= { mesUniEntry 43 }

mesUniMgmtVlanEtherType OBJECT-TYPE
    SYNTAX      Unsigned32  (0..65535)
    MAX-ACCESS  read-create
    STATUS      current
    DESCRIPTION
        "Applicable if tag type is 'other'
         Choose your own Ether Type.

"
    DEFVAL { 0 }
    ::= { mesUniEntry 44 }

mesUniMgmtVlanVlanId OBJECT-TYPE
    SYNTAX      Unsigned32 (1..4094)
    MAX-ACCESS  read-create
    STATUS      current
    DESCRIPTION
        "The VLAN-ID of the management VLAN.

         This is a temporary modelling of mgmt VLAN for 9.1,
         might be changed later.

"
    DEFVAL { 4094 }
    ::= { mesUniEntry 45 }

mesUniMgmtVlanPriority OBJECT-TYPE
    SYNTAX      Unsigned32 (0..7)
    MAX-ACCESS  read-create
    STATUS      current
    DESCRIPTION
        "Priority value for the mgmt VLAN.

         This value will be used in the priority
         field of the mgmt VLAN tag.

"
    DEFVAL { 0 }
    ::= { mesUniEntry 46 }

mesUniMgmtVlanMacAddress OBJECT-TYPE
    SYNTAX      MacAddress
    MAX-ACCESS  read-only
    STATUS      current
    DESCRIPTION
        "The mac address of the port.

"
    DEFVAL { "" }
    ::= { mesUniEntry 47 }

mesUniMacInMac OBJECT-TYPE
    SYNTAX      INTEGER {
                    disabled (1),
                    enabled (2) }
    MAX-ACCESS  read-create
    STATUS      current
    DESCRIPTION
        "The Mac-in-Mac enacpsulation that can be
        enabled/disabled on the management channel.

        disabled Mac-In-Mac not used on Mgmt VLAN port.

        enabled  Mac-In-Mac used on Mgmt VLAN port.

"
    DEFVAL { disabled }
    ::= { mesUniEntry 48 }

mesUniMacInMacIsid OBJECT-TYPE
    SYNTAX      Unsigned32(256..16777214)
    MAX-ACCESS  read-create
    STATUS      current
    DESCRIPTION
        "The I-SID is the 24-bit service instance identifier
         that identifies the frame in a Provider Backbone
         Network.

"
    DEFVAL { 256 }
    ::= { mesUniEntry 49 }

mesUniMacInMacDa OBJECT-TYPE
    SYNTAX      DisplayString
    MAX-ACCESS  read-create
    STATUS      current
    DESCRIPTION
        "The Mac-in-Mac DA is the destination backbone
         Mac address.

"
    DEFVAL { "" }
    ::= { mesUniEntry 50 }

mesUniDefineMac OBJECT-TYPE
    SYNTAX      CommandString
    MAX-ACCESS  read-only
    STATUS      current
    DESCRIPTION
        "Define MAC attributes for the management channel on
        this NNI.

"
    ::= { mesUniEntry 51 }

mesUniLagStatus OBJECT-TYPE
    SYNTAX      INTEGER {
                         noLag (1),
                         master (2),
                         slave (3) }
    MAX-ACCESS  read-only
    STATUS      current
    DESCRIPTION
        "The Link Aggregation Group (LAG) status

         noLag - port does not belong to a LAG

         master - port is master in a LAG

         slave - port is slave in a LAG

"
    DEFVAL {noLag}
    ::= { mesUniEntry 52 }

mesUniLagPortmask OBJECT-TYPE
    SYNTAX      Unsigned32 (0..2147483647)
    MAX-ACCESS  read-create
    STATUS      current
    DESCRIPTION
        "

"
    DEFVAL { 0 }
    ::= { mesUniEntry 53 }

mesUniAssociateLag OBJECT-TYPE
    SYNTAX      CommandString
    MAX-ACCESS  read-only
    STATUS      current
    DESCRIPTION
        "Creates a Link Aggregation Group.

"
    ::= { mesUniEntry 54 }

-- ----------------------------------------------------
-- NNI
-- ----------------------------------------------------

mesNniTable  OBJECT-TYPE
    SYNTAX      SEQUENCE OF MesNniEntry
    MAX-ACCESS  not-accessible
    STATUS      obsolete
    DESCRIPTION
        "The NNI list."
    ::= { mesNniList 1 }

mesNniEntry OBJECT-TYPE
    SYNTAX      MesNniEntry
    MAX-ACCESS  not-accessible
    STATUS      current
    DESCRIPTION
        "An entry in the NNI list.
"
    INDEX { mesNniIndex }
    ::= { mesNniTable 1 }

MesNniEntry ::=
    SEQUENCE {
        mesNniIndex                      Unsigned32,
        mesNniName                       MgmtNameString,
        mesNniDescr                      DisplayString,
        mesNniSubrack                    SubrackNumber,
        mesNniSlot                       SlotNumber,
        mesNniTxPort                     PortNumber,
        mesNniRxPort                     PortNumber,
        mesNniObjectProperty             ObjectProperty,
        mesNniAdminStatus                BoardOrInterfaceAdminStatus,
        mesNniOperStatus                 BoardOrInterfaceOperStatus,
        mesNniIdentifier                 DisplayString,
        mesNniCurrentNoOfEvcs            Unsigned32,
        mesNniAvailableCapacity          Unsigned32,
        mesNniDefineMgmtVlan             CommandString,
        mesNniMgmtVlanTagType            INTEGER,
        mesNniMgmtVlanEtherType          Unsigned32,
        mesNniMgmtVlanVlanId             Unsigned32,
        mesNniMgmtVlanPriority           Unsigned32,
        mesNniMgmtVlanIpAddress          IpAddress,
        mesNniMgmtVlanNetMask            IpAddress,
        mesNniMgmtVlanMacAddress         MacAddress,
        mesNniSetupCommand               CommandString,
        mesNniMgmtVlan                   INTEGER,
        mesNniMacInMac                   INTEGER,
        mesNniMacInMacIsid               Unsigned32,
        mesNniMacInMacDa                 DisplayString,
        mesNniDefineMac                  CommandString,
        mesNniLagStatus                  INTEGER
    }

mesNniIndex OBJECT-TYPE
    SYNTAX      Unsigned32 (1..2147483647)
    MAX-ACCESS  read-only
    STATUS      current
    DESCRIPTION
        "An arbitrary index assigned to each if entry.
"
    ::= { mesNniEntry 1 }

mesNniName OBJECT-TYPE
    SYNTAX      MgmtNameString
    MAX-ACCESS  read-only
    STATUS      current
    DESCRIPTION
        "The management name of the interface, for example
        'nni:1:2:1-2'.

"
    ::= { mesNniEntry 2 }

mesNniDescr OBJECT-TYPE
    SYNTAX      DisplayString
    MAX-ACCESS  read-write
    STATUS      current
    DESCRIPTION
        "User configurable label.

"
    DEFVAL { "" }
    ::= { mesNniEntry 3 }

mesNniSubrack OBJECT-TYPE
    SYNTAX      SubrackNumber
    MAX-ACCESS  read-only
    STATUS      current
    DESCRIPTION
        "The number of the subrack where the interface
        is located.

"
    ::= { mesNniEntry 4 }

mesNniSlot OBJECT-TYPE
    SYNTAX      SlotNumber
    MAX-ACCESS  read-only
    STATUS      current
    DESCRIPTION
        "The number of the slot where the interface is
        located.

"
    ::= { mesNniEntry 5 }

mesNniTxPort OBJECT-TYPE
    SYNTAX      PortNumber
    MAX-ACCESS  read-only
    STATUS      current
    DESCRIPTION
        "The TX-port of the interface corresponding to the
        NNI.

"
    ::= { mesNniEntry 6 }

mesNniRxPort OBJECT-TYPE
    SYNTAX      PortNumber
    MAX-ACCESS  read-only
    STATUS      current
    DESCRIPTION
        "The RX-port of the interface corresponding to the
        NNI.

"
    ::= { mesNniEntry 7 }

mesNniObjectProperty  OBJECT-TYPE
    SYNTAX      ObjectProperty
    MAX-ACCESS  read-only
    STATUS      current
    DESCRIPTION
        "Property mask.

"
    ::= { mesNniEntry 8 }

mesNniAdminStatus OBJECT-TYPE
    SYNTAX      BoardOrInterfaceAdminStatus
    MAX-ACCESS  read-write
    STATUS      current
    DESCRIPTION
        "The administrative state for the object.

        down - The object is de-activated.

        service - The object is activated but alarms
        are suppressed. Intended for use during service
        or re-configuration. When service is concluded
        adminStatus should be set to 'up' again. Note that
        there is no difference between 'up' and 'service',
        if no alarms can be raised from this object.

        up - The object will be activated when
        available. Alarms are not suppressed.

"
    DEFVAL { up }
    ::= { mesNniEntry 9 }

mesNniOperStatus OBJECT-TYPE
    SYNTAX      BoardOrInterfaceOperStatus
    MAX-ACCESS  read-only
    STATUS      current
    DESCRIPTION
        "The operational state for the object.

        notPresent - The object is not available.

        down - The object is de-activated or there are
        faults preventing its transition to the 'up' state.

        up - The object is active.

"
    DEFVAL { notPresent }
    ::= { mesNniEntry 10 }

mesNniIdentifier OBJECT-TYPE
    SYNTAX      DisplayString
    MAX-ACCESS  read-create
    STATUS      current
    DESCRIPTION
        "Unique identifier for the NNI.

"
    DEFVAL { "" }
    ::= { mesNniEntry 11 }

mesNniCurrentNoOfEvcs OBJECT-TYPE
    SYNTAX      Unsigned32
    MAX-ACCESS  read-only
    STATUS      current
    DESCRIPTION
        "The current number of EVCs associated to this NNI.

"
    ::= { mesNniEntry 12 }

mesNniAvailableCapacity OBJECT-TYPE
    SYNTAX      Unsigned32
    MAX-ACCESS  read-only
    STATUS      current
    DESCRIPTION
        "Available (unused) bandwidth capacity at the NNI.

"
    DEFVAL { 1 }
    ::= { mesNniEntry 13 }

mesNniDefineMgmtVlan OBJECT-TYPE
    SYNTAX      CommandString
    MAX-ACCESS  read-only
    STATUS      current
    DESCRIPTION
        "Procedure to define how the management
        frames shall be tagged.

        Sets tag type, ether type,
        VLAN id and priority to be used for the
        management frames.

"
    ::= { mesNniEntry 14 }

mesNniMgmtVlanTagType OBJECT-TYPE
    SYNTAX      INTEGER {
                    noTag (0),
                    qTag0x8100 (1),
                    sTag0x88a8 (2),
                    tag0x9100 (3),
                    macInMac    (4),
                    other (5)}
    MAX-ACCESS  read-create
    STATUS      current
    DESCRIPTION
        "Defines what Ether Type the tag applied
         to the mgmt VLAN shall have.

        noTag           - No mgmt VLAN is active
        qTag0x8100      - 802.1Q
        sTag0x88a8      - 802.1ad Service tag
        tag0x9100       - Proprietary, deprecated by 802.1ad
        other           - Select your own ether type

"
    DEFVAL { noTag }
    ::= { mesNniEntry 15 }

mesNniMgmtVlanEtherType OBJECT-TYPE
    SYNTAX      Unsigned32  (0..65535)
    MAX-ACCESS  read-create
    STATUS      current
    DESCRIPTION
        "Applicable if tag type is 'other'
         Choose your own Ether Type.

"
    DEFVAL { 0 }
    ::= { mesNniEntry 16 }

mesNniMgmtVlanVlanId OBJECT-TYPE
    SYNTAX      Unsigned32 (1..4094)
    MAX-ACCESS  read-create
    STATUS      current
    DESCRIPTION
        "The VLAN-ID of the management VLAN.

         This is a temporary modelling of mgmt VLAN for 9.1,
         might be changed later.

"
    DEFVAL { 4094 }
    ::= { mesNniEntry 17 }

mesNniMgmtVlanPriority OBJECT-TYPE
    SYNTAX      Unsigned32 (0..7)
    MAX-ACCESS  read-create
    STATUS      current
    DESCRIPTION
        "Priority value for the mgmt VLAN.

         This value will be used in the priority
         field of the mgmt VLAN tag.

"
    DEFVAL { 0 }
    ::= { mesNniEntry 18 }

mesNniMgmtVlanIpAddress OBJECT-TYPE
    SYNTAX      IpAddress
    MAX-ACCESS  read-write
    STATUS      current
    DESCRIPTION
        "The IP address of the ethernet interface associated
         with the mgmt VLAN.

"
    DEFVAL { "" }
    ::= { mesNniEntry 19 }

mesNniMgmtVlanNetMask OBJECT-TYPE
    SYNTAX      IpAddress
    MAX-ACCESS  read-write
    STATUS      current
    DESCRIPTION
        "The IP net mask of the ethernet interface associated
         with the mgmt VLAN.

"
    DEFVAL { "" }
    ::= { mesNniEntry 20 }

mesNniMgmtVlanMacAddress OBJECT-TYPE
    SYNTAX      MacAddress
    MAX-ACCESS  read-only
    STATUS      current
    DESCRIPTION
        "The mac address of the port.

"
    DEFVAL { "" }
    ::= { mesNniEntry 21 }

mesNniSetupCommand OBJECT-TYPE
    SYNTAX      CommandString
    MAX-ACCESS  read-only
    STATUS      current
    DESCRIPTION
        "Do basic settings of the NNI.

         Identifier can be selected.

"
    ::= { mesNniEntry 22 }

mesNniMgmtVlan OBJECT-TYPE
    SYNTAX      INTEGER {
                    disabled (1),
                    enabled (2) }
    MAX-ACCESS  read-write
    STATUS      current
    DESCRIPTION
        "Defines whether the management VLAN is enabled or
         disabled on the line port.

        disabled - Management VLAN on port is disabled.

        enabled  - Management VLAN on is enabled.

"
    DEFVAL { disabled }
    ::= { mesNniEntry 23 }

mesNniMacInMac OBJECT-TYPE
    SYNTAX      INTEGER {
                    disabled (1),
                    enabled (2) }
    MAX-ACCESS  read-create
    STATUS      current
    DESCRIPTION
        "The Mac-in-Mac encapsulation that can be
        enabled/disabled on the management channel.

        disabled Mac-In-Mac not used on Mgmt VLAN port.

        enabled  Mac-In-Mac used on Mgmt VLAN port.

"
    DEFVAL { disabled }
    ::= { mesNniEntry 24 }

mesNniMacInMacIsid OBJECT-TYPE
    SYNTAX      Unsigned32(256..16777214)
    MAX-ACCESS  read-create
    STATUS      current
    DESCRIPTION
        "The I-SID is the 24-bit service instance identifier
         that identifies the frame in a Provider Backbone
         Network.

"
    DEFVAL { 256 }
    ::= { mesNniEntry 25 }

mesNniMacInMacDa OBJECT-TYPE
    SYNTAX      DisplayString
    MAX-ACCESS  read-create
    STATUS      current
    DESCRIPTION
        "The Mac-in-Mac DA is the destination backbone
         Mac address.

"
    DEFVAL { "" }
    ::= { mesNniEntry 26 }

mesNniDefineMac OBJECT-TYPE
    SYNTAX      CommandString
    MAX-ACCESS  read-only
    STATUS      current
    DESCRIPTION
        "Define MAC attributes for this NNI.

"
    ::= { mesNniEntry 27 }

mesNniLagStatus OBJECT-TYPE
    SYNTAX      INTEGER {
                    disabled (1),
                    enabled (2) }
    MAX-ACCESS  read-write
    STATUS      current
    DESCRIPTION
        "Defines whether a Link Aggregation Group is created
         by the two lines.

        disabled - no LAG is available.

        enabled  - the two lines belong to a LAG

"
    DEFVAL { disabled }
    ::= { mesNniEntry 28 }

-- ----------------------------------------------------
-- EVC
-- ----------------------------------------------------

mesEvcTable  OBJECT-TYPE
    SYNTAX      SEQUENCE OF MesEvcEntry
    MAX-ACCESS  not-accessible
    STATUS      obsolete
    DESCRIPTION
        "The EVC list."
    ::= { mesEvcList 1 }

mesEvcEntry OBJECT-TYPE
    SYNTAX      MesEvcEntry
    MAX-ACCESS  not-accessible
    STATUS      current
    DESCRIPTION
        "An entry in the EVC list.
"
    INDEX { mesEvcIndex }
    ::= { mesEvcTable 1 }

MesEvcEntry ::=
    SEQUENCE {
        mesEvcIndex                      Unsigned32,
        mesEvcName                       MgmtNameString,
        mesEvcDescr                      DisplayString,
        mesEvcObjectProperty             ObjectProperty,
        mesEvcAdminStatus                BoardOrInterfaceAdminStatus,
        mesEvcOperStatus                 BoardOrInterfaceOperStatus,
        mesEvcIdentifier                 DisplayString,
        mesEvcUniIdentifier              DisplayString,
        mesEvcNniIdentifier              DisplayString,
        mesEvcType                       INTEGER,
        mesEvcMtuSize                    Unsigned32,
        mesEvcFrameDeliveryUnicast       INTEGER,
        mesEvcFrameDeliveryMulticast     INTEGER,
        mesEvcFrameDeliveryBroadcast     INTEGER,
        mesEvcDefineL2Control            CommandString,
        mesEvcL2ControlProtocolDisposition INTEGER,
        mesEvcL2DestinationMacAddress    MacAddress,
        mesEvcCeVlanIdPreservation       INTEGER,
        mesEvcCosPreservation            INTEGER,
        mesEvcAssociateBwp               CommandString,
        mesEvcReleaseBwp                 CommandString,
        mesEvcIngressBwProfilePerEvc     INTEGER,
        mesEvcIngressBwp                 DisplayString,
        mesEvcEgressBwProfilePerEvc      INTEGER,
        mesEvcEgressBwp                  DisplayString,
        mesEvcCreateCeVlanIdMap          CommandString,
        mesEvcDefineProviderTag          CommandString,
        mesEvcProviderTagType            INTEGER,
        mesEvcProviderTagEtherType       Unsigned32,
        mesEvcProviderTagVlanId          Unsigned32,
        mesEvcDefineClassOfService       CommandString,
        mesEvcCoSClassification          INTEGER,
        mesEvcCoSPriority                Unsigned32,
        mesEvcInternalReference          Unsigned32,
        mesEvcRowStatus                  RowStatus,
        mesEvcQProfile                   INTEGER,
        mesEvcCeVlanIdMap                DisplayString,
        mesEvcDefaultCeVlanPriority      Unsigned32,
        mesEvcClientEgressTagVlanIdAssignment INTEGER,
        mesEvcClientEgressTagVlanId      Unsigned32,
        mesEvcTagPriorityAssignment      INTEGER,
        -- mesEvcClientEgressTagPriority         Unsigned32,
        mesEvcClientEgressTagTypeAssignment INTEGER,
        mesEvcClientEgressTagType        INTEGER,
        mesEvcClientEgressTagEtherType   Unsigned32,
        mesEvcMacInMac                   INTEGER,
        mesEvcMacInMacLtoC               INTEGER,
        mesEvcCopyIsid                   INTEGER,
        mesEvcMacInMacIsid               Unsigned32,
        mesEvcMacInMacIsidLtoC           Unsigned32,
        mesEvcMacInMacDa                 DisplayString,
        mesEvcMacInMacDaLtoC             DisplayString,
        mesEvcDefineMac                  CommandString,
        mesEvcIngressBwProfileModel      INTEGER,
        mesEvcIngressBwProfileMap        DisplayString }

mesEvcIndex OBJECT-TYPE
    SYNTAX      Unsigned32 (1..2147483647)
    MAX-ACCESS  read-only
    STATUS      current
    DESCRIPTION
        "An arbitrary index assigned to each if entry.
"
    ::= { mesEvcEntry 1 }

mesEvcName OBJECT-TYPE
    SYNTAX      MgmtNameString
    MAX-ACCESS  read-only
    STATUS      current
    DESCRIPTION
        "The management name of the interface, for example
        'evc-1'.

"
    ::= { mesEvcEntry 2 }

mesEvcDescr OBJECT-TYPE
    SYNTAX      DisplayString
    MAX-ACCESS  read-write
    STATUS      current
    DESCRIPTION
        "User configurable label.

"
    DEFVAL { "" }
    ::= { mesEvcEntry 3 }

mesEvcObjectProperty  OBJECT-TYPE
    SYNTAX      ObjectProperty
    MAX-ACCESS  read-only
    STATUS      current
    DESCRIPTION
        "Property mask.

"
    ::= { mesEvcEntry 4 }

mesEvcAdminStatus OBJECT-TYPE
    SYNTAX      BoardOrInterfaceAdminStatus
    MAX-ACCESS  read-write
    STATUS      current
    DESCRIPTION
        "The administrative state for the object.

        down - The object is de-activated.

        service - The object is activated but alarms
        are suppressed. Intended for use during service
        or re-configuration. When service is concluded
        adminStatus should be set to 'up' again.

        up - The object will be activated when
        available. Alarms are not suppressed.

"
    DEFVAL { down }
    ::= { mesEvcEntry 5 }

mesEvcOperStatus OBJECT-TYPE
    SYNTAX      BoardOrInterfaceOperStatus
    MAX-ACCESS  read-only
    STATUS      current
    DESCRIPTION
        "The operational state for the object.

        notPresent - The object is not available.

        down - The object is de-activated or there are
        faults preventing its transition to the 'up' state.

        up - The object is active.

"
    DEFVAL { notPresent }
    ::= { mesEvcEntry 6 }

mesEvcIdentifier OBJECT-TYPE
    SYNTAX      DisplayString
    MAX-ACCESS  read-create
    STATUS      current
    DESCRIPTION
        "Unique identifier for the EVC.

"
    DEFVAL { "" }
    ::= { mesEvcEntry 7 }

mesEvcUniIdentifier OBJECT-TYPE
    SYNTAX      DisplayString
    MAX-ACCESS  read-create
    STATUS      current
    DESCRIPTION
        "The UNI ID of the local UNI terminating this EVC.

        Persistent cross-reference to UNI table

"
    ::= { mesEvcEntry 8 }

mesEvcNniIdentifier OBJECT-TYPE
    SYNTAX      DisplayString
    MAX-ACCESS  read-create
    STATUS      current
    DESCRIPTION
        "The NNI ID of the local NNI terminating this EVC.

        Persistent cross-reference to NNI table

"
    ::= { mesEvcEntry 9 }

mesEvcType OBJECT-TYPE
    SYNTAX      INTEGER {
                    pointToPoint (1),
                    multiPointToMultiPoint (2) }
    MAX-ACCESS  read-create
    STATUS      current
    DESCRIPTION
        "The EVC type.

        Currently only pointToPoint EVCs
        are supported.
"
    ::= { mesEvcEntry 10 }

mesEvcMtuSize OBJECT-TYPE
    SYNTAX      Unsigned32(1518..9600)
    MAX-ACCESS  read-write
    STATUS      current
    DESCRIPTION
        "The Max Transmission Unit (MTU) Size for the EVC.

"
    DEFVAL { 1518 }
    ::= { mesEvcEntry 11 }

mesEvcFrameDeliveryUnicast OBJECT-TYPE
    SYNTAX      INTEGER {
                    discard (1),
                    deliverUnconditionally (2),
                    deliverConditionally (3) }
    MAX-ACCESS  read-write
    STATUS      current
    DESCRIPTION
        "Decides whether unicast frames should be
         delivered, or not.

        Not available in this release. Always set
        to deliverUnconditionally.
"
    DEFVAL { deliverUnconditionally }
    ::= { mesEvcEntry 12 }

mesEvcFrameDeliveryMulticast OBJECT-TYPE
    SYNTAX      INTEGER {
                    discard (1),
                    deliverUnconditionally (2),
                    deliverConditionally (3) }
    MAX-ACCESS  read-write
    STATUS      current
    DESCRIPTION
        "Decides whether multicast frames should be
         delivered, or not.

        Not available in this release. Always set
        to deliverUnconditionally.
"
    DEFVAL { deliverUnconditionally }
    ::= { mesEvcEntry 13 }

mesEvcFrameDeliveryBroadcast OBJECT-TYPE
    SYNTAX      INTEGER {
                    discard (1),
                    deliverUnconditionally (2),
                    deliverConditionally (3) }
    MAX-ACCESS  read-write
    STATUS      current
    DESCRIPTION
        "Decides whether broadcast frames should be
         delivered, or not.

        Not available in this release. Always set
        to deliverUnconditionally.
"
    DEFVAL { deliverUnconditionally }
    ::= { mesEvcEntry 14 }

mesEvcDefineL2Control OBJECT-TYPE
    SYNTAX      CommandString
    MAX-ACCESS  read-only
    STATUS      current
    DESCRIPTION
        "Define how L2 protocols will be handled for this
        EVC.

"
    ::= { mesEvcEntry 15 }

mesEvcL2ControlProtocolDisposition OBJECT-TYPE
    SYNTAX      INTEGER {
                    discard (1),
                    tunnel (2),
                    wrapMac (3) }
    MAX-ACCESS  read-create
    STATUS      current
    DESCRIPTION
        "Defines how the L2-protocols shall be handled
         for this EVC.

         discard - discard all ingress frames carrying
                   L2 Control Protocols.

         tunnel  - tunnel through the EVC.

         wrapMac - wrap MAC header with new destination
         address. Not available in this release.

"
    DEFVAL { discard }
    ::= { mesEvcEntry 16 }

mesEvcL2DestinationMacAddress OBJECT-TYPE
    SYNTAX      MacAddress
    MAX-ACCESS  read-create
    STATUS      current
    DESCRIPTION
        "Defines the wrapper destination MAC address
         for L2 control protocols.

         String representation.

         Not available in this release.
"
    DEFVAL { "" }
    ::= { mesEvcEntry 17 }

mesEvcCeVlanIdPreservation OBJECT-TYPE
    SYNTAX      INTEGER {
                    no (1),
                    yes (2) }
    MAX-ACCESS  read-write
    STATUS      current
    DESCRIPTION
        "If enabled, the egress CE-VLAN ID is the
         same as the ingress CE-VLAN ID for a given frame.

         yes - preserve CE-VLAN IDs.

         no  - the CE-VLAN ID may be mapped

"
    DEFVAL { yes }
    ::= { mesEvcEntry 18 }

mesEvcCosPreservation OBJECT-TYPE
    SYNTAX      INTEGER {
                    no (1),
                    yes (2) }
    MAX-ACCESS  read-write
    STATUS      current
    DESCRIPTION
        "If enabled, the egress Class of Service is the
         same as the ingress Class of Service for a
         given frame.

         yes - preserve Class of Service.

         no  - Class of Service may be changed

"
    DEFVAL { yes }
    ::= { mesEvcEntry 19 }


mesEvcAssociateBwp OBJECT-TYPE
    SYNTAX      CommandString
    MAX-ACCESS  read-only
    STATUS      current
    DESCRIPTION
        "Create and associate ingress or egress BW
        profile for the EVC.

        This will create an entry in the BWP table,
        unless it already exists.

"
    ::= { mesEvcEntry 20 }

mesEvcReleaseBwp OBJECT-TYPE
    SYNTAX      CommandString
    MAX-ACCESS  read-only
    STATUS      current
    DESCRIPTION
        "Release relationship to BW profile.

"
    ::= { mesEvcEntry 21 }

mesEvcIngressBwProfilePerEvc OBJECT-TYPE
    SYNTAX      INTEGER {
                    disabled (1),
                    enabled (2) }
    MAX-ACCESS  read-create
    STATUS      current
    DESCRIPTION
        "Defines whether the ingress BW profile is applied
         at the EVC level (instead of at the CoS level).

        disabled - BW profiling is done per CoS

        enabled  - BW profiling is done at EVC level

"
    DEFVAL { disabled }
    ::= { mesEvcEntry 22 }

mesEvcIngressBwp OBJECT-TYPE
    SYNTAX      DisplayString
    MAX-ACCESS  read-create
    STATUS      current
    DESCRIPTION
        "The CoS Identifier for the ingress BW profile.

"
    DEFVAL { "" }
    ::= { mesEvcEntry 23 }

mesEvcEgressBwProfilePerEvc OBJECT-TYPE
    SYNTAX      INTEGER {
                    disabled (1),
                    enabled (2) }
    MAX-ACCESS  read-create
    STATUS      current
    DESCRIPTION
        "Defines whether the egress BW profile is applied
         at the EVC level (instead of at the CoS level).

        disabled - BW profiling is done per CoS

        enabled  - BW profiling is done at EVC level

"
    DEFVAL { disabled }
    ::= { mesEvcEntry 24 }

mesEvcEgressBwp OBJECT-TYPE
    SYNTAX      DisplayString
    MAX-ACCESS  read-create
    STATUS      current
    DESCRIPTION
        "The CoS Identifier for the egress
        bandwidth profile.

"
    DEFVAL { "" }
    ::= { mesEvcEntry 25 }

mesEvcCreateCeVlanIdMap OBJECT-TYPE
    SYNTAX      CommandString
    MAX-ACCESS  read-only
    STATUS      current
    DESCRIPTION
        "Create a new map for a CE-VLAN ID associated
        with this EVC at the local UNI.

        Sets the following attributes of the map:
        Map type; single or range.
        First CE-VLAN id and (optionally) last CE-VLAN id.
        Wether to include all priorities or not.

        This will create an entry in the 'map' table.

"
    ::= { mesEvcEntry 26 }

mesEvcDefineProviderTag OBJECT-TYPE
    SYNTAX      CommandString
    MAX-ACCESS  read-only
    STATUS      current
    DESCRIPTION
        "Procedure to define how the service frames
         shall be tagged before propagated to the MEN.

         Sets the tag type, the ether type
         and the VLAN id for the uplink tag.

"
    ::= { mesEvcEntry 27 }

mesEvcProviderTagType OBJECT-TYPE
    SYNTAX      INTEGER {
                    noTag (0),
                    qTag0x8100 (1),
                    sTag0x88a8 (2),
                    tag0x9100 (3),
                    macInMac    (4),
                    other (5)}
    MAX-ACCESS  read-create
    STATUS      current
    DESCRIPTION
        "Defines what Ether Type the provider tag applied
         to the EVC shall have.

        qTag0x8100      - 802.1Q
        sTag0x88a8      - 802.1ad Service tag
        tag0x9100       - Proprietary, deprecated by 802.1ad
        other           - Select your own ether type

"
    DEFVAL { sTag0x88a8 }
    ::= { mesEvcEntry 28 }

mesEvcProviderTagEtherType OBJECT-TYPE
    SYNTAX      Unsigned32  (0..65535)
    MAX-ACCESS  read-create
    STATUS      current
    DESCRIPTION
        "Applicable if tag type is 'other'
         Choose your own Ether Type.

"
    DEFVAL { 0 }
    ::= { mesEvcEntry 29 }

mesEvcProviderTagVlanId OBJECT-TYPE
    SYNTAX      Unsigned32 (0..4094)
    MAX-ACCESS  read-create
    STATUS      current
    DESCRIPTION
        "Defines what VLAN id that shall used
         at the line egress.

"
    DEFVAL { 4094 }
    ::= { mesEvcEntry 30 }

mesEvcDefineClassOfService OBJECT-TYPE
    SYNTAX      CommandString
    MAX-ACCESS  read-only
    STATUS      current
    DESCRIPTION
        "Procedure to define how Service Frames
         shall be classified and given priority
         within the MEN.

        Not available in this release.

"
    ::= { mesEvcEntry 31 }

mesEvcCoSClassification OBJECT-TYPE
    SYNTAX      INTEGER {
                    manual (1),
                    cePriority (2),
                    dscp (3) }
    MAX-ACCESS  read-create
    STATUS      deprecated
    DESCRIPTION
        "Defines how the Class of Service of a
         given Service Frame shall be decided.

        Not available in this release.

         manual - Hard-coded for the EVC.

         cePriority - Use the Priority Code Point
         Field in the CE/VLAN tag 'Trusted port'.

         dscp - Differentiated Services Code Point.
         Not available in this release.

"
    DEFVAL { manual }
    ::= { mesEvcEntry 32 }

mesEvcCoSPriority OBJECT-TYPE
    SYNTAX      Unsigned32 (0..7)
    MAX-ACCESS  read-write
    STATUS      current
    DESCRIPTION
        "Hard-coded priority value for this EVC.

         This value will be set in the priority
         code point field of the line egress
         serice frames.

"
    DEFVAL { 0 }
    ::= { mesEvcEntry 33 }

mesEvcInternalReference OBJECT-TYPE
    SYNTAX      Unsigned32 (0..2147483647)
    MAX-ACCESS  read-create
    STATUS      current
    DESCRIPTION
        "For internal use only.

"
    DEFVAL { 0 }
    ::= { mesEvcEntry 34 }

mesEvcRowStatus OBJECT-TYPE
    SYNTAX      RowStatus
    MAX-ACCESS  read-create
    STATUS      current
    DESCRIPTION
        "Manages creation and deletion of conceptual rows.
        See also SNMPv2-TC.

        Note: The newly created object will not necessarily
        receive the same index as used in the create
        procedure.
"
    ::= { mesEvcEntry 35 }

mesEvcQProfile OBJECT-TYPE
    SYNTAX      MesQProfileId
    MAX-ACCESS  read-write
    STATUS      current
    DESCRIPTION
        "Indicates the queue profile to use for
        this EVC.

"
    DEFVAL { wrr6 }
    ::= { mesEvcEntry 36 }

mesEvcCeVlanIdMap OBJECT-TYPE
    SYNTAX      DisplayString
    MAX-ACCESS  read-only
    STATUS      current
    DESCRIPTION
        "Textual presentation of the CE-VLAN IDs
        mapped to this EVC, e.g.: '1-4094'.

"
    DEFVAL { "" }
    ::= { mesEvcEntry 37 }

mesEvcDefaultCeVlanPriority OBJECT-TYPE
    SYNTAX      Unsigned32 (0..7)
    MAX-ACCESS  read-write
    STATUS      current
    DESCRIPTION
        "The priority assigned at client egress if
        CE-VLAN CoS preservation for the EVC in
        question is disabled or when priority is set
        for an UNI in transparent mode.

"
    DEFVAL { 0 }
    ::= { mesEvcEntry 38 }

mesEvcClientEgressTagVlanIdAssignment OBJECT-TYPE
    SYNTAX      INTEGER {
                    set (1),
                    copy (2) }
    MAX-ACCESS  read-write
    STATUS      current
    DESCRIPTION
        "Defines how the VLAN id
         of a service frame shall be set
         at the client egress.

         set - Set to specified value.

         copy - Use the VLAN id from the
         original tag.

"
    DEFVAL { copy }
    ::= { mesEvcEntry 39 }

mesEvcClientEgressTagVlanId OBJECT-TYPE
    SYNTAX      Unsigned32 (0..4094)
    MAX-ACCESS  read-write
    STATUS      current
    DESCRIPTION
        "The client egress VLAN id.

"
    DEFVAL { 4094 }
    ::= { mesEvcEntry 40 }

mesEvcTagPriorityAssignment OBJECT-TYPE
    SYNTAX      INTEGER {
                    set (1),
                    preserve (2) }
    MAX-ACCESS  read-write
    STATUS      current
    DESCRIPTION
        "Defines how the priority code point field
         of a service frame shall be assigned
         at the client egress and the line egress.

         set - Set to one of the specified values.

         preserve - Use the priority code point
         field in the original tag.

"
    DEFVAL { preserve }
    ::= { mesEvcEntry 41 }

mesEvcClientEgressTagTypeAssignment OBJECT-TYPE
    SYNTAX      INTEGER {
                    set (1),
                    copy (2) }
    MAX-ACCESS  read-write
    STATUS      current
    DESCRIPTION
        "Defines how the tag type
         shall be assigned for client egress
         service frames.

         set - Set to specified value.

         copy - Use the original tag.

"
    DEFVAL { copy }
    ::= { mesEvcEntry 42 }

mesEvcClientEgressTagType OBJECT-TYPE
    SYNTAX      INTEGER {
                    noTag (0),
                    qTag0x8100 (1),
                    sTag0x88a8 (2),
                    tag0x9100 (3),
                    macInMac    (4),
                    other (5)}
    MAX-ACCESS  read-write
    STATUS      current
    DESCRIPTION
        "The tag type to be set at
        the client egress if not copied.

        qTag0x8100      - 802.1Q
        sTag0x88a8      - 802.1ad Service tag
        tag0x9100       - Proprietary, deprecated by 802.1ad
        other           - Select your own ether type

"
    DEFVAL { sTag0x88a8 }
    ::= { mesEvcEntry 43 }

mesEvcClientEgressTagEtherType OBJECT-TYPE
    SYNTAX      Unsigned32  (0..65535)
    MAX-ACCESS  read-write
    STATUS      current
    DESCRIPTION
        "Applicable if tag type is 'other'
         Choose your own Ether Type.

"
    DEFVAL { 0 }
    ::= { mesEvcEntry 44 }

mesEvcMacInMac OBJECT-TYPE
    SYNTAX      INTEGER {
                    disabled (1),
                    enabled (2) }
    MAX-ACCESS  read-create
    STATUS      current
    DESCRIPTION
        "The Mac-in-Mac encapsulation that can be enabled/disabled.

        disabled Mac-In-Mac not used on Mgmt VLAN port.

        enabled  Mac-In-Mac used on Mgmt VLAN port.

"
    DEFVAL { disabled }
    ::= { mesEvcEntry 45 }

mesEvcMacInMacLtoC OBJECT-TYPE
    SYNTAX      INTEGER {
                    disabled (1),
                    enabled (2) }
    MAX-ACCESS  read-create
    STATUS      current
    DESCRIPTION
        ".

        disabled -

        enabled  -

"
    DEFVAL { disabled }
    ::= { mesEvcEntry 46 }

mesEvcCopyIsid OBJECT-TYPE
    SYNTAX      INTEGER {
                    disabled (1),
                    enabled (2) }
    MAX-ACCESS  read-create
    STATUS      current
    DESCRIPTION
        ".

        disabled -

        enabled  -

"
    DEFVAL { disabled }
    ::= { mesEvcEntry 47 }

mesEvcMacInMacIsid OBJECT-TYPE
    SYNTAX      Unsigned32(256..16777214)
    MAX-ACCESS  read-create
    STATUS      current
    DESCRIPTION
        "The I-SID is the 24-bit service instance identifier
         that identifies the frame in a Provider Backbone Net-
         work.

"
    DEFVAL { 256 }
    ::= { mesEvcEntry 48 }

mesEvcMacInMacIsidLtoC OBJECT-TYPE
    SYNTAX      Unsigned32(256..16777214)
    MAX-ACCESS  read-create
    STATUS      current
    DESCRIPTION
        "The I-SID is the 24-bit service instance identifier
         that identifies the frame in a Provider Backbone
         Network.

"
    DEFVAL { 256 }
    ::= { mesEvcEntry 49 }

mesEvcMacInMacDa OBJECT-TYPE
    SYNTAX      DisplayString
    MAX-ACCESS  read-create
    STATUS      current
    DESCRIPTION
        "The Mac-in-Mac DA is the destination backbone
         Mac address.

"
    DEFVAL { "" }
    ::= { mesEvcEntry 50 }

mesEvcMacInMacDaLtoC OBJECT-TYPE
    SYNTAX      DisplayString
    MAX-ACCESS  read-create
    STATUS      current
    DESCRIPTION
        ".

"
    DEFVAL { "" }
    ::= { mesEvcEntry 51 }

mesEvcDefineMac OBJECT-TYPE
    SYNTAX      CommandString
    MAX-ACCESS  read-only
    STATUS      current
    DESCRIPTION
        "Define MAC attributes for this EVC.

"
    ::= { mesEvcEntry 52 }

mesEvcIngressBwProfileModel OBJECT-TYPE
    SYNTAX      INTEGER {
                        none (1),
                        bwpPerUni (2),
                        bwpPerEvc (3),
                        bwpPerCos (4) }
    MAX-ACCESS  read-only
    STATUS      current
    DESCRIPTION
        "

"
    DEFVAL { none }
    ::= { mesEvcEntry 53 }

mesEvcIngressBwProfileMap OBJECT-TYPE
    SYNTAX      DisplayString
    MAX-ACCESS  read-only
    STATUS      current
    DESCRIPTION
        "

"
    DEFVAL { "" }
    ::= { mesEvcEntry 54 }

-- ----------------------------------------------------
-- CE EVC MAP - mapping of CE-VLAN ID to EVC
-- ----------------------------------------------------

mesCeEvcMapTable  OBJECT-TYPE
    SYNTAX      SEQUENCE OF MesCeEvcMapEntry
    MAX-ACCESS  not-accessible
    STATUS      obsolete
    DESCRIPTION
        "The CE to EVC map list."
    ::= { mesCeEvcMapList 1 }

mesCeEvcMapEntry OBJECT-TYPE
    SYNTAX      MesCeEvcMapEntry
    MAX-ACCESS  not-accessible
    STATUS      current
    DESCRIPTION
        "An entry in the CE EVC map list.
"
    INDEX { mesCeEvcMapIndex }
    ::= { mesCeEvcMapTable 1 }

MesCeEvcMapEntry ::=
    SEQUENCE {
        mesCeEvcMapIndex                      Unsigned32,
        mesCeEvcMapName                       MgmtNameString,
        mesCeEvcMapObjectProperty             ObjectProperty,
        mesCeEvcMapType                       INTEGER,
        mesCeEvcMapVlanIdRangeLower           Unsigned32,
        mesCeEvcMapVlanIdRangeUpper           Unsigned32,
        mesCeEvcMapEvcId                      MgmtNameString,
        mesCeEvcMapInternalReference          Unsigned32,
        mesCeEvcMapRowStatus                  RowStatus,
        mesCeEvcMapPrio0Included              INTEGER,
        mesCeEvcMapPrio1Included              INTEGER,
        mesCeEvcMapPrio2Included              INTEGER,
        mesCeEvcMapPrio3Included              INTEGER,
        mesCeEvcMapPrio4Included              INTEGER,
        mesCeEvcMapPrio5Included              INTEGER,
        mesCeEvcMapPrio6Included              INTEGER,
        mesCeEvcMapPrio7Included              INTEGER,
        mesCeEvcMapDefaultCeVlanId            Unsigned32,
        mesCeEvcMapPrioIncluded               Unsigned32 }

mesCeEvcMapIndex OBJECT-TYPE
    SYNTAX      Unsigned32 (1..2147483647)
    MAX-ACCESS  read-only
    STATUS      current
    DESCRIPTION
        "An arbitrary index assigned to each if entry.
"
    ::= { mesCeEvcMapEntry 1 }

mesCeEvcMapName OBJECT-TYPE
    SYNTAX      MgmtNameString
    MAX-ACCESS  read-only
    STATUS      current
    DESCRIPTION
        "The management name of the map, for example
        'map-1'.

"
    ::= { mesCeEvcMapEntry 2 }

mesCeEvcMapObjectProperty  OBJECT-TYPE
    SYNTAX      ObjectProperty
    MAX-ACCESS  read-only
    STATUS      current
    DESCRIPTION
        "Property mask.

"
    ::= { mesCeEvcMapEntry 3 }

mesCeEvcMapType OBJECT-TYPE
    SYNTAX      INTEGER {
                        single (1),
                        range (2) }
    MAX-ACCESS  read-create
    STATUS      current
    DESCRIPTION
        "CE-VLAN ID that shall be mapped to EVC.
         Specifies the lower end of the range.

"
    ::= { mesCeEvcMapEntry 4 }

mesCeEvcMapVlanIdRangeLower OBJECT-TYPE
    SYNTAX      Unsigned32 (0..4095)
    MAX-ACCESS  read-create
    STATUS      current
    DESCRIPTION
        "CE-VLAN ID that shall be mapped to the EVC.
         Specifies the lower end of the range.

"
    DEFVAL { 1 }
    ::= { mesCeEvcMapEntry 5 }

mesCeEvcMapVlanIdRangeUpper OBJECT-TYPE
    SYNTAX      Unsigned32 (0..4095)
    MAX-ACCESS  read-create
    STATUS      current
    DESCRIPTION
        "CE-VLAN ID that shall be mapped to the EVC.
         Specifies the upper end of the range.

"
    DEFVAL { 1 }
    ::= { mesCeEvcMapEntry 6 }

mesCeEvcMapEvcId OBJECT-TYPE
    SYNTAX      MgmtNameString
    MAX-ACCESS  read-create
    STATUS      current
    DESCRIPTION
        "Specifies the identifier of the EVC that the
         CE-VLAN ID shall be mapped to.

         Persistent cross reference.

"
    ::= { mesCeEvcMapEntry 7 }

mesCeEvcMapInternalReference OBJECT-TYPE
    SYNTAX      Unsigned32 (0..2147483647)
    MAX-ACCESS  read-create
    STATUS      current
    DESCRIPTION
        "For internal use only.

"
    DEFVAL { 0 }
    ::= { mesCeEvcMapEntry 8 }

mesCeEvcMapRowStatus OBJECT-TYPE
    SYNTAX      RowStatus
    MAX-ACCESS  read-create
    STATUS      current
    DESCRIPTION
        "Manages creation and deletion of conceptual rows.
        See also SNMPv2-TC.

        Note: The newly created object will not necessarily
        receive the same index as used in the create
        procedure.
"
    ::= { mesCeEvcMapEntry 9 }

mesCeEvcMapPrio0Included OBJECT-TYPE
    SYNTAX      INTEGER {
                    no (1),
                    yes (2) }
    MAX-ACCESS  read-write
    STATUS      current
    DESCRIPTION
        "Include frames tagged with priority 0.

"
    DEFVAL { yes }
    ::= { mesCeEvcMapEntry 10 }

mesCeEvcMapPrio1Included OBJECT-TYPE
    SYNTAX      INTEGER {
                    no (1),
                    yes (2) }
    MAX-ACCESS  read-write
    STATUS      current
    DESCRIPTION
        "Include frames tagged with priority 1.

"
    DEFVAL { yes }
    ::= { mesCeEvcMapEntry 11 }

mesCeEvcMapPrio2Included OBJECT-TYPE
    SYNTAX      INTEGER {
                    no (1),
                    yes (2) }
    MAX-ACCESS  read-write
    STATUS      current
    DESCRIPTION
        "Include frames tagged with priority 2.

"
    DEFVAL { yes }
    ::= { mesCeEvcMapEntry 12 }

mesCeEvcMapPrio3Included OBJECT-TYPE
    SYNTAX      INTEGER {
                    no (1),
                    yes (2) }
    MAX-ACCESS  read-write
    STATUS      current
    DESCRIPTION
        "Include frames tagged with priority 3.

"
    DEFVAL { yes }
    ::= { mesCeEvcMapEntry 13 }

mesCeEvcMapPrio4Included OBJECT-TYPE
    SYNTAX      INTEGER {
                    no (1),
                    yes (2) }
    MAX-ACCESS  read-write
    STATUS      current
    DESCRIPTION
        "Include frames tagged with priority 4.

"
    DEFVAL { yes }
    ::= { mesCeEvcMapEntry 14 }

mesCeEvcMapPrio5Included OBJECT-TYPE
    SYNTAX      INTEGER {
                    no (1),
                    yes (2) }
    MAX-ACCESS  read-write
    STATUS      current
    DESCRIPTION
        "Include frames tagged with priority 5.

"
    DEFVAL { yes }
    ::= { mesCeEvcMapEntry 15 }

mesCeEvcMapPrio6Included OBJECT-TYPE
    SYNTAX      INTEGER {
                    no (1),
                    yes (2) }
    MAX-ACCESS  read-write
    STATUS      current
    DESCRIPTION
        "Include frames tagged with priority 6.

"
    DEFVAL { yes }
    ::= { mesCeEvcMapEntry 16 }

mesCeEvcMapPrio7Included OBJECT-TYPE
    SYNTAX      INTEGER {
                    no (1),
                    yes (2) }
    MAX-ACCESS  read-write
    STATUS      current
    DESCRIPTION
        "Include frames tagged with priority 7.

"
    DEFVAL { yes }
    ::= { mesCeEvcMapEntry 17 }

mesCeEvcMapDefaultCeVlanId OBJECT-TYPE
    SYNTAX      Unsigned32 (0..4095)
    MAX-ACCESS  read-only
    STATUS      current
    DESCRIPTION
        "The default CE-VLAN ID for untagged frames.

"
    ::= { mesCeEvcMapEntry 18 }

mesCeEvcMapPrioIncluded OBJECT-TYPE
    SYNTAX      Unsigned32 (0..255)
    MAX-ACCESS  read-create
    STATUS      current
    DESCRIPTION
        "Include frames tagged with priority 0..7.  Least
         significant bit is 1 if prioOIncluded is yes
         otherwise 0, next bit is 1 if prio1Included is
         yes...

"
    DEFVAL { 255 }
    ::= { mesCeEvcMapEntry 19 }

-- ----------------------------------------------------
-- BWP - band-width profile
-- ----------------------------------------------------

mesBwpTable  OBJECT-TYPE
    SYNTAX      SEQUENCE OF MesBwpEntry
    MAX-ACCESS  not-accessible
    STATUS      current
    DESCRIPTION
        "The BWP list."
    ::= { mesBwpList 1 }

mesBwpEntry OBJECT-TYPE
    SYNTAX      MesBwpEntry
    MAX-ACCESS  not-accessible
    STATUS      current
    DESCRIPTION
        "An entry in the BWP list.
"
    INDEX { mesBwpIndex }
    ::= { mesBwpTable 1 }

MesBwpEntry ::=
    SEQUENCE {
        mesBwpIndex                      Unsigned32,
        mesBwpName                       MgmtNameString,
        mesBwpObjectProperty             ObjectProperty,
        mesBwpCoSIdentifier              MgmtNameString,
        mesBwpCir                        Unsigned32,
        mesBwpCbs                        Unsigned32,
        mesBwpEir                        Unsigned32,
        mesBwpEbs                        Unsigned32,
        mesBwpCouplingFlag               Unsigned32,
        mesBwpColorMode                  INTEGER,
        mesBwpInternalReference          Unsigned32,
        mesBwpRowStatus                  RowStatus,
        mesBwpServiceId                  ServiceIdWithNotUsed,
        mesBwpPolicerId                  Integer32,
        mesBwpSubrack                    SubrackNumber,
        mesBwpSlot                       SlotNumber}

mesBwpIndex OBJECT-TYPE
    SYNTAX      Unsigned32 (1..2147483647)
    MAX-ACCESS  read-only
    STATUS      current
    DESCRIPTION
        "An arbitrary index assigned to each BWP entry.
"
    ::= { mesBwpEntry 1 }

mesBwpName OBJECT-TYPE
    SYNTAX      MgmtNameString
    MAX-ACCESS  read-only
    STATUS      current
    DESCRIPTION
        "The management name of the BWP, for example
        'mef:1:4:id'.

"
    ::= { mesBwpEntry 2 }

mesBwpObjectProperty  OBJECT-TYPE
    SYNTAX      ObjectProperty
    MAX-ACCESS  read-only
    STATUS      current
    DESCRIPTION
        "Property mask.

"
    ::= { mesBwpEntry 3 }

mesBwpCoSIdentifier OBJECT-TYPE
    SYNTAX      MgmtNameString(SIZE(1..24))
    MAX-ACCESS  read-create
    STATUS      current
    DESCRIPTION
        "The Class of Service identifier associated with this
        profile.

         This attribute can be written via SNMP.

"
    DEFVAL { "" }
    ::= { mesBwpEntry 4 }

mesBwpCir OBJECT-TYPE
    SYNTAX      Unsigned32 (0..100000000)
    MAX-ACCESS  read-write
    STATUS      current
    DESCRIPTION
        "The Committed Information Rate of this profile.
        The average rate in bits/s up to which the
        network delivers service frames and meets the
        defined performance objectives.

        This attribute can be written via SNMP.

"
    DEFVAL { 0 }
    ::= { mesBwpEntry 5 }

mesBwpCbs OBJECT-TYPE
    SYNTAX      Unsigned32 (0..2147483647)
    MAX-ACCESS  read-write
    STATUS      current
    DESCRIPTION
        "The Committed Burst Size of this profile.
        The maximum number of bytes available for
        a burst sent at UNI speed to remain CIR-conformant.

        Ex: 100 mBit/s * 100 ms = 1250 kB
        1 Gbit/s   * 32  ms = 4000 kB
            1 Gbit/s   * 10  ms = 1250 kB
            10 Gbit/s  * 1   ms = 1250 kB

"
    DEFVAL { 0 }
    ::= { mesBwpEntry 6 }

mesBwpEir OBJECT-TYPE
    SYNTAX      Unsigned32 (0..100000000)
    MAX-ACCESS  read-write
    STATUS      current
    DESCRIPTION
        "The Excess Information Rate of this profile.
        The average rate in bits/s up to which the
        network may deliver service frames without
        any performance objectives.

        This value must be set within certain ranges, see
        help text for 'Committed info rate'.

        This attribute can be written via SNMP.

"
    DEFVAL { 0 }
    ::= { mesBwpEntry 7 }

mesBwpEbs OBJECT-TYPE
    SYNTAX      Unsigned32 (0..2147483647)
    MAX-ACCESS  read-write
    STATUS      current
    DESCRIPTION
        "The Excess Burst Size of this profile.
        The maximum number of bytes available for
        a burst sent at UNI speed to remain EIR-conformant.

        Ex: 100 mBit/s * 100 ms = 1250 kB
        1 Gbit/s   * 32  ms = 4000 kB
        1 Gbit/s   * 10  ms = 1250 kB
        10 Gbit/s  * 1   ms = 1250 kB

"
    DEFVAL { 0 }
    ::= { mesBwpEntry 8 }

mesBwpCouplingFlag OBJECT-TYPE
    SYNTAX      Unsigned32 (0..1)
    MAX-ACCESS  read-only
    STATUS      current
    DESCRIPTION
        "The Coupling Flag for this profile.

"
    DEFVAL { 0 }
    ::= { mesBwpEntry 9 }

mesBwpColorMode OBJECT-TYPE
    SYNTAX      INTEGER {
                        colorAware (1),
                        colorBlind (2)
                }
    MAX-ACCESS  read-write
    STATUS      current
    DESCRIPTION
        "In color blind mode, the outgoing frame color is
        based only on the profile status of each bucket. In
        color aware mode, the outgoing frame color is based
        on the incoming color and the profile status of each
        bucket. The incoming color is derived from the
        ingress classification stage.

        This attribute can be written via SNMP.

"
    DEFVAL { colorAware }
    ::= { mesBwpEntry 10 }

mesBwpInternalReference OBJECT-TYPE
    SYNTAX      Unsigned32 (0..2147483647)
    MAX-ACCESS  read-create
    STATUS      current
    DESCRIPTION
        "For internal use only.

"
    DEFVAL { 0 }
    ::= { mesBwpEntry 11 }

mesBwpRowStatus OBJECT-TYPE
    SYNTAX      RowStatus
    MAX-ACCESS  read-create
    STATUS      current
    DESCRIPTION
        "Manages creation and deletion of conceptual rows.
        See also SNMPv2-TC.

        Note: The newly created object will not necessarily
        receive the same index as used in the create
        procedure.
        This attribute can be written via SNMP.

"
    ::= { mesBwpEntry 12 }

mesBwpServiceId OBJECT-TYPE
    SYNTAX      ServiceIdWithNotUsed
    MAX-ACCESS  read-write
    STATUS      current
    DESCRIPTION
        "Service ID is used by TNM for multi-layer
        service and network management.
        Default value is -1. All objects that created
        from ENM will have default service ID.
        Change of the service ID may affect
        TNM service mappings.
"
    DEFVAL { -1 }
    ::= { mesBwpEntry 13 }

mesBwpPolicerId OBJECT-TYPE
    SYNTAX      Integer32   (-1..2147483647)
    MAX-ACCESS  read-create
    STATUS      current
    DESCRIPTION
        "Unique persistent identifier for MEF policer and Internal reference for
        the MEF policer in the traffic unit.
"
    DEFVAL { -1 }
    ::= { mesBwpEntry 14 }

mesBwpSubrack OBJECT-TYPE
    SYNTAX      SubrackNumber
    MAX-ACCESS  read-create
    STATUS      current
    DESCRIPTION
        "The number of the subrack where the policer is located.

"
    ::= { mesBwpEntry 15 }

mesBwpSlot OBJECT-TYPE
    SYNTAX      SlotNumber
    MAX-ACCESS  read-create
    STATUS      current
    DESCRIPTION
        "The number of the slot where the policer is located.

"
    ::= { mesBwpEntry 16 }


-- ----------------------------------------------------
-- Queue profiles
-- ----------------------------------------------------

mesQProfileTable  OBJECT-TYPE
    SYNTAX      SEQUENCE OF MesQProfileEntry
    MAX-ACCESS  not-accessible
    STATUS      obsolete
    DESCRIPTION
        "The queue profile list."
    ::= { mesQProfileList 1 }

mesQProfileEntry OBJECT-TYPE
    SYNTAX      MesQProfileEntry
    MAX-ACCESS  not-accessible
    STATUS      current
    DESCRIPTION
        "An entry in the queue profile list.
"
    INDEX { mesQProfileIndex }
    ::= { mesQProfileTable 1 }

MesQProfileEntry ::=
    SEQUENCE {
        mesQProfileIndex                 Unsigned32,
        mesQProfileName                  MgmtNameString,
        mesQProfileObjectProperty        ObjectProperty,
        mesQProfileId                    INTEGER,
        mesQProfileType                  INTEGER,
        mesQProfileWeight                Unsigned32,
        mesQProfileGreenLowThreshold     Unsigned32,
        mesQProfileGreenHighThreshold    Unsigned32,
        mesQProfileGreenDropProbability  Unsigned32,
        mesQProfileYellowLowThreshold    Unsigned32,
        mesQProfileYellowHighThreshold   Unsigned32,
        mesQProfileYellowDropProbability Unsigned32,
        mesQProfileInternalReference     Unsigned32 }

        -- mesQProfileLowThresholdRed    Unsigned32,
        -- mesQProfileHighThresholdRed   Unsigned32,
        -- mesQProfileDropProbabilityRed Unsigned32,

mesQProfileIndex OBJECT-TYPE
    SYNTAX      Unsigned32 (1..2147483647)
    MAX-ACCESS  read-only
    STATUS      current
    DESCRIPTION
        "An arbitrary index assigned to each Q Profile entry.
"
    ::= { mesQProfileEntry 1 }

mesQProfileName OBJECT-TYPE
    SYNTAX      MgmtNameString
    MAX-ACCESS  read-only
    STATUS      current
    DESCRIPTION
        "The management name of the queue profile,
        for example 'wrr1:1:3'.

"
    ::= { mesQProfileEntry 2 }

mesQProfileObjectProperty  OBJECT-TYPE
    SYNTAX      ObjectProperty
    MAX-ACCESS  read-only
    STATUS      current
    DESCRIPTION
        "Property mask.

"
    ::= { mesQProfileEntry 3 }

mesQProfileId OBJECT-TYPE
    SYNTAX      MesQProfileId
    MAX-ACCESS  read-only
    STATUS      current
    DESCRIPTION
        "Queue profile id.

"
    ::= { mesQProfileEntry 4 }

mesQProfileType OBJECT-TYPE
    SYNTAX      INTEGER {
                    strictPriority (1),
                    roundRobin (2),
                    weightedRoundRobin (3) }
    MAX-ACCESS  read-only
    STATUS      current
    DESCRIPTION
        "Type of queue profile.

"
    DEFVAL { strictPriority }
    ::= { mesQProfileEntry 5 }

mesQProfileWeight OBJECT-TYPE
    SYNTAX      Unsigned32 (1..127)
    MAX-ACCESS  read-write
    STATUS      current
    DESCRIPTION
        "The weight for this queue profile.

        Only applicable for weighted round-robin
        type of queues.

"
    DEFVAL { 63 }
    ::= { mesQProfileEntry 6 }

mesQProfileGreenLowThreshold OBJECT-TYPE
    SYNTAX      Unsigned32 (9600..524288)
    MAX-ACCESS  read-write
    STATUS      current
    DESCRIPTION
        "Low threshold queue size in bytes
        for frames classified as green.

"
    DEFVAL { 81920 }
    ::= { mesQProfileEntry 7 }

mesQProfileGreenHighThreshold OBJECT-TYPE
    SYNTAX      Unsigned32 (9600..524288)
    MAX-ACCESS  read-write
    STATUS      current
    DESCRIPTION
        "High threshold queue size in bytes
        for frames classified as green.

"
    DEFVAL { 163840 }
    ::= { mesQProfileEntry 8 }

mesQProfileGreenDropProbability OBJECT-TYPE
    SYNTAX      Unsigned32 (1..100)
    MAX-ACCESS  read-write
    STATUS      current
    DESCRIPTION
        "The probability for frames classified
        as green to be dropped when exceeding
        the low threshold.

"
    DEFVAL { 77 }
    ::= { mesQProfileEntry 9 }

mesQProfileYellowLowThreshold OBJECT-TYPE
    SYNTAX      Unsigned32 (9600..524288)
    MAX-ACCESS  read-write
    STATUS      current
    DESCRIPTION
        "Low threshold queue size in bytes for
        frames classified as yellow.

"
    DEFVAL { 40960 }
    ::= { mesQProfileEntry 10 }

mesQProfileYellowHighThreshold OBJECT-TYPE
    SYNTAX      Unsigned32 (9600..524288)
    MAX-ACCESS  read-write
    STATUS      current
    DESCRIPTION
        "High threshold queue size in bytes for
        frames classified as yellow.

"
    DEFVAL { 81920 }
    ::= { mesQProfileEntry 11 }

mesQProfileYellowDropProbability OBJECT-TYPE
    SYNTAX      Unsigned32 (1..100)
    MAX-ACCESS  read-write
    STATUS      current
    DESCRIPTION
        "The probability for frames classified
        as yellow to be dropped when exceeding
        the low threshold.

"
    DEFVAL { 85 }
    ::= { mesQProfileEntry 12 }

mesQProfileInternalReference OBJECT-TYPE
    SYNTAX      Unsigned32 (0..2147483647)
    MAX-ACCESS  read-create
    STATUS      current
    DESCRIPTION
        "For internal use only.

"
    DEFVAL { 0 }
    ::= { mesQProfileEntry 13 }


-- ----------------------------------------------------
-- Maintenance entity group end points (MEP)
-- ----------------------------------------------------

mesMepTable  OBJECT-TYPE
    SYNTAX      SEQUENCE OF MesMepEntry
    MAX-ACCESS  not-accessible
    STATUS      obsolete
    DESCRIPTION
        "The maintenance entity group end point (MEP) list."
    ::= { mesMepList 1 }

mesMepEntry OBJECT-TYPE
    SYNTAX      MesMepEntry
    MAX-ACCESS  not-accessible
    STATUS      current
    DESCRIPTION
        "An entry in the MEP list.
"
    INDEX { mesMepIndex }
    ::= { mesMepTable 1 }

MesMepEntry ::=
    SEQUENCE {
        mesMepIndex                 Unsigned32,
        mesMepName                  MgmtNameString,
        mesMepObjectProperty        ObjectProperty,
        mesMepInternalReference     Unsigned32,
        mesMepMeIdentifier          MgmtNameString,
        mesMepAdminStatus           BoardOrInterfaceAdminStatus,
        mesMepOperStatus            BoardOrInterfaceOperStatus,
        mesMepTransmissionInterval  Unsigned32,
        mesMepLossOfContinuity      FaultStatus,
        mesMepUnexpectedMegId       FaultStatus,
        mesMepUnexpectedTransmissionInterval FaultStatus,
        mesMepRemoteDefectIndication FaultStatus,
        mesMepUnexpectedOpCode      FaultStatus,
        mesMepAlarmIndicationSignal FaultStatus,
        mesMepMegIdFormatReceived   INTEGER,
        mesMepMegIdIccReceived      DisplayString,
        mesMepMegIdReceived         OCTET STRING,
        mesMepId                    Unsigned32,
        mesMepIdExpected            Unsigned32,
        mesMepIdReceived            Unsigned32,
        mesMepUnexpectedMepId       FaultStatus,
        mesMepUnexpectedMegLevel    FaultStatus,
        mesMepMegId                 OCTET STRING,
        mesMepMegIdFormat           INTEGER,
        mesMepMegIdIcc              DisplayString }

mesMepIndex OBJECT-TYPE
    SYNTAX      Unsigned32 (1..2147483647)
    MAX-ACCESS  read-only
    STATUS      current
    DESCRIPTION
        "An arbitrary index assigned to each MEP entry.
"
    ::= { mesMepEntry 1 }

mesMepName OBJECT-TYPE
    SYNTAX      MgmtNameString
    MAX-ACCESS  read-only
    STATUS      current
    DESCRIPTION
        "The management name of the maintenance entity
        group end point, for example 'mep:evc:1:1:3'.

"
    ::= { mesMepEntry 2 }

mesMepObjectProperty  OBJECT-TYPE
    SYNTAX      ObjectProperty
    MAX-ACCESS  read-only
    STATUS      current
    DESCRIPTION
        "Property mask.

"
    ::= { mesMepEntry 3 }

mesMepInternalReference OBJECT-TYPE
    SYNTAX      Unsigned32 (0..2147483647)
    MAX-ACCESS  read-create
    STATUS      current
    DESCRIPTION
        "For internal use only.

"
    DEFVAL { 0 }
    ::= { mesMepEntry 4 }

mesMepMeIdentifier OBJECT-TYPE
    SYNTAX      MgmtNameString
    MAX-ACCESS  read-create
    STATUS      current
    DESCRIPTION
        "The identifier for the object associated
        with this MEP.

"
    DEFVAL { "" }
    ::= { mesMepEntry 5 }

mesMepAdminStatus OBJECT-TYPE
    SYNTAX      BoardOrInterfaceAdminStatus
    MAX-ACCESS  read-write
    STATUS      current
    DESCRIPTION
        "The administrative state for the object.

        down - The object is de-activated.

        service - The object is activated but alarms
        are suppressed. Intended for use during service
        or re-configuration. When service is concluded
        adminStatus should be set to 'up' again.

        up - The object will be activated when
        available. Alarms are not suppressed.

"
    DEFVAL { down }
    ::= { mesMepEntry 6 }

mesMepOperStatus OBJECT-TYPE
    SYNTAX      BoardOrInterfaceOperStatus
    MAX-ACCESS  read-only
    STATUS      current
    DESCRIPTION
        "The operational state for the object.

        notPresent - The object is not available.

        down - The object is de-activated or there are
        faults preventing its transition to the 'up' state.

        up - The object is active.

"
    DEFVAL { notPresent }
    ::= { mesMepEntry 7 }

mesMepTransmissionInterval OBJECT-TYPE
    SYNTAX      Unsigned32 (3..600000)
    MAX-ACCESS  read-write
    STATUS      current
    DESCRIPTION
        "Transmission interval in milliseconds.
        Rounded up to the nearest supported value.

        3 ms (not yet supported)
        10 ms (not yet supported)
        100 ms (not yet supported)
        1 s
        10 s
        1 min
        10 min

"
    DEFVAL { 1000 }
    ::= { mesMepEntry 8 }

mesMepLossOfContinuity OBJECT-TYPE
    SYNTAX      FaultStatus
    MAX-ACCESS  read-only
    STATUS      current
    DESCRIPTION
        "Loss of continuity.

        A: Continuity check messages are not received
        from the peer MEP within 3.5 times the
        transmission interval.

        D: Messages are recevied from the peer MEP.

"
    ::= { mesMepEntry 9 }

mesMepUnexpectedMegId OBJECT-TYPE
    SYNTAX      FaultStatus
    MAX-ACCESS  read-only
    STATUS      current
    DESCRIPTION
        "Unexpected MEG identity.

        A: The received OAM messages contains an
        unexpected MEG identity.

        D: The OAM messages contains an
        expected MEG identity.

"
    ::= { mesMepEntry 10 }

mesMepUnexpectedTransmissionInterval OBJECT-TYPE
    SYNTAX      FaultStatus
    MAX-ACCESS  read-only
    STATUS      current
    DESCRIPTION
        "Unexpected transmission interval.

        A: The recevied OAM messages contains an
        unexpected transmission interval.

        D: The OAM messages contains the
        expected transmission interval.

"
    ::= { mesMepEntry 11 }

mesMepRemoteDefectIndication
OBJECT-TYPE
    SYNTAX      FaultStatus
    MAX-ACCESS  read-only
    STATUS      current
    DESCRIPTION
        "Remote defect indication.

        A: The recevied OAM messages contains a
        remote defect indication.

        D: Remote defect indication is not
        received.

"
    ::= { mesMepEntry 12 }

mesMepUnexpectedOpCode OBJECT-TYPE
    SYNTAX      FaultStatus
    MAX-ACCESS  read-only
    STATUS      current
    DESCRIPTION
        "Unexpected operation code.

        A: The recevied OAM messages contains an
        unexpected operation code.

        D: The OAM messages contains an
        expected operation code.

"
    ::= { mesMepEntry 13 }

mesMepAlarmIndicationSignal OBJECT-TYPE
    SYNTAX      FaultStatus
    MAX-ACCESS  read-only
    STATUS      current
    DESCRIPTION
        "Alarm indication signal.

        A: The received OAM messages contains an
        alarm indication signal.

        D: Alarm indication signal is not
        received.

"
    ::= { mesMepEntry 14 }

mesMepMegIdFormatReceived OBJECT-TYPE
    SYNTAX      INTEGER {
                    other (0),
                    icc (32) }
    MAX-ACCESS  read-only
    STATUS      current
    DESCRIPTION
        "The Management Entity Group (MEG) identifier
        format. The MEG identifier is a 48 octet string
        used to identify the maintenance entity group.

        icc - ITU Carrier Code (ICC)-based format:
        Byte 1 is set to 1.
        Byte 2 is set to 32.
        Byte 3 is set to 13 (length of the identifier).
        Byte 4-18 are set to the ICC-based identifier.
        Byte 19 to 48 are set to 0.

"
    ::= { mesMepEntry 15 }

mesMepMegIdIccReceived OBJECT-TYPE
    SYNTAX      DisplayString (SIZE (0..13))
    MAX-ACCESS  read-only
    STATUS      current
    DESCRIPTION
        "The received Management Entity Group (MEG)
        identifier in ICC-based format.  Composed of ICC,
        1-6 characters, followed by a unique MEG id code
        consisting of 7-12 characters.

"
    ::= { mesMepEntry 16 }

mesMepMegIdReceived OBJECT-TYPE
    SYNTAX      OCTET STRING (SIZE (48))
     MAX-ACCESS  read-only
     STATUS      current
     DESCRIPTION
         "The received Management Entity Group (MEG)
          identifier.  A 48 octet identifier that should be
          globally unique.

"
     DEFVAL { "" }
     ::= { mesMepEntry 17 }

mesMepId OBJECT-TYPE
    SYNTAX      Unsigned32 (1..8191)
    MAX-ACCESS  read-write
    STATUS      current
    DESCRIPTION
        "The MEG end points own identity in the MEG.

"
    DEFVAL { 1 }
    ::= { mesMepEntry 18 }

mesMepIdExpected OBJECT-TYPE
    SYNTAX      Unsigned32 (1..8191)
    MAX-ACCESS  read-write
    STATUS      current
    DESCRIPTION
        "The expected received MEG end point identity.

"
    DEFVAL { 1 }
    ::= { mesMepEntry 19 }

mesMepIdReceived OBJECT-TYPE
    SYNTAX      Unsigned32 (1..8191)
    MAX-ACCESS  read-only
    STATUS      current
    DESCRIPTION
        "The recevied MEG end point identity.

"
    ::= { mesMepEntry 20 }

mesMepUnexpectedMepId OBJECT-TYPE
    SYNTAX      FaultStatus
    MAX-ACCESS  read-only
    STATUS      current
    DESCRIPTION
        "Unexpected received MEP identity.

        A: The received OAM messages contains an
        unexpected MEP id.

        D: The OAM messages contains an
        expected MEP id.

"
    ::= { mesMepEntry 21 }

mesMepUnexpectedMegLevel OBJECT-TYPE
    SYNTAX      FaultStatus
    MAX-ACCESS  read-only
    STATUS      current
    DESCRIPTION
        "Unexpected received MEP identity.

        A: The received OAM messages contains an
        unexpected MEG level.

        D: The OAM messages contains an
        expected MEG level.

"
    ::= { mesMepEntry 22 }

mesMepMegId OBJECT-TYPE
    SYNTAX      OCTET STRING (SIZE (48))
     MAX-ACCESS  read-write
     STATUS      current
     DESCRIPTION
         "The Management Entity Group (MEG) identifier.  A
          48 octet identifier that should be globally
          unique.

"
     DEFVAL { "" }
     ::= { mesMepEntry 23 }

mesMepMegIdFormat OBJECT-TYPE
    SYNTAX      INTEGER {
                    icc (32) }
    MAX-ACCESS  read-write
    STATUS      current
    DESCRIPTION
        "The Management Entity Group (MEG) identifier
        format. The MEG identifier is a 48 octet string
        used to identify the maintenance entity group.

        icc - ITU Carrier Code (ICC)-based format:
        Byte 1 is set to 1.
        Byte 2 is set to 32.
        Byte 3 is set to 13 (length of the identifier).
        Byte 4-18 are set to the ICC-based identifier.
        Byte 19 to 48 are set to 0.

"
    DEFVAL { 32 }
    ::= { mesMepEntry 24 }

mesMepMegIdIcc OBJECT-TYPE
    SYNTAX      DisplayString (SIZE (0..13))
    MAX-ACCESS  read-write
    STATUS      current
    DESCRIPTION
        "The Management Entity Group (MEG) identifier
        in ICC-based format.
        Composed of ICC, 1-6 characters, followed by
        a unique MEG id code consisting of 7-12
        characters.

"
    DEFVAL { "undefined" }
    ::= { mesMepEntry 25 }


-- ----------------------------------------------------
-- Maintenance entity group configurations
-- ----------------------------------------------------

mesMegTable  OBJECT-TYPE
    SYNTAX      SEQUENCE OF MesMegEntry
    MAX-ACCESS  not-accessible
    STATUS      obsolete
    DESCRIPTION
        "The maintenance entity group (MEG) list."
    ::= { mesMegList 1 }

mesMegEntry OBJECT-TYPE
    SYNTAX      MesMegEntry
    MAX-ACCESS  not-accessible
    STATUS      current
    DESCRIPTION
        "An entry in the MEG list.
"
    INDEX { mesMegIndex }
    ::= { mesMegTable 1 }

MesMegEntry ::=
    SEQUENCE {
        mesMegIndex                 Unsigned32,
        mesMegName                  MgmtNameString,
        mesMegObjectProperty        ObjectProperty,
        mesMegInternalReference     Unsigned32,
        mesMegAdminStatus           BoardOrInterfaceAdminStatus,
        mesMegOperStatus            BoardOrInterfaceOperStatus,
        mesMegLevel                 Unsigned32,
        mesMegUnexpectedMessage     FaultStatus }

mesMegIndex OBJECT-TYPE
    SYNTAX      Unsigned32 (1..2147483647)
    MAX-ACCESS  read-only
    STATUS      current
    DESCRIPTION
        "An arbitrary index assigned to each MEG entry.
"
    ::= { mesMegEntry 1 }

mesMegName OBJECT-TYPE
    SYNTAX      MgmtNameString
    MAX-ACCESS  read-only
    STATUS      current
    DESCRIPTION
        "The management name of the maintenance entity
        group, for example 'meg:1:2'.

"
    ::= { mesMegEntry 2 }

mesMegObjectProperty  OBJECT-TYPE
    SYNTAX      ObjectProperty
    MAX-ACCESS  read-only
    STATUS      current
    DESCRIPTION
        "Property mask.

"
    ::= { mesMegEntry 3 }

mesMegInternalReference OBJECT-TYPE
    SYNTAX      Unsigned32 (0..2147483647)
    MAX-ACCESS  read-create
    STATUS      current
    DESCRIPTION
        "For internal use only.

"
    DEFVAL { 0 }
    ::= { mesMegEntry 4 }

mesMegAdminStatus OBJECT-TYPE
    SYNTAX      BoardOrInterfaceAdminStatus
    MAX-ACCESS  read-write
    STATUS      current
    DESCRIPTION
        "The administrative state for the object.

        down - The object is de-activated.

        service - The object is activated but alarms
        are suppressed. Intended for use during service
        or re-configuration. When service is concluded
        adminStatus should be set to 'up' again.

        up - The object will be activated when
        available. Alarms are not suppressed.

"
    DEFVAL { down }
    ::= { mesMegEntry 5 }

mesMegOperStatus OBJECT-TYPE
    SYNTAX      BoardOrInterfaceOperStatus
    MAX-ACCESS  read-only
    STATUS      current
    DESCRIPTION
        "The operational state for the object.

        notPresent - The object is not available.

        down - The object is de-activated or there are
        faults preventing its transition to the 'up' state.

        up - The object is active.

"
    DEFVAL { notPresent }
    ::= { mesMegEntry 6 }

mesMegLevel OBJECT-TYPE
    SYNTAX      Unsigned32 (0..7)
    MAX-ACCESS  read-write
    STATUS      current
    DESCRIPTION
         "MEG level.
        Used to identify OAM flows where MEGs are nested.
        By convention the following levels are used:

        0-2     Provider role
        3-4     Provider role
        5-7     Customer role

"
    DEFVAL { 4 }
    ::= { mesMegEntry 10 }

mesMegUnexpectedMessage OBJECT-TYPE
    SYNTAX      FaultStatus
    MAX-ACCESS  read-only
    STATUS      current
    DESCRIPTION
        "Unexpected received OAM message.

        A: An unexpected OAM message is received.

        D: An expected OAM message is received.

"
    ::= { mesMegEntry 11 }



-- ----------------------------------------------------
-- Misc group configurations
-- ----------------------------------------------------

mesMiscTable  OBJECT-TYPE
    SYNTAX      SEQUENCE OF MesMiscEntry
    MAX-ACCESS  not-accessible
    STATUS      current
    DESCRIPTION
        "The misc group list."
    ::= { mesMiscList 1 }

mesMiscEntry OBJECT-TYPE
    SYNTAX      MesMiscEntry
    MAX-ACCESS  not-accessible
    STATUS      current
    DESCRIPTION
        "An entry in the Misc list.
"
    INDEX { mesMiscIndex }
    ::= { mesMiscTable 1 }

MesMiscEntry ::=
    SEQUENCE {
        mesMiscIndex                 Unsigned32,
        mesMiscName                  MgmtNameString,
        mesMiscObjectProperty        ObjectProperty,
        mesMiscInternalReference    Unsigned32,
        mesMiscAdminStatus          BoardOrInterfaceAdminStatus,
        mesMiscOperStatus           BoardOrInterfaceOperStatus,
        mesMiscMgmtVlanIpAddress    IpAddress,
        mesMiscMgmtVlanNetMask      IpAddress,
        mesMiscMgmtVlanMacAddress0  DisplayString,
        mesMiscMgmtVlanMacAddress1  DisplayString,
        mesMiscMgmtVlanMacAddress2  DisplayString,
        mesMiscConfigureAddress     CommandString,
        mesMiscMgmtVlanNode         INTEGER,
        mesMiscMacAgeing            Unsigned32,
        mesMiscMacGetTable          CommandString,
        mesMiscNoOfMegs             Unsigned32,
        mesMiscAssociateMeg         CommandString,
        mesMiscNoOfErps             Unsigned32,
        mesMiscAssociateErp         CommandString,
        mesMiscNoOfErpV2s           Unsigned32,
        mesMiscAssociateErpV2       CommandString,
        mesMiscL2Mode               INTEGER,
        mesMiscConfigureMode        CommandString,
        mesMiscIdentity             Counter64,
        mesMiscAssociateClass       CommandString,
        mesMiscAssociateBwp         CommandString,
        mesMiscWred                 INTEGER,
        mesMiscGetPacketMonitor     CommandString,
        mesMiscSfpPortUsageCurrent  INTEGER,
        mesMiscSfpPortUsageNext     INTEGER,
        mesMiscAssociateErrorProp   CommandString,
        mesMiscAssociateVlanProt    CommandString,
        mesMiscCreateVlan           CommandString,
        mesMiscEnablePtp1588        INTEGER,
        mesMiscEnableStpMgmtVlan    INTEGER,
        mesMiscAssociateClassAdvanced CommandString,
        mesMiscAssociateErpAdvanced   CommandString,
        mesMiscAssociateMegAdvanced   CommandString,
        mesMiscCreateClass            CommandString,
        mesMiscCreateAction           CommandString,
        mesMiscCreateMeg              CommandString,
        mesMiscCreateMep              CommandString,
        mesMiscCreateErrorProp        CommandString,
        mesMiscCreatePolicer          CommandString,
        mesMiscResendConfig           CommandString}

mesMiscIndex OBJECT-TYPE
    SYNTAX      Unsigned32 (1..2147483647)
    MAX-ACCESS  read-only
    STATUS      current
    DESCRIPTION
        "An arbitrary index assigned to each Misc entry.
"
    ::= { mesMiscEntry 1 }

mesMiscName OBJECT-TYPE
    SYNTAX      MgmtNameString
    MAX-ACCESS  read-only
    STATUS      current
    DESCRIPTION
        "The management name of the misc group, for example
        'misc:1:2'.

"
    ::= { mesMiscEntry 2 }

mesMiscObjectProperty  OBJECT-TYPE
    SYNTAX      ObjectProperty
    MAX-ACCESS  read-only
    STATUS      current
    DESCRIPTION
        "Property mask.

"
    ::= { mesMiscEntry 3 }

mesMiscInternalReference OBJECT-TYPE
    SYNTAX      Unsigned32 (0..2147483647)
    MAX-ACCESS  read-only
    STATUS      current
    DESCRIPTION
        "For internal use only.

"
    DEFVAL { 0 }
    ::= { mesMiscEntry 4 }

mesMiscAdminStatus OBJECT-TYPE
    SYNTAX      BoardOrInterfaceAdminStatus
    MAX-ACCESS  read-write
    STATUS      current
    DESCRIPTION
        "The administrative state for the object.

        down - The object is de-activated. For a CU-less
        system, admin status cannot be set to 'up' or
        'service' if mgmt VLAN IP address or netmask is not
        configured.

        service - The object is activated but alarms
        are suppressed. Intended for use during service
        or re-configuration. When service is concluded
        adminStatus should be set to 'up' again.

        up - The object will be activated when
        available. Alarms are not suppressed.

        Note: If 'System/Equipment/Management VLAN' is set
        to off, management VLAN will be deactivated even if
        'Misc/Administrative status' is up.
        (only for gbeMxp10GFEC, msMxp10G, fhmxp10g, gbe10Emxp10G and
        gbe22Emxp10G) See 'Management VLAN enabled in node'
        for status.

"
    DEFVAL { down }
    ::= { mesMiscEntry 5 }

mesMiscOperStatus OBJECT-TYPE
    SYNTAX      BoardOrInterfaceOperStatus
    MAX-ACCESS  read-only
    STATUS      current
    DESCRIPTION
        "The operational state for the object.

        notPresent - The object is not available.

        down - The object is de-activated or there are
        faults preventing its transition to the 'up' state.

        up - The object is active.

"
    DEFVAL { notPresent }
    ::= { mesMiscEntry 6 }

mesMiscMgmtVlanIpAddress OBJECT-TYPE
    SYNTAX      IpAddress
    MAX-ACCESS  read-create
    STATUS      current
    DESCRIPTION
        "The IP address of the ethernet interface associated
         with the mgmt VLAN.

         Set to 0.0.0.0 if not used.

"
    DEFVAL { '00000000'H }
    ::= { mesMiscEntry 7 }

mesMiscMgmtVlanNetMask OBJECT-TYPE
    SYNTAX      IpAddress
    MAX-ACCESS  read-create
    STATUS      current
    DESCRIPTION
        "The IP net mask of the ethernet interface associated
         with the mgmt VLAN.

         Set to 0.0.0.0 if not used.

"
    DEFVAL { '00000000'H }
    ::= { mesMiscEntry 8 }

mesMiscMgmtVlanMacAddress0 OBJECT-TYPE
    SYNTAX      DisplayString
    MAX-ACCESS  read-only
    STATUS      current
    DESCRIPTION
        "The mac address of eth0.

"
    DEFVAL { "" }
    ::= { mesMiscEntry 9 }

mesMiscMgmtVlanMacAddress1 OBJECT-TYPE
    SYNTAX      DisplayString
    MAX-ACCESS  read-only
    STATUS      current
    DESCRIPTION
        "The mac address of eth1.

"
    DEFVAL { "" }
    ::= { mesMiscEntry 10 }

mesMiscMgmtVlanMacAddress2 OBJECT-TYPE
    SYNTAX      DisplayString
    MAX-ACCESS  read-only
    STATUS      current
    DESCRIPTION
        "The mac address of eth2.

"
    DEFVAL { "" }
    ::= { mesMiscEntry 11 }

mesMiscConfigureAddress OBJECT-TYPE
    SYNTAX      CommandString
    MAX-ACCESS  read-only
    STATUS      current
    DESCRIPTION
        "Change the IP address and netmask.

"
    ::= { mesMiscEntry 12 }

mesMiscMgmtVlanNode OBJECT-TYPE
    SYNTAX      INTEGER {
                    off (1),
                    bridge2dcn (2),
                    on (3) }
    MAX-ACCESS  read-only
    STATUS      current
    DESCRIPTION

        "Indicates if mgmt VLAN is enabled in equipment-node
        mib.

        Note that if mgmt VLAN is disabled in node, it
        overrides Misc/Administrative status.
        (to change this setting, go to System/Equipment)

        off - VLAN is disabled

        bridge2dcn - mgmt VLAN is bridged to DCN.(enabled,
        used on CU)

        on - mgmt VLAN is enabled (used on culess).
"
    ::= { mesMiscEntry 13 }

mesMiscMacAgeing OBJECT-TYPE
    SYNTAX      Unsigned32 (10..1000000)
    MAX-ACCESS  read-write
    STATUS      current
    DESCRIPTION
        "The MAC table ageing time in seconds.

"
    DEFVAL { 300 }
    ::= { mesMiscEntry 14 }

mesMiscMacGetTable OBJECT-TYPE
    SYNTAX      CommandString
    MAX-ACCESS  read-only
    STATUS      current
    DESCRIPTION
        "Get MAC address table. It is possible to filter the MAC table per port,
        per VLAN and per MAC address. The MAC address field also allows regular
        expressions.

        To search for Infinera MAC addresses, enter the following regular
        expression: ^00:06:9C:.*

        Only about 70 MAC addresses will be displayed.

        A snapshot of all MAC addresses are written to a file in the network
        element (directory /tftpboot/log). The file name is max_X_Y.txt, where X
        is the subrack number and Y is the slot number.

"
    ::= { mesMiscEntry 15 }

mesMiscNoOfMegs OBJECT-TYPE
    SYNTAX      Unsigned32
    MAX-ACCESS  read-only
    STATUS      current
    DESCRIPTION
        "The current number of MEGs associated with this
        board.

"
    DEFVAL { 0 }
    ::= { mesMiscEntry 16 }

mesMiscAssociateMeg OBJECT-TYPE
    SYNTAX      CommandString
    MAX-ACCESS  read-only
    STATUS      current
    DESCRIPTION
        "Create and associate a MEG (MAID) for the board.

        Identifier - A unique user defined identifier for the MEG.

        Level - Maintenance domain level.

        CCM interval - Interval between CCM transmissions to be used by all MEPs in the MA.
          invalid  No CCMs are sent
          3.33 ms  CCMs are sent every 3 1/3 milliseconds (300Hz)
          10 ms    CCMs are sent every 10 milliseconds
          100 ms   CCMs are sent every 100 milliseconds
          1 s      CCMs are sent every 1 second
          10 s     CCMs are sent every 10 seconds
          1 min    CCMs are sent every minute
          10 min   CCMs are sent every 10 minutes

          The supported CCM intervals for Down MEPs are: 3.33 ms,10 ms, 100 ms, 1 s, 10 s, 1 min, 10 min.
          The supported CCM intervals for Up MEPs are: 1 s, 10 s, 1 min, 10 min.

        Domain format - The format of the domain. none, dnsLikeName, macAddressAndUint and charString are supported.

        Domain name - Applicable for the format dnsLikeName and charString.

        MAC - MAC address. Only applicable if domain format is macAddrAndUint.

        Uint - Unsigned integer. Only applicable if domain format is macAddrAndUint.

        Association format - The format of the association. primaryVid, charString, unsignedInt16, rfc2865VpnId and ICC are supported.

        Association name - Applicable for the formats charString and ICC.

        VPN OUI - VPN authority Organizationally Unique Indentifier. Only applicable if association format is rfc2865VpnId. Example of an VPN OUI is 0A:12:BF.

        VPN index - VPN index. Only applicable if association format is rfc2865VpnId. Example of an VPN index is 0A:12:BF:11.

        Uint - Unsigned integer. Only applicable if association format is unsignedInt16.

        VLAN ID - Primary VLAN ID. Only applicable if association format is primaryVid.
"
    ::= { mesMiscEntry 17 }

mesMiscAssociateMegAdvanced OBJECT-TYPE
        SYNTAX      CommandString
        MAX-ACCESS  read-only
        STATUS      current
        DESCRIPTION
            "Create and associate a MEG (MAID) for the board.

            Identifier - A unique user defined identifier for the MEG.

            Level - Maintenance domain level.

            CCM interval - Interval between CCM transmissions to be used by all MEPs in the MA.
              invalid  No CCMs are sent
              3.33 ms  CCMs are sent every 3 1/3 milliseconds (300Hz)
              10 ms    CCMs are sent every 10 milliseconds
              100 ms   CCMs are sent every 100 milliseconds
              1 s      CCMs are sent every 1 second
              10 s     CCMs are sent every 10 seconds
              1 min    CCMs are sent every minute
              10 min   CCMs are sent every 10 minutes

              The supported CCM intervals for Down MEPs are: 3.33 ms,10 ms, 100 ms, 1 s, 10 s, 1 min, 10 min.
              The supported CCM intervals for Up MEPs are: 1 s, 10 s, 1 min, 10 min.

            Domain format - The format of the domain. none, dnsLikeName, macAddressAndUint and charString are supported.

            Domain name - Applicable for the format dnsLikeName and charString.

            MAC - MAC address. Only applicable if domain format is macAddrAndUint.

            Uint - Unsigned integer. Only applicable if domain format is macAddrAndUint.

            Association format - The format of the association. primaryVid, charString, unsignedInt16, rfc2865VpnId and ICC are supported.

            Association name - Applicable for the formats charString and ICC.

            VPN OUI - VPN authority Organizationally Unique Indentifier. Only applicable if association format is rfc2865VpnId. Example of an VPN OUI is 0A:12:BF.

            VPN index - VPN index. Only applicable if association format is rfc2865VpnId. Example of an VPN index is 0A:12:BF:11.

            Uint - Unsigned integer. Only applicable if association format is unsignedInt16.

            VLAN ID - Primary VLAN ID. Only applicable if association format is primaryVid.
"
        ::= { mesMiscEntry 38 }

mesMiscNoOfErps OBJECT-TYPE
    SYNTAX      Unsigned32
    MAX-ACCESS  read-only
    STATUS      current
    DESCRIPTION
        "The current number of ERPs associated with this
        board.

"
    DEFVAL { 0 }
    ::= { mesMiscEntry 18 }

mesMiscAssociateErp OBJECT-TYPE
    SYNTAX      CommandString
    MAX-ACCESS  read-only
    STATUS      current
    DESCRIPTION
        "Create and associate an ERP (Ethernet Ring Protection) for the board.

        VLAN ID         - The VLAN ID that carries the control messages. The
                          VLAN ID is also used to uniquely define the ring.
                          The VLAN ID must be created before it can be used in
                          an ERP.
        Description     - A user configurable label.
        MEG level       - Must match MAID/MEG level if OAM messaging is used
                          to detect link failures.
        Interface left/right - The interfaces that are connected to the ring links. The
                          interfaces must belong to the created VLAN and they must be
                          trusted. LAG is allowed for the interfaces in an ERPV2 ring,
                          but not in an ERPV1 ring.
        Protection link - Which of the interfaces (or none) that is connected to the
                          Ring Protection Link (RPL).
        Guard time      - The guard time is used to protect from receiving old
                          R-APS messages during a recovery from a failed link.
                          When the guard timer is running, all received R-APS
                          messages are ignored. The period of the guard timer
                          should be longer than the time it takes for a packet to
                          circle around the ring.
"
    ::= { mesMiscEntry 19 }

mesMiscL2Mode OBJECT-TYPE
    SYNTAX      INTEGER {
                    switch (1),
                    aggregator (2) }
    MAX-ACCESS  read-only
    STATUS      current
    DESCRIPTION
        "The initial mode (switch or aggregator) of the board.

        Switch     - All ports are acting as NNI and all ports are trusted.

        Aggregator - 1G ports are acting as UNI and 10G ports are acting as
                     NNI. All 1G ports are trusted with the first 10G port.
                     All 10G ports are trusted with all 1G ports.
        Board emxp80Gii, emxp40Gii only has Switch Mode.
"
    DEFVAL { switch }
    ::= { mesMiscEntry 20 }

mesMiscConfigureMode OBJECT-TYPE
    SYNTAX      CommandString
    MAX-ACCESS  read-only
    STATUS      current
    DESCRIPTION
        "Defines if the board should be acting as a switch or an aggregator.

        Switch     - All ports are acting as NNI and all ports trust each other.

        Aggregator - 1G ports are acting as UNI and 10G ports are acting as
                     NNI. All 1G ports are trusted with the first 10G port.
                     All 10G ports are trusted with all 1G ports.
"
    ::= { mesMiscEntry 21 }

mesMiscIdentity OBJECT-TYPE
     SYNTAX Counter64
     MAX-ACCESS read-create
     STATUS current
     DESCRIPTION
        "For internal use only.
"
    DEFVAL { 0 }
    ::= { mesMiscEntry 22 }

mesMiscAssociateClass OBJECT-TYPE
    SYNTAX      CommandString
    MAX-ACCESS  read-only
    STATUS      current
    DESCRIPTION
        "Create a classification to be used in a policy.

        Classification enables dynamic assignment of actions (rules) when
        traffic is received or before traffic is sent.
        The classification defines the traffic matching criteria for which
        the action (rule) is applied

        Identifier
        A unique (per board) identifier for the classification.

        Precedence
        When two policy classifications match, only the classification with the
        highest precedence will be carried out. If two classifiers have the same
        precedence, the classification created first will be carried out.

        Direction
        Defines if classification is made on incoming traffic or processed and
        outgoing traffic.

        Port
        The port or LAG  to classify on.

        MAC
        Destination MAC address to classify on.

        MAC mask
        Masked destination MAC address to classify on.

        Outer VLAN PCP
        Outer VLAN PCP to classify on.

        Outer VLAN ID
        Outer VLAN ID to classify on.

        Outer VLAN CFI/DEI
        Outer VLAN CFI/DEI to classify on.

        Inner VLAN PCP
        Inner VLAN PCP to classify on.

        Inner VLAN ID
        Inner VLAN ID to classify on.

        Inner VLAN CFI/DEI
        Inner VLAN CFI/DEI to classify on.

        DSCP
        Differentiated Services CodePoint to classify on.

"
    ::= { mesMiscEntry 23 }


mesMiscAssociateBwp OBJECT-TYPE
    SYNTAX      CommandString
    MAX-ACCESS  read-only
    STATUS      current
    DESCRIPTION
        "Create a MEF Policer.

        CIR (Commited Information Rate)
        The average rate in bits/s up to which the network delivers
        service frames and meets the defined performance objectives.

        CBS (Commited Burst Size)
        The maximum number of bytes available for a burst to remain
        CIR-conformant. Packets conformant to CIR/CBS are marked as
        green. Value is entered in kB, and can be interpreted as the
        amount of data  that can be sent consecutively at the port line rate.
        Ex: 100 mBit/s * 100 ms = 1250 kB
        1 Gbit/s   * 32  ms = 4000 kB
            1 Gbit/s   * 10  ms = 1250 kB
            10 Gbit/s  * 1   ms = 1250 kB

        EIR (Excess Information Rate)
        The average rate in bits/s up to which the network may deliver
        service frames without any performance objectives.

        EBS(Excess Burst Size)
        The maximum number of bytes available for a burst to remain
        EIR-conformant. Packets conformant to EIR/EBS but not CIR/CBS
        are marked as yellow. Value is entered in kB, and can be interpreted as the
        amount of data  that can be sent consecutively at the port line rate.
        Ex: 100 mBit/s * 100 ms = 1250 kB
        1 Gbit/s   * 32  ms = 4000 kB
            1 Gbit/s   * 10  ms = 1250 kB
            10 Gbit/s  * 1   ms = 1250 kB

        In color blind mode, the outgoing frame color is
        based only on the profile status of each bucket. In
        color aware mode, the outgoing frame color is based
        on the incoming color and the profile status of each
        bucket. The incoming color is derived from the
        ingress classification stage.
"
    ::= { mesMiscEntry 24 }

mesMiscWred OBJECT-TYPE
    SYNTAX      INTEGER {
                    disabled (1),
                    enabled (2) }
    MAX-ACCESS  read-write
    STATUS      current
    DESCRIPTION
        "Defines if WRED (Weighted Random Early Detection) is
         enabled on the board.

         disabled - WRED is disabled on the board.

         enabled - WRED is enabled on the board.

"
    DEFVAL { disabled }
    ::= { mesMiscEntry 25 }

mesMiscGetPacketMonitor OBJECT-TYPE
    SYNTAX      CommandString
    MAX-ACCESS  read-only
    STATUS      current
    DESCRIPTION
        "Get data packet(s) from a specified interface. The monitor function
        waits for a user defined maximum number of packets and for a user
        defined maximum number of seconds.

        Only the initial 128 octets of each packet will be returned/presented.

        Executing getPackets dump generates a snapshot of captured packets
        written to a file in the network element (directory /tftpboot/log).
        The file name is pkts_X_Y.txt, where X is the subrack number and Y is the slot number.

        User can run getPackets dump several times during a capture session
        without affecting the capture.

"
    ::= { mesMiscEntry 26 }

mesMiscSfpPortUsageCurrent OBJECT-TYPE
    SYNTAX          INTEGER {
                          external (1),
                          mgmtVlan (2)}
    MAX-ACCESS      read-only
    STATUS          current
    DESCRIPTION

        "Indicates if the 1 Gbe port is connected to the front panel or
        is connected to the CPU for mgmt VLAN.
        Only applicable for emxp40Gii.

        external - The 1 GbE port is connected to the front.
                   mgmt VLAN is disabled on the board.


        mgmtVlan - The 1 GbE port is connected to the CPU.
                   mgmt VLAN is enabled on the board.

        mgmt VLAN is enabled by default. The board need to be re-started for
        the setting to take effect.

"
    DEFVAL { mgmtVlan }
    ::= { mesMiscEntry 27 }

mesMiscSfpPortUsageNext OBJECT-TYPE
    SYNTAX        INTEGER {
                      external (1),
                      mgmtVlan (2)}
    MAX-ACCESS      read-write
    STATUS          current
    DESCRIPTION

        "Indicates usage of the 1 Gbe port after a cold start of the board.
        Only applicable for emxp40Gii.

        external - The 1 GbE port will be connected to the front.
                   mgmt VLAN will be disabled on the board.

        mgmtVlan - The 1 GbE port will be connected to the CPU.
                   mgmt VLAN will be enabled on the board.

"
    DEFVAL { mgmtVlan }
    ::= { mesMiscEntry 28 }

mesMiscAssociateErrorProp OBJECT-TYPE
    SYNTAX      CommandString
    MAX-ACCESS  read-only
    STATUS      current
    DESCRIPTION
        "Internal dialog command for configuring and create an Error Propagation rule.
          Select the following:
          - Trigger type
          - Trigger MEP or Port depending on trigger type
          - Action type
          - Action MEP or Port depending on action type
          - Hold-off time

"
    ::= { mesMiscEntry 29 }

mesMiscNoOfErpV2s OBJECT-TYPE
    SYNTAX      Unsigned32
    MAX-ACCESS  read-only
    STATUS      current
    DESCRIPTION
        "The current number of ERPV2s associated with this
        board.

"
    DEFVAL { 0 }
    ::= { mesMiscEntry 30 }

mesMiscAssociateErpV2 OBJECT-TYPE
    SYNTAX      CommandString
    MAX-ACCESS  read-only
    STATUS      current
    DESCRIPTION
        "Create and associate an ERP V2 (Ethernet Ring Protection V2) for the board.

        Ring ID         - The Ring Id and VLAN Id is used to uniquely define
                          the ring.
        VLAN ID         - The VLAN ID that carries the control messages, R-APS VLAN. The
                          VLAN ID and the RING ID is used to uniquely define
                          the ring. The VLAN ID must be created before it can
                          be used in an ERP.
        MEG level       - Must match MAID/MEG level if OAM messaging is used
                          to detect link failures.
        Description     - A user configurable label.
        Node type       - Ring node or interconnection point
                          for a sub-ring to a major ring
        Port left/right - The ports that are connected to the ring links. The
                          ports must belong to the created VLAN and the must be
                          trusted. For interconnection node only left port is
                          selected. LAG is not allowed for the ports in an ERP.
        Protection link - Which of the ports (or none) that is connected to the
                          Ring Protection Link (RPL) or is the a neighbor to the
                          RPL link.
        Protection mode - For an RPL owner the mode of operation of the protection
                          can be selected as revertive or non-revertive.
        VLAN Protection identifier - Identifier for the VLAN Protection group of the
                          R-APS VLAN for the ERP. The name of the new
                          group is set in this field. If the R-APS VLAN is
                          already part of a VLAN protection group the name of
                          the group is displayed in the field.
"
    ::= { mesMiscEntry 31 }

mesMiscAssociateErpAdvanced OBJECT-TYPE
    SYNTAX      CommandString
    MAX-ACCESS  read-only
    STATUS      current
    DESCRIPTION
        "Create and associate an ERP V2 (Ethernet Ring Protection V2) for the board.

        Ring ID         - The Ring Id and VLAN Id is used to uniquely define
                          the ring.
        VLAN ID         - The VLAN ID that carries the control messages, R-APS VLAN. The
                          VLAN ID and the RING ID is used to uniquely define
                          the ring. The VLAN ID must be created before it can
                          be used in an ERP.
        MEG level       - Must match MAID/MEG level if OAM messaging is used
                          to detect link failures.
        Description     - A user configurable label.
        Node type       - Ring node or interconnection point
                          for a sub-ring to a major ring
        Port left/right - The ports that are connected to the ring links. The
                          ports must belong to the created VLAN and the must be
                          trusted. For interconnection node only left port is
                          selected. LAG is not allowed for the ports in an ERP.
        Protection link - Which of the ports (or none) that is connected to the
                          Ring Protection Link (RPL) or is the a neighbor to the
                          RPL link.
        Protection mode - For an RPL owner the mode of operation of the protection
                          can be selected as revertive or non-revertive.
        VLAN Protection identifier - Identifier for the VLAN Protection group of the
                          R-APS VLAN for the ERP. The name of the new
                          group is set in this field. If the R-APS VLAN is
                          already part of a VLAN protection group the name of
                          the group is displayed in the field.
"
    ::= { mesMiscEntry 37 }

mesMiscAssociateVlanProt OBJECT-TYPE
    SYNTAX      CommandString
    MAX-ACCESS  read-only
    STATUS      current
    DESCRIPTION
        "Dialog command for create and configuring a VLAN Protection Group.
        The VLAN protection group is used for the EPR V2 ring protection
        to define the VLAN protected by the ring.
        Select the following:
            Identifier      - Unique identifier for the VLAN Protection
                              Group.
            Protected VLANs - A comma separated list of VLANs or VLAN
                              ranges one or more ERP V2 ring should protect
                              (ex: '100,200-300,401'). The VLANs may or may
                              not exist. When a VLAN is created and match a
                              protection group the protection is
                              automatically added for the VLAN.

          In the dialog select the rings for the protection of the VLANs.
          In CLI add ring protection using the command:
          'mes::vlanProt::vlanProt:X:Y:ID::addRing'
"
    ::= { mesMiscEntry 32 }

mesMiscEnablePtp1588 OBJECT-TYPE
    SYNTAX      INTEGER {
                    disabled (1),
                    enabled (2) }
    MAX-ACCESS  read-write
    STATUS      current
    DESCRIPTION
        "Enable precision time protocol 1588v2 transparent clock on all ports.

        disabled - ptp 1588v2 transparent clock is disabled

        enabled - ptp 1588v2 transparent clock is enabled.

"
    DEFVAL { disabled }
    ::= { mesMiscEntry 34 }

mesMiscEnableStpMgmtVlan OBJECT-TYPE
    SYNTAX      INTEGER {
                    disabled (1),
                    enabled (2) }
    MAX-ACCESS  read-write
    STATUS      current
    DESCRIPTION
        "Enable spanning tree protocol for management vlan on all ports.

        disabled - spanning tree protocol for mangagement vlan is disabled

        enabled - panning tree protocol for mangagement vlan is enabled.

"
    DEFVAL { enabled }
    ::= { mesMiscEntry 35 }

mesMiscCreateVlan OBJECT-TYPE
    SYNTAX      CommandString
    MAX-ACCESS  read-only
    STATUS      current
    DESCRIPTION
        "Dialog command for create and configuring a VLAN Map Entry
"
    ::= { mesMiscEntry 33 }

mesMiscAssociateClassAdvanced OBJECT-TYPE
    SYNTAX      CommandString
    MAX-ACCESS  read-only
    STATUS      current
    DESCRIPTION
        "Create a classification to be used in a policy.

        Classification enables dynamic assignment of actions (rules) when
        traffic is received or before traffic is sent.
        The classification defines the traffic matching criteria for which
        the action (rule) is applied

        Identifier
        A unique (per board) identifier for the classification.

        Precedence
        When two policy classifications match, only the classification with the
        highest precedence will be carried out. If two classifiers have the same
        precedence, the classification created first will be carried out.

        Direction
        Defines if classification is made on incoming traffic or processed and
        outgoing traffic.

        If number
        The interface number of the multi-connector port or port group.

        Tx port
        The tx port to classificate on.

        LAG
        The identifier of the LAG to classify on.

        MAC
        Destination MAC address to classify on.

        MAC mask
        Masked destination MAC address to classify on.

        Outer VLAN PCP
        Outer VLAN PCP to classify on.

        Outer VLAN ID
        Outer VLAN ID to classify on.

        Outer VLAN CFI/DEI
        Outer VLAN CFI/DEI to classify on.

        Inner VLAN PCP
        Inner VLAN PCP to classify on.

        Inner VLAN ID
        Inner VLAN ID to classify on.

        Inner VLAN CFI/DEI
        Inner VLAN CFI/DEI to classify on.

        DSCP
        Differentiated Services CodePoint to classify on.

"
    ::= {  mesMiscEntry 36 }


    mesMiscCreateClass OBJECT-TYPE
        SYNTAX      CommandString
        MAX-ACCESS  read-only
        STATUS      current
        DESCRIPTION
            "Dialog command for creating a classifier.
"
    ::= { mesMiscEntry 39 }

    mesMiscCreateAction OBJECT-TYPE
        SYNTAX      CommandString
        MAX-ACCESS  read-only
        STATUS      current
        DESCRIPTION
            "Dialog command for creating an action.
"
    ::= { mesMiscEntry 40 }

    mesMiscCreateMeg OBJECT-TYPE
        SYNTAX      CommandString
        MAX-ACCESS  read-only
        STATUS      current
        DESCRIPTION
            "Dialog command for creating a MEG.
"
    ::= { mesMiscEntry 41 }

    mesMiscCreateMep OBJECT-TYPE
        SYNTAX      CommandString
        MAX-ACCESS  read-only
        STATUS      current
        DESCRIPTION
            "Dialog command for creating a MEP.
"
    ::= { mesMiscEntry 42 }

    mesMiscCreateErrorProp OBJECT-TYPE
        SYNTAX      CommandString
        MAX-ACCESS  read-only
        STATUS      current
        DESCRIPTION
            "Dialog command for creating an error propagation.
"
    ::= { mesMiscEntry 43 }

    mesMiscCreatePolicer OBJECT-TYPE
        SYNTAX      CommandString
        MAX-ACCESS  read-only
        STATUS      current
        DESCRIPTION
            "Dialog command for creating a policer.
"
    ::= { mesMiscEntry 44 }

    mesMiscResendConfig OBJECT-TYPE
        SYNTAX      CommandString
        MAX-ACCESS  read-only
        STATUS      current
        DESCRIPTION
            "Dialog command to send a specific configuration.
"
    ::= { mesMiscEntry 45 }

-- ----------------------------------------------------
-- LAG group configurations
-- ----------------------------------------------------

mesLagTable  OBJECT-TYPE
    SYNTAX      SEQUENCE OF MesLagEntry
    MAX-ACCESS  not-accessible
    STATUS      current
    DESCRIPTION
        "The LAG group list."
    ::= { mesLagList 1 }

mesLagEntry OBJECT-TYPE
    SYNTAX      MesLagEntry
    MAX-ACCESS  not-accessible
    STATUS      current
    DESCRIPTION
        "An entry in the LAG list.
"
    INDEX { mesLagIndex }
    ::= { mesLagTable 1 }

MesLagEntry ::=
    SEQUENCE {
        mesLagIndex                 Unsigned32,
        mesLagName                  MgmtNameString,
        mesLagInternalReference     Unsigned32,
        mesLagPortmask              Unsigned32,
        mesLagMasterIndex           Unsigned32,
        mesLagConfigure             CommandString,
        mesLagHash                  INTEGER,
        mesLagIdentifier            DisplayString,
        mesLagRowStatus             RowStatus,
        mesLagLacpEnabled           INTEGER,
        mesLagLacpSystemPriority    Unsigned32,
        mesLagLacpPeriod            INTEGER,
        mesLagLacpLinkProtection    MesLacpLinkProtectionValue,
        mesLagDegraded              FaultStatus,
        mesLagFailure               FaultStatus,
        mesLagLacpMaxNumberOfActiveLinks Unsigned32,
        mesLagNoOfPorts             Unsigned32,
        mesLagLacpMinNumberOfActiveLinks Unsigned32,
        mesLagIsMcLag               INTEGER,
        mesLagConfigureTagRule      CommandString,
        mesLagNoOfTagRules          Unsigned32,
        mesLagDescr                 DisplayString,
        mesLagAdminStatus           BoardOrInterfaceAdminStatus,
        mesLagOperStatus            BoardOrInterfaceOperStatus,
        mesLagPortmaskIf1           Unsigned32,
        mesLagPortmaskIf2           Unsigned32,
        mesLagPortmaskIf3           Unsigned32,
        mesLagPortmaskIf4           Unsigned32,
        mesLagPortmaskIf5           Unsigned32,
        mesLagPortmaskIf6           Unsigned32,
        mesLagPortmaskIf7           Unsigned32,
        mesLagPortmaskIf8           Unsigned32,
        mesLagMasterIfNo            PortNumber,
        mesLagMasterTxPort          PortNumber,
        mesLagLocalId               Integer32,
        mesLagPrepareConfigPortMask CommandString,
        mesLagPortmaskIf9           Unsigned32,
        mesLagPortmaskIf10          Unsigned32,
        mesLagPortmaskIf11          Unsigned32,
        mesLagPortmaskIf12          Unsigned32,
        mesLagPortmaskIf13          Unsigned32,
        mesLagPortmaskIf14          Unsigned32,
        mesLagPortmaskIf15          Unsigned32,
        mesLagPortmaskIf16          Unsigned32,
        mesLagServiceId             ServiceIdWithNotUsed
        }

mesLagIndex OBJECT-TYPE
    SYNTAX      Unsigned32 (1..2147483647)
    MAX-ACCESS  read-only
    STATUS      current
    DESCRIPTION
        "An arbitrary index assigned to each LAG entry.
"
    ::= { mesLagEntry 1 }

mesLagName OBJECT-TYPE
    SYNTAX      MgmtNameString
    MAX-ACCESS  read-only
    STATUS      current
    DESCRIPTION
        "The management name of the LAG group, for example
        'lag:1:2:1'.

"
    ::= { mesLagEntry 2 }

mesLagInternalReference OBJECT-TYPE
    SYNTAX      Unsigned32 (0..2147483647)
    MAX-ACCESS  read-create
    STATUS      current
    DESCRIPTION
        "For internal use only.

"
    DEFVAL { 0 }
    ::= { mesLagEntry 3 }

mesLagPortmask OBJECT-TYPE
    SYNTAX      Unsigned32 (0..2147483647)
    MAX-ACCESS  read-create
    STATUS      current
    DESCRIPTION
        "The ports belonging to the link aggregation group.

        This attribute can be written via SNMP.

"
    DEFVAL { 0 }
    ::= { mesLagEntry 4 }

mesLagMasterIndex OBJECT-TYPE
    SYNTAX      Unsigned32 (0..2147483647)
    MAX-ACCESS  read-create
    STATUS      current
    DESCRIPTION
        "The port that is master in the LAG.

"
    DEFVAL { 0 }
    ::= { mesLagEntry 5 }

mesLagConfigure OBJECT-TYPE
    SYNTAX      CommandString
    MAX-ACCESS  read-only
    STATUS      current
    DESCRIPTION
        "Change the members and hash algorithm in the Link
        Aggregation Group.

        Ports that are used in Ethernet Ring Protection
        (ERP) are not available for LAG.

        Changing the hash algorithm will affect all LAGs in
        this board.

"
    ::= { mesLagEntry 6 }

mesLagHash OBJECT-TYPE
    SYNTAX      INTEGER {
                    mac (1),
                    ip (2),
                    vlan (3),
                    mpls (4),
                    automatic (5)}
    MAX-ACCESS  read-create
    STATUS      current
    DESCRIPTION
        "The hash algorithm used for LAG load balancing

        mac - Based on src/dst MAC adresses

        ip - Based on src/dst IP addresses and TCP/UDP ports

        vlan - Based on VLAN ID

        mpls - EMXP/II boards: Based on up to two MPLS labels
               EMXP/IIe: Based on up to three MPLS labels and IPv4 and IPv6 headers in IP-MPLS packets

        automatic - The fields selected for hashing is depending on ethertype.
                  IPv4/IPv6 packets uses the IP src/dst addresses and TCP/UDP ports,
                  MPLS packets uses labels and the remaining ethertypes use VLAN ID and src/dst MAC addresses (Default value)

        This attribute can be written via SNMP.

"
    DEFVAL { automatic }
    ::= { mesLagEntry 7 }

mesLagIdentifier OBJECT-TYPE
    SYNTAX      DisplayString(SIZE(1..17))
    MAX-ACCESS  read-create
    STATUS      current
    DESCRIPTION
        "Unique identifier for the LAG.

        This attribute can be written via SNMP.

"
    DEFVAL { "" }
    ::= { mesLagEntry 8 }

mesLagRowStatus OBJECT-TYPE
    SYNTAX      RowStatus
    MAX-ACCESS  read-create
    STATUS      current
    DESCRIPTION
        "Manages creation and deletion of conceptual rows.
        See also SNMPv2-TC.

        Note: The newly created object will not necessarily
        receive the same index as used in the create
        procedure.
        This attribute can be written via SNMP.

"
    ::=  { mesLagEntry 9 }

mesLagLacpEnabled OBJECT-TYPE
    SYNTAX      INTEGER {
                off (0),
                passive (1),
                active (2) }
    MAX-ACCESS  read-write
    STATUS      current
    DESCRIPTION
        "Enables LACP for the LAG.

        Passive - Passive LACP indicates the ports preference for not transmitting LACPDUs unless
        its Partners control value is Active LACP (i.e., a preference not to speak unless spoken to)

        Active - Active LACP indicates the ports preference to participate in the protocol regardless
        of the Partners control value (i.e., a preference to speak regardless).

        Off - The links neither initialize nor respond to the protocol.

"
    DEFVAL { 0 }
    ::=  { mesLagEntry 10 }

mesLagLacpSystemPriority OBJECT-TYPE
    SYNTAX      Unsigned32 (0..65535)
    MAX-ACCESS  read-create
    STATUS      current
    DESCRIPTION
        "System priority -

        The system priority of the system. A lower value indicates a higher priority [0...65535]
"
    DEFVAL { 32768 }
    ::= { mesLagEntry 11 }

mesLagLacpPeriod OBJECT-TYPE
    SYNTAX      INTEGER {
                slow (0),
                fast (1) }
    MAX-ACCESS  read-write
    STATUS      current
    DESCRIPTION
        "LACP period

         slow - LACP messages are received using a 30 second transmission interval with a timeout of 90 seconds.
         fast - LACP messages are received using a one second transmission interval with a timeout of 3 seconds.

"
    DEFVAL { 0 }
    ::=  { mesLagEntry 12 }

mesLagLacpLinkProtection OBJECT-TYPE
    SYNTAX      MesLacpLinkProtectionValue
    MAX-ACCESS  read-write
    STATUS      deprecated
    DESCRIPTION
        "LACP link protection

        normal - The load is distributed on all links in the LAG.
        onePlusOne - All traffic is carried by the primary link while the other is used as a standby link in case of failure on the primary link.
"
    DEFVAL { 0 }
    ::=  { mesLagEntry 13 }

mesLagDegraded OBJECT-TYPE
    SYNTAX      FaultStatus
    MAX-ACCESS  read-only
    STATUS      current
    DESCRIPTION
        "LAG degraded

         Alarm - One or more of the links have link and/or LACP fault.

         Ok - All links and LACP (if used) are up.

"
    ::= { mesLagEntry 14 }

mesLagFailure OBJECT-TYPE
    SYNTAX      FaultStatus
    MAX-ACCESS  read-only
    STATUS      current
    DESCRIPTION
        "LAG failure

         Alarm - All of the links have link and/or LACP fault.

         Ok - At least one link and LACP (if used) is up.

"
    ::= { mesLagEntry 15 }

mesLagLacpMaxNumberOfActiveLinks OBJECT-TYPE
    SYNTAX      Unsigned32 (0..12)
    MAX-ACCESS  read-write
    STATUS      current
    DESCRIPTION
        "Define the maximum number of active links within a LAG.
        The range is normally from 1 to 8 (0 is though set if McLAG is
        disabled/removed from the LAG).
        If the maximum number of active links equals to the number
        of ports configured in the LAG, the load is distributed
        on all links in the LAG.
        If the maximum number of active links is less than the
        number of ports configured in the LAG, traffic is carried by the
        primary link(s) while the other(s) is used as a standby link(s)
        in case of failure on the primary link.
        Port priority is used to determine the active links.
"
    DEFVAL { 1 }
    ::=  { mesLagEntry 16 }

mesLagNoOfPorts OBJECT-TYPE
    SYNTAX      Unsigned32
    MAX-ACCESS  read-only
    STATUS      current
    DESCRIPTION
        "The number of ports in LAG.
"
    ::=  { mesLagEntry 17 }

mesLagLacpMinNumberOfActiveLinks OBJECT-TYPE
    SYNTAX      Unsigned32 (0..12)
    MAX-ACCESS  read-write
    STATUS      current
    DESCRIPTION
        "Define the minimum number of active links within a LAG.
        The range is normally from 1 to 8 (0 is though set if McLAG is
        disabled/removed from the LAG).
"
    DEFVAL { 1 }
    ::=  { mesLagEntry 18 }

mesLagIsMcLag OBJECT-TYPE
    SYNTAX      INTEGER {
                false (0),
                true (1) }
    MAX-ACCESS  read-write
    STATUS      current
    DESCRIPTION
        "If Lag is MC Lag.
"
    DEFVAL { 0 }
    ::=  { mesLagEntry 19 }

 mesLagConfigureTagRule OBJECT-TYPE
    SYNTAX      CommandString
    MAX-ACCESS  read-only
    STATUS      current
    DESCRIPTION

        "VLAN rule classification enables dynamic assignment
        of VLAN when traffic is received. Currently, only
        VLAN classification is possible.

        Classification

          The classification defines the traffic matching
          criteria for which the rule are applied.

          - Interface:  The name of the port or the lag.

          - Outer VLAN: The VLAN ID of the outer VLAN.

        Rule

          The rule defines the type of operation (pop, push
          or swap), new VLAN ID/priority and the direction
          of the traffic.

          - Type: Ingress or egress.

          - Operation: Different combinations of pop, push
                       and swap depending on the direction
                       (ingress or egress).

          - New VLAN : The new VLAN ID for a push or swap
            operation.

          - Priority assignment: Defines if a new priority
                                 is assigned or if the
                                 priority is copy from the
                                 ingress tag.

"
    ::= { mesLagEntry 20 }

mesLagNoOfTagRules OBJECT-TYPE
    SYNTAX      Unsigned32
    MAX-ACCESS  read-only
    STATUS      current
    DESCRIPTION
        "The current number of VLAN tag rules associated
        with this lag.

"
    ::= { mesLagEntry 21 }


mesLagDescr OBJECT-TYPE
    SYNTAX      DisplayString
    MAX-ACCESS  read-write
    STATUS      current
    DESCRIPTION
        "User configurable label.

"
    DEFVAL { "" }
    ::= { mesLagEntry 22 }


mesLagAdminStatus OBJECT-TYPE
    SYNTAX      BoardOrInterfaceAdminStatus
    MAX-ACCESS  read-write
    STATUS      current
    DESCRIPTION
        "The administrative state for the object.

        service - The object is activated but alarms
        are suppressed. Intended for use during service
        or re-configuration. When service is concluded
        adminStatus should be set to 'up' again.

        up - The object will be activated when
        available. Alarms are not suppressed.

"
    DEFVAL { up }
    ::= { mesLagEntry 23 }

mesLagOperStatus OBJECT-TYPE
    SYNTAX      BoardOrInterfaceOperStatus
    MAX-ACCESS  read-only
    STATUS      current
    DESCRIPTION
        "The operational state for the object.

        notPresent - The object is not available.

        down - The object is de-activated or there are
        faults preventing its transition to the 'up' state.

        up - The object is active.

"
    DEFVAL { notPresent }
    ::= { mesLagEntry 24 }

mesLagPortmaskIf1 OBJECT-TYPE
    SYNTAX      Unsigned32 (0..2147483647)
    MAX-ACCESS  read-create
    STATUS      current
    DESCRIPTION
        "The ports belonging to the link aggregation group.

        This attribute can be written via SNMP.

"
    DEFVAL { 0 }
    ::= { mesLagEntry 25 }

mesLagPortmaskIf2 OBJECT-TYPE
    SYNTAX      Unsigned32 (0..2147483647)
    MAX-ACCESS  read-create
    STATUS      current
    DESCRIPTION
        "The ports belonging to the link aggregation group.

        This attribute can be written via SNMP.

"
    DEFVAL { 0 }
    ::= { mesLagEntry 26}

mesLagPortmaskIf3 OBJECT-TYPE
    SYNTAX      Unsigned32 (0..2147483647)
    MAX-ACCESS  read-create
    STATUS      current
    DESCRIPTION
        "The ports belonging to the link aggregation group.

        This attribute can be written via SNMP.

"
    DEFVAL { 0 }
    ::= { mesLagEntry 27 }

mesLagPortmaskIf4 OBJECT-TYPE
    SYNTAX      Unsigned32 (0..2147483647)
    MAX-ACCESS  read-create
    STATUS      current
    DESCRIPTION
        "The ports belonging to the link aggregation group.

        This attribute can be written via SNMP.

"
    DEFVAL { 0 }
    ::= { mesLagEntry 28 }

mesLagPortmaskIf5 OBJECT-TYPE
    SYNTAX      Unsigned32 (0..2147483647)
    MAX-ACCESS  read-create
    STATUS      current
    DESCRIPTION
        "The ports belonging to the link aggregation group.

        This attribute can be written via SNMP.

"
    DEFVAL { 0 }
    ::= { mesLagEntry 29 }

mesLagPortmaskIf6 OBJECT-TYPE
    SYNTAX      Unsigned32 (0..2147483647)
    MAX-ACCESS  read-create
    STATUS      current
    DESCRIPTION
        "The ports belonging to the link aggregation group.

        This attribute can be written via SNMP.

"
    DEFVAL { 0 }
    ::= { mesLagEntry 30 }

mesLagPortmaskIf7 OBJECT-TYPE
    SYNTAX      Unsigned32 (0..2147483647)
    MAX-ACCESS  read-create
    STATUS      current
    DESCRIPTION
        "The ports belonging to the link aggregation group.

        This attribute can be written via SNMP.

"
    DEFVAL { 0 }
    ::= { mesLagEntry 31 }

mesLagPortmaskIf8 OBJECT-TYPE
    SYNTAX      Unsigned32 (0..2147483647)
    MAX-ACCESS  read-create
    STATUS      current
    DESCRIPTION
        "The ports belonging to the link aggregation group.

        This attribute can be written via SNMP.

"
    DEFVAL { 0 }
    ::= { mesLagEntry 32 }

mesLagMasterIfNo OBJECT-TYPE
    SYNTAX      PortNumber
    MAX-ACCESS  read-create
    STATUS      current
    DESCRIPTION
        "The interface number of the multi-connector port or port group.

"
    DEFVAL { 1 }
    ::= { mesLagEntry 33 }

mesLagMasterTxPort OBJECT-TYPE
    SYNTAX      PortNumber
    MAX-ACCESS  read-create
    STATUS      current
    DESCRIPTION
        "The TX-port of the interface.

"
    DEFVAL { 0 }
    ::= { mesLagEntry 34 }

mesLagLocalId OBJECT-TYPE
    SYNTAX      Integer32   (-1..2147483647)
    MAX-ACCESS  read-create
    STATUS      current
    DESCRIPTION
        "Id for index calculation.

"
    DEFVAL { -1 }
    ::= { mesLagEntry 35 }

mesLagPrepareConfigPortMask OBJECT-TYPE
    SYNTAX      CommandString
    MAX-ACCESS  read-only
    STATUS      current
    DESCRIPTION
        "Converts portmasks to input for dialog LagConfigure
"
    ::= { mesLagEntry 36 }

mesLagPortmaskIf9 OBJECT-TYPE
    SYNTAX      Unsigned32 (0..2147483647)
    MAX-ACCESS  read-create
    STATUS      current
    DESCRIPTION
        "The ports belonging to the link aggregation group.

        This attribute can be written via SNMP.

"
    DEFVAL { 0 }
    ::= { mesLagEntry 37 }

mesLagPortmaskIf10 OBJECT-TYPE
    SYNTAX      Unsigned32 (0..2147483647)
    MAX-ACCESS  read-create
    STATUS      current
    DESCRIPTION
        "The ports belonging to the link aggregation group.

        This attribute can be written via SNMP.

"
    DEFVAL { 0 }
    ::= { mesLagEntry 38 }

mesLagPortmaskIf11 OBJECT-TYPE
    SYNTAX      Unsigned32 (0..2147483647)
    MAX-ACCESS  read-create
    STATUS      current
    DESCRIPTION
        "The ports belonging to the link aggregation group.

        This attribute can be written via SNMP.

"
    DEFVAL { 0 }
    ::= { mesLagEntry 39 }

mesLagPortmaskIf12 OBJECT-TYPE
    SYNTAX      Unsigned32 (0..2147483647)
    MAX-ACCESS  read-create
    STATUS      current
    DESCRIPTION
        "The ports belonging to the link aggregation group.

        This attribute can be written via SNMP.

"
    DEFVAL { 0 }
    ::= { mesLagEntry 40 }

mesLagPortmaskIf13 OBJECT-TYPE
    SYNTAX      Unsigned32 (0..2147483647)
    MAX-ACCESS  read-create
    STATUS      current
    DESCRIPTION
        "The ports belonging to the link aggregation group.

        This attribute can be written via SNMP.

"
    DEFVAL { 0 }
    ::= { mesLagEntry 41 }

mesLagPortmaskIf14 OBJECT-TYPE
    SYNTAX      Unsigned32 (0..2147483647)
    MAX-ACCESS  read-create
    STATUS      current
    DESCRIPTION
        "The ports belonging to the link aggregation group.

        This attribute can be written via SNMP.

"
    DEFVAL { 0 }
    ::= { mesLagEntry 42 }

mesLagPortmaskIf15 OBJECT-TYPE
    SYNTAX      Unsigned32 (0..2147483647)
    MAX-ACCESS  read-create
    STATUS      current
    DESCRIPTION
        "The ports belonging to the link aggregation group.

        This attribute can be written via SNMP.

"
    DEFVAL { 0 }
    ::= { mesLagEntry 43 }

mesLagPortmaskIf16 OBJECT-TYPE
    SYNTAX      Unsigned32 (0..2147483647)
    MAX-ACCESS  read-create
    STATUS      current
    DESCRIPTION
        "The ports belonging to the link aggregation group.

        This attribute can be written via SNMP.

"
    DEFVAL { 0 }
    ::= { mesLagEntry 44 }

mesLagServiceId OBJECT-TYPE
    SYNTAX      ServiceIdWithNotUsed
    MAX-ACCESS  read-write
    STATUS      current
    DESCRIPTION
        "Service ID is used by TNM for multi-layer
        service and network management.
        Default value is -1. All objects that created
        from ENM will have default service ID.
        Change of the service ID may affect
        TNM service mappings.
"
    DEFVAL { -1 }
    ::= { mesLagEntry 45 }

-- ----------------------------------------------------
-- LACP group configurations
-- ----------------------------------------------------

mesLacpTable  OBJECT-TYPE
    SYNTAX      SEQUENCE OF MesLacpEntry
    MAX-ACCESS  not-accessible
    STATUS      current
    DESCRIPTION
        "The LACP group list."
    ::= { mesLacpList 1 }

mesLacpEntry OBJECT-TYPE
    SYNTAX      MesLacpEntry
    MAX-ACCESS  not-accessible
    STATUS      current
    DESCRIPTION
        "An entry in the LACP list.
"
    INDEX { mesLacpIndex }
    ::= { mesLacpTable 1 }

MesLacpEntry ::=
    SEQUENCE {
        mesLacpIndex                  Unsigned32,
        mesLacpName                   MgmtNameString,
        mesLacpInternalReference      Unsigned32,
        mesLacpLagIdentifier          DisplayString,
        mesLacpLagId                  DisplayString,
        mesLacpPortPriority           Unsigned32,
        mesLacpSelected               INTEGER,
        mesLacpReceiveState           INTEGER,
        mesLacpTransmitState          INTEGER,
        mesLacpMuxState               INTEGER,
        mesLacpActorExpired           INTEGER,
        mesLacpActorDefault           INTEGER,
        mesLacpActorDistributing      INTEGER,
        mesLacpActorCollecting        INTEGER,
        mesLacpActorSynchronization   INTEGER,
        mesLacpActorAggregation       INTEGER,
        mesLacpActorTimeout           INTEGER,
        mesLacpActorActivity          INTEGER,
        mesLacpPartnerExpired         INTEGER,
        mesLacpPartnerDefault         INTEGER,
        mesLacpPartnerDistributing    INTEGER,
        mesLacpPartnerCollecting      INTEGER,
        mesLacpPartnerSynchronization INTEGER,
        mesLacpPartnerAggregation     INTEGER,
        mesLacpPartnerTimeout         INTEGER,
        mesLacpPartnerActivity        INTEGER,
        mesLacpTxLacpPdus             Counter64,
        mesLacpRxLacpPdus             Counter64,
        mesLacpInternalIndex          Unsigned32,
        mesLacpResetCounters          INTEGER,
        mesLacpIfNo                   PortNumber,
        mesLacpTxPort                 PortNumber,
        mesLacpUpPortId               Integer32
}

mesLacpIndex OBJECT-TYPE
    SYNTAX      Unsigned32 (1..2147483647)
    MAX-ACCESS  read-only
    STATUS      current
    DESCRIPTION
        "An arbitrary index assigned to each LACP entry.
"
    ::= { mesLacpEntry 1 }

mesLacpName OBJECT-TYPE
    SYNTAX      MgmtNameString
    MAX-ACCESS  read-only
    STATUS      current
    DESCRIPTION
        "The management name of the LACP group, for example
        'lacp:1:2:lag1:1-2' (lacp:[subrack]:[slot]:[LAG identifier]:[LACP port])

"
    ::= { mesLacpEntry 2 }

mesLacpInternalReference OBJECT-TYPE
    SYNTAX      Unsigned32 (0..2147483647)
    MAX-ACCESS  read-create
    STATUS      current
    DESCRIPTION
        "For internal use only.

"
    DEFVAL { 0 }
    ::= { mesLacpEntry 3 }


mesLacpLagIdentifier OBJECT-TYPE
    SYNTAX      DisplayString
    MAX-ACCESS  read-create
    STATUS      current
    DESCRIPTION
        "Unique identifier for the LAG. Internal use.

"
    ::= { mesLacpEntry 4 }

mesLacpLagId OBJECT-TYPE
    SYNTAX      DisplayString
    MAX-ACCESS  read-only
    STATUS      current
    DESCRIPTION
        "LAG ID

        The Link Aggregation Group Identifier (LAG ID) is constructed from the following parameters for each of the communicating Systems:

        a) The System Identifier
        b) The operational Key assigned to the ports in the LAG
        c) The Port Identifier, if the link is identified as an Individual link

        The general form of the LAG ID is [(SKP), (TLQ)] where:

        - S and T are System Identifiers
        - K and L are the operational Keys assigned to a LAG by S and T respectively
        - P and Q are the Port Identifiers of the ports being attached if the LAG comprises a single Individual
           Link and zero if the LAG comprises one or more Aggregateable links

        The complete LAG ID derived from this information is represented as follows, for an Individual link:
        [(SKP), (TLQ)] = [(8000,AC-DE-48-03-67-80,0001,80,0002), (8000,AC-DE-48-03-FF-FF,00AA,80,0002)]

        The corresponding LAG ID for a set of Aggregateable links is represented as follows:
        [(SKP), (TLQ)] = [(8000,AC-DE-48-03-67-80,0001,00,0000), (8000,AC-DE-48-03-FF-FF,00AA,00,0000)]

"
    ::= { mesLacpEntry 5 }

mesLacpPortPriority OBJECT-TYPE
    SYNTAX      Unsigned32 (0..65535)
    MAX-ACCESS  read-write
    STATUS      current
    DESCRIPTION
        "Port prio

         The priority assigned to this port [0...65535]

"
    DEFVAL { 32768 }
    ::= { mesLacpEntry 6 }

mesLacpSelected OBJECT-TYPE
    SYNTAX     INTEGER {
        unselected(0),
        selected(1),
        standby(2)
    }
    MAX-ACCESS read-only
    STATUS     current
    DESCRIPTION
        "Selected

        unselected - No aggregator is currently selected.

        selected -  The selection logic has selected an appropriate aggregator.

        standby - Although the selection logic has selected an appropriate aggregator,
                  aggregation restrictions currently prevent the port from being enabled as part of the aggregation (onePlusOne Link Protection).

"
    ::= { mesLacpEntry 7 }

mesLacpReceiveState OBJECT-TYPE
    SYNTAX     INTEGER {
        expired(0),
        defaulted(1),
        current(2)
    }
    MAX-ACCESS read-only
    STATUS     current
    DESCRIPTION
        "LACP Receive state

        none - Not started

        expired - If no LACPDU is received before the current while_timer expires, the state machine enters the expired state

        defaulted - If no LACPDU is received before the current while_timer expires again, the state machine enters the defaulted state

        current - A LACPDU has been received and the state machine enters the current state

"
    ::= { mesLacpEntry 8 }

mesLacpTransmitState OBJECT-TYPE
    SYNTAX     INTEGER {
        slowPeriodic(0),
        fastPeriodic(1)
    }
    MAX-ACCESS read-only
    STATUS     current
    DESCRIPTION
        "LACP Transmit state

        fastPeriodic - Periodic transmissions are enabled at a fast transmission rate

        slowPeriodic - Periodic transmissions are enabled at a slow transmission rate

"
    ::= { mesLacpEntry 9 }

mesLacpMuxState OBJECT-TYPE
    SYNTAX     INTEGER {
        detached(0),
        attached(1),
        collectingDistributing(2)
    }
    MAX-ACCESS read-only
    STATUS     current
    DESCRIPTION
        "LACP Mux state

        detached - The link is not included in the LAG

        attached - The link has been attached to the LAG

        collectingDistributing - The link is included in the LAG and is used for traffic

"
    ::= { mesLacpEntry 10 }

mesLacpActorExpired OBJECT-TYPE
    SYNTAX     INTEGER {
       false(0),
       true(1)
    }
    MAX-ACCESS read-only
    STATUS     current
    DESCRIPTION
        "LACP actor expired

         true - Indicates that the Actors Receive machine is in the EXPIRED state
         false - Indicates that the Actors Receive machine is not in the EXPIRED state

"
    ::= { mesLacpEntry 11 }

mesLacpActorDefault OBJECT-TYPE
    SYNTAX     INTEGER {
        false(0),
        true(1)
    }
    MAX-ACCESS read-only
    STATUS     current
    DESCRIPTION
        "LACP actor defaulted

         true - Indicates that the Actors Receive machine is in the DEFAULTED state
         false - Indicates that the Actors Receive machine is not in the DEFAULTED state

"
    ::= { mesLacpEntry 12 }

mesLacpActorDistributing OBJECT-TYPE
    SYNTAX     INTEGER {
        false(0),
        true(1)
    }
    MAX-ACCESS read-only
    STATUS     current
    DESCRIPTION
        "LACP actor distributing

         true - Distribution of outgoing frames is enabled

         false - Distribution of outgoing frames is disabled

"
    ::= { mesLacpEntry 13 }

mesLacpActorCollecting OBJECT-TYPE
    SYNTAX     INTEGER {
        false(0),
        true(1)
    }
    MAX-ACCESS read-only
    STATUS     current
    DESCRIPTION
        "LACP actor collecting

         true - Distribution of incoming frames is enabled
         false - Distribution of incoming frames is disabled

"
    ::= { mesLacpEntry 14 }

mesLacpActorSynchronization OBJECT-TYPE
    SYNTAX     INTEGER {
        outOfSync(0),
        inSync(1)
    }
    MAX-ACCESS read-only
    STATUS     current
    DESCRIPTION
        "LACP Actor Synchronization

         inSync - The link is considered synchronized. It has been allocated to the correct link aggregation group, the group has been associated with a compatible aggregator, and the identity of the link aggregation group is consistent with the system ID and operational key information transmitted.

         outOfSync - The link is not synchronized. It is currently not in the right aggregation.

"
    ::= { mesLacpEntry 15 }

mesLacpActorAggregation OBJECT-TYPE
    SYNTAX     INTEGER {
        false(0),
        true(1)
    }
    MAX-ACCESS read-only
    STATUS     current
    DESCRIPTION
        "LACP Actor Aggregation.

         true - Indicates that the system considers this link to be Aggregateable; i.e., a potential candidate for aggregation

         false - The link is considered to be Individual; i.e., this link can be operated only as an individual link

"
    ::= { mesLacpEntry 16 }

mesLacpActorTimeout OBJECT-TYPE
    SYNTAX     INTEGER {
        slowPeriodic(0),
        fastPeriodic(1)
    }
    MAX-ACCESS read-only
    STATUS     current
    DESCRIPTION
        "LACP actor timeout.

        slowPeriodic - Indicates that the actor requests a slow transmission rate from its partner.
        fastPeriodic - Indicates that the actor requests a fast transmission rate from its partner.

"
    ::= { mesLacpEntry 17 }

mesLacpActorActivity OBJECT-TYPE
    SYNTAX     INTEGER {
        passive(0),
        active(1)
    }
    MAX-ACCESS read-only
    STATUS     current
    DESCRIPTION
        "Actors port activity

        active - The actor is configured for active LACP.

        passive - The actor is configured for passive LACP.


"
    ::= { mesLacpEntry 18 }

mesLacpPartnerExpired OBJECT-TYPE
    SYNTAX     INTEGER {
        false(0),
        true(1)
    }
    MAX-ACCESS read-only
    STATUS     current
    DESCRIPTION
        "LACP partner expired

         true - Indicates that the partners receive machine is in the EXPIRED state
         false - Indicates that the partners receive machine is not in the EXPIRED state

"
    ::= { mesLacpEntry 19 }

mesLacpPartnerDefault OBJECT-TYPE
    SYNTAX     INTEGER {
        false(0),
        true(1)
    }
    MAX-ACCESS read-only
    STATUS     current
    DESCRIPTION
        "LACP actor defaulted

         true - Indicates that the partners receive machine is in the DEFAULTED state
         false - Indicates that the partners receive machine is not in the DEFAULTED state

"
    ::= { mesLacpEntry 20 }

mesLacpPartnerDistributing OBJECT-TYPE
    SYNTAX     INTEGER {
        false(0),
        true(1)
    }
    MAX-ACCESS read-only
    STATUS     current
    DESCRIPTION
        "LACP partner distributing

         true - Distribution of outgoing frames is enabled

         false - Distribution of outgoing frames is disabled

"
    ::= { mesLacpEntry 21 }

mesLacpPartnerCollecting OBJECT-TYPE
    SYNTAX     INTEGER {
        false(0),
        true(1)
    }
    MAX-ACCESS read-only
    STATUS     current
    DESCRIPTION
        "LACP partner collecting

         true - Distribution of incoming frames is enabled

         false - Distribution of incoming frames is disabled

"
    ::= { mesLacpEntry 22 }

mesLacpPartnerSynchronization OBJECT-TYPE
    SYNTAX     INTEGER {
        outOfSync(0),
        inSync(1)
    }
    MAX-ACCESS read-only
    STATUS     current
    DESCRIPTION
        "LACP partner Synchronization

         inSync - The link is considered synchronized. It has been allocated to the correct link aggregation group, the group has been associated with a compatible aggregator, and the identity of the link aggregation group is consistent with the system ID and operational key information transmitted.

         outOfSync - The link is not synchronized. It is currently not in the right aggregation.


"
    ::= { mesLacpEntry 23 }

mesLacpPartnerAggregation OBJECT-TYPE
    SYNTAX     INTEGER {
        false(0),
        true(1)
    }
    MAX-ACCESS read-only
    STATUS     current
    DESCRIPTION
        "LACP partner Aggregation.

         true - Indicates that the system considers this link to be Aggregateable; i.e., a potential candidate for aggregation

         false - The link is considered to be Individual; i.e., this link can be operated only as an individual link

"
    ::= { mesLacpEntry 24 }

mesLacpPartnerTimeout OBJECT-TYPE
    SYNTAX     INTEGER {
        slowPeriodic(0),
        fastPeriodic(1)
    }
    MAX-ACCESS read-only
    STATUS     current
    DESCRIPTION
        "LACP partner timeout

        slowPeriodic - Indicates that the partner requests a slow transmission rate from its actor.
        fastPeriodic - Indicates that the partner requests a fast transmission rate from its actor.

"
    ::= { mesLacpEntry 25 }

mesLacpPartnerActivity OBJECT-TYPE
    SYNTAX     INTEGER {
        passive(0),
        active(1)
    }
    MAX-ACCESS read-only
    STATUS     current
    DESCRIPTION
        "Partner port activity

        active - The partner is configured for active LACP.

        passive - The partner is configured for passive LACP.


"
    ::= { mesLacpEntry 26 }

mesLacpTxLacpPdus OBJECT-TYPE
    SYNTAX      Counter64
    MAX-ACCESS  read-only
    STATUS      current
    DESCRIPTION
        "Number of transmitted LACPDUs.
"
    ::= { mesLacpEntry 27 }

mesLacpRxLacpPdus OBJECT-TYPE
    SYNTAX      Counter64
    MAX-ACCESS  read-only
    STATUS      current
    DESCRIPTION
        "Number of received LACPDUs.
"
    ::= { mesLacpEntry 28 }

mesLacpInternalIndex OBJECT-TYPE
    SYNTAX      Unsigned32 (0..2147483647)
    MAX-ACCESS  read-create
    STATUS      current
    DESCRIPTION
        "For internal use only.

"
    DEFVAL { 0 }
    ::= { mesLacpEntry 29 }

mesLacpResetCounters OBJECT-TYPE
    SYNTAX      INTEGER {
                    normal (1),
                    reset (2) }
    MAX-ACCESS  read-write
    STATUS      current
    DESCRIPTION
        "Reset the Tx LACPDU and Rx LACPDU counters.

"
    DEFVAL { normal }
    ::= { mesLacpEntry 30 }

mesLacpIfNo OBJECT-TYPE
    SYNTAX      PortNumber
    MAX-ACCESS  read-create
    STATUS      current
    DESCRIPTION
        "The interface number of the multi-connector port or port group.

"
    DEFVAL { 1 }
    ::= { mesLacpEntry 31 }

mesLacpTxPort OBJECT-TYPE
    SYNTAX      PortNumber
    MAX-ACCESS  read-create
    STATUS      current
    DESCRIPTION
        "The TX-port of the interface.

"
    DEFVAL { 0 }
    ::= { mesLacpEntry 32 }

mesLacpUpPortId OBJECT-TYPE
    SYNTAX      Integer32   (-1..2147483647)
    MAX-ACCESS  read-only
    STATUS      current
    DESCRIPTION
        "Internal port reference for traffic unit.
"
    DEFVAL { -1 }
    ::= { mesLacpEntry 33 }



-- ------------------------------------------------------
-- EVC BWP MAP - mapping of BWP to different prios in EVC
-- ------------------------------------------------------

mesEvcBwpMapTable  OBJECT-TYPE
    SYNTAX      SEQUENCE OF MesEvcBwpMapEntry
    MAX-ACCESS  not-accessible
    STATUS      obsolete
    DESCRIPTION
        "The BWP to EVC map list."
    ::= { mesEvcBwpMapList 1 }

mesEvcBwpMapEntry OBJECT-TYPE
    SYNTAX      MesEvcBwpMapEntry
    MAX-ACCESS  not-accessible
    STATUS      current
    DESCRIPTION
        "An entry in the CE EVC map list.
"
    INDEX { mesEvcBwpMapIndex }
    ::= { mesEvcBwpMapTable 1 }

MesEvcBwpMapEntry ::=
    SEQUENCE {
        mesEvcBwpMapIndex                     Unsigned32,
        mesEvcBwpMapName                      MgmtNameString,
        mesEvcBwpMapObjectProperty            ObjectProperty,
        mesEvcBwpMapEvcId                     MgmtNameString,
        mesEvcBwpMapBwpId                     MgmtNameString,
        mesEvcBwpMapModel                     INTEGER,
        mesEvcBwpMapPriority                  Unsigned32,
        mesEvcBwpMapInternalReference         Unsigned32,
        mesEvcBwpMapRowStatus                 RowStatus }

mesEvcBwpMapIndex OBJECT-TYPE
    SYNTAX      Unsigned32 (1..2147483647)
    MAX-ACCESS  read-only
    STATUS      current
    DESCRIPTION
        "An arbitrary index assigned to each if entry.
"
    ::= { mesEvcBwpMapEntry 1 }

mesEvcBwpMapName OBJECT-TYPE
    SYNTAX      MgmtNameString
    MAX-ACCESS  read-only
    STATUS      current
    DESCRIPTION
        "The management name of the map, for example
        'map-1'.

"
    ::= { mesEvcBwpMapEntry 2 }

mesEvcBwpMapObjectProperty  OBJECT-TYPE
    SYNTAX      ObjectProperty
    MAX-ACCESS  read-only
    STATUS      current
    DESCRIPTION
        "Property mask.

"
    ::= { mesEvcBwpMapEntry 3 }

mesEvcBwpMapEvcId OBJECT-TYPE
    SYNTAX      MgmtNameString
    MAX-ACCESS  read-create
    STATUS      current
    DESCRIPTION
        "The management name of the map, for example
        'map-1'.

"
    ::= { mesEvcBwpMapEntry 4 }

mesEvcBwpMapBwpId OBJECT-TYPE
    SYNTAX      MgmtNameString
    MAX-ACCESS  read-create
    STATUS      current
    DESCRIPTION
        "The management name of the map, for example
        'map-1'.

"
    ::= { mesEvcBwpMapEntry 5 }

mesEvcBwpMapModel OBJECT-TYPE
    SYNTAX      INTEGER {
                        none (1),
                        bwpPerUni (2),
                        bwpPerEvc (3),
                        bwpPerCos (4) }
    MAX-ACCESS  read-create
    STATUS      current
    DESCRIPTION
        "

"
    DEFVAL { bwpPerEvc }
    ::= { mesEvcBwpMapEntry 6 }

mesEvcBwpMapPriority OBJECT-TYPE
    SYNTAX      Unsigned32 (0..7)
    MAX-ACCESS  read-create
    STATUS      current
    DESCRIPTION
        "CE-VLAN ID that shall be mapped to the EVC.
         Specifies the lower end of the range.

"
    DEFVAL { 0 }
    ::= { mesEvcBwpMapEntry 7 }

mesEvcBwpMapInternalReference OBJECT-TYPE
    SYNTAX      Unsigned32 (0..2147483647)
    MAX-ACCESS  read-create
    STATUS      current
    DESCRIPTION
        "For internal use only.

"
    DEFVAL { 0 }
    ::= { mesEvcBwpMapEntry 8 }

mesEvcBwpMapRowStatus OBJECT-TYPE
    SYNTAX      RowStatus
    MAX-ACCESS  read-create
    STATUS      current
    DESCRIPTION
        "Manages creation and deletion of conceptual rows.
        See also SNMPv2-TC.

        Note: The newly created object will not necessarily
        receive the same index as used in the create
        procedure.
"
    ::= { mesEvcBwpMapEntry 9 }

-- ----------------------------------------------------
-- Port
-- ----------------------------------------------------

mesPortTable  OBJECT-TYPE
    SYNTAX      SEQUENCE OF MesPortEntry
    MAX-ACCESS  not-accessible
    STATUS      current
    DESCRIPTION
        "The Port list."
    ::= { mesPortList 1 }

mesPortEntry OBJECT-TYPE
    SYNTAX      MesPortEntry
    MAX-ACCESS  not-accessible
    STATUS      current
    DESCRIPTION
        "An entry in the Port list.
"
    INDEX { mesPortIndex }
    ::= { mesPortTable 1 }

MesPortEntry ::=
    SEQUENCE {
        mesPortIndex                      Unsigned32,
        mesPortName                       MgmtNameString,
        mesPortDescr                      DisplayString,
        mesPortSubrack                    SubrackNumber,
        mesPortSlot                       SlotNumber,
        mesPortTxPort                     PortNumber,
        mesPortRxPort                     PortNumber,
        mesPortAdminStatus                BoardOrInterfaceAdminStatus,
        mesPortOperStatus                 BoardOrInterfaceOperStatus,
        mesPortMtuSize                    Unsigned32,
        mesPortTagType                    INTEGER,
        mesPortNoOfVlans                  Unsigned32,
        mesPortVlanAware                  INTEGER,
        mesPortVlanTagged                 INTEGER,
        mesPortVlanUntagged               INTEGER,
        mesPortIngressFiltering           INTEGER,
        mesPortEgressTag                  INTEGER,
        mesPortDefaultCeVlanId            Unsigned32,
        mesPortAssociateVlan              CommandString,
        mesPortReleaseVlan                CommandString,
        mesPortActingAsLine               INTEGER,
        mesPortTrustedPortmask            Unsigned32,
        mesPortTrustedPortmaskIf2         Unsigned32,
        mesPortTrustedPortmaskIf3         Unsigned32,
        mesPortTrustedPortmaskIf4         Unsigned32,
        mesPortTrustedPortmaskIf5         Unsigned32,
        mesPortTrustedPortmaskIf6         Unsigned32,
        mesPortTrustedPortmaskIf7         Unsigned32,
        mesPortTrustedPortmaskIf8         Unsigned32,
        mesPortTrustedPortmaskIf9         Unsigned32,
        mesPortTrustedPortmaskIf10         Unsigned32,
        mesPortTrustedPortmaskIf11        Unsigned32,
        mesPortTrustedPortmaskIf12        Unsigned32,
        mesPortTrustedPortmaskIf13        Unsigned32,
        mesPortTrustedPortmaskIf14        Unsigned32,
        mesPortTrustedPortmaskIf15        Unsigned32,
        mesPortTrustedPortmaskIf16        Unsigned32,
        mesPortConfigureTrustedPortmask   CommandString,
        mesPortMacAddress                 DisplayString,
        mesPortLagStatus                  INTEGER,
        mesPortLagPortmask                Unsigned32,
        mesPortAssociateLag               CommandString,
        mesPortTxEthUtilization           Unsigned32,
        mesPortRxEthUtilization           Unsigned32,
        mesPortFlowControlMode            INTEGER,
        mesPortAutoNegotiationMode        INTEGER,
        mesPortAutoNegotiationStatus      INTEGER,
        mesPortLinkDown                   FaultStatus,
        mesPortLinkFaultRemote            FaultStatus,
        mesPortLinkFaultLocal             FaultStatus,
        mesPortNoOfShapers                Unsigned32,
        mesPortNoOfPolicers               Unsigned32,
        mesPortAssociateShaper            CommandString,
        mesPortReleaseShaper              CommandString,
        mesPortAssociatePolicer           CommandString,
        mesPortReleasePolicer             CommandString,
        mesPortRestartAutoNegotiation     CommandString,
        mesPortConfigureLine              CommandString,
        mesPortEtherType                  Unsigned32,
        mesPortConfigureEtherType         CommandString,
        mesPortNoOfMirrorSources          Unsigned32,
        mesPortMirroring                  INTEGER,
        mesPortIngressPushTag             INTEGER,
        mesPortEgressPopTag               INTEGER,
        mesPortDefaultCeVlanPriority      Unsigned32,
        mesPortConfigureTagRule           CommandString,
        mesPortCosProfile                 INTEGER,
        mesPortMode                       INTEGER,
        mesPortPrioAssignment             INTEGER,
        mesPortConfigurePrioAssignment    CommandString,
        mesPortNoOfTagRules               Unsigned32,
        mesPortNoOfVlanSchedPrios         Unsigned32,
        mesPortObjectProperty             ObjectProperty,
        mesPortHighBitErrorRate           FaultStatus,
        mesPortIdx                        Integer32,
        mesPortIfNo                       PortNumber,
        mesPortClientIdx                  Integer32,
        mesPortUpPortId                   Integer32,
        mesPortLagPortmaskIf1             Unsigned32,
        mesPortLagPortmaskIf2             Unsigned32,
        mesPortLagPortmaskIf3             Unsigned32,
        mesPortLagPortmaskIf4             Unsigned32,
        mesPortLagPortmaskIf5             Unsigned32,
        mesPortLagPortmaskIf6             Unsigned32,
        mesPortLagPortmaskIf7             Unsigned32,
        mesPortLagPortmaskIf8             Unsigned32,
        mesPortAutoNegMasterSlaveCfg      INTEGER,
        mesPortAutoNegMasterSlaveStatus   INTEGER,
        mesPortLagPortmaskIf9             Unsigned32,
        mesPortLagPortmaskIf10            Unsigned32,
        mesPortLagPortmaskIf11            Unsigned32,
        mesPortLagPortmaskIf12            Unsigned32,
        mesPortLagPortmaskIf13            Unsigned32,
        mesPortLagPortmaskIf14            Unsigned32,
        mesPortLagPortmaskIf15            Unsigned32,
        mesPortLagPortmaskIf16            Unsigned32,
        mesPortCreateVlanTagClass         CommandString,
        mesPortCreateTagRuleWoutClass     CommandString,
        mesPortServiceId                  ServiceIdWithNotUsed
        }

mesPortIndex OBJECT-TYPE
    SYNTAX      Unsigned32 (1..2147483647)
    MAX-ACCESS  read-create
    STATUS      current
    DESCRIPTION
        "An arbitrary index assigned to each Port entry.
        The index is read-only and persistent, i.e the index
        is kept over reboot and backed up by stable storage.
"
    ::= { mesPortEntry 1 }

mesPortName OBJECT-TYPE
    SYNTAX      MgmtNameString
    MAX-ACCESS  read-create
    STATUS      current
    DESCRIPTION
        "The management name of the interface, for example
        'port:1:2:1-2'.

"
    ::= { mesPortEntry 2 }

mesPortDescr OBJECT-TYPE
    SYNTAX      DisplayString
    MAX-ACCESS  read-write
    STATUS      current
    DESCRIPTION
        "User configurable label.

"
    DEFVAL { "" }
    ::= { mesPortEntry 3 }

mesPortSubrack OBJECT-TYPE
    SYNTAX      SubrackNumber
    MAX-ACCESS  read-create
    STATUS      current
    DESCRIPTION
        "The number of the subrack where the interface
        is located.

"
    ::= { mesPortEntry 4 }

mesPortSlot OBJECT-TYPE
    SYNTAX      SlotNumber
    MAX-ACCESS  read-create
    STATUS      current
    DESCRIPTION
        "The number of the slot where the interface is
        located.

"
    ::= { mesPortEntry 5 }

mesPortTxPort OBJECT-TYPE
    SYNTAX      PortNumber
    MAX-ACCESS  read-create
    STATUS      current
    DESCRIPTION
        "The TX-port of the interface.

"
    ::= { mesPortEntry 6 }

mesPortRxPort OBJECT-TYPE
    SYNTAX      PortNumber
    MAX-ACCESS  read-create
    STATUS      current
    DESCRIPTION
        "The RX-port of the interface.

"
    ::= { mesPortEntry 7 }

mesPortAdminStatus OBJECT-TYPE
    SYNTAX      BoardOrInterfaceAdminStatus
    MAX-ACCESS  read-write
    STATUS      current
    DESCRIPTION
        "The administrative state for the object.

        down - The object is de-activated.

        service - The object is activated but alarms
        are suppressed. Intended for use during service
        or re-configuration. When service is concluded
        adminStatus should be set to 'up' again.

        up - The object will be activated when
        available. Alarms are not suppressed.

"
    DEFVAL { up }
    ::= { mesPortEntry 8 }

mesPortOperStatus OBJECT-TYPE
    SYNTAX      BoardOrInterfaceOperStatus
    MAX-ACCESS  read-only
    STATUS      current
    DESCRIPTION
        "The operational state for the object.

        notPresent - The object is not available.

        down - The object is de-activated or there are
        faults preventing its transition to the 'up' state.

        up - The object is active.

"
    DEFVAL { up }
    ::= { mesPortEntry 9 }

mesPortMtuSize OBJECT-TYPE
    SYNTAX      Unsigned32(1518..10248)
    MAX-ACCESS  read-write
    STATUS      current
    DESCRIPTION
        "Max Transmission Unit (MTU) Size in bytes for the
        Port.

"
    DEFVAL { 2096 }
    ::= { mesPortEntry 10 }

mesPortTagType OBJECT-TYPE
    SYNTAX      INTEGER {
                    qTag0x8100 (1),
                    sTag0x88a8 (2),
                    other (5)}
    MAX-ACCESS  read-create
    STATUS      current
    DESCRIPTION
        "Defines what Ether Type the tag applied to the port
        shall have.

        qTag0x8100      - 802.1Q
        sTag0x88a8      - 802.1ad Service tag
        other           - Select your own ether type

"
    DEFVAL { qTag0x8100 }
    ::= { mesPortEntry 11 }

mesPortNoOfVlans OBJECT-TYPE
    SYNTAX      Unsigned32
    MAX-ACCESS  read-only
    STATUS      current
    DESCRIPTION
        "The current number of VLANs associated with this
        port.

"
    ::= { mesPortEntry 12 }

mesPortVlanAware OBJECT-TYPE
    SYNTAX      INTEGER {
                    no (1),
                    yes (2) }
    MAX-ACCESS  read-write
    STATUS      current
    DESCRIPTION
        "Define VLAN awareness on the port. A VLAN aware
         port will strip of the VLAN tag (if any) on ingress
         and classify the frame to this VLAN ID. A VLAN
         unaware port will classify the frame to the Native
         VLAN ID.

         Q-in-Q can be achieved by setting the ingress port
         VLAN unaware and the egress port to tag.

         Access ports (UNI) are VLAN unware whereas trunk
         ports (NNI) are VLAN aware.

         no - Port is VLAN unaware (use Native VLAN ID.)

         yes - Port is VLAN aware (use tagged frame VLAN ID).

"
    DEFVAL { no }
    ::= { mesPortEntry 13 }

mesPortVlanTagged OBJECT-TYPE
    SYNTAX      INTEGER {
                    no (1),
                    yes (2) }
    MAX-ACCESS  read-write
    STATUS      current
    DESCRIPTION
        "Defines whether VLAN tagged frames are
        accepted. The port must be VLAN aware to understand
        tagged frames.

        Access ports (UNI) admit all frames (untagged and
        tagged), whereas trunk ports (NNI) admit only tagged
        frames.

        no  - VLAN tagged frames are discarded.

        yes - VLAN tagged frames are accepted.

"
    DEFVAL { no }
    ::= { mesPortEntry 14 }

mesPortVlanUntagged OBJECT-TYPE
    SYNTAX      INTEGER {
                    no (1),
                    yes (2) }
    MAX-ACCESS  read-write
    STATUS      current
    DESCRIPTION
       "Defines whether untagged frames are accepted. The
        port must be VLAN aware to understand tagged frames.

        no   - Untagged frames are discarded.

        yes  - Untagged frames are accepted.

"
    DEFVAL { yes }
    ::= { mesPortEntry 15 }

mesPortIngressFiltering OBJECT-TYPE
    SYNTAX      INTEGER {
                    no (1),
                    yes (2) }
    MAX-ACCESS  read-write
    STATUS      current
    DESCRIPTION
        "Controls if frames are VLAN filtered on
        ingress. The port must be VLAN aware to understand
        tagged frames.

        no - No filtering of frames.

        yes - Frames that are classified to a VLAN that does
               not have the port as a member are discarded.

"
    DEFVAL { yes }
    ::= { mesPortEntry 16 }

mesPortEgressTag OBJECT-TYPE
    SYNTAX      INTEGER {
                    no (1),
                    yes (2) }
    MAX-ACCESS  read-write
    STATUS      current
    DESCRIPTION
        "Controls if frames are transmitted VLAN tagged.

         Access ports (UNI) do not egress tag whereas trunk
         ports (NNI) tag on egress.

         no - Transmit untagged, i.e. do not add tag on
         egress.

         yes - Transmit frames tagged, i.e. add tag on
         egress.

"
    DEFVAL { yes }
    ::= { mesPortEntry 17 }

mesPortDefaultCeVlanId OBJECT-TYPE
    SYNTAX      Unsigned32(0..4094)
    MAX-ACCESS  read-write
    STATUS      current
    DESCRIPTION
        "Native VLAN ID assigned to untagged frames. The
         default VLAN is also the untagged VLAN for the
         port.

        0 means that no Push VLAN ID is used.

        This attribute can be written via SNMP.

"
    DEFVAL { 0 }
    ::= { mesPortEntry 18 }

mesPortAssociateVlan OBJECT-TYPE
    SYNTAX      CommandString
    MAX-ACCESS  read-only
    STATUS      current
    DESCRIPTION
       "Associate VLAN ID (or range of VLAN IDs) to this port.

        VLAN ID   -   VLAN ID that shall be mapped to the ports

        Ports     -   Specifies the ports belonging to the VLAN followed by the L2 port description

        Learning  -   Defines what type of learning the VLAN shall have
                      off-no learning
                      on -independent learning

        MAC address
        limit     -   Specifies the max number of MAC address entries if learning is turned on.
                      Feature is supported in G2 and G2E boards.


        Ether type -  Specifies the ether type of the VLAN.
                      qTag0x8100-802.1Q
                      sTag0x88a8-802.1ad Service tag


        Description -  User configurable label.

        Trust ports -  Trusted port defines what other port members are trusted with this
                       port. A frame received on this ingress port can only egress to the
                       members defined in the trusted port.

"
    ::= { mesPortEntry 19 }

mesPortReleaseVlan OBJECT-TYPE
    SYNTAX      CommandString
    MAX-ACCESS  read-only
    STATUS      current
    DESCRIPTION
        "Remove all VLANs from the port.

"
    ::= { mesPortEntry 20 }

mesPortActingAsLine OBJECT-TYPE
    SYNTAX      INTEGER {
                    disabled (1),
                    enabled (2) }
    MAX-ACCESS  read-only
    STATUS      current
    DESCRIPTION
        "Defines if port is acting as line or client.

         disabled - port is acting as client.

         enabled - port is acting as line.

"
    DEFVAL { disabled }
    ::= { mesPortEntry 21 }

mesPortTrustedPortmask OBJECT-TYPE
    SYNTAX      Unsigned32 (0..4294967295)
    MAX-ACCESS  read-create
    STATUS      current
    DESCRIPTION
        "Trusted port defines what other port members are
        trusted with this port. A frame received on this
        ingress port can only egress to the members defined
        in the trusted port.

"
    DEFVAL { 4294967295 }
    ::= { mesPortEntry 22 }

mesPortConfigureTrustedPortmask OBJECT-TYPE
    SYNTAX      CommandString
    MAX-ACCESS  read-only
    STATUS      current
    DESCRIPTION
        "Select the ports that shall be trusted by this port.

        Enter trusted ports as a comma separated list of tx ports, ex:'1,3,9-13' or none, -, all or LAG name.
        When specifying a range with numbers the own tx port must be omitted.
        But if 'all' is used the system will solve this automatically.

"
    ::= { mesPortEntry 23 }

mesPortMacAddress OBJECT-TYPE
    SYNTAX      DisplayString
    MAX-ACCESS  read-only
    STATUS      current
    DESCRIPTION
        "The mac address of the port.

"
    DEFVAL { "" }
    ::= { mesPortEntry 24 }

mesPortLagStatus OBJECT-TYPE
    SYNTAX      INTEGER {
                         noLag (1),
                         master (2),
                         slave (3) }
    MAX-ACCESS  read-only
    STATUS      current
    DESCRIPTION
        "The Link Aggregation Group (LAG) status

         noLag - port does not belong to a LAG

         master - port is master in a LAG

         slave - port is slave in a LAG

"
    DEFVAL {noLag}
    ::= { mesPortEntry 25 }

mesPortLagPortmask OBJECT-TYPE
    SYNTAX      Unsigned32 (0..2147483647)
    MAX-ACCESS  read-create
    STATUS      current
    DESCRIPTION
        "Specifies the LAG ports if this ports is in a LAG. The least
         significant bit represents client 1 (port 1-2), then client 2 (port 3-4),
         then client 3 (port 5-6) etc.
"
    DEFVAL { 0 }
    ::= { mesPortEntry 26 }

mesPortAssociateLag OBJECT-TYPE
    SYNTAX      CommandString
    MAX-ACCESS  read-only
    STATUS      current
    DESCRIPTION
        "Creates a Link Aggregation Group (LAG). The
        selected ports will be used as 'slaves' in the LAG.

        Ports that are used in Ethernet Ring Protection
        (ERP) are not available for LAG.

        The selected hash algorithm will be used by all LAGs
        in this board.

"
    ::= { mesPortEntry 27 }

mesPortTxEthUtilization OBJECT-TYPE
    SYNTAX      Unsigned32 (0..1000 | 2147483646)
    MAX-ACCESS  read-only
    STATUS      current
    DESCRIPTION
        "Shows a snapshot of the current bandwidth
         utilization of the transmitted ethernet signal
         during the last second.

"
    ::= { mesPortEntry 28 }

mesPortRxEthUtilization OBJECT-TYPE
    SYNTAX      Unsigned32 (0..1000 | 2147483646)
    MAX-ACCESS  read-only
    STATUS      current
    DESCRIPTION
        "Shows a snapshot of the current bandwidth
         utilization of the received ethernet signal during
         the last second.

"
    ::= { mesPortEntry 29 }

mesPortFlowControlMode OBJECT-TYPE
    SYNTAX      INTEGER {
                        noPause (1),
                        rxPause (2),
                        txPause (3),
                        bothPause (4) }
    MAX-ACCESS  read-write
    STATUS      current
    DESCRIPTION
        "The mode for handling flow control between
         the local device and link partner.

         The PAUSE settings has the following meaning
         when auto-negotiation is enabled.

         Setting    802.3 equivalent
         -------    ----------------

         noPause    No PAUSE.

         txPause    Asymmetric PAUSE toward link partner
                    (send only).

         bothPause  Symmetric PAUSE (send and receive).

         rxPause    Both symmetric PAUSE and asymmetric
                    PAUSE toward local device (send
                    and/or receive).


         The PAUSE settings has the following meaning
         when auto-negotiation is disabled.

         Setting    Result
         -------    ------

         noPause    PAUSE frame reception and transmission
                    is disabled.

         txPause    PAUSE frame transmission is enabled.

         bothPause  PAUSE frame reception and transmission
                    is enabled.

         rxPause    PAUSE frame reception is enabled.


"
    DEFVAL { noPause }
    ::= { mesPortEntry 30 }

mesPortAutoNegotiationMode OBJECT-TYPE
    SYNTAX      INTEGER {
                         off (1),
                         on (2) }
    MAX-ACCESS  read-write
    STATUS      current
    DESCRIPTION
        "The wanted auto negotiation mode.

        off - auto negotiation process is disabled

        on - auto negotiation process is enabled

"
    DEFVAL { on }
    ::= { mesPortEntry 31 }

mesPortAutoNegotiationStatus OBJECT-TYPE
    SYNTAX      INTEGER {
                         incomplete (1),
                         halfDuplex (2),
                         fullDuplex (3),
                         halfDuplexRxPauseOn (4),
                         halfDuplexTxPauseOn (5),
                         halfDuplexRxTxPauseOn (6),
                         fullDuplexRxPauseOn (7),
                         fullDuplexTxPauseOn (8),
                         fullDuplexRxTxPauseOn (9),
                         fullDuplexFec (10),
                         fec (11) }
    MAX-ACCESS  read-only
    STATUS      current
    DESCRIPTION
        "The result of the auto negotiation procedure

         incomplete - the result is still pending

         halfDuplex - half duplex

         fullDuplex - full duplex

         halfDuplexRxPauseOn - half duplex, Rx pause on

         halfDuplexTxPauseOn - half duplex, Tx pause on

         halfDuplexRxTxPauseOn - half duplex, Rx and Tx
         pause on

         fullDuplexRxPauseOn - full duplex, Rx pause on

         fullDuplexTxPauseOn - full duplex, Tx pause on

         fullDuplexRxTxPauseOn - full duplex, Rx and Tx
         pause on

         fullDuplexFec - full duplex, forwarding error
         correction

         fec - forwarding error correction

"
    DEFVAL {incomplete}
    ::= { mesPortEntry 32 }

mesPortLinkDown OBJECT-TYPE
    SYNTAX      FaultStatus
    MAX-ACCESS  read-only
    STATUS      current
    DESCRIPTION
        "A: Failure to negotiate a connection with the
        other party.

         D: A connection is negotiated.

"
    ::= { mesPortEntry 33 }

mesPortLinkFaultRemote OBJECT-TYPE
    SYNTAX      FaultStatus
    MAX-ACCESS  read-only
    STATUS      current
    DESCRIPTION
        "Remote link fault. IEEE 802.3ah

        A: Active remote link fault indication.

        D: Inactive remote link fault indication.

"
    ::= { mesPortEntry 34 }

mesPortLinkFaultLocal OBJECT-TYPE
    SYNTAX      FaultStatus
    MAX-ACCESS  read-only
    STATUS      current
    DESCRIPTION
        "Local link fault. IEEE 802.3ah

        A: Active local link fault indication.

        D: Inactive local link fault indication.

"
    ::= { mesPortEntry 35 }

mesPortNoOfShapers OBJECT-TYPE
    SYNTAX      Unsigned32
    MAX-ACCESS  read-only
    STATUS      current
    DESCRIPTION
        "The current number of shapers associated with this
        port.

"
    DEFVAL { 0 }
    ::= { mesPortEntry 36 }

mesPortNoOfPolicers OBJECT-TYPE
    SYNTAX      Unsigned32
    MAX-ACCESS  read-only
    STATUS      current
    DESCRIPTION
        "The current number of policers associated with this
        port.

"
    DEFVAL { 0 }
    ::= { mesPortEntry 37 }

mesPortAssociateShaper OBJECT-TYPE
    SYNTAX      CommandString
    MAX-ACCESS  read-only
    STATUS      current
    DESCRIPTION
        "Create and associate an egress shaper for the port.

        Traffic shaping retains excess packets in a queue and then
        schedules the excess for later transmission.

        Identifier   - The name of the shaper.

        Rate         - Excess traffic is held back until traffic falls below set
                       limit, thus smoothing out bursts. The shaper rate scales
                       linearly from zero to line rate with a resolution of 153 kb/s.
        Burst size   - The burst size defines the maximum burst length that
                       can be sent at wire speed before the shaper rate limit is
                       applied. The burst size can range from 64B to 8kB.

        Rate and Burst size are used for the first generation boards(10xEMxp, gbe22Emxp10G).
        Maximum rate and Minimum are used for the second generation boards
        (gbe10Emxp10Gii and gbe22Emxp10Gii).

        Minimum rate - Minimum shaping rate.
                       The shaper works with the scheduler on egress and causes excess
                       traffic to be held back until traffic falls below set limit,
                       thus smoothing out bursts.

        Maximum rate - Maximum shaping rate.


        Queue        - The queue number for the shaper.

"
    ::= { mesPortEntry 38 }

mesPortReleaseShaper OBJECT-TYPE
    SYNTAX      CommandString
    MAX-ACCESS  read-only
    STATUS      current
    DESCRIPTION
        "Remove all shapers associated to the port.

"
    ::= { mesPortEntry 39 }

mesPortAssociatePolicer OBJECT-TYPE
    SYNTAX      CommandString
    MAX-ACCESS  read-only
    STATUS      current
    DESCRIPTION
        "Create and associate an ingress policer for the port.

        Traffic policing propagates bursts. When the traffic rate reaches the
        configured maximum rate, excess traffic is dropped.

        Identifier - The name of the policer.
        Rate       - The policer rate scales linearly from 64 kb/s to
                     line rate with a resolution of 64 kb/s.
        Burst size - The burst size defines the maximum burst length that
                     can be sent at wire speed before the policer rate limit
                     is applied. The burst size can range from 4kB to 4096kB.
                     The configured value will be mapped into an actual burst size
                     according to the table below:
                     4kB = Burst size                 : Actual burst size is 4kB (32 kbit)
                     4kB < Burst size < 17kB          : Actual burst size is 16kB (131 kbit)
                     17kB <= Burst size < 65kB        : Actual burst size is 64kB (524 kbit)
                     65kB <= Burst size < 257kB       : Actual burst size is 256kB (2097 kbit)
                     257kB <= Burst size < 1025kB     : Actual burst size is 1MB (8388 kbit)
                     1025kB <= Burst size <= 4096kB   : Actual burst size is 4MB (33554 kbit)
        Type       - The policer can limit different traffic types:
                     All                              : All traffic (including unknown unicast traffic)
                     Broadcast                        : Broadcast traffic
                     BroadcastMulticast               : Broadcast and multicast traffic
                     BroadcastUnknownunicast          : Broadcast and unknown unicast traffic
                     BroadcastMulticastUnknownunicast : Broadcast, multicast and unknown unicast traffic

"
    ::= { mesPortEntry 40 }

mesPortReleasePolicer OBJECT-TYPE
    SYNTAX      CommandString
    MAX-ACCESS  read-only
    STATUS      current
    DESCRIPTION
        "Remove all policers associated to the port.

"
    ::= { mesPortEntry 41 }

mesPortRestartAutoNegotiation OBJECT-TYPE
    SYNTAX                    CommandString
    MAX-ACCESS                read-only
    STATUS                    current
    DESCRIPTION
        "Issue a restart of the auto-negotiation process, regardless of
        the current state.

"
    ::= { mesPortEntry 42 }

mesPortConfigureLine OBJECT-TYPE
    SYNTAX                    CommandString
    MAX-ACCESS                read-only
    STATUS                    current
    DESCRIPTION
        "Procedure to define if the port is acting as line or client.

"
    ::= { mesPortEntry 43 }

mesPortEtherType OBJECT-TYPE
    SYNTAX      Unsigned32  (0..65535)
    MAX-ACCESS  read-create
    STATUS      current
    DESCRIPTION
        "Applicable if tag type is 'other'
         Choose your own Ether Type.

"
    DEFVAL { 33024 }
    ::= { mesPortEntry 44 }

mesPortConfigureEtherType OBJECT-TYPE
    SYNTAX      CommandString
    MAX-ACCESS  read-only
    STATUS      current
    DESCRIPTION
        "Procedure to define how frames shall be tagged.

        Sets tag type and ether type settings to be used for
        the frames.
"
    ::= { mesPortEntry 45 }

mesPortNoOfMirrorSources OBJECT-TYPE
    SYNTAX      Unsigned32
    MAX-ACCESS  read-only
    STATUS      current
    DESCRIPTION
        "The current number of mirroring sources associated
        with this port.

"
    DEFVAL { 0 }
    ::= { mesPortEntry 46 }

mesPortMirroring OBJECT-TYPE
    SYNTAX      INTEGER {
                         disabled (1),
                         enabled (2) }
    MAX-ACCESS  read-only
    STATUS      current
    DESCRIPTION
        "The mirroring status of the port

         disabled - port is not mirrored to an analyzer port

         enabled - port is mirrored to an analyser port

"
    DEFVAL { disabled }
    ::= { mesPortEntry 47 }

mesPortIngressPushTag OBJECT-TYPE
    SYNTAX      INTEGER {
                    no (1),
                    yes (2) }
    MAX-ACCESS  read-write
    STATUS      current
    DESCRIPTION
        "Controls if the port pushes (adds) a VLAN tag on
         ingress. Setting this attribute enables double
         tagging as port becomes VLAN unaware.  In this mode
         the port will always push the Native VLAN ID.

         Q-in-Q is achieved by setting the ingress port to
         push a tag and and the egress port to pop tag.

         Access ports (UNI) pushes tag on ingress whereas
         trunk ports (NNI) does not.

         yes - Push tag on ingress (use Native VLAN ID).

         no - Do not push tag on ingress if frame is
              tagged. If frame is untagged, then push Native
              VLAN ID.

"
    DEFVAL { yes }
    ::= { mesPortEntry 48 }

mesPortEgressPopTag OBJECT-TYPE
    SYNTAX      INTEGER {
                    no (1),
                    yes (2) }
    MAX-ACCESS  read-write
    STATUS      current
    DESCRIPTION
        "Controls if the port pops (removes) the VLAN tag on
        egress.

         Access ports (UNI) pops tag on egress whereas trunk
         ports (NNI) does not.

         yes - Pop tag on egress.

         no - Do not pop tag on egress.

"
    DEFVAL { no }
    ::= { mesPortEntry 49 }

mesPortDefaultCeVlanPriority OBJECT-TYPE
    SYNTAX      Unsigned32 (0..7)
    MAX-ACCESS  read-write
    STATUS      current
    DESCRIPTION
        "Priority for the default CE-VLAN ID. Priority is
        only valid for untagged traffic when 'priority
        assignment' is 'copy'.

"
    DEFVAL { 0 }
    ::= { mesPortEntry 50 }

mesPortConfigureTagRule OBJECT-TYPE
    SYNTAX      CommandString
    MAX-ACCESS  read-only
    STATUS      current
    DESCRIPTION

        "VLAN rule classification enables dynamic assignment
        of VLAN when traffic is received. Currently, only
        VLAN classification is possible.

        Classification

          The classification defines the traffic matching
          criteria for which the rule are applied.

          - Interface:  The name of the port or the lag.

          - Outer VLAN: The VLAN ID of the outer VLAN.

        Rule

          The rule defines the type of operation (pop, push
          or swap), new VLAN ID/priority and the direction
          of the traffic.

          - Type: Ingress or egress.

          - Operation: Different combinations of pop, push
                       and swap depending on the direction
                       (ingress or egress).

          - New VLAN : The new VLAN ID for a push or swap
            operation.

          - Priority assignment: Defines if a new priority
                                 is assigned or if the
                                 priority is copy from the
                                 ingress tag.

"
    ::= { mesPortEntry 51 }

mesPortCosProfile OBJECT-TYPE
    SYNTAX      INTEGER {
                    profile1 (1),
                    profile2 (2),
                    profile3 (3),
                    profile4 (4) }
    MAX-ACCESS  read-write
    STATUS      current
    DESCRIPTION
        "The COS Queue profile to which this port belongs.

"
    DEFVAL { profile1 }
    ::= { mesPortEntry 52 }

mesPortMode OBJECT-TYPE
    SYNTAX      INTEGER {
                    uni (1),
                    uniMux (2),
                    nni (3),
                    userDefined (4) }
    MAX-ACCESS  read-write
    STATUS      current
    DESCRIPTION
        "Defines the mode in which the port operates.

        uni - User Network Interface. The port is an access
              port.  This setting treats all ingress frames
              as untagged. I.e. untagged, priority tagged,
              customer tagged (0x8100), service provider
              tagged (0x88a8) frames will all be treated
              as untagged.  Ingress action:
              The native VLAN ID and priority is always
              pushed to all frames.  Egress action: The
              outermost tag is always popped.

        uniMux - Service Multiplexing User Network
                 Interface.  This settings requires a VLAN
                 rule for mapping C-VLAN frames on ingress
                 to S-VLAN frames on egress. Only C-VLAN
                 frames are treated as tagged frames.
                 Ingress action: The native VLAN ID and
                 priority is always pushed on untagged
                 frames.  Egress action: The outermost tag
                 is always popped.

        nni - Network to Network Interface. The port is an
              trunk port.  This setting treats C-VLAN and
              S-VLAN frames as tagged, all other frames are
              treated as untagged.  Ingress action: The
              native VLAN ID and priority is always pushed
              on untagged frames.  Egress action: The native
              VLAN ID is always popped.

        userDefined - Ingress push tag, egress pop tag and
                      ether type can be set individually by
                      the user.

                      Ingress push tag yes: Push the native
                      VLAN ID and priority on all ingress
                      frames.

                      Ingress push tag no: Push the native
                      VLAN ID and priority on untagged
                      ingress frames.

                      Egress pop tag yes: Pop the outermost
                      tag on all egress frames.

                      Egress pop tag no: Pop the native VLAN
                      ID on egress frames.

        Notes:

        Filtering settings gives the option to discard or
        forward tagged and untagged frames.  The meaning of
        tagged and untagged depends on the mode (uni, uniMux
        and nni).

        Customer tagged, C-VLAN and 0x8100 is the
        same. Service provider tagged, S-VLAN and 0x88a8 is
        the same.

         This attribute can be written via SNMP.

"
    DEFVAL { nni }
    ::= { mesPortEntry 53 }

mesPortPrioAssignment OBJECT-TYPE
    SYNTAX      INTEGER {
                    set (1),
                    copy (2) }
    MAX-ACCESS  read-create
    STATUS      current
    DESCRIPTION
        "Defines how the priority is assigned when pushing
         VLAN ID on ingress.

         set - Set to specified value.

         copy - Use the priority from the ingress tag.

"
    DEFVAL { set }
    ::= { mesPortEntry 54 }

mesPortConfigurePrioAssignment OBJECT-TYPE
    SYNTAX      CommandString
    MAX-ACCESS  read-only
    STATUS      current
    DESCRIPTION
        "Defines if the priority is copied from ingress tag
        or set to a specific value.

"
    ::= { mesPortEntry 55 }

mesPortNoOfTagRules OBJECT-TYPE
    SYNTAX      Unsigned32
    MAX-ACCESS  read-only
    STATUS      current
    DESCRIPTION
        "The current number of VLAN tag rules associated
        with this port.

"
    ::= { mesPortEntry 56 }

mesPortNoOfVlanSchedPrios OBJECT-TYPE
    SYNTAX      Unsigned32
    MAX-ACCESS  read-only
    STATUS      deprecated
    DESCRIPTION
        "The current number of VLAN schedule priorities
        associated with this port.

"
    ::= { mesPortEntry 57 }

mesPortObjectProperty  OBJECT-TYPE
    SYNTAX      ObjectProperty
    MAX-ACCESS  read-only
    STATUS      current
    DESCRIPTION
        "Property mask.

"
    ::= { mesPortEntry 58 }

mesPortHighBitErrorRate OBJECT-TYPE
    SYNTAX      FaultStatus
    MAX-ACCESS  read-only
    STATUS      current
    DESCRIPTION
        "High bit error rate (Hi-Ber). IEEE 802.3ah

        A: Active high bit error rate.

        D: Inactive high bit error rate.

"
    ::= { mesPortEntry 59 }


mesPortIdx OBJECT-TYPE
    SYNTAX      Integer32   (-1..2147483647)
    MAX-ACCESS  read-create
    STATUS      current
    DESCRIPTION
        "Internal object reference

"
    DEFVAL { -1  }
    ::= { mesPortEntry 60 }

mesPortIfNo OBJECT-TYPE
    SYNTAX      PortNumber
    MAX-ACCESS  read-create
    STATUS      current
    DESCRIPTION
        "The interface number of the multi-connector port or port group.

"
    DEFVAL { 1  }
    ::= { mesPortEntry 61 }

mesPortClientIdx OBJECT-TYPE
    SYNTAX      Integer32   (-1..2147483647)
    MAX-ACCESS  read-create
    STATUS      current
    DESCRIPTION
        "Internal object reference  client interface.

"
    DEFVAL { -1  }
    ::= { mesPortEntry 62 }

mesPortUpPortId OBJECT-TYPE
    SYNTAX      Integer32   (-1..2147483647)
    MAX-ACCESS  read-only
    STATUS      current
    DESCRIPTION
        "Internal port reference for traffic unit.
"
    DEFVAL { -1  }
    ::= { mesPortEntry 63 }


mesPortLagPortmaskIf1 OBJECT-TYPE
    SYNTAX      Unsigned32 (0..2147483647)
    MAX-ACCESS  read-create
    STATUS      current
    DESCRIPTION
        "Specifies the LAG ports if this ports is in a LAG. The least
         significant bit represents client 1 (port 1-2), then client 2 (port 3-4),
         then client 3 (port 5-6) etc.
"
    DEFVAL { 0 }
    ::= { mesPortEntry 64 }

mesPortLagPortmaskIf2 OBJECT-TYPE
    SYNTAX      Unsigned32 (0..2147483647)
    MAX-ACCESS  read-create
    STATUS      current
    DESCRIPTION
        "Specifies the LAG ports if this ports is in a LAG. The least
         significant bit represents client 1 (port 1-2), then client 2 (port 3-4),
         then client 3 (port 5-6) etc.
"
    DEFVAL { 0 }
    ::= { mesPortEntry 65 }

mesPortLagPortmaskIf3 OBJECT-TYPE
    SYNTAX      Unsigned32 (0..2147483647)
    MAX-ACCESS  read-create
    STATUS      current
    DESCRIPTION
        "Specifies the LAG ports if this ports is in a LAG. The least
         significant bit represents client 1 (port 1-2), then client 2 (port 3-4),
         then client 3 (port 5-6) etc.
"
    DEFVAL { 0 }
    ::= { mesPortEntry 66 }

mesPortLagPortmaskIf4 OBJECT-TYPE
    SYNTAX      Unsigned32 (0..2147483647)
    MAX-ACCESS  read-create
    STATUS      current
    DESCRIPTION
        "Specifies the LAG ports if this ports is in a LAG. The least
         significant bit represents client 1 (port 1-2), then client 2 (port 3-4),
         then client 3 (port 5-6) etc.
"
    DEFVAL { 0 }
    ::= { mesPortEntry 67 }

mesPortLagPortmaskIf5 OBJECT-TYPE
    SYNTAX      Unsigned32 (0..2147483647)
    MAX-ACCESS  read-create
    STATUS      current
    DESCRIPTION
        "Specifies the LAG ports if this ports is in a LAG. The least
         significant bit represents client 1 (port 1-2), then client 2 (port 3-4),
         then client 3 (port 5-6) etc.
"
    DEFVAL { 0 }
    ::= { mesPortEntry 68 }

mesPortLagPortmaskIf6 OBJECT-TYPE
    SYNTAX      Unsigned32 (0..2147483647)
    MAX-ACCESS  read-create
    STATUS      current
    DESCRIPTION
        "Specifies the LAG ports if this ports is in a LAG. The least
         significant bit represents client 1 (port 1-2), then client 2 (port 3-4),
         then client 3 (port 5-6) etc.
"
    DEFVAL { 0 }
    ::= { mesPortEntry 69 }

mesPortLagPortmaskIf7 OBJECT-TYPE
    SYNTAX      Unsigned32 (0..2147483647)
    MAX-ACCESS  read-create
    STATUS      current
    DESCRIPTION
        "Specifies the LAG ports if this ports is in a LAG. The least
         significant bit represents client 1 (port 1-2), then client 2 (port 3-4),
         then client 3 (port 5-6) etc.
"
    DEFVAL { 0 }
    ::= { mesPortEntry 70 }

mesPortLagPortmaskIf8 OBJECT-TYPE
    SYNTAX      Unsigned32 (0..2147483647)
    MAX-ACCESS  read-create
    STATUS      current
    DESCRIPTION
        "Specifies the LAG ports if this ports is in a LAG. The least
         significant bit represents client 1 (port 1-2), then client 2 (port 3-4),
         then client 3 (port 5-6) etc.
"
    DEFVAL { 0 }
    ::= { mesPortEntry 71 }

mesPortAutoNegMasterSlaveCfg OBJECT-TYPE
    SYNTAX      INTEGER {
                         auto (0),
                         master (1),
                         slave (2)}
    MAX-ACCESS  read-write
    STATUS      current
    DESCRIPTION
        "1000BASE-T PHYs shall provide support for Auto-Negotiation (802.3-2015 Clause 28) and shall be capable of
         operating as master or slave. This relationship is necessary for establishing the timing control of each PHY.
         The 1000BASE-T master PHY is clocked from a local source. The slave PHY uses loop timing where the clock is
         recovered from the received data stream.

         auto   - A random seed is used as input to master-slave negotiation. Should be used for non-SyncE applications
         master - Configure PHY as master during master-slave negotiation
         slave  - Configure PHY as slave during master-slave negotiation

"
    DEFVAL { auto }
    ::= { mesPortEntry 72 }

mesPortAutoNegMasterSlaveStatus OBJECT-TYPE
    SYNTAX      INTEGER {
                         undefined (0),
                         master (1),
                         slave (2) }
    MAX-ACCESS  read-only
    STATUS      current
    DESCRIPTION
        "The result of the auto negotiation master-slave procedure

         undefined - not possible to read attribute at the moment or
                     resolution of negotiation is still pending
         master    - Local PHY configuration resolved to master in auto negotiation
         slave     - Local PHY configuration resolved to slave  in auto negotiation

"
    DEFVAL {undefined}
    ::= { mesPortEntry 73 }

mesPortLagPortmaskIf9 OBJECT-TYPE
    SYNTAX      Unsigned32 (0..2147483647)
    MAX-ACCESS  read-create
    STATUS      current
    DESCRIPTION
        "Specifies the LAG ports if this ports is in a LAG. The least
         significant bit represents client 1 (port 1-2), then client 2 (port 3-4),
         then client 3 (port 5-6) etc.
"
    DEFVAL { 0 }
    ::= { mesPortEntry 74 }

mesPortLagPortmaskIf10 OBJECT-TYPE
    SYNTAX      Unsigned32 (0..2147483647)
    MAX-ACCESS  read-create
    STATUS      current
    DESCRIPTION
        "Specifies the LAG ports if this ports is in a LAG. The least
         significant bit represents client 1 (port 1-2), then client 2 (port 3-4),
         then client 3 (port 5-6) etc.
"
    DEFVAL { 0 }
    ::= { mesPortEntry 75 }

mesPortLagPortmaskIf11 OBJECT-TYPE
    SYNTAX      Unsigned32 (0..2147483647)
    MAX-ACCESS  read-create
    STATUS      current
    DESCRIPTION
        "Specifies the LAG ports if this ports is in a LAG. The least
         significant bit represents client 1 (port 1-2), then client 2 (port 3-4),
         then client 3 (port 5-6) etc.
"
    DEFVAL { 0 }
    ::= { mesPortEntry 76 }

mesPortLagPortmaskIf12 OBJECT-TYPE
    SYNTAX      Unsigned32 (0..2147483647)
    MAX-ACCESS  read-create
    STATUS      current
    DESCRIPTION
        "Specifies the LAG ports if this ports is in a LAG. The least
         significant bit represents client 1 (port 1-2), then client 2 (port 3-4),
         then client 3 (port 5-6) etc.
"
    DEFVAL { 0 }
    ::= { mesPortEntry 77 }

mesPortLagPortmaskIf13 OBJECT-TYPE
    SYNTAX      Unsigned32 (0..2147483647)
    MAX-ACCESS  read-create
    STATUS      current
    DESCRIPTION
        "Specifies the LAG ports if this ports is in a LAG. The least
         significant bit represents client 1 (port 1-2), then client 2 (port 3-4),
         then client 3 (port 5-6) etc.
"
    DEFVAL { 0 }
    ::= { mesPortEntry 78 }

mesPortLagPortmaskIf14 OBJECT-TYPE
    SYNTAX      Unsigned32 (0..2147483647)
    MAX-ACCESS  read-create
    STATUS      current
    DESCRIPTION
        "Specifies the LAG ports if this ports is in a LAG. The least
         significant bit represents client 1 (port 1-2), then client 2 (port 3-4),
         then client 3 (port 5-6) etc.
"
    DEFVAL { 0 }
    ::= { mesPortEntry 79 }

mesPortLagPortmaskIf15 OBJECT-TYPE
    SYNTAX      Unsigned32 (0..2147483647)
    MAX-ACCESS  read-create
    STATUS      current
    DESCRIPTION
        "Specifies the LAG ports if this ports is in a LAG. The least
         significant bit represents client 1 (port 1-2), then client 2 (port 3-4),
         then client 3 (port 5-6) etc.
"
    DEFVAL { 0 }
    ::= { mesPortEntry 80 }

mesPortLagPortmaskIf16 OBJECT-TYPE
    SYNTAX      Unsigned32 (0..2147483647)
    MAX-ACCESS  read-create
    STATUS      current
    DESCRIPTION
        "Specifies the LAG ports if this ports is in a LAG. The least
         significant bit represents client 1 (port 1-2), then client 2 (port 3-4),
         then client 3 (port 5-6) etc.
"
    DEFVAL { 0 }
    ::= { mesPortEntry 81 }

mesPortCreateVlanTagClass OBJECT-TYPE
        SYNTAX      CommandString
        MAX-ACCESS  read-only
        STATUS      current
        DESCRIPTION
            "Create and associate a class to a Vlan Rule Tag.
"
    ::= { mesPortEntry 82 }

mesPortCreateTagRuleWoutClass OBJECT-TYPE
    SYNTAX      CommandString
    MAX-ACCESS  read-only
    STATUS      current
    DESCRIPTION
        "VLAN rule classification enables dynamic assignment
        of VLAN when traffic is received. Currently, only
        VLAN classification is possible.

        Classification

          The classification defines the traffic matching
          criteria for which the rule are applied.

          - Interface:  The name of the port or the lag.
          - Outer VLAN: The VLAN ID of the outer VLAN.

        Rule

          The rule defines the type of operation (pop, push
          or swap), new VLAN ID/priority and the direction
          of the traffic.
          - Type: Ingress or egress.

          - Operation: Different combinations of pop, push
                       and swap depending on the direction
                       (ingress or egress).

          - New VLAN : The new VLAN ID for a push or swap
            operation.

          - Priority assignment: Defines if a new priority
                                 is assigned or if the
                                 priority is copy from the
                                 ingress tag.

"
    ::= { mesPortEntry 83 }

mesPortTrustedPortmaskIf2 OBJECT-TYPE
    SYNTAX      Unsigned32 (0..4294967295)
    MAX-ACCESS  read-create
    STATUS      current
    DESCRIPTION
        "Trusted port defines what other port members are
        trusted with this port. A frame received on this
        ingress port can only egress to the members defined
        in the trusted port.

"
    DEFVAL { 4294967295 }
    ::= { mesPortEntry 84 }

mesPortTrustedPortmaskIf3 OBJECT-TYPE
    SYNTAX      Unsigned32 (0..4294967295)
    MAX-ACCESS  read-create
    STATUS      current
    DESCRIPTION
        "Trusted port defines what other port members are
        trusted with this port. A frame received on this
        ingress port can only egress to the members defined
        in the trusted port.

"
    DEFVAL { 4294967295 }
    ::= { mesPortEntry 85 }

mesPortTrustedPortmaskIf4 OBJECT-TYPE
    SYNTAX      Unsigned32 (0..4294967295)
    MAX-ACCESS  read-create
    STATUS      current
    DESCRIPTION
        "Trusted port defines what other port members are
        trusted with this port. A frame received on this
        ingress port can only egress to the members defined
        in the trusted port.

"
    DEFVAL { 4294967295 }
    ::= { mesPortEntry 86 }

mesPortTrustedPortmaskIf5 OBJECT-TYPE
    SYNTAX      Unsigned32 (0..4294967295)
    MAX-ACCESS  read-create
    STATUS      current
    DESCRIPTION
        "Trusted port defines what other port members are
        trusted with this port. A frame received on this
        ingress port can only egress to the members defined
        in the trusted port.

"
    DEFVAL { 4294967295 }
    ::= { mesPortEntry 87 }

mesPortTrustedPortmaskIf6 OBJECT-TYPE
    SYNTAX      Unsigned32 (0..4294967295)
    MAX-ACCESS  read-create
    STATUS      current
    DESCRIPTION
        "Trusted port defines what other port members are
        trusted with this port. A frame received on this
        ingress port can only egress to the members defined
        in the trusted port.

"
    DEFVAL { 4294967295 }
    ::= { mesPortEntry 88 }

mesPortTrustedPortmaskIf7 OBJECT-TYPE
    SYNTAX      Unsigned32 (0..4294967295)
    MAX-ACCESS  read-create
    STATUS      current
    DESCRIPTION
        "Trusted port defines what other port members are
        trusted with this port. A frame received on this
        ingress port can only egress to the members defined
        in the trusted port.

"
    DEFVAL { 4294967295 }
    ::= { mesPortEntry 89 }

mesPortTrustedPortmaskIf8 OBJECT-TYPE
    SYNTAX      Unsigned32 (0..4294967295)
    MAX-ACCESS  read-create
    STATUS      current
    DESCRIPTION
        "Trusted port defines what other port members are
        trusted with this port. A frame received on this
        ingress port can only egress to the members defined
        in the trusted port.

"
    DEFVAL { 4294967295 }
    ::= { mesPortEntry 90 }

mesPortTrustedPortmaskIf9 OBJECT-TYPE
    SYNTAX      Unsigned32 (0..4294967295)
    MAX-ACCESS  read-create
    STATUS      current
    DESCRIPTION
        "Trusted port defines what other port members are
        trusted with this port. A frame received on this
        ingress port can only egress to the members defined
        in the trusted port.

"
    DEFVAL { 4294967295 }
    ::= { mesPortEntry 91 }

mesPortTrustedPortmaskIf10 OBJECT-TYPE
    SYNTAX      Unsigned32 (0..4294967295)
    MAX-ACCESS  read-create
    STATUS      current
    DESCRIPTION
        "Trusted port defines what other port members are
        trusted with this port. A frame received on this
        ingress port can only egress to the members defined
        in the trusted port.

"
    DEFVAL { 4294967295 }
    ::= { mesPortEntry 92 }

mesPortTrustedPortmaskIf11 OBJECT-TYPE
    SYNTAX      Unsigned32 (0..4294967295)
    MAX-ACCESS  read-create
    STATUS      current
    DESCRIPTION
        "Trusted port defines what other port members are
        trusted with this port. A frame received on this
        ingress port can only egress to the members defined
        in the trusted port.

"
    DEFVAL { 4294967295 }
    ::= { mesPortEntry 93 }

mesPortTrustedPortmaskIf12 OBJECT-TYPE
    SYNTAX      Unsigned32 (0..4294967295)
    MAX-ACCESS  read-create
    STATUS      current
    DESCRIPTION
        "Trusted port defines what other port members are
        trusted with this port. A frame received on this
        ingress port can only egress to the members defined
        in the trusted port.

"
    DEFVAL { 4294967295 }
    ::= { mesPortEntry 94 }

mesPortTrustedPortmaskIf13 OBJECT-TYPE
    SYNTAX      Unsigned32 (0..4294967295)
    MAX-ACCESS  read-create
    STATUS      current
    DESCRIPTION
        "Trusted port defines what other port members are
        trusted with this port. A frame received on this
        ingress port can only egress to the members defined
        in the trusted port.

"
    DEFVAL { 4294967295 }
    ::= { mesPortEntry 95 }

mesPortTrustedPortmaskIf14 OBJECT-TYPE
    SYNTAX      Unsigned32 (0..4294967295)
    MAX-ACCESS  read-create
    STATUS      current
    DESCRIPTION
        "Trusted port defines what other port members are
        trusted with this port. A frame received on this
        ingress port can only egress to the members defined
        in the trusted port.

"
    DEFVAL { 4294967295 }
    ::= { mesPortEntry 96 }

mesPortTrustedPortmaskIf15 OBJECT-TYPE
    SYNTAX      Unsigned32 (0..4294967295)
    MAX-ACCESS  read-create
    STATUS      current
    DESCRIPTION
        "Trusted port defines what other port members are
        trusted with this port. A frame received on this
        ingress port can only egress to the members defined
        in the trusted port.

"
    DEFVAL { 4294967295 }
    ::= { mesPortEntry 97 }

mesPortTrustedPortmaskIf16 OBJECT-TYPE
    SYNTAX      Unsigned32 (0..4294967295)
    MAX-ACCESS  read-create
    STATUS      current
    DESCRIPTION
        "Trusted port defines what other port members are
        trusted with this port. A frame received on this
        ingress port can only egress to the members defined
        in the trusted port.

"
    DEFVAL { 4294967295 }
    ::= { mesPortEntry 98 }

mesPortServiceId OBJECT-TYPE
    SYNTAX      ServiceIdWithNotUsed
    MAX-ACCESS  read-write
    STATUS      current
    DESCRIPTION
        "Service ID is used by TNM for multi-layer
        service and network management.
        Default value is -1. All objects that created
        from ENM will have default service ID.
        Change of the service ID may affect
        TNM service mappings.
"
    DEFVAL { -1 }
    ::= { mesPortEntry 99 }

-- ----------------------------------------------------
-- VLAN MAP - mapping of VLAN ID to ports
-- ----------------------------------------------------

mesVlanMapTable  OBJECT-TYPE
    SYNTAX      SEQUENCE OF MesVlanMapEntry
    MAX-ACCESS  not-accessible
    STATUS      current
    DESCRIPTION
        "The VLAN to port map list."
    ::= { mesVlanMapList 1 }

mesVlanMapEntry OBJECT-TYPE
    SYNTAX      MesVlanMapEntry
    MAX-ACCESS  not-accessible
    STATUS      current
    DESCRIPTION
        "An entry in the VLAN map list.
"
    INDEX { mesVlanMapIndex }
    ::= { mesVlanMapTable 1 }

MesVlanMapEntry ::=
    SEQUENCE {
        mesVlanMapIndex                      Unsigned32,
        mesVlanMapName                       MgmtNameString,
        mesVlanMapVlanIdRangeLower           Unsigned32,
        mesVlanMapVlanIdRangeUpper           Unsigned32,
        mesVlanMapInternalReference          Unsigned32,
        mesVlanMapPortmask                   Unsigned32,
        mesVlanMapConfigurePortMask          CommandString,
        mesVlanMapLearning                   INTEGER,
        mesVlanMapEtherType                  INTEGER,
        mesVlanMapRowStatus                  RowStatus,
        mesVlanMapDescr                      DisplayString,
        mesVlanMapTrustPorts                 CommandString,
        mesVlanMapRings                      Counter64,
        mesVlanMapServiceId                  ServiceIdWithNotUsed,
        mesVlanMapPortmaskIf1                Unsigned32,
        mesVlanMapPortmaskIf2                Unsigned32,
        mesVlanMapPortmaskIf3                Unsigned32,
        mesVlanMapPortmaskIf4                Unsigned32,
        mesVlanMapPortmaskIf5                Unsigned32,
        mesVlanMapPortmaskIf6                Unsigned32,
        mesVlanMapPortmaskIf7                Unsigned32,
        mesVlanMapPortmaskIf8                Unsigned32,
        mesVlanMapPrepareConfigPortMask      CommandString,
        mesVlanMapPortmaskIf9                Unsigned32,
        mesVlanMapPortmaskIf10               Unsigned32,
        mesVlanMapPortmaskIf11               Unsigned32,
        mesVlanMapPortmaskIf12               Unsigned32,
        mesVlanMapPortmaskIf13               Unsigned32,
        mesVlanMapPortmaskIf14               Unsigned32,
        mesVlanMapPortmaskIf15               Unsigned32,
        mesVlanMapPortmaskIf16               Unsigned32,
        mesVlanMapSubrack                    SubrackNumber,
        mesVlanMapSlot                       SlotNumber,
        mesVlanMapMacLearningLimit           Unsigned32
        }

mesVlanMapIndex OBJECT-TYPE
    SYNTAX      Unsigned32 (1..2147483647)
    MAX-ACCESS  read-only
    STATUS      current
    DESCRIPTION
        "An arbitrary index assigned to each VLAN entry.
"
    ::= { mesVlanMapEntry 1 }

mesVlanMapName OBJECT-TYPE
    SYNTAX      MgmtNameString
    MAX-ACCESS  read-only
    STATUS      current
    DESCRIPTION
        "The management name of the map, for example
        'map:1:3:4090-4094'.

"
    ::= { mesVlanMapEntry 2 }

mesVlanMapVlanIdRangeLower OBJECT-TYPE
    SYNTAX      Unsigned32 (0..4095)
    MAX-ACCESS  read-create
    STATUS      current
    DESCRIPTION
        "VLAN ID that shall be mapped to the ports.
         Specifies the lower end of the range.
         This attribute can be written via SNMP.

"
    DEFVAL { 1 }
    ::= { mesVlanMapEntry 3 }

mesVlanMapVlanIdRangeUpper OBJECT-TYPE
    SYNTAX      Unsigned32 (0..4095)
    MAX-ACCESS  read-create
    STATUS      current
    DESCRIPTION
        "VLAN ID that shall be mapped to the ports.
         Specifies the upper end of the range.

"
    DEFVAL { 1 }
    ::= { mesVlanMapEntry 4 }

mesVlanMapInternalReference OBJECT-TYPE
    SYNTAX      Unsigned32 (0..2147483647)
    MAX-ACCESS  read-create
    STATUS      current
    DESCRIPTION
        "For internal use only.

"
    DEFVAL { 0 }
    ::= { mesVlanMapEntry 5 }

mesVlanMapPortmask OBJECT-TYPE
    SYNTAX      Unsigned32 (0..2147483647)
    MAX-ACCESS  read-create
    STATUS      current
    DESCRIPTION
        "Specifies the ports belonging to the VLAN (VLAN range). The least
         significant bit represents client 1 (port 1-2), then client 2 (port 3-4),
         then client 3 (port 5-6) etc.

        This attribute can be written via SNMP.

"
    DEFVAL { 0 }
    ::= { mesVlanMapEntry 6 }

mesVlanMapConfigurePortMask OBJECT-TYPE
    SYNTAX      CommandString
    MAX-ACCESS  read-only
    STATUS      current
    DESCRIPTION
        "Change the ports belonging to this VLAN.
"
    ::= { mesVlanMapEntry 7 }

mesVlanMapLearning OBJECT-TYPE
    SYNTAX      INTEGER {
                    off (1),
                    on (2)}
    MAX-ACCESS  read-write
    STATUS      current
    DESCRIPTION
        "Defines what type of learning the VLAN shall have.

        off             - no learning
        on              - independent learning

        This attribute can be written via SNMP.

"
    DEFVAL { off }
    ::= { mesVlanMapEntry 8 }

mesVlanMapEtherType OBJECT-TYPE
    SYNTAX      INTEGER {
                    qTag0x8100 (1),
                    sTag0x88a8 (2)}
    MAX-ACCESS  read-write
    STATUS      current
    DESCRIPTION
        "Specifies the ether type of the VLAN.

        qTag0x8100      - 802.1Q
        sTag0x88a8      - 802.1ad Service tag

         This attribute can be written via SNMP.

"
    DEFVAL { sTag0x88a8 }
    ::= { mesVlanMapEntry 9 }

mesVlanMapRowStatus OBJECT-TYPE
    SYNTAX      RowStatus
    MAX-ACCESS  read-create
    STATUS      current
    DESCRIPTION
        "Manages creation and deletion of conceptual rows.
        See also SNMPv2-TC.

        Note: The newly created object will not necessarily
        receive the same index as used in the create
        procedure.
"
    ::= { mesVlanMapEntry 10 }

mesVlanMapDescr OBJECT-TYPE
    SYNTAX      DisplayString
    MAX-ACCESS  read-write
    STATUS      current
    DESCRIPTION
        "User configurable label.

"
    DEFVAL { "" }
    ::= { mesVlanMapEntry 11 }

mesVlanMapTrustPorts OBJECT-TYPE
    SYNTAX      CommandString
    MAX-ACCESS  read-only
    STATUS      current
    DESCRIPTION
        "Trust all ports in the VLAN.

"
    ::= { mesVlanMapEntry 12 }

mesVlanMapRings OBJECT-TYPE
    SYNTAX Counter64
    MAX-ACCESS  read-only
    STATUS      current
    DESCRIPTION
        "List of Ring Indexs of protecting ERP v2 rings.
"
    DEFVAL { 0 }
    ::= { mesVlanMapEntry 13 }

mesVlanMapServiceId OBJECT-TYPE
    SYNTAX      ServiceIdWithNotUsed
    MAX-ACCESS  read-write
    STATUS      current
    DESCRIPTION
        "Service ID is used by TNM for multi-layer
        service and network management.
        Default value is -1. All objects that created
        from ENM will have default service ID.
        Change of the service ID may affect
        TNM service mappings.
"
    DEFVAL { -1 }
    ::= { mesVlanMapEntry 14 }

mesVlanMapPortmaskIf1 OBJECT-TYPE
    SYNTAX      Unsigned32 (0..2147483647)
    MAX-ACCESS  read-create
    STATUS      current
    DESCRIPTION
        "Specifies the ports belonging to the VLAN (VLAN range).
         There is one port mask for each interface.
         The least significant bit represents client 1 (port 1-2), then client 2 (port 3-4),
         then client 3 (port 5-6) etc.

"
    DEFVAL { 0 }
    ::= { mesVlanMapEntry 15 }

mesVlanMapPortmaskIf2 OBJECT-TYPE
    SYNTAX      Unsigned32 (0..2147483647)
    MAX-ACCESS  read-create
    STATUS      current
    DESCRIPTION
        "Specifies the ports belonging to the VLAN (VLAN range).
         There is one port mask for each interface.
         The least significant bit represents client 1 (port 1-2), then client 2 (port 3-4),
         then client 3 (port 5-6) etc.

"
    DEFVAL { 0 }
    ::= { mesVlanMapEntry 16 }

mesVlanMapPortmaskIf3 OBJECT-TYPE
    SYNTAX      Unsigned32 (0..2147483647)
    MAX-ACCESS  read-create
    STATUS      current
    DESCRIPTION
        "Specifies the ports belonging to the VLAN (VLAN range).
         There is one port mask for each interface.
         The least significant bit represents client 1 (port 1-2), then client 2 (port 3-4),
         then client 3 (port 5-6) etc.

"
    DEFVAL { 0 }
    ::= { mesVlanMapEntry 17 }

mesVlanMapPortmaskIf4 OBJECT-TYPE
    SYNTAX      Unsigned32 (0..2147483647)
    MAX-ACCESS  read-create
    STATUS      current
    DESCRIPTION
        "Specifies the ports belonging to the VLAN (VLAN range).
         There is one port mask for each interface.
         The least significant bit represents client 1 (port 1-2), then client 2 (port 3-4),
         then client 3 (port 5-6) etc.

"
    DEFVAL { 0 }
    ::= { mesVlanMapEntry 18 }

mesVlanMapPortmaskIf5 OBJECT-TYPE
    SYNTAX      Unsigned32 (0..2147483647)
    MAX-ACCESS  read-create
    STATUS      current
    DESCRIPTION
        "Specifies the ports belonging to the VLAN (VLAN range).
         There is one port mask for each interface.
         The least significant bit represents client 1 (port 1-2), then client 2 (port 3-4),
         then client 3 (port 5-6) etc.

"
    DEFVAL { 0 }
    ::= { mesVlanMapEntry 19 }

mesVlanMapPortmaskIf6 OBJECT-TYPE
    SYNTAX      Unsigned32 (0..2147483647)
    MAX-ACCESS  read-create
    STATUS      current
    DESCRIPTION
        "Specifies the ports belonging to the VLAN (VLAN range).
         There is one port mask for each interface.
         The least significant bit represents client 1 (port 1-2), then client 2 (port 3-4),
         then client 3 (port 5-6) etc.

"
    DEFVAL { 0 }
    ::= { mesVlanMapEntry 20 }

mesVlanMapPortmaskIf7 OBJECT-TYPE
    SYNTAX      Unsigned32 (0..2147483647)
    MAX-ACCESS  read-create
    STATUS      current
    DESCRIPTION
        "Specifies the ports belonging to the VLAN (VLAN range).
         There is one port mask for each interface.
         The least significant bit represents client 1 (port 1-2), then client 2 (port 3-4),
         then client 3 (port 5-6) etc.

"
    DEFVAL { 0 }
    ::= { mesVlanMapEntry 21 }

mesVlanMapPortmaskIf8 OBJECT-TYPE
    SYNTAX      Unsigned32 (0..2147483647)
    MAX-ACCESS  read-create
    STATUS      current
    DESCRIPTION
        "Specifies the ports belonging to the VLAN (VLAN range).
         There is one port mask for each interface.
         The least significant bit represents client 1 (port 1-2), then client 2 (port 3-4),
         then client 3 (port 5-6) etc.

"
    DEFVAL { 0 }
    ::= { mesVlanMapEntry 22 }

mesVlanMapPrepareConfigPortMask OBJECT-TYPE
    SYNTAX      CommandString
    MAX-ACCESS  read-only
    STATUS      current
    DESCRIPTION
        "Converts portmasks to input for dialog configurePortMask
"
    ::= { mesVlanMapEntry 23 }

mesVlanMapPortmaskIf9 OBJECT-TYPE
        SYNTAX      Unsigned32 (0..2147483647)
        MAX-ACCESS  read-create
        STATUS      current
        DESCRIPTION
            "Specifies the ports belonging to the VLAN (VLAN range).
             There is one port mask for each interface.
             The least significant bit represents client 1 (port 1-2), then client 2 (port 3-4),
             then client 3 (port 5-6) etc.

"
        DEFVAL { 0 }
        ::= { mesVlanMapEntry 24 }

mesVlanMapPortmaskIf10 OBJECT-TYPE
    SYNTAX      Unsigned32 (0..2147483647)
    MAX-ACCESS  read-create
    STATUS      current
    DESCRIPTION
        "Specifies the ports belonging to the VLAN (VLAN range).
         There is one port mask for each interface.
         The least significant bit represents client 1 (port 1-2), then client 2 (port 3-4),
         then client 3 (port 5-6) etc.

"
    DEFVAL { 0 }
    ::= { mesVlanMapEntry 25 }

mesVlanMapPortmaskIf11 OBJECT-TYPE
    SYNTAX      Unsigned32 (0..2147483647)
    MAX-ACCESS  read-create
    STATUS      current
    DESCRIPTION
        "Specifies the ports belonging to the VLAN (VLAN range).
         There is one port mask for each interface.
         The least significant bit represents client 1 (port 1-2), then client 2 (port 3-4),
         then client 3 (port 5-6) etc.

"
    DEFVAL { 0 }
    ::= { mesVlanMapEntry 26 }

mesVlanMapPortmaskIf12 OBJECT-TYPE
    SYNTAX      Unsigned32 (0..2147483647)
    MAX-ACCESS  read-create
    STATUS      current
    DESCRIPTION
        "Specifies the ports belonging to the VLAN (VLAN range).
         There is one port mask for each interface.
         The least significant bit represents client 1 (port 1-2), then client 2 (port 3-4),
         then client 3 (port 5-6) etc.

"
    DEFVAL { 0 }
    ::= { mesVlanMapEntry 27 }

mesVlanMapPortmaskIf13 OBJECT-TYPE
    SYNTAX      Unsigned32 (0..2147483647)
    MAX-ACCESS  read-create
    STATUS      current
    DESCRIPTION
        "Specifies the ports belonging to the VLAN (VLAN range).
         There is one port mask for each interface.
         The least significant bit represents client 1 (port 1-2), then client 2 (port 3-4),
         then client 3 (port 5-6) etc.

"
    DEFVAL { 0 }
    ::= { mesVlanMapEntry 28 }

mesVlanMapPortmaskIf14 OBJECT-TYPE
    SYNTAX      Unsigned32 (0..2147483647)
    MAX-ACCESS  read-create
    STATUS      current
    DESCRIPTION
        "Specifies the ports belonging to the VLAN (VLAN range).
         There is one port mask for each interface.
         The least significant bit represents client 1 (port 1-2), then client 2 (port 3-4),
         then client 3 (port 5-6) etc.

"
    DEFVAL { 0 }
    ::= { mesVlanMapEntry 29 }

mesVlanMapPortmaskIf15 OBJECT-TYPE
    SYNTAX      Unsigned32 (0..2147483647)
    MAX-ACCESS  read-create
    STATUS      current
    DESCRIPTION
        "Specifies the ports belonging to the VLAN (VLAN range).
         There is one port mask for each interface.
         The least significant bit represents client 1 (port 1-2), then client 2 (port 3-4),
         then client 3 (port 5-6) etc.

"
    DEFVAL { 0 }
    ::= { mesVlanMapEntry 30 }

mesVlanMapPortmaskIf16 OBJECT-TYPE
    SYNTAX      Unsigned32 (0..2147483647)
    MAX-ACCESS  read-create
    STATUS      current
    DESCRIPTION
        "Specifies the ports belonging to the VLAN (VLAN range).
         There is one port mask for each interface.
         The least significant bit represents client 1 (port 1-2), then client 2 (port 3-4),
         then client 3 (port 5-6) etc.

"
    DEFVAL { 0 }
    ::= { mesVlanMapEntry 31 }

mesVlanMapSubrack OBJECT-TYPE
    SYNTAX      SubrackNumber
    MAX-ACCESS  read-create
    STATUS      current
    DESCRIPTION
        "The number of the subrack where the VLAN is located.

"
    ::= { mesVlanMapEntry 32 }

mesVlanMapSlot OBJECT-TYPE
    SYNTAX      SlotNumber
    MAX-ACCESS  read-create
    STATUS      current
    DESCRIPTION
        "The number of the slot where the VLAN is located.

"
    ::= { mesVlanMapEntry 33 }

mesVlanMapMacLearningLimit OBJECT-TYPE
    SYNTAX      Unsigned32 (0..262143)
    MAX-ACCESS  read-create
    STATUS      current
    DESCRIPTION

        "Max number of MAC address entries if VLAN learning is turned on.
         Value: 0 is only for internal use.

        This attribute can be written via SNMP.

"
    DEFVAL { 0 }
    ::= { mesVlanMapEntry 34 }


-- ----------------------------------------------------
-- BWP MAP - mapping of policers and shapers to ports
-- ----------------------------------------------------

mesBwpMapTable  OBJECT-TYPE
    SYNTAX      SEQUENCE OF MesBwpMapEntry
    MAX-ACCESS  not-accessible
    STATUS      current
    DESCRIPTION
        "The BWP to port map list."
    ::= { mesBwpMapList 1 }

mesBwpMapEntry OBJECT-TYPE
    SYNTAX      MesBwpMapEntry
    MAX-ACCESS  not-accessible
    STATUS      current
    DESCRIPTION
        "An entry in the BWP map list.
"
    INDEX { mesBwpMapIndex }
    ::= { mesBwpMapTable 1 }

MesBwpMapEntry ::=
    SEQUENCE {
        mesBwpMapIndex                      Unsigned32,
        mesBwpMapName                       MgmtNameString,
        mesBwpMapPortName                   MgmtNameString,
        mesBwpMapBwpName                    MgmtNameString,
        mesBwpMapInternalReference          Unsigned32 }

mesBwpMapIndex OBJECT-TYPE
    SYNTAX      Unsigned32 (1..2147483647)
    MAX-ACCESS  read-only
    STATUS      current
    DESCRIPTION
        "An arbitrary index assigned to each BWP entry.
"
    ::= { mesBwpMapEntry 1 }

mesBwpMapName OBJECT-TYPE
    SYNTAX      MgmtNameString
    MAX-ACCESS  read-only
    STATUS      current
    DESCRIPTION
        "The management name of the map, for example
        'map:1:3:1'.

"
    ::= { mesBwpMapEntry 2 }

mesBwpMapPortName OBJECT-TYPE
    SYNTAX      MgmtNameString
    MAX-ACCESS  read-create
    STATUS      current
    DESCRIPTION
        "The name of the port belonging to the BWP
        'map:1:3:1'.

"
    ::= { mesBwpMapEntry 3 }

mesBwpMapBwpName OBJECT-TYPE
    SYNTAX      MgmtNameString
    MAX-ACCESS  read-create
    STATUS      current
    DESCRIPTION
        "The name of the policer or shaper, for example
        'shaper:1:3:1'.

"
    ::= { mesBwpMapEntry 4 }

mesBwpMapInternalReference OBJECT-TYPE
    SYNTAX      Unsigned32 (0..2147483647)
    MAX-ACCESS  read-create
    STATUS      current
    DESCRIPTION
        "For internal use only.

"
    DEFVAL { 0 }
    ::= { mesBwpMapEntry 5 }

-- ----------------------------------------------------
-- MGMT VLAN
-- ----------------------------------------------------

mesMgmtVlanTable  OBJECT-TYPE
    SYNTAX      SEQUENCE OF MesMgmtVlanEntry
    MAX-ACCESS  not-accessible
    STATUS      current
    DESCRIPTION
        "The MGMT VLAN list."
    ::= { mesMgmtVlanList 1 }

mesMgmtVlanEntry OBJECT-TYPE
    SYNTAX      MesMgmtVlanEntry
    MAX-ACCESS  not-accessible
    STATUS      current
    DESCRIPTION
        "An entry in the mgmt vlan list.
"
    INDEX { mesMgmtVlanIndex }
    ::= { mesMgmtVlanTable 1 }

MesMgmtVlanEntry ::=
    SEQUENCE {
        mesMgmtVlanIndex                      Unsigned32,
        mesMgmtVlanName                       MgmtNameString,
        mesMgmtVlanDescr                      DisplayString,
        mesMgmtVlanSubrack                    SubrackNumber,
        mesMgmtVlanSlot                       SlotNumber,
        mesMgmtVlanTxPort                     PortNumber,
        mesMgmtVlanRxPort                     PortNumber,
        mesMgmtVlanObjectProperty             ObjectProperty,
        mesMgmtVlanAdminStatus                BoardOrInterfaceAdminStatus,
        mesMgmtVlanConfigure                  CommandString,
        mesMgmtVlanTagType                    INTEGER,
        mesMgmtVlanEtherType                  Unsigned32,
        mesMgmtVlanVlanId                     Unsigned32,
        mesMgmtVlanPriority                   Unsigned32,
        mesMgmtVlanMacInMac                   INTEGER,
        mesMgmtVlanMacInMacIsid               Unsigned32,
        mesMgmtVlanMacInMacDa                 DisplayString,
        mesMgmtVlanForceMgmtVlan              INTEGER,
        mesMgmtVlanRings                      Counter64,
        mesMgmtVlanIfNo                       PortNumber
        }


mesMgmtVlanIndex OBJECT-TYPE
    SYNTAX      Unsigned32 (1..2147483647)
    MAX-ACCESS  read-only
    STATUS      current
    DESCRIPTION
        "An arbitrary index assigned to each MGMT VLAN entry.
"
    ::= { mesMgmtVlanEntry 1 }

mesMgmtVlanName OBJECT-TYPE
    SYNTAX      MgmtNameString
    MAX-ACCESS  read-only
    STATUS      current
    DESCRIPTION
        "The management name of the interface, for example
        'mgmtVlan:1:2:1-2'.

"
    ::= { mesMgmtVlanEntry 2 }

mesMgmtVlanDescr OBJECT-TYPE
    SYNTAX      DisplayString
    MAX-ACCESS  read-write
    STATUS      current
    DESCRIPTION
        "User configurable label.

"
    DEFVAL { "" }
    ::= { mesMgmtVlanEntry 3 }

mesMgmtVlanSubrack OBJECT-TYPE
    SYNTAX      SubrackNumber
    MAX-ACCESS  read-only
    STATUS      current
    DESCRIPTION
        "The number of the subrack where the interface
        is located.

"
    ::= { mesMgmtVlanEntry 4 }

mesMgmtVlanSlot OBJECT-TYPE
    SYNTAX      SlotNumber
    MAX-ACCESS  read-only
    STATUS      current
    DESCRIPTION
        "The number of the slot where the interface is
        located.

"
    ::= { mesMgmtVlanEntry 5 }

mesMgmtVlanTxPort OBJECT-TYPE
    SYNTAX      PortNumber
    MAX-ACCESS  read-only
    STATUS      current
    DESCRIPTION
        "The TX-port of the interface.

"
    ::= { mesMgmtVlanEntry 6 }

mesMgmtVlanRxPort OBJECT-TYPE
    SYNTAX      PortNumber
    MAX-ACCESS  read-only
    STATUS      current
    DESCRIPTION
        "The RX-port of the interface.

"
    ::= { mesMgmtVlanEntry 7 }

mesMgmtVlanObjectProperty  OBJECT-TYPE
    SYNTAX      ObjectProperty
    MAX-ACCESS  read-only
    STATUS      current
    DESCRIPTION
        "Property mask.

"
    ::= { mesMgmtVlanEntry 8 }

mesMgmtVlanAdminStatus OBJECT-TYPE
    SYNTAX      BoardOrInterfaceAdminStatus
    MAX-ACCESS  read-write
    STATUS      current
    DESCRIPTION
        "The administrative state for the object.

        down - The object is de-activated.

        service - The object is activated but alarms
        are suppressed. Intended for use during service
        or re-configuration. When service is concluded
        adminStatus should be set to 'up' again.

        up - The object will be activated when
        available. Alarms are not suppressed.

"
    DEFVAL { down }
    ::= { mesMgmtVlanEntry 9 }

mesMgmtVlanConfigure OBJECT-TYPE
    SYNTAX      CommandString
    MAX-ACCESS  read-only
    STATUS      current
    DESCRIPTION
        "Procedure to define how the management
        frames shall be tagged.

        Sets tag type, ether type, VLAN id, priority
        and Mac-In-Mac settings to be used for the
        management frames. Note! tag type, priority
        and Mac-In-Mac settings cannot be set on all
        type of boards that supports Mgmt VLAN.

"
    ::= { mesMgmtVlanEntry 10 }

mesMgmtVlanTagType OBJECT-TYPE
    SYNTAX      INTEGER {
                    qTag0x8100 (1),
                    sTag0x88a8 (2)}
    MAX-ACCESS  read-create
    STATUS      current
    DESCRIPTION
        "Defines what Tag Type the tag applied
         to the mgmt VLAN shall have.

        qTag0x8100      - 802.1Q
        sTag0x88a8      - 802.1ad Service tag


"
    DEFVAL { qTag0x8100 }
    ::= { mesMgmtVlanEntry 11 }

mesMgmtVlanEtherType OBJECT-TYPE
    SYNTAX      Unsigned32  (0..65535)
    MAX-ACCESS  read-create
    STATUS      current
    DESCRIPTION
        "A two-octet value for the Ether Type in the ethernet frame.

"
    DEFVAL { 0 }
    ::= { mesMgmtVlanEntry 12 }

mesMgmtVlanVlanId OBJECT-TYPE
    SYNTAX      Unsigned32 (1..4094)
    MAX-ACCESS  read-create
    STATUS      current
    DESCRIPTION
        "The VLAN-ID of the management VLAN.

"
    DEFVAL { 4094 }
    ::= { mesMgmtVlanEntry 13 }

mesMgmtVlanPriority OBJECT-TYPE
    SYNTAX      Unsigned32 (0..7)
    MAX-ACCESS  read-create
    STATUS      current
    DESCRIPTION
        "Priority value for the mgmt VLAN.

         This value will be used in the priority
         field of the mgmt VLAN tag.

"
    DEFVAL { 0 }
    ::= { mesMgmtVlanEntry 14 }

mesMgmtVlanMacInMac OBJECT-TYPE
    SYNTAX      INTEGER {
                    disabled (1),
                    enabled (2) }
    MAX-ACCESS  read-create
    STATUS      current
    DESCRIPTION
        "The Mac-in-Mac encapsulation that can be enabled/disabled.

        disabled Mac-In-Mac not used on Mgmt VLAN port.

        enabled  Mac-In-Mac used on Mgmt VLAN port.

"
    DEFVAL { disabled }
    ::= { mesMgmtVlanEntry 15 }

mesMgmtVlanMacInMacIsid OBJECT-TYPE
    SYNTAX      Unsigned32(256..16777214)
    MAX-ACCESS  read-create
    STATUS      current
    DESCRIPTION
        "The I-SID is the 24-bit service instance identifier
         that identifies the frame in a Provider Backbone Net-
         work.

"
    DEFVAL { 256 }
    ::= { mesMgmtVlanEntry 16 }

mesMgmtVlanMacInMacDa OBJECT-TYPE
    SYNTAX      DisplayString
    MAX-ACCESS  read-create
    STATUS      current
    DESCRIPTION
        "The Mac-in-Mac DA is the destination backbone

"
    DEFVAL { "" }
    ::= { mesMgmtVlanEntry 17 }

mesMgmtVlanForceMgmtVlan OBJECT-TYPE
    SYNTAX      INTEGER {
                    disabled (1),
                    enabled (2) }
    MAX-ACCESS  read-write
    STATUS      current
    DESCRIPTION
        "Force Mgmnt VLAN

         When disabled, Mgmnt VLAN will lose connectivity when
         fault is detected on the incoming line (Loss of Signal,
         Far End Client Fail, Alarm Indication Signal,
         Local Fault, Remote Fault)
         When enabling Force Mgmnt VLAN, faults on the incoming
         line will be overrided to keep Mgmnt VLAN connectivity.
         Note that the propagation of Local Fault/Remote fault
         will be affected.

         Default: disabled

         Range: enabled/disabled

"
    DEFVAL { disabled }
    ::= { mesMgmtVlanEntry 18 }

mesMgmtVlanRings OBJECT-TYPE
    SYNTAX Counter64
    MAX-ACCESS  read-only
    STATUS      current
    DESCRIPTION
        "List of ERPv2 ring indexes of protecting rings for managment vlan,
"
    DEFVAL { 0 }
    ::= { mesMgmtVlanEntry 19 }

mesMgmtVlanIfNo OBJECT-TYPE
    SYNTAX      PortNumber
    MAX-ACCESS  read-create
    STATUS      current
    DESCRIPTION
        "The interface number of the multi-connector port or port group.

"
    DEFVAL { 1  }
    ::= { mesMgmtVlanEntry 20 }


-- ----------------------------------------------------
-- Policing - band-width profile
-- ----------------------------------------------------

mesPolicingTable OBJECT-TYPE
    SYNTAX      SEQUENCE OF MesPolicingEntry
    MAX-ACCESS  not-accessible
    STATUS      current
    DESCRIPTION
        "The policing list."
    ::= { mesPolicingList 1 }

mesPolicingEntry OBJECT-TYPE
    SYNTAX      MesPolicingEntry
    MAX-ACCESS  not-accessible
    STATUS      current
    DESCRIPTION
        "An entry in the policing list.
"
    INDEX { mesPolicingIndex }
    ::= { mesPolicingTable 1 }

MesPolicingEntry ::=
    SEQUENCE {
        mesPolicingIndex             Unsigned32,
        mesPolicingName              MgmtNameString,
        mesPolicingRate              Unsigned32,
        mesPolicingBurstSize         Unsigned32,
        mesPolicingType              INTEGER,
        mesPolicingInternalReference Unsigned32,
        mesPolicingIdentifier        DisplayString,
        mesPolicingUpId              Unsigned32,
        mesPolicingBurstSize2        Unsigned32,
        mesPolicingId                Integer32 }

mesPolicingIndex OBJECT-TYPE
    SYNTAX      Unsigned32 (1..2147483647)
    MAX-ACCESS  read-only
    STATUS      current
    DESCRIPTION
        "An arbitrary index assigned to each policer entry.
"
    ::= { mesPolicingEntry 1 }

mesPolicingName OBJECT-TYPE
    SYNTAX      MgmtNameString
    MAX-ACCESS  read-only
    STATUS      current
    DESCRIPTION
        "The management name of the policer, for example
        'policer:1:4:0'.

"
    ::= { mesPolicingEntry 2 }

mesPolicingRate OBJECT-TYPE
    SYNTAX      Unsigned32 (0..100000000)
    MAX-ACCESS  read-write
    STATUS      current
    DESCRIPTION
        "The policer limits traffic on ingress and causes
        excess traffic to be dropped. The policer rate
        scales linearly from zero to line rate with a
        resolution of 153 kb/s.

        The policer ignores BPDU and GARP frames. Policing
        limits ingress traffic rate, but it does not smooth
        out traffic bursts, unlike shaping.

"
    DEFVAL { 0 }
    ::= { mesPolicingEntry 3 }

mesPolicingBurstSize OBJECT-TYPE
    SYNTAX      Unsigned32 (0..16320)
    MAX-ACCESS  read-write
    STATUS      current
    DESCRIPTION
        "The policer burst size defines the maximum burst
        length that can be sent at wire speed before the
        policer rate limit is applied.

        The burst size can range from 64B to 16kB.

"
    DEFVAL { 0 }
    ::= { mesPolicingEntry 4 }

mesPolicingType OBJECT-TYPE
    SYNTAX      INTEGER {
                    all (1),
                    broadcast (2),
                    broadcastMulticast (3),
                    broadcastUnknownunicast (4),
                    broadcastMulticastUnknownunicast (5)}
    MAX-ACCESS  read-create
    STATUS      current
    DESCRIPTION
        "The policer can limit different traffic types
        which is useful for achieving storm control.

"
    DEFVAL { all }
    ::= { mesPolicingEntry 5 }

mesPolicingInternalReference OBJECT-TYPE
    SYNTAX      Unsigned32 (0..2147483647)
    MAX-ACCESS  read-create
    STATUS      obsolete
    DESCRIPTION
        "For internal use only.

"
    DEFVAL { 0 }
    ::= { mesPolicingEntry 6 }

mesPolicingIdentifier OBJECT-TYPE
    SYNTAX      DisplayString(SIZE(1..20))
    MAX-ACCESS  read-create
    STATUS      current
    DESCRIPTION
        "Unique identifier for the policer.

"
    DEFVAL { " " }
    ::= { mesPolicingEntry 7 }

mesPolicingUpId OBJECT-TYPE
    SYNTAX      Unsigned32   (0..2147483647)
    MAX-ACCESS  read-only
    STATUS      current
    DESCRIPTION
        "Internal reference for the policer in the traffic unit.
"
    DEFVAL { 0  }
    ::= { mesPolicingEntry 8 }

mesPolicingBurstSize2 OBJECT-TYPE
    SYNTAX      Unsigned32 (0..4096)
    MAX-ACCESS  read-write
    STATUS      current
    DESCRIPTION
        "The policer burst size defines the maximum burst
        length that can be sent at wire speed before the
        policer rate limit is applied.

        The burst size can range from 4kB to 4096kB.

        The configured value will be mapped into an actual burst size
        according to the table below:
        4kB = Burst size                  : Actual burst size is 4kB (32 kbit)
        4kB < Burst size < 17kB           : Actual burst size is 16kB (131 kbit)
        17kB <= Burst size < 65kB         : Actual burst size is 64kB (524 kbit)
        65kB <= Burst size < 257kB        : Actual burst size is 256kB (2097 kbit)
        257kB <= Burst size < 1025kB      : Actual burst size is 1MB (8388 kbit)
        1025kB <= Burst size <= 4096kB    : Actual burst size is 4MB (33554 kbit)

"
    DEFVAL { 0 }
    ::= { mesPolicingEntry 9 }

mesPolicingId OBJECT-TYPE
    SYNTAX      Integer32   (-1..2147483647)
    MAX-ACCESS  read-create
    STATUS      current
    DESCRIPTION
        "Unique persistent identifier for policer and Internal reference for the policer in the traffic unit.

"
    DEFVAL { -1 }
    ::= { mesPolicingEntry 10 }

-- ----------------------------------------------------
-- Shaping - band-width profile
-- ----------------------------------------------------

mesShapingTable OBJECT-TYPE
    SYNTAX      SEQUENCE OF MesShapingEntry
    MAX-ACCESS  not-accessible
    STATUS      current
    DESCRIPTION
        "The shaping list."
    ::= { mesShapingList 1 }

mesShapingEntry OBJECT-TYPE
    SYNTAX      MesShapingEntry
    MAX-ACCESS  not-accessible
    STATUS      current
    DESCRIPTION
        "An entry in the shaping list.
"
    INDEX { mesShapingIndex }
    ::= { mesShapingTable 1 }

MesShapingEntry ::=
    SEQUENCE {
        mesShapingIndex             Unsigned32,
        mesShapingName              MgmtNameString,
        mesShapingRate              Unsigned32,
        mesShapingBurstSize         Unsigned32,
        mesShapingQueue             Unsigned32,
        mesShapingInternalReference Unsigned32,
        mesShapingExcess            INTEGER,
        mesShapingIdentifier        DisplayString,
        mesShapingMinRate           Unsigned32,
        mesShapingLocalId           Integer32}

mesShapingIndex OBJECT-TYPE
    SYNTAX      Unsigned32 (1..2147483647)
    MAX-ACCESS  read-only
    STATUS      current
    DESCRIPTION
        "An arbitrary index assigned to each shaper entry.
"
    ::= { mesShapingEntry 1 }

mesShapingName OBJECT-TYPE
    SYNTAX      MgmtNameString
    MAX-ACCESS  read-only
    STATUS      current
    DESCRIPTION
        "The management name of the shaper, for example
        'bwp-1'.

"
    ::= { mesShapingEntry 2 }

mesShapingRate OBJECT-TYPE
    SYNTAX      Unsigned32 (0..100000000)
    MAX-ACCESS  read-write
    STATUS      current
    DESCRIPTION
        "The shaper works with the scheduler on egress and
        causes excess traffic to be held back until traffic
        falls below set limit, thus smoothing out
        bursts. The shaper rate scales linearly from zero to
        line rate with a resolution of 153 kb/s.  For the
        first generation boards(10xEMxp, gbe22Emxp10G), this
        value is the shaping rate.  For the second
        generation boards(gbe10Emxp10Gii and
        gbe22Emxp10Gii), this value is the maximum shaping
        rate.

"
    DEFVAL { 0 }
    ::= { mesShapingEntry 3 }

mesShapingBurstSize OBJECT-TYPE
    SYNTAX      Unsigned32 (0..8128)
    MAX-ACCESS  read-write
    STATUS      current
    DESCRIPTION
        "The shaper burst size defines the maximum burst
        length that can be sent at wire speed before the
        shaper rate limit is applied.

        The burst size can range from 64B to 8kB.

"
    DEFVAL { 0 }
    ::= { mesShapingEntry 4 }

mesShapingQueue OBJECT-TYPE
    SYNTAX      Unsigned32 (1..8)
    MAX-ACCESS  read-create
    STATUS      current
    DESCRIPTION
        "The queue number for this shaper.

"
    DEFVAL { 1 }
    ::= { mesShapingEntry 5 }

mesShapingInternalReference OBJECT-TYPE
    SYNTAX      Unsigned32 (0..2147483647)
    MAX-ACCESS  read-create
    STATUS      obsolete
    DESCRIPTION
        "For internal use only.

"
    DEFVAL { 0 }
    ::= { mesShapingEntry 6 }

mesShapingExcess OBJECT-TYPE
    SYNTAX      INTEGER {
                    disabled (1),
                    enabled (2) }
    MAX-ACCESS  read-write
    STATUS      current
    DESCRIPTION
       "The shaper excess parameter allows the queue to use
        more bandwidth if all other shapers are
        satisfied. If more than one shaper has the excess
        flag set, then the queues arbitrate in strict
        priority order.

"
    DEFVAL { disabled }
    ::= { mesShapingEntry 7 }

mesShapingIdentifier OBJECT-TYPE
    SYNTAX      DisplayString(SIZE(1..21))
    MAX-ACCESS  read-create
    STATUS      current
    DESCRIPTION
        "Unique identifier for the shaper.

"
    DEFVAL { " " }
    ::= { mesShapingEntry 8 }

mesShapingMinRate OBJECT-TYPE
    SYNTAX      Unsigned32 (0..100000000)
    MAX-ACCESS  read-write
    STATUS      current
    DESCRIPTION
        "The shaper works with the scheduler on egress and
        causes excess traffic to be held back until traffic
        falls below set limit, thus smoothing out
        bursts. The shaper rate scales linearly from zero to
        line rate with a resolution of 153 kb/s.  Minimum
        shaping rate is only used on the second generation
        boards (gbe10Emxp10Gii, gbe22Emxp10Gii, emxp80Gii,
        emxp40Gii, emxp48iie, emxp62iie, emxp120iie,
        emxp220iie, emxp240iie, emxp3, emxp440, hdea1600 ).

"
    DEFVAL { 0 }
    ::= { mesShapingEntry 9 }

mesShapingLocalId OBJECT-TYPE
    SYNTAX      Integer32   (-1..2147483647)
    MAX-ACCESS  read-only
    STATUS      current
    DESCRIPTION
        "Id for index calculation.

"
    DEFVAL { -1 }
    ::= { mesShapingEntry 10 }

-- ----------------------------------------------------
-- COS group configurations
-- ----------------------------------------------------

mesCosTable     OBJECT-TYPE
    SYNTAX      SEQUENCE OF MesCosEntry
    MAX-ACCESS  not-accessible
    STATUS      current
    DESCRIPTION
        "The COS group list."
    ::= { mesCosList 1 }

mesCosEntry OBJECT-TYPE
    SYNTAX      MesCosEntry
    MAX-ACCESS  not-accessible
    STATUS      current
    DESCRIPTION
        "An entry in the COS list.
"
    INDEX { mesCosIndex }
    ::= { mesCosTable 1 }

MesCosEntry ::=
    SEQUENCE {
        mesCosIndex                 Unsigned32,
        mesCosName                  MgmtNameString,
        mesCosTxPort                PortNumber,
        mesCosMap                   INTEGER,
        mesCosPriority0             INTEGER,
        mesCosPriority1             INTEGER,
        mesCosPriority2             INTEGER,
        mesCosPriority3             INTEGER,
        mesCosPriority4             INTEGER,
        mesCosPriority5             INTEGER,
        mesCosPriority6             INTEGER,
        mesCosPriority7             INTEGER }

mesCosIndex OBJECT-TYPE
    SYNTAX      Unsigned32 (1..2147483647)
    MAX-ACCESS  read-only
    STATUS      current
    DESCRIPTION
        "An arbitrary index assigned to each COS entry.
"
    ::= { mesCosEntry 1 }

mesCosName OBJECT-TYPE
    SYNTAX      MgmtNameString
    MAX-ACCESS  read-only
    STATUS      current
    DESCRIPTION
        "The management name of the COS group, for example 'cos:1:2:2'.

"
    ::= { mesCosEntry 2 }

mesCosTxPort OBJECT-TYPE
    SYNTAX      PortNumber
    MAX-ACCESS  read-create
    STATUS      current
    DESCRIPTION
        "The TX-port of the interface.

"
    ::= { mesCosEntry 3 }

mesCosMap         OBJECT-TYPE
    SYNTAX        INTEGER {
                  disabled (1),
                  enabled (2) }
    MAX-ACCESS  read-write
    STATUS      current
    DESCRIPTION
        "Cos map states if the CoS group is enabled or not.
         Possible values enabled or disabled.

"
    DEFVAL { enabled }
    ::= { mesCosEntry 4 }

mesCosPriority0 OBJECT-TYPE
    SYNTAX      INTEGER {
                q1 (1),
                q2 (2),
                q3 (3),
                q4 (4),
                q5 (5),
                q6 (6),
                q7 (7),
                q8 (8) }
    MAX-ACCESS  read-write
    STATUS      current
    DESCRIPTION
        "The queue that should have user priority 0.

"
    DEFVAL { q1 }
    ::= { mesCosEntry 5 }

mesCosPriority1 OBJECT-TYPE
    SYNTAX      INTEGER {
                q1 (1),
                q2 (2),
                q3 (3),
                q4 (4),
                q5 (5),
                q6 (6),
                q7 (7),
                q8 (8) }
    MAX-ACCESS  read-write
    STATUS      current
    DESCRIPTION
        "The queue that should have priority 1.

"
    DEFVAL { q1 }
    ::= { mesCosEntry 6 }

mesCosPriority2 OBJECT-TYPE
    SYNTAX      INTEGER {
                q1 (1),
                q2 (2),
                q3 (3),
                q4 (4),
                q5 (5),
                q6 (6),
                q7 (7),
                q8 (8) }
    MAX-ACCESS  read-write
    STATUS      current
    DESCRIPTION
        "The queue that should have priority 2.

"
    DEFVAL { q1 }
    ::= { mesCosEntry 7 }

mesCosPriority3 OBJECT-TYPE
    SYNTAX      INTEGER {
                q1 (1),
                q2 (2),
                q3 (3),
                q4 (4),
                q5 (5),
                q6 (6),
                q7 (7),
                q8 (8) }
    MAX-ACCESS  read-write
    STATUS      current
    DESCRIPTION
        "The queue that should have priority 3.

"
    DEFVAL { q1 }
    ::= { mesCosEntry 8 }

mesCosPriority4 OBJECT-TYPE
    SYNTAX      INTEGER {
                q1 (1),
                q2 (2),
                q3 (3),
                q4 (4),
                q5 (5),
                q6 (6),
                q7 (7),
                q8 (8) }
    MAX-ACCESS  read-write
    STATUS      current
    DESCRIPTION
        "The queue that should have priority 4.

"
    DEFVAL { q1 }
    ::= { mesCosEntry 9 }

mesCosPriority5 OBJECT-TYPE
    SYNTAX      INTEGER {
                q1 (1),
                q2 (2),
                q3 (3),
                q4 (4),
                q5 (5),
                q6 (6),
                q7 (7),
                q8 (8) }
    MAX-ACCESS  read-write
    STATUS      current
    DESCRIPTION
        "The queue that should have priority 5.

"
    DEFVAL { q1 }
    ::= { mesCosEntry 10 }

mesCosPriority6 OBJECT-TYPE
    SYNTAX      INTEGER {
                q1 (1),
                q2 (2),
                q3 (3),
                q4 (4),
                q5 (5),
                q6 (6),
                q7 (7),
                q8 (8) }
    MAX-ACCESS  read-write
    STATUS      current
    DESCRIPTION
        "The queue that should have priority 6.

"
    DEFVAL { q1 }
    ::= { mesCosEntry 11 }

mesCosPriority7 OBJECT-TYPE
    SYNTAX      INTEGER {
                q1 (1),
                q2 (2),
                q3 (3),
                q4 (4),
                q5 (5),
                q6 (6),
                q7 (7),
                q8 (8) }
    MAX-ACCESS  read-write
    STATUS      current
    DESCRIPTION
        "The queue that should have priority 7.

"
    DEFVAL { q1 }
    ::= { mesCosEntry 12 }

-- ----------------------------------------------------
-- COS Profile group configurations
-- ----------------------------------------------------

mesCosProfileTable     OBJECT-TYPE
    SYNTAX      SEQUENCE OF MesCosProfileEntry
    MAX-ACCESS  not-accessible
    STATUS      current
    DESCRIPTION
        "The COS Profile group list."
    ::= { mesCosProfileList 1 }

mesCosProfileEntry OBJECT-TYPE
    SYNTAX      MesCosProfileEntry
    MAX-ACCESS  not-accessible
    STATUS      current
    DESCRIPTION
        "An entry in the COS Profile list.
"
    INDEX { mesCosProfileIndex }
    ::= { mesCosProfileTable 1 }

MesCosProfileEntry ::=
    SEQUENCE {
        mesCosProfileIndex             Unsigned32,
        mesCosProfileName              MgmtNameString,
        mesCosProfilePortmask          Unsigned32,
        mesCosProfilePortmaskIf1       Unsigned32,
        mesCosProfilePortmaskIf2       Unsigned32,
        mesCosProfilePortmaskIf3       Unsigned32,
        mesCosProfilePortmaskIf4       Unsigned32,
        mesCosProfilePortmaskIf5       Unsigned32,
        mesCosProfilePortmaskIf6       Unsigned32,
        mesCosProfilePortmaskIf7       Unsigned32,
        mesCosProfilePortmaskIf8       Unsigned32,
        mesCosProfileScheduler         INTEGER,
        mesCosProfileWeight0           Unsigned32,
        mesCosProfileWeight1           Unsigned32,
        mesCosProfileWeight2           Unsigned32,
        mesCosProfileWeight3           Unsigned32,
        mesCosProfileWeight4           Unsigned32,
        mesCosProfileWeight5           Unsigned32,
        mesCosProfileWeight6           Unsigned32,
        mesCosProfileWeight7           Unsigned32,
        mesCosProfilePriority0         INTEGER,
        mesCosProfilePriority1         INTEGER,
        mesCosProfilePriority2         INTEGER,
        mesCosProfilePriority3         INTEGER,
        mesCosProfilePriority4         INTEGER,
        mesCosProfilePriority5         INTEGER,
        mesCosProfilePriority6         INTEGER,
        mesCosProfilePriority7         INTEGER,
        mesCosProfileConfigureScheduler CommandString,
        mesCosProfileIngressPcpDecoding INTEGER,
        mesCosProfileIngressDeiDecoding INTEGER,
        mesCosProfileIngressColor0      INTEGER,
        mesCosProfileIngressColor1      INTEGER,
        mesCosProfileIngressColor2      INTEGER,
        mesCosProfileIngressColor3      INTEGER,
        mesCosProfileIngressColor4      INTEGER,
        mesCosProfileIngressColor5      INTEGER,
        mesCosProfileIngressColor6      INTEGER,
        mesCosProfileIngressColor7      INTEGER,
        mesCosProfileEgressPcpEncoding INTEGER,
        mesCosProfileEgressDeiEncoding INTEGER,
        mesCosProfileEgressPcpGreen0 Unsigned32,
        mesCosProfileEgressPcpGreen1 Unsigned32,
        mesCosProfileEgressPcpGreen2 Unsigned32,
        mesCosProfileEgressPcpGreen3 Unsigned32,
        mesCosProfileEgressPcpGreen4 Unsigned32,
        mesCosProfileEgressPcpGreen5 Unsigned32,
        mesCosProfileEgressPcpGreen6 Unsigned32,
        mesCosProfileEgressPcpGreen7 Unsigned32,
        mesCosProfileEgressPcpYellow0 Unsigned32,
        mesCosProfileEgressPcpYellow1 Unsigned32,
        mesCosProfileEgressPcpYellow2 Unsigned32,
        mesCosProfileEgressPcpYellow3 Unsigned32,
        mesCosProfileEgressPcpYellow4 Unsigned32,
        mesCosProfileEgressPcpYellow5 Unsigned32,
        mesCosProfileEgressPcpYellow6 Unsigned32,
        mesCosProfileEgressPcpYellow7 Unsigned32,
        mesCosProfilePortmaskIf9      Unsigned32,
        mesCosProfilePortmaskIf10     Unsigned32,
        mesCosProfilePortmaskIf11     Unsigned32,
        mesCosProfilePortmaskIf12     Unsigned32,
        mesCosProfilePortmaskIf13     Unsigned32,
        mesCosProfilePortmaskIf14     Unsigned32,
        mesCosProfilePortmaskIf15     Unsigned32,
        mesCosProfilePortmaskIf16     Unsigned32
        }

mesCosProfileIndex OBJECT-TYPE
    SYNTAX      Unsigned32 (1..2147483647)
    MAX-ACCESS  read-only
    STATUS      current
    DESCRIPTION
        "An arbitrary index assigned to each COS Profile entry.
"
    ::= { mesCosProfileEntry 1 }

mesCosProfileName OBJECT-TYPE
    SYNTAX      MgmtNameString
    MAX-ACCESS  read-only
    STATUS      current
    DESCRIPTION
        "The management name of the COS Profile group, for
        example 'cos:1:2:2'.

"
    ::= { mesCosProfileEntry 2 }

mesCosProfilePortmask OBJECT-TYPE
    SYNTAX      Unsigned32 (0..2147483647)
    MAX-ACCESS  read-create
    STATUS      current
    DESCRIPTION
        "The ports that the profile applies to.

"
    DEFVAL { 0 }
    ::= { mesCosProfileEntry 3 }

mesCosProfileScheduler OBJECT-TYPE
    SYNTAX      INTEGER {
                strict (1),
                rr (2),
                wrr (3) }
    MAX-ACCESS  read-create
    STATUS      current
    DESCRIPTION
        "The scheduler type for the queue.

        strict - strict priority

        rr - round robin

        wrr - weighted round robin

"
    DEFVAL { strict }
    ::= { mesCosProfileEntry 4 }

mesCosProfileWeight0 OBJECT-TYPE
    SYNTAX      Unsigned32 (0..127)
    MAX-ACCESS  read-create
    STATUS      current
    DESCRIPTION
        "The weight for prio 0 when scheduler is WRR.

"
    DEFVAL { 1 }
    ::= { mesCosProfileEntry 5 }

mesCosProfileWeight1 OBJECT-TYPE
    SYNTAX      Unsigned32 (0..127)
    MAX-ACCESS  read-create
    STATUS      current
    DESCRIPTION
        "The weight for prio 1 when scheduler is WRR.

"
    DEFVAL { 1 }
    ::= { mesCosProfileEntry 6 }

mesCosProfileWeight2 OBJECT-TYPE
    SYNTAX      Unsigned32 (0..127)
    MAX-ACCESS  read-create
    STATUS      current
    DESCRIPTION
        "The weight for prio 2 when scheduler is WRR.

"
    DEFVAL { 1 }
    ::= { mesCosProfileEntry 7 }

mesCosProfileWeight3 OBJECT-TYPE
    SYNTAX      Unsigned32 (0..127)
    MAX-ACCESS  read-create
    STATUS      current
    DESCRIPTION
        "The weight for prio 3 when scheduler is WRR.

"
    DEFVAL { 1 }
    ::= { mesCosProfileEntry 8 }

mesCosProfileWeight4 OBJECT-TYPE
    SYNTAX      Unsigned32 (0..127)
    MAX-ACCESS  read-create
    STATUS      current
    DESCRIPTION
        "The weight for prio 4 when scheduler is WRR.

"
    DEFVAL { 1 }
    ::= { mesCosProfileEntry 9 }

mesCosProfileWeight5 OBJECT-TYPE
    SYNTAX      Unsigned32 (0..127)
    MAX-ACCESS  read-create
    STATUS      current
    DESCRIPTION
        "The weight for prio 5 when scheduler is WRR.

"
    DEFVAL { 1 }
    ::= { mesCosProfileEntry 10 }

mesCosProfileWeight6 OBJECT-TYPE
    SYNTAX      Unsigned32 (0..127)
    MAX-ACCESS  read-create
    STATUS      current
    DESCRIPTION
        "The weight for prio 6 when scheduler is WRR.

"
    DEFVAL { 1 }
    ::= { mesCosProfileEntry 11 }

mesCosProfileWeight7 OBJECT-TYPE
    SYNTAX      Unsigned32 (0..127)
    MAX-ACCESS  read-create
    STATUS      current
    DESCRIPTION
        "The weight for prio 7 when scheduler is WRR.

"
    DEFVAL { 1 }
    ::= { mesCosProfileEntry 12 }

mesCosProfilePriority0 OBJECT-TYPE
    SYNTAX      INTEGER {
                q1 (1),
                q2 (2),
                q3 (3),
                q4 (4),
                q5 (5),
                q6 (6),
                q7 (7),
                q8 (8) }
    MAX-ACCESS  read-write
    STATUS      current
    DESCRIPTION
        "The queue that should have user priority 0.

"
    DEFVAL { q1 }
    ::= { mesCosProfileEntry 13 }

mesCosProfilePriority1 OBJECT-TYPE
    SYNTAX      INTEGER {
                q1 (1),
                q2 (2),
                q3 (3),
                q4 (4),
                q5 (5),
                q6 (6),
                q7 (7),
                q8 (8) }
    MAX-ACCESS  read-write
    STATUS      current
    DESCRIPTION
        "The queue that should have user priority 1.

"
    DEFVAL { q2 }
    ::= { mesCosProfileEntry 14 }

mesCosProfilePriority2 OBJECT-TYPE
    SYNTAX      INTEGER {
                q1 (1),
                q2 (2),
                q3 (3),
                q4 (4),
                q5 (5),
                q6 (6),
                q7 (7),
                q8 (8) }
    MAX-ACCESS  read-write
    STATUS      current
    DESCRIPTION
        "The queue that should have user priority 2.

"
    DEFVAL { q3 }
    ::= { mesCosProfileEntry 15 }

mesCosProfilePriority3 OBJECT-TYPE
    SYNTAX      INTEGER {
                q1 (1),
                q2 (2),
                q3 (3),
                q4 (4),
                q5 (5),
                q6 (6),
                q7 (7),
                q8 (8) }
    MAX-ACCESS  read-write
    STATUS      current
    DESCRIPTION
        "The queue that should have user priority 3.

"
    DEFVAL { q4 }
    ::= { mesCosProfileEntry 16 }

mesCosProfilePriority4 OBJECT-TYPE
    SYNTAX      INTEGER {
                q1 (1),
                q2 (2),
                q3 (3),
                q4 (4),
                q5 (5),
                q6 (6),
                q7 (7),
                q8 (8) }
    MAX-ACCESS  read-write
    STATUS      current
    DESCRIPTION
        "The queue that should have user priority 4.

"
    DEFVAL { q5 }
    ::= { mesCosProfileEntry 17 }

mesCosProfilePriority5 OBJECT-TYPE
    SYNTAX      INTEGER {
                q1 (1),
                q2 (2),
                q3 (3),
                q4 (4),
                q5 (5),
                q6 (6),
                q7 (7),
                q8 (8) }
    MAX-ACCESS  read-write
    STATUS      current
    DESCRIPTION
        "The queue that should have user priority 5.

"
    DEFVAL { q6 }
    ::= { mesCosProfileEntry 18 }

mesCosProfilePriority6 OBJECT-TYPE
    SYNTAX      INTEGER {
                q1 (1),
                q2 (2),
                q3 (3),
                q4 (4),
                q5 (5),
                q6 (6),
                q7 (7),
                q8 (8) }
    MAX-ACCESS  read-write
    STATUS      current
    DESCRIPTION
        "The queue that should have user priority 6.

"
    DEFVAL { q7 }
    ::= { mesCosProfileEntry 19 }

mesCosProfilePriority7 OBJECT-TYPE
    SYNTAX      INTEGER {
                q1 (1),
                q2 (2),
                q3 (3),
                q4 (4),
                q5 (5),
                q6 (6),
                q7 (7),
                q8 (8) }
    MAX-ACCESS  read-write
    STATUS      current
    DESCRIPTION
        "The queue that should have user priority 7.

"
    DEFVAL { q8 }
    ::= { mesCosProfileEntry 20 }

mesCosProfileConfigureScheduler OBJECT-TYPE
    SYNTAX      CommandString
    MAX-ACCESS  read-only
    STATUS      current
    DESCRIPTION
        "Change the the scheduler type of this profile.
"
    ::= { mesCosProfileEntry 21 }

mesCosProfileIngressPcpDecoding OBJECT-TYPE
    SYNTAX      INTEGER {
                disabled (1),
                userDefined (2),
                pcp8P0D (3),
                pcp7P1D (4),
                pcp6P2D (5),
                pcp5P3D (6) }
    MAX-ACCESS  read-write
    STATUS      current
    DESCRIPTION
        "

"
    DEFVAL { disabled }
    ::= { mesCosProfileEntry 22 }

mesCosProfileIngressDeiDecoding OBJECT-TYPE
    SYNTAX      INTEGER {
                disabled (1),
                enabled (2) }
    MAX-ACCESS  read-write
    STATUS      current
    DESCRIPTION
        "

"
    DEFVAL { enabled }
    ::= { mesCosProfileEntry 23 }

mesCosProfileIngressColor0 OBJECT-TYPE
    SYNTAX      INTEGER {
                green (1),
                yellow (2) }
    MAX-ACCESS  read-write
    STATUS      current
    DESCRIPTION
        "

"
    DEFVAL { green }
    ::= { mesCosProfileEntry 24 }

mesCosProfileIngressColor1 OBJECT-TYPE
    SYNTAX      INTEGER {
                green (1),
                yellow (2) }
    MAX-ACCESS  read-write
    STATUS      current
    DESCRIPTION
        "

"
    DEFVAL { green }
    ::= { mesCosProfileEntry 25 }

mesCosProfileIngressColor2 OBJECT-TYPE
    SYNTAX      INTEGER {
                green (1),
                yellow (2) }
    MAX-ACCESS  read-write
    STATUS      current
    DESCRIPTION
        "

"
    DEFVAL { green }
    ::= { mesCosProfileEntry 26 }

mesCosProfileIngressColor3 OBJECT-TYPE
    SYNTAX      INTEGER {
                green (1),
                yellow (2) }
    MAX-ACCESS  read-write
    STATUS      current
    DESCRIPTION
        "

"
    DEFVAL { green }
    ::= { mesCosProfileEntry 27 }

mesCosProfileIngressColor4 OBJECT-TYPE
    SYNTAX      INTEGER {
                green (1),
                yellow (2) }
    MAX-ACCESS  read-write
    STATUS      current
    DESCRIPTION
        "

"
    DEFVAL { green }
    ::= { mesCosProfileEntry 28 }

mesCosProfileIngressColor5 OBJECT-TYPE
    SYNTAX      INTEGER {
                green (1),
                yellow (2) }
    MAX-ACCESS  read-write
    STATUS      current
    DESCRIPTION
        "

"
    DEFVAL { green }
    ::= { mesCosProfileEntry 29 }

mesCosProfileIngressColor6 OBJECT-TYPE
    SYNTAX      INTEGER {
                green (1),
                yellow (2) }
    MAX-ACCESS  read-write
    STATUS      current
    DESCRIPTION
        "

"
    DEFVAL { green }
    ::= { mesCosProfileEntry 30 }

mesCosProfileIngressColor7 OBJECT-TYPE
    SYNTAX      INTEGER {
                green (1),
                yellow (2) }
    MAX-ACCESS  read-write
    STATUS      current
    DESCRIPTION
        "

"
    DEFVAL { green }
    ::= { mesCosProfileEntry 31 }

mesCosProfileEgressPcpEncoding OBJECT-TYPE
    SYNTAX      INTEGER {
                disabled (1),
                userDefined (2),
                pcp8P0D (3),
                pcp7P1D (4),
                pcp6P2D (5),
                pcp5P3D (6) }
    MAX-ACCESS  read-write
    STATUS      current
    DESCRIPTION
        "

"
    DEFVAL { disabled }
    ::= { mesCosProfileEntry 32 }

mesCosProfileEgressDeiEncoding OBJECT-TYPE
    SYNTAX      INTEGER {
                disabled (1),
                enabled (2) }
    MAX-ACCESS  read-write
    STATUS      current
    DESCRIPTION
        "

"
    DEFVAL { disabled }
    ::= { mesCosProfileEntry 33 }

mesCosProfileEgressPcpGreen0 OBJECT-TYPE
    SYNTAX      Unsigned32 (0..7)
    MAX-ACCESS  read-write
    STATUS      current
    DESCRIPTION
        "

"
    DEFVAL { 0 }
    ::= { mesCosProfileEntry 34 }

mesCosProfileEgressPcpGreen1 OBJECT-TYPE
    SYNTAX      Unsigned32 (0..7)
    MAX-ACCESS  read-write
    STATUS      current
    DESCRIPTION
        "

"
    DEFVAL { 1 }
    ::= { mesCosProfileEntry 35 }

mesCosProfileEgressPcpGreen2 OBJECT-TYPE
    SYNTAX      Unsigned32 (0..7)
    MAX-ACCESS  read-write
    STATUS      current
    DESCRIPTION
        "

"
    DEFVAL { 2 }
    ::= { mesCosProfileEntry 36 }

mesCosProfileEgressPcpGreen3 OBJECT-TYPE
    SYNTAX      Unsigned32 (0..7)
    MAX-ACCESS  read-write
    STATUS      current
    DESCRIPTION
        "

"
    DEFVAL { 3 }
    ::= { mesCosProfileEntry 37 }

mesCosProfileEgressPcpGreen4 OBJECT-TYPE
    SYNTAX      Unsigned32 (0..7)
    MAX-ACCESS  read-write
    STATUS      current
    DESCRIPTION
        "

"
    DEFVAL { 4 }
    ::= { mesCosProfileEntry 38 }

mesCosProfileEgressPcpGreen5 OBJECT-TYPE
    SYNTAX      Unsigned32 (0..7)
    MAX-ACCESS  read-write
    STATUS      current
    DESCRIPTION
        "

"
    DEFVAL { 5 }
    ::= { mesCosProfileEntry 39 }

mesCosProfileEgressPcpGreen6 OBJECT-TYPE
    SYNTAX      Unsigned32 (0..7)
    MAX-ACCESS  read-write
    STATUS      current
    DESCRIPTION
        "

"
    DEFVAL { 6 }
    ::= { mesCosProfileEntry 40 }

mesCosProfileEgressPcpGreen7 OBJECT-TYPE
    SYNTAX      Unsigned32 (0..7)
    MAX-ACCESS  read-write
    STATUS      current
    DESCRIPTION
        "

"
    DEFVAL { 7 }
    ::= { mesCosProfileEntry 41 }

mesCosProfileEgressPcpYellow0 OBJECT-TYPE
    SYNTAX      Unsigned32 (0..7)
    MAX-ACCESS  read-write
    STATUS      current
    DESCRIPTION
        "

"
    DEFVAL { 0 }
    ::= { mesCosProfileEntry 42 }

mesCosProfileEgressPcpYellow1 OBJECT-TYPE
    SYNTAX      Unsigned32 (0..7)
    MAX-ACCESS  read-write
    STATUS      current
    DESCRIPTION
        "

"
    DEFVAL { 1 }
    ::= { mesCosProfileEntry 43 }

mesCosProfileEgressPcpYellow2 OBJECT-TYPE
    SYNTAX      Unsigned32 (0..7)
    MAX-ACCESS  read-write
    STATUS      current
    DESCRIPTION
        "

"
    DEFVAL { 2 }
    ::= { mesCosProfileEntry 44 }

mesCosProfileEgressPcpYellow3 OBJECT-TYPE
    SYNTAX      Unsigned32 (0..7)
    MAX-ACCESS  read-write
    STATUS      current
    DESCRIPTION
        "

"
    DEFVAL { 3 }
    ::= { mesCosProfileEntry 45 }

mesCosProfileEgressPcpYellow4 OBJECT-TYPE
    SYNTAX      Unsigned32 (0..7)
    MAX-ACCESS  read-write
    STATUS      current
    DESCRIPTION
        "

"
    DEFVAL { 4 }
    ::= { mesCosProfileEntry 46 }

mesCosProfileEgressPcpYellow5 OBJECT-TYPE
    SYNTAX      Unsigned32 (0..7)
    MAX-ACCESS  read-write
    STATUS      current
    DESCRIPTION
        "

"
    DEFVAL { 5 }
    ::= { mesCosProfileEntry 47 }

mesCosProfileEgressPcpYellow6 OBJECT-TYPE
    SYNTAX      Unsigned32 (0..7)
    MAX-ACCESS  read-write
    STATUS      current
    DESCRIPTION
        "

"
    DEFVAL { 6 }
    ::= { mesCosProfileEntry 48 }

mesCosProfileEgressPcpYellow7 OBJECT-TYPE
    SYNTAX      Unsigned32 (0..7)
    MAX-ACCESS  read-write
    STATUS      current
    DESCRIPTION
        "

"
    DEFVAL { 7 }
    ::= { mesCosProfileEntry 49 }

mesCosProfilePortmaskIf1 OBJECT-TYPE
    SYNTAX      Unsigned32 (0..2147483647)
    MAX-ACCESS  read-create
    STATUS      current
    DESCRIPTION
        "The ports that the profile applies to.

"
    DEFVAL { 0 }
    ::= { mesCosProfileEntry 50 }

mesCosProfilePortmaskIf2 OBJECT-TYPE
    SYNTAX      Unsigned32 (0..2147483647)
    MAX-ACCESS  read-create
    STATUS      current
    DESCRIPTION
        "The ports that the profile applies to.

"
    DEFVAL { 0 }
    ::= { mesCosProfileEntry 51 }

mesCosProfilePortmaskIf3 OBJECT-TYPE
    SYNTAX      Unsigned32 (0..2147483647)
    MAX-ACCESS  read-create
    STATUS      current
    DESCRIPTION
        "The ports that the profile applies to.

"
    DEFVAL { 0 }
    ::= { mesCosProfileEntry 52 }

mesCosProfilePortmaskIf4 OBJECT-TYPE
    SYNTAX      Unsigned32 (0..2147483647)
    MAX-ACCESS  read-create
    STATUS      current
    DESCRIPTION
        "The ports that the profile applies to.

"
    DEFVAL { 0 }
    ::= { mesCosProfileEntry 53 }

mesCosProfilePortmaskIf5 OBJECT-TYPE
    SYNTAX      Unsigned32 (0..2147483647)
    MAX-ACCESS  read-create
    STATUS      current
    DESCRIPTION
        "The ports that the profile applies to.

"
    DEFVAL { 0 }
    ::= { mesCosProfileEntry 54 }

mesCosProfilePortmaskIf6 OBJECT-TYPE
    SYNTAX      Unsigned32 (0..2147483647)
    MAX-ACCESS  read-create
    STATUS      current
    DESCRIPTION
        "The ports that the profile applies to.

"
    DEFVAL { 0 }
    ::= { mesCosProfileEntry 55 }

mesCosProfilePortmaskIf7 OBJECT-TYPE
    SYNTAX      Unsigned32 (0..2147483647)
    MAX-ACCESS  read-create
    STATUS      current
    DESCRIPTION
        "The ports that the profile applies to.

"
    DEFVAL { 0 }
    ::= { mesCosProfileEntry 56 }

mesCosProfilePortmaskIf8 OBJECT-TYPE
    SYNTAX      Unsigned32 (0..2147483647)
    MAX-ACCESS  read-create
    STATUS      current
    DESCRIPTION
        "The ports that the profile applies to.

"
    DEFVAL { 0 }
    ::= { mesCosProfileEntry 57 }

mesCosProfilePortmaskIf9 OBJECT-TYPE
    SYNTAX      Unsigned32 (0..2147483647)
    MAX-ACCESS  read-create
    STATUS      current
    DESCRIPTION
        "The ports that the profile applies to.

"
    DEFVAL { 0 }
    ::= { mesCosProfileEntry 58 }

mesCosProfilePortmaskIf10 OBJECT-TYPE
    SYNTAX      Unsigned32 (0..2147483647)
    MAX-ACCESS  read-create
    STATUS      current
    DESCRIPTION
        "The ports that the profile applies to.

"
    DEFVAL { 0 }
    ::= { mesCosProfileEntry 59 }

mesCosProfilePortmaskIf11 OBJECT-TYPE
    SYNTAX      Unsigned32 (0..2147483647)
    MAX-ACCESS  read-create
    STATUS      current
    DESCRIPTION
        "The ports that the profile applies to.

"
    DEFVAL { 0 }
    ::= { mesCosProfileEntry 60 }

mesCosProfilePortmaskIf12 OBJECT-TYPE
    SYNTAX      Unsigned32 (0..2147483647)
    MAX-ACCESS  read-create
    STATUS      current
    DESCRIPTION
        "The ports that the profile applies to.

"
    DEFVAL { 0 }
    ::= { mesCosProfileEntry 61 }

mesCosProfilePortmaskIf13 OBJECT-TYPE
    SYNTAX      Unsigned32 (0..2147483647)
    MAX-ACCESS  read-create
    STATUS      current
    DESCRIPTION
        "The ports that the profile applies to.

"
    DEFVAL { 0 }
    ::= { mesCosProfileEntry 62 }

mesCosProfilePortmaskIf14 OBJECT-TYPE
    SYNTAX      Unsigned32 (0..2147483647)
    MAX-ACCESS  read-create
    STATUS      current
    DESCRIPTION
        "The ports that the profile applies to.

"
    DEFVAL { 0 }
    ::= { mesCosProfileEntry 63 }

mesCosProfilePortmaskIf15 OBJECT-TYPE
    SYNTAX      Unsigned32 (0..2147483647)
    MAX-ACCESS  read-create
    STATUS      current
    DESCRIPTION
        "The ports that the profile applies to.

"
    DEFVAL { 0 }
    ::= { mesCosProfileEntry 64 }

mesCosProfilePortmaskIf16 OBJECT-TYPE
    SYNTAX      Unsigned32 (0..2147483647)
    MAX-ACCESS  read-create
    STATUS      current
    DESCRIPTION
        "The ports that the profile applies to.

"
    DEFVAL { 0 }
    ::= { mesCosProfileEntry 65 }


-- ----------------------------------------------------
-- Mirroring group configurations
-- ----------------------------------------------------

mesMirroringTable     OBJECT-TYPE
    SYNTAX      SEQUENCE OF MesMirroringEntry
    MAX-ACCESS  not-accessible
    STATUS      current
    DESCRIPTION
        "The mirroring group list.

         Port mirroring is a method of monitoring traffic
         that forwards a copy of each packet from one port
         (source) to another port (destination) where the
         packet can be studied. Port mirroring is used as a
         diagnostic tool or debugging feature. "
    ::= { mesMirroringList 1 }

mesMirroringEntry OBJECT-TYPE
    SYNTAX      MesMirroringEntry
    MAX-ACCESS  not-accessible
    STATUS      current
    DESCRIPTION
        "An entry in the mirroring list.
"
    INDEX { mesMirroringIndex }
    ::= { mesMirroringTable 1 }

MesMirroringEntry ::=
    SEQUENCE {
        mesMirroringIndex                 Unsigned32,
        mesMirroringName                  MgmtNameString,
        mesMirroringDestination           Unsigned32,
        mesMirroringDirection             INTEGER,
        mesMirroringConfigureDestination  CommandString,
        mesMirroringDestInterface         PortNumber,
        mesMirroringDestTxPort            PortNumber,
        mesMirroringIfNo                  PortNumber,
        mesMirroringTxPort                PortNumber }

mesMirroringIndex OBJECT-TYPE
    SYNTAX      Unsigned32 (1..2147483647)
    MAX-ACCESS  read-only
    STATUS      current
    DESCRIPTION
        "An arbitrary index assigned to each interface entry.
"
    ::= { mesMirroringEntry 1 }

mesMirroringName OBJECT-TYPE
    SYNTAX      MgmtNameString
    MAX-ACCESS  read-only
    STATUS      current
    DESCRIPTION
        "The management name of the mirroring source, for
        example 'mirror:1:2:1-2'.

"
    ::= { mesMirroringEntry 2 }

mesMirroringDestination OBJECT-TYPE
    SYNTAX      Unsigned32 (0..2147483647)
    MAX-ACCESS  read-create
    STATUS      current
    DESCRIPTION
        "The analyzer port, to which traffic is
        mirrored. Only one analyzer port per board is
        allowed for EMXP.

"
    DEFVAL { 0 }
    ::= { mesMirroringEntry 3 }

mesMirroringDirection OBJECT-TYPE
    SYNTAX        INTEGER {
                  ingress (1),
                  egress (2),
                  both (3) }
    MAX-ACCESS  read-write
    STATUS      current
    DESCRIPTION
        "The direction of the mirrored traffic.

"
    DEFVAL { both }
    ::= { mesMirroringEntry 4 }

mesMirroringConfigureDestination OBJECT-TYPE
    SYNTAX      CommandString
    MAX-ACCESS  read-only
    STATUS      current
    DESCRIPTION
        "Defines the mirroring destination (analyzer) for the
        selected port. Only one destination port per board is
        allowed. If 'Not selected' is chosen, the destination
        port will be removed.

"
    ::= { mesMirroringEntry 5 }

mesMirroringDestInterface OBJECT-TYPE
    SYNTAX      PortNumber
    MAX-ACCESS  read-create
    STATUS      current
    DESCRIPTION
        "The analyzer interface, to which traffic is
        mirrored. Only one analyzer port per board is
        allowed for EMXP.

"
    DEFVAL { 0 }
    ::= { mesMirroringEntry 6 }

mesMirroringDestTxPort OBJECT-TYPE
    SYNTAX      PortNumber
    MAX-ACCESS  read-create
    STATUS      current
    DESCRIPTION
        "The analyzer tx port, to which traffic is
        mirrored. Only one analyzer port per board is
        allowed for EMXP.

"
    DEFVAL { 0 }
    ::= { mesMirroringEntry 7 }

mesMirroringIfNo OBJECT-TYPE
    SYNTAX      PortNumber
    MAX-ACCESS  read-create
    STATUS      current
    DESCRIPTION
        "The interface number of the mirror entry.

"
    DEFVAL { 1 }
    ::= { mesMirroringEntry 8 }

mesMirroringTxPort OBJECT-TYPE
    SYNTAX      PortNumber
    MAX-ACCESS  read-create
    STATUS      current
    DESCRIPTION
        "The number of the port where the TX-side of the
        interface is located.

"
    DEFVAL { 1 }
    ::= { mesMirroringEntry 9 }


-- ----------------------------------------------------
-- VLAN tag rule group configurations
-- ----------------------------------------------------

mesVlanTagRuleTable     OBJECT-TYPE
    SYNTAX      SEQUENCE OF MesVlanTagRuleEntry
    MAX-ACCESS  not-accessible
    STATUS      current
    DESCRIPTION
        "The VLAN tag rule group list.

        VLAN rule classification enables dynamic assignment
        of VLAN when traffic is received. The rule defines
        the type of VLAN rewrite operation (pop, push or
        swap), the new VLAN ID and priority as well as the
        direction (ingress or egress traffic) where the rule
        is applied. The classification defines the traffic
        matching criteria for which the rule are applied.

        Currently, only VLAN classification is possible."
    ::= { mesVlanTagRuleList 1 }

mesVlanTagRuleEntry OBJECT-TYPE
    SYNTAX      MesVlanTagRuleEntry
    MAX-ACCESS  not-accessible
    STATUS      current
    DESCRIPTION
        "An entry in the VLAN tag rule list.
"
    INDEX { mesVlanTagRuleIndex }
    ::= { mesVlanTagRuleTable 1 }

MesVlanTagRuleEntry ::=
    SEQUENCE {
        mesVlanTagRuleIndex                 Unsigned32,
        mesVlanTagRuleName                  MgmtNameString,
        mesVlanTagRuleInternalReference     Unsigned32,
        mesVlanTagRuleClassificationName    DisplayString,
        mesVlanTagRuleType                  INTEGER,
        mesVlanTagRuleOperation             INTEGER,
        mesVlanTagRuleInnerVlanId           Unsigned32,
        mesVlanTagRuleInnerPrio             Unsigned32,
        mesVlanTagRuleOuterVlanId           Unsigned32,
        mesVlanTagRuleOuterPrio             Unsigned32,
        mesVlanTagRulePrioAssignment        INTEGER,
        mesVlanTagRuleConfigurePrioAssignment CommandString,
        mesVlanTagRuleQueue                 Unsigned32,
        mesVlanTagRuleRowStatus             RowStatus,
        mesVlanTagRuleInterfaceName         DisplayString
 }

mesVlanTagRuleIndex OBJECT-TYPE
    SYNTAX      Unsigned32 (1..2147483647)
    MAX-ACCESS  read-only
    STATUS      current
    DESCRIPTION
        "An arbitrary index assigned to each rule entry.
"
    ::= { mesVlanTagRuleEntry 1 }

mesVlanTagRuleName OBJECT-TYPE
    SYNTAX      MgmtNameString
    MAX-ACCESS  read-only
    STATUS      current
    DESCRIPTION
        "The management name of the rule, for example
        'rule:1'.

"
    ::= { mesVlanTagRuleEntry 2 }

mesVlanTagRuleInternalReference OBJECT-TYPE
    SYNTAX      Unsigned32 (0..2147483647)
    MAX-ACCESS  read-create
    STATUS      current
    DESCRIPTION
        "For internal use only.
"
    DEFVAL { 0 }
    ::= { mesVlanTagRuleEntry 3 }

mesVlanTagRuleClassificationName OBJECT-TYPE
    SYNTAX      DisplayString
    MAX-ACCESS  read-create
    STATUS      current
    DESCRIPTION
        "The name of the classification associated with this
        rule.


"
    DEFVAL { "" }
    ::= { mesVlanTagRuleEntry 4 }

mesVlanTagRuleType OBJECT-TYPE
    SYNTAX      INTEGER {
                  ingress (1),
                  egress (2),
                  queue (3) }
    MAX-ACCESS  read-create
    STATUS      current
    DESCRIPTION
        "Indicates if the type of the rule.

        ingress - The rule applies to ingress traffic.
        egress  - The rule applies to egress traffic.
        queue   - Indicates mapping to a specific COS queue.
                  Not applicable for all boards.

"
    DEFVAL { ingress }
    ::= { mesVlanTagRuleEntry 5 }

mesVlanTagRuleOperation OBJECT-TYPE
    SYNTAX      INTEGER {
                    none (1),
                    pop (2),
                    push (3),
                    swap (4),
                    pushPush (5),
                    swapPush (6),
                    swapSwap (7),
                    popPop (8),
                    popSwap (9) }
    MAX-ACCESS  read-create
    STATUS      current
    DESCRIPTION
        "The type of operation applied to this rule.

        For ingress direction, only push and swap are
        currently supported.

        For egress direction, only pop and popSwap are
        currently supported.

        none     - No operation

        pop      - Remove the outer VLAN tag.

        push     - Push a new VLAN tag in front of the
                   existing VLAN tag.

        swap     - Replace a the existing outer VLAN tag.

        pushPush - Two new VLAN tags are pushed in front of
                   the existing VLAN tag.

        swapPush - Outer VLAN tag is replaced. A new VLAN tag
                   is pushed in front of the existing VLAN tag.

        swapSwap - Both outer and inner VLAN tags are
                   replaced.

        popPop   - Both outer and inner VLAN tags are
                   removed.

        popSwap  - Remove outer VLAN tag. Replace inner VLAN
                   tag.

        This attribute can be written via SNMP.

"
    DEFVAL { none }
    ::= { mesVlanTagRuleEntry 6 }

mesVlanTagRuleInnerVlanId OBJECT-TYPE
    SYNTAX      Unsigned32 (1..4096)
    MAX-ACCESS  read-write
    STATUS      current
    DESCRIPTION
        "The new inner VLAN ID.

        Only needed for the following operations:
        - pushPush
        - swapPush
        - swapSwap
        - popSwap
        This attribute can be written via SNMP.
        Values: 4095-4096 are only for internal use.

"
    DEFVAL { 1 }
    ::= { mesVlanTagRuleEntry 7 }

mesVlanTagRuleInnerPrio OBJECT-TYPE
    SYNTAX      Unsigned32 (0..7)
    MAX-ACCESS  read-write
    STATUS      current
    DESCRIPTION
        "The new inner VLAN priority.

        Only needed for the following operations:
        - pushPush
        - swapPush
        - swapSwap
        - popSwap
        This attribute can be written via SNMP.

"
    DEFVAL { 0 }
    ::= { mesVlanTagRuleEntry 8 }

mesVlanTagRuleOuterVlanId OBJECT-TYPE
    SYNTAX      Unsigned32 (1..4096)
    MAX-ACCESS  read-write
    STATUS      current
    DESCRIPTION
        "The new outer VLAN ID.

        Only needed for the following operations:
        - push
        - swap
        - pushPush
        - swapPush
        - swapSwap
        This attribute can be written via SNMP.
        Values: 4095-4096 are only for internal use.

"
    DEFVAL { 1 }
    ::= { mesVlanTagRuleEntry 9 }

mesVlanTagRuleOuterPrio OBJECT-TYPE
    SYNTAX      Unsigned32 (0..7)
    MAX-ACCESS  read-write
    STATUS      current
    DESCRIPTION
        "The new outer VLAN priority.

        Only needed for the following operations:
        - push
        - swap
        - pushPush
        - swapPush
        - swapSwap
        This attribute can be written via SNMP.

"
    DEFVAL { 0 }
    ::= { mesVlanTagRuleEntry 10 }

mesVlanTagRulePrioAssignment OBJECT-TYPE
    SYNTAX      INTEGER {
                    set (1),
                    copy (2),
                    none (3) }
    MAX-ACCESS  read-create
    STATUS      current
    DESCRIPTION
        "Defines how the priority is assigned when pushing
         VLAN ID on ingress.

         set - Set to specified value.

         copy - Use the priority from the ingress tag.

         none - Priority assignment is not valid for the
                selected operation.

        This attribute can be written via SNMP.

"
    DEFVAL { set }
    ::= { mesVlanTagRuleEntry 11 }

mesVlanTagRuleConfigurePrioAssignment OBJECT-TYPE
    SYNTAX      CommandString
    MAX-ACCESS  read-only
    STATUS      current
    DESCRIPTION
        "Defines if the priority is copied from ingress tag
        or set to a specific value.

"
    ::= { mesVlanTagRuleEntry 12 }

mesVlanTagRuleQueue OBJECT-TYPE
    SYNTAX      Unsigned32 (1..8)
    MAX-ACCESS  read-write
    STATUS      current
    DESCRIPTION
        "The VLAN queue number if 'type' is 'queue'.

        This attribute can be written via SNMP.

"
    DEFVAL { 1 }
    ::= { mesVlanTagRuleEntry 13 }

mesVlanTagRuleRowStatus OBJECT-TYPE
    SYNTAX      RowStatus
    MAX-ACCESS  read-create
    STATUS      current
    DESCRIPTION
        "Manages creation and deletion of conceptual rows.
        See also SNMPv2-TC.

        Note: The newly created object will not necessarily
        receive the same index as used in the create
        procedure.
        This attribute can be written via SNMP.

"
    ::= { mesVlanTagRuleEntry 14 }

mesVlanTagRuleInterfaceName OBJECT-TYPE
    SYNTAX      DisplayString
    MAX-ACCESS  read-only
    STATUS      current
    DESCRIPTION
        "Vlan Tag Rule interface name

"
    DEFVAL { "" }
    ::= { mesVlanTagRuleEntry 15 }


-- ----------------------------------------------------
-- VLAN tag classification VLAN group configurations
-- ----------------------------------------------------

mesVlanTagClassVlanTable     OBJECT-TYPE
    SYNTAX      SEQUENCE OF MesVlanTagClassVlanEntry
    MAX-ACCESS  not-accessible
    STATUS      current
    DESCRIPTION
        "The VLAN tag classification VLAN group list.

        VLAN rule classification enables dynamic assignment
        of VLAN when traffic is received. The rule defines
        the type of operation (pop, push or swap) and new
        VLAN ID/priority. The classification defines the
        traffic matching criteria for which the rule are
        applied.

        Currently, only VLAN classification on outer VLAN ID
        is possible."

    ::= { mesVlanTagClassVlanList 1 }

mesVlanTagClassVlanEntry OBJECT-TYPE
    SYNTAX      MesVlanTagClassVlanEntry
    MAX-ACCESS  not-accessible
    STATUS      current
    DESCRIPTION
        "An entry in the VLAN tag classification VLAN list.
"
    INDEX { mesVlanTagClassVlanIndex }
    ::= { mesVlanTagClassVlanTable 1 }

MesVlanTagClassVlanEntry ::=
    SEQUENCE {
        mesVlanTagClassVlanIndex                 Unsigned32,
        mesVlanTagClassVlanName                  MgmtNameString,
        mesVlanTagClassVlanTxPort                PortNumber,
        mesVlanTagClassVlanInternalReference     Unsigned32,
        mesVlanTagClassVlanRuleName              DisplayString,
        mesVlanTagClassVlanRuleIndex             Unsigned32,
        mesVlanTagClassVlanOuterVlanId           Integer32,
        mesVlanTagClassVlanLagIndex              Unsigned32,
        mesVlanTagClassVlanResourceType          INTEGER,
        mesVlanTagClassVlanIfNo                  PortNumber,
        mesVlanTagClassVlanLocalId               Integer32,
        mesVlanTagClassVlanRowStatus             RowStatus}

mesVlanTagClassVlanIndex OBJECT-TYPE
    SYNTAX      Unsigned32 (1..2147483647)
    MAX-ACCESS  read-only
    STATUS      current
    DESCRIPTION
        "An arbitrary index assigned to each classification entry.
"
    ::= { mesVlanTagClassVlanEntry 1 }

mesVlanTagClassVlanName OBJECT-TYPE
    SYNTAX      MgmtNameString
    MAX-ACCESS  read-only
    STATUS      current
    DESCRIPTION
        "The management name of the classification, for example 'classVlan:1'.
"
    ::= { mesVlanTagClassVlanEntry 2 }

mesVlanTagClassVlanTxPort OBJECT-TYPE
    SYNTAX      PortNumber
    MAX-ACCESS  read-create
    STATUS      current
    DESCRIPTION
        "The TX-port of the interface.

"
    ::= { mesVlanTagClassVlanEntry 3 }

mesVlanTagClassVlanInternalReference OBJECT-TYPE
    SYNTAX      Unsigned32 (0..2147483647)
    MAX-ACCESS  read-create
    STATUS      current
    DESCRIPTION
        "For internal use only.
"
    DEFVAL { 0 }
    ::= { mesVlanTagClassVlanEntry 4 }

mesVlanTagClassVlanRuleName OBJECT-TYPE
    SYNTAX      DisplayString
    MAX-ACCESS  read-create
    STATUS      current
    DESCRIPTION
        "The name of the rule associated with this
        classification.

"
    DEFVAL { "" }
    ::= { mesVlanTagClassVlanEntry 5 }

mesVlanTagClassVlanRuleIndex OBJECT-TYPE
    SYNTAX      Unsigned32 (1..2147483647)
    MAX-ACCESS  read-create
    STATUS      current
    DESCRIPTION
        "The index of the rule associated with this
        classification.

"
    ::= { mesVlanTagClassVlanEntry 6 }

mesVlanTagClassVlanOuterVlanId OBJECT-TYPE
    SYNTAX      Integer32 (-1..4094)
    MAX-ACCESS  read-create
    STATUS      current
    DESCRIPTION
        "The outer VLAN ID of the classification. -1 means no
        classification on outer VLAN ID.

"
    DEFVAL { -1 }
    ::= { mesVlanTagClassVlanEntry 7 }

mesVlanTagClassVlanLagIndex OBJECT-TYPE
    SYNTAX      Unsigned32 (0..2147483647)
    MAX-ACCESS  read-create
    STATUS      current
    DESCRIPTION
        "The Lag Index of the interface.

"
    ::= { mesVlanTagClassVlanEntry 8 }

 mesVlanTagClassVlanResourceType OBJECT-TYPE
    SYNTAX      INTEGER {
                    port  (1),
                    lag   (2) }
    MAX-ACCESS  read-create
    STATUS      current
    DESCRIPTION
        "The type of resource the Vlan Tag Class is connected.
"
    DEFVAL { port }
    ::= { mesVlanTagClassVlanEntry 9 }

 mesVlanTagClassVlanIfNo OBJECT-TYPE
    SYNTAX      PortNumber
    MAX-ACCESS  read-create
    STATUS      current
    DESCRIPTION
        "The interface number of the multi-connector port or port group.

"
    DEFVAL { 1  }
    ::= { mesVlanTagClassVlanEntry 10 }

 mesVlanTagClassVlanLocalId OBJECT-TYPE
    SYNTAX      Integer32   (-1..2147483647)
    MAX-ACCESS  read-create
    STATUS      current
    DESCRIPTION
        "Id for index calculation.

"
    DEFVAL { -1 }
    ::= { mesVlanTagClassVlanEntry 11 }

mesVlanTagClassVlanRowStatus OBJECT-TYPE
    SYNTAX      RowStatus
    MAX-ACCESS  read-create
    STATUS      current
    DESCRIPTION
        "Manages creation and deletion of conceptual rows via snmp.
        See also SNMPv2-TC.
        This object is only valid for creation and deletion of Vlan Tga Class.

        Note: The newly created object will not necessarily
        receive the same index as used in the create
        procedure.
"
    ::= { mesVlanTagClassVlanEntry 12 }

-- ----------------------------------------------------
-- OAM (based on 802.1ag) - Maid
-- ----------------------------------------------------

mesMaidTable  OBJECT-TYPE
    SYNTAX      SEQUENCE OF MesMaidEntry
    MAX-ACCESS  not-accessible
    STATUS      current
    DESCRIPTION
       "The Maintenance Domain table. Each row in the table
        represents a different Maintenance Domain.  A
        Maintenance Domain is described in 802.1ag (3.22) as
        the network or the part of the network for which
        faults in connectivity are to be managed. The
        boundary of a Maintenance Domain is defined by a set
        of DSAPs, each of which can become a point of
        connectivity to a service instance.  "
    REFERENCE
       "802.1ag clauses 3.22 and 18.1"
    ::= { mesMaidList 1 }

mesMaidEntry OBJECT-TYPE
    SYNTAX MesMaidEntry
    MAX-ACCESS not-accessible
    STATUS current
    DESCRIPTION

       "The Maintenance Domain table entry. This entry is
        not lost upon reboot. It is backed up by stable
        storage.
"
    INDEX { mesMaidIndex }
    ::= { mesMaidTable 1 }

MesMaidEntry ::=
    SEQUENCE {
        mesMaidIndex             Unsigned32,
        mesMaidName              MgmtNameString,
        mesMaidGroupId           Unsigned32,
        mesMaidMdFormat          Dot1agCfmMaintDomainNameType,
        mesMaidMdName            Dot1agCfmMaintDomainName,
        mesMaidMdMac             DisplayString,
        mesMaidMd2Octet          DisplayString,
        mesMaidMdString          DisplayString,
        mesMaidLevel             Dot1agCfmMDLevel,
        mesMaidMaFormat          Dot1agCfmMaintAssocNameType,
        mesMaidMaName            Dot1agCfmMaintAssocName,
        mesMaidMaVpnOui          DisplayString,
        mesMaidMaVpnIndex        DisplayString,
        mesMaidMa2Octet          DisplayString,
        mesMaidMaVlan            DisplayString,
        mesMaidMaString          DisplayString,
        mesMaidCcmInterval       Dot1agCfmCcmInterval,
        mesMaidInternalReference Unsigned32,
        mesMaidIdentifier        DisplayString,
        mesMaidNoOfMeps          Unsigned32,
        mesMaidAssociateMep      CommandString,
        mesMaidAssociateMepAdvanced CommandString,
        mesMaidReleaseMeps       CommandString,
        mesMaidRowStatus         RowStatus,
        mesMaidNoOfUpMeps        Unsigned32,
        mesMaidSubrack           SubrackNumber,
        mesMaidSlot              SlotNumber,
        mesMaidServiceId         ServiceIdWithNotUsed,

-- Added for port device (NID)
        mesMaidLocalDeviceType   INTEGER,
        mesMaidViewFilter        INTEGER,
        mesMaidNoOfNidMeps       Unsigned32,
        mesMaidAssociateMepNid   CommandString}

mesMaidIndex OBJECT-TYPE
    SYNTAX      Unsigned32 (1..4294967295)
    MAX-ACCESS  read-only
    STATUS      current
    DESCRIPTION
        "The index to the Maintenance Domain table.

         Referential integrity is required, i.e., the index
         needs to be persistent upon a reboot or restart of
         a device. The index can never be reused for other
         Maintenance Domain. The index value should keep
         increasing up to the time that they wrap
         around. This is to facilitate access control based
         on OID.

        "
    ::= { mesMaidEntry 1 }

mesMaidName OBJECT-TYPE
    SYNTAX      MgmtNameString
    MAX-ACCESS  read-only
    STATUS      current
    DESCRIPTION

        "The management name of the classification, for
        example 'meg:1:6:0:identifier'
        (meg:[subrack]:[slot]:[identifier]).

"
    ::= { mesMaidEntry 2 }

mesMaidGroupId OBJECT-TYPE
    SYNTAX      Unsigned32 (1..4294967295)
    MAX-ACCESS  read-only
    STATUS      current
    DESCRIPTION
        "A unique index for the MEG. Automatically generated
        by the system.

"
    ::= { mesMaidEntry 3 }

mesMaidMdFormat OBJECT-TYPE
    SYNTAX Dot1agCfmMaintDomainNameType
    MAX-ACCESS read-create
    STATUS current
    DESCRIPTION
       "The type (and thereby format) of the Maintenance
       Domain Name.

       This attribute can be written via SNMP.

       "
    REFERENCE
       "802.1ag clause 21.6.5.1"
    DEFVAL { charString }
    ::= { mesMaidEntry 4 }

mesMaidMdName OBJECT-TYPE
    SYNTAX Dot1agCfmMaintDomainName
    MAX-ACCESS read-create
    STATUS current
    DESCRIPTION
      "The Maintenance Domain name. The type/format of this
       object is determined by the value of the
       dot1agCfmMdNameType object.

       Each Maintenance Domain has unique name amongst all
       those used or available to a service provider or
       operator. It facilitates easy identification of
       administrative responsibility for each Maintenance
       Domain.

       Clause 3.24 defines a Maintenance Domain name as the
       identifier, unique over the domain for which CFM is to
       protect against accidental concatenation of Service
       Instances, of a particular Maintenance Domain.

       This attribute can be written via SNMP.

"
    REFERENCE
      "802.1ag clauses 3.24, 12.14.5, and 21.6.5.3"
    DEFVAL { "DEFAULT" }
    ::= { mesMaidEntry 5 }

mesMaidMdMac OBJECT-TYPE
    SYNTAX      DisplayString
    MAX-ACCESS  read-create
    STATUS      current
    DESCRIPTION
        "Represents the MAC address if MD format is
        macAddrAndUint.

        This attribute can be written via SNMP.

"
    DEFVAL { " " }
    ::= { mesMaidEntry 6 }

mesMaidMd2Octet OBJECT-TYPE
    SYNTAX      DisplayString
    MAX-ACCESS  read-create
    STATUS      current
    DESCRIPTION
        "Represents the unsigned integer if MD format is
        macAddrAndUint.

        This attribute can be written via SNMP.

"
    DEFVAL { " " }
    ::= { mesMaidEntry 7 }

mesMaidMdString OBJECT-TYPE
    SYNTAX      DisplayString
    MAX-ACCESS  read-create
    STATUS      current
    DESCRIPTION
        "Represents the string if MA format is charString .
"
    DEFVAL { " " }
    ::= { mesMaidEntry 8 }

mesMaidLevel OBJECT-TYPE
    SYNTAX Dot1agCfmMDLevel
    MAX-ACCESS read-create
    STATUS current
    DESCRIPTION
      "The Maintenance Domain Level.
      For a specific level, only one MEP with a specific VLAN ID
      and port is allowed.
      This attribute can be written via SNMP.

      "
    REFERENCE
      "802.1ag clause 12.14.5.1.1:b"
    DEFVAL { 0 }
    ::= { mesMaidEntry 9 }

mesMaidMaFormat OBJECT-TYPE
    SYNTAX Dot1agCfmMaintAssocNameType
    MAX-ACCESS read-create
    STATUS current
    DESCRIPTION
       "The type (and thereby format) of the Maintenance
        Association Name.

       This attribute can be written via SNMP.

       "
    REFERENCE
       "802.1ag clauses 21.6.5.4"
    ::= { mesMaidEntry 10 }

mesMaidMaName OBJECT-TYPE
    SYNTAX Dot1agCfmMaintAssocName
    MAX-ACCESS read-create
    STATUS current
    DESCRIPTION
       "The Short Maintenance Association name. The
        type/format of this object is determined by the
        value of the dot1agCfmMaNetNameType object. This
        name must be unique within a maintenance domain.

       This attribute can be written via SNMP.

"
    REFERENCE
       "802.1ag clauses 21.6.5.6, and Table 21-20"
    ::= { mesMaidEntry 11 }

mesMaidMaVpnOui OBJECT-TYPE
    SYNTAX      DisplayString
    MAX-ACCESS  read-create
    STATUS      current
    DESCRIPTION
        "Represents the VPN authority Organizationally
        Unique identifier if MA format is rfc2865VpnId.

        This attribute can be written via SNMP.

"
    DEFVAL { " " }
    ::= { mesMaidEntry 12 }

mesMaidMaVpnIndex OBJECT-TYPE
    SYNTAX      DisplayString
    MAX-ACCESS  read-create
    STATUS      current
    DESCRIPTION
        "Represents the VPN index if MA format is
        rfc2865VpnId.

        This attribute can be written via SNMP.

"
    DEFVAL { " " }
    ::= { mesMaidEntry 13 }

mesMaidMa2Octet OBJECT-TYPE
    SYNTAX      DisplayString
    MAX-ACCESS  read-create
    STATUS      current
    DESCRIPTION
        "Represents the unsigned integer if MA format is
        unsignedInt16.

        This attribute can be written via SNMP.

"
    DEFVAL { " " }
    ::= { mesMaidEntry 14 }

mesMaidMaVlan OBJECT-TYPE
    SYNTAX      DisplayString
    MAX-ACCESS  read-create
    STATUS      current
    DESCRIPTION
        "Represents the Primary VLAN ID if MA format is
        primaryVid.

        This attribute can be written via SNMP.

"
    DEFVAL { " " }
    ::= { mesMaidEntry 15 }

mesMaidMaString OBJECT-TYPE
    SYNTAX      DisplayString
    MAX-ACCESS  read-create
    STATUS      current
    DESCRIPTION
        "Represents the string if MA format is charString .
"
    DEFVAL { " " }
    ::= { mesMaidEntry 16 }

mesMaidCcmInterval OBJECT-TYPE
    SYNTAX Dot1agCfmCcmInterval
    MAX-ACCESS read-write
    STATUS current
    DESCRIPTION
       "Interval between CCM transmissions to be used by all MEPs in the MA.

        intervalInvalid No CCMs are sent (disabled).
        interval300Hz   CCMs are sent every 3 1/3 milliseconds  (300Hz).
        interval10ms    CCMs are sent every 10 milliseconds.
        interval100ms   CCMs are sent every 100 milliseconds.
        interval1s      CCMs are sent every 1 second.
        interval10s     CCMs are sent every 10 seconds.
        interval1min    CCMs are sent every minute.
        interval10min   CCMs are sent every 10 minutes.

        The supported CCM intervals for Down MEPs are: 3.33 ms,10 ms, 100 ms, 1 s, 10 s, 1 min, 10 min.
        The supported CCM intervals for Up MEPs are: 1 s, 10 s, 1 min, 10 min.

        The supported CCM intervals for NID Portdevices are: 3.33 ms,10 ms, 100 ms, 1 s.
        The default CCM interval for NID Portdevices is: 1s.
       "
    REFERENCE
       "802.1ag clause 12.14.6.1.3:e"
    DEFVAL { interval10s }
    ::= { mesMaidEntry 17 }

mesMaidInternalReference OBJECT-TYPE
    SYNTAX      Unsigned32 (0..2147483647)
    MAX-ACCESS  read-create
    STATUS      current
    DESCRIPTION
        "For internal use only.
        "
    DEFVAL { 0 }
    ::= { mesMaidEntry 18 }

mesMaidIdentifier OBJECT-TYPE
    SYNTAX      DisplayString(SIZE(1..16))
    MAX-ACCESS  read-create
    STATUS      current
    DESCRIPTION
        "A unique user definied identifier for the MEG.
        This attribute can be written via SNMP.

"
    DEFVAL { " " }
    ::= { mesMaidEntry 19 }

mesMaidNoOfMeps OBJECT-TYPE
    SYNTAX      Unsigned32
    MAX-ACCESS  read-only
    STATUS      current
    DESCRIPTION
        "The current number of down-MEPs associated with this MEG.
"
    DEFVAL { 0 }
    ::= { mesMaidEntry 20 }

mesMaidAssociateMep OBJECT-TYPE
    SYNTAX      CommandString
    MAX-ACCESS  read-only
    STATUS      current
    DESCRIPTION
        "Create and associate a MEP for the MEG.
        For a specific MEG level, only one MEP with a specific VLAN ID
        and interface is allowed.

        Interface - The name of the port/lag this MEP belongs to.

        Primary VLAN ID - An integer indicating the primary VLAN ID of the MEP.

        Priority - VLAN priority of the MEP.

        Type - Local (Tx) or remote (Rx). Only one local MEP is allowed in each MEG.

        Identifier - Unique integer among other MEPs in the same MA.

        Direction - The direction in which the MEP faces on the bridge interface.

            down(1)     Sends Continuity Check Messages away from the
                        MAC Relay Entity.
            up(2)       Sends Continuity Check Messages towards the
                        MAC Relay Entity.

                    If MEP direction is 'up' the CCM interval of associated MEG can not
                    be faster than 1 second.

      Loopback - indicates if loopback response is sent. Only valid for local and down MEPs

      CCM sequence counter - Value to enable or disable generation of CCM sequence
                             number increments for a MEP. Only valid for local and up MEPs

        disabled(1) - the MEP transmits a sequence number set to zero
        enabled(2)  - the MEP transmits a sequence number incrementing
                        by one for each CCM.

"
    ::= { mesMaidEntry 21 }

mesMaidReleaseMeps OBJECT-TYPE
    SYNTAX      CommandString
    MAX-ACCESS  read-only
    STATUS      current
    DESCRIPTION
        "Deletes all MEPs associated with this MEG.
"
    ::= { mesMaidEntry 22 }

mesMaidRowStatus OBJECT-TYPE
    SYNTAX      RowStatus
    MAX-ACCESS  read-create
    STATUS      current
    DESCRIPTION
        "Manages creation and deletion of conceptual rows.
        See also SNMPv2-TC.

        Note: The newly created object will not necessarily
        receive the same index as used in the create
        procedure.
        This attribute can be written via SNMP.

"
    ::=  { mesMaidEntry 23 }

mesMaidNoOfUpMeps OBJECT-TYPE
    SYNTAX      Unsigned32
    MAX-ACCESS  read-only
    STATUS      current
    DESCRIPTION
        "The current number of up-MEPs associated with this MEG.
"
    DEFVAL { 0 }
    ::= { mesMaidEntry 24 }

mesMaidLocalDeviceType OBJECT-TYPE
    SYNTAX      INTEGER {
                    emxp  (1),
                    nidGe (2) }
    MAX-ACCESS  read-create
    STATUS      current
    DESCRIPTION
        "The type of device the MEG is created and associated.
"
    DEFVAL { emxp }
    ::= { mesMaidEntry 25 }


mesMaidViewFilter OBJECT-TYPE
    SYNTAX      INTEGER {
                    emxp  (1),
                    nidGe (2) }
    MAX-ACCESS  read-create
    STATUS      current
    DESCRIPTION
        "The type of device the Maid is created,
         this attribute is used to filter object in views.
"
    DEFVAL { emxp }
    ::= { mesMaidEntry 26 }

mesMaidNoOfNidMeps OBJECT-TYPE
    SYNTAX      Unsigned32
    MAX-ACCESS  read-only
    STATUS      current
    DESCRIPTION
        "The current number of nid MEPs associated with this MEG.
"
    DEFVAL { 0 }
    ::= { mesMaidEntry 27 }

mesMaidAssociateMepNid OBJECT-TYPE
    SYNTAX      CommandString
    MAX-ACCESS  read-only
    STATUS      current
    DESCRIPTION
        "Create and associate a MEP for the MEG.
         MEG       - Identifies to which Meg the Mep will be added.

         Mep type   -  Local  or Remote.

         MEP identifier - Identifier for the Mep (range 1-8191)

         Portdevice - The selected Portdevice.
"
    ::= { mesMaidEntry 28 }

mesMaidAssociateMepAdvanced OBJECT-TYPE
        SYNTAX      CommandString
        MAX-ACCESS  read-only
        STATUS      current
        DESCRIPTION
            "Create and associate a MEP for the MEG.
            For a specific MEG level, only one MEP with a specific VLAN ID
            and interface is allowed.

            Interface - The name of the port/lag this MEP belongs to.

            Primary VLAN ID - An integer indicating the primary VLAN ID of the MEP.

            Priority - VLAN priority of the MEP.

            Type - Local (Tx) or remote (Rx). Only one local MEP is allowed in each MEG.

            Identifier - Unique integer among other MEPs in the same MA.

            Direction - The direction in which the MEP faces on the bridge interface.

                down(1)     Sends Continuity Check Messages away from the
                            MAC Relay Entity.
                up(2)       Sends Continuity Check Messages towards the
                            MAC Relay Entity.

                        If MEP direction is 'up' the CCM interval of associated MEG can not
                        be faster than 1 second.

          Loopback - indicates if loopback response is sent. Only valid for local and down MEPs

          CCM sequence counter - Value to enable or disable generation of CCM sequence
                                 number increments for a MEP. Only valid for local and up MEPs

            disabled(1) - the MEP transmits a sequence number set to zero
            enabled(2)  - the MEP transmits a sequence number incrementing
                            by one for each CCM.

"
        ::= { mesMaidEntry 29 }

mesMaidSubrack  OBJECT-TYPE
    SYNTAX      SubrackNumber
    MAX-ACCESS  read-only
    STATUS      current
    DESCRIPTION
        "The number of the subrack where the Maid is located.

"
    ::= { mesMaidEntry 30 }

mesMaidSlot  OBJECT-TYPE
    SYNTAX      SlotNumber
    MAX-ACCESS  read-only
    STATUS      current
    DESCRIPTION
        "The number of the slot where the Maid is located.

"
    ::= { mesMaidEntry 31 }

mesMaidServiceId OBJECT-TYPE
    SYNTAX      ServiceIdWithNotUsed
    MAX-ACCESS  read-write
    STATUS      current
    DESCRIPTION
        "Service ID is used by TNM for multi-layer
        service and network management.
        Default value is -1. All objects that created
        from ENM will have default service ID.
        Change of the service ID may affect
        TNM service mappings.
"
    DEFVAL { -1 }
    ::= { mesMaidEntry 32 }


-- ----------------------------------------------------
-- OAM (based on 802.1ag) - CfmMep
-- ----------------------------------------------------

mesCfmMepTable OBJECT-TYPE
    SYNTAX SEQUENCE OF MesCfmMepEntry
    MAX-ACCESS not-accessible
    STATUS current
    DESCRIPTION
       "The Maintenance Association End Point (MEP) table.

       Each row in the table represents a different MEP. A
       MEP is an actively managed CFM entity, associated
       with a specific DSAP of a Service Instance, which can
       generate and receive CFM PDUs and track any
       responses. It is an end point of a single Maintenance
       Association, and is an endpoint of a separate
       Maintenance Entity for each of the other MEPs in the
       same Maintenance Association (802.lag clause 3.18).
       "
    REFERENCE
       "802.1ag clause 18.2"
    ::= { mesCfmMepList 1 }

mesCfmMepEntry OBJECT-TYPE
    SYNTAX MesCfmMepEntry
    MAX-ACCESS not-accessible
    STATUS current
    DESCRIPTION
       "The CFM MEP table entry.
       "
    INDEX { mesCfmMepIndex }
    ::= { mesCfmMepTable 1 }

MesCfmMepEntry ::= SEQUENCE {
    mesCfmMepIndex              Unsigned32,
    mesCfmMepName               MgmtNameString,
    mesCfmMepMaid               DisplayString,
    mesCfmMepTxPort             PortNumber,
    mesCfmMepPortName           DisplayString,
    mesCfmMepPrimaryVid         Unsigned32,
    mesCfmMepAdminStatus        BoardOrInterfaceAdminStatus,
    mesCfmMepOperStatus         BoardOrInterfaceOperStatus,
    mesCfmMepVlanPriority       Integer32,
    mesCfmMepType               INTEGER,
    mesCfmMepIdentifier         Dot1agCfmMepId,
    mesCfmMepInternalReference  Unsigned32,
    mesCfmMepRDICCM             FaultStatus,
    mesCfmMepMACstatus          FaultStatus,
    mesCfmMepRemoteCCM          FaultStatus,
    mesCfmMepErrorCCM           FaultStatus,
    mesCfmMepXconCCM            FaultStatus,
    mesCfmMepAis                FaultStatus,
    mesCfmMepChangePort         CommandString,
    mesCfmMepTransmitLbrStatus  INTEGER,
    mesCfmMepRowStatus          RowStatus,
    mesCfmMepDirection          Dot1agCfmMpDirection,
    mesCfmMepCcmSeqNumStatus    INTEGER,
    mesCfmMepRemoteCsfLos       FaultStatus,
    mesCfmMepRemoteCsfRdi       FaultStatus,
    mesCfmMepRemoteCsfFdi       FaultStatus,
    mesCfmMepLocalCsfLos        FaultStatus,

-- Added for port device (NID)
    mesCfmMepLocalDeviceType    INTEGER,
    mesCfmMepLocalDeviceName    DisplayString,
    mesCfmMepLocalDeviceId      Unsigned32,
    mesCfmMepViewFilter         INTEGER,
    mesCfmMepUnexpectedPeriod   FaultStatus,
    mesCfmMepUnexpectedMepId    FaultStatus,
    mesCfmMepUnexpectedMegLevel FaultStatus,
    mesCfmMepMismerge           FaultStatus,
-- Added command for LM/DM
    mesCfmMepNoOfLMs            Unsigned32,
    mesCfmMepNoOfDMs            Unsigned32,
    mesCfmMepAssociateLM        CommandString,
    mesCfmMepAssociateDM        CommandString,
-- R23 Added LM DM Responder status
    mesCfmMepTransmitDmrStatus  INTEGER,
    mesCfmMepTransmitLmrStatus  INTEGER,
    mesCfmMepLmCosAwareness     INTEGER,
-- R24 Added Logical interfaces
    mesCfmMepResourceType       INTEGER,
    mesCfmMepLagId              DisplayString,
    mesCfmMepInterfaceName      DisplayString,
    mesCfmMepIfNo               PortNumber,
    mesCfmMepLocalId            Integer32,

    mesCfmMepSubrack            SubrackNumber,
    mesCfmMepSlot               SlotNumber,
    mesCfmMepServiceId          ServiceIdWithNotUsed
}
mesCfmMepIndex OBJECT-TYPE
    SYNTAX Unsigned32(1..4294967295)
    MAX-ACCESS read-only
    STATUS current
    DESCRIPTION
        "The index to the MEP table.

         This object is the interface index of the interface
         either a bridge port, or an aggregated IEEE 802.1
         link within a bridge port, to which the MEP is
         attached.

       "
::= { mesCfmMepEntry 1 }

mesCfmMepName OBJECT-TYPE
    SYNTAX      MgmtNameString
    MAX-ACCESS  read-only
    STATUS      current
    DESCRIPTION
        "The management name of the mep, for example
        'megNo1:1:6:67' (megName:subrack:slot:identifier).

"
    ::= { mesCfmMepEntry 2 }

mesCfmMepMaid OBJECT-TYPE
    SYNTAX      DisplayString
    MAX-ACCESS  read-create
    STATUS      current
    DESCRIPTION
        "The identifier of the MEG this MEP belongs to.

        Persistent cross-reference to MEG table.
"
    DEFVAL { " " }
    ::= { mesCfmMepEntry 3 }

mesCfmMepTxPort OBJECT-TYPE
    SYNTAX      PortNumber
    MAX-ACCESS  read-create
    STATUS      current
    DESCRIPTION
        "The Tx-port of the MEP.
        This attribute can be written via SNMP.

"
    DEFVAL { 1 }
    ::= { mesCfmMepEntry 4 }

mesCfmMepPortName OBJECT-TYPE
    SYNTAX      DisplayString
    MAX-ACCESS  read-only
    STATUS      current
    DESCRIPTION
        "The name of the port this MEP belongs to.
"
    ::= { mesCfmMepEntry 5 }

mesCfmMepAdminStatus OBJECT-TYPE
    SYNTAX      BoardOrInterfaceAdminStatus
    MAX-ACCESS  read-write
    STATUS      current
    DESCRIPTION
        "The administrative state for the object.

        down - The object is de-activated.

        service - The object is activated but alarms
        are suppressed. Intended for use during service
        or re-configuration. When service is concluded
        adminStatus should be set to 'up' again. Note that
        there is no difference between 'up' and 'service',
        if no alarms can be raised from this object.

        up - The object will be activated when
        available. Alarms are not suppressed.

"
    DEFVAL { up }
    ::= { mesCfmMepEntry 6 }

mesCfmMepOperStatus OBJECT-TYPE
    SYNTAX      BoardOrInterfaceOperStatus
    MAX-ACCESS  read-only
    STATUS      current
    DESCRIPTION
        "The operational state for the object.

        notPresent - The object is not available.

        down - The object is de-activated or there are
        faults preventing its transition to the 'up' state.

        up - The object is active.

"
    DEFVAL { notPresent }
    ::= { mesCfmMepEntry 7 }

mesCfmMepPrimaryVid OBJECT-TYPE
    SYNTAX      Unsigned32 (0..4094)
    MAX-ACCESS  read-write
    STATUS      current
    DESCRIPTION
        "An integer indicating the Primary VID of the MEP,
        always one of the VIDs assigned to the MA of the
        MEP. The value 0 indicates that either the Primary
        VID is that of the MEP's MA, or that the MEP's MA is
        associated with no VID.

        This attribute can be written via SNMP.

"
    REFERENCE
        "802.1ag clause 12.14.7.3.2:e"
        DEFVAL { 1 }
    ::= { mesCfmMepEntry 8 }

mesCfmMepVlanPriority OBJECT-TYPE
    SYNTAX      Integer32 (0..7)
    MAX-ACCESS  read-write
    STATUS      current
    DESCRIPTION
        "Priority. 3 bit value to be used in the VLAN tag,
        if present in the transmitted frame.

        The default value is the CCM priority.
        This attribute can be written via SNMP.

"
    REFERENCE
        "802.1ag clause 12.14.7.3.2:e"
    DEFVAL { 0 }
    ::= { mesCfmMepEntry 9 }

mesCfmMepType OBJECT-TYPE
    SYNTAX      INTEGER {
                    local (1),
                    remote (2) }
    MAX-ACCESS  read-create
    STATUS      current
    DESCRIPTION
       "The type of the MEP. Local (Tx) or Remote (Rx).
       Only one local MEP is allowed in each MEG.
        This attribute can be written via SNMP.

"
    DEFVAL { local }
    ::= { mesCfmMepEntry 10 }

mesCfmMepIdentifier OBJECT-TYPE
    SYNTAX      Dot1agCfmMepId
    MAX-ACCESS  read-create
    STATUS      current
    DESCRIPTION
        "Integer that is unique among all the MEPs in the
        same MA.

        Other definition is: a small integer,
        unique over a given Maintenance Association,
        identifying a specific Maintenance association End
        Point (3.19).

        Also known as the MEPID.
        This attribute can be written via SNMP.

"
    REFERENCE
        "802.1ag clause 3.19, 19.2 and 12.14.7"
    DEFVAL { 1 }
    ::= { mesCfmMepEntry 11 }

mesCfmMepInternalReference OBJECT-TYPE
    SYNTAX      Unsigned32 (0..2147483647)
    MAX-ACCESS  read-create
    STATUS      current
    DESCRIPTION
        "For internal use only.
        "
    DEFVAL { 0 }
    ::= { mesCfmMepEntry 12 }

mesCfmMepRDICCM OBJECT-TYPE
    SYNTAX      FaultStatus
    MAX-ACCESS  read-only
    STATUS      current
    DESCRIPTION
        "A remote MEP is reported the RDI bit in its last
        CCM.

"
    ::= { mesCfmMepEntry 13 }

mesCfmMepMACstatus OBJECT-TYPE
    SYNTAX      FaultStatus
    MAX-ACCESS  read-only
    STATUS      current
    DESCRIPTION
        "Either some remote MEP is reporting its Interface
         Status TLV as not isUp, or all remote MEPs are
         reporting a Port Status TLV that contains some
         value other than psUp.

"
    ::= { mesCfmMepEntry 14 }

mesCfmMepRemoteCCM OBJECT-TYPE
    SYNTAX      FaultStatus
    MAX-ACCESS  read-only
    STATUS      current
    DESCRIPTION
        "The MEP is not receiving valid CCMs from at least
         one of the remote MEPs.

"
    ::= { mesCfmMepEntry 15 }

mesCfmMepErrorCCM OBJECT-TYPE
    SYNTAX      FaultStatus
    MAX-ACCESS  read-only
    STATUS      current
    DESCRIPTION
        "The MEP has received at least one invalid CCM whose
         CCM Interval has not yet timed out.

"
    ::= { mesCfmMepEntry 16 }

mesCfmMepXconCCM OBJECT-TYPE
    SYNTAX      FaultStatus
    MAX-ACCESS  read-only
    STATUS      current
    DESCRIPTION
        "The MEP has received at least one CCM from either
         another MAID or a lower MD Level whose CCM Interval
         has not yet timed out.

"
    ::= { mesCfmMepEntry 17 }

mesCfmMepAis OBJECT-TYPE
    SYNTAX      FaultStatus
    MAX-ACCESS  read-only
    STATUS      current
    DESCRIPTION
        "Alarm indication signal.
"
    REFERENCE
       "Y.1731"
    ::= { mesCfmMepEntry 18 }

mesCfmMepChangePort OBJECT-TYPE
    SYNTAX      CommandString
    MAX-ACCESS  read-only
    STATUS      deprecated
    DESCRIPTION
        "Procedure to change port.

"
    ::= { mesCfmMepEntry 19 }

mesCfmMepTransmitLbrStatus OBJECT-TYPE
    SYNTAX      INTEGER {
                    disabled (1),
                    enabled (2) }
    MAX-ACCESS read-write
    STATUS current
    DESCRIPTION
        "Indicates if loopback response is sent. Only valid for local and down MEPs
"
    DEFVAL { disabled }
    ::= { mesCfmMepEntry 20 }

mesCfmMepRowStatus OBJECT-TYPE
    SYNTAX      RowStatus
    MAX-ACCESS  read-create
    STATUS      current
    DESCRIPTION
        "Manages creation and deletion of conceptual rows.
        See also SNMPv2-TC.

        Note: The newly created object will not necessarily
        receive the same index as used in the create
        procedure.
        This attribute can be written via SNMP.

"
    ::=  { mesCfmMepEntry 21 }

mesCfmMepDirection OBJECT-TYPE
    SYNTAX      Dot1agCfmMpDirection
    MAX-ACCESS  read-create
    STATUS      current
    DESCRIPTION
    "The direction in which the MEP faces on the Bridge port.
        down(1)    Sends Continuity Check Messages away from the
                   MAC Relay Entity.
        up(2)      Sends Continuity Check Messages towards the
                   MAC Relay Entity.

"
    REFERENCE
        "802.1ag clauses 12.14.7.1.3:c and 19.2"
    DEFVAL { down }
    ::= { mesCfmMepEntry 22 }

mesCfmMepCcmSeqNumStatus OBJECT-TYPE
    SYNTAX      INTEGER {
                    disabled (1),
                    enabled (2) }

    MAX-ACCESS  read-write
    STATUS      current
    DESCRIPTION
    "Value to enable or disable generation of CCM sequence number increments for a MEP.

        disabled(1) - the MEP transmits a sequence number set to zero
        enabled(2)  - the MEP transmits a sequence number incrementing
                        by one for each CCM.
"
    DEFVAL { disabled }
    ::= { mesCfmMepEntry 23 }

mesCfmMepRemoteCsfLos OBJECT-TYPE
    SYNTAX      FaultStatus
    MAX-ACCESS  read-only
    STATUS      current
    DESCRIPTION
        "A Remote CSF LOS indication (Loss Of Signal) has been recived from the remote MEP.

"
    ::= { mesCfmMepEntry 24 }


mesCfmMepRemoteCsfRdi OBJECT-TYPE
    SYNTAX      FaultStatus
    MAX-ACCESS  read-only
    STATUS      current
    DESCRIPTION
        "An Remote CSF RDI indication (Remote Defect Indication) has been recived from the remote MEP.

"
    ::= { mesCfmMepEntry 25 }

mesCfmMepRemoteCsfFdi OBJECT-TYPE
    SYNTAX      FaultStatus
    MAX-ACCESS  read-only
    STATUS      current
    DESCRIPTION
        "A Remote CSF FDI indication (Forward Defect Indication) has been recived from the remote MEP.

"
    ::= { mesCfmMepEntry 26 }

mesCfmMepLocalCsfLos OBJECT-TYPE
    SYNTAX      FaultStatus
    MAX-ACCESS  read-only
    STATUS      current
    DESCRIPTION
        "A Local CSF LOS indication (Loss Of Signal Defect Indication) has been recived on the local MEP.

"
    ::= { mesCfmMepEntry 27 }

mesCfmMepLocalDeviceType OBJECT-TYPE
    SYNTAX      INTEGER {
                    emxp  (1),
                    nidGe (2) }
    MAX-ACCESS  read-create
    STATUS      current
    DESCRIPTION
        "The type of device the MEP is created and associated.
"
    DEFVAL { emxp }
    ::= { mesCfmMepEntry 28 }

mesCfmMepLocalDeviceName OBJECT-TYPE
    SYNTAX      DisplayString
    MAX-ACCESS  read-create
    STATUS      current
    DESCRIPTION
        "The name of device the MEP is created and associated.
        Only valid when the local device type is nidGe.
"
        DEFVAL { " " }
    ::= { mesCfmMepEntry 29 }

mesCfmMepLocalDeviceId OBJECT-TYPE
    SYNTAX      Unsigned32 (0..2147483647)
    MAX-ACCESS  read-create
    STATUS      current
    DESCRIPTION
        "An arbitrary index(aka sdId) assigned to the local device
        entry, where the MEP is associated to.
        Only valid when the local device type is nidGe.
"
    DEFVAL {0}
    ::= { mesCfmMepEntry 30 }

mesCfmMepViewFilter OBJECT-TYPE
    SYNTAX      INTEGER {
                    emxp  (1),
                    nidGe (2) }
    MAX-ACCESS  read-create
    STATUS      current
    DESCRIPTION
        "The type of device the MEP is created,
         this attribute is used to filter object in views.
"
    DEFVAL { emxp }
    ::= { mesCfmMepEntry 31 }

mesCfmMepUnexpectedPeriod OBJECT-TYPE
    SYNTAX      FaultStatus
    MAX-ACCESS  read-only
    STATUS      current
    DESCRIPTION
        "Unexpected Period, alarm signal received from nid
        which together with Unexpected MEP ID trigger the
        ErrorCCM alarm.

"
    ::= { mesCfmMepEntry 32 }

mesCfmMepUnexpectedMepId OBJECT-TYPE
    SYNTAX      FaultStatus
    MAX-ACCESS  read-only
    STATUS      current
    DESCRIPTION
        "Unexpected MEP-ID, alarm signal received from nid
        which together with Unexpected Period trigger the
        ErrorCCM alarm

"
    ::= { mesCfmMepEntry 33 }

mesCfmMepUnexpectedMegLevel OBJECT-TYPE
    SYNTAX      FaultStatus
    MAX-ACCESS  read-only
    STATUS      current
    DESCRIPTION
        "Unexpected Meg Level, alarm signal received from nid
        which together with Mismerge trigger the
        XconCCM alarm

"
    ::= { mesCfmMepEntry 34 }

mesCfmMepMismerge OBJECT-TYPE
    SYNTAX      FaultStatus
    MAX-ACCESS  read-only
    STATUS      current
    DESCRIPTION
        "Mismerge, alarm signal received from nid
        which together with Unexpected Meg Level trigger the
        XconCCM alarm

"
    ::= { mesCfmMepEntry 35 }

mesCfmMepNoOfLMs OBJECT-TYPE
    SYNTAX      Unsigned32
    MAX-ACCESS  read-only
    STATUS      current
    DESCRIPTION
        "The current number of LM Sessions with this MEP.
"
    DEFVAL { 0 }
    ::= { mesCfmMepEntry 36 }

mesCfmMepNoOfDMs OBJECT-TYPE
    SYNTAX      Unsigned32
    MAX-ACCESS  read-only
    STATUS      current
    DESCRIPTION
        "The current number of DM Sessions with this MEP.
"
    DEFVAL { 0 }
    ::= { mesCfmMepEntry 37 }

mesCfmMepAssociateLM OBJECT-TYPE
    SYNTAX      CommandString
    MAX-ACCESS  read-only
    STATUS      current
    DESCRIPTION
        "Procedure to add Y.1731/MEF-35 Loss Measurement to a remote MEP.
         LMM interval   - Interval of LMM messages, 1s, 10s, 100ms.
         Type           - MEP or MAC Address, (MEP for Automatic MAC Discovery or a MAC address)
         High Loss Threshold - 0 to 100.00 %
         Unavailable seconds alarm threshold, - 0..900s

"
    ::= { mesCfmMepEntry 38 }


mesCfmMepAssociateDM OBJECT-TYPE
    SYNTAX      CommandString
    MAX-ACCESS  read-only
    STATUS      current
    DESCRIPTION
        "Procedure to add Y.1731/MEF-35 Delay Measurement to a remote MEP.
         DMM interval   - Interval of DMM messages, 100ms, 1s, 10s.
         Type           - MEP or MAC Address, (MEP for Automatic MAC Discovery or a MAC address)

"
    ::= { mesCfmMepEntry 39 }

mesCfmMepTransmitDmrStatus OBJECT-TYPE
    SYNTAX      INTEGER {
                    disabled (1),
                    enabled (2) }
    MAX-ACCESS read-write
    STATUS current
    DESCRIPTION
        "Indicates if Delay Measurement (DM) responder is active. Only valid for down MEPs
"
    DEFVAL { enabled }
    ::= { mesCfmMepEntry 40 }

mesCfmMepTransmitLmrStatus OBJECT-TYPE
    SYNTAX      INTEGER {
                    disabled (1),
                    enabled (2) }
    MAX-ACCESS read-write
    STATUS current
    DESCRIPTION
        "Indicates if Loss Measurement (LM) responder is active. Only valid for down MEPs
"
    DEFVAL { enabled }
    ::= { mesCfmMepEntry 41 }

mesCfmMepLmCosAwareness OBJECT-TYPE
    SYNTAX      INTEGER {
                        priorityBlind (1),
                        priorityAware (2) }
    MAX-ACCESS read-write
    STATUS current
    DESCRIPTION
        "Define CoS awareness for the LM responder.
         A CoS aware LM Responder will return counters associated with the priority of the incoming LMM packets.

         priorityBlind - LM Responder is Cos unaware (return counters for all priorities.)

         priorityAware - LM Responder is CoS aware (return counters associated with the priority of incoming LMM packet).
"
    DEFVAL { priorityBlind }
    ::= { mesCfmMepEntry 42 }

mesCfmMepResourceType OBJECT-TYPE
    SYNTAX      INTEGER {
                    port  (1),
                    lag   (2) }
    MAX-ACCESS  read-create
    STATUS      current
    DESCRIPTION
        "The type of resource the MEP is connected.
"
    DEFVAL { port }
    ::= { mesCfmMepEntry 43 }

 mesCfmMepLagId OBJECT-TYPE
    SYNTAX      DisplayString(SIZE(1..17))
    MAX-ACCESS  read-create
    STATUS      current
    DESCRIPTION
        "Id of the lag connected to mep.
"
    DEFVAL { " " }
    ::= { mesCfmMepEntry 44 }

 mesCfmMepInterfaceName OBJECT-TYPE
    SYNTAX      DisplayString
    MAX-ACCESS  read-create
    STATUS      current
    DESCRIPTION
        "Name of the Interface connected to mep.
"
    DEFVAL { " " }
    ::= { mesCfmMepEntry 45 }

 mesCfmMepIfNo OBJECT-TYPE
    SYNTAX      PortNumber
    MAX-ACCESS  read-create
    STATUS      current
    DESCRIPTION
        "The interface number of the multi-connector port or port group.

"
    DEFVAL { 1  }
    ::= { mesCfmMepEntry 46 }

 mesCfmMepLocalId OBJECT-TYPE
    SYNTAX      Integer32   (-1..2147483647)
    MAX-ACCESS  read-create
    STATUS      current
    DESCRIPTION
        "Id for index calculation.

"
    DEFVAL { -1 }
    ::= { mesCfmMepEntry 47 }

mesCfmMepSubrack  OBJECT-TYPE
    SYNTAX      SubrackNumber
    MAX-ACCESS  read-only
    STATUS      current
    DESCRIPTION
        "The number of the subrack where the Mep is located.

"
    ::= { mesCfmMepEntry 48 }

mesCfmMepSlot  OBJECT-TYPE
    SYNTAX      SlotNumber
    MAX-ACCESS  read-only
    STATUS      current
    DESCRIPTION
        "The number of the slot where the Mep is located.

"
    ::= { mesCfmMepEntry 49 }

mesCfmMepServiceId OBJECT-TYPE
    SYNTAX      ServiceIdWithNotUsed
    MAX-ACCESS  read-write
    STATUS      current
    DESCRIPTION
        "Service ID is used by TNM for multi-layer
        service and network management.
        Default value is -1. All objects that created
        from ENM will have default service ID.
        Change of the service ID may affect
        TNM service mappings.
"
    DEFVAL { -1 }
    ::= { mesCfmMepEntry 50 }

-- ----------------------------------------------------
-- ERP (Ethernet Ring Protection)
-- ----------------------------------------------------

mesErpTable  OBJECT-TYPE
    SYNTAX      SEQUENCE OF MesErpEntry
    MAX-ACCESS  not-accessible
    STATUS      current
    DESCRIPTION
       "An ethernet ring is made of two or more nodes (EMXPii boards) which
       are connected via links. Each node has two ring links connected to
       other nodes. To avoid loops, one link in the ring must always be
       blocked. The link that is blocked under normal conditions is called
       Ring Protection Link (or RPL). One of the nodes connected to this
       link is called the RPL owner and is responsible to control the status
       of the RPL."
    ::= { mesErpList 1 }

mesErpEntry OBJECT-TYPE
    SYNTAX MesErpEntry
    MAX-ACCESS not-accessible
    STATUS current
    DESCRIPTION
       "An entry in the ERP list.
       "
    INDEX { mesErpIndex }
    ::= { mesErpTable 1 }

MesErpEntry ::=
    SEQUENCE {
        mesErpIndex                     Unsigned32,
        mesErpName                      MgmtNameString,
        mesErpPortLeft                  Unsigned32,
        mesErpPortRight                 Unsigned32,
        mesErpAdminStatus               BoardOrInterfaceAdminStatus,
        mesErpInternalReference         Unsigned32,
        mesErpDescr                     DisplayString,
        mesErpVlanId                    Unsigned32,
        mesErpMegLevel                  Dot1agCfmMDLevel,
        mesErpProtLink                  INTEGER,
        mesErpGuardTime                 Unsigned32,
        mesErpHoldOffTime               Unsigned32,
        mesErpWtrTime                   Unsigned32,
        mesErpOamDetectionLeft          INTEGER,
        mesErpOamDetectionRight         INTEGER,
        mesErpStatusLeft                INTEGER,
        mesErpStatusRight               INTEGER,
        mesErpProtState                 INTEGER,
        mesErpActiveEvent               INTEGER,
        mesErpRapsReqState              INTEGER,
        mesErpServiceFailure            FaultStatus,
        mesErpServiceDegraded           FaultStatus,
        mesErpUnexpectedMegLevel        FaultStatus,
        mesErpCommunicationFailure      FaultStatus,
        mesErpProvisioningMismatch      FaultStatus,
        mesErpChangePort                CommandString,
        mesErpRowStatus                 RowStatus,
        mesErpNodeType                  INTEGER,
        mesErpProtectionMode            INTEGER,
        mesErpVersion                   INTEGER,
        mesErpMajorName                 MgmtNameString,
        mesErpRingId                    Unsigned32,
        mesErpRingIndex                 Unsigned32,
        mesErpOperatorCommand           INTEGER,
        mesErpGroupId                   Unsigned32,
        mesErpSwitchInformation         FaultStatus,
        mesErpTopologyChangePropagation INTEGER,
        mesErpSubRings                  Counter64,
        mesErpResourceTypeLeft          INTEGER,
        mesErpLagIdLeft                 DisplayString,
        mesErpResourceTypeRight         INTEGER,
        mesErpLagIdRight                DisplayString,
        mesErpInterfaceLeft             DisplayString,
        mesErpInterfaceRight            DisplayString,
        mesErpIfNoLeft                  PortNumber,
        mesErpTxPortLeft                PortNumber,
        mesErpIfNoRight                 PortNumber,
        mesErpTxPortRight               PortNumber,
        mesErpOamDetectionVlanId        Unsigned32
         }


mesErpIndex OBJECT-TYPE
    SYNTAX      Unsigned32 (1..4294967295)
    MAX-ACCESS  read-only
    STATUS      current
    DESCRIPTION
        "An arbitrary index. Subrack, slot and VLAN ID can
        be derived from the index.

        "
    ::= { mesErpEntry 1 }

mesErpName OBJECT-TYPE
    SYNTAX      MgmtNameString
    MAX-ACCESS  read-only
    STATUS      current
    DESCRIPTION
        "The management name of the ERP.
        For ERP V1:
        'erp:1:5:4094' (erp:[subrack]:[slot]:[vlanId])
        For ERP V2:
        'erp2:1:5:1:4094' (erpv2:[subrack]:[slot]:[ringId]:[vlanId]).

"
    ::= { mesErpEntry 2 }

mesErpPortLeft OBJECT-TYPE
    SYNTAX      Unsigned32 (0..2147483647)
    MAX-ACCESS  read-create
    STATUS      current
    DESCRIPTION
        "The interface (Tx-Rx) where the left ERP link is located.

"
    ::= { mesErpEntry 3 }

mesErpPortRight OBJECT-TYPE
    SYNTAX      Unsigned32 (0..2147483647)
    MAX-ACCESS  read-create
    STATUS      current
    DESCRIPTION
       "The interface (Tx-Rx) where the right ERP link is located.

"
    ::= { mesErpEntry 4 }

mesErpAdminStatus OBJECT-TYPE
    SYNTAX      BoardOrInterfaceAdminStatus
    MAX-ACCESS  read-write
    STATUS      current
    DESCRIPTION
        "The administrative state for the object.

        service - The object is activated but alarms
        are suppressed. Intended for use during service
        or re-configuration. When service is concluded
        adminStatus should be set to 'up' again. Note that
        there is no difference between 'up' and 'service',
        if no alarms can be raised from this object.

        up - The object will be activated when
        available. Alarms are not suppressed.

"
    DEFVAL { up }
    ::= { mesErpEntry 5 }

mesErpInternalReference OBJECT-TYPE
    SYNTAX      Unsigned32 (0..2147483647)
    MAX-ACCESS  read-create
    STATUS      current
    DESCRIPTION
        "For internal use only.
        "
    DEFVAL { 0 }
    ::= { mesErpEntry 6 }

mesErpDescr OBJECT-TYPE
    SYNTAX      DisplayString
    MAX-ACCESS  read-write
    STATUS      current
    DESCRIPTION
        "User configurable label.
"
    DEFVAL { "" }
    ::= { mesErpEntry 7 }

mesErpVlanId OBJECT-TYPE
    SYNTAX      Unsigned32 (1..4094)
    MAX-ACCESS  read-create
    STATUS      current
    DESCRIPTION
        "All control messaging (R-APS channel) for the ring are transmitted
        on a specific VLAN ID.

"
    DEFVAL { 4094 }
    ::= { mesErpEntry 8 }

mesErpMegLevel OBJECT-TYPE
    SYNTAX Dot1agCfmMDLevel
    MAX-ACCESS read-write
    STATUS current
    DESCRIPTION
      "The Maintenance Domain Level (or MEG Level). The MEG level must be the same
      across all ERP instances in the same ERP ring.

      "
    REFERENCE
      "802.1ag clause 12.14.5.1.1:b"
    DEFVAL { 3 }
    ::= { mesErpEntry 9 }

mesErpProtLink OBJECT-TYPE
    SYNTAX      INTEGER {
                    none (1),
                    left (2),
                    right (3),
                    leftNeighbour (4),
                    rightNeighbour (5) }
    MAX-ACCESS  read-write
    STATUS      current
    DESCRIPTION
        "The direction towards the Ring Protection Link (RPL) and the role of the node.
        For the owner the RPL is situated on the chosen port while for the neighbour the
        specified port is connected to the RPL owner (neighbour only valid for ERP V2).

"
    DEFVAL { none }
    ::= { mesErpEntry 10 }

mesErpGuardTime OBJECT-TYPE
    SYNTAX      Unsigned32 (10..2000)
    MAX-ACCESS  read-write
    STATUS      current
    DESCRIPTION
        "The guard time is used to protect from receiving
         old R-APS messages during a recovery from a failed
         link. When the guard timer is running, all received
         R-APS messages are ignored. The period of the guard
         timer should be longer than the time it takes for a
         packet to circle around the ring. The guard time is
         defined in milliseconds.

         The guard time is defined in steps of
         10 milliseconds.

"
    DEFVAL { 500 }
    ::= { mesErpEntry 11 }

mesErpHoldOffTime OBJECT-TYPE
    SYNTAX      Unsigned32 (0..10000)
    MAX-ACCESS  read-create
    STATUS      current
    DESCRIPTION
        "A hold-off timer coordinates timing of protection
         switches between multiple layers. The timer gives
         another protection layer the possibility to solve
         the issue before performing the protection
         switch. When a signal fail event occurs, this event
         is not reported until the hold-off timer has elapsed.

         The hold-off time is defined in steps of
         100 milliseconds.

         Note! A non-zero hold-off time will impact the
         protection switch time performance.

"
    DEFVAL { 0 }
    ::= { mesErpEntry 12 }

mesErpWtrTime OBJECT-TYPE
    SYNTAX      Unsigned32 (1..12)
    MAX-ACCESS  read-write
    STATUS      current
    DESCRIPTION
        "After the link has recovered from a failure, the RPL
         owner waits a fixed period before
         blocking the RPL and restoring it to idle state.
         The wait to restore time is defined in minutes.
"
    DEFVAL { 5 }
    ::= { mesErpEntry 13 }

mesErpOamDetectionLeft OBJECT-TYPE
    SYNTAX      INTEGER {
                    disabled (1),
                    enabled (2) }
    MAX-ACCESS  read-write
    STATUS      current
    DESCRIPTION
        "Defines whether OAM signal failure detection is
        enabled on the left ERP port.

"
    DEFVAL { disabled }
    ::= { mesErpEntry 14 }

mesErpOamDetectionRight OBJECT-TYPE
    SYNTAX      INTEGER {
                    disabled (1),
                    enabled (2) }
    MAX-ACCESS  read-write
    STATUS      current
    DESCRIPTION
        "Defines whether OAM signal failure detection is
        enabled on the right ERP port.

"
    DEFVAL { disabled }
    ::= { mesErpEntry 15 }

mesErpStatusLeft OBJECT-TYPE
    SYNTAX      INTEGER {
                    undefined (0),
                    forwarding (1),
                    blocked (2) }
    MAX-ACCESS  read-only
    STATUS      current
    DESCRIPTION
        "Indicates if the left ERP port forwards or blocks
        traffic.

"
    ::= { mesErpEntry 16 }

mesErpStatusRight OBJECT-TYPE
    SYNTAX      INTEGER {
                    undefined (0),
                    forwarding (1),
                    blocked (2) }
    MAX-ACCESS  read-only
    STATUS      current
    DESCRIPTION
        "Indicates if the right ERP port forwards or blocks
        traffic.

"
    ::= { mesErpEntry 17 }

mesErpProtState OBJECT-TYPE
    SYNTAX      INTEGER {
                    undefined (0),
                    starting (1),
                    idle (2),
                    protection (3),
                    manualSwitch (4),
                    forcedSwitch (5),
                    pending (6) }
    MAX-ACCESS  read-only
    STATUS      current
    DESCRIPTION
        "Indicates the protection state of the ring.

        Starting
                - The ring is in start-up phase.
        Idle
                - No failure has been detected and the Ring
                  Protection Link (RPL) is carrying no
                  traffic.
        Protection
                - A failure has been detected and the ring has
                  entered protection state and blocked off failed
                  ring links.

        Manual switch
                 - A 'Manual switch' command induces a block
                   on a ring port. The manual switch will be
                   disregarded if the ring detects a failure
                   or if the ring is in protection state.

        Forced switch
                 - A 'Forced switch' command forces a block
                   on a ring port disregarding the ring state.
        Pending
                - Wait state when returning from a protection
                switch or clear an operator command.
                Ring will stay in the state until a clear command
                is issued if in non-revertive mode. If ring is in
                revertive mode the state will change to idle
                when timers have elapsed.
"
    ::= { mesErpEntry 18 }

mesErpActiveEvent OBJECT-TYPE
    SYNTAX      INTEGER {
                    undefined (0),
                    none (1),
                    localSignalFail (2),
                    localClearSignalFail (3),
                    remoteSignalFail (4),
                    wtrExpire (5),
                    wtrRunning (6),
                    noRequestRb (7),
                    noRequest (8),
                    localClear (9),
                    localFs (10),
                    remoteFs (11),
                    remoteMs (12),
                    localMs (13),
                    wtbExpires (14),
                    wtbRunning (15),
                    remoteEvent (16) }
    MAX-ACCESS  read-only
    STATUS      current
    DESCRIPTION
        "Information about latest input to the ERP state machine.

"
    ::= { mesErpEntry 19 }

mesErpRapsReqState OBJECT-TYPE
    SYNTAX      INTEGER {
                    undefined (0),
                    signalFail (1),
                    noRequest (2),
                    reserved (3),
                    reqStateForcedSwitch (4),
                    reqStateEvent (5),
                    reqManualSwitch (6) }
    MAX-ACCESS  read-only
    STATUS      current
    DESCRIPTION
        "Request in the latest sent or received R-APS message.

"
    ::= { mesErpEntry 20 }

mesErpServiceFailure OBJECT-TYPE
    SYNTAX      FaultStatus
    MAX-ACCESS  read-only
    STATUS      current
    DESCRIPTION
        "New signal failure detected while in protected
         state. I.e. two or more faults in the ring.

"
    REFERENCE
       "G.8032"
    ::= { mesErpEntry 21 }

mesErpServiceDegraded OBJECT-TYPE
    SYNTAX      FaultStatus
    MAX-ACCESS  read-only
    STATUS      current
    DESCRIPTION
        "The ERP is in protection state.
"
    REFERENCE
       "G.8032"
    ::= { mesErpEntry 22 }

mesErpUnexpectedMegLevel OBJECT-TYPE
    SYNTAX      FaultStatus
    MAX-ACCESS  read-only
    STATUS      current
    DESCRIPTION
        "Invalid R-APS messages received.

"
    REFERENCE
       "Y.1731"
    ::= { mesErpEntry 23 }

mesErpCommunicationFailure OBJECT-TYPE
    SYNTAX      FaultStatus
    MAX-ACCESS  read-only
    STATUS      current
    DESCRIPTION
        "An expected R-APS message has not been received in
         the last 15 second period. dFOP-TO in G.8032.

"
    REFERENCE
       "G.8032"
    ::= { mesErpEntry 24 }

mesErpChangePort OBJECT-TYPE
    SYNTAX      CommandString
    MAX-ACCESS  read-only
    STATUS      deprecated
    DESCRIPTION
        "Procedure to change left and right port and
         protection link. This functionality
         is only available for ERPv1.

"
    ::= { mesErpEntry 25 }

mesErpRowStatus OBJECT-TYPE
    SYNTAX      RowStatus
    MAX-ACCESS  read-create
    STATUS      current
    DESCRIPTION
        "Manages creation and deletion of conceptual rows.
        See also SNMPv2-TC.

        Note: The newly created object will not necessarily
        receive the same index as used in the create
        procedure.

"
    ::=  { mesErpEntry 26 }

mesErpNodeType OBJECT-TYPE
    SYNTAX      INTEGER {
           ringNode (1),
           subInterconnection (2)  }
    MAX-ACCESS  read-create
    STATUS      current
    DESCRIPTION
       "The type of the ERPV2 node.

           Ring node - Standard ring node.

           Sub Interconnection - Node that connects a sub ring to a major ring.

"
    DEFVAL { ringNode }
    ::= { mesErpEntry  27 }

mesErpProtectionMode OBJECT-TYPE
    SYNTAX      INTEGER {
                  nonRevertive (1),
                  revertive (2)}
    MAX-ACCESS  read-write
    STATUS      current
    DESCRIPTION
        "The protection mode of the ERPv2 instance.
        nonRevertive -- non-revertive mode
        revertive    -- revertive mode

"
    DEFVAL { revertive }
    ::= { mesErpEntry 28 }

mesErpVersion OBJECT-TYPE
    SYNTAX      INTEGER {
                  erpV1 (1),
                  erpV2 (2)}
    MAX-ACCESS  read-create
    STATUS      current
    DESCRIPTION
        "The protocol version of the ERP instance.
        erpV1 -- ERPv1
        erpV2 -- ERPv2

"
    DEFVAL { erpV1 }
    ::= { mesErpEntry 29 }

mesErpMajorName OBJECT-TYPE
    SYNTAX      MgmtNameString
    MAX-ACCESS  read-create
    STATUS      current
    DESCRIPTION
        "The management name of the major ring that the
        subring is connected to.
        For example
        'erp2:1:5:1:4094' (erp:[subrack]:[slot]:[ringId]:[vlanId]).

"
        DEFVAL { "" }
    ::= { mesErpEntry 30 }

mesErpRingId OBJECT-TYPE
    SYNTAX      Unsigned32 (1..239)
    MAX-ACCESS  read-create
    STATUS      current
    DESCRIPTION
        "Ring ID for the ERPv2 instance. All ERP instances
        must have the same ring ID throughout the ERP ring.

"
        DEFVAL { 1 }
    ::= { mesErpEntry 31 }

mesErpRingIndex OBJECT-TYPE
    SYNTAX      Unsigned32 (1..64)
    MAX-ACCESS  read-create
    STATUS      current
    DESCRIPTION
        "Index of ring used by VLAN Protection Groups and
        VLAN Map when referring to a ring.

"
        DEFVAL { 1 }
    ::= { mesErpEntry 32 }

mesErpOperatorCommand  OBJECT-TYPE
    SYNTAX      INTEGER {
                    noRequest (1),
                    forcedLeft (2),
                    forcedRight (3),
                    manualLeft (4),
                    manualRight (5),
                    clear (6) }
    MAX-ACCESS  read-write
    STATUS      current
    DESCRIPTION
        "The operator commands.
         noRequest (1)
            -- initial state and the return state after issuing an operator command.
         forced left (2)
            -- force a block on the left ring port where the command is issued.
         forced right (3)
            -- force a block on the right ring port where the command is issued.
         manual left (4)
            -- in the absence of a failure or a forced command, this command sets a block
               on the left port where the command is issued.
         manual right (5)
            -- in the absence of a failure or a forced command, this command sets a block
               on the right port where the command is issued.
         clear (6)
            -- clears an active operator command, triggering reversion before WTR or WTB expires
            in the case of revertive mode, triggering reversion in the case of non revertive mode.

"
    DEFVAL { noRequest }
    ::= { mesErpEntry 33 }

mesErpGroupId OBJECT-TYPE
    SYNTAX      Unsigned32 (0..2147483647)
    MAX-ACCESS  read-create
    STATUS      current
    DESCRIPTION
        "Unique number identifying group VLAN protection group for the R-APS VLAN of this ring.

"
    DEFVAL { 0 }
    ::= { mesErpEntry 34 }

mesErpSwitchInformation OBJECT-TYPE
    SYNTAX      FaultStatus
    MAX-ACCESS  read-only
    STATUS      current
    DESCRIPTION
        "User has set a manual or a forced ERP switch.

"
    ::= { mesErpEntry 35 }

mesErpTopologyChangePropagation OBJECT-TYPE
    SYNTAX      INTEGER {
                    disabled (1),
                    enabled (2)}

    MAX-ACCESS  read-write
    STATUS      current
    DESCRIPTION
        "Disable or enable forwarding of topology change from sub-ring to major ring.
"
    DEFVAL { disabled }
    ::= { mesErpEntry 36 }

mesErpSubRings OBJECT-TYPE
    SYNTAX Counter64
    MAX-ACCESS  read-create
    STATUS      current
    DESCRIPTION
        "List of Ring Indexs of connected ERP v2 sub rings,
"
    DEFVAL { 0 }
    ::= { mesErpEntry 37 }

mesErpResourceTypeLeft OBJECT-TYPE
    SYNTAX      INTEGER {
                    port  (1),
                    lag   (2) }
    MAX-ACCESS  read-create
    STATUS      current
    DESCRIPTION
        "The type of resource the left leg of erp is connected.
"
    DEFVAL { port }
    ::= { mesErpEntry 38 }

 mesErpLagIdLeft OBJECT-TYPE
    SYNTAX      DisplayString(SIZE(1..17))
    MAX-ACCESS  read-create
    STATUS      current
    DESCRIPTION
        "Id of the left lag connected to erp.
"
    DEFVAL { "" }
    ::= { mesErpEntry 39 }

mesErpResourceTypeRight OBJECT-TYPE
    SYNTAX      INTEGER {
                    port  (1),
                    lag   (2) }
    MAX-ACCESS  read-create
    STATUS      current
    DESCRIPTION
        "The type of resource the right leg of erp is connected.
"
    DEFVAL { port }
    ::= { mesErpEntry 40 }

 mesErpLagIdRight OBJECT-TYPE
    SYNTAX      DisplayString(SIZE(1..17))
    MAX-ACCESS  read-create
    STATUS      current
    DESCRIPTION
        "Id of the right lag connected to erp.
"
    DEFVAL { "" }
    ::= { mesErpEntry 41 }

 mesErpInterfaceLeft OBJECT-TYPE
    SYNTAX      DisplayString(SIZE(1..17))
    MAX-ACCESS  read-create
    STATUS      current
    DESCRIPTION
        "Displayname for the left interface connected to erp.
"
    DEFVAL { "" }
    ::= { mesErpEntry 42 }

 mesErpInterfaceRight OBJECT-TYPE
    SYNTAX      DisplayString(SIZE(1..17))
    MAX-ACCESS  read-create
    STATUS      current
    DESCRIPTION
        "Displayname for the right interface connected to erp.
"
    DEFVAL { "" }
    ::= { mesErpEntry 43 }

mesErpProvisioningMismatch OBJECT-TYPE
    SYNTAX      FaultStatus
    MAX-ACCESS  read-only
    STATUS      current
    DESCRIPTION
        "Detected if the RPL owner receives one or more
         No request R-APS message(s) with the RPL blocked status flag
         set (NR, RB) and a node ID that differs from its own. dFOP-PM in G.8032.

"
    REFERENCE
       "G.8032"
    ::= { mesErpEntry 44 }

mesErpIfNoLeft OBJECT-TYPE
    SYNTAX      PortNumber
    MAX-ACCESS  read-create
    STATUS      current
    DESCRIPTION
        "The left interface number of the multi-connector port or port group.

"
    DEFVAL { 1 }
    ::= { mesErpEntry 45 }

mesErpTxPortLeft OBJECT-TYPE
    SYNTAX      PortNumber
    MAX-ACCESS  read-create
    STATUS      current
    DESCRIPTION
        "The TX-port of the left interface.

"
    DEFVAL { 0 }
    ::= { mesErpEntry 46 }

mesErpIfNoRight OBJECT-TYPE
    SYNTAX      PortNumber
    MAX-ACCESS  read-create
    STATUS      current
    DESCRIPTION
        "The right interface number of the multi-connector port or port group.

"
    DEFVAL { 1 }
    ::= { mesErpEntry 47 }

mesErpTxPortRight OBJECT-TYPE
    SYNTAX      PortNumber
    MAX-ACCESS  read-create
    STATUS      current
    DESCRIPTION
        "The TX-port of the right interface.

"
    DEFVAL { 0 }
    ::= { mesErpEntry 48 }

mesErpOamDetectionVlanId OBJECT-TYPE
    SYNTAX      Unsigned32 (1..4094)
    MAX-ACCESS  read-write
    STATUS      current
    DESCRIPTION
        "The VLAN ID in CCM:s used for OAM detection.

"
    DEFVAL { 4094 }
    ::= { mesErpEntry 49 }

-- ----------------------------------------------------
-- VLAN Protection Group
-- ----------------------------------------------------

mesVlanProtTable  OBJECT-TYPE
    SYNTAX      SEQUENCE OF MesVlanProtEntry
    MAX-ACCESS  not-accessible
    STATUS      current
    DESCRIPTION
       "Table of protected VLAN groups."
    ::= { mesVlanProtList 1 }

mesVlanProtEntry OBJECT-TYPE
    SYNTAX MesVlanProtEntry
    MAX-ACCESS not-accessible
    STATUS current
    DESCRIPTION
       "An entry in the VLAN protection group list.
       "
    INDEX { mesVlanProtIndex }
    ::= { mesVlanProtTable 1 }

MesVlanProtEntry ::=
    SEQUENCE {
        mesVlanProtIndex                     Unsigned32,
        mesVlanProtName                      MgmtNameString,
        mesVlanProtInternalReference         Unsigned32,
        mesVlanProtRings                     Counter64,
        mesVlanProtProtectedVlan             DisplayString,
        mesVlanProtIdentifier                DisplayString,
        mesVlanProtGroupId                   Unsigned32,
        mesVlanProtAddRingAction             CommandString,
        mesVlanProtRemoveRingAction          CommandString,
        mesVlanProtDescr                     DisplayString,
        mesVlanProtChangeVlansAction         CommandString}

mesVlanProtIndex OBJECT-TYPE
    SYNTAX      Unsigned32 (1..4294967295)
    MAX-ACCESS  read-only
    STATUS      current
    DESCRIPTION
        "An arbitrary index. Subrack and slot can
        be derived from the index.

        "
    ::= { mesVlanProtEntry 1 }

mesVlanProtName OBJECT-TYPE
    SYNTAX      MgmtNameString
    MAX-ACCESS  read-only
    STATUS      current
    DESCRIPTION
        "The management name of the VLAN protection group entry, for example
        'vlanProt:1:5:identifier' (vlanProt:[subrack]:[slot]:'identifier').

"
    ::= { mesVlanProtEntry 2 }

mesVlanProtInternalReference OBJECT-TYPE
    SYNTAX      Unsigned32 (0..2147483647)
    MAX-ACCESS  read-create
    STATUS      current
    DESCRIPTION
        "For internal use only.
        "
    DEFVAL { 0 }
    ::= { mesVlanProtEntry 3 }

mesVlanProtRings OBJECT-TYPE
    SYNTAX Counter64
    MAX-ACCESS  read-create
    STATUS      current
    DESCRIPTION
        "List of ERPv2 ring indexes of protecting rings,
"
    DEFVAL { 0 }
    ::= { mesVlanProtEntry 4 }

mesVlanProtProtectedVlan OBJECT-TYPE
    SYNTAX      DisplayString
    MAX-ACCESS  read-write
    STATUS      current
    DESCRIPTION
        "Comma separated list of VLANs and VLAN ranges that should be
         included in the ERPv2 protection.
        ex: 100,150-200,301

"
    DEFVAL { "" }
    ::= { mesVlanProtEntry 5 }

mesVlanProtGroupId OBJECT-TYPE
    SYNTAX      Unsigned32 (0..2147483647)
    MAX-ACCESS  read-create
    STATUS      current
    DESCRIPTION
        "Group identifier identifying this VLAN Protection group.
        The number is unique and generated by system.

"
    DEFVAL { 0 }
    ::= { mesVlanProtEntry 6 }

mesVlanProtIdentifier OBJECT-TYPE
    SYNTAX      DisplayString(SIZE(1..19))
    MAX-ACCESS  read-create
    STATUS      current
    DESCRIPTION
        "A unique identifier for the VLAN protection group on this traffic unit.
"
    DEFVAL { "" }
    ::= { mesVlanProtEntry 7 }

mesVlanProtAddRingAction OBJECT-TYPE
    SYNTAX      CommandString
    MAX-ACCESS  read-only
    STATUS      current
    DESCRIPTION
        "In the WEB dialog add or remove ERPv2 ring protection
        to/from a VLAN protection group:
        - choose ring to add or remove.

        In CLI add a ring protection to a VLAN protection group

        For removing ring protection in CLI use:
        'mes::vlanProt::vlanProt:X:Y:ID::removeRing'
"
    ::= { mesVlanProtEntry 8 }

mesVlanProtRemoveRingAction OBJECT-TYPE
    SYNTAX      CommandString
    MAX-ACCESS  read-only
    STATUS      current
    DESCRIPTION
        "Removes a ring protection from a VLAN protection group.

        For adding ring protection in CLI use:
        'mes::vlanProt::vlanProt:X:Y:ID::addRing'
"
    ::= { mesVlanProtEntry 9 }

mesVlanProtDescr OBJECT-TYPE
    SYNTAX      DisplayString
    MAX-ACCESS  read-write
    STATUS      current
    DESCRIPTION
        "User configurable label.

"
    DEFVAL { "" }
    ::= { mesVlanProtEntry 10 }

mesVlanProtChangeVlansAction OBJECT-TYPE
    SYNTAX      CommandString
    MAX-ACCESS  read-only
    STATUS      current
    DESCRIPTION
        "Change the VLANs protected by the VLAN protection group.

        Comma separated list of VLANs and VLAN ranges
        ex: 100,150-200,301

        For changing protected vlans in CLI use:
        'mes::vlanProt::vlanProt:X:Y:ID::changeVlans'
"
    ::= { mesVlanProtEntry 11 }


-- ----------------------------------------------------
-- Classification
-- ----------------------------------------------------

mesClassTable     OBJECT-TYPE
    SYNTAX      SEQUENCE OF MesClassEntry
    MAX-ACCESS  not-accessible
    STATUS      current
    DESCRIPTION
        "The classification list.

        Classification enables dynamic assignment of actions (rules) when
        traffic is received. The classification defines the traffic matching
        criteria for which the action (rule) is applied."
    ::= { mesClassList 1 }

mesClassEntry OBJECT-TYPE
    SYNTAX      MesClassEntry
    MAX-ACCESS  not-accessible
    STATUS      current
    DESCRIPTION
        "An entry in the classification list.
"
    INDEX { mesClassIndex }
    ::= { mesClassTable 1 }

MesClassEntry ::=
    SEQUENCE {
        mesClassIndex                 Unsigned32,
        mesClassName                  MgmtNameString,
        mesClassIdentifier            DisplayString,
        mesClassInternalReference     Unsigned32,
        mesClassPort                  Unsigned32,
        mesClassLagId                 MgmtNameString,
        mesClassOuterVlanId           Integer32,
        mesClassOuterVlanPcp          Integer32,
        mesClassPrecedence            Unsigned32,
        mesClassDaMacAddress          MacAddress,
        mesClassAssociateAction       CommandString,
        mesClassRowStatus             RowStatus,
        mesClassDaMacAddressMask      MacAddress,
        mesClassDSCP                  Integer32,
        mesClassInnerVlanId           Integer32,
        mesClassInnerVlanPcp          Integer32,
        mesClassInnerVlanCfi          Integer32,
        mesClassOuterVlanCfi          Integer32,
        mesClassDirection             INTEGER,
        mesClassOuterTpid             INTEGER,
        mesClassInternalClassId       Unsigned32,
        mesClassSourceAddressIPV4     Unsigned32,
        mesClassSourceMaskIPV4        Unsigned32,
        mesClassDestAddressIPV4       Unsigned32,
        mesClassDestMaskIPV4          Unsigned32,
        mesClassSubrack               SubrackNumber,
        mesClassSlot                  SlotNumber,
        mesClassVlanStackStructure    INTEGER,
        mesClassServiceId             ServiceIdWithNotUsed,
        mesClassEthertype             INTEGER,
        mesClassIfNo                  PortNumber,
        mesClassTxPort                PortNumber,
        mesClassAssociateActionAdvanced CommandString}

mesClassIndex OBJECT-TYPE
    SYNTAX      Unsigned32 (1..2147483647)
    MAX-ACCESS  read-only
    STATUS      current
    DESCRIPTION
        "An arbitrary index assigned to each classification entry.
"
    ::= { mesClassEntry 1 }

mesClassName OBJECT-TYPE
    SYNTAX      MgmtNameString
    MAX-ACCESS  read-only
    STATUS      current
    DESCRIPTION
        "The management name of the classification, for example 'class:1:6:myIdentifier'
        (class:[subrack]:[slot]:[identifier]).
"
    ::= { mesClassEntry 2 }

mesClassIdentifier OBJECT-TYPE
    SYNTAX      DisplayString(SIZE(1..22))
    MAX-ACCESS  read-create
    STATUS      current
    DESCRIPTION
        "Unique identifier for the classification.

"
    DEFVAL { "" }
    ::= { mesClassEntry 3 }

mesClassInternalReference OBJECT-TYPE
    SYNTAX      Unsigned32 (0..2147483647)
    MAX-ACCESS  read-create
    STATUS      current
    DESCRIPTION
        "For internal use only.
"
    DEFVAL { 0 }
    ::= { mesClassEntry 4 }

mesClassPort OBJECT-TYPE
    SYNTAX      Unsigned32 (0..2147483647)
    MAX-ACCESS  read-create
    STATUS      current
    DESCRIPTION
        "The port(s) to classificate on.

        This attribute is a bitmask, where each bit represents a port. The
        least significant bit represents port 1-2. The second least significant
        bit represents port 3-4, and so on.

        0 means no classification on port. The classification will match on all
        ports matching the classification criterias.

        Today it is only possibly to classify on a single port.

"
    ::= { mesClassEntry 5 }

mesClassLagId OBJECT-TYPE
    SYNTAX      MgmtNameString
    MAX-ACCESS  read-create
    STATUS      current
    DESCRIPTION
        "The identifier of the LAG to classify on.

        An empty string means no classification on LAG.
"
    ::= { mesClassEntry 6 }

mesClassOuterVlanId OBJECT-TYPE
    SYNTAX      Integer32 (-1..4094)
    MAX-ACCESS  read-create
    STATUS      current
    DESCRIPTION
        "Outer VLAN ID to classify on.

        -1: No classification on outer VLAN ID.

        0: Classification on priority tagged traffic.

"
    DEFVAL { -1 }
    ::= { mesClassEntry 7 }

mesClassOuterVlanPcp OBJECT-TYPE
    SYNTAX      Integer32 (-1..7)
    MAX-ACCESS  read-create
    STATUS      current
    DESCRIPTION
        "Outer VLAN PCP to classify on.

         If value is set to -1, then there is no classification
         performed on outer VLAN PCP.
"
    DEFVAL { -1 }
    ::= { mesClassEntry 8 }

mesClassPrecedence OBJECT-TYPE
    SYNTAX      Unsigned32 (0..511)
    MAX-ACCESS  read-create
    STATUS      current
    DESCRIPTION
        "When two policy classifications match, only the classification with the
         highest precedence will be carried out. If two classifiers have the same
         precedence, the classification created first will be carried out.

"
    ::= { mesClassEntry 9 }

mesClassDaMacAddress OBJECT-TYPE
    SYNTAX      MacAddress
    MAX-ACCESS  read-create
    STATUS      current
    DESCRIPTION
        "MAC destination address to classify on.

        If every byte in the MAC destination address is set to 0, then
        there is no classification made on MAC destination address.

"
    ::= { mesClassEntry 10 }

mesClassAssociateAction OBJECT-TYPE
    SYNTAX      CommandString
    MAX-ACCESS  read-only
    STATUS      current
    DESCRIPTION
        "Create and associate an action (rule) with a classification.

        Classification
          Select the classification for which the action should be applied.

        General policy action
          Action
          - None: Allows queue assignment or VLAN policy action.
          - Drop: All traffic is dropped.
          - Redirect: Traffic is redirected to a specific port.
          Queue assignment
          - Green frame: Assign green frames to a specific queue.
          - Yellow frame: Assign yellow frames to a specific queue.

        VLAN policy action
          Outer VLAN ID action
          - Push: Push a new VLAN tag in front of the existing outer VLAN tag.
          - Swap: Replace the existing outer VLAN ID.
          Outer VLAN PCP
          - Set: Assign a new PCP value for green or yellow frames.
          - Copy: Outer VLAN PCP is copied from the inner VLAN.
          Inner VLAN ID action
          - Pop: Inner VLAN tag is removed.
          - Push: Push a new VLAN tag in front of the existing inner VLAN tag. Pushing an
                  inner VLAN requires the frame to be single tagged. If not single tagged,
                  then no action is carried out. However, pushing both inner and outer
                  VLAN ID is allowed on an untagged frame.
          - Swap: Replace the existing inner VLAN ID and copy the outer VLAN PCP to the
                  inner VLAN tag.

        MEF policer
          Assign an existing  MEF policer (bandwidth profile) to the classification.
"
    ::= { mesClassEntry 11 }

mesClassRowStatus OBJECT-TYPE
    SYNTAX      RowStatus
    MAX-ACCESS  read-create
    STATUS      current
    DESCRIPTION
        "Manages creation and deletion of conceptual rows.
        See also SNMPv2-TC.

        Note: The newly created object will not necessarily
        receive the same index as used in the create
        procedure.

"
    ::= { mesClassEntry 12 }

mesClassDaMacAddressMask OBJECT-TYPE
    SYNTAX      MacAddress
    MAX-ACCESS  read-create
    STATUS      current
    DESCRIPTION
        "MAC destination address mask to classify on.

        This is a classification attribute that is used in combination
        with classification attribute MAC destination address. If every
        byte in the MAC destination address mask is set to FF, the
        classification on the mask is not used and the MAC address
        filtering will be done without the mask on MAC address
        classification attribute.

        If not used set to FF:FF:FF:FF:FF:FF. This is the
        default value.

"
    DEFVAL { 'FFFFFFFFFFFF'H }
    ::= { mesClassEntry 13 }

mesClassInnerVlanId OBJECT-TYPE
    SYNTAX      Integer32 (-1..4094)
    MAX-ACCESS  read-create
    STATUS      current
    DESCRIPTION
        "Inner VLAN ID to classify on.

        -1: No classification on inner VLAN ID.

        0: Classification on priority tagged traffic.

"
    DEFVAL { -1 }
    ::= { mesClassEntry 14 }

mesClassInnerVlanPcp OBJECT-TYPE
    SYNTAX      Integer32 (-1..7)
    MAX-ACCESS  read-create
    STATUS      current
    DESCRIPTION
        "Inner VLAN PCP to classify on.

         If value is set to -1, then there is no classification
         performed on inner VLAN PCP.
"
    DEFVAL { -1 }
    ::= { mesClassEntry  15 }

mesClassDSCP OBJECT-TYPE
    SYNTAX      Integer32 (-1..63)
    MAX-ACCESS  read-create
    STATUS      current
    DESCRIPTION
        "DSCP Differentiated Services CodePoint to classify on.
        If value is set to -1, then there is no classification performed on DSCP

"
    DEFVAL { -1 }
    ::= { mesClassEntry  16 }

mesClassInnerVlanCfi OBJECT-TYPE
    SYNTAX      Integer32 (-1..1)
    MAX-ACCESS  read-create
    STATUS      current
    DESCRIPTION
        "Inner VLAN CFI/DEI, Canonical Format Indicator/Discard Eligibility Indication.
        If value is set to -1, then there is no classification performed on CFI/DEI

"
    DEFVAL { -1 }
    ::= { mesClassEntry  17 }

mesClassOuterVlanCfi OBJECT-TYPE
    SYNTAX      Integer32 (-1..1)
    MAX-ACCESS  read-create
    STATUS      current
    DESCRIPTION
        "Outer VLAN CFI/DEI, Canonical Format Indicator/Discard Eligibility Indication.
        If value is set to -1, then there is no classification performed on CFI/DEI

"
    DEFVAL { -1 }
    ::= { mesClassEntry  18 }

mesClassDirection OBJECT-TYPE
    SYNTAX      INTEGER {
           undefined (0),
           ingress (1),
           egress (2)  }
    MAX-ACCESS  read-create
    STATUS      current
    DESCRIPTION
       "Direction of the data the classification is made on.

           ingress - Classfication is made on incoming traffic.

           egress - Classification is made on processed and outgoing traffic.

        If direction is not set ingress is assumed.

"
    ::= { mesClassEntry  19 }

mesClassOuterTpid OBJECT-TYPE
    SYNTAX      INTEGER {
                    undefined (0),
                    anyTag (1),
                    qTag0x8100 (2),
                    sTag0x88a8 (3)}
    MAX-ACCESS  read-create
    STATUS      current
    DESCRIPTION
        "Outer ethertype/TPID to classify on. Only valid if classification is made on outer VLAN ID,
        outer PCP or outer CFI.
"
    DEFVAL { 1 }
    ::= { mesClassEntry 20 }

mesClassInternalClassId OBJECT-TYPE
    SYNTAX      Unsigned32 (0..2147483647)
    MAX-ACCESS  read-create
    STATUS      current
    DESCRIPTION
        "For internal use only.
"
    DEFVAL { 0 }
    ::= { mesClassEntry 21 }


mesClassSourceAddressIPV4 OBJECT-TYPE
    SYNTAX      Unsigned32 (0..4294967295)
    MAX-ACCESS  read-create
    STATUS      current
    DESCRIPTION
        "Source IP address.
"
    DEFVAL { 0 }
    ::= { mesClassEntry 22 }

mesClassSourceMaskIPV4 OBJECT-TYPE
    SYNTAX      Unsigned32 (0..4294967295)
    MAX-ACCESS  read-create
    STATUS      current
    DESCRIPTION
        "Source network mask.
"
    DEFVAL { 0 }
    ::= { mesClassEntry 23 }

mesClassDestAddressIPV4 OBJECT-TYPE
    SYNTAX      Unsigned32 (0..4294967295)
    MAX-ACCESS  read-create
    STATUS      current
    DESCRIPTION
        "Destination IP address.
"
    DEFVAL { 0 }
    ::= { mesClassEntry 24 }

mesClassDestMaskIPV4 OBJECT-TYPE
    SYNTAX      Unsigned32 (0..4294967295)
    MAX-ACCESS  read-create
    STATUS      current
    DESCRIPTION
        "Destination network Mask.
"
    DEFVAL { 0 }
    ::= { mesClassEntry 25 }

mesClassSubrack  OBJECT-TYPE
    SYNTAX      SubrackNumber
    MAX-ACCESS  read-only
    STATUS      current
    DESCRIPTION
        "The number of the subrack where the classification
        is located.

"
    ::= { mesClassEntry 26 }

mesClassSlot  OBJECT-TYPE
    SYNTAX      SlotNumber
    MAX-ACCESS  read-only
    STATUS      current
    DESCRIPTION
        "The number of the slot where the classification
        is located.

"
    ::= { mesClassEntry 27 }

mesClassVlanStackStructure OBJECT-TYPE
    SYNTAX      INTEGER {
                    none (0),
                    untagged (1)}
    MAX-ACCESS  read-create
    STATUS      current
    DESCRIPTION
        "Vlan Stack Structure to classify on.

         untagged - Classification is made on traffic without vlan tag.

"
    DEFVAL { 0 }
    ::= { mesClassEntry 28 }

mesClassServiceId OBJECT-TYPE
    SYNTAX      ServiceIdWithNotUsed
    MAX-ACCESS  read-write
    STATUS      current
    DESCRIPTION
        "Service ID is used by TNM for multi-layer
        service and network management.
        Default value is -1. All objects that created
        from ENM will have default service ID.
        Change of the service ID may affect
        TNM service mappings.
"
    DEFVAL { -1 }
    ::= { mesClassEntry 29 }

mesClassEthertype OBJECT-TYPE
    SYNTAX      INTEGER {
                    undefined (0),
                    ipv40x0800 (1),
                    ipv60x86DD (2),
                    slow0x8809 (3),
                    macsec0x88E5 (4),
                    ptp0x88F7 (5),
                    oamcfm0x8902 (6)}
    MAX-ACCESS  read-create
    STATUS      current
    DESCRIPTION
        "Ethertype to classify on.

        ipv40x0800 - Internet Protocol version 4 (IPv4)
        ipv60x86DD - Internet Protocol Version 6 (IPv6)
        slow0x8809 - Slow Protocols (IEEE 802.3)
        macsec0x88E5 - MAC security (IEEE 802.1AE)
        ptp0x88F7 - Precision Time Protocol (PTP) over Ethernet (IEEE 1588)
        oamcfm0x8902 - IEEE 802.1ag Connectivity Fault Management (CFM) Protocol / ITU-T Recommendation Y.1731 (OAM)
"
    DEFVAL { 0 }
    ::= { mesClassEntry 30 }

mesClassIfNo OBJECT-TYPE
    SYNTAX      PortNumber
    MAX-ACCESS  read-create
    STATUS      current
    DESCRIPTION
        "The interface number of the multi-connector port or port group.

"
    DEFVAL { 1 }
    ::= { mesClassEntry 31 }

mesClassTxPort OBJECT-TYPE
    SYNTAX      PortNumber
    MAX-ACCESS  read-create
    STATUS      current
    DESCRIPTION
        "The tx port to classificate on.

"
    DEFVAL { 0 }
    ::= { mesClassEntry 32 }

mesClassAssociateActionAdvanced OBJECT-TYPE
    SYNTAX      CommandString
    MAX-ACCESS  read-only
    STATUS      current
    DESCRIPTION
        "Create and associate an action (rule) with a classification.

        Classification
          Select the classification for which the action should be applied.

        General policy action
          Action
          - None: Allows queue assignment or VLAN policy action.
          - Drop: All traffic is dropped.
          - Redirect: Traffic is redirected to a specific port.
          Queue assignment
          - Green frame: Assign green frames to a specific queue.
          - Yellow frame: Assign yellow frames to a specific queue.

        VLAN policy action
          Outer VLAN ID action
          - Push: Push a new VLAN tag in front of the existing outer VLAN tag.
          - Swap: Replace the existing outer VLAN ID.
          Outer VLAN PCP
          - Set: Assign a new PCP value for green or yellow frames.
          - Copy: Outer VLAN PCP is copied from the inner VLAN.
          Inner VLAN ID action
          - Pop: Inner VLAN tag is removed.
          - Push: Push a new VLAN tag in front of the existing inner VLAN tag. Pushing an
                  inner VLAN requires the frame to be single tagged. If not single tagged,
                  then no action is carried out. However, pushing both inner and outer
                  VLAN ID is allowed on an untagged frame.
          - Swap: Replace the existing inner VLAN ID and copy the outer VLAN PCP to the
                  inner VLAN tag.

        MEF policer
          Assign an existing  MEF policer (bandwidth profile) to the classification.
"
    ::= { mesClassEntry 39 }

-- ----------------------------------------------------
-- Action
-- ----------------------------------------------------

mesActionTable     OBJECT-TYPE
    SYNTAX      SEQUENCE OF MesActionEntry
    MAX-ACCESS  not-accessible
    STATUS      current
    DESCRIPTION
        "The VLAN action (rule) list.

        VLAN rule classification enables dynamic assignment of rules (actions)
        when traffic is received. When the incoming frame matches the criterias
         in the classification, the rule is applied to the frame."
    ::= { mesActionList 1 }

mesActionEntry OBJECT-TYPE
    SYNTAX      MesActionEntry
    MAX-ACCESS  not-accessible
    STATUS      current
    DESCRIPTION
        "An entry in the VLAN action list.
"
    INDEX { mesActionIndex }
    ::= { mesActionTable 1 }

MesActionEntry ::=
    SEQUENCE {
        mesActionIndex                 Unsigned32,
        mesActionName                  MgmtNameString,
        mesActionIdentifier            DisplayString,
        mesActionInternalReference     Unsigned32,
        mesActionType                  INTEGER,
        mesActionOuterVlanId           Unsigned32,
        mesActionPcp                   Unsigned32,
        mesActionPolicerId             DisplayString,
        mesActionInnerVlanId           Unsigned32,
        mesActionQueue                 Unsigned32,
        mesActionRowStatus             RowStatus,
        mesActionRedirectPort          Unsigned32,
        mesActionServiceId             ServiceIdWithNotUsed,
        mesActionRedirectIfNo          PortNumber,
        mesActionRedirectTxPort        PortNumber,
        mesActionClassId               DisplayString,
        mesActionSubrack               SubrackNumber,
        mesActionSlot                  SlotNumber}

mesActionIndex OBJECT-TYPE
    SYNTAX      Unsigned32 (1..2147483647)
    MAX-ACCESS  read-only
    STATUS      current
    DESCRIPTION
        "An arbitrary index assigned to each action entry.
"
    ::= { mesActionEntry 1 }

mesActionName OBJECT-TYPE
    SYNTAX      MgmtNameString
    MAX-ACCESS  read-only
    STATUS      current
    DESCRIPTION
        "The management name of the action, for example 'action:1:6:13'.
"
    ::= { mesActionEntry 2 }

mesActionIdentifier OBJECT-TYPE
    SYNTAX      DisplayString(SIZE(1..21))
    MAX-ACCESS  read-create
    STATUS      current
    DESCRIPTION
        "Unique identifier for the action.
        This attribute can be written via SNMP.

"
    DEFVAL { "" }
    ::= { mesActionEntry 3 }

mesActionInternalReference OBJECT-TYPE
    SYNTAX      Unsigned32 (0..2147483647)
    MAX-ACCESS  read-create
    STATUS      current
    DESCRIPTION
        "For internal use only.
"
    DEFVAL { 0 }
    ::= { mesActionEntry 4 }

mesActionType OBJECT-TYPE
    SYNTAX      INTEGER {
                    police (1),
                    greenPcp (2),
                    yellowPcp (3),
                    outerVlanIdPush (4),
                    outerVlanIdSwap (5),
                    innerVlanPop (6),
                    drop (7),
                    innerVlanIdPush (8),
                    innerVlanIdSwap (9),
                    greenQueue (10),
                    yellowQueue (11),
                    outerVlanPcpCopy (12),
                    redirect (13)}
    MAX-ACCESS  read-create
    STATUS      current
    DESCRIPTION
        "Type of action to be carried out.

        Police:              A MEF policer (bandwidth profile) is applied.

        Green PCP:           New PCP values for green frames.

        Yellow PCP:          New PCP value for yellow frames.

        Outer VLAN ID push:  A VLAN tag is pushed in front of the existing outer VLAN.
                             Pushing outer and inner VLAN can only be done to untagged frames,
                             otherwise no action is carried out.

        Outer VLAN ID swap:  The outer VLAN ID is replaced.

        Outer VLAN PCP copy: The outer VLAN PCP is copied from the incoming frame.

        Drop:                All traffic is dropped.

        Inner VLAN pop:      The inner VLAN tag is removed.

        Inner VLAN ID push:  A VLAN tag is pushed in front on the existing inner VLAN. Pushing an
                             inner VLAN requires the frame to be single tagged, otherwise no action
                             is carried out.

        Inner VLAN ID swap:  The inner VLAN ID is replaced. Swapping an inner VLAN requires the frame
                             to be single tagged, otherwise no action is carried out.

        Green queue:         Green frames are added to a specific queue.

        Yellow queue:        Yellow frames are added to a specific queue.

        Redirect:            Traffic is redirected to a specific port.

        This attribute can be written via SNMP.

"
    DEFVAL { police }
    ::= { mesActionEntry 5 }

mesActionOuterVlanId OBJECT-TYPE
    SYNTAX      Unsigned32 (1..4094)
    MAX-ACCESS  read-write
    STATUS      current
    DESCRIPTION
        "New outer VLAN ID. Only used when action is 'Outer VLAN ID push' or
        'Outer VLAN ID swap'.

        This attribute can be written via SNMP.

"
    DEFVAL { 1 }
    ::= { mesActionEntry 6 }

mesActionPcp OBJECT-TYPE
    SYNTAX      Unsigned32 (0..7)
    MAX-ACCESS  read-write
    STATUS      current
    DESCRIPTION
        "New PCP value. Only used when action is 'Green PCP' or 'Yellow PCP'.

        This attribute can be written via SNMP.

"
    DEFVAL { 0 }
    ::= { mesActionEntry 7 }

mesActionPolicerId OBJECT-TYPE
    SYNTAX      DisplayString
    MAX-ACCESS  read-create
    STATUS      current
    DESCRIPTION
        "The MEF Policer identifier. Only used when action is 'Policer'.

        This attribute can be written via SNMP.

"
        DEFVAL { "" }
    ::= { mesActionEntry 8 }

mesActionInnerVlanId OBJECT-TYPE
    SYNTAX      Unsigned32 (1..4094)
    MAX-ACCESS  read-write
    STATUS      current
    DESCRIPTION
        "New inner VLAN ID. Only used when action is 'Inner VLAN ID push' or
        'Inner VLAN ID swap'.
        This attribute can be written via SNMP.

"
    DEFVAL { 1 }
    ::= { mesActionEntry 9 }

mesActionQueue OBJECT-TYPE
    SYNTAX      Unsigned32 (1..8)
    MAX-ACCESS  read-create
    STATUS      current
    DESCRIPTION
        "The queue number. Only used when action is 'Green queue' or 'Yellow queue'.
        This attribute can be written via SNMP.

"
    DEFVAL { 1 }
    ::= { mesActionEntry 10 }

mesActionRowStatus OBJECT-TYPE
    SYNTAX      RowStatus
    MAX-ACCESS  read-create
    STATUS      current
    DESCRIPTION
        "Manages creation and deletion of conceptual rows.
        See also SNMPv2-TC.

        Note: The newly created object will not necessarily
        receive the same index as used in the create
        procedure.
        This attribute can be written via SNMP.

"
    ::= { mesActionEntry 11 }

mesActionRedirectPort OBJECT-TYPE
    SYNTAX      Unsigned32 (0..2147483647)
    MAX-ACCESS  read-create
    STATUS      current
    DESCRIPTION
         "The port to redirect traffic.

        This attribute is a bitmask, where each bit represents a port. The
        least significant bit represents port 1-2. The second least significant
        bit represents port 3-4, and so on.

"
    ::= { mesActionEntry 12 }

mesActionServiceId OBJECT-TYPE
    SYNTAX      ServiceIdWithNotUsed
    MAX-ACCESS  read-write
    STATUS      current
    DESCRIPTION
        "Service ID is used by TNM for multi-layer
        service and network management.
        Default value is -1. All objects that created
        from ENM will have default service ID.
        Change of the service ID may affect
        TNM service mappings.
"
    DEFVAL { -1 }
    ::= { mesActionEntry 13 }

mesActionRedirectIfNo OBJECT-TYPE
    SYNTAX      PortNumber
    MAX-ACCESS  read-create
    STATUS      current
    DESCRIPTION
        "The interface number of the multi-connector to the redirect traffic port.

"
    DEFVAL { 1 }
    ::= { mesActionEntry 14 }

mesActionRedirectTxPort OBJECT-TYPE
    SYNTAX      PortNumber
    MAX-ACCESS  read-create
    STATUS      current
    DESCRIPTION
        "The port to redirect traffic.

"
    DEFVAL { 0 }
    ::= { mesActionEntry 15 }

mesActionClassId OBJECT-TYPE
    SYNTAX      DisplayString
    MAX-ACCESS  read-create
    STATUS      current
    DESCRIPTION
        "The classifier identifier.

"
        DEFVAL { "" }
    ::= { mesActionEntry 16 }

mesActionSubrack  OBJECT-TYPE
    SYNTAX      SubrackNumber
    MAX-ACCESS  read-only
    STATUS      current
    DESCRIPTION
        "The number of the subrack where the action is located.

"
    ::= { mesActionEntry 17 }

mesActionSlot  OBJECT-TYPE
    SYNTAX      SlotNumber
    MAX-ACCESS  read-only
    STATUS      current
    DESCRIPTION
        "The number of the slot where the action is located.

"
    ::= { mesActionEntry 18 }


-- ----------------------------------------------------
-- Policy
-- ----------------------------------------------------

mesPolicyTable     OBJECT-TYPE
    SYNTAX      SEQUENCE OF MesPolicyEntry
    MAX-ACCESS  not-accessible
    STATUS      current
    DESCRIPTION
        "The policy list.

        Policy enables dynamic assignment of rules (actions) when traffic is received. The
        policy consist of two parts, classification and rule (action). The classification
        defines the traffic matching criteria for which the rule are applied.

        When a frame arrives on a port, the network element checks if the frame match the
        classification criteria. If it does, then the action will by applied to the frame.

        One action can be assigned to many classifications."
    ::= { mesPolicyList 1 }

mesPolicyEntry OBJECT-TYPE
    SYNTAX      MesPolicyEntry
    MAX-ACCESS  not-accessible
    STATUS      current
    DESCRIPTION
        "An entry in the policy list.
"
    INDEX { mesPolicyIndex }
    ::= { mesPolicyTable 1 }

MesPolicyEntry ::=
    SEQUENCE {
        mesPolicyIndex                 Unsigned32,
        mesPolicyName                  MgmtNameString,
        mesPolicyInternalReference     Unsigned32,
        mesPolicyClass                 DisplayString,
        mesPolicyAction                DisplayString,
        mesPolicyServiceId             ServiceIdWithNotUsed}

mesPolicyIndex OBJECT-TYPE
    SYNTAX      Unsigned32 (1..2147483647)
    MAX-ACCESS  read-only
    STATUS      current
    DESCRIPTION
        "An arbitrary index assigned to each policy entry.
"
    ::= { mesPolicyEntry 1 }

mesPolicyName OBJECT-TYPE
    SYNTAX      MgmtNameString
    MAX-ACCESS  read-only
    STATUS      current
    DESCRIPTION
        "The management name of the policy, for example 'map:1:6:13'.
        (map:[subrack]:[slot]:[generatedNumber]).
"
    ::= { mesPolicyEntry 2 }

mesPolicyInternalReference OBJECT-TYPE
    SYNTAX      Unsigned32 (0..2147483647)
    MAX-ACCESS  read-create
    STATUS      current
    DESCRIPTION
        "For internal use only.
"
    DEFVAL { 0 }
    ::= { mesPolicyEntry 4 }

mesPolicyClass OBJECT-TYPE
    SYNTAX      DisplayString
    MAX-ACCESS  read-create
    STATUS      current
    DESCRIPTION
        "The identifier of the classification for which this policy applies.
"
    ::= { mesPolicyEntry 5 }

mesPolicyAction OBJECT-TYPE
    SYNTAX      DisplayString
    MAX-ACCESS  read-create
    STATUS      current
    DESCRIPTION
        "The identifier of the action (rule) for which this policy applies.
"
    ::= { mesPolicyEntry 6 }

mesPolicyServiceId OBJECT-TYPE
    SYNTAX      ServiceIdWithNotUsed
    MAX-ACCESS  read-write
    STATUS      current
    DESCRIPTION
        "Service ID is used by TNM for multi-layer
        service and network management.
        Default value is -1. All objects that created
        from ENM will have default service ID.
        Change of the service ID may affect
        TNM service mappings.
"
    DEFVAL { -1 }
    ::= { mesPolicyEntry 7 }

-- ----------------------------------------------------
-- Error prop
-- ----------------------------------------------------

mesErrorPropTable     OBJECT-TYPE
    SYNTAX      SEQUENCE OF MesErrorPropEntry
    MAX-ACCESS  not-accessible
    STATUS      current
    DESCRIPTION
        "The error propagator group rule list."
    ::= { mesErrorPropList 1 }

mesErrorPropEntry OBJECT-TYPE
    SYNTAX      MesErrorPropEntry
    MAX-ACCESS  not-accessible
    STATUS      current
    DESCRIPTION
        "An entry in the error propagation rule list.
"
    INDEX { mesErrorPropIndex }
    ::= { mesErrorPropTable 1 }

MesErrorPropEntry ::=
    SEQUENCE {
        mesErrorPropIndex                 Unsigned32,
        mesErrorPropName                  MgmtNameString,
        mesErrorPropDescr                 DisplayString,
        mesErrorPropInternalReference     Unsigned32,
        mesErrorPropAdminStatus           BoardOrInterfaceAdminStatus,
        mesErrorPropOperStatus            BoardOrInterfaceOperStatus,
        mesErrorPropState                 INTEGER,
        mesErrorPropTriggerType           INTEGER,
        mesErrorPropTriggerObject         DisplayString,
        mesErrorPropTriggerPortIndex      Unsigned32,
        mesErrorPropTriggerMepIndex       Unsigned32,
        mesErrorPropTriggerLagIndex       Unsigned32,
        mesErrorPropActionType            INTEGER,
        mesErrorPropActionObject          DisplayString,
        mesErrorPropActionPortIndex       Unsigned32,
        mesErrorPropActionMepIndex        Unsigned32,
        mesErrorPropActionErpIndex        Unsigned32,
        mesErrorPropHoldOffTimer          Unsigned32,
        mesErrorPropRowStatus             RowStatus,
        mesErrorPropFault                 FaultStatus,
        mesErrorPropSubrack               SubrackNumber,
        mesErrorPropSlot                  SlotNumber,
        mesErrorPropServiceId             ServiceIdWithNotUsed}

mesErrorPropIndex OBJECT-TYPE
    SYNTAX      Unsigned32 (1..2147483647)
    MAX-ACCESS  read-only
    STATUS      current
    DESCRIPTION
        "An arbitrary index assigned to each error propagation rule entry.
"
    ::= { mesErrorPropEntry 1 }

mesErrorPropName OBJECT-TYPE
    SYNTAX      MgmtNameString
    MAX-ACCESS  read-only
    STATUS      current
    DESCRIPTION
        "The management name of the error propagation rule. The name changes depending on rule type, for example 'ep:1:4:port:3-4:port:21-22'.
        (ep:[subrack]:[slot]:[triggerObject]:[actionObject]:[index]).
"
    ::= { mesErrorPropEntry 2 }

mesErrorPropDescr OBJECT-TYPE
    SYNTAX      DisplayString
    MAX-ACCESS  read-write
    STATUS      current
    DESCRIPTION
        "User configurable label.

"
    DEFVAL { "" }
    ::= { mesErrorPropEntry 3 }

mesErrorPropInternalReference OBJECT-TYPE
    SYNTAX      Unsigned32 (0..2147483647)
    MAX-ACCESS  read-create
    STATUS      current
    DESCRIPTION
        "For internal use only.
"
    DEFVAL { 0 }
    ::= { mesErrorPropEntry 4 }

mesErrorPropAdminStatus  OBJECT-TYPE
    SYNTAX      BoardOrInterfaceAdminStatus
    MAX-ACCESS  read-write
    STATUS      current
    DESCRIPTION
        "The administrative state of the error propagation rule.

        down - The rule is de-activated.
        up - The rule is activated.
        service - The rule is activated, but alarms are suppressed.

"
    DEFVAL { up }
 ::= { mesErrorPropEntry 5 }

mesErrorPropOperStatus OBJECT-TYPE
    SYNTAX      BoardOrInterfaceOperStatus
    MAX-ACCESS  read-only
    STATUS      current
    DESCRIPTION
        "The operational state for the object.
        notPresent - The object is not available.
        down - The object is de-activated or depending objects are in 'admin down'.
        up - The object is active.

"
    DEFVAL { down }
    ::= { mesErrorPropEntry 6 }

mesErrorPropState  OBJECT-TYPE
    SYNTAX      INTEGER {
                    inactive(1),
                    active(2) }
    MAX-ACCESS  read-only
    STATUS      current
    DESCRIPTION
        "Indicates whether the error propagation rule is invoked or not.
"
    DEFVAL { 1 }
    ::= { mesErrorPropEntry 7 }

mesErrorPropTriggerType OBJECT-TYPE
    SYNTAX      INTEGER {
                    mepStatus (1),
                    portStatus (2),
                    mepCsf (3),
                    lagStateChange (4) }
    MAX-ACCESS  read-create
    STATUS      current
    DESCRIPTION
        "Defines the type of trigger that will activate the error propagation rule.
"
   DEFVAL { mepStatus }
   ::= { mesErrorPropEntry 8 }

mesErrorPropTriggerObject OBJECT-TYPE
    SYNTAX      DisplayString
    MAX-ACCESS  read-create
    STATUS      current
    DESCRIPTION
        "The name of the object that will trigger the error propagation rule.
"
    ::= { mesErrorPropEntry 9 }

mesErrorPropTriggerPortIndex OBJECT-TYPE
    SYNTAX      Unsigned32
    MAX-ACCESS  read-only
    STATUS      current
    DESCRIPTION
        "The index of the port that will trigger the error propagation rule.
         Only valid if the trigger type is set to 'portStatus'.
"
    ::= { mesErrorPropEntry 10 }

mesErrorPropTriggerMepIndex OBJECT-TYPE
    SYNTAX      Unsigned32
    MAX-ACCESS  read-only
    STATUS      current
    DESCRIPTION
        "The index of the MEP that will trigger the error propagation rule.
         Only valid if the trigger type is set to 'mepStatus' or 'mepCsf'.
"
    ::= { mesErrorPropEntry 11 }

mesErrorPropActionType OBJECT-TYPE
    SYNTAX      INTEGER {
                    laserShutdown (1),
                    sendCsf (3),
                    flushMacTable (4),
                    flushMacTableAll (5),
                    flushMacTableERPv2 (6)}
    MAX-ACCESS  read-create
    STATUS      current
    DESCRIPTION
        "Defines the type of action that will be performed when the
         error propagation rule is triggered.
        - laserShutdown : Shuts down the laser on the action port.
        - sendCsf : Transmits a csf-los message on action MEP.
        - flushMacTable : Flushes the MAC table on the trigger MEP VLAN.
        - flushMacTableAll : Flushes the entire MAC table on the board.
        - flushMacTableERPv2 : Flushes the protected VLANs on an ERPv2 major ring by topology change propagation. For EMXP generation 3 it will flush all VLANs on the protected ports.
"
    DEFVAL { laserShutdown }
    ::= { mesErrorPropEntry 12 }

mesErrorPropActionObject OBJECT-TYPE
    SYNTAX      DisplayString
    MAX-ACCESS  read-create
    STATUS      current
    DESCRIPTION
        "The name of the object on which the action will be performed when the rule is triggered.
"
    ::= { mesErrorPropEntry 13 }

mesErrorPropActionPortIndex OBJECT-TYPE
    SYNTAX      Unsigned32
    MAX-ACCESS  read-only
    STATUS      current
    DESCRIPTION
        "The index of the port on which the action will be performed
         when the rule is triggered. Only valid if the action type is set to 'laserShutDown'.
"
    ::= { mesErrorPropEntry 14 }

mesErrorPropActionMepIndex OBJECT-TYPE
    SYNTAX      Unsigned32
    MAX-ACCESS  read-only
    STATUS      current
    DESCRIPTION
        "The identifier of the MEP on which the action will be performed
         when the rule is triggered. Only valid if the action type is set to 'sendCsf'.
"
      DEFVAL { 0 }
    ::= { mesErrorPropEntry 15 }

mesErrorPropActionErpIndex OBJECT-TYPE
    SYNTAX      Unsigned32
    MAX-ACCESS  read-only
    STATUS      current
    DESCRIPTION
        "The identifier of the ERPv2 on which the action will be performed
         when the rule is triggered. Only valid if the action type is set to LAG State Change.
"
      DEFVAL { 0 }
    ::= { mesErrorPropEntry 19 }

mesErrorPropHoldOffTimer OBJECT-TYPE
    SYNTAX      Unsigned32 (0..10000)
    MAX-ACCESS  read-write
    STATUS      current
    DESCRIPTION
        "Hold-off timer coordinates timing of error propagation
         actions. When an event occurs, this event
         should not be acted upon before the hold-off timer
         has elapsed.

"
    DEFVAL { 0 }
    ::= { mesErrorPropEntry 16 }

mesErrorPropRowStatus OBJECT-TYPE
    SYNTAX      RowStatus
    MAX-ACCESS  read-create
    STATUS      current
    DESCRIPTION
        "Manages creation and deletion of conceptual rows.
        See also SNMPv2-TC.

"
    ::= { mesErrorPropEntry 17 }

mesErrorPropFault OBJECT-TYPE
    SYNTAX      FaultStatus
    MAX-ACCESS  read-only
    STATUS      current
    DESCRIPTION
        "Error propagation rule is active.

"
    ::= { mesErrorPropEntry 18 }

mesErrorPropTriggerLagIndex OBJECT-TYPE
    SYNTAX      Unsigned32
    MAX-ACCESS  read-only
    STATUS      current
    DESCRIPTION
        "The index of the LAG that will trigger the error propagation rule.
         Only valid if the trigger type is set to 'lagStateChange'.
"
    ::= { mesErrorPropEntry 20 }

mesErrorPropSubrack OBJECT-TYPE
    SYNTAX      SubrackNumber
    MAX-ACCESS  read-create
    STATUS      current
    DESCRIPTION
        "The number of the subrack where the error propagation is located.

"
    ::= { mesErrorPropEntry 21 }

mesErrorPropSlot OBJECT-TYPE
    SYNTAX      SlotNumber
    MAX-ACCESS  read-create
    STATUS      current
    DESCRIPTION
        "The number of the slot where the error propagation is located.

"
    ::= { mesErrorPropEntry 22 }

mesErrorPropServiceId OBJECT-TYPE
    SYNTAX      ServiceIdWithNotUsed
    MAX-ACCESS  read-write
    STATUS      current
    DESCRIPTION
        "Service ID is used by TNM for multi-layer
        service and network management.
        Default value is -1. All objects that created
        from ENM will have default service ID.
        Change of the service ID may affect
        TNM service mappings.
"
    DEFVAL { -1 }
    ::= { mesErrorPropEntry 23 }

-- ----------------------------------------------------
-- Object and event groups
-- ----------------------------------------------------

mesGeneralGroup OBJECT-GROUP
    OBJECTS {
        mesGeneralConfigLastChangeTime,
        mesGeneralStateLastChangeTime,
        mesGeneralUniTableSize,
        mesGeneralNniTableSize,
        mesGeneralEvcTableSize,
        mesGeneralBwpTableSize,
        mesGeneralCeEvcMapTableSize }
    STATUS      deprecated
    DESCRIPTION
        "The general objects."
    ::= { lumMesGroups 1 }

mesUniGroup OBJECT-GROUP
    OBJECTS {
        mesUniIndex,
        mesUniName,
        mesUniDescr,
        mesUniSubrack,
        mesUniSlot,
        mesUniTxPort,
        mesUniRxPort,
        mesUniObjectProperty,
        mesUniAdminStatus,
        mesUniOperStatus,
        mesUniIdentifier,
        mesUniMtuSize,
        mesUniMaxNoOfEvcs,
        mesUniCurrentNoOfEvcs,
        mesUniAvailableCapacity,
        mesUniServiceMultiplexing,
        mesUniBundling,
        mesUniAllToOneBundling,
        mesUniUntaggedCeVlanIdAssignment,
        mesUniAssociateBwp,
        mesUniReleaseBwp,
        mesUniIngressBwProfilePerUni,
        mesUniIngressBwp,
        mesUniEgressBwProfilePerUni,
        mesUniEgressBwp,
        mesUniL2ControlProtocolProcessing,
        mesUniSetupCommand,
        mesUniCreateEvcCommand,
        mesUniListCeVlanIdsCommand,
        mesUniTaggingOfUntaggedFrames,
        mesUniCeVlanIdAssignmentCommand
    }
    STATUS      deprecated
    DESCRIPTION
        "The UNI objects."
    ::= { lumMesGroups 2 }

mesNniGroup OBJECT-GROUP
    OBJECTS {
        mesNniIndex,
        mesNniName,
        mesNniDescr,
        mesNniSubrack,
        mesNniSlot,
        mesNniTxPort,
        mesNniRxPort,
        mesNniObjectProperty,
        mesNniAdminStatus,
        mesNniOperStatus,
        mesNniIdentifier,
        mesNniCurrentNoOfEvcs,
        mesNniAvailableCapacity,
        mesNniDefineMgmtVlan,
        mesNniMgmtVlanTagType,
        mesNniMgmtVlanEtherType,
        mesNniMgmtVlanVlanId,
        mesNniMgmtVlanPriority,
        mesNniMgmtVlanIpAddress,
        mesNniMgmtVlanNetMask,
        mesNniMgmtVlanMacAddress
    }
    STATUS      deprecated
    DESCRIPTION
        "The UNI objects."
    ::= { lumMesGroups 3 }

mesEvcGroup OBJECT-GROUP
    OBJECTS {
        mesEvcIndex,
        mesEvcName,
        mesEvcDescr,
        mesEvcObjectProperty,
        mesEvcAdminStatus,
        mesEvcOperStatus,
        mesEvcIdentifier,
        mesEvcUniIdentifier,
        mesEvcNniIdentifier,
        mesEvcType,
        mesEvcMtuSize,
        mesEvcFrameDeliveryUnicast,
        mesEvcFrameDeliveryMulticast,
        mesEvcFrameDeliveryBroadcast,
        mesEvcDefineL2Control,
        mesEvcL2ControlProtocolDisposition,
        mesEvcL2DestinationMacAddress,
        mesEvcCeVlanIdPreservation,
        mesEvcCosPreservation,
        mesEvcAssociateBwp,
        mesEvcReleaseBwp,
        mesEvcIngressBwProfilePerEvc,
        mesEvcIngressBwp,
        mesEvcEgressBwProfilePerEvc,
        mesEvcEgressBwp,
        mesEvcCreateCeVlanIdMap,
        mesEvcDefineProviderTag,
        mesEvcProviderTagType,
        mesEvcProviderTagEtherType,
        mesEvcProviderTagVlanId,
        mesEvcDefineClassOfService,
        mesEvcCoSClassification,
        mesEvcCoSPriority,
        mesEvcInternalReference
    }
    STATUS      deprecated
    DESCRIPTION
        "The EVC objects."
    ::= { lumMesGroups 4 }

mesCeEvcMapGroup OBJECT-GROUP
    OBJECTS {
        mesCeEvcMapIndex,
        mesCeEvcMapName,
        mesCeEvcMapObjectProperty,
        mesCeEvcMapType,
        mesCeEvcMapVlanIdRangeLower,
        mesCeEvcMapVlanIdRangeUpper,
        mesCeEvcMapEvcId,
        mesCeEvcMapInternalReference
    }
    STATUS      deprecated
    DESCRIPTION
        "The CE EVC map objects."
    ::= { lumMesGroups 5 }

mesBwpGroup OBJECT-GROUP
    OBJECTS {
        mesBwpIndex,
        mesBwpName,
        mesBwpObjectProperty,
        mesBwpCoSIdentifier,
        mesBwpCir,
        mesBwpCbs,
        mesBwpEir,
        mesBwpEbs,
        mesBwpCouplingFlag,
        mesBwpColorMode,
        mesBwpInternalReference
    }
    STATUS      deprecated
    DESCRIPTION
        "The BWP objects."
    ::= { lumMesGroups 6 }

mesCeEvcMapGroupV2 OBJECT-GROUP
    OBJECTS {
        mesCeEvcMapIndex,
        mesCeEvcMapName,
        mesCeEvcMapObjectProperty,
        mesCeEvcMapType,
        mesCeEvcMapVlanIdRangeLower,
        mesCeEvcMapVlanIdRangeUpper,
        mesCeEvcMapEvcId,
        mesCeEvcMapInternalReference,
        mesCeEvcMapRowStatus,
        mesCeEvcMapPrio0Included,
        mesCeEvcMapPrio1Included,
        mesCeEvcMapPrio2Included,
        mesCeEvcMapPrio3Included,
        mesCeEvcMapPrio4Included,
        mesCeEvcMapPrio5Included,
        mesCeEvcMapPrio6Included,
        mesCeEvcMapPrio7Included,
        mesCeEvcMapDefaultCeVlanId,
        mesCeEvcMapPrioIncluded }
    STATUS      current
    DESCRIPTION
        "The CE EVC map objects v2 (10.0)."
    ::= { lumMesGroups 7 }

mesBwpGroupV2 OBJECT-GROUP
    OBJECTS {
        mesBwpIndex,
        mesBwpName,
        mesBwpObjectProperty,
        mesBwpCoSIdentifier,
        mesBwpCir,
        mesBwpCbs,
        mesBwpEir,
        mesBwpEbs,
        mesBwpCouplingFlag,
        mesBwpColorMode,
        mesBwpInternalReference,
        mesBwpRowStatus }
    STATUS      deprecated
    DESCRIPTION
        "The BWP objects v2 (10.0)."
    ::= { lumMesGroups 8 }

mesUniGroupV2 OBJECT-GROUP
    OBJECTS {
        mesUniIndex,
        mesUniName,
        mesUniDescr,
        mesUniSubrack,
        mesUniSlot,
        mesUniTxPort,
        mesUniRxPort,
        mesUniObjectProperty,
        mesUniAdminStatus,
        mesUniOperStatus,
        mesUniIdentifier,
        mesUniMtuSize,
        mesUniMaxNoOfEvcs,
        mesUniCurrentNoOfEvcs,
        mesUniAvailableCapacity,
        mesUniServiceMultiplexing,
        mesUniBundling,
        mesUniAllToOneBundling,
        mesUniUntaggedCeVlanIdAssignment,
        mesUniAssociateBwp,
        mesUniReleaseBwp,
        mesUniIngressBwProfilePerUni,
        mesUniIngressBwp,
        mesUniEgressBwProfilePerUni,
        mesUniEgressBwp,
        mesUniSetupCommand,
        mesUniCreateEvcCommand,
        mesUniListCeVlanIdsCommand,
        mesUniTaggingOfUntaggedFrames,
        mesUniCeVlanIdAssignmentCommand,
        mesUniL2SpanningTreeProcessing,
        mesUniL2PauseProcessing,
        mesUniL2SlowProtocolsProcessing,
        mesUniL2PortAuthenticationProcessing,
        mesUniL2OtherBridgeBlockProcessing,
        mesUniL2AllLANsBridgeMgmtProcessing,
        mesUniL2GarpProcessing,
        mesUniL2OamUniMeProcessing }
    STATUS      deprecated
    DESCRIPTION
        "The UNI objects V2 (10.0)."
    ::= { lumMesGroups 9 }

mesEvcGroupV2 OBJECT-GROUP
    OBJECTS {
        mesEvcIndex,
        mesEvcName,
        mesEvcDescr,
        mesEvcObjectProperty,
        mesEvcAdminStatus,
        mesEvcOperStatus,
        mesEvcIdentifier,
        mesEvcUniIdentifier,
        mesEvcNniIdentifier,
        mesEvcType,
        mesEvcMtuSize,
        mesEvcFrameDeliveryUnicast,
        mesEvcFrameDeliveryMulticast,
        mesEvcFrameDeliveryBroadcast,
        mesEvcDefineL2Control,
        mesEvcL2ControlProtocolDisposition,
        mesEvcL2DestinationMacAddress,
        mesEvcCeVlanIdPreservation,
        mesEvcCosPreservation,
        mesEvcAssociateBwp,
        mesEvcReleaseBwp,
        mesEvcIngressBwProfilePerEvc,
        mesEvcIngressBwp,
        mesEvcEgressBwProfilePerEvc,
        mesEvcEgressBwp,
        mesEvcCreateCeVlanIdMap,
        mesEvcDefineProviderTag,
        mesEvcProviderTagType,
        mesEvcProviderTagEtherType,
        mesEvcProviderTagVlanId,
        mesEvcDefineClassOfService,
        mesEvcCoSClassification,
        mesEvcCoSPriority,
        mesEvcInternalReference,
        mesEvcRowStatus,
        mesEvcQProfile,
        mesEvcCeVlanIdMap,
        mesEvcDefaultCeVlanPriority }
    STATUS      deprecated
    DESCRIPTION
        "The EVC objects v2 (10.0)."
    ::= { lumMesGroups 10 }

mesQProfileGroup OBJECT-GROUP
    OBJECTS {
        mesQProfileIndex,
        mesQProfileName,
        mesQProfileObjectProperty,
        mesQProfileType,
        mesQProfileId,
        mesQProfileType,
        mesQProfileWeight,
        mesQProfileGreenLowThreshold,
        mesQProfileGreenHighThreshold,
        mesQProfileGreenDropProbability,
        mesQProfileYellowLowThreshold,
        mesQProfileYellowHighThreshold,
        mesQProfileYellowDropProbability,
        mesQProfileInternalReference }
    STATUS      current
    DESCRIPTION
        "The queue profile objects."
    ::= { lumMesGroups 11 }

mesMepGroup OBJECT-GROUP
    OBJECTS {
        mesMepIndex,
        mesMepName,
        mesMepObjectProperty,
        mesMepMeIdentifier,
        mesMepInternalReference,
        mesMepAdminStatus,
        mesMepOperStatus,
        mesMepTransmissionInterval,
        mesMepLossOfContinuity,
        mesMepUnexpectedMegId,
        mesMepUnexpectedTransmissionInterval,
        mesMepRemoteDefectIndication,
        mesMepUnexpectedOpCode,
        mesMepAlarmIndicationSignal,
        mesMepMegIdFormatReceived,
        mesMepMegIdReceived,
        mesMepMegIdIccReceived,
        mesMepId,
        mesMepIdExpected,
        mesMepIdReceived,
        mesMepUnexpectedMepId,
        mesMepUnexpectedMegLevel,
        mesMepMegId,
        mesMepMegIdFormat,
        mesMepMegIdIcc }
    STATUS      current
    DESCRIPTION
        "The maintenance entity group end point objects."
    ::= { lumMesGroups 12 }

mesGeneralGroupV2 OBJECT-GROUP
    OBJECTS {
        mesGeneralConfigLastChangeTime,
        mesGeneralStateLastChangeTime,
        mesGeneralUniTableSize,
        mesGeneralNniTableSize,
        mesGeneralEvcTableSize,
        mesGeneralBwpTableSize,
        mesGeneralCeEvcMapTableSize,
        mesGeneralMepTableSize,
        mesGeneralMegTableSize,
        mesGeneralEvcBwpMapTableSize }
    STATUS      deprecated
    DESCRIPTION
        "The general objects."
    ::= { lumMesGroups 13 }

mesMegGroup OBJECT-GROUP
    OBJECTS {
        mesMegIndex,
        mesMegName,
        mesMegObjectProperty,
        mesMegInternalReference,
        mesMegAdminStatus,
        mesMegOperStatus,
        mesMegLevel,
        mesMegUnexpectedMessage }
    STATUS      current
    DESCRIPTION
        "The maintenance entity group objects."
    ::= { lumMesGroups 14 }

mesUniGroupV3 OBJECT-GROUP
    OBJECTS {
        mesUniIndex,
        mesUniName,
        mesUniDescr,
        mesUniSubrack,
        mesUniSlot,
        mesUniTxPort,
        mesUniRxPort,
        mesUniObjectProperty,
        mesUniAdminStatus,
        mesUniOperStatus,
        mesUniIdentifier,
        mesUniMtuSize,
        mesUniMaxNoOfEvcs,
        mesUniCurrentNoOfEvcs,
        mesUniAvailableCapacity,
        mesUniServiceMultiplexing,
        mesUniBundling,
        mesUniAllToOneBundling,
        mesUniUntaggedCeVlanIdAssignment,
        mesUniAssociateBwp,
        mesUniReleaseBwp,
        mesUniIngressBwProfilePerUni,
        mesUniIngressBwp,
        mesUniEgressBwProfilePerUni,
        mesUniEgressBwp,
        mesUniSetupCommand,
        mesUniCreateEvcCommand,
        mesUniListCeVlanIdsCommand,
        mesUniTaggingOfUntaggedFrames,
        mesUniCeVlanIdAssignmentCommand,
        mesUniL2SpanningTreeProcessing,
        mesUniL2PauseProcessing,
        mesUniL2SlowProtocolsProcessing,
        mesUniL2PortAuthenticationProcessing,
        mesUniL2OtherBridgeBlockProcessing,
        mesUniL2AllLANsBridgeMgmtProcessing,
        mesUniL2GarpProcessing,
        mesUniL2OamUniMeProcessing,
        mesUniTagTransparency,
        mesUniMgmtVlan,
        mesUniDefineMgmtVlan,
        mesUniMgmtVlanTagType,
        mesUniMgmtVlanEtherType,
        mesUniMgmtVlanVlanId,
        mesUniMgmtVlanPriority,
        mesUniMgmtVlanMacAddress,
        mesUniMacInMac,
        mesUniMacInMacIsid,
        mesUniMacInMacDa,
        mesUniDefineMac }
    STATUS      deprecated
    DESCRIPTION
        "The UNI objects V3 (11.0)."
    ::= { lumMesGroups 15 }

mesEvcGroupV3 OBJECT-GROUP
    OBJECTS {
        mesEvcIndex,
        mesEvcName,
        mesEvcDescr,
        mesEvcObjectProperty,
        mesEvcAdminStatus,
        mesEvcOperStatus,
        mesEvcIdentifier,
        mesEvcUniIdentifier,
        mesEvcNniIdentifier,
        mesEvcType,
        mesEvcMtuSize,
        mesEvcFrameDeliveryUnicast,
        mesEvcFrameDeliveryMulticast,
        mesEvcFrameDeliveryBroadcast,
        mesEvcDefineL2Control,
        mesEvcL2ControlProtocolDisposition,
        mesEvcL2DestinationMacAddress,
        mesEvcCeVlanIdPreservation,
        mesEvcCosPreservation,
        mesEvcAssociateBwp,
        mesEvcReleaseBwp,
        mesEvcIngressBwProfilePerEvc,
        mesEvcIngressBwp,
        mesEvcEgressBwProfilePerEvc,
        mesEvcEgressBwp,
        mesEvcCreateCeVlanIdMap,
        mesEvcDefineProviderTag,
        mesEvcProviderTagType,
        mesEvcProviderTagEtherType,
        mesEvcProviderTagVlanId,
        mesEvcDefineClassOfService,
        mesEvcCoSPriority,
        mesEvcInternalReference,
        mesEvcRowStatus,
        mesEvcQProfile,
        mesEvcCeVlanIdMap,
        mesEvcDefaultCeVlanPriority,
        mesEvcClientEgressTagVlanIdAssignment,
        mesEvcClientEgressTagVlanId,
        mesEvcTagPriorityAssignment,
        mesEvcClientEgressTagTypeAssignment,
        mesEvcClientEgressTagType,
        mesEvcClientEgressTagEtherType,
        mesEvcMacInMac,
        mesEvcMacInMacLtoC,
        mesEvcCopyIsid,
        mesEvcMacInMacIsid,
        mesEvcMacInMacIsidLtoC,
        mesEvcMacInMacDa,
        mesEvcMacInMacDaLtoC,
        mesEvcDefineMac,
        mesEvcIngressBwProfileModel,
        mesEvcIngressBwProfileMap }
    STATUS      current
    DESCRIPTION
        "The EVC objects v3 (11.0)."
    ::= { lumMesGroups 16 }

mesNniGroupV2 OBJECT-GROUP
    OBJECTS {
        mesNniIndex,
        mesNniName,
        mesNniDescr,
        mesNniSubrack,
        mesNniSlot,
        mesNniTxPort,
        mesNniRxPort,
        mesNniObjectProperty,
        mesNniAdminStatus,
        mesNniOperStatus,
        mesNniIdentifier,
        mesNniCurrentNoOfEvcs,
        mesNniAvailableCapacity,
        mesNniDefineMgmtVlan,
        mesNniMgmtVlanTagType,
        mesNniMgmtVlanEtherType,
        mesNniMgmtVlanVlanId,
        mesNniMgmtVlanPriority,
        mesNniMgmtVlanIpAddress,
        mesNniMgmtVlanNetMask,
        mesNniMgmtVlanMacAddress,
        mesNniSetupCommand,
        mesNniMgmtVlan,
        mesNniMacInMac,
        mesNniMacInMacIsid,
        mesNniMacInMacDa,
        mesNniDefineMac }
    STATUS      deprecated
    DESCRIPTION
        "The NNI objects V2. (11.0)"
    ::= { lumMesGroups 17 }

mesMiscGroup OBJECT-GROUP
    OBJECTS {
        mesMiscIndex,
        mesMiscName,
        mesMiscObjectProperty,
        mesMiscAdminStatus,
        mesMiscOperStatus,
        mesMiscMgmtVlanIpAddress,
        mesMiscMgmtVlanNetMask,
        mesMiscMgmtVlanMacAddress0,
        mesMiscMgmtVlanMacAddress1,
        mesMiscMgmtVlanMacAddress2 }
    STATUS      deprecated
    DESCRIPTION
        "The misc group objects."
    ::= { lumMesGroups 18 }

mesEvcBwpMapGroup OBJECT-GROUP
    OBJECTS {
        mesEvcBwpMapIndex,
        mesEvcBwpMapName,
        mesEvcBwpMapObjectProperty,
        mesEvcBwpMapEvcId,
        mesEvcBwpMapModel,
        mesEvcBwpMapPriority,
        mesEvcBwpMapBwpId,
        mesEvcBwpMapInternalReference,
        mesEvcBwpMapRowStatus }
    STATUS      current
    DESCRIPTION
        "The EVC BWP map objects (11.0)."
    ::= { lumMesGroups 19 }

mesGeneralGroupV3 OBJECT-GROUP
    OBJECTS {
        mesGeneralConfigLastChangeTime,
        mesGeneralStateLastChangeTime,
        mesGeneralUniTableSize,
        mesGeneralNniTableSize,
        mesGeneralEvcTableSize,
        mesGeneralBwpTableSize,
        mesGeneralCeEvcMapTableSize,
        mesGeneralMepTableSize,
        mesGeneralMegTableSize,
        mesGeneralEvcBwpMapTableSize,
        mesGeneralPortTableSize,
        mesGeneralVlanMapTableSize }
    STATUS      deprecated
    DESCRIPTION
        "The general objects."
    ::= { lumMesGroups 20 }

mesPortGroup OBJECT-GROUP
    OBJECTS {
        mesPortIndex,
        mesPortName,
        mesPortDescr,
        mesPortSubrack,
        mesPortSlot,
        mesPortTxPort,
        mesPortRxPort,
        mesPortAdminStatus,
        mesPortOperStatus,
        mesPortMtuSize,
        mesPortTagType,
        mesPortNoOfVlans,
        mesPortVlanAware,
        mesPortVlanTagged,
        mesPortVlanUntagged,
        mesPortIngressFiltering,
        mesPortEgressTag,
        mesPortDefaultCeVlanId,
        mesPortAssociateVlan,
        mesPortReleaseVlan,
        mesPortActingAsLine,
        mesPortTrustedPortmask,
        mesPortMacAddress,
        mesPortLagStatus,
        mesPortLagPortmask,
        mesPortAssociateLag,
        mesPortTxEthUtilization,
        mesPortRxEthUtilization,
        mesPortFlowControlMode,
        mesPortAutoNegotiationMode,
        mesPortAutoNegotiationStatus,
        mesPortLinkDown,
        mesPortLinkFaultRemote,
        mesPortLinkFaultLocal }
    STATUS      deprecated
    DESCRIPTION
        "The port objects (12.0)."
    ::= { lumMesGroups 21 }

mesVlanMapGroup OBJECT-GROUP
    OBJECTS {
        mesVlanMapIndex,
        mesVlanMapName,
        mesVlanMapVlanIdRangeLower,
        mesVlanMapVlanIdRangeUpper,
        mesVlanMapInternalReference,
        mesVlanMapPortmask }
    STATUS      deprecated
    DESCRIPTION
        "The VLAN map objects (12.0)."
    ::= { lumMesGroups 22 }

mesMgmtVlanGroup OBJECT-GROUP
    OBJECTS {
        mesMgmtVlanIndex,
        mesMgmtVlanName,
        mesMgmtVlanDescr,
        mesMgmtVlanSubrack,
        mesMgmtVlanSlot,
        mesMgmtVlanTxPort,
        mesMgmtVlanRxPort,
        mesMgmtVlanObjectProperty,
        mesMgmtVlanAdminStatus,
        mesMgmtVlanConfigure,
        mesMgmtVlanTagType,
        mesMgmtVlanEtherType,
        mesMgmtVlanVlanId,
        mesMgmtVlanPriority,
        mesMgmtVlanMacInMac,
        mesMgmtVlanMacInMacIsid,
        mesMgmtVlanMacInMacDa }
    STATUS      deprecated
    DESCRIPTION
        "The Mgmt VLAN objects (12.0)."
    ::= { lumMesGroups 23 }

mesMiscGroupV2 OBJECT-GROUP
    OBJECTS {
        mesMiscIndex,
        mesMiscName,
        mesMiscObjectProperty,
        mesMiscAdminStatus,
        mesMiscOperStatus,
        mesMiscMgmtVlanIpAddress,
        mesMiscMgmtVlanNetMask,
        mesMiscMgmtVlanMacAddress0,
        mesMiscMgmtVlanMacAddress1,
        mesMiscMgmtVlanMacAddress2,
        mesMiscConfigureAddress }
    STATUS      deprecated
    DESCRIPTION
        "The misc group objects."
    ::= { lumMesGroups 24 }

mesLagGroup OBJECT-GROUP
    OBJECTS {
        mesLagIndex,
        mesLagName,
        mesLagInternalReference,
        mesLagPortmask,
        mesLagMasterIndex,
        mesLagConfigure }
    STATUS      deprecated
    DESCRIPTION
        "The LAG group objects (12.0)."
    ::= { lumMesGroups 25 }

mesNniGroupV3 OBJECT-GROUP
    OBJECTS {
        mesNniIndex,
        mesNniName,
        mesNniDescr,
        mesNniSubrack,
        mesNniSlot,
        mesNniTxPort,
        mesNniRxPort,
        mesNniObjectProperty,
        mesNniAdminStatus,
        mesNniOperStatus,
        mesNniIdentifier,
        mesNniCurrentNoOfEvcs,
        mesNniAvailableCapacity,
        mesNniDefineMgmtVlan,
        mesNniMgmtVlanTagType,
        mesNniMgmtVlanEtherType,
        mesNniMgmtVlanVlanId,
        mesNniMgmtVlanPriority,
        mesNniMgmtVlanIpAddress,
        mesNniMgmtVlanNetMask,
        mesNniMgmtVlanMacAddress,
        mesNniSetupCommand,
        mesNniMgmtVlan,
        mesNniMacInMac,
        mesNniMacInMacIsid,
        mesNniMacInMacDa,
        mesNniDefineMac,
        mesNniLagStatus }
    STATUS      current
    DESCRIPTION
        "The NNI objects V3. (13.0)"
    ::= { lumMesGroups 26 }

mesPortGroupV2 OBJECT-GROUP
    OBJECTS {
        mesPortIndex,
        mesPortName,
        mesPortDescr,
        mesPortSubrack,
        mesPortSlot,
        mesPortTxPort,
        mesPortRxPort,
        mesPortAdminStatus,
        mesPortOperStatus,
        mesPortMtuSize,
        mesPortTagType,
        mesPortNoOfVlans,
        mesPortVlanAware,
        mesPortVlanTagged,
        mesPortVlanUntagged,
        mesPortIngressFiltering,
        mesPortEgressTag,
        mesPortDefaultCeVlanId,
        mesPortAssociateVlan,
        mesPortReleaseVlan,
        mesPortActingAsLine,
        mesPortTrustedPortmask,
        mesPortMacAddress,
        mesPortLagStatus,
        mesPortLagPortmask,
        mesPortAssociateLag,
        mesPortTxEthUtilization,
        mesPortRxEthUtilization,
        mesPortFlowControlMode,
        mesPortAutoNegotiationMode,
        mesPortAutoNegotiationStatus,
        mesPortLinkDown,
        mesPortLinkFaultRemote,
        mesPortLinkFaultLocal,
        mesPortNoOfShapers,
        mesPortNoOfPolicers,
        mesPortAssociateShaper,
        mesPortReleaseShaper,
        mesPortAssociatePolicer,
        mesPortReleasePolicer,
        mesPortRestartAutoNegotiation,
        mesPortConfigureLine }
    STATUS      deprecated
    DESCRIPTION
        "The port objects (13.0)."
    ::= { lumMesGroups 27 }

mesPolicingGroup OBJECT-GROUP
    OBJECTS {
        mesPolicingIndex,
        mesPolicingName,
        mesPolicingRate,
        mesPolicingBurstSize,
        mesPolicingType,
        mesPolicingInternalReference,
        mesPolicingIdentifier }
    STATUS      deprecated
    DESCRIPTION
        "The policing objects (13.0)."
    ::= { lumMesGroups 28 }

mesShapingGroup OBJECT-GROUP
    OBJECTS {
        mesShapingIndex,
        mesShapingName,
        mesShapingRate,
        mesShapingBurstSize,
        mesShapingQueue,
        mesShapingInternalReference,
        mesShapingExcess,
        mesShapingIdentifier }
    STATUS      deprecated
    DESCRIPTION
        "The shaping objects (13.0)."
    ::= { lumMesGroups 29 }

mesCosGroup OBJECT-GROUP
    OBJECTS {
        mesCosIndex,
        mesCosName,
        mesCosTxPort,
        mesCosMap,
        mesCosPriority0,
        mesCosPriority1,
        mesCosPriority2,
        mesCosPriority3,
        mesCosPriority4,
        mesCosPriority5,
        mesCosPriority6,
        mesCosPriority7 }
    STATUS      current
    DESCRIPTION
        "The COS objects (13.0)."
    ::= { lumMesGroups 30 }

mesBwpMapGroup OBJECT-GROUP
    OBJECTS {
        mesBwpMapIndex,
        mesBwpMapName,
        mesBwpMapPortName,
        mesBwpMapBwpName,
        mesBwpMapInternalReference }
    STATUS      deprecated
    DESCRIPTION
        "The BWP map objects (13.0)."
    ::= { lumMesGroups 31 }

mesUniGroupV4 OBJECT-GROUP
    OBJECTS {
        mesUniIndex,
        mesUniName,
        mesUniDescr,
        mesUniSubrack,
        mesUniSlot,
        mesUniTxPort,
        mesUniRxPort,
        mesUniObjectProperty,
        mesUniAdminStatus,
        mesUniOperStatus,
        mesUniIdentifier,
        mesUniMtuSize,
        mesUniMaxNoOfEvcs,
        mesUniCurrentNoOfEvcs,
        mesUniAvailableCapacity,
        mesUniServiceMultiplexing,
        mesUniBundling,
        mesUniAllToOneBundling,
        mesUniUntaggedCeVlanIdAssignment,
        mesUniAssociateBwp,
        mesUniReleaseBwp,
        mesUniIngressBwProfilePerUni,
        mesUniIngressBwp,
        mesUniEgressBwProfilePerUni,
        mesUniEgressBwp,
        mesUniSetupCommand,
        mesUniCreateEvcCommand,
        mesUniListCeVlanIdsCommand,
        mesUniTaggingOfUntaggedFrames,
        mesUniCeVlanIdAssignmentCommand,
        mesUniL2SpanningTreeProcessing,
        mesUniL2PauseProcessing,
        mesUniL2SlowProtocolsProcessing,
        mesUniL2PortAuthenticationProcessing,
        mesUniL2OtherBridgeBlockProcessing,
        mesUniL2AllLANsBridgeMgmtProcessing,
        mesUniL2GarpProcessing,
        mesUniL2OamUniMeProcessing,
        mesUniTagTransparency,
        mesUniMgmtVlan,
        mesUniDefineMgmtVlan,
        mesUniMgmtVlanTagType,
        mesUniMgmtVlanEtherType,
        mesUniMgmtVlanVlanId,
        mesUniMgmtVlanPriority,
        mesUniMgmtVlanMacAddress,
        mesUniMacInMac,
        mesUniMacInMacIsid,
        mesUniMacInMacDa,
        mesUniDefineMac,
        mesUniLagStatus,
        mesUniLagPortmask,
        mesUniAssociateLag }
    STATUS      current
    DESCRIPTION
        "The UNI objects V3 (13.0)."
    ::= { lumMesGroups 32 }

mesGeneralGroupV4 OBJECT-GROUP
    OBJECTS {
        mesGeneralConfigLastChangeTime,
        mesGeneralStateLastChangeTime,
        mesGeneralUniTableSize,
        mesGeneralNniTableSize,
        mesGeneralEvcTableSize,
        mesGeneralBwpTableSize,
        mesGeneralCeEvcMapTableSize,
        mesGeneralMepTableSize,
        mesGeneralMegTableSize,
        mesGeneralEvcBwpMapTableSize,
        mesGeneralPortTableSize,
        mesGeneralVlanMapTableSize,
        mesGeneralMgmtVlanTableSize,
        mesGeneralLagTableSize,
        mesGeneralPolicingTableSize,
        mesGeneralShapingTableSize,
        mesGeneralBwpMapTableSize,
        mesGeneralCosTableSize }
    STATUS      deprecated
    DESCRIPTION
        "The general objects."
    ::= { lumMesGroups 33 }

mesPortGroupV3 OBJECT-GROUP
    OBJECTS {
        mesPortIndex,
        mesPortName,
        mesPortDescr,
        mesPortSubrack,
        mesPortSlot,
        mesPortTxPort,
        mesPortRxPort,
        mesPortAdminStatus,
        mesPortOperStatus,
        mesPortMtuSize,
        mesPortTagType,
        mesPortNoOfVlans,
        mesPortVlanAware,
        mesPortVlanTagged,
        mesPortVlanUntagged,
        mesPortIngressFiltering,
        mesPortEgressTag,
        mesPortDefaultCeVlanId,
        mesPortAssociateVlan,
        mesPortReleaseVlan,
        mesPortActingAsLine,
        mesPortTrustedPortmask,
        mesPortMacAddress,
        mesPortLagStatus,
        mesPortLagPortmask,
        mesPortAssociateLag,
        mesPortTxEthUtilization,
        mesPortRxEthUtilization,
        mesPortFlowControlMode,
        mesPortAutoNegotiationMode,
        mesPortAutoNegotiationStatus,
        mesPortLinkDown,
        mesPortLinkFaultRemote,
        mesPortLinkFaultLocal,
        mesPortNoOfShapers,
        mesPortNoOfPolicers,
        mesPortAssociateShaper,
        mesPortReleaseShaper,
        mesPortAssociatePolicer,
        mesPortReleasePolicer,
        mesPortRestartAutoNegotiation,
        mesPortConfigureLine,
        mesPortEtherType,
        mesPortConfigureEtherType,
        mesPortNoOfMirrorSources,
        mesPortMirroring,
        mesPortIngressPushTag,
        mesPortEgressPopTag,
        mesPortDefaultCeVlanPriority,
        mesPortConfigureTagRule }
    STATUS      deprecated
    DESCRIPTION
        "The port objects (14.0)."
    ::= { lumMesGroups 34 }

mesMirroringGroup OBJECT-GROUP
    OBJECTS {
        mesMirroringIndex,
        mesMirroringName,
        mesMirroringDestination,
        mesMirroringDirection,
        mesMirroringConfigureDestination }
    STATUS      deprecated
    DESCRIPTION
        "The mirroring objects (14.0)."
    ::= { lumMesGroups 36 }

mesMiscGroupV3 OBJECT-GROUP
    OBJECTS {
        mesMiscIndex,
        mesMiscName,
        mesMiscObjectProperty,
        mesMiscAdminStatus,
        mesMiscOperStatus,
        mesMiscMgmtVlanIpAddress,
        mesMiscMgmtVlanNetMask,
        mesMiscMgmtVlanMacAddress0,
        mesMiscMgmtVlanMacAddress1,
        mesMiscMgmtVlanMacAddress2,
        mesMiscConfigureAddress,
        mesMiscMgmtVlanNode,
        mesMiscMacAgeing,
        mesMiscMacGetTable }
    STATUS      deprecated
    DESCRIPTION
        "The misc group objects (14.0)."
    ::= { lumMesGroups 37 }

mesVlanTagRuleGroup OBJECT-GROUP
    OBJECTS {
        mesVlanTagRuleIndex,
        mesVlanTagRuleName,
        mesVlanTagRuleInternalReference,
        mesVlanTagRuleClassificationName,
        mesVlanTagRuleType,
        mesVlanTagRuleOperation,
        mesVlanTagRuleInnerPrio,
        mesVlanTagRuleInnerVlanId,
        mesVlanTagRuleOuterPrio,
        mesVlanTagRuleOuterVlanId }
    STATUS      deprecated
    DESCRIPTION
        "The vlan tag rule objects (14.0)."
    ::= { lumMesGroups 38 }

mesVlanTagClassVlanGroup OBJECT-GROUP
    OBJECTS {
        mesVlanTagClassVlanIndex,
        mesVlanTagClassVlanName,
        mesVlanTagClassVlanInternalReference,
        mesVlanTagClassVlanTxPort,
        mesVlanTagClassVlanOuterVlanId }
    STATUS      deprecated
    DESCRIPTION
        "The vlan tag classification vlan objects (14.0)."
    ::= { lumMesGroups 39 }

mesVlanMapGroupV2 OBJECT-GROUP
    OBJECTS {
        mesVlanMapIndex,
        mesVlanMapName,
        mesVlanMapVlanIdRangeLower,
        mesVlanMapVlanIdRangeUpper,
        mesVlanMapInternalReference,
        mesVlanMapPortmask,
        mesVlanMapConfigurePortMask,
        mesVlanMapLearning }
    STATUS      deprecated
    DESCRIPTION
        "The VLAN map objects (14.0)."
    ::= { lumMesGroups 40 }

mesCosProfileGroup OBJECT-GROUP
    OBJECTS {
        mesCosProfileIndex,
        mesCosProfileName,
        mesCosProfilePortmask,
        mesCosProfileScheduler,
        mesCosProfileWeight0,
        mesCosProfileWeight1,
        mesCosProfileWeight2,
        mesCosProfileWeight3,
        mesCosProfileWeight4,
        mesCosProfileWeight5,
        mesCosProfileWeight6,
        mesCosProfileWeight7,
        mesCosProfilePriority0,
        mesCosProfilePriority1,
        mesCosProfilePriority2,
        mesCosProfilePriority3,
        mesCosProfilePriority4,
        mesCosProfilePriority5,
        mesCosProfilePriority6,
        mesCosProfilePriority7,
        mesCosProfileConfigureScheduler }
    STATUS      deprecated
    DESCRIPTION
        "The COS Profile objects (14.0)."
    ::= { lumMesGroups 41 }

mesLagGroupV2 OBJECT-GROUP
    OBJECTS {
        mesLagIndex,
        mesLagName,
        mesLagInternalReference,
        mesLagPortmask,
        mesLagMasterIndex,
        mesLagConfigure,
        mesLagHash }
    STATUS      deprecated
    DESCRIPTION
        "The LAG group objects (15.0)."
    ::= { lumMesGroups 42 }

mesPortGroupV4 OBJECT-GROUP
    OBJECTS {
        mesPortIndex,
        mesPortName,
        mesPortDescr,
        mesPortSubrack,
        mesPortSlot,
        mesPortTxPort,
        mesPortRxPort,
        mesPortAdminStatus,
        mesPortOperStatus,
        mesPortMtuSize,
        mesPortTagType,
        mesPortNoOfVlans,
        mesPortVlanAware,
        mesPortVlanTagged,
        mesPortVlanUntagged,
        mesPortIngressFiltering,
        mesPortEgressTag,
        mesPortDefaultCeVlanId,
        mesPortAssociateVlan,
        mesPortReleaseVlan,
        mesPortActingAsLine,
        mesPortTrustedPortmask,
        mesPortMacAddress,
        mesPortLagStatus,
        mesPortLagPortmask,
        mesPortAssociateLag,
        mesPortTxEthUtilization,
        mesPortRxEthUtilization,
        mesPortFlowControlMode,
        mesPortAutoNegotiationMode,
        mesPortAutoNegotiationStatus,
        mesPortLinkDown,
        mesPortLinkFaultRemote,
        mesPortLinkFaultLocal,
        mesPortNoOfShapers,
        mesPortNoOfPolicers,
        mesPortAssociateShaper,
        mesPortReleaseShaper,
        mesPortAssociatePolicer,
        mesPortReleasePolicer,
        mesPortRestartAutoNegotiation,
        mesPortConfigureLine,
        mesPortEtherType,
        mesPortConfigureEtherType,
        mesPortNoOfMirrorSources,
        mesPortMirroring,
        mesPortIngressPushTag,
        mesPortEgressPopTag,
        mesPortDefaultCeVlanPriority,
        mesPortConfigureTagRule,
        mesPortMode,
        mesPortPrioAssignment,
        mesPortConfigurePrioAssignment,
        mesPortNoOfTagRules,
        mesPortNoOfVlanSchedPrios }
    STATUS      deprecated
    DESCRIPTION
        "The port objects (15.0)."
    ::= { lumMesGroups 43 }

mesMiscGroupV4 OBJECT-GROUP
    OBJECTS {
        mesMiscIndex,
        mesMiscName,
        mesMiscObjectProperty,
        mesMiscAdminStatus,
        mesMiscOperStatus,
        mesMiscMgmtVlanIpAddress,
        mesMiscMgmtVlanNetMask,
        mesMiscMgmtVlanMacAddress0,
        mesMiscMgmtVlanMacAddress1,
        mesMiscMgmtVlanMacAddress2,
        mesMiscConfigureAddress,
        mesMiscMgmtVlanNode,
        mesMiscMacAgeing,
        mesMiscMacGetTable,
        mesMiscNoOfMegs,
        mesMiscAssociateMeg,
        mesMiscNoOfErps,
        mesMiscAssociateErp,
        mesMiscL2Mode,
        mesMiscConfigureMode,
        mesMiscIdentity }
    STATUS      deprecated
    DESCRIPTION
        "The misc group objects (15.0)."
    ::= { lumMesGroups 44 }

mesMaidGroup OBJECT-GROUP
    OBJECTS {
        mesMaidIndex,
        mesMaidName,
        mesMaidGroupId,
        mesMaidMdFormat,
        mesMaidMdName,
        mesMaidMdMac,
        mesMaidMd2Octet,
        mesMaidMdString,
        mesMaidLevel,
        mesMaidMaFormat,
        mesMaidMaName,
        mesMaidMaVpnOui,
        mesMaidMaVpnIndex,
        mesMaidMa2Octet,
        mesMaidMaVlan,
        mesMaidMaString,
        mesMaidCcmInterval,
        mesMaidInternalReference,
        mesMaidIdentifier,
        mesMaidNoOfMeps,
        mesMaidAssociateMep,
        mesMaidReleaseMeps }
    STATUS      deprecated
    DESCRIPTION
        "The Maintainance Domain objects (15.0)."
    ::= { lumMesGroups 45 }

mesCfmMepGroup OBJECT-GROUP
    OBJECTS {
        mesCfmMepIndex,
        mesCfmMepName,
        mesCfmMepMaid,
        mesCfmMepTxPort,
        mesCfmMepPortName,
        mesCfmMepPrimaryVid,
        mesCfmMepAdminStatus,
        mesCfmMepOperStatus,
        mesCfmMepVlanPriority,
        mesCfmMepType,
        mesCfmMepIdentifier,
        mesCfmMepInternalReference,
        mesCfmMepRDICCM,
        mesCfmMepMACstatus,
        mesCfmMepRemoteCCM,
        mesCfmMepErrorCCM,
        mesCfmMepXconCCM,
        mesCfmMepAis,
        mesCfmMepChangePort }
    STATUS      deprecated
    DESCRIPTION
        "The MEP objects (15.0)."
    ::= { lumMesGroups 46 }

mesErpGroup OBJECT-GROUP
    OBJECTS {
        mesErpIndex,
        mesErpName,
        mesErpPortLeft,
        mesErpPortRight,
        mesErpAdminStatus,
        mesErpInternalReference,
        mesErpDescr,
        mesErpVlanId,
        mesErpMegLevel,
        mesErpProtLink,
        mesErpGuardTime,
        mesErpHoldOffTime,
        mesErpWtrTime,
        mesErpOamDetectionLeft,
        mesErpOamDetectionRight,
        mesErpStatusLeft,
        mesErpStatusRight,
        mesErpProtState,
        mesErpActiveEvent,
        mesErpRapsReqState,
        mesErpServiceFailure,
        mesErpServiceDegraded,
        mesErpUnexpectedMegLevel,
        mesErpCommunicationFailure,
        mesErpChangePort }
    STATUS      deprecated
    DESCRIPTION
        "The ERP objects (15.0)."
    ::= { lumMesGroups 47 }

mesVlanMapGroupV3 OBJECT-GROUP
    OBJECTS {
        mesVlanMapIndex,
        mesVlanMapName,
        mesVlanMapVlanIdRangeLower,
        mesVlanMapVlanIdRangeUpper,
        mesVlanMapInternalReference,
        mesVlanMapPortmask,
        mesVlanMapConfigurePortMask,
        mesVlanMapLearning,
        mesVlanMapEtherType }
    STATUS      deprecated
    DESCRIPTION
        "The VLAN map objects (15.0)."
    ::= { lumMesGroups 48 }

mesVlanTagRuleGroupV2 OBJECT-GROUP
    OBJECTS {
        mesVlanTagRuleIndex,
        mesVlanTagRuleName,
        mesVlanTagRuleInternalReference,
        mesVlanTagRuleClassificationName,
        mesVlanTagRuleType,
        mesVlanTagRuleOperation,
        mesVlanTagRuleInnerVlanId,
        mesVlanTagRuleInnerPrio,
        mesVlanTagRuleOuterVlanId,
        mesVlanTagRuleOuterPrio,
        mesVlanTagRulePrioAssignment,
        mesVlanTagRuleConfigurePrioAssignment,
        mesVlanTagRuleQueue }
    STATUS      deprecated
    DESCRIPTION
        "The vlan tag rule objects (15.0)."
    ::= { lumMesGroups 49 }

mesVlanTagClassVlanGroupV2 OBJECT-GROUP
    OBJECTS {
        mesVlanTagClassVlanIndex,
        mesVlanTagClassVlanName,
        mesVlanTagClassVlanTxPort,
        mesVlanTagClassVlanInternalReference,
        mesVlanTagClassVlanRuleName,
        mesVlanTagClassVlanRuleIndex,
        mesVlanTagClassVlanOuterVlanId }
    STATUS      deprecated
    DESCRIPTION
        "The vlan tag classification vlan objects (15.0)."
    ::= { lumMesGroups 50 }

mesMirroringGroupV2 OBJECT-GROUP
    OBJECTS {
        mesMirroringIndex,
        mesMirroringName,
        mesMirroringDestination,
        mesMirroringDirection,
        mesMirroringConfigureDestination }
    STATUS      deprecated
    DESCRIPTION
        "The mirroring objects (15.0)."
    ::= { lumMesGroups 51 }

mesShapingGroupV2 OBJECT-GROUP
    OBJECTS {
        mesShapingIndex,
        mesShapingName,
        mesShapingRate,
        mesShapingBurstSize,
        mesShapingQueue,
        mesShapingInternalReference,
        mesShapingExcess,
        mesShapingIdentifier,
        mesShapingMinRate }
    STATUS      deprecated
    DESCRIPTION
        "The shaping objects (15.0)."
    ::= { lumMesGroups 52 }

mesPortGroupV5 OBJECT-GROUP
    OBJECTS {
        mesPortIndex,
        mesPortName,
        mesPortDescr,
        mesPortSubrack,
        mesPortSlot,
        mesPortTxPort,
        mesPortRxPort,
        mesPortAdminStatus,
        mesPortOperStatus,
        mesPortMtuSize,
        mesPortTagType,
        mesPortNoOfVlans,
        mesPortVlanAware,
        mesPortVlanTagged,
        mesPortVlanUntagged,
        mesPortIngressFiltering,
        mesPortEgressTag,
        mesPortDefaultCeVlanId,
        mesPortAssociateVlan,
        mesPortReleaseVlan,
        mesPortActingAsLine,
        mesPortTrustedPortmask,
        mesPortMacAddress,
        mesPortLagStatus,
        mesPortLagPortmask,
        mesPortAssociateLag,
        mesPortTxEthUtilization,
        mesPortRxEthUtilization,
        mesPortFlowControlMode,
        mesPortAutoNegotiationMode,
        mesPortAutoNegotiationStatus,
        mesPortLinkDown,
        mesPortLinkFaultRemote,
        mesPortLinkFaultLocal,
        mesPortNoOfShapers,
        mesPortNoOfPolicers,
        mesPortAssociateShaper,
        mesPortReleaseShaper,
        mesPortAssociatePolicer,
        mesPortReleasePolicer,
        mesPortRestartAutoNegotiation,
        mesPortConfigureLine,
        mesPortEtherType,
        mesPortConfigureEtherType,
        mesPortNoOfMirrorSources,
        mesPortMirroring,
        mesPortIngressPushTag,
        mesPortEgressPopTag,
        mesPortDefaultCeVlanPriority,
        mesPortConfigureTagRule,
        mesPortMode,
        mesPortPrioAssignment,
        mesPortConfigurePrioAssignment,
        mesPortNoOfTagRules,
        mesPortNoOfVlanSchedPrios}
    STATUS      deprecated
    DESCRIPTION
        "The port objects (16.0)."
    ::= { lumMesGroups 53 }

mesBwpMapGroupV2 OBJECT-GROUP
    OBJECTS {
        mesBwpMapIndex,
        mesBwpMapName,
        mesBwpMapPortName,
        mesBwpMapBwpName,
        mesBwpMapInternalReference }
    STATUS      current
    DESCRIPTION
        "The BWP map objects (16.0)."
    ::= { lumMesGroups 54 }

mesClassGroup OBJECT-GROUP
    OBJECTS {
        mesClassIndex,
        mesClassName,
        mesClassIdentifier,
        mesClassPort,
        mesClassLagId,
        mesClassInternalReference,
        mesClassOuterVlanId,
        mesClassOuterVlanPcp,
        mesClassPrecedence,
        mesClassDaMacAddress,
        mesClassAssociateAction,
        mesClassRowStatus}
    STATUS      deprecated
    DESCRIPTION
        "The classification objects (16.0)."
    ::= { lumMesGroups 55 }

mesMiscGroupV5 OBJECT-GROUP
    OBJECTS {
        mesMiscIndex,
        mesMiscName,
        mesMiscObjectProperty,
        mesMiscAdminStatus,
        mesMiscOperStatus,
        mesMiscMgmtVlanIpAddress,
        mesMiscMgmtVlanNetMask,
        mesMiscMgmtVlanMacAddress0,
        mesMiscMgmtVlanMacAddress1,
        mesMiscMgmtVlanMacAddress2,
        mesMiscConfigureAddress,
        mesMiscMgmtVlanNode,
        mesMiscMacAgeing,
        mesMiscMacGetTable,
        mesMiscNoOfMegs,
        mesMiscAssociateMeg,
        mesMiscNoOfErps,
        mesMiscAssociateErp,
        mesMiscL2Mode,
        mesMiscConfigureMode,
        mesMiscIdentity,
        mesMiscAssociateClass,
        mesMiscAssociateBwp,
        mesMiscWred }
    STATUS      deprecated
    DESCRIPTION
        "The misc group objects (16.0)."
    ::= { lumMesGroups 56 }

mesActionGroup OBJECT-GROUP
    OBJECTS {
        mesActionIndex,
        mesActionName,
        mesActionIdentifier,
        mesActionInternalReference,
        mesActionType,
        mesActionOuterVlanId,
        mesActionPcp,
        mesActionPolicerId,
        mesActionInnerVlanId,
        mesActionQueue,
        mesActionRowStatus }
    STATUS      deprecated
    DESCRIPTION
        "The action objects (16.0)."
    ::= { lumMesGroups 57 }

mesPolicyGroup OBJECT-GROUP
    OBJECTS {
        mesPolicyIndex,
        mesPolicyName,
        mesPolicyInternalReference,
        mesPolicyClass,
        mesPolicyAction }
    STATUS      deprecated
    DESCRIPTION
        "The policy objects (16.0)."
    ::= { lumMesGroups 58 }


mesCosProfileGroupV2 OBJECT-GROUP
    OBJECTS {
        mesCosProfileIndex,
        mesCosProfileName,
        mesCosProfilePortmask,
        mesCosProfileScheduler,
        mesCosProfileWeight0,
        mesCosProfileWeight1,
        mesCosProfileWeight2,
        mesCosProfileWeight3,
        mesCosProfileWeight4,
        mesCosProfileWeight5,
        mesCosProfileWeight6,
        mesCosProfileWeight7,
        mesCosProfilePriority0,
        mesCosProfilePriority1,
        mesCosProfilePriority2,
        mesCosProfilePriority3,
        mesCosProfilePriority4,
        mesCosProfilePriority5,
        mesCosProfilePriority6,
        mesCosProfilePriority7,
        mesCosProfileConfigureScheduler,
        mesCosProfileIngressPcpDecoding,
        mesCosProfileIngressDeiDecoding,
        mesCosProfileIngressColor0,
        mesCosProfileIngressColor1,
        mesCosProfileIngressColor2,
        mesCosProfileIngressColor3,
        mesCosProfileIngressColor4,
        mesCosProfileIngressColor5,
        mesCosProfileIngressColor6,
        mesCosProfileIngressColor7,
        mesCosProfileEgressPcpEncoding,
        mesCosProfileEgressDeiEncoding,
        mesCosProfileEgressPcpGreen0,
        mesCosProfileEgressPcpGreen1,
        mesCosProfileEgressPcpGreen2,
        mesCosProfileEgressPcpGreen3,
        mesCosProfileEgressPcpGreen4,
        mesCosProfileEgressPcpGreen5,
        mesCosProfileEgressPcpGreen6,
        mesCosProfileEgressPcpGreen7,
        mesCosProfileEgressPcpYellow0,
        mesCosProfileEgressPcpYellow1,
        mesCosProfileEgressPcpYellow2,
        mesCosProfileEgressPcpYellow3,
        mesCosProfileEgressPcpYellow4,
        mesCosProfileEgressPcpYellow5,
        mesCosProfileEgressPcpYellow6,
        mesCosProfileEgressPcpYellow7 }
    STATUS      deprecated
    DESCRIPTION
        "The COS Profile objects (16.0)."
    ::= { lumMesGroups 59 }

mesLagGroupV3 OBJECT-GROUP
    OBJECTS {
        mesLagIndex,
        mesLagName,
        mesLagInternalReference,
        mesLagPortmask,
        mesLagMasterIndex,
        mesLagConfigure,
        mesLagHash,
        mesLagIdentifier,
        mesLagRowStatus}
    STATUS      deprecated
    DESCRIPTION
        "The LAG group objects (16.0)."
    ::= { lumMesGroups 60 }

mesVlanMapGroupV4 OBJECT-GROUP
    OBJECTS {
        mesVlanMapIndex,
        mesVlanMapName,
        mesVlanMapVlanIdRangeLower,
        mesVlanMapVlanIdRangeUpper,
        mesVlanMapInternalReference,
        mesVlanMapPortmask,
        mesVlanMapConfigurePortMask,
        mesVlanMapLearning,
        mesVlanMapEtherType,
        mesVlanMapRowStatus }
    STATUS      deprecated
    DESCRIPTION
        "The VLAN map objects (16.0)."
    ::= { lumMesGroups 61 }

mesCfmMepGroupV2 OBJECT-GROUP
    OBJECTS {
        mesCfmMepIndex,
        mesCfmMepName,
        mesCfmMepMaid,
        mesCfmMepTxPort,
        mesCfmMepPortName,
        mesCfmMepPrimaryVid,
        mesCfmMepAdminStatus,
        mesCfmMepOperStatus,
        mesCfmMepVlanPriority,
        mesCfmMepType,
        mesCfmMepIdentifier,
        mesCfmMepInternalReference,
        mesCfmMepRDICCM,
        mesCfmMepMACstatus,
        mesCfmMepRemoteCCM,
        mesCfmMepErrorCCM,
        mesCfmMepXconCCM,
        mesCfmMepAis,
        mesCfmMepChangePort,
        mesCfmMepTransmitLbrStatus,
        mesCfmMepRowStatus }
    STATUS      deprecated
    DESCRIPTION
        "The MEP objects (16.0)."
    ::= { lumMesGroups 62 }

mesVlanTagRuleGroupV3 OBJECT-GROUP
    OBJECTS {
        mesVlanTagRuleIndex,
        mesVlanTagRuleName,
        mesVlanTagRuleInternalReference,
        mesVlanTagRuleClassificationName,
        mesVlanTagRuleType,
        mesVlanTagRuleOperation,
        mesVlanTagRuleInnerVlanId,
        mesVlanTagRuleInnerPrio,
        mesVlanTagRuleOuterVlanId,
        mesVlanTagRuleOuterPrio,
        mesVlanTagRulePrioAssignment,
        mesVlanTagRuleConfigurePrioAssignment,
        mesVlanTagRuleQueue,
        mesVlanTagRuleRowStatus}
    STATUS      deprecated
    DESCRIPTION
        "The vlan tag rule objects (16.0)."
    ::= { lumMesGroups 63 }

mesErpGroupV2 OBJECT-GROUP
    OBJECTS {
        mesErpIndex,
        mesErpName,
        mesErpPortLeft,
        mesErpPortRight,
        mesErpAdminStatus,
        mesErpInternalReference,
        mesErpDescr,
        mesErpVlanId,
        mesErpMegLevel,
        mesErpProtLink,
        mesErpGuardTime,
        mesErpHoldOffTime,
        mesErpWtrTime,
        mesErpOamDetectionLeft,
        mesErpOamDetectionRight,
        mesErpStatusLeft,
        mesErpStatusRight,
        mesErpProtState,
        mesErpActiveEvent,
        mesErpRapsReqState,
        mesErpServiceFailure,
        mesErpServiceDegraded,
        mesErpUnexpectedMegLevel,
        mesErpCommunicationFailure,
        mesErpChangePort,
        mesErpRowStatus }
    STATUS      deprecated
    DESCRIPTION
        "The ERP objects (16.0)."
    ::= { lumMesGroups 64 }

mesMaidGroupV2 OBJECT-GROUP
    OBJECTS {
        mesMaidIndex,
        mesMaidName,
        mesMaidGroupId,
        mesMaidMdFormat,
        mesMaidMdName,
        mesMaidMdMac,
        mesMaidMd2Octet,
        mesMaidMdString,
        mesMaidLevel,
        mesMaidMaFormat,
        mesMaidMaName,
        mesMaidMaVpnOui,
        mesMaidMaVpnIndex,
        mesMaidMa2Octet,
        mesMaidMaVlan,
        mesMaidMaString,
        mesMaidCcmInterval,
        mesMaidInternalReference,
        mesMaidIdentifier,
        mesMaidNoOfMeps,
        mesMaidAssociateMep,
        mesMaidReleaseMeps,
        mesMaidRowStatus}
    STATUS      deprecated
    DESCRIPTION
        "The Maintainance Domain objects (16.0)."
    ::= { lumMesGroups 65 }

mesMiscGroupV6 OBJECT-GROUP
    OBJECTS {
        mesMiscIndex,
        mesMiscName,
        mesMiscObjectProperty,
        mesMiscAdminStatus,
        mesMiscOperStatus,
        mesMiscMgmtVlanIpAddress,
        mesMiscMgmtVlanNetMask,
        mesMiscMgmtVlanMacAddress0,
        mesMiscMgmtVlanMacAddress1,
        mesMiscMgmtVlanMacAddress2,
        mesMiscConfigureAddress,
        mesMiscMgmtVlanNode,
        mesMiscMacAgeing,
        mesMiscMacGetTable,
        mesMiscNoOfMegs,
        mesMiscAssociateMeg,
        mesMiscNoOfErps,
        mesMiscAssociateErp,
        mesMiscL2Mode,
        mesMiscConfigureMode,
        mesMiscIdentity,
        mesMiscAssociateClass,
        mesMiscAssociateBwp,
        mesMiscWred,
        mesMiscGetPacketMonitor }
    STATUS      deprecated
    DESCRIPTION
        "The misc group objects (17.0)."
    ::= { lumMesGroups 66 }

mesVlanMapGroupV5 OBJECT-GROUP
    OBJECTS {
        mesVlanMapIndex,
        mesVlanMapName,
        mesVlanMapVlanIdRangeLower,
        mesVlanMapVlanIdRangeUpper,
        mesVlanMapInternalReference,
        mesVlanMapPortmask,
        mesVlanMapConfigurePortMask,
        mesVlanMapLearning,
        mesVlanMapEtherType,
        mesVlanMapRowStatus,
        mesVlanMapDescr,
        mesVlanMapTrustPorts }
    STATUS      current
    DESCRIPTION
        "The VLAN map objects (17.0)."
    ::= { lumMesGroups 67 }

mesClassGroupV2 OBJECT-GROUP
    OBJECTS {
        mesClassIndex,
        mesClassName,
        mesClassIdentifier,
        mesClassPort,
        mesClassLagId,
        mesClassInternalReference,
        mesClassOuterVlanId,
        mesClassOuterVlanPcp,
        mesClassPrecedence,
        mesClassDaMacAddress,
        mesClassAssociateAction,
        mesClassRowStatus,
        mesClassDaMacAddressMask,
        mesClassDSCP,
        mesClassInnerVlanId,
        mesClassInnerVlanPcp,
        mesClassInnerVlanCfi,
        mesClassOuterVlanCfi,
        mesClassDirection,
        mesClassOuterTpid
        }
    STATUS      deprecated
    DESCRIPTION
        "The classification objects (18.0)."
    ::= { lumMesGroups 68 }

mesPortGroupV6 OBJECT-GROUP
    OBJECTS {
        mesPortIndex,
        mesPortName,
        mesPortDescr,
        mesPortSubrack,
        mesPortSlot,
        mesPortTxPort,
        mesPortRxPort,
        mesPortAdminStatus,
        mesPortOperStatus,
        mesPortMtuSize,
        mesPortTagType,
        mesPortNoOfVlans,
        mesPortVlanAware,
        mesPortVlanTagged,
        mesPortVlanUntagged,
        mesPortIngressFiltering,
        mesPortEgressTag,
        mesPortDefaultCeVlanId,
        mesPortAssociateVlan,
        mesPortReleaseVlan,
        mesPortActingAsLine,
        mesPortTrustedPortmask,
        mesPortMacAddress,
        mesPortLagStatus,
        mesPortLagPortmask,
        mesPortAssociateLag,
        mesPortTxEthUtilization,
        mesPortRxEthUtilization,
        mesPortFlowControlMode,
        mesPortAutoNegotiationMode,
        mesPortAutoNegotiationStatus,
        mesPortLinkDown,
        mesPortLinkFaultRemote,
        mesPortLinkFaultLocal,
        mesPortNoOfShapers,
        mesPortNoOfPolicers,
        mesPortAssociateShaper,
        mesPortReleaseShaper,
        mesPortAssociatePolicer,
        mesPortReleasePolicer,
        mesPortRestartAutoNegotiation,
        mesPortConfigureLine,
        mesPortEtherType,
        mesPortConfigureEtherType,
        mesPortNoOfMirrorSources,
        mesPortMirroring,
        mesPortIngressPushTag,
        mesPortEgressPopTag,
        mesPortDefaultCeVlanPriority,
        mesPortConfigureTagRule,
        mesPortMode,
        mesPortPrioAssignment,
        mesPortConfigurePrioAssignment,
        mesPortNoOfTagRules,
        mesPortNoOfVlanSchedPrios,
        mesPortObjectProperty,
        mesPortHighBitErrorRate}
    STATUS      deprecated
    DESCRIPTION
        "The port objects (18.0)."
    ::= { lumMesGroups 69 }

mesMiscGroupV7 OBJECT-GROUP
    OBJECTS {
        mesMiscIndex,
        mesMiscName,
        mesMiscObjectProperty,
        mesMiscAdminStatus,
        mesMiscOperStatus,
        mesMiscMgmtVlanIpAddress,
        mesMiscMgmtVlanNetMask,
        mesMiscMgmtVlanMacAddress0,
        mesMiscMgmtVlanMacAddress1,
        mesMiscMgmtVlanMacAddress2,
        mesMiscConfigureAddress,
        mesMiscMgmtVlanNode,
        mesMiscMacAgeing,
        mesMiscMacGetTable,
        mesMiscNoOfMegs,
        mesMiscAssociateMeg,
        mesMiscNoOfErps,
        mesMiscAssociateErp,
        mesMiscL2Mode,
        mesMiscConfigureMode,
        mesMiscIdentity,
        mesMiscAssociateClass,
        mesMiscAssociateBwp,
        mesMiscWred,
        mesMiscGetPacketMonitor,
        mesMiscSfpPortUsageCurrent,
        mesMiscSfpPortUsageNext }
    STATUS      current
    DESCRIPTION
        "The misc group objects (18.0)."
    ::= { lumMesGroups 70 }

mesCfmMepGroupV3 OBJECT-GROUP
    OBJECTS {
        mesCfmMepIndex,
        mesCfmMepName,
        mesCfmMepMaid,
        mesCfmMepTxPort,
        mesCfmMepPortName,
        mesCfmMepPrimaryVid,
        mesCfmMepAdminStatus,
        mesCfmMepOperStatus,
        mesCfmMepVlanPriority,
        mesCfmMepType,
        mesCfmMepIdentifier,
        mesCfmMepInternalReference,
        mesCfmMepRDICCM,
        mesCfmMepMACstatus,
        mesCfmMepRemoteCCM,
        mesCfmMepErrorCCM,
        mesCfmMepXconCCM,
        mesCfmMepAis,
        mesCfmMepChangePort,
        mesCfmMepTransmitLbrStatus,
        mesCfmMepRowStatus,
        mesCfmMepDirection,
        mesCfmMepCcmSeqNumStatus }
    STATUS      current
    DESCRIPTION
        "The MEP objects (18.0)."
    ::= { lumMesGroups 71 }

mesMaidGroupV3 OBJECT-GROUP
    OBJECTS {
        mesMaidIndex,
        mesMaidName,
        mesMaidGroupId,
        mesMaidMdFormat,
        mesMaidMdName,
        mesMaidMdMac,
        mesMaidMd2Octet,
        mesMaidMdString,
        mesMaidLevel,
        mesMaidMaFormat,
        mesMaidMaName,
        mesMaidMaVpnOui,
        mesMaidMaVpnIndex,
        mesMaidMa2Octet,
        mesMaidMaVlan,
        mesMaidMaString,
        mesMaidCcmInterval,
        mesMaidInternalReference,
        mesMaidIdentifier,
        mesMaidNoOfMeps,
        mesMaidAssociateMep,
        mesMaidReleaseMeps,
        mesMaidRowStatus,
        mesMaidNoOfUpMeps}
    STATUS      deprecated
    DESCRIPTION
        "The Maintainance Domain objects (18.0)."
    ::= { lumMesGroups 72 }

mesMgmtVlanGroupV2 OBJECT-GROUP
    OBJECTS {
        mesMgmtVlanIndex,
        mesMgmtVlanName,
        mesMgmtVlanDescr,
        mesMgmtVlanSubrack,
        mesMgmtVlanSlot,
        mesMgmtVlanTxPort,
        mesMgmtVlanRxPort,
        mesMgmtVlanObjectProperty,
        mesMgmtVlanAdminStatus,
        mesMgmtVlanConfigure,
        mesMgmtVlanTagType,
        mesMgmtVlanEtherType,
        mesMgmtVlanVlanId,
        mesMgmtVlanPriority,
        mesMgmtVlanMacInMac,
        mesMgmtVlanMacInMacIsid,
        mesMgmtVlanMacInMacDa,
        mesMgmtVlanForceMgmtVlan}
    STATUS      deprecated
    DESCRIPTION
        "The Mgmt VLAN objects (19.0)."
    ::= { lumMesGroups 73 }

mesErrorPropGroup OBJECT-GROUP
    OBJECTS {
        mesErrorPropIndex,
        mesErrorPropName,
        mesErrorPropDescr,
        mesErrorPropInternalReference,
        mesErrorPropAdminStatus,
        mesErrorPropOperStatus,
        mesErrorPropState,
        mesErrorPropTriggerType,
        mesErrorPropTriggerObject,
        mesErrorPropTriggerPortIndex,
        mesErrorPropTriggerMepIndex,
        mesErrorPropActionType,
        mesErrorPropActionObject,
        mesErrorPropActionPortIndex,
        mesErrorPropActionMepIndex,
        mesErrorPropHoldOffTimer,
        mesErrorPropRowStatus,
        mesErrorPropFault }
    STATUS      deprecated
    DESCRIPTION
        "The Error Prop objects (21.0)."
    ::= { lumMesGroups 74 }

mesMiscGroupV8 OBJECT-GROUP
    OBJECTS {
        mesMiscIndex,
        mesMiscName,
        mesMiscObjectProperty,
        mesMiscAdminStatus,
        mesMiscOperStatus,
        mesMiscMgmtVlanIpAddress,
        mesMiscMgmtVlanNetMask,
        mesMiscMgmtVlanMacAddress0,
        mesMiscMgmtVlanMacAddress1,
        mesMiscMgmtVlanMacAddress2,
        mesMiscConfigureAddress,
        mesMiscMgmtVlanNode,
        mesMiscMacAgeing,
        mesMiscMacGetTable,
        mesMiscNoOfMegs,
        mesMiscAssociateMeg,
        mesMiscNoOfErps,
        mesMiscAssociateErp,
        mesMiscL2Mode,
        mesMiscConfigureMode,
        mesMiscIdentity,
        mesMiscAssociateClass,
        mesMiscAssociateBwp,
        mesMiscWred,
        mesMiscGetPacketMonitor,
        mesMiscSfpPortUsageCurrent,
        mesMiscSfpPortUsageNext,
        mesMiscAssociateErrorProp }
    STATUS      deprecated
    DESCRIPTION
        "The misc group objects (21.0)."
    ::= { lumMesGroups 75 }

mesGeneralGroupV5 OBJECT-GROUP
    OBJECTS {
        mesGeneralConfigLastChangeTime,
        mesGeneralStateLastChangeTime,
        mesGeneralUniTableSize,
        mesGeneralNniTableSize,
        mesGeneralEvcTableSize,
        mesGeneralBwpTableSize,
        mesGeneralCeEvcMapTableSize,
        mesGeneralMepTableSize,
        mesGeneralMegTableSize,
        mesGeneralEvcBwpMapTableSize,
        mesGeneralPortTableSize,
        mesGeneralVlanMapTableSize,
        mesGeneralMgmtVlanTableSize,
        mesGeneralLagTableSize,
        mesGeneralPolicingTableSize,
        mesGeneralShapingTableSize,
        mesGeneralBwpMapTableSize,
        mesGeneralCosTableSize,
        mesGeneralErrorPropTableSize}
    STATUS      deprecated
    DESCRIPTION
        "The general objects."
    ::= { lumMesGroups 76 }

mesCfmMepGroupV4 OBJECT-GROUP
    OBJECTS {
        mesCfmMepIndex,
        mesCfmMepName,
        mesCfmMepMaid,
        mesCfmMepTxPort,
        mesCfmMepPortName,
        mesCfmMepPrimaryVid,
        mesCfmMepAdminStatus,
        mesCfmMepOperStatus,
        mesCfmMepVlanPriority,
        mesCfmMepType,
        mesCfmMepIdentifier,
        mesCfmMepInternalReference,
        mesCfmMepRDICCM,
        mesCfmMepMACstatus,
        mesCfmMepRemoteCCM,
        mesCfmMepErrorCCM,
        mesCfmMepXconCCM,
        mesCfmMepAis,
        mesCfmMepChangePort,
        mesCfmMepTransmitLbrStatus,
        mesCfmMepRowStatus,
        mesCfmMepDirection,
        mesCfmMepCcmSeqNumStatus,
        mesCfmMepRemoteCsfLos,
        mesCfmMepRemoteCsfRdi,
        mesCfmMepRemoteCsfFdi,
        mesCfmMepLocalCsfLos,
        mesCfmMepLocalDeviceType,
        mesCfmMepLocalDeviceName,
        mesCfmMepLocalDeviceId,
        mesCfmMepViewFilter,
        mesCfmMepUnexpectedPeriod,
        mesCfmMepUnexpectedMepId,
        mesCfmMepUnexpectedMegLevel,
        mesCfmMepMismerge}
    STATUS      current
    DESCRIPTION
        "The MEP objects (21.0)."
    ::= { lumMesGroups 77 }

mesMaidGroupV4 OBJECT-GROUP
    OBJECTS {
        mesMaidIndex,
        mesMaidName,
        mesMaidGroupId,
        mesMaidMdFormat,
        mesMaidMdName,
        mesMaidMdMac,
        mesMaidMd2Octet,
        mesMaidMdString,
        mesMaidLevel,
        mesMaidMaFormat,
        mesMaidMaName,
        mesMaidMaVpnOui,
        mesMaidMaVpnIndex,
        mesMaidMa2Octet,
        mesMaidMaVlan,
        mesMaidMaString,
        mesMaidCcmInterval,
        mesMaidInternalReference,
        mesMaidIdentifier,
        mesMaidNoOfMeps,
        mesMaidAssociateMep,
        mesMaidReleaseMeps,
        mesMaidRowStatus,
        mesMaidNoOfUpMeps,
        mesMaidNoOfNidMeps,
        mesMaidLocalDeviceType,
        mesMaidViewFilter}
    STATUS      deprecated
    DESCRIPTION
        "The Maintainance Domain objects (21.0)."
    ::= { lumMesGroups 78 }

mesMiscGroupV9 OBJECT-GROUP
    OBJECTS {
        mesMiscIndex,
        mesMiscName,
        mesMiscObjectProperty,
        mesMiscAdminStatus,
        mesMiscOperStatus,
        mesMiscMgmtVlanIpAddress,
        mesMiscMgmtVlanNetMask,
        mesMiscMgmtVlanMacAddress0,
        mesMiscMgmtVlanMacAddress1,
        mesMiscMgmtVlanMacAddress2,
        mesMiscConfigureAddress,
        mesMiscMgmtVlanNode,
        mesMiscMacAgeing,
        mesMiscMacGetTable,
        mesMiscNoOfMegs,
        mesMiscAssociateMeg,
        mesMiscNoOfErps,
        mesMiscAssociateErp,
        mesMiscL2Mode,
        mesMiscConfigureMode,
        mesMiscIdentity,
        mesMiscAssociateClass,
        mesMiscAssociateBwp,
        mesMiscWred,
        mesMiscGetPacketMonitor,
        mesMiscSfpPortUsageCurrent,
        mesMiscSfpPortUsageNext,
        mesMiscNoOfErpV2s,
        mesMiscAssociateErpV2,
        mesMiscAssociateVlanProt}
    STATUS      deprecated
    DESCRIPTION
        "The misc group objects (22.0)."
::= { lumMesGroups 79 }

mesMiscGroupV10 OBJECT-GROUP
    OBJECTS {
        mesMiscIndex,
        mesMiscName,
        mesMiscObjectProperty,
        mesMiscAdminStatus,
        mesMiscOperStatus,
        mesMiscMgmtVlanIpAddress,
        mesMiscMgmtVlanNetMask,
        mesMiscMgmtVlanMacAddress0,
        mesMiscMgmtVlanMacAddress1,
        mesMiscMgmtVlanMacAddress2,
        mesMiscConfigureAddress,
        mesMiscMgmtVlanNode,
        mesMiscMacAgeing,
        mesMiscMacGetTable,
        mesMiscNoOfMegs,
        mesMiscAssociateMeg,
        mesMiscNoOfErps,
        mesMiscAssociateErp,
        mesMiscL2Mode,
        mesMiscConfigureMode,
        mesMiscIdentity,
        mesMiscAssociateClass,
        mesMiscAssociateBwp,
        mesMiscWred,
        mesMiscGetPacketMonitor,
        mesMiscSfpPortUsageCurrent,
        mesMiscSfpPortUsageNext,
        mesMiscNoOfErpV2s,
        mesMiscAssociateErpV2,
        mesMiscAssociateVlanProt,
        mesMiscAssociateClassAdvanced,
        mesMiscAssociateErpAdvanced,
        mesMiscAssociateMegAdvanced,
        mesMiscCreateClass,
        mesMiscCreateAction,
        mesMiscCreateMeg,
        mesMiscCreateMep,
        mesMiscCreateErrorProp,
        mesMiscCreatePolicer}
    STATUS      current
    DESCRIPTION
        "The misc group objects (30.1)."
::= { lumMesGroups 127 }

mesErpGroupV3 OBJECT-GROUP
    OBJECTS {
        mesErpIndex,
        mesErpName,
        mesErpPortLeft,
        mesErpPortRight,
        mesErpAdminStatus,
        mesErpInternalReference,
        mesErpDescr,
        mesErpVlanId,
        mesErpMegLevel,
        mesErpProtLink,
        mesErpGuardTime,
        mesErpHoldOffTime,
        mesErpWtrTime,
        mesErpOamDetectionLeft,
        mesErpOamDetectionRight,
        mesErpStatusLeft,
        mesErpStatusRight,
        mesErpProtState,
        mesErpActiveEvent,
        mesErpRapsReqState,
        mesErpServiceFailure,
        mesErpServiceDegraded,
        mesErpUnexpectedMegLevel,
        mesErpCommunicationFailure,
        mesErpChangePort,
        mesErpRowStatus,
        mesErpNodeType,
        mesErpProtectionMode,
        mesErpVersion,
        mesErpMajorName,
        mesErpRingId,
        mesErpRingIndex,
        mesErpOperatorCommand,
        mesErpGroupId,
        mesErpSwitchInformation,
        mesErpTopologyChangePropagation,
        mesErpSubRings}
    STATUS      deprecated
    DESCRIPTION
        "The ERP objects (22.0)."
    ::= { lumMesGroups 80 }

mesVlanProtV1 OBJECT-GROUP
    OBJECTS {
        mesVlanProtIndex,
        mesVlanProtName,
        mesVlanProtInternalReference,
        mesVlanProtRings,
        mesVlanProtProtectedVlan,
        mesVlanProtGroupId,
        mesVlanProtAddRingAction,
        mesVlanProtRemoveRingAction,
        mesVlanProtDescr,
        mesVlanProtChangeVlansAction}
    STATUS      current
    DESCRIPTION
        "The ERP VLAN objects (22.0)."
    ::= { lumMesGroups 81 }

mesCfmMepGroupV5 OBJECT-GROUP
    OBJECTS {
        mesCfmMepIndex,
        mesCfmMepName,
        mesCfmMepMaid,
        mesCfmMepTxPort,
        mesCfmMepPortName,
        mesCfmMepPrimaryVid,
        mesCfmMepAdminStatus,
        mesCfmMepOperStatus,
        mesCfmMepVlanPriority,
        mesCfmMepType,
        mesCfmMepIdentifier,
        mesCfmMepInternalReference,
        mesCfmMepRDICCM,
        mesCfmMepMACstatus,
        mesCfmMepRemoteCCM,
        mesCfmMepErrorCCM,
        mesCfmMepXconCCM,
        mesCfmMepAis,
        mesCfmMepChangePort,
        mesCfmMepTransmitLbrStatus,
        mesCfmMepRowStatus,
        mesCfmMepDirection,
        mesCfmMepCcmSeqNumStatus,
        mesCfmMepRemoteCsfLos,
        mesCfmMepRemoteCsfRdi,
        mesCfmMepRemoteCsfFdi,
        mesCfmMepLocalCsfLos,
        mesCfmMepLocalDeviceType,
        mesCfmMepLocalDeviceName,
        mesCfmMepLocalDeviceId,
        mesCfmMepViewFilter,
        mesCfmMepUnexpectedPeriod,
        mesCfmMepUnexpectedMepId,
        mesCfmMepUnexpectedMegLevel,
        mesCfmMepMismerge,
        mesCfmMepNoOfLMs,
        mesCfmMepNoOfDMs
}
    STATUS      current
    DESCRIPTION
        "The MEP objects (22.0)."
    ::= { lumMesGroups 82 }

mesVlanMapGroupV6 OBJECT-GROUP
    OBJECTS {
        mesVlanMapIndex,
        mesVlanMapName,
        mesVlanMapVlanIdRangeLower,
        mesVlanMapVlanIdRangeUpper,
        mesVlanMapInternalReference,
        mesVlanMapPortmask,
        mesVlanMapConfigurePortMask,
        mesVlanMapLearning,
        mesVlanMapEtherType,
        mesVlanMapRowStatus,
        mesVlanMapDescr,
        mesVlanMapTrustPorts,
        mesVlanMapRings}
    STATUS      deprecated
    DESCRIPTION
        "The VLAN map objects (22.0)."
    ::= { lumMesGroups 83 }

mesClassGroupV3 OBJECT-GROUP
    OBJECTS {
        mesClassIndex,
        mesClassName,
        mesClassIdentifier,
        mesClassPort,
        mesClassLagId,
        mesClassInternalReference,
        mesClassOuterVlanId,
        mesClassOuterVlanPcp,
        mesClassPrecedence,
        mesClassDaMacAddress,
        mesClassAssociateAction,
        mesClassRowStatus,
        mesClassDaMacAddressMask,
        mesClassDSCP,
        mesClassInnerVlanId,
        mesClassInnerVlanPcp,
        mesClassInnerVlanCfi,
        mesClassOuterVlanCfi,
        mesClassDirection,
        mesClassOuterTpid,
        mesClassInternalClassId
        }
    STATUS      deprecated
    DESCRIPTION
        "The classification objects (22.0)."
    ::= { lumMesGroups 84 }

mesMgmtVlanGroupV3 OBJECT-GROUP
    OBJECTS {
        mesMgmtVlanIndex,
        mesMgmtVlanName,
        mesMgmtVlanDescr,
        mesMgmtVlanSubrack,
        mesMgmtVlanSlot,
        mesMgmtVlanTxPort,
        mesMgmtVlanRxPort,
        mesMgmtVlanObjectProperty,
        mesMgmtVlanAdminStatus,
        mesMgmtVlanConfigure,
        mesMgmtVlanTagType,
        mesMgmtVlanEtherType,
        mesMgmtVlanVlanId,
        mesMgmtVlanPriority,
        mesMgmtVlanMacInMac,
        mesMgmtVlanMacInMacIsid,
        mesMgmtVlanMacInMacDa,
        mesMgmtVlanForceMgmtVlan,
        mesMgmtVlanRings
        }
    STATUS      deprecated
    DESCRIPTION
        "The Mgmt VLAN objects (22.0)."
    ::= { lumMesGroups 85 }

mesClassGroupV4 OBJECT-GROUP
    OBJECTS {
        mesClassIndex,
        mesClassName,
        mesClassIdentifier,
        mesClassPort,
        mesClassLagId,
        mesClassInternalReference,
        mesClassOuterVlanId,
        mesClassOuterVlanPcp,
        mesClassPrecedence,
        mesClassDaMacAddress,
        mesClassAssociateAction,
        mesClassRowStatus,
        mesClassDaMacAddressMask,
        mesClassDSCP,
        mesClassInnerVlanId,
        mesClassInnerVlanPcp,
        mesClassInnerVlanCfi,
        mesClassOuterVlanCfi,
        mesClassDirection,
        mesClassOuterTpid,
        mesClassInternalClassId,
        mesClassSourceAddressIPV4,
        mesClassSourceMaskIPV4,
        mesClassDestAddressIPV4,
        mesClassDestMaskIPV4,
        mesClassSubrack,
        mesClassSlot,
        mesClassVlanStackStructure,
        mesClassServiceId}
    STATUS      deprecated
    DESCRIPTION
        "The classification objects (23.0)."
    ::= { lumMesGroups 86 }

mesActionGroupV2 OBJECT-GROUP
    OBJECTS {
        mesActionIndex,
        mesActionName,
        mesActionIdentifier,
        mesActionInternalReference,
        mesActionType,
        mesActionOuterVlanId,
        mesActionPcp,
        mesActionPolicerId,
        mesActionInnerVlanId,
        mesActionQueue,
        mesActionRowStatus,
        mesActionRedirectPort,
        mesActionServiceId}
    STATUS      deprecated
    DESCRIPTION
        "The action objects (23.0)."
    ::= { lumMesGroups 87 }

mesCfmMepGroupV6 OBJECT-GROUP
    OBJECTS {
        mesCfmMepIndex,
        mesCfmMepName,
        mesCfmMepMaid,
        mesCfmMepTxPort,
        mesCfmMepPortName,
        mesCfmMepPrimaryVid,
        mesCfmMepAdminStatus,
        mesCfmMepOperStatus,
        mesCfmMepVlanPriority,
        mesCfmMepType,
        mesCfmMepIdentifier,
        mesCfmMepInternalReference,
        mesCfmMepRDICCM,
        mesCfmMepMACstatus,
        mesCfmMepRemoteCCM,
        mesCfmMepErrorCCM,
        mesCfmMepXconCCM,
        mesCfmMepAis,
        mesCfmMepChangePort,
        mesCfmMepTransmitLbrStatus,
        mesCfmMepRowStatus,
        mesCfmMepDirection,
        mesCfmMepCcmSeqNumStatus,
        mesCfmMepRemoteCsfLos,
        mesCfmMepRemoteCsfRdi,
        mesCfmMepRemoteCsfFdi,
        mesCfmMepLocalCsfLos,
        mesCfmMepLocalDeviceType,
        mesCfmMepLocalDeviceName,
        mesCfmMepLocalDeviceId,
    mesCfmMepViewFilter,
        mesCfmMepUnexpectedPeriod,
        mesCfmMepUnexpectedMepId,
        mesCfmMepUnexpectedMegLevel,
        mesCfmMepMismerge,
        mesCfmMepNoOfLMs,
        mesCfmMepNoOfDMs,
        mesCfmMepTransmitDmrStatus,
        mesCfmMepTransmitLmrStatus,
        mesCfmMepLmCosAwareness
}
    STATUS      deprecated
    DESCRIPTION
        "The MEP objects (23.0)."
    ::= { lumMesGroups 88 }

mesLacpGroup OBJECT-GROUP
    OBJECTS {
        mesLacpIndex,
        mesLacpName,
        mesLacpInternalReference,
        mesLacpLagIdentifier,
        mesLacpLagId,
        mesLacpPortPriority,
        mesLacpSelected,
        mesLacpReceiveState,
        mesLacpTransmitState,
        mesLacpMuxState,
        mesLacpActorExpired,
        mesLacpActorDefault,
        mesLacpActorDistributing,
        mesLacpActorCollecting,
        mesLacpActorSynchronization,
        mesLacpActorAggregation,
        mesLacpActorTimeout,
        mesLacpActorActivity,
        mesLacpPartnerExpired,
        mesLacpPartnerDefault,
        mesLacpPartnerDistributing,
        mesLacpPartnerCollecting,
        mesLacpPartnerSynchronization,
        mesLacpPartnerAggregation,
        mesLacpPartnerTimeout,
        mesLacpPartnerActivity,
        mesLacpTxLacpPdus,
    mesLacpRxLacpPdus,
        mesLacpInternalIndex,
        mesLacpResetCounters
}
    STATUS      deprecated
    DESCRIPTION
        "The LACP group objects (23.0)."
    ::= { lumMesGroups 89 }

mesVlanMapGroupV7 OBJECT-GROUP
    OBJECTS {
        mesVlanMapIndex,
        mesVlanMapName,
        mesVlanMapVlanIdRangeLower,
        mesVlanMapVlanIdRangeUpper,
        mesVlanMapInternalReference,
        mesVlanMapPortmask,
        mesVlanMapConfigurePortMask,
        mesVlanMapLearning,
        mesVlanMapEtherType,
        mesVlanMapRowStatus,
        mesVlanMapDescr,
        mesVlanMapTrustPorts,
        mesVlanMapRings,
        mesVlanMapServiceId}
    STATUS      deprecated
    DESCRIPTION
        "The VLAN map objects (23.0)."
    ::= { lumMesGroups 90 }

mesPolicyGroupV2 OBJECT-GROUP
    OBJECTS {
        mesPolicyIndex,
        mesPolicyName,
        mesPolicyInternalReference,
        mesPolicyClass,
        mesPolicyAction,
        mesPolicyServiceId}
    STATUS      current
    DESCRIPTION
        "The policy objects (23.0)."
    ::= { lumMesGroups 91 }

mesBwpGroupV3 OBJECT-GROUP
    OBJECTS {
        mesBwpIndex,
        mesBwpName,
        mesBwpObjectProperty,
        mesBwpCoSIdentifier,
        mesBwpCir,
        mesBwpCbs,
        mesBwpEir,
        mesBwpEbs,
        mesBwpCouplingFlag,
        mesBwpColorMode,
        mesBwpInternalReference,
        mesBwpRowStatus,
        mesBwpServiceId}
    STATUS      deprecated
    DESCRIPTION
        "The BWP objects v3 (23.0)."
    ::= { lumMesGroups 92 }

mesLagGroupV4 OBJECT-GROUP
    OBJECTS {
        mesLagIndex,
        mesLagName,
        mesLagInternalReference,
        mesLagPortmask,
        mesLagMasterIndex,
        mesLagConfigure,
        mesLagHash,
        mesLagIdentifier,
        mesLagRowStatus,
        mesLagLacpEnabled,
        mesLagLacpSystemPriority,
        mesLagLacpPeriod,
        mesLagDegraded,
        mesLagFailure }
    STATUS      deprecated
    DESCRIPTION
        "The LAG group objects v4(23.0)."
    ::= { lumMesGroups 93 }

mesLagGroupV5 OBJECT-GROUP
    OBJECTS {
        mesLagIndex,
        mesLagName,
        mesLagInternalReference,
        mesLagPortmask,
        mesLagMasterIndex,
        mesLagConfigure,
        mesLagHash,
        mesLagIdentifier,
        mesLagRowStatus,
        mesLagLacpEnabled,
        mesLagLacpSystemPriority,
        mesLagLacpPeriod,
        mesLagLacpLinkProtection,
        mesLagDegraded,
        mesLagFailure,
        mesLagLacpMaxNumberOfActiveLinks,
        mesLagNoOfPorts,
        mesLagLacpMinNumberOfActiveLinks}
    STATUS      deprecated
    DESCRIPTION
        "The LAG group objects v5(23.1)."
    ::= { lumMesGroups 94 }

mesCfmMepGroupV7 OBJECT-GROUP
    OBJECTS {
        mesCfmMepIndex,
        mesCfmMepName,
        mesCfmMepMaid,
        mesCfmMepTxPort,
        mesCfmMepPortName,
        mesCfmMepPrimaryVid,
        mesCfmMepAdminStatus,
        mesCfmMepOperStatus,
        mesCfmMepVlanPriority,
        mesCfmMepType,
        mesCfmMepIdentifier,
        mesCfmMepInternalReference,
        mesCfmMepRDICCM,
        mesCfmMepMACstatus,
        mesCfmMepRemoteCCM,
        mesCfmMepErrorCCM,
        mesCfmMepXconCCM,
        mesCfmMepAis,
        mesCfmMepChangePort,
        mesCfmMepTransmitLbrStatus,
        mesCfmMepRowStatus,
        mesCfmMepDirection,
        mesCfmMepCcmSeqNumStatus,
        mesCfmMepRemoteCsfLos,
        mesCfmMepRemoteCsfRdi,
        mesCfmMepRemoteCsfFdi,
        mesCfmMepLocalCsfLos,
        mesCfmMepLocalDeviceType,
        mesCfmMepLocalDeviceName,
        mesCfmMepLocalDeviceId,
        mesCfmMepViewFilter,
        mesCfmMepUnexpectedPeriod,
        mesCfmMepUnexpectedMepId,
        mesCfmMepUnexpectedMegLevel,
        mesCfmMepMismerge,
        mesCfmMepNoOfLMs,
        mesCfmMepNoOfDMs,
        mesCfmMepTransmitDmrStatus,
        mesCfmMepTransmitLmrStatus,
        mesCfmMepLmCosAwareness,
        mesCfmMepResourceType,
        mesCfmMepLagId,
        mesCfmMepInterfaceName }
    STATUS      deprecated
    DESCRIPTION
        "The MEP objects (24.0)."
    ::= { lumMesGroups 95 }

mesErpGroupV4 OBJECT-GROUP
    OBJECTS {
        mesErpIndex,
        mesErpName,
        mesErpPortLeft,
        mesErpPortRight,
        mesErpAdminStatus,
        mesErpInternalReference,
        mesErpDescr,
        mesErpVlanId,
        mesErpMegLevel,
        mesErpProtLink,
        mesErpGuardTime,
        mesErpHoldOffTime,
        mesErpWtrTime,
        mesErpOamDetectionLeft,
        mesErpOamDetectionRight,
        mesErpStatusLeft,
        mesErpStatusRight,
        mesErpProtState,
        mesErpActiveEvent,
        mesErpRapsReqState,
        mesErpServiceFailure,
        mesErpServiceDegraded,
        mesErpUnexpectedMegLevel,
        mesErpCommunicationFailure,
        mesErpChangePort,
        mesErpRowStatus,
        mesErpNodeType,
        mesErpProtectionMode,
        mesErpVersion,
        mesErpMajorName,
        mesErpRingId,
        mesErpRingIndex,
        mesErpOperatorCommand,
        mesErpGroupId,
        mesErpSwitchInformation,
        mesErpTopologyChangePropagation,
        mesErpSubRings,
        mesErpResourceTypeLeft,
        mesErpLagIdLeft,
        mesErpResourceTypeRight,
        mesErpLagIdRight,
        mesErpInterfaceLeft,
        mesErpInterfaceRight }
    STATUS      deprecated
    DESCRIPTION
        "The ERP objects (24.0)."
    ::= { lumMesGroups 96 }

mesLagGroupV6 OBJECT-GROUP
    OBJECTS {
        mesLagIndex,
        mesLagName,
        mesLagInternalReference,
        mesLagPortmask,
        mesLagMasterIndex,
        mesLagConfigure,
        mesLagHash,
        mesLagIdentifier,
        mesLagRowStatus,
        mesLagLacpEnabled,
        mesLagLacpSystemPriority,
        mesLagLacpPeriod,
        mesLagLacpLinkProtection,
        mesLagDegraded,
        mesLagFailure,
        mesLagLacpMaxNumberOfActiveLinks,
        mesLagNoOfPorts,
        mesLagLacpMinNumberOfActiveLinks,
        mesLagIsMcLag}
    STATUS      deprecated
    DESCRIPTION
        "The LAG group objects v6(24.0)."
    ::= { lumMesGroups 97 }

mesErpGroupV5 OBJECT-GROUP
    OBJECTS {
        mesErpIndex,
        mesErpName,
        mesErpPortLeft,
        mesErpPortRight,
        mesErpAdminStatus,
        mesErpInternalReference,
        mesErpDescr,
        mesErpVlanId,
        mesErpMegLevel,
        mesErpProtLink,
        mesErpGuardTime,
        mesErpHoldOffTime,
        mesErpWtrTime,
        mesErpOamDetectionLeft,
        mesErpOamDetectionRight,
        mesErpStatusLeft,
        mesErpStatusRight,
        mesErpProtState,
        mesErpActiveEvent,
        mesErpRapsReqState,
        mesErpServiceFailure,
        mesErpServiceDegraded,
        mesErpUnexpectedMegLevel,
        mesErpCommunicationFailure,
        mesErpProvisioningMismatch,
        mesErpChangePort,
        mesErpRowStatus,
        mesErpNodeType,
        mesErpProtectionMode,
        mesErpVersion,
        mesErpMajorName,
        mesErpRingId,
        mesErpRingIndex,
        mesErpOperatorCommand,
        mesErpGroupId,
        mesErpSwitchInformation,
        mesErpTopologyChangePropagation,
        mesErpSubRings,
        mesErpResourceTypeLeft,
        mesErpLagIdLeft,
        mesErpResourceTypeRight,
        mesErpLagIdRight,
        mesErpInterfaceLeft,
        mesErpInterfaceRight }
    STATUS      deprecated
    DESCRIPTION
        "The ERP objects (25.0)."
    ::= { lumMesGroups 98 }


mesLagGroupV7 OBJECT-GROUP
    OBJECTS {
        mesLagIndex,
        mesLagName,
        mesLagInternalReference,
        mesLagPortmask,
        mesLagMasterIndex,
        mesLagConfigure,
        mesLagHash,
        mesLagIdentifier,
        mesLagRowStatus,
        mesLagLacpEnabled,
        mesLagLacpSystemPriority,
        mesLagLacpPeriod,
        mesLagLacpLinkProtection,
        mesLagDegraded,
        mesLagFailure,
        mesLagLacpMaxNumberOfActiveLinks,
        mesLagNoOfPorts,
        mesLagLacpMinNumberOfActiveLinks,
        mesLagIsMcLag,
        mesLagConfigureTagRule,
        mesLagNoOfTagRules,
        mesLagDescr,
        mesLagAdminStatus,
        mesLagOperStatus }
    STATUS      deprecated
    DESCRIPTION
        "The LAG group objects v7(25.0)."
    ::= { lumMesGroups 99 }

mesLagGroupV8 OBJECT-GROUP
    OBJECTS {
        mesLagIndex,
        mesLagName,
        mesLagInternalReference,
        mesLagPortmask,
        mesLagMasterIndex,
        mesLagConfigure,
        mesLagHash,
        mesLagIdentifier,
        mesLagRowStatus,
        mesLagLacpEnabled,
        mesLagLacpSystemPriority,
        mesLagLacpPeriod,
        mesLagLacpLinkProtection,
        mesLagDegraded,
        mesLagFailure,
        mesLagLacpMaxNumberOfActiveLinks,
        mesLagNoOfPorts,
        mesLagLacpMinNumberOfActiveLinks,
        mesLagIsMcLag,
        mesLagConfigureTagRule,
        mesLagNoOfTagRules,
        mesLagDescr,
        mesLagAdminStatus,
        mesLagOperStatus,
        mesLagPortmaskIf1,
        mesLagPortmaskIf2,
        mesLagPortmaskIf3,
        mesLagPortmaskIf4,
        mesLagPortmaskIf5,
        mesLagPortmaskIf6,
        mesLagPortmaskIf7,
        mesLagPortmaskIf8,
        mesLagMasterIfNo,
        mesLagMasterTxPort,
        mesLagLocalId,
        mesLagPrepareConfigPortMask
         }
    STATUS      deprecated
    DESCRIPTION
        "The LAG group objects v8(26.0)."
    ::= { lumMesGroups 108 }

mesVlanTagClassVlanGroupV3 OBJECT-GROUP
    OBJECTS {
        mesVlanTagClassVlanIndex,
        mesVlanTagClassVlanName,
        mesVlanTagClassVlanTxPort,
        mesVlanTagClassVlanInternalReference,
        mesVlanTagClassVlanRuleName,
        mesVlanTagClassVlanRuleIndex,
        mesVlanTagClassVlanOuterVlanId,
        mesVlanTagClassVlanLagIndex }
    STATUS      deprecated
    DESCRIPTION
        "The vlan tag classification vlan objects (25.0)."
    ::= { lumMesGroups 100 }


mesCfmMepGroupV8 OBJECT-GROUP
    OBJECTS {
        mesCfmMepIndex,
        mesCfmMepName,
        mesCfmMepMaid,
        mesCfmMepTxPort,
        mesCfmMepPortName,
        mesCfmMepPrimaryVid,
        mesCfmMepAdminStatus,
        mesCfmMepOperStatus,
        mesCfmMepVlanPriority,
        mesCfmMepType,
        mesCfmMepIdentifier,
        mesCfmMepInternalReference,
        mesCfmMepRDICCM,
        mesCfmMepMACstatus,
        mesCfmMepRemoteCCM,
        mesCfmMepErrorCCM,
        mesCfmMepXconCCM,
        mesCfmMepAis,
        mesCfmMepTransmitLbrStatus,
        mesCfmMepRowStatus,
        mesCfmMepDirection,
        mesCfmMepCcmSeqNumStatus,
        mesCfmMepRemoteCsfLos,
        mesCfmMepRemoteCsfRdi,
        mesCfmMepRemoteCsfFdi,
        mesCfmMepLocalCsfLos,
        mesCfmMepLocalDeviceType,
        mesCfmMepLocalDeviceName,
        mesCfmMepLocalDeviceId,
        mesCfmMepViewFilter,
        mesCfmMepUnexpectedPeriod,
        mesCfmMepUnexpectedMepId,
        mesCfmMepUnexpectedMegLevel,
        mesCfmMepMismerge,
        mesCfmMepNoOfLMs,
        mesCfmMepNoOfDMs,
        mesCfmMepTransmitDmrStatus,
        mesCfmMepTransmitLmrStatus,
        mesCfmMepLmCosAwareness,
        mesCfmMepResourceType,
        mesCfmMepLagId,
        mesCfmMepInterfaceName }
    STATUS      deprecated
    DESCRIPTION
        "The MEP objects (25.0)."
    ::= { lumMesGroups 101 }

mesMaidGroupV5 OBJECT-GROUP
    OBJECTS {
        mesMaidIndex,
        mesMaidName,
        mesMaidGroupId,
        mesMaidMdFormat,
        mesMaidMdName,
        mesMaidMdMac,
        mesMaidMd2Octet,
        mesMaidMdString,
        mesMaidLevel,
        mesMaidMaFormat,
        mesMaidMaName,
        mesMaidMaVpnOui,
        mesMaidMaVpnIndex,
        mesMaidMa2Octet,
        mesMaidMaVlan,
        mesMaidMaString,
        mesMaidCcmInterval,
        mesMaidInternalReference,
        mesMaidIdentifier,
        mesMaidNoOfMeps,
        mesMaidAssociateMep,
        mesMaidReleaseMeps,
        mesMaidRowStatus,
        mesMaidNoOfUpMeps,
        mesMaidNoOfNidMeps,
        mesMaidLocalDeviceType,
        mesMaidViewFilter,
	    mesMaidAssociateMepNid}
    STATUS      deprecated
    DESCRIPTION
        "The Maintainance Domain objects (25.0)."
    ::= { lumMesGroups 102 }

mesMaidGroupV6 OBJECT-GROUP
    OBJECTS {
        mesMaidIndex,
        mesMaidName,
        mesMaidGroupId,
        mesMaidMdFormat,
        mesMaidMdName,
        mesMaidMdMac,
        mesMaidMd2Octet,
        mesMaidMdString,
        mesMaidLevel,
        mesMaidMaFormat,
        mesMaidMaName,
        mesMaidMaVpnOui,
        mesMaidMaVpnIndex,
        mesMaidMa2Octet,
        mesMaidMaVlan,
        mesMaidMaString,
        mesMaidCcmInterval,
        mesMaidInternalReference,
        mesMaidIdentifier,
        mesMaidNoOfMeps,
        mesMaidAssociateMep,
        mesMaidReleaseMeps,
        mesMaidRowStatus,
        mesMaidNoOfUpMeps,
        mesMaidNoOfNidMeps,
        mesMaidLocalDeviceType,
        mesMaidViewFilter,
        mesMaidAssociateMepNid,
        mesMaidAssociateMepAdvanced,
        mesMaidSubrack,
        mesMaidSlot,
	mesMaidServiceId}
    STATUS      current
    DESCRIPTION
        "The Maintainance Domain objects (30.1)."
    ::= { lumMesGroups 129 }


mesPortGroupV7 OBJECT-GROUP
    OBJECTS {
        mesPortIndex,
        mesPortName,
        mesPortDescr,
        mesPortSubrack,
        mesPortSlot,
        mesPortTxPort,
        mesPortRxPort,
        mesPortAdminStatus,
        mesPortOperStatus,
        mesPortMtuSize,
        mesPortTagType,
        mesPortNoOfVlans,
        mesPortVlanAware,
        mesPortVlanTagged,
        mesPortVlanUntagged,
        mesPortIngressFiltering,
        mesPortEgressTag,
        mesPortDefaultCeVlanId,
        mesPortAssociateVlan,
        mesPortReleaseVlan,
        mesPortActingAsLine,
        mesPortTrustedPortmask,
        mesPortConfigureTrustedPortmask,
        mesPortMacAddress,
        mesPortLagStatus,
        mesPortLagPortmask,
        mesPortAssociateLag,
        mesPortTxEthUtilization,
        mesPortRxEthUtilization,
        mesPortFlowControlMode,
        mesPortAutoNegotiationMode,
        mesPortAutoNegotiationStatus,
        mesPortLinkDown,
        mesPortLinkFaultRemote,
        mesPortLinkFaultLocal,
        mesPortNoOfShapers,
        mesPortNoOfPolicers,
        mesPortAssociateShaper,
        mesPortReleaseShaper,
        mesPortAssociatePolicer,
        mesPortReleasePolicer,
        mesPortRestartAutoNegotiation,
        mesPortConfigureLine,
        mesPortEtherType,
        mesPortConfigureEtherType,
        mesPortNoOfMirrorSources,
        mesPortMirroring,
        mesPortIngressPushTag,
        mesPortEgressPopTag,
        mesPortDefaultCeVlanPriority,
        mesPortConfigureTagRule,
        mesPortCosProfile,
        mesPortMode,
        mesPortPrioAssignment,
        mesPortConfigurePrioAssignment,
        mesPortNoOfTagRules,
        mesPortNoOfVlanSchedPrios,
        mesPortObjectProperty,
        mesPortHighBitErrorRate,
        mesPortIdx,
        mesPortIfNo,
        mesPortClientIdx,
        mesPortUpPortId,
        mesPortLagPortmaskIf1,
        mesPortLagPortmaskIf2,
        mesPortLagPortmaskIf3,
        mesPortLagPortmaskIf4,
        mesPortLagPortmaskIf5,
        mesPortLagPortmaskIf6,
        mesPortLagPortmaskIf7,
        mesPortLagPortmaskIf8
        }
    STATUS      deprecated
    DESCRIPTION
        "The port objects (26.0)."
    ::= { lumMesGroups 103 }


mesVlanMapGroupV8 OBJECT-GROUP
    OBJECTS {
        mesVlanMapIndex,
        mesVlanMapName,
        mesVlanMapVlanIdRangeLower,
        mesVlanMapVlanIdRangeUpper,
        mesVlanMapInternalReference,
        mesVlanMapPortmask,
        mesVlanMapConfigurePortMask,
        mesVlanMapLearning,
        mesVlanMapEtherType,
        mesVlanMapRowStatus,
        mesVlanMapDescr,
        mesVlanMapTrustPorts,
        mesVlanMapRings,
        mesVlanMapServiceId,
        mesVlanMapPortmaskIf1,
        mesVlanMapPortmaskIf2,
        mesVlanMapPortmaskIf3,
        mesVlanMapPortmaskIf4,
        mesVlanMapPortmaskIf5,
        mesVlanMapPortmaskIf6,
        mesVlanMapPortmaskIf7,
        mesVlanMapPortmaskIf8,
        mesVlanMapPrepareConfigPortMask
        }
    STATUS      deprecated
    DESCRIPTION
        "The VLAN map objects (26.0)."
    ::= { lumMesGroups 104 }

mesErpGroupV6 OBJECT-GROUP
    OBJECTS {
        mesErpIndex,
        mesErpName,
        mesErpPortLeft,
        mesErpPortRight,
        mesErpAdminStatus,
        mesErpInternalReference,
        mesErpDescr,
        mesErpVlanId,
        mesErpMegLevel,
        mesErpProtLink,
        mesErpGuardTime,
        mesErpHoldOffTime,
        mesErpWtrTime,
        mesErpOamDetectionLeft,
        mesErpOamDetectionRight,
        mesErpStatusLeft,
        mesErpStatusRight,
        mesErpProtState,
        mesErpActiveEvent,
        mesErpRapsReqState,
        mesErpServiceFailure,
        mesErpServiceDegraded,
        mesErpUnexpectedMegLevel,
        mesErpCommunicationFailure,
        mesErpProvisioningMismatch,
        mesErpRowStatus,
        mesErpNodeType,
        mesErpProtectionMode,
        mesErpVersion,
        mesErpMajorName,
        mesErpRingId,
        mesErpRingIndex,
        mesErpOperatorCommand,
        mesErpGroupId,
        mesErpSwitchInformation,
        mesErpTopologyChangePropagation,
        mesErpSubRings,
        mesErpResourceTypeLeft,
        mesErpLagIdLeft,
        mesErpResourceTypeRight,
        mesErpLagIdRight,
        mesErpInterfaceLeft,
        mesErpInterfaceRight,
        mesErpIfNoLeft,
        mesErpTxPortLeft,
        mesErpIfNoRight,
        mesErpTxPortRight }
    STATUS      deprecated
    DESCRIPTION
        "The ERP objects (26.0)."
    ::= { lumMesGroups 105 }

mesMgmtVlanGroupV4 OBJECT-GROUP
    OBJECTS {
        mesMgmtVlanIndex,
        mesMgmtVlanName,
        mesMgmtVlanDescr,
        mesMgmtVlanSubrack,
        mesMgmtVlanSlot,
        mesMgmtVlanTxPort,
        mesMgmtVlanRxPort,
        mesMgmtVlanObjectProperty,
        mesMgmtVlanAdminStatus,
        mesMgmtVlanConfigure,
        mesMgmtVlanTagType,
        mesMgmtVlanEtherType,
        mesMgmtVlanVlanId,
        mesMgmtVlanPriority,
        mesMgmtVlanMacInMac,
        mesMgmtVlanMacInMacIsid,
        mesMgmtVlanMacInMacDa,
        mesMgmtVlanForceMgmtVlan,
        mesMgmtVlanRings,
        mesMgmtVlanIfNo
        }
    STATUS      current
    DESCRIPTION
        "The Mgmt VLAN objects (26.0)."
    ::= { lumMesGroups 106 }

mesPolicingGroupV2 OBJECT-GROUP
    OBJECTS {
        mesPolicingIndex,
        mesPolicingName,
        mesPolicingRate,
        mesPolicingBurstSize,
        mesPolicingType,
        mesPolicingInternalReference,
        mesPolicingIdentifier,
	mesPolicingUpId }
    STATUS      deprecated
    DESCRIPTION
        "The policing objects (26.0)."
    ::= { lumMesGroups 107 }

mesCosProfileGroupV3 OBJECT-GROUP
    OBJECTS {
        mesCosProfileIndex,
        mesCosProfileName,
        mesCosProfilePortmask,
        mesCosProfilePortmaskIf1,
        mesCosProfilePortmaskIf2,
        mesCosProfilePortmaskIf3,
        mesCosProfilePortmaskIf4,
        mesCosProfilePortmaskIf5,
        mesCosProfilePortmaskIf6,
        mesCosProfilePortmaskIf7,
        mesCosProfilePortmaskIf8,
        mesCosProfileScheduler,
        mesCosProfileWeight0,
        mesCosProfileWeight1,
        mesCosProfileWeight2,
        mesCosProfileWeight3,
        mesCosProfileWeight4,
        mesCosProfileWeight5,
        mesCosProfileWeight6,
        mesCosProfileWeight7,
        mesCosProfilePriority0,
        mesCosProfilePriority1,
        mesCosProfilePriority2,
        mesCosProfilePriority3,
        mesCosProfilePriority4,
        mesCosProfilePriority5,
        mesCosProfilePriority6,
        mesCosProfilePriority7,
        mesCosProfileConfigureScheduler,
        mesCosProfileIngressPcpDecoding,
        mesCosProfileIngressDeiDecoding,
        mesCosProfileIngressColor0,
        mesCosProfileIngressColor1,
        mesCosProfileIngressColor2,
        mesCosProfileIngressColor3,
        mesCosProfileIngressColor4,
        mesCosProfileIngressColor5,
        mesCosProfileIngressColor6,
        mesCosProfileIngressColor7,
        mesCosProfileEgressPcpEncoding,
        mesCosProfileEgressDeiEncoding,
        mesCosProfileEgressPcpGreen0,
        mesCosProfileEgressPcpGreen1,
        mesCosProfileEgressPcpGreen2,
        mesCosProfileEgressPcpGreen3,
        mesCosProfileEgressPcpGreen4,
        mesCosProfileEgressPcpGreen5,
        mesCosProfileEgressPcpGreen6,
        mesCosProfileEgressPcpGreen7,
        mesCosProfileEgressPcpYellow0,
        mesCosProfileEgressPcpYellow1,
        mesCosProfileEgressPcpYellow2,
        mesCosProfileEgressPcpYellow3,
        mesCosProfileEgressPcpYellow4,
        mesCosProfileEgressPcpYellow5,
        mesCosProfileEgressPcpYellow6,
        mesCosProfileEgressPcpYellow7 }
    STATUS      deprecated
    DESCRIPTION
        "The COS Profile objects (26.0)."
    ::= { lumMesGroups 109 }

mesVlanTagClassVlanGroupV4 OBJECT-GROUP
    OBJECTS {
        mesVlanTagClassVlanIndex,
        mesVlanTagClassVlanName,
        mesVlanTagClassVlanTxPort,
        mesVlanTagClassVlanInternalReference,
        mesVlanTagClassVlanRuleName,
        mesVlanTagClassVlanRuleIndex,
        mesVlanTagClassVlanOuterVlanId,
        mesVlanTagClassVlanLagIndex,
        mesVlanTagClassVlanIfNo }
    STATUS      deprecated
    DESCRIPTION
        "The vlan tag classification vlan objects (26.0)."
    ::= { lumMesGroups 110 }


mesLacpGroupV1 OBJECT-GROUP
    OBJECTS {
        mesLacpIndex,
        mesLacpName,
        mesLacpInternalReference,
        mesLacpLagIdentifier,
        mesLacpLagId,
        mesLacpPortPriority,
        mesLacpSelected,
        mesLacpReceiveState,
        mesLacpTransmitState,
        mesLacpMuxState,
        mesLacpActorExpired,
        mesLacpActorDefault,
        mesLacpActorDistributing,
        mesLacpActorCollecting,
        mesLacpActorSynchronization,
        mesLacpActorAggregation,
        mesLacpActorTimeout,
        mesLacpActorActivity,
        mesLacpPartnerExpired,
        mesLacpPartnerDefault,
        mesLacpPartnerDistributing,
        mesLacpPartnerCollecting,
        mesLacpPartnerSynchronization,
        mesLacpPartnerAggregation,
        mesLacpPartnerTimeout,
        mesLacpPartnerActivity,
        mesLacpTxLacpPdus,
        mesLacpRxLacpPdus,
        mesLacpInternalIndex,
        mesLacpResetCounters,
        mesLacpIfNo,
        mesLacpTxPort,
        mesLacpUpPortId
}
    STATUS      current
    DESCRIPTION
        "The LACP group objects (26.0)."
    ::= { lumMesGroups 111 }



mesVlanTagRuleGroupV4 OBJECT-GROUP
    OBJECTS {
        mesVlanTagRuleIndex,
        mesVlanTagRuleName,
        mesVlanTagRuleInternalReference,
        mesVlanTagRuleClassificationName,
        mesVlanTagRuleType,
        mesVlanTagRuleOperation,
        mesVlanTagRuleInnerVlanId,
        mesVlanTagRuleInnerPrio,
        mesVlanTagRuleOuterVlanId,
        mesVlanTagRuleOuterPrio,
        mesVlanTagRulePrioAssignment,
        mesVlanTagRuleConfigurePrioAssignment,
        mesVlanTagRuleQueue,
        mesVlanTagRuleRowStatus,
        mesVlanTagRuleInterfaceName}
    STATUS      current
    DESCRIPTION
        "The vlan tag rule objects (26.0)."
    ::= { lumMesGroups 112 }

mesCfmMepGroupV9 OBJECT-GROUP
    OBJECTS {
        mesCfmMepIndex,
        mesCfmMepName,
        mesCfmMepMaid,
        mesCfmMepTxPort,
        mesCfmMepPortName,
        mesCfmMepPrimaryVid,
        mesCfmMepAdminStatus,
        mesCfmMepOperStatus,
        mesCfmMepVlanPriority,
        mesCfmMepType,
        mesCfmMepIdentifier,
        mesCfmMepInternalReference,
        mesCfmMepRDICCM,
        mesCfmMepMACstatus,
        mesCfmMepRemoteCCM,
        mesCfmMepErrorCCM,
        mesCfmMepXconCCM,
        mesCfmMepAis,
        mesCfmMepTransmitLbrStatus,
        mesCfmMepRowStatus,
        mesCfmMepDirection,
        mesCfmMepCcmSeqNumStatus,
        mesCfmMepRemoteCsfLos,
        mesCfmMepRemoteCsfRdi,
        mesCfmMepRemoteCsfFdi,
        mesCfmMepLocalCsfLos,
        mesCfmMepLocalDeviceType,
        mesCfmMepLocalDeviceName,
        mesCfmMepLocalDeviceId,
        mesCfmMepViewFilter,
        mesCfmMepUnexpectedPeriod,
        mesCfmMepUnexpectedMepId,
        mesCfmMepUnexpectedMegLevel,
        mesCfmMepMismerge,
        mesCfmMepNoOfLMs,
        mesCfmMepNoOfDMs,
        mesCfmMepTransmitDmrStatus,
        mesCfmMepTransmitLmrStatus,
        mesCfmMepLmCosAwareness,
        mesCfmMepResourceType,
        mesCfmMepLagId,
        mesCfmMepInterfaceName,
        mesCfmMepIfNo}
    STATUS      deprecated
    DESCRIPTION
        "The MEP objects (26.0)."
    ::= { lumMesGroups 113 }

mesPolicingGroupV3 OBJECT-GROUP
    OBJECTS {
        mesPolicingIndex,
        mesPolicingName,
        mesPolicingRate,
        mesPolicingType,
        mesPolicingInternalReference,
        mesPolicingIdentifier,
        mesPolicingUpId,
        mesPolicingBurstSize2 }
    STATUS      deprecated
    DESCRIPTION
        "The policing objects (26.1)."
    ::= { lumMesGroups 114 }

mesErpGroupV7 OBJECT-GROUP
    OBJECTS {
        mesErpIndex,
        mesErpName,
        mesErpPortLeft,
        mesErpPortRight,
        mesErpAdminStatus,
        mesErpInternalReference,
        mesErpDescr,
        mesErpVlanId,
        mesErpMegLevel,
        mesErpProtLink,
        mesErpGuardTime,
        mesErpHoldOffTime,
        mesErpWtrTime,
        mesErpOamDetectionLeft,
        mesErpOamDetectionRight,
        mesErpStatusLeft,
        mesErpStatusRight,
        mesErpProtState,
        mesErpActiveEvent,
        mesErpRapsReqState,
        mesErpServiceFailure,
        mesErpServiceDegraded,
        mesErpUnexpectedMegLevel,
        mesErpCommunicationFailure,
        mesErpProvisioningMismatch,
        mesErpRowStatus,
        mesErpNodeType,
        mesErpProtectionMode,
        mesErpVersion,
        mesErpMajorName,
        mesErpRingId,
        mesErpRingIndex,
        mesErpOperatorCommand,
        mesErpGroupId,
        mesErpSwitchInformation,
        mesErpTopologyChangePropagation,
        mesErpSubRings,
        mesErpResourceTypeLeft,
        mesErpLagIdLeft,
        mesErpResourceTypeRight,
        mesErpLagIdRight,
        mesErpInterfaceLeft,
        mesErpInterfaceRight,
        mesErpIfNoLeft,
        mesErpTxPortLeft,
        mesErpIfNoRight,
        mesErpTxPortRight,
        mesErpOamDetectionVlanId}
    STATUS      current
    DESCRIPTION
        "The ERP objects (27.0)."
    ::= { lumMesGroups 115 }

mesPortGroupV8 OBJECT-GROUP
    OBJECTS {
        mesPortIndex,
        mesPortName,
        mesPortDescr,
        mesPortSubrack,
        mesPortSlot,
        mesPortTxPort,
        mesPortRxPort,
        mesPortAdminStatus,
        mesPortOperStatus,
        mesPortMtuSize,
        mesPortTagType,
        mesPortNoOfVlans,
        mesPortVlanAware,
        mesPortVlanTagged,
        mesPortVlanUntagged,
        mesPortIngressFiltering,
        mesPortEgressTag,
        mesPortDefaultCeVlanId,
        mesPortAssociateVlan,
        mesPortReleaseVlan,
        mesPortActingAsLine,
        mesPortTrustedPortmask,
        mesPortConfigureTrustedPortmask,
        mesPortMacAddress,
        mesPortLagStatus,
        mesPortLagPortmask,
        mesPortAssociateLag,
        mesPortTxEthUtilization,
        mesPortRxEthUtilization,
        mesPortFlowControlMode,
        mesPortAutoNegotiationMode,
        mesPortAutoNegotiationStatus,
        mesPortLinkDown,
        mesPortLinkFaultRemote,
        mesPortLinkFaultLocal,
        mesPortNoOfShapers,
        mesPortNoOfPolicers,
        mesPortAssociateShaper,
        mesPortReleaseShaper,
        mesPortAssociatePolicer,
        mesPortReleasePolicer,
        mesPortRestartAutoNegotiation,
        mesPortConfigureLine,
        mesPortEtherType,
        mesPortConfigureEtherType,
        mesPortNoOfMirrorSources,
        mesPortMirroring,
        mesPortIngressPushTag,
        mesPortEgressPopTag,
        mesPortDefaultCeVlanPriority,
        mesPortConfigureTagRule,
        mesPortCosProfile,
        mesPortMode,
        mesPortPrioAssignment,
        mesPortConfigurePrioAssignment,
        mesPortNoOfTagRules,
        mesPortObjectProperty,
        mesPortHighBitErrorRate,
        mesPortIdx,
        mesPortIfNo,
        mesPortClientIdx,
        mesPortUpPortId,
        mesPortLagPortmaskIf1,
        mesPortLagPortmaskIf2,
        mesPortLagPortmaskIf3,
        mesPortLagPortmaskIf4,
        mesPortLagPortmaskIf5,
        mesPortLagPortmaskIf6,
        mesPortLagPortmaskIf7,
        mesPortLagPortmaskIf8
        }
    STATUS     deprecated
    DESCRIPTION
        "The port objects (27.0)."
    ::= { lumMesGroups 116 }

mesActionGroupV3 OBJECT-GROUP
    OBJECTS {
        mesActionIndex,
        mesActionName,
        mesActionIdentifier,
        mesActionInternalReference,
        mesActionType,
        mesActionOuterVlanId,
        mesActionPcp,
        mesActionPolicerId,
        mesActionInnerVlanId,
        mesActionQueue,
        mesActionRowStatus,
        mesActionRedirectPort,
        mesActionServiceId,
        mesActionRedirectIfNo,
        mesActionRedirectTxPort}
    STATUS      deprecated
    DESCRIPTION
        "The action objects (27.0)."
    ::= { lumMesGroups 117 }

mesClassGroupV5 OBJECT-GROUP
    OBJECTS {
        mesClassIndex,
        mesClassName,
        mesClassIdentifier,
        mesClassPort,
        mesClassLagId,
        mesClassInternalReference,
        mesClassOuterVlanId,
        mesClassOuterVlanPcp,
        mesClassPrecedence,
        mesClassDaMacAddress,
        mesClassAssociateAction,
        mesClassRowStatus,
        mesClassDaMacAddressMask,
        mesClassDSCP,
        mesClassInnerVlanId,
        mesClassInnerVlanPcp,
        mesClassInnerVlanCfi,
        mesClassOuterVlanCfi,
        mesClassDirection,
        mesClassOuterTpid,
        mesClassInternalClassId,
        mesClassSourceAddressIPV4,
        mesClassSourceMaskIPV4,
        mesClassDestAddressIPV4,
        mesClassDestMaskIPV4,
        mesClassSubrack,
        mesClassSlot,
        mesClassVlanStackStructure,
        mesClassServiceId,
        mesClassIfNo,
        mesClassTxPort}
    STATUS      deprecated
    DESCRIPTION
        "The classification objects (27.0)."
    ::= { lumMesGroups 118 }


mesShapingGroupV3 OBJECT-GROUP
    OBJECTS {
        mesShapingIndex,
        mesShapingName,
        mesShapingRate,
        mesShapingBurstSize,
        mesShapingQueue,
        mesShapingInternalReference,
        mesShapingExcess,
        mesShapingIdentifier,
        mesShapingMinRate,
        mesShapingLocalId}
    STATUS      current
    DESCRIPTION
        "The shaping objects (27.0)."
    ::= { lumMesGroups 119 }

mesPolicingGroupV4 OBJECT-GROUP
    OBJECTS {
        mesPolicingIndex,
        mesPolicingName,
        mesPolicingRate,
        mesPolicingType,
        mesPolicingInternalReference,
        mesPolicingIdentifier,
        mesPolicingUpId,
        mesPolicingBurstSize2,
        mesPolicingId }
    STATUS      current
    DESCRIPTION
        "The policing objects (27.0)."
    ::= { lumMesGroups 120 }

mesBwpGroupV4 OBJECT-GROUP
    OBJECTS {
        mesBwpIndex,
        mesBwpName,
        mesBwpObjectProperty,
        mesBwpCoSIdentifier,
        mesBwpCir,
        mesBwpCbs,
        mesBwpEir,
        mesBwpEbs,
        mesBwpCouplingFlag,
        mesBwpColorMode,
        mesBwpInternalReference,
        mesBwpRowStatus,
        mesBwpServiceId,
        mesBwpPolicerId }
    STATUS      deprecated
    DESCRIPTION
        "The BWP objects v4 (27.0)."
    ::= { lumMesGroups 121 }

mesCfmMepGroupV10 OBJECT-GROUP
    OBJECTS {
        mesCfmMepIndex,
        mesCfmMepName,
        mesCfmMepMaid,
        mesCfmMepTxPort,
        mesCfmMepPortName,
        mesCfmMepPrimaryVid,
        mesCfmMepAdminStatus,
        mesCfmMepOperStatus,
        mesCfmMepVlanPriority,
        mesCfmMepType,
        mesCfmMepIdentifier,
        mesCfmMepInternalReference,
        mesCfmMepRDICCM,
        mesCfmMepMACstatus,
        mesCfmMepRemoteCCM,
        mesCfmMepErrorCCM,
        mesCfmMepXconCCM,
        mesCfmMepAis,
        mesCfmMepTransmitLbrStatus,
        mesCfmMepRowStatus,
        mesCfmMepDirection,
        mesCfmMepCcmSeqNumStatus,
        mesCfmMepRemoteCsfLos,
        mesCfmMepRemoteCsfRdi,
        mesCfmMepRemoteCsfFdi,
        mesCfmMepLocalCsfLos,
        mesCfmMepLocalDeviceType,
        mesCfmMepLocalDeviceName,
        mesCfmMepLocalDeviceId,
        mesCfmMepViewFilter,
        mesCfmMepUnexpectedPeriod,
        mesCfmMepUnexpectedMepId,
        mesCfmMepUnexpectedMegLevel,
        mesCfmMepMismerge,
        mesCfmMepNoOfLMs,
        mesCfmMepNoOfDMs,
        mesCfmMepTransmitDmrStatus,
        mesCfmMepTransmitLmrStatus,
        mesCfmMepLmCosAwareness,
        mesCfmMepResourceType,
        mesCfmMepLagId,
        mesCfmMepInterfaceName,
        mesCfmMepIfNo,
        mesCfmMepLocalId}
    STATUS      deprecated
    DESCRIPTION
        "The MEP objects (28.0)."
    ::= { lumMesGroups 122 }

mesPortGroupV9 OBJECT-GROUP
    OBJECTS {
        mesPortIndex,
        mesPortName,
        mesPortDescr,
        mesPortSubrack,
        mesPortSlot,
        mesPortTxPort,
        mesPortRxPort,
        mesPortAdminStatus,
        mesPortOperStatus,
        mesPortMtuSize,
        mesPortTagType,
        mesPortNoOfVlans,
        mesPortVlanAware,
        mesPortVlanTagged,
        mesPortVlanUntagged,
        mesPortIngressFiltering,
        mesPortEgressTag,
        mesPortDefaultCeVlanId,
        mesPortAssociateVlan,
        mesPortReleaseVlan,
        mesPortActingAsLine,
        mesPortTrustedPortmask,
        mesPortConfigureTrustedPortmask,
        mesPortMacAddress,
        mesPortLagStatus,
        mesPortLagPortmask,
        mesPortAssociateLag,
        mesPortTxEthUtilization,
        mesPortRxEthUtilization,
        mesPortFlowControlMode,
        mesPortAutoNegotiationMode,
        mesPortAutoNegotiationStatus,
        mesPortLinkDown,
        mesPortLinkFaultRemote,
        mesPortLinkFaultLocal,
        mesPortNoOfShapers,
        mesPortNoOfPolicers,
        mesPortAssociateShaper,
        mesPortReleaseShaper,
        mesPortAssociatePolicer,
        mesPortReleasePolicer,
        mesPortRestartAutoNegotiation,
        mesPortConfigureLine,
        mesPortEtherType,
        mesPortConfigureEtherType,
        mesPortNoOfMirrorSources,
        mesPortMirroring,
        mesPortIngressPushTag,
        mesPortEgressPopTag,
        mesPortDefaultCeVlanPriority,
        mesPortConfigureTagRule,
        mesPortCosProfile,
        mesPortMode,
        mesPortPrioAssignment,
        mesPortConfigurePrioAssignment,
        mesPortNoOfTagRules,
        mesPortObjectProperty,
        mesPortHighBitErrorRate,
        mesPortIdx,
        mesPortIfNo,
        mesPortClientIdx,
        mesPortUpPortId,
        mesPortLagPortmaskIf1,
        mesPortLagPortmaskIf2,
        mesPortLagPortmaskIf3,
        mesPortLagPortmaskIf4,
        mesPortLagPortmaskIf5,
        mesPortLagPortmaskIf6,
        mesPortLagPortmaskIf7,
        mesPortLagPortmaskIf8,
        mesPortAutoNegMasterSlaveCfg,
        mesPortAutoNegMasterSlaveStatus
        }
    STATUS     deprecated
    DESCRIPTION
        "The port objects (29.0)."
    ::= { lumMesGroups 123 }

mesGeneralGroupV6 OBJECT-GROUP
    OBJECTS {
        mesGeneralConfigLastChangeTime,
        mesGeneralStateLastChangeTime,
        mesGeneralUniTableSize,
        mesGeneralNniTableSize,
        mesGeneralEvcTableSize,
        mesGeneralBwpTableSize,
        mesGeneralCeEvcMapTableSize,
        mesGeneralMepTableSize,
        mesGeneralMegTableSize,
        mesGeneralEvcBwpMapTableSize,
        mesGeneralPortTableSize,
        mesGeneralVlanMapTableSize,
        mesGeneralMgmtVlanTableSize,
        mesGeneralLagTableSize,
        mesGeneralPolicingTableSize,
        mesGeneralShapingTableSize,
        mesGeneralBwpMapTableSize,
        mesGeneralCosTableSize,
        mesGeneralErrorPropTableSize,
        mesGeneralLagStateLastChangeTime,
        mesGeneralLagConfigLastChangeTime,
        mesGeneralErpStateLastChangeTime,
        mesGeneralErpConfigLastChangeTime,
        mesGeneralMaidStateLastChangeTime,
        mesGeneralMaidConfigLastChangeTime,
        mesGeneralCfmMepStateLastChangeTime,
        mesGeneralCfmMepConfigLastChangeTime,
        mesGeneralVlanMapStateLastChangeTime,
        mesGeneralVlanMapConfigLastChangeTime,
        mesGeneralMgmtVlanStateLastChangeTime,
        mesGeneralMgmtVlanConfigLastChangeTime,
        mesGeneralClassStateLastChangeTime,
        mesGeneralClassConfigLastChangeTime,
        mesGeneralActionStateLastChangeTime,
        mesGeneralActionConfigLastChangeTime,
        mesGeneralPolicyStateLastChangeTime,
        mesGeneralPolicyConfigLastChangeTime,
        mesGeneralErrorPropStateLastChangeTime,
        mesGeneralErrorPropConfigLastChangeTime,
        mesGeneralVlanProtStateLastChangeTime,
        mesGeneralVlanProtConfigLastChangeTime,
        mesGeneralLacpStateLastChangeTime,
        mesGeneralLacpConfigLastChangeTime,
        mesGeneralPolicingStateLastChangeTime,
        mesGeneralPolicingConfigLastChangeTime,
        mesGeneralShapingStateLastChangeTime,
        mesGeneralShapingConfigLastChangeTime,
        mesGeneralCosStateLastChangeTime,
        mesGeneralCosConfigLastChangeTime,
        mesGeneralBwpMapStateLastChangeTime,
        mesGeneralBwpMapConfigLastChangeTime,
        mesGeneralMirroringStateLastChangeTime,
        mesGeneralMirroringConfigLastChangeTime,
        mesGeneralVlanTagRuleStateLastChangeTime,
        mesGeneralVlanTagRuleConfigLastChangeTime,
        mesGeneralVlanTagClassVlanStateLastChangeTime,
        mesGeneralVlanTagClassVlanConfigLastChangeTime,
        mesGeneralCosProfileStateLastChangeTime,
        mesGeneralCosProfileConfigLastChangeTime,
        mesGeneralBwpStateLastChangeTime,
        mesGeneralBwpConfigLastChangeTime,
        mesGeneralMiscStateLastChangeTime,
        mesGeneralMiscConfigLastChangeTime,
        mesGeneralPortStateLastChangeTime,
        mesGeneralPortConfigLastChangeTime}
    STATUS      current
    DESCRIPTION
        "The general objects (29.0) ."
    ::= { lumMesGroups 124 }

mesVlanMapGroupV9 OBJECT-GROUP
    OBJECTS {
        mesVlanMapIndex,
        mesVlanMapName,
        mesVlanMapVlanIdRangeLower,
        mesVlanMapVlanIdRangeUpper,
        mesVlanMapInternalReference,
        mesVlanMapPortmask,
        mesVlanMapConfigurePortMask,
        mesVlanMapLearning,
        mesVlanMapEtherType,
        mesVlanMapRowStatus,
        mesVlanMapDescr,
        mesVlanMapTrustPorts,
        mesVlanMapRings,
        mesVlanMapServiceId,
        mesVlanMapPortmaskIf1,
        mesVlanMapPortmaskIf2,
        mesVlanMapPortmaskIf3,
        mesVlanMapPortmaskIf4,
        mesVlanMapPortmaskIf5,
        mesVlanMapPortmaskIf6,
        mesVlanMapPortmaskIf7,
        mesVlanMapPortmaskIf8,
        mesVlanMapPrepareConfigPortMask,
        mesVlanMapPortmaskIf9,
        mesVlanMapPortmaskIf10,
        mesVlanMapPortmaskIf11,
        mesVlanMapPortmaskIf12,
        mesVlanMapPortmaskIf13,
        mesVlanMapPortmaskIf14,
        mesVlanMapPortmaskIf15,
        mesVlanMapPortmaskIf16,
        mesVlanMapSubrack,
        mesVlanMapSlot
        }
    STATUS     deprecated
    DESCRIPTION
        "The VLAN map objects (30.0)."
    ::= { lumMesGroups 125 }

mesMirroringGroupV3 OBJECT-GROUP
    OBJECTS {
        mesMirroringIndex,
        mesMirroringName,
        mesMirroringDestination,
        mesMirroringDirection,
        mesMirroringConfigureDestination,
        mesMirroringDestInterface,
        mesMirroringDestTxPort,
        mesMirroringIfNo,
        mesMirroringTxPort}
    STATUS      current
    DESCRIPTION
        "The mirroring objects (30.0)."
    ::= { lumMesGroups 126 }

mesClassGroupV6 OBJECT-GROUP
    OBJECTS {
        mesClassIndex,
        mesClassName,
        mesClassIdentifier,
        mesClassPort,
        mesClassLagId,
        mesClassInternalReference,
        mesClassOuterVlanId,
        mesClassOuterVlanPcp,
        mesClassPrecedence,
        mesClassDaMacAddress,
        mesClassAssociateAction,
        mesClassRowStatus,
        mesClassDaMacAddressMask,
        mesClassDSCP,
        mesClassInnerVlanId,
        mesClassInnerVlanPcp,
        mesClassInnerVlanCfi,
        mesClassOuterVlanCfi,
        mesClassDirection,
        mesClassOuterTpid,
        mesClassInternalClassId,
        mesClassSourceAddressIPV4,
        mesClassSourceMaskIPV4,
        mesClassDestAddressIPV4,
        mesClassDestMaskIPV4,
        mesClassSubrack,
        mesClassSlot,
        mesClassVlanStackStructure,
        mesClassServiceId,
        mesClassIfNo,
        mesClassTxPort,
        mesClassAssociateActionAdvanced}
    STATUS      current
    DESCRIPTION
        "The classification objects (30.1)."
    ::= { lumMesGroups 128 }


mesCosProfileGroupV4 OBJECT-GROUP
    OBJECTS {
        mesCosProfileIndex,
        mesCosProfileName,
        mesCosProfilePortmask,
        mesCosProfilePortmaskIf1,
        mesCosProfilePortmaskIf2,
        mesCosProfilePortmaskIf3,
        mesCosProfilePortmaskIf4,
        mesCosProfilePortmaskIf5,
        mesCosProfilePortmaskIf6,
        mesCosProfilePortmaskIf7,
        mesCosProfilePortmaskIf8,
        mesCosProfileScheduler,
        mesCosProfileWeight0,
        mesCosProfileWeight1,
        mesCosProfileWeight2,
        mesCosProfileWeight3,
        mesCosProfileWeight4,
        mesCosProfileWeight5,
        mesCosProfileWeight6,
        mesCosProfileWeight7,
        mesCosProfilePriority0,
        mesCosProfilePriority1,
        mesCosProfilePriority2,
        mesCosProfilePriority3,
        mesCosProfilePriority4,
        mesCosProfilePriority5,
        mesCosProfilePriority6,
        mesCosProfilePriority7,
        mesCosProfileConfigureScheduler,
        mesCosProfileIngressPcpDecoding,
        mesCosProfileIngressDeiDecoding,
        mesCosProfileIngressColor0,
        mesCosProfileIngressColor1,
        mesCosProfileIngressColor2,
        mesCosProfileIngressColor3,
        mesCosProfileIngressColor4,
        mesCosProfileIngressColor5,
        mesCosProfileIngressColor6,
        mesCosProfileIngressColor7,
        mesCosProfileEgressPcpEncoding,
        mesCosProfileEgressDeiEncoding,
        mesCosProfileEgressPcpGreen0,
        mesCosProfileEgressPcpGreen1,
        mesCosProfileEgressPcpGreen2,
        mesCosProfileEgressPcpGreen3,
        mesCosProfileEgressPcpGreen4,
        mesCosProfileEgressPcpGreen5,
        mesCosProfileEgressPcpGreen6,
        mesCosProfileEgressPcpGreen7,
        mesCosProfileEgressPcpYellow0,
        mesCosProfileEgressPcpYellow1,
        mesCosProfileEgressPcpYellow2,
        mesCosProfileEgressPcpYellow3,
        mesCosProfileEgressPcpYellow4,
        mesCosProfileEgressPcpYellow5,
        mesCosProfileEgressPcpYellow6,
        mesCosProfileEgressPcpYellow7
        }
    STATUS      current
    DESCRIPTION
        "The COS Profile objects (31.0)."
    ::= { lumMesGroups 131 }

mesLagGroupV9 OBJECT-GROUP
    OBJECTS {
        mesLagIndex,
        mesLagName,
        mesLagInternalReference,
        mesLagPortmask,
        mesLagMasterIndex,
        mesLagConfigure,
        mesLagHash,
        mesLagIdentifier,
        mesLagRowStatus,
        mesLagLacpEnabled,
        mesLagLacpSystemPriority,
        mesLagLacpPeriod,
        mesLagLacpLinkProtection,
        mesLagDegraded,
        mesLagFailure,
        mesLagLacpMaxNumberOfActiveLinks,
        mesLagNoOfPorts,
        mesLagLacpMinNumberOfActiveLinks,
        mesLagIsMcLag,
        mesLagConfigureTagRule,
        mesLagNoOfTagRules,
        mesLagDescr,
        mesLagAdminStatus,
        mesLagOperStatus,
        mesLagPortmaskIf1,
        mesLagPortmaskIf2,
        mesLagPortmaskIf3,
        mesLagPortmaskIf4,
        mesLagPortmaskIf5,
        mesLagPortmaskIf6,
        mesLagPortmaskIf7,
        mesLagPortmaskIf8,
        mesLagMasterIfNo,
        mesLagMasterTxPort,
        mesLagLocalId,
        mesLagPrepareConfigPortMask,
        mesLagPortmaskIf9,
        mesLagPortmaskIf10,
        mesLagPortmaskIf11,
        mesLagPortmaskIf12,
        mesLagPortmaskIf13,
        mesLagPortmaskIf14,
        mesLagPortmaskIf15,
        mesLagPortmaskIf16,
	mesLagServiceId
         }
    STATUS      current
    DESCRIPTION
        "The LAG group objects v9(31.0)."
    ::= { lumMesGroups 132 }


mesPortGroupV10 OBJECT-GROUP
    OBJECTS {
        mesPortIndex,
        mesPortName,
        mesPortDescr,
        mesPortSubrack,
        mesPortSlot,
        mesPortTxPort,
        mesPortRxPort,
        mesPortAdminStatus,
        mesPortOperStatus,
        mesPortMtuSize,
        mesPortTagType,
        mesPortNoOfVlans,
        mesPortVlanAware,
        mesPortVlanTagged,
        mesPortVlanUntagged,
        mesPortIngressFiltering,
        mesPortEgressTag,
        mesPortDefaultCeVlanId,
        mesPortAssociateVlan,
        mesPortReleaseVlan,
        mesPortActingAsLine,
        mesPortTrustedPortmask,
        mesPortConfigureTrustedPortmask,
        mesPortMacAddress,
        mesPortLagStatus,
        mesPortLagPortmask,
        mesPortAssociateLag,
        mesPortTxEthUtilization,
        mesPortRxEthUtilization,
        mesPortFlowControlMode,
        mesPortAutoNegotiationMode,
        mesPortAutoNegotiationStatus,
        mesPortLinkDown,
        mesPortLinkFaultRemote,
        mesPortLinkFaultLocal,
        mesPortNoOfShapers,
        mesPortNoOfPolicers,
        mesPortAssociateShaper,
        mesPortReleaseShaper,
        mesPortAssociatePolicer,
        mesPortReleasePolicer,
        mesPortRestartAutoNegotiation,
        mesPortConfigureLine,
        mesPortEtherType,
        mesPortConfigureEtherType,
        mesPortNoOfMirrorSources,
        mesPortMirroring,
        mesPortIngressPushTag,
        mesPortEgressPopTag,
        mesPortDefaultCeVlanPriority,
        mesPortConfigureTagRule,
        mesPortCosProfile,
        mesPortMode,
        mesPortPrioAssignment,
        mesPortConfigurePrioAssignment,
        mesPortNoOfTagRules,
        mesPortObjectProperty,
        mesPortHighBitErrorRate,
        mesPortIdx,
        mesPortIfNo,
        mesPortClientIdx,
        mesPortUpPortId,
        mesPortLagPortmaskIf1,
        mesPortLagPortmaskIf2,
        mesPortLagPortmaskIf3,
        mesPortLagPortmaskIf4,
        mesPortLagPortmaskIf5,
        mesPortLagPortmaskIf6,
        mesPortLagPortmaskIf7,
        mesPortLagPortmaskIf8,
        mesPortAutoNegMasterSlaveCfg,
        mesPortAutoNegMasterSlaveStatus,
        mesPortLagPortmaskIf9,
        mesPortLagPortmaskIf10,
        mesPortLagPortmaskIf11,
        mesPortLagPortmaskIf12,
        mesPortLagPortmaskIf13,
        mesPortLagPortmaskIf14,
        mesPortLagPortmaskIf15,
        mesPortLagPortmaskIf16,
        mesPortCreateVlanTagClass,
        mesPortCreateTagRuleWoutClass
        }
    STATUS     deprecated
    DESCRIPTION
        "The port objects (30.1)."
    ::= { lumMesGroups 130 }

mesVlanTagClassVlanGroupV5 OBJECT-GROUP
    OBJECTS {
        mesVlanTagClassVlanIndex,
        mesVlanTagClassVlanName,
        mesVlanTagClassVlanTxPort,
        mesVlanTagClassVlanInternalReference,
        mesVlanTagClassVlanRuleName,
        mesVlanTagClassVlanRuleIndex,
        mesVlanTagClassVlanOuterVlanId,
        mesVlanTagClassVlanLagIndex,
        mesVlanTagClassVlanIfNo,
        mesVlanTagClassVlanLocalId,
        mesVlanTagClassVlanRowStatus}
    STATUS      current
    DESCRIPTION
        "The vlan tag classification vlan objects (30.1)."
    ::= { lumMesGroups 133 }

mesActionGroupV4 OBJECT-GROUP
    OBJECTS {
        mesActionIndex,
        mesActionName,
        mesActionIdentifier,
        mesActionInternalReference,
        mesActionType,
        mesActionOuterVlanId,
        mesActionPcp,
        mesActionPolicerId,
        mesActionInnerVlanId,
        mesActionQueue,
        mesActionRowStatus,
        mesActionRedirectPort,
        mesActionServiceId,
        mesActionRedirectIfNo,
        mesActionRedirectTxPort,
        mesActionClassId,
	mesActionSubrack,
	mesActionSlot}
    STATUS      current
    DESCRIPTION
        "The action objects (30.1)."
    ::= { lumMesGroups 134 }

mesErrorPropGroupV2 OBJECT-GROUP
    OBJECTS {
        mesErrorPropIndex,
        mesErrorPropName,
        mesErrorPropDescr,
        mesErrorPropInternalReference,
        mesErrorPropAdminStatus,
        mesErrorPropOperStatus,
        mesErrorPropState,
        mesErrorPropTriggerType,
        mesErrorPropTriggerObject,
        mesErrorPropTriggerPortIndex,
        mesErrorPropTriggerMepIndex,
        mesErrorPropActionType,
        mesErrorPropActionObject,
        mesErrorPropActionPortIndex,
        mesErrorPropActionMepIndex,
        mesErrorPropHoldOffTimer,
        mesErrorPropRowStatus,
        mesErrorPropFault,
	mesErrorPropSubrack,
	mesErrorPropSlot,
	mesErrorPropServiceId}
    STATUS      current
    DESCRIPTION
        "The Error Prop objects (30.1)."
    ::= { lumMesGroups 135 }

mesBwpGroupV5 OBJECT-GROUP
    OBJECTS {
        mesBwpIndex,
        mesBwpName,
        mesBwpObjectProperty,
        mesBwpCoSIdentifier,
        mesBwpCir,
        mesBwpCbs,
        mesBwpEir,
        mesBwpEbs,
        mesBwpCouplingFlag,
        mesBwpColorMode,
        mesBwpInternalReference,
        mesBwpRowStatus,
        mesBwpServiceId,
        mesBwpPolicerId,
	mesBwpSubrack,
	mesBwpSlot}
    STATUS      current
    DESCRIPTION
        "The BWP objects v5 (30.1)."
    ::= { lumMesGroups 136 }

mesPortGroupV11 OBJECT-GROUP
    OBJECTS {
        mesPortIndex,
        mesPortName,
        mesPortDescr,
        mesPortSubrack,
        mesPortSlot,
        mesPortTxPort,
        mesPortRxPort,
        mesPortAdminStatus,
        mesPortOperStatus,
        mesPortMtuSize,
        mesPortTagType,
        mesPortNoOfVlans,
        mesPortVlanAware,
        mesPortVlanTagged,
        mesPortVlanUntagged,
        mesPortIngressFiltering,
        mesPortEgressTag,
        mesPortDefaultCeVlanId,
        mesPortAssociateVlan,
        mesPortReleaseVlan,
        mesPortActingAsLine,
        mesPortTrustedPortmask,
        mesPortConfigureTrustedPortmask,
        mesPortMacAddress,
        mesPortLagStatus,
        mesPortLagPortmask,
        mesPortAssociateLag,
        mesPortTxEthUtilization,
        mesPortRxEthUtilization,
        mesPortFlowControlMode,
        mesPortAutoNegotiationMode,
        mesPortAutoNegotiationStatus,
        mesPortLinkDown,
        mesPortLinkFaultRemote,
        mesPortLinkFaultLocal,
        mesPortNoOfShapers,
        mesPortNoOfPolicers,
        mesPortAssociateShaper,
        mesPortReleaseShaper,
        mesPortAssociatePolicer,
        mesPortReleasePolicer,
        mesPortRestartAutoNegotiation,
        mesPortConfigureLine,
        mesPortEtherType,
        mesPortConfigureEtherType,
        mesPortNoOfMirrorSources,
        mesPortMirroring,
        mesPortIngressPushTag,
        mesPortEgressPopTag,
        mesPortDefaultCeVlanPriority,
        mesPortConfigureTagRule,
        mesPortCosProfile,
        mesPortMode,
        mesPortPrioAssignment,
        mesPortConfigurePrioAssignment,
        mesPortNoOfTagRules,
        mesPortObjectProperty,
        mesPortHighBitErrorRate,
        mesPortIdx,
        mesPortIfNo,
        mesPortClientIdx,
        mesPortUpPortId,
        mesPortLagPortmaskIf1,
        mesPortLagPortmaskIf2,
        mesPortLagPortmaskIf3,
        mesPortLagPortmaskIf4,
        mesPortLagPortmaskIf5,
        mesPortLagPortmaskIf6,
        mesPortLagPortmaskIf7,
        mesPortLagPortmaskIf8,
        mesPortAutoNegMasterSlaveCfg,
        mesPortAutoNegMasterSlaveStatus,
        mesPortLagPortmaskIf9,
        mesPortLagPortmaskIf10,
        mesPortLagPortmaskIf11,
        mesPortLagPortmaskIf12,
        mesPortLagPortmaskIf13,
        mesPortLagPortmaskIf14,
        mesPortLagPortmaskIf15,
        mesPortLagPortmaskIf16,
        mesPortCreateVlanTagClass,
        mesPortCreateTagRuleWoutClass,
        mesPortTrustedPortmaskIf2,
        mesPortTrustedPortmaskIf3,
        mesPortTrustedPortmaskIf4,
        mesPortTrustedPortmaskIf5,
        mesPortTrustedPortmaskIf6,
        mesPortTrustedPortmaskIf7,
        mesPortTrustedPortmaskIf8,
        mesPortTrustedPortmaskIf9,
        mesPortTrustedPortmaskIf10,
        mesPortTrustedPortmaskIf11,
        mesPortTrustedPortmaskIf12,
        mesPortTrustedPortmaskIf13,
        mesPortTrustedPortmaskIf14,
        mesPortTrustedPortmaskIf15,
        mesPortTrustedPortmaskIf16,
	mesPortServiceId
        }
    STATUS     current
    DESCRIPTION
        "The port objects (31.1)."
    ::= { lumMesGroups 137 }


    mesCfmMepGroupV11 OBJECT-GROUP
    OBJECTS {
        mesCfmMepIndex,
        mesCfmMepName,
        mesCfmMepMaid,
        mesCfmMepTxPort,
        mesCfmMepPortName,
        mesCfmMepPrimaryVid,
        mesCfmMepAdminStatus,
        mesCfmMepOperStatus,
        mesCfmMepVlanPriority,
        mesCfmMepType,
        mesCfmMepIdentifier,
        mesCfmMepInternalReference,
        mesCfmMepRDICCM,
        mesCfmMepMACstatus,
        mesCfmMepRemoteCCM,
        mesCfmMepErrorCCM,
        mesCfmMepXconCCM,
        mesCfmMepAis,
        mesCfmMepTransmitLbrStatus,
        mesCfmMepRowStatus,
        mesCfmMepDirection,
        mesCfmMepCcmSeqNumStatus,
        mesCfmMepRemoteCsfLos,
        mesCfmMepRemoteCsfRdi,
        mesCfmMepRemoteCsfFdi,
        mesCfmMepLocalCsfLos,
        mesCfmMepLocalDeviceType,
        mesCfmMepLocalDeviceName,
        mesCfmMepLocalDeviceId,
        mesCfmMepViewFilter,
        mesCfmMepUnexpectedPeriod,
        mesCfmMepUnexpectedMepId,
        mesCfmMepUnexpectedMegLevel,
        mesCfmMepMismerge,
        mesCfmMepNoOfLMs,
        mesCfmMepNoOfDMs,
        mesCfmMepTransmitDmrStatus,
        mesCfmMepTransmitLmrStatus,
        mesCfmMepLmCosAwareness,
        mesCfmMepResourceType,
        mesCfmMepLagId,
        mesCfmMepInterfaceName,
        mesCfmMepIfNo,
        mesCfmMepLocalId,
	mesCfmMepSubrack,
	mesCfmMepSlot,
	mesCfmMepServiceId}
    STATUS      current
    DESCRIPTION
        "The MEP objects (30.1)."
    ::= { lumMesGroups 138 }

mesVlanMapGroupV10 OBJECT-GROUP
    OBJECTS {
        mesVlanMapIndex,
        mesVlanMapName,
        mesVlanMapVlanIdRangeLower,
        mesVlanMapVlanIdRangeUpper,
        mesVlanMapInternalReference,
        mesVlanMapPortmask,
        mesVlanMapConfigurePortMask,
        mesVlanMapLearning,
        mesVlanMapEtherType,
        mesVlanMapRowStatus,
        mesVlanMapDescr,
        mesVlanMapTrustPorts,
        mesVlanMapRings,
        mesVlanMapServiceId,
        mesVlanMapPortmaskIf1,
        mesVlanMapPortmaskIf2,
        mesVlanMapPortmaskIf3,
        mesVlanMapPortmaskIf4,
        mesVlanMapPortmaskIf5,
        mesVlanMapPortmaskIf6,
        mesVlanMapPortmaskIf7,
        mesVlanMapPortmaskIf8,
        mesVlanMapPrepareConfigPortMask,
        mesVlanMapPortmaskIf9,
        mesVlanMapPortmaskIf10,
        mesVlanMapPortmaskIf11,
        mesVlanMapPortmaskIf12,
        mesVlanMapPortmaskIf13,
        mesVlanMapPortmaskIf14,
        mesVlanMapPortmaskIf15,
        mesVlanMapPortmaskIf16,
        mesVlanMapSubrack,
        mesVlanMapSlot,
        mesVlanMapMacLearningLimit
        }
    STATUS    current
    DESCRIPTION
        "The VLAN map objects (32.0)."
    ::= { lumMesGroups 139 }

-- ----------------------------------------------------
-- Compliance
-- ----------------------------------------------------

lumMesBasicComplV1 MODULE-COMPLIANCE
    STATUS      deprecated
    DESCRIPTION
        "Basic implementation requirements for the MES MIB (9.0)."
    MODULE
        MANDATORY-GROUPS {
                mesGeneralGroup,
                mesUniGroup,
                mesNniGroup,
                mesEvcGroup,
                mesCeEvcMapGroup,
                mesBwpGroup }
    ::= { lumMesCompl 1 }

lumMesBasicComplV2 MODULE-COMPLIANCE
    STATUS      deprecated
    DESCRIPTION
        "Basic implementation requirements for the MES MIB (10.0)."
    MODULE
        MANDATORY-GROUPS {
                mesGeneralGroup,
                mesUniGroupV2,
                mesNniGroup,
                mesEvcGroupV2,
                mesCeEvcMapGroupV2,
                mesBwpGroupV2,
                mesQProfileGroup }
    ::= { lumMesCompl 2 }

lumMesBasicComplV3 MODULE-COMPLIANCE
    STATUS      deprecated
    DESCRIPTION
        "Basic implementation requirements for the MES MIB (11.0)."
    MODULE
        MANDATORY-GROUPS {
                mesGeneralGroupV2,
                mesUniGroupV3,
                mesNniGroupV2,
                mesEvcGroupV3,
                mesCeEvcMapGroupV2,
                mesBwpGroupV2,
                mesQProfileGroup,
                mesMepGroup,
                mesMegGroup,
                mesMiscGroup,
                mesEvcBwpMapGroup }
    ::= { lumMesCompl 3 }

lumMesBasicComplV4 MODULE-COMPLIANCE
    STATUS      deprecated
    DESCRIPTION
        "Basic implementation requirements for the MES MIB (12.0)."
    MODULE
        MANDATORY-GROUPS {
                mesGeneralGroupV3,
                mesUniGroupV3,
                mesNniGroupV2,
                mesEvcGroupV3,
                mesCeEvcMapGroupV2,
                mesBwpGroupV2,
                mesQProfileGroup,
                mesMepGroup,
                mesMegGroup,
                mesMiscGroupV2,
                mesEvcBwpMapGroup,
                mesPortGroup,
                mesVlanMapGroup,
                mesMgmtVlanGroup,
                mesLagGroup }
    ::= { lumMesCompl 4 }

lumMesBasicComplV5 MODULE-COMPLIANCE
    STATUS      deprecated
    DESCRIPTION
        "Basic implementation requirements for the MES MIB (13.0)."
    MODULE
        MANDATORY-GROUPS {
                mesGeneralGroupV3,
                mesUniGroupV4,
                mesNniGroupV3,
                mesEvcGroupV3,
                mesCeEvcMapGroupV2,
                mesBwpGroupV2,
                mesQProfileGroup,
                mesMepGroup,
                mesMegGroup,
                mesMiscGroupV2,
                mesEvcBwpMapGroup,
                mesPortGroupV2,
                mesVlanMapGroup,
                mesBwpMapGroup,
                mesMgmtVlanGroup,
                mesLagGroup,
                mesPolicingGroup,
                mesShapingGroup,
                mesCosGroup }
    ::= { lumMesCompl 5 }

lumMesBasicComplV6 MODULE-COMPLIANCE
    STATUS      deprecated
    DESCRIPTION
        "Basic implementation requirements for the MES MIB (14.0)."
    MODULE
        MANDATORY-GROUPS {
                mesGeneralGroupV3,
                mesUniGroupV4,
                mesNniGroupV3,
                mesEvcGroupV3,
                mesCeEvcMapGroupV2,
                mesBwpGroupV2,
                mesQProfileGroup,
                mesMepGroup,
                mesMegGroup,
                mesMiscGroupV3,
                mesEvcBwpMapGroup,
                mesPortGroupV3,
                mesVlanMapGroupV2,
                mesBwpMapGroup,
                mesMgmtVlanGroup,
                mesLagGroup,
                mesPolicingGroup,
                mesShapingGroup,
                mesCosGroup,
                mesMirroringGroup,
                mesVlanTagRuleGroup,
                mesVlanTagClassVlanGroup,
                mesCosProfileGroup }
    ::= { lumMesCompl 6 }

lumMesBasicComplV7 MODULE-COMPLIANCE
    STATUS      deprecated
    DESCRIPTION
        "Basic implementation requirements for the MES MIB (15.0)."
    MODULE
        MANDATORY-GROUPS {
                mesGeneralGroupV3,
                mesUniGroupV4,
                mesNniGroupV3,
                mesEvcGroupV3,
                mesCeEvcMapGroupV2,
                mesBwpGroupV2,
                mesQProfileGroup,
                mesMepGroup,
                mesMegGroup,
                mesMiscGroupV4,
                mesEvcBwpMapGroup,
                mesPortGroupV4,
                mesVlanMapGroupV3,
                mesBwpMapGroup,
                mesMgmtVlanGroup,
                mesLagGroupV2,
                mesPolicingGroup,
                mesShapingGroup,
                mesCosGroup,
                mesMirroringGroupV2,
                mesVlanTagRuleGroupV2,
                mesVlanTagClassVlanGroupV2,
                mesCosProfileGroup,
                mesMaidGroup,
                mesCfmMepGroup,
                mesErpGroup }
    ::= { lumMesCompl 7 }

lumMesBasicComplV8 MODULE-COMPLIANCE
    STATUS      deprecated
    DESCRIPTION
        "Basic implementation requirements for the MES MIB (15.0)."
    MODULE
        MANDATORY-GROUPS {
                mesGeneralGroupV3,
                mesUniGroupV4,
                mesNniGroupV3,
                mesEvcGroupV3,
                mesCeEvcMapGroupV2,
                mesBwpGroupV2,
                mesQProfileGroup,
                mesMepGroup,
                mesMegGroup,
                mesMiscGroupV4,
                mesEvcBwpMapGroup,
                mesPortGroupV4,
                mesVlanMapGroupV3,
                mesBwpMapGroup,
                mesMgmtVlanGroup,
                mesLagGroupV2,
                mesPolicingGroup,
                mesShapingGroupV2,
                mesCosGroup,
                mesMirroringGroupV2,
                mesVlanTagRuleGroupV2,
                mesVlanTagClassVlanGroupV2,
                mesCosProfileGroup,
                mesMaidGroup,
                mesCfmMepGroup,
                mesErpGroup }
    ::= { lumMesCompl 8 }

lumMesBasicComplV9 MODULE-COMPLIANCE
    STATUS      deprecated
    DESCRIPTION
        "Basic implementation requirements for the MES MIB (16.0)."
    MODULE
        MANDATORY-GROUPS {
                mesGeneralGroupV3,
                mesUniGroupV4,
                mesNniGroupV3,
                mesEvcGroupV3,
                mesCeEvcMapGroupV2,
                mesBwpGroupV2,
                mesQProfileGroup,
                mesMepGroup,
                mesMegGroup,
                mesMiscGroupV5,
                mesEvcBwpMapGroup,
                mesPortGroupV5,
                mesVlanMapGroupV4,
                mesBwpMapGroupV2,
                mesMgmtVlanGroup,
                mesLagGroupV3,
                mesPolicingGroup,
                mesShapingGroupV2,
                mesCosGroup,
                mesMirroringGroupV2,
                mesVlanTagRuleGroupV3,
                mesVlanTagClassVlanGroupV2,
                mesCosProfileGroupV2,
                mesMaidGroupV2,
                mesCfmMepGroupV2,
                mesErpGroupV2,
                mesClassGroup,
                mesActionGroup,
                mesPolicyGroup }
    ::= { lumMesCompl 9 }

lumMesBasicComplV10 MODULE-COMPLIANCE
    STATUS      deprecated
    DESCRIPTION
        "Basic implementation requirements for the MES MIB (17.0)."
    MODULE
        MANDATORY-GROUPS {
                mesGeneralGroupV3,
                mesBwpGroupV2,
                mesMiscGroupV6,
                mesPortGroupV5,
                mesVlanMapGroupV5,
                mesBwpMapGroupV2,
                mesMgmtVlanGroup,
                mesLagGroupV3,
                mesPolicingGroup,
                mesShapingGroupV2,
                mesCosGroup,
                mesMirroringGroupV2,
                mesVlanTagRuleGroupV3,
                mesVlanTagClassVlanGroupV2,
                mesCosProfileGroupV2,
                mesMaidGroupV2,
                mesCfmMepGroupV2,
                mesErpGroupV2,
                mesClassGroup,
                mesActionGroup,
                mesPolicyGroup }
    ::= { lumMesCompl 10}

lumMesBasicComplV11 MODULE-COMPLIANCE
    STATUS      deprecated
    DESCRIPTION
        "Basic implementation requirements for the MES MIB (18.0)."
    MODULE
        MANDATORY-GROUPS {
                mesGeneralGroupV3,
                mesBwpGroupV2,
                mesMiscGroupV7,
                mesPortGroupV6,
                mesVlanMapGroupV5,
                mesBwpMapGroupV2,
                mesMgmtVlanGroup,
                mesLagGroupV3,
                mesPolicingGroup,
                mesShapingGroupV2,
                mesCosGroup,
                mesMirroringGroupV2,
                mesVlanTagRuleGroupV3,
                mesVlanTagClassVlanGroupV2,
                mesCosProfileGroupV2,
                mesMaidGroupV3,
                mesCfmMepGroupV3,
                mesErpGroupV2,
                mesClassGroupV2,
                mesActionGroup,
                mesPolicyGroup }
    ::= { lumMesCompl 11}

lumMesBasicComplV12 MODULE-COMPLIANCE
    STATUS      deprecated
    DESCRIPTION
        "Basic implementation requirements for the MES MIB (19.0)."
    MODULE
        MANDATORY-GROUPS {
                mesGeneralGroupV3,
                mesBwpGroupV2,
                mesMiscGroupV7,
                mesPortGroupV6,
                mesVlanMapGroupV5,
                mesBwpMapGroupV2,
                mesMgmtVlanGroupV2,
                mesLagGroupV3,
                mesPolicingGroup,
                mesShapingGroupV2,
                mesCosGroup,
                mesMirroringGroupV2,
                mesVlanTagRuleGroupV3,
                mesVlanTagClassVlanGroupV2,
                mesCosProfileGroupV2,
                mesMaidGroupV3,
                mesCfmMepGroupV3,
                mesErpGroupV2,
                mesClassGroupV2,
                mesActionGroup,
                mesPolicyGroup }
    ::= { lumMesCompl 12}

lumMesBasicComplV13 MODULE-COMPLIANCE
    STATUS      deprecated
    DESCRIPTION
        "Basic implementation requirements for the MES MIB (21.0)."
    MODULE
        MANDATORY-GROUPS {
                mesGeneralGroupV3,
                mesBwpGroupV2,
                mesMiscGroupV8,
                mesPortGroupV6,
                mesVlanMapGroupV5,
                mesBwpMapGroupV2,
                mesMgmtVlanGroupV2,
                mesLagGroupV3,
                mesPolicingGroup,
                mesShapingGroupV2,
                mesCosGroup,
                mesMirroringGroupV2,
                mesVlanTagRuleGroupV3,
                mesVlanTagClassVlanGroupV2,
                mesCosProfileGroupV2,
                mesMaidGroupV4,
                mesCfmMepGroupV4,
                mesErpGroupV2,
                mesClassGroupV2,
                mesActionGroup,
                mesPolicyGroup,
                mesErrorPropGroup }
    ::= { lumMesCompl 13}

lumMesBasicComplV14 MODULE-COMPLIANCE
    STATUS      deprecated
    DESCRIPTION
        "Basic implementation requirements for the MES MIB (22.0)."
    MODULE
        MANDATORY-GROUPS {
                mesGeneralGroupV3,
                mesBwpGroupV2,
                mesMiscGroupV9,
                mesPortGroupV6,
                mesVlanMapGroupV6,
                mesBwpMapGroupV2,
                mesMgmtVlanGroupV3,
                mesLagGroupV3,
                mesPolicingGroup,
                mesShapingGroupV2,
                mesCosGroup,
                mesMirroringGroupV2,
                mesVlanTagRuleGroupV3,
                mesVlanTagClassVlanGroupV2,
                mesCosProfileGroupV2,
                mesMaidGroupV4,
                mesCfmMepGroupV5,
                mesErpGroupV3,
                mesClassGroupV3,
                mesActionGroup,
                mesPolicyGroup,
                mesErrorPropGroup,
                mesVlanProtV1}
    ::= { lumMesCompl 14}

lumMesBasicComplV15 MODULE-COMPLIANCE
    STATUS      deprecated
    DESCRIPTION
        "Basic implementation requirements for the MES MIB (23.0)."
    MODULE
        MANDATORY-GROUPS {
                mesGeneralGroupV3,
                mesBwpGroupV3,
                mesMiscGroupV9,
                mesPortGroupV6,
                mesVlanMapGroupV7,
                mesBwpMapGroupV2,
                mesMgmtVlanGroupV3,
                mesLagGroupV4,
                mesPolicingGroup,
                mesShapingGroupV2,
                mesCosGroup,
                mesMirroringGroupV2,
                mesVlanTagRuleGroupV3,
                mesVlanTagClassVlanGroupV2,
                mesCosProfileGroupV2,
                mesMaidGroupV4,
                mesCfmMepGroupV6,
                mesErpGroupV3,
                mesClassGroupV4,
                mesActionGroupV2,
                mesPolicyGroupV2,
                mesErrorPropGroup,
                mesVlanProtV1,
                mesLacpGroup}
    ::= { lumMesCompl 15}

lumMesBasicComplV16 MODULE-COMPLIANCE
    STATUS      deprecated
    DESCRIPTION
        "Basic implementation requirements for the MES MIB (23.1)."
    MODULE
        MANDATORY-GROUPS {
                mesGeneralGroupV3,
                mesBwpGroupV3,
                mesMiscGroupV9,
                mesPortGroupV6,
                mesVlanMapGroupV7,
                mesBwpMapGroupV2,
                mesMgmtVlanGroupV3,
                mesLagGroupV5,
                mesPolicingGroup,
                mesShapingGroupV2,
                mesCosGroup,
                mesMirroringGroupV2,
                mesVlanTagRuleGroupV3,
                mesVlanTagClassVlanGroupV2,
                mesCosProfileGroupV2,
                mesMaidGroupV4,
                mesCfmMepGroupV6,
                mesErpGroupV3,
                mesClassGroupV4,
                mesActionGroupV2,
                mesPolicyGroupV2,
                mesErrorPropGroup,
                mesVlanProtV1,
                mesLacpGroup}
    ::= { lumMesCompl 16}

lumMesBasicComplV17 MODULE-COMPLIANCE
    STATUS      deprecated
    DESCRIPTION
        "Basic implementation requirements for the MES MIB (24.0)."
    MODULE
        MANDATORY-GROUPS {
                mesGeneralGroupV3,
                mesBwpGroupV3,
                mesMiscGroupV9,
                mesPortGroupV6,
                mesVlanMapGroupV7,
                mesBwpMapGroupV2,
                mesMgmtVlanGroupV3,
                mesLagGroupV6,
                mesPolicingGroup,
                mesShapingGroupV2,
                mesCosGroup,
                mesMirroringGroupV2,
                mesVlanTagRuleGroupV3,
                mesVlanTagClassVlanGroupV2,
                mesCosProfileGroupV2,
                mesMaidGroupV4,
                mesCfmMepGroupV7,
                mesErpGroupV4,
                mesClassGroupV4,
                mesActionGroupV2,
                mesPolicyGroupV2,
                mesErrorPropGroup,
                mesVlanProtV1,
                mesLacpGroup}
    ::= { lumMesCompl 17}

 lumMesBasicComplV18 MODULE-COMPLIANCE
    STATUS      deprecated
    DESCRIPTION
        "Basic implementation requirements for the MES MIB (25.0)."
    MODULE
        MANDATORY-GROUPS {
                mesGeneralGroupV5,
                mesBwpGroupV3,
                mesMiscGroupV9,
                mesPortGroupV6,
                mesVlanMapGroupV7,
                mesBwpMapGroupV2,
                mesMgmtVlanGroupV3,
                mesLagGroupV7,
                mesPolicingGroup,
                mesShapingGroupV2,
                mesCosGroup,
                mesMirroringGroupV2,
                mesVlanTagRuleGroupV3,
                mesVlanTagClassVlanGroupV3,
                mesCosProfileGroupV2,
                mesMaidGroupV5,
                mesCfmMepGroupV8,
                mesErpGroupV5,
                mesClassGroupV4,
                mesActionGroupV2,
                mesPolicyGroupV2,
                mesErrorPropGroup,
                mesVlanProtV1,
                mesLacpGroup}
    ::= { lumMesCompl 18}

lumMesBasicComplV22 MODULE-COMPLIANCE
    STATUS      deprecated
    DESCRIPTION
        "Basic implementation requirements for the MES MIB (26.0)."
    MODULE
        MANDATORY-GROUPS {
                mesGeneralGroupV5,
                mesBwpGroupV3,
                mesMiscGroupV9,
                mesPortGroupV7,
                mesVlanMapGroupV8,
                mesBwpMapGroupV2,
                mesMgmtVlanGroupV4,
                mesLagGroupV8,
                mesPolicingGroupV2,
                mesShapingGroupV2,
                mesCosGroup,
                mesMirroringGroupV2,
                mesVlanTagRuleGroupV4,
                mesVlanTagClassVlanGroupV4,
                mesCosProfileGroupV3,
                mesMaidGroupV5,
                mesCfmMepGroupV9,
                mesErpGroupV6,
                mesClassGroupV4,
                mesActionGroupV2,
                mesPolicyGroupV2,
                mesErrorPropGroup,
                mesVlanProtV1,
                mesLacpGroupV1}
    ::= { lumMesCompl 22}

lumMesBasicComplV23 MODULE-COMPLIANCE
    STATUS      deprecated
    DESCRIPTION
        "Basic implementation requirements for the MES MIB (26.1)."
    MODULE
        MANDATORY-GROUPS {
                mesGeneralGroupV5,
                mesBwpGroupV3,
                mesMiscGroupV9,
                mesPortGroupV7,
                mesVlanMapGroupV8,
                mesBwpMapGroupV2,
                mesMgmtVlanGroupV4,
                mesLagGroupV8,
                mesPolicingGroupV3,
                mesShapingGroupV2,
                mesCosGroup,
                mesMirroringGroupV2,
                mesVlanTagRuleGroupV4,
                mesVlanTagClassVlanGroupV4,
                mesCosProfileGroupV3,
                mesMaidGroupV5,
                mesCfmMepGroupV9,
                mesErpGroupV6,
                mesClassGroupV4,
                mesActionGroupV2,
                mesPolicyGroupV2,
                mesErrorPropGroup,
                mesVlanProtV1,
                mesLacpGroupV1}
    ::= { lumMesCompl 23}

lumMesBasicComplV24 MODULE-COMPLIANCE
    STATUS      deprecated
    DESCRIPTION
        "Basic implementation requirements for the MES MIB (27.0)."
    MODULE
        MANDATORY-GROUPS {
                mesGeneralGroupV5,
                mesBwpGroupV4,
                mesMiscGroupV9,
                mesPortGroupV8,
                mesVlanMapGroupV8,
                mesBwpMapGroupV2,
                mesMgmtVlanGroupV4,
                mesLagGroupV8,
                mesPolicingGroupV4,
                mesShapingGroupV3,
                mesCosGroup,
                mesMirroringGroupV2,
                mesVlanTagRuleGroupV4,
                mesVlanTagClassVlanGroupV4,
                mesCosProfileGroupV3,
                mesMaidGroupV5,
                mesCfmMepGroupV9,
                mesErpGroupV7,
                mesClassGroupV5,
                mesActionGroupV3,
                mesPolicyGroupV2,
                mesErrorPropGroup,
                mesVlanProtV1,
                mesLacpGroupV1}
    ::= { lumMesCompl 24}

 lumMesBasicComplV25 MODULE-COMPLIANCE
    STATUS      deprecated
    DESCRIPTION
        "Basic implementation requirements for the MES MIB (28.0)."
    MODULE
        MANDATORY-GROUPS {
                mesGeneralGroupV5,
                mesBwpGroupV4,
                mesMiscGroupV9,
                mesPortGroupV8,
                mesVlanMapGroupV8,
                mesBwpMapGroupV2,
                mesMgmtVlanGroupV4,
                mesLagGroupV8,
                mesPolicingGroupV4,
                mesShapingGroupV3,
                mesCosGroup,
                mesMirroringGroupV2,
                mesVlanTagRuleGroupV4,
                mesVlanTagClassVlanGroupV4,
                mesCosProfileGroupV3,
                mesMaidGroupV5,
                mesCfmMepGroupV10,
                mesErpGroupV7,
                mesClassGroupV5,
                mesActionGroupV3,
                mesPolicyGroupV2,
                mesErrorPropGroup,
                mesVlanProtV1,
                mesLacpGroupV1}
    ::= { lumMesCompl 25}

 lumMesBasicComplV26 MODULE-COMPLIANCE
    STATUS      deprecated
    DESCRIPTION
        "Basic implementation requirements for the MES MIB (29.0)."
    MODULE
        MANDATORY-GROUPS {
                mesGeneralGroupV6,
                mesBwpGroupV4,
                mesMiscGroupV9,
                mesPortGroupV9,
                mesVlanMapGroupV8,
                mesBwpMapGroupV2,
                mesMgmtVlanGroupV4,
                mesLagGroupV8,
                mesPolicingGroupV4,
                mesShapingGroupV3,
                mesCosGroup,
                mesMirroringGroupV2,
                mesVlanTagRuleGroupV4,
                mesVlanTagClassVlanGroupV4,
                mesCosProfileGroupV3,
                mesMaidGroupV5,
                mesCfmMepGroupV10,
                mesErpGroupV7,
                mesClassGroupV5,
                mesActionGroupV3,
                mesPolicyGroupV2,
                mesErrorPropGroup,
                mesVlanProtV1,
                mesLacpGroupV1}
    ::= { lumMesCompl 26}

lumMesBasicComplV27 MODULE-COMPLIANCE
    STATUS      deprecated
    DESCRIPTION
        "Basic implementation requirements for the MES MIB (30.1)."
    MODULE
        MANDATORY-GROUPS {
                mesGeneralGroupV6,
                mesBwpGroupV4,
                mesMiscGroupV9,
                mesPortGroupV9,
                mesVlanMapGroupV9,
                mesBwpMapGroupV2,
                mesMgmtVlanGroupV4,
                mesLagGroupV8,
                mesPolicingGroupV4,
                mesShapingGroupV3,
                mesCosGroup,
                mesMirroringGroupV3,
                mesVlanTagRuleGroupV4,
                mesVlanTagClassVlanGroupV4,
                mesCosProfileGroupV3,
                mesMaidGroupV5,
                mesCfmMepGroupV10,
                mesErpGroupV7,
                mesClassGroupV5,
                mesActionGroupV3,
                mesPolicyGroupV2,
                mesErrorPropGroup,
                mesVlanProtV1,
                mesLacpGroupV1}
    ::= { lumMesCompl 27}

lumMesBasicComplV28 MODULE-COMPLIANCE
    STATUS      deprecated
    DESCRIPTION
        "Basic implementation requirements for the MES MIB (30.1)."
    MODULE
        MANDATORY-GROUPS {
                mesGeneralGroupV6,
                mesBwpGroupV5,
                mesMiscGroupV10,
                mesPortGroupV10,
                mesVlanMapGroupV9,
                mesBwpMapGroupV2,
                mesMgmtVlanGroupV4,
                mesLagGroupV9,
                mesPolicingGroupV4,
                mesShapingGroupV3,
                mesCosGroup,
                mesMirroringGroupV3,
                mesVlanTagRuleGroupV4,
                mesVlanTagClassVlanGroupV5,
                mesCosProfileGroupV4,
                mesMaidGroupV6,
                mesCfmMepGroupV11,
                mesErpGroupV7,
                mesClassGroupV6,
                mesActionGroupV4,
                mesPolicyGroupV2,
                mesErrorPropGroupV2,
                mesVlanProtV1,
                mesLacpGroupV1}
    ::= { lumMesCompl 28}

lumMesBasicComplV29 MODULE-COMPLIANCE
    STATUS      deprecated
    DESCRIPTION
        "Basic implementation requirements for the MES MIB (31.1)."
    MODULE
        MANDATORY-GROUPS {
                mesGeneralGroupV6,
                mesBwpGroupV5,
                mesMiscGroupV10,
                mesPortGroupV11,
                mesVlanMapGroupV9,
                mesBwpMapGroupV2,
                mesMgmtVlanGroupV4,
                mesLagGroupV9,
                mesPolicingGroupV4,
                mesShapingGroupV3,
                mesCosGroup,
                mesMirroringGroupV3,
                mesVlanTagRuleGroupV4,
                mesVlanTagClassVlanGroupV5,
                mesCosProfileGroupV4,
                mesMaidGroupV6,
                mesCfmMepGroupV10,
                mesErpGroupV7,
                mesClassGroupV6,
                mesActionGroupV4,
                mesPolicyGroupV2,
                mesErrorPropGroupV2,
                mesVlanProtV1,
                mesLacpGroupV1}
    ::= { lumMesCompl 29}

lumMesBasicComplV30 MODULE-COMPLIANCE
    STATUS      current
    DESCRIPTION
        "Basic implementation requirements for the MES MIB (32)."
    MODULE
        MANDATORY-GROUPS {
                mesGeneralGroupV6,
                mesBwpGroupV5,
                mesMiscGroupV10,
                mesPortGroupV11,
                mesVlanMapGroupV10,
                mesBwpMapGroupV2,
                mesMgmtVlanGroupV4,
                mesLagGroupV9,
                mesPolicingGroupV4,
                mesShapingGroupV3,
                mesCosGroup,
                mesMirroringGroupV3,
                mesVlanTagRuleGroupV4,
                mesVlanTagClassVlanGroupV5,
                mesCosProfileGroupV4,
                mesMaidGroupV6,
                mesCfmMepGroupV10,
                mesErpGroupV7,
                mesClassGroupV6,
                mesActionGroupV4,
                mesPolicyGroupV2,
                mesErrorPropGroupV2,
                mesVlanProtV1,
                mesLacpGroupV1}
    ::= { lumMesCompl 30}

END
