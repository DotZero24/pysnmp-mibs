-- *****************************************************************
-- INFINERA-TP-TRIBPTP-MIB
--
-- October 2008, Sharfuddin Syed / Narendra Gupta
--
--
-- Copyright (c) 2008-2012 by Infinera Inc.
-- All rights reserved.
-- ****************************************************************

INFINERA-TP-TRIBPTP-MIB DEFINITIONS ::= BEGIN

IMPORTS
    MODULE-IDENTITY, OBJECT-TYPE, Integer32     FROM SNMPv2-SMI
    MODULE-COMPLIANCE, OBJECT-GROUP             FROM SNMPv2-CONF
    DisplayString                               FROM SNMPv2-TC
    ifIndex                                     FROM IF-MIB
    FloatTenths, InfnServiceType, InfnDirectionality,
    InfnInterfaceType, InfnServiceTypeList,InfnEnableDisable,
    InfnTribAction,InfnOperationalState,
    InfnPmHistStatsControl, InfnReporting,
    InfnEnetPswLaserCtrlState,
    InfnAutoCableEqualization, InfnProtectionMode,
    InfnCfgProtState,InfnCurrProtState, InfnPsDirn,
    InfnSwitchReason, InfnSwitchRequestState,
	InfnFecEncodingMode						    FROM INFINERA-TC-MIB
    terminationPoint                            FROM INFINERA-REG-MIB;

tribPtpMIB MODULE-IDENTITY
    LAST-UPDATED  "200810200000Z"
    ORGANIZATION
        "Infinera"
    CONTACT-INFO
        "Infinera
                1322 Bordeaux Drive
                Sunnyvale, CA - 94089

                Contact : Technical Support
                Email   : support@infinera.com
                Phone   : 1-877-INF-5288"
    DESCRIPTION
        " "

    REVISION  "200810200000Z"
    DESCRIPTION
        " "
::= { terminationPoint 17 }


tribPtpConformance   OBJECT IDENTIFIER ::= { tribPtpMIB 3 }
tribPtpCompliances   OBJECT IDENTIFIER ::= { tribPtpConformance 1 }
tribPtpGroups        OBJECT IDENTIFIER ::= { tribPtpConformance 2 }

tribPtpTable  OBJECT-TYPE
    SYNTAX SEQUENCE OF TribPtpEntry
    MAX-ACCESS not-accessible
    STATUS     current
    DESCRIPTION
        "A list of TribPtp entries. Each entry is uniquely identified by
                the value of ifIndex."
    ::= { tribPtpMIB 1 }

tribPtpEntry  OBJECT-TYPE
    SYNTAX     TribPtpEntry
    MAX-ACCESS not-accessible
    STATUS     current
    DESCRIPTION
        "A TribPtp entry containing information pertaining to
                Infinera TribPtp interfaces. . This table is a subclass of IfCommon.
                Entries will exist in this table only for interfaces of type TribPtp."
    INDEX { ifIndex }
    ::= { tribPtpTable 1 }

TribPtpEntry  ::= SEQUENCE {
    tribPtpPgMoId                         DisplayString,
    tribPtpProtMod                        InfnProtectionMode,
    tribPtpCfgProtSt                      InfnCfgProtState,
    tribPtpCurProtSt                      InfnCurrProtState,
    tribPtpPsDirn                         InfnPsDirn,
    tribPtpSwReason                       InfnSwitchReason,
    tribPtpSwRqState                      InfnSwitchRequestState,
    tribPtpMaxPerChannelCapacity          InfnServiceType,
    tribPtpTribDisableAction              InfnTribAction,
    tribPtpProvisionedServiceType         InfnServiceType,
    tribPtpOprOorHighThresholdOffset      FloatTenths,
    tribPtpOprOorLowThresholdOffset       FloatTenths,
    tribPtpOprOorAlarmReporting           InfnReporting,
    tribPtpOprOverloadThreshold           FloatTenths,
    tribPtpOprSensitivityThreshold        FloatTenths,
    tribPtpAINS                           InfnOperationalState,
    tribPtpValidSignalTimeInterval        Integer32,
    tribPtpRemValidSignalTimer            Integer32,
    tribPtpSupportedServiceTypes          InfnServiceTypeList,
    tribPtpPmHistStatsEnable              InfnPmHistStatsControl,
    tribPtpMaxAllowedDrops                Integer32,
    tribPtpCurrNumOfDrops                 Integer32,
    tribPtpLocalInterfaceIndex            Integer32,
    tribPtpRemoteInterfaceIndex           Integer32,
    tribPtpAssocMoInteropCPTEInterface    DisplayString,
    tribPtpDtpAISOnClientSF               InfnOperationalState,
    tribPtpEnetPswLaserCtrl               InfnEnetPswLaserCtrlState,
    tribPtpDisableActionOnBERSF   	      InfnEnableDisable,
    tribPtpAutoCableEqualization          InfnAutoCableEqualization,
    tribPtpDirectionality                 InfnDirectionality,
    tribPtpInterfaceType                  InfnInterfaceType,
    tribPtpAutoDiscovery                  InfnEnableDisable,
    tribPtpDiscoveredRemoteTP             DisplayString,
    tribPtpProvisionedRemoteTP            DisplayString,
    tribPtpForwardDefectTDATrigger        InfnEnableDisable,
    tribPtpProvisionedFecEncodingMode	  InfnFecEncodingMode,
    tribPtpAppliedFecEncodingMode	 	  InfnFecEncodingMode
}

tribPtpPgMoId  OBJECT-TYPE
    SYNTAX     DisplayString
    MAX-ACCESS read-only
    STATUS     current
    DESCRIPTION
        "An identifer for the digital SNCP protection."
    ::= { tribPtpEntry 1 }

tribPtpProtMod  OBJECT-TYPE
    SYNTAX      InfnProtectionMode
    MAX-ACCESS read-only
    STATUS     current
    DESCRIPTION
        "This attribute represents whether this DTP (as PU or Reliable TP)
         is contributing to Single TAM SDNCP or Dual TAM DSNCP. For GTP this
         will always be STDSNCP if Protected. For unprotected service this
         value shall be None."
    ::= { tribPtpEntry 2 }

tribPtpCfgProtSt  OBJECT-TYPE
    SYNTAX     InfnProtectionMode
    MAX-ACCESS read-only
    STATUS     current
    DESCRIPTION
        "The preferred state of the protection unit."
    ::= { tribPtpEntry 3 }

tribPtpCurProtSt  OBJECT-TYPE
    SYNTAX    InfnCurrProtState
    MAX-ACCESS read-only
    STATUS     current
    DESCRIPTION
        "The actual state of the protection unit."
    ::= { tribPtpEntry 4 }

tribPtpPsDirn  OBJECT-TYPE
    SYNTAX     InfnPsDirn
    MAX-ACCESS read-only
    STATUS     current
    DESCRIPTION
        "Protection switch direction (unidirectional or bidirectional) of the
         protection group."
    ::= { tribPtpEntry 5 }

tribPtpSwReason  OBJECT-TYPE
    SYNTAX     InfnSwitchReason
    MAX-ACCESS read-only
    STATUS     current
    DESCRIPTION
        "The reason for the protection switch."
    ::= { tribPtpEntry 6 }

tribPtpSwRqState  OBJECT-TYPE
    SYNTAX     InfnSwitchRequestState
    MAX-ACCESS read-only
    STATUS     current
    DESCRIPTION
        "Indicates the protection switch request state of the protecting
        protection unit."
    ::= { tribPtpEntry 7 }

tribPtpMaxPerChannelCapacity  OBJECT-TYPE
    SYNTAX     InfnServiceType
    MAX-ACCESS read-only
    STATUS     current
    DESCRIPTION
        "The maximum channel capacity of the signal port of the TOM."
    ::= { tribPtpEntry 8 }

tribPtpTribDisableAction  OBJECT-TYPE
    SYNTAX     InfnTribAction
    MAX-ACCESS read-write
    STATUS     current
    DESCRIPTION
        "This attribute indicates the action taken on the
                trib/facility side when the line-side is not receiving valid
                signal. Any loss of signal trigger this action. Similarly, a
                valid signal from line side should turn back on the XFP. Any loss
                of signal on the trib side (facility side) does not cause
                tribDisableAction to be enabled."
    DEFVAL  { sendAISL }
    ::= { tribPtpEntry 9 }

tribPtpProvisionedServiceType  OBJECT-TYPE
    SYNTAX     InfnServiceType
    MAX-ACCESS read-write
    STATUS     current
    DESCRIPTION
        "The supported values for this field are determined based on
                the circuit pack inserted (and its capabilities). The appropriate
                Client CTP object is created based on this value. Changing this
                value will cause the existing Client CTP to be deleted and a new
                one created. Any change to this attribute need to be checked
                against the TAM equipment to see if the new service type is
                supported."
    ::= { tribPtpEntry 10 }

tribPtpOprOorHighThresholdOffset  OBJECT-TYPE
    SYNTAX     FloatTenths
    MAX-ACCESS read-write
    STATUS     current
    DESCRIPTION
        "An offset to the already configured hardware value for  the high threshold can be set."
    DEFVAL  { 0 }
    ::= { tribPtpEntry 11 }

tribPtpOprOorLowThresholdOffset  OBJECT-TYPE
    SYNTAX     FloatTenths
    MAX-ACCESS read-write
    STATUS     current
    DESCRIPTION
        "An offset to the already configured hardware value for the low threshold can be set."
    DEFVAL  { 0 }
    ::= { tribPtpEntry 12 }

tribPtpOprOorAlarmReporting  OBJECT-TYPE
    SYNTAX     InfnReporting
    MAX-ACCESS read-write
    STATUS     current
    DESCRIPTION
        "Flag to enable Optical Power Received - Out of Range alarm reporting."
    DEFVAL  { disabled }
    ::= { tribPtpEntry 13 }

tribPtpOprOverloadThreshold  OBJECT-TYPE
    SYNTAX     FloatTenths
    MAX-ACCESS read-only
    STATUS     current
    DESCRIPTION
        "TRIB port receiver overload threshold."
    ::= { tribPtpEntry 14 }

tribPtpOprSensitivityThreshold  OBJECT-TYPE
    SYNTAX     FloatTenths
    MAX-ACCESS read-only
    STATUS     current
    DESCRIPTION
        "TRIB port receiver sensitivity threshold."
    ::= { tribPtpEntry 15 }

tribPtpAINS  OBJECT-TYPE
    SYNTAX     InfnOperationalState
    MAX-ACCESS read-write
    STATUS     current
    DESCRIPTION
        "Flag to enable or disable AINS."
    DEFVAL  { disabled }
    ::= { tribPtpEntry 16 }

tribPtpValidSignalTimeInterval  OBJECT-TYPE
    SYNTAX     Integer32
    MAX-ACCESS read-write
    STATUS     current
    DESCRIPTION
        "The valid signal time interval can be configured only when AINS is enabled."
    DEFVAL  { 480 }
    ::= { tribPtpEntry 17 }

tribPtpRemValidSignalTimer  OBJECT-TYPE
    SYNTAX     Integer32
    MAX-ACCESS read-only
    STATUS     current
    DESCRIPTION
        "The remaining time interval for which AINS is enabled."
    ::= { tribPtpEntry 18 }

tribPtpSupportedServiceTypes  OBJECT-TYPE
    SYNTAX     InfnServiceTypeList
    MAX-ACCESS read-only
    STATUS     current
    DESCRIPTION
        "The list of services that can be supported by the hardware."
    ::= { tribPtpEntry 19 }

tribPtpPmHistStatsEnable  OBJECT-TYPE
    SYNTAX      InfnPmHistStatsControl
    MAX-ACCESS read-write
    STATUS     current
    DESCRIPTION
        "Flag to enable or disable PM collection."
    DEFVAL  { enabled }
    ::= { tribPtpEntry 20 }

tribPtpMaxAllowedDrops  OBJECT-TYPE
    SYNTAX     Integer32
    MAX-ACCESS read-only
    STATUS     current
    DESCRIPTION
        "The maximum number of drops allowed on this trip port. This is decided
         based on the type of xcon or snc and dsncp to be created."
    ::= { tribPtpEntry 21 }

tribPtpCurrNumOfDrops  OBJECT-TYPE
    SYNTAX     Integer32
    MAX-ACCESS read-only
    STATUS     current
    DESCRIPTION
        "The count of the number of drops on this trib port"
    ::= { tribPtpEntry 22 }

tribPtpLocalInterfaceIndex  OBJECT-TYPE
    SYNTAX     Integer32
    MAX-ACCESS read-only
    STATUS     current
    DESCRIPTION
        "An identifier for the UNI GMPLS Link interface on the local end,
         auto-generated by the network element. When the UNI GMPLS Link is
         first created, the index is empty."
    ::= { tribPtpEntry 23 }

tribPtpRemoteInterfaceIndex  OBJECT-TYPE
    SYNTAX     Integer32
    MAX-ACCESS read-write
    STATUS     current
    DESCRIPTION
        "An identifier for the UNI GMPLS Link interface on the remote end."
    DEFVAL  { 0 }
    ::= { tribPtpEntry 24 }

tribPtpAssocMoInteropCPTEInterface  OBJECT-TYPE
    SYNTAX     DisplayString
    MAX-ACCESS read-only
    STATUS     current
    DESCRIPTION
        "TE interface for UNI."
    ::= { tribPtpEntry 25 }

tribPtpDtpAISOnClientSF  OBJECT-TYPE
    SYNTAX      InfnOperationalState
    MAX-ACCESS read-write
    STATUS     current
    DESCRIPTION
        "Object controls the client failure insertion in the infinera digital path failure."
    DEFVAL  { disabled }
    ::= { tribPtpEntry 26 }

tribPtpEnetPswLaserCtrl  OBJECT-TYPE
    SYNTAX      InfnEnetPswLaserCtrlState
    MAX-ACCESS read-write
    STATUS     current
    DESCRIPTION
        "Flag to control the laser of trib port."
    DEFVAL  { turnLaserOff }
    ::= { tribPtpEntry 27 }


tribPtpDisableActionOnBERSF OBJECT-TYPE
    SYNTAX      InfnEnableDisable
    MAX-ACCESS  read-write
    STATUS      current
    DESCRIPTION "Flag to disable trib on DTP signal failure"
    DEFVAL      { disabled }
    ::= { tribPtpEntry  28 }

tribPtpAutoCableEqualization OBJECT-TYPE
    SYNTAX     InfnAutoCableEqualization
    MAX-ACCESS  read-write
    STATUS      current
    DESCRIPTION "Auto Cable equalization"
    DEFVAL      { enabled }
    ::= { tribPtpEntry  29 }

tribPtpDirectionality OBJECT-TYPE
    SYNTAX      InfnDirectionality
    MAX-ACCESS  read-only
    STATUS      current
    DESCRIPTION "Directionality "
    DEFVAL      { bidirectional }
    ::= { tribPtpEntry  30 }

tribPtpInterfaceType OBJECT-TYPE
    SYNTAX      InfnInterfaceType
    MAX-ACCESS  read-only
    STATUS      current
    DESCRIPTION "Interface type"
    ::= { tribPtpEntry  31 }

tribPtpAutoDiscovery  OBJECT-TYPE
    SYNTAX      InfnEnableDisable
    MAX-ACCESS  read-write
    STATUS      current
    DESCRIPTION "ATN DTN Auto Discovery"
    DEFVAL      { enabled }
    ::= { tribPtpEntry  32 }

tribPtpDiscoveredRemoteTP     OBJECT-TYPE
    SYNTAX     DisplayString
    MAX-ACCESS read-only
    STATUS     current
    DESCRIPTION
        "ATN DTN DiscoveredRemote TP."
    ::= { tribPtpEntry 33 }

tribPtpProvisionedRemoteTP  OBJECT-TYPE
    SYNTAX     DisplayString
    MAX-ACCESS read-write
    STATUS     current
    DESCRIPTION
        "ATN DTN Provisioned Remote TP"
    ::= { tribPtpEntry 34 }

tribPtpForwardDefectTDATrigger OBJECT-TYPE
    SYNTAX      InfnEnableDisable
    MAX-ACCESS  read-write
    STATUS      current
    DESCRIPTION "Egress Trib Disable Action"
    DEFVAL      { disabled }
    ::= { tribPtpEntry  35 }

tribPtpProvisionedFecEncodingMode	OBJECT-TYPE
    SYNTAX      InfnFecEncodingMode
    MAX-ACCESS  read-write
    STATUS      current
    DESCRIPTION "Provisioned FEC Encoding"
    ::= { tribPtpEntry  36 }

tribPtpAppliedFecEncodingMode	OBJECT-TYPE
    SYNTAX      InfnFecEncodingMode
    MAX-ACCESS  read-only
    STATUS      current
    DESCRIPTION "Applied FEC Encoding"
    ::= { tribPtpEntry  37 }

tribPtpCompliance  MODULE-COMPLIANCE
    STATUS     current
    DESCRIPTION
        "Describes the requirements for conformance to the TRIBPTP-MIB"
    MODULE
        MANDATORY-GROUPS { tribPtpGroup }
    ::= { tribPtpCompliances 1 }

tribPtpGroup  OBJECT-GROUP
    OBJECTS {
        tribPtpPgMoId,
        tribPtpProtMod,
        tribPtpCfgProtSt,
        tribPtpCurProtSt,
        tribPtpPsDirn,
        tribPtpSwReason,
        tribPtpSwRqState,
        tribPtpMaxPerChannelCapacity,
        tribPtpTribDisableAction,
        tribPtpProvisionedServiceType,
        tribPtpOprOorHighThresholdOffset,
        tribPtpOprOorLowThresholdOffset,
        tribPtpOprOorAlarmReporting,
        tribPtpOprOverloadThreshold,
        tribPtpOprSensitivityThreshold,
        tribPtpAINS,
        tribPtpValidSignalTimeInterval,
        tribPtpRemValidSignalTimer,
        tribPtpSupportedServiceTypes,
        tribPtpPmHistStatsEnable,
        tribPtpMaxAllowedDrops,
        tribPtpCurrNumOfDrops,
        tribPtpLocalInterfaceIndex,
        tribPtpRemoteInterfaceIndex,
        tribPtpAssocMoInteropCPTEInterface,
        tribPtpDtpAISOnClientSF,
        tribPtpEnetPswLaserCtrl,
        tribPtpDisableActionOnBERSF,
        tribPtpAutoCableEqualization,
        tribPtpDirectionality,
        tribPtpInterfaceType,
        tribPtpAutoDiscovery,
        tribPtpDiscoveredRemoteTP,
        tribPtpProvisionedRemoteTP,
        tribPtpForwardDefectTDATrigger,
		tribPtpProvisionedFecEncodingMode,
		tribPtpAppliedFecEncodingMode
        }
    STATUS     current
    DESCRIPTION
        " A collection of objects for managing tribPtp interfaces."
    ::= { tribPtpGroups 1 }
END

-- This MIB was created using NuDesign Team's Visual MIBuilder (Ver 4.7).
