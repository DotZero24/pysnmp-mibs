-- *****************************************************************
-- INFINERA-TP-OSCPTP-MIB
--
-- Copyright (c) 2008-2012 by Infinera Inc.
-- All rights reserved.
-- ****************************************************************

INFINERA-TP-OSCPTP-MIB DEFINITIONS ::= BEGIN

IMPORTS
    OBJECT-TYPE, MODULE-IDENTITY, Integer32        FROM SNMPv2-SMI
    OBJECT-GROUP, MODULE-COMPLIANCE                FROM SNMPv2-CONF
    TruthValue                                     FROM SNMPv2-TC
    ifIndex                                        FROM IF-MIB
    terminationPoint                               FROM INFINERA-REG-MIB;

oscPtpMIB MODULE-IDENTITY
    LAST-UPDATED  "201210200000Z"
    ORGANIZATION
        "Infinera"
    CONTACT-INFO
        "Infinera
                1322 Bordeaux Drive
                Sunnyvale, CA - 94089

                Contact : Technical Support
                Email   : support@infinera.com
                Phone   : 1-877-INF-5288"
    DESCRIPTION
        " "

    REVISION  "201210200000Z"
    DESCRIPTION
        "First Version"
::= { terminationPoint 36}

-- Conformance Statements

oscPtpConformance    OBJECT IDENTIFIER ::= { oscPtpMIB 3 }
oscPtpCompliances    OBJECT IDENTIFIER ::= { oscPtpConformance 1 }
oscPtpGroups         OBJECT IDENTIFIER ::= { oscPtpConformance 2 }

oscPtpTable  OBJECT-TYPE
    SYNTAX SEQUENCE OF OscPtpEntry
    MAX-ACCESS not-accessible
    STATUS     current
    DESCRIPTION
        "A list of OscPtp entries. Each entry is uniquely identified by the value of ifIndex."
    ::= { oscPtpMIB 1 }

oscPtpEntry  OBJECT-TYPE
    SYNTAX     OscPtpEntry
    MAX-ACCESS not-accessible
    STATUS     current
    DESCRIPTION
        "A OscPtp entry containing information pertaining to Infinera OscPtp interfaces.
         This table is a subclass of IfCommon. Entries will exist in this table only for
         interfaces of type OSC PTP."
    INDEX { ifIndex }
    ::= { oscPtpTable 1 }

OscPtpEntry ::= SEQUENCE {
    oscPtpPmHistStatsEnable                    INTEGER
}

oscPtpPmHistStatsEnable  OBJECT-TYPE
    SYNTAX     INTEGER {
        enabled (1),
        disabled (2)
    }
    MAX-ACCESS read-write
    STATUS     current
    DESCRIPTION
        "Flag to enable or disable PM collection."
    DEFVAL  { enabled }
    ::= { oscPtpEntry 1 }

oscPtpCompliance  MODULE-COMPLIANCE
    STATUS     current
    DESCRIPTION
        "Describes the requirements for conformance to the OSCPTP-MIB"
    MODULE
        MANDATORY-GROUPS { oscPtpGroup }
    ::= { oscPtpCompliances 1 }

oscPtpGroup  OBJECT-GROUP
    OBJECTS { oscPtpPmHistStatsEnable }
    STATUS     current
    DESCRIPTION
        " A collection of objects for managing the oscPtp"
    ::= { oscPtpGroups 1 }
END
