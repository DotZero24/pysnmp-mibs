-- *****************************************************************
-- INFINERA-TP-OtdmOtdrPtp-MIB
--
-- October 2008, Sharfuddin Syed / Narendra Gupta
--
--
-- Copyright (c) 2008-2012 by Infinera Inc.
-- All rights reserved.
-- ****************************************************************

INFINERA-TP-OtdmOtdrPtp-MIB DEFINITIONS ::= BEGIN

IMPORTS
    MODULE-IDENTITY, OBJECT-TYPE                FROM SNMPv2-SMI
    MODULE-COMPLIANCE, OBJECT-GROUP             FROM SNMPv2-CONF
    ifIndex                                     FROM IF-MIB
    terminationPoint                            FROM INFINERA-REG-MIB
    FloatHundredths, InfnFiberType              FROM INFINERA-TC-MIB
    DisplayString                               FROM SNMPv2-TC;


otdmOtdrPtpMIB MODULE-IDENTITY
    LAST-UPDATED  "201310200000Z"
    ORGANIZATION  "Infinera"
    CONTACT-INFO
        "Infinera
        1322 Bordeaux Drive
        Sunnyvale, CA - 94089

        Contact : Technical Support
        Email   : support@infinera.com
        Phone   : 1-877-INF-5288"
    DESCRIPTION " "
    REVISION    "201310200000Z"
    DESCRIPTION "First Version"
    ::= { terminationPoint 48 }

otdmOtdrPtpTable OBJECT-TYPE
    SYNTAX      SEQUENCE OF OtsPTPEntry
    MAX-ACCESS  not-accessible
    STATUS      current
    DESCRIPTION
        "A list of otdmOtdrPtp entries. Each entry is uniquely identified by the value of ifIndex."
    ::= { otdmOtdrPtpMIB 1 }

otdmOtdrPtpEntry  OBJECT-TYPE
    SYNTAX      OtsPTPEntry
    MAX-ACCESS  not-accessible
    STATUS      current
    DESCRIPTION ""
    INDEX { ifIndex }
    ::= { otdmOtdrPtpTable 1 }


OtsPTPEntry  ::= SEQUENCE {
    otdmOtdrPtpConnectivityState            INTEGER,
    otdmOtdrPtpLstSuccConnValidationTime    Integer32,
    otdmOtdrPtpProvisionedNeighborPtp       DisplayString,
    otdmOtdrPtpTestControlStatus            INTEGER,
    otdmOtdrPtpTestAquistionMode            INTEGER,
    otdmOtdrPtpTestPulseWidth               INTEGER,
    otdmOtdrPtpDetectionRange               INTEGER,
    otdmOtdrPtpAcquistionTime               INTEGER,
    otdmOtdrPtpTestCableID                  DisplayString,
    otdmOtdrPtpTestFiberID                  DisplayString,
    otdmOtdrPtpTestFiberType                InfnFiberType,
    otdmOtdrPtpTestEventLossThreshold       FloatHundredths,
    otdmOtdrPtpTestReflectionThreshold      FloatHundredths,
    otdmOtdrPtpTestEndOfFiberThreshold      FloatHundredths,
    otdmOtdrPtpTestResultFileName           DisplayString,
    otdmOtdrPtpTestResultUpload             INTEGER
    }

otdmOtdrPtpConnectivityState OBJECT-TYPE
    SYNTAX      INTEGER {
        notVerified(1),
        valid(2),
        inValid(3)
    }
    MAX-ACCESS  read-only
    STATUS      current
    DESCRIPTION ""
    ::= { otdmOtdrPtpEntry  1 }


otdmOtdrPtpLstSuccConnValidationTime OBJECT-TYPE
    SYNTAX      Integer32
    MAX-ACCESS  read-only
    STATUS      current
    DESCRIPTION ""
    ::= { otdmOtdrPtpEntry  2 }

otdmOtdrPtpProvisionedNeighborPtp   OBJECT-TYPE
    SYNTAX      DisplayString
    MAX-ACCESS  read-write
    STATUS      current
    DESCRIPTION ""
    ::= { otdmOtdrPtpEntry  3 }

otdmOtdrPtpTestControlStatus    OBJECT-TYPE
    SYNTAX      INTEGER{
        inProgress(1),
        queuedUp(2),
        scheduled(3),
        idle(4)
    }
    MAX-ACCESS  read-only
    STATUS      current
    DESCRIPTION ""
    ::= { otdmOtdrPtpEntry  4 }

otdmOtdrPtpTestAquistionMode    OBJECT-TYPE
    SYNTAX      INTEGER {
        automatic(1),
        manual(2)
    }
    MAX-ACCESS  read-write
    STATUS      current
    DESCRIPTION ""
    ::= { otdmOtdrPtpEntry  5 }

otdmOtdrPtpTestPulseWidth   OBJECT-TYPE
    SYNTAX  INTEGER {
        ns5(1),
        ns10(2),
        ns30(3),
        ns100(4),
        ns300(5),
        us1(6),
        us3(7),
        us10(8),
        us20(9)
    }
    MAX-ACCESS  read-write
    STATUS      current
    DESCRIPTION ""
    ::= { otdmOtdrPtpEntry 6 }

otdmOtdrPtpDetectionRange   OBJECT-TYPE
    SYNTAX      INTEGER {
		km05(1),
		km1(2),
		km2(3),
		km5(4),
		km10(5),
		km20(6),
		km40(7),
		km80(8),
		km160(9),
		km260(10)
    }
    MAX-ACCESS  read-write
    STATUS      current
    DESCRIPTION ""
    ::= { otdmOtdrPtpEntry 7 }

otdmOtdrPtpAcquistionTime   OBJECT-TYPE
    SYNTAX      INTEGER {
        sec1(1),
        sec5(2),
        sec10(3),
        sec20(4),
        sec30(5),
        sec60(6),
        sec120(7),
        sec180(8),
        sec240(9),
        sec300(10)
    }
    MAX-ACCESS  read-write
    STATUS      current
    DESCRIPTION ""
    ::= { otdmOtdrPtpEntry 8 }

otdmOtdrPtpTestCableID OBJECT-TYPE
    SYNTAX      DisplayString
    MAX-ACCESS  read-write
    STATUS      current
    DESCRIPTION ""
    ::= { otdmOtdrPtpEntry 9 }

otdmOtdrPtpTestFiberID  OBJECT-TYPE
    SYNTAX      DisplayString
    MAX-ACCESS  read-write
    STATUS      current
    DESCRIPTION ""
    ::= { otdmOtdrPtpEntry 10 }

otdmOtdrPtpTestFiberType OBJECT-TYPE
    SYNTAX      InfnFiberType
    MAX-ACCESS  read-only
    STATUS      current
    DESCRIPTION ""
    ::= { otdmOtdrPtpEntry 11 }

otdmOtdrPtpTestEventLossThreshold   OBJECT-TYPE
    SYNTAX      FloatHundredths
    MAX-ACCESS  read-write
    STATUS      current
    DESCRIPTION ""
    ::= { otdmOtdrPtpEntry 12 }

otdmOtdrPtpTestReflectionThreshold  OBJECT-TYPE
    SYNTAX      FloatHundredths
    MAX-ACCESS  read-write
    STATUS      current
    DESCRIPTION ""
    ::= { otdmOtdrPtpEntry  13 }

otdmOtdrPtpTestEndOfFiberThreshold  OBJECT-TYPE
    SYNTAX      FloatHundredths
    MAX-ACCESS  read-write
    STATUS      current
    DESCRIPTION ""
    ::= { otdmOtdrPtpEntry 15 }

otdmOtdrPtpTestResultFileName   OBJECT-TYPE
    SYNTAX      DisplayString
    MAX-ACCESS  read-write
    STATUS      current
    DESCRIPTION ""
    ::= { otdmOtdrPtpEntry 16 }

otdmOtdrPtpTestResultUpload     OBJECT-TYPE
    SYNTAX      INTEGER {
        enable(1),
        disable(2)
    }
    MAX-ACCESS  read-write
    STATUS      current
    DESCRIPTION ""
    ::= { otdmOtdrPtpEntry  17 }

-- Conformance Statements
otdmOtdrPtpConformance    OBJECT IDENTIFIER ::= { otdmOtdrPtpMIB 3 }
otdmOtdrPtpCompliances    OBJECT IDENTIFIER ::= { otdmOtdrPtpConformance 1 }
otdmOtdrPtpGroups         OBJECT IDENTIFIER ::= { otdmOtdrPtpConformance 2 }

otdmOtdrPtpCompliance MODULE-COMPLIANCE
    STATUS current
    DESCRIPTION
    "Describes the requirements for conformance to the otdmOtdrPtp-MIB"
    MODULE
        MANDATORY-GROUPS { otdmOtdrPtpGroup }
    ::= { otdmOtdrPtpCompliances 1 }

otdmOtdrPtpGroup OBJECT-GROUP
    OBJECTS {
        otdmOtdrPtpConnectivityState,
        otdmOtdrPtpLstSuccConnValidationTime,
        otdmOtdrPtpProvisionedNeighborPtp,
        otdmOtdrPtpTestControlStatus,
        otdmOtdrPtpTestAquistionMode,
        otdmOtdrPtpTestPulseWidth,
        otdmOtdrPtpDetectionRange,
        otdmOtdrPtpAcquistionTime,
        otdmOtdrPtpTestCableID,
        otdmOtdrPtpTestFiberID,
        otdmOtdrPtpTestFiberType,
        otdmOtdrPtpTestEventLossThreshold,
        otdmOtdrPtpTestReflectionThreshold,
        otdmOtdrPtpTestEndOfFiberThreshold,
        otdmOtdrPtpTestResultFileName,
        otdmOtdrPtpTestResultUpload
    }
    STATUS current
    DESCRIPTION
        " A collection of objects for managing the otdmOtdrPtp"
    ::= { otdmOtdrPtpGroups 1 }
END
