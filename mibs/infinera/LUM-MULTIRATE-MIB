LUM-MULTIRATE-MIB DEFINITIONS ::= BEGIN

IMPORTS
    MODULE-IDENTITY, OBJECT-TYPE, Unsigned32, Integer32, NOTIFICATION-TYPE,
    Gauge32
        FROM SNMPv2-SMI
    OBJECT-GROUP, MODULE-COMPLIANCE, NOTIFICATION-GROUP
        FROM SNMPv2-CONF
    TestAndIncr, DisplayString, DateAndTime
        FROM SNMPv2-TC
    lumModules, lumMultirateMIB
        FROM LUM-REG
    FaultStatus, MgmtNameString, SubrackNumber, SlotNumber, PortNumber,
    BoardOrInterfaceOperStatus, BoardOrInterfaceAdminStatus, CommandString,
    LambdaFrequency, SignalFormat, TrxMedia, ObjectProperty
        FROM LUM-TC;

lumMultirateMIBModule MODULE-IDENTITY
    LAST-UPDATED
        "201706150000Z" -- June 15th 2017
    ORGANIZATION
        "Infinera Corporation"
    CONTACT-INFO
        "techsupport@infinera.com"
    DESCRIPTION
        "The multi-bitrate client interface MIB.

        - General

        - Multi bit-rate client interfaces

"
    REVISION
        "201706150000Z" -- June 15th 2017
    DESCRIPTION
        "Changes made for release r29.0:
         - Changed ORGANIZATION and CONTACT-INFO"
    REVISION
        "201601110000Z" -- Jan 11th 2016
    DESCRIPTION
        "Added default value notPresent for operStatus."
    REVISION
        "201104120000Z" -- April 12th 2011
    DESCRIPTION
        "Added new compliance group to mark adding write support for trail trace."
    REVISION
        "200711120000Z" -- November 12th 2007
    DESCRIPTION
        "Added mrtIfHighSpeed2 to mrtIfGroupV16."
    REVISION
        "200301290000Z" -- January 29th 2003
    DESCRIPTION
        "Added mrtIfTruncVc4Status."
    REVISION
        "200212040000Z" -- December 4th 2002
    DESCRIPTION
        "Added trace identifier attributes in the multirate interface table."
    REVISION
        "200210010000Z" -- October 1st 2002
    DESCRIPTION
        "Added VC-4 id."
    REVISION
        "200206040000Z" -- June 4th 2002
    DESCRIPTION
        "Added signalStatus and related notifications."
    REVISION
        "200205150000Z" -- May 15th 2002
    DESCRIPTION
        "Added PM alarm thresholds."
    REVISION
        "200201170000Z" -- January 17th 2002
    DESCRIPTION
        "Added AU4 alarm indication signal and loss of pointer."
    REVISION
        "200112030000Z" -- December 3rd 2001
    DESCRIPTION
        "Moved admin and operStatus definitions to LUM-TC"
    REVISION
        "200111090000Z" -- November 9th 2001
    DESCRIPTION
        "lossOfLock is now called bitrateMismatch.
        Added laser bias meter and threshold.
        Added J0 path trace."
    REVISION
        "200110300000Z" -- October 30th 2001
    DESCRIPTION
        "testAndIncr and MIB-versions hidden - not supported yet."
    REVISION
        "200110220000Z" -- October 22nd 2001
    DESCRIPTION
        "Added mrtIfRx port, changed mrtPort to mrtTxPort."
    REVISION
        "200110180000Z" -- October 18th 2001
    DESCRIPTION
        "Changed aliases to the 'long'-version for all faultStatus objects."
    REVISION
        "200110110000Z" -- October 11th 2001
    DESCRIPTION
        "Renamed TRANSPONDER to MULTIRATE."
    REVISION
        "200109050000Z" -- September 5th 2001
    DESCRIPTION
        "Added lossOfLock."
    REVISION
        "200108140000Z" -- August 14th 2001
    DESCRIPTION
        "Added alias.
        Removed lambda info from mrtIfEntry.
        Added compliance info."
    REVISION
        "200108080000Z" -- August 9th 2001
    DESCRIPTION
        "The initial revision of this module."
    ::= { lumModules 13 }


-- ----------------------------------------------------
-- Conformance area, containing groups and complicance
-- specifications.
-- ----------------------------------------------------

lumMultirateConfs OBJECT IDENTIFIER ::= { lumMultirateMIB 1 }
lumMultirateGroups OBJECT IDENTIFIER ::= { lumMultirateConfs 1 }
lumMultirateCompl OBJECT IDENTIFIER ::= { lumMultirateConfs 2 }


-- ----------------------------------------------------
-- Root for objects in the multirate MIB
-- ----------------------------------------------------

lumMultirateMIBObjects OBJECT IDENTIFIER ::= { lumMultirateMIB 2 }


-- ----------------------------------------------------
-- This MIB contains the following groups:
-- ----------------------------------------------------

mrtGeneral OBJECT IDENTIFIER ::= { lumMultirateMIBObjects 1 }
mrtIfList OBJECT IDENTIFIER ::= { lumMultirateMIBObjects 2 }
lumentisMrtNotifications  OBJECT IDENTIFIER ::= { lumMultirateMIBObjects 3 }


-- ----------------------------------------------------
-- Textual Conventions
-- ----------------------------------------------------


-- ----------------------------------------------------
-- General group
-- ----------------------------------------------------

mrtGeneralTestAndIncr OBJECT-TYPE
    SYNTAX      TestAndIncr
    MAX-ACCESS  read-write
    STATUS      current
    DESCRIPTION
        "Protection against simultaneous access from
        multiple managers. See SNMPv2-TC.

"
    DEFVAL { 1 }
    ::= { mrtGeneral 1 }

mrtGeneralMibSpecVersion OBJECT-TYPE
    SYNTAX      DisplayString
    MAX-ACCESS  read-write
    STATUS      current
    DESCRIPTION
        "The MIB specification version.

"
    DEFVAL { "" }
    ::= { mrtGeneral 2 }

mrtGeneralMibImplVersion OBJECT-TYPE
    SYNTAX      DisplayString
    MAX-ACCESS  read-write
    STATUS      current
    DESCRIPTION
        "The MIB implementation version.

"
    DEFVAL { "" }
    ::= { mrtGeneral 3 }

mrtGeneralLastChangeTime OBJECT-TYPE
    SYNTAX      DateAndTime
    MAX-ACCESS  read-only
    STATUS      current
    DESCRIPTION
        "The time when the configuration of the MIB was
        last changed.

"
    ::= { mrtGeneral 4 }

mrtGeneralStateLastChangeTime OBJECT-TYPE
    SYNTAX      DateAndTime
    MAX-ACCESS  read-only
    STATUS      current
    DESCRIPTION
        "The time when the state of the MIB was last
        changed.

"
    ::= { mrtGeneral 5 }

mrtGeneralMrtIfTableSize OBJECT-TYPE
    SYNTAX      Unsigned32
    MAX-ACCESS  read-only
    STATUS      current
    DESCRIPTION
        "Size of table

"
    ::= { mrtGeneral 6 }


-- ----------------------------------------------------
-- Multi-bit rate client interfaces
-- ----------------------------------------------------

mrtIfTable  OBJECT-TYPE
    SYNTAX      SEQUENCE OF MrtIfEntry
    MAX-ACCESS  not-accessible
    STATUS      current
    DESCRIPTION
        "The interface list."
    ::= { mrtIfList 1 }

mrtIfEntry OBJECT-TYPE
    SYNTAX      MrtIfEntry
    MAX-ACCESS  not-accessible
    STATUS      current
    DESCRIPTION
        "An entry in the interface list.

"
    INDEX { mrtIfIndex }
    ::= { mrtIfTable 1 }

MrtIfEntry ::=
    SEQUENCE {
        mrtIfIndex                      Unsigned32,
        mrtIfName                       MgmtNameString,
        mrtIfDescr                      DisplayString,
        mrtIfSubrack                    SubrackNumber,
        mrtIfSlot                       SlotNumber,
        mrtIfTxPort                     PortNumber,
        mrtIfRxPort                     PortNumber,
        mrtIfInvPhysIndexOrZero         Unsigned32,
        mrtIfFormat                     SignalFormat,
        mrtIfHighSpeed                  Gauge32,
        mrtIfHighSpeedMin               Gauge32,
        mrtIfHighSpeedMax               Gauge32,
        mrtIfPowerLevel                 Integer32,
        mrtIfPowerLevelHighThreshold    Integer32,
        mrtIfPowerLevelLowThreshold     Integer32,
        mrtIfLaserStatus                INTEGER,
        mrtIfAdminStatus                BoardOrInterfaceAdminStatus,
        mrtIfOperStatus                 BoardOrInterfaceOperStatus,
        mrtIfLossOfSignal               FaultStatus,
        mrtIfReceivedPowerHigh          FaultStatus,
        mrtIfReceivedPowerLow           FaultStatus,
        mrtIfLaserBiasHigh              FaultStatus,
        mrtIfErroredSeconds             FaultStatus,
        mrtIfSeverelyErroredSeconds     FaultStatus,
        mrtIfBackgroundBlockErrors      FaultStatus,
        mrtIfUnavailableSeconds         FaultStatus,
        mrtIfLossOfFrame                FaultStatus,
        mrtIfMsAlarmIndicationSignalC2W FaultStatus,
        mrtIfRemoteDefectIndication     FaultStatus,
        mrtIfLossOfSync                 FaultStatus,
        mrtIfBitrateMismatch            FaultStatus,
        mrtIfLaserBias                  Unsigned32,
        mrtIfLaserBiasThreshold         Unsigned32,
        mrtIfJ0PathTrace                OCTET STRING,
        mrtIfAuAlarmIndicationSignalW2C FaultStatus,
        mrtIfAuLossOfPointerW2C         FaultStatus,
        mrtIfTxSignalStatus             INTEGER,
        mrtIfTruncVc4                   Unsigned32,
        mrtIfAuAlarmIndicationSignalC2W FaultStatus,
        mrtIfAuLossOfPointerC2W         FaultStatus,
        mrtIfTraceIntrusionMode         INTEGER,
        mrtIfTraceTransmitted           DisplayString,
        mrtIfTraceReceived              DisplayString,
        mrtIfTraceExpected              DisplayString,
        mrtIfTraceAlarmMode             INTEGER,
        mrtIfTraceMismatch              FaultStatus,
        mrtIfTruncVc4Status             INTEGER,
        mrtIfMsAlarmIndicationSignalW2C FaultStatus,
        mrtIfForwardAls                 INTEGER,
        mrtIfSuppressRemoteAlarms       INTEGER,
        mrtIfConfigurationCommand       CommandString,
        mrtIfTrxCodeMismatch            FaultStatus,
        mrtIfTrxBitrateUnavailable      FaultStatus,
        mrtIfTrxMissing                 FaultStatus,
        mrtIfTrxClass                   DisplayString,
        mrtIfEntityId                   Unsigned32,
        mrtIfTransmitterFailed          FaultStatus,
        mrtIfReceiverSensitivity        Integer32,
        mrtIfPowerLevelLowRelativeThreshold Integer32,
        mrtIfFarEndLoopback             INTEGER,
        mrtIfConfigureModeCommand       CommandString,
        mrtIfTrxMode                    INTEGER,
        mrtIfExpectedTxFrequency        LambdaFrequency,
        mrtIfTxFrequency                LambdaFrequency,
        mrtIfUnexpectedTxFrequency      FaultStatus,
        mrtIfIllegalFrequency           FaultStatus,
        mrtIfTrxMedia                   TrxMedia,
        mrtIfTrxMediaMismatch           FaultStatus,
        mrtIfLaserForcedOn              INTEGER,
        mrtIfTruncAutoNegotiationMode   INTEGER,
        mrtIfObjectProperty             ObjectProperty,
        mrtIfTxPowerLevel               Integer32,
        mrtIfLaserTempActual            Integer32,
        mrtIfHighSpeed2                 Gauge32,
        mrtIfRxSignalStatus             INTEGER }

mrtIfIndex OBJECT-TYPE
    SYNTAX      Unsigned32 (1..2147483647)
    MAX-ACCESS  read-only
    STATUS      current
    DESCRIPTION
        "An arbitrary index assigned to each entry.

"
    ::= { mrtIfEntry 1 }

mrtIfName OBJECT-TYPE
    SYNTAX      MgmtNameString
    MAX-ACCESS  read-only
    STATUS      current
    DESCRIPTION
        "The management name of the interface, for
        example 'mrti1:2:1', where the first number
        indicates sub-rack, the second slot number and
        the third is the port number.
        Examples:

        mrti:s:s:p - Multirate client interface

        stm1:s:s:p - STM-1/OC3 client interface

        stm4:s:s:p - STM-4/OC12 client interface

"
    ::= { mrtIfEntry 2 }

mrtIfDescr OBJECT-TYPE
    SYNTAX      DisplayString
    MAX-ACCESS  read-write
    STATUS      current
    DESCRIPTION
        "User configurable label.

        This attribute can be written via SNMP.
"
    DEFVAL { "" }
    ::= { mrtIfEntry 3 }

mrtIfSubrack OBJECT-TYPE
    SYNTAX      SubrackNumber
    MAX-ACCESS  read-only
    STATUS      current
    DESCRIPTION
        "The number of the subrack where the interface
        is located.

"
    ::= { mrtIfEntry 4 }

mrtIfSlot OBJECT-TYPE
    SYNTAX      SlotNumber
    MAX-ACCESS  read-only
    STATUS      current
    DESCRIPTION
        "The number of the slot where the interface is
        located.

"
    ::= { mrtIfEntry 5 }

mrtIfTxPort OBJECT-TYPE
    SYNTAX      PortNumber
    MAX-ACCESS  read-only
    STATUS      current
    DESCRIPTION
        "The number of the port where the TX-side of the
        interface is located.

"
    ::= { mrtIfEntry 6 }

mrtIfRxPort OBJECT-TYPE
    SYNTAX      PortNumber
    MAX-ACCESS  read-only
    STATUS      current
    DESCRIPTION
        "The number of the port where the RX-side of the
        interface is located.

"
    ::= { mrtIfEntry 7 }

mrtIfInvPhysIndexOrZero OBJECT-TYPE
    SYNTAX      Unsigned32 (0..2147483647)
    MAX-ACCESS  read-only
    STATUS      current
    DESCRIPTION
        "The row in the invPhysTable for this interface.
        Set to 0 if not known.

"
    ::= { mrtIfEntry 8 }

mrtIfFormat OBJECT-TYPE
    SYNTAX      SignalFormat
    MAX-ACCESS  read-create
    STATUS      current
    DESCRIPTION
        "The expected signal format.

        The default value is board dependent. For information
        about the default value for this particular board,
        please refer to the user manual.

"
    DEFVAL { stm16 }
    ::= { mrtIfEntry 9 }

mrtIfHighSpeed OBJECT-TYPE
    SYNTAX      Gauge32 (125..2500)
    MAX-ACCESS  read-create
    STATUS      current
    DESCRIPTION
        "The expected signal bit rate in units of
        1,000,000 bits (Mb) per second. If this object
        reports a value of 'n' then the speed of the
        interface is somewhere in the range of 'n-500,000'
        to 'n+499,999'.

"
    DEFVAL { 2500 }
    ::= { mrtIfEntry 10 }

mrtIfHighSpeedMin OBJECT-TYPE
    SYNTAX      Gauge32
    MAX-ACCESS  read-only
    STATUS      current
    DESCRIPTION
        "The minmum speed in units of 1,000,000 bits (Mb)
        per second. If this object reports a value of 'n'
        then the speed of the interface is somewhere in
        the range of 'n-500,000' to 'n+499,999'.

"
    ::= { mrtIfEntry 11 }

mrtIfHighSpeedMax OBJECT-TYPE
    SYNTAX      Gauge32
    MAX-ACCESS  read-only
    STATUS      current
    DESCRIPTION
        "The maximum speed in units of 1,000,000 bits per
        second. If this object reports a value of 'n'
        then the speed of the interface is somewhere in
        the range of 'n-500,000' to 'n+499,999'.

"
    ::= { mrtIfEntry 12 }

mrtIfPowerLevel OBJECT-TYPE
    SYNTAX      Integer32
    MAX-ACCESS  read-only
    STATUS      current
    DESCRIPTION
        "The received power level in units of 0.1 dBm.

"
    ::= { mrtIfEntry 13 }

mrtIfPowerLevelHighThreshold OBJECT-TYPE
    SYNTAX      Integer32 (-280..0)
    MAX-ACCESS  read-write
    STATUS      current
    DESCRIPTION
        "The upper threshold for received power level in
        units of 0.1 dBm.

        Note: Depending on the type of board and interface
        the value range may vary. The 'stm4' and 'stm1'
        ranges are applicable for muxponder interfaces.

"
    DEFVAL { -80 }
    ::= { mrtIfEntry 14 }

mrtIfPowerLevelLowThreshold OBJECT-TYPE
    SYNTAX      Integer32 (-280..0)
    MAX-ACCESS  read-write
    STATUS      current
    DESCRIPTION
        "The lower threshold for received power level in
        units of 0.1 dBm.

        Note: Depending on the type of board and interface
        the value range may vary. The 'stm4' and 'stm1'
        ranges are applicable for muxponder interfaces.

"
    DEFVAL { -200 }
    ::= { mrtIfEntry 15 }

mrtIfLaserStatus OBJECT-TYPE
    SYNTAX      INTEGER {
                    off (1),
                    on (2) }
    MAX-ACCESS  read-only
    STATUS      current
    DESCRIPTION
        "The operational state of the laser.

        off - The laser is turned off.

        on - The laser is turned on.

"
    ::= { mrtIfEntry 16 }

mrtIfAdminStatus OBJECT-TYPE
    SYNTAX      BoardOrInterfaceAdminStatus
    MAX-ACCESS  read-write
    STATUS      current
    DESCRIPTION
        "The administrative state for the interface.

        down - The interface should be inactive.

        service - The interface is activated but alarms
        are suppressed. Intended for use during service
        or re-configuration. When service is concluded
        adminStatus should be set to 'up' again.

        up - The interface should be activated when
        it becomes available. Alarms are not suppressed.

        This attribute can be written via SNMP.
"
    DEFVAL { up }
    ::= { mrtIfEntry 17 }

mrtIfOperStatus OBJECT-TYPE
    SYNTAX      BoardOrInterfaceOperStatus
    MAX-ACCESS  read-only
    STATUS      current
    DESCRIPTION
        "The operational state for the interface.

        notPresent - The physical resources are not
        available.

        down - The interface is de-activated or the are
        faults preventing it from going to the
        'up'-state.

        up - The interface is operational.

"
    DEFVAL { notPresent }
    ::= { mrtIfEntry 18 }

mrtIfLossOfSignal OBJECT-TYPE
    SYNTAX      FaultStatus
    MAX-ACCESS  read-only
    STATUS      current
    DESCRIPTION
        "Loss of signal.
        Applicable for all signal formats.

        A(ctivation): Active loss of signal HW
        indication.

        D(e-activation): Inactive loss of signal HW
        indication.

"
    ::= { mrtIfEntry 19 }

mrtIfReceivedPowerHigh OBJECT-TYPE
    SYNTAX      FaultStatus
    MAX-ACCESS  read-only
    STATUS      current
    DESCRIPTION
        "Received power level is too high.
        Applicable for all signal formats.

        A: The received power level exceeds the
        the built-in overload threshold.

        D: The received power level is 0.5 dB below the
        overload threshold.

"
    ::= { mrtIfEntry 20 }

mrtIfReceivedPowerLow OBJECT-TYPE
    SYNTAX      FaultStatus
    MAX-ACCESS  read-only
    STATUS      current
    DESCRIPTION
        "Received power level low threshold exceeded.
        Applicable for all signal formats.

        A: The received power level is below the
        associated threshold.

        D: The received power level is 0.5 dB above the
        threshold.

"
    ::= { mrtIfEntry 21 }

mrtIfLaserBiasHigh OBJECT-TYPE
    SYNTAX      FaultStatus
    MAX-ACCESS  read-only
    STATUS      current
    DESCRIPTION
        "Laser bias high threshold exceeded.

        A: The laser bias current exceeds the
        associated threshold.

        D: The laser bias current is 0.5 mA below the
        associated threshold.

"
    ::= { mrtIfEntry 22 }

mrtIfErroredSeconds OBJECT-TYPE
    SYNTAX      FaultStatus
    MAX-ACCESS  read-only
    STATUS      deprecated
    DESCRIPTION
        "Note: This attribute is deprecated!

        Errored seconds threshold exceeded.

        A: The number of errored seconds (ES) during a
        period exceeds the associated threshold.

        D: At the start of a new period.

"
    ::= { mrtIfEntry 23 }

mrtIfSeverelyErroredSeconds OBJECT-TYPE
    SYNTAX FaultStatus
    MAX-ACCESS  read-only
    STATUS      deprecated
    DESCRIPTION
        "Note: This attribute is deprecated!

        Severely errored seconds (SES) threshold exceeded.

        A: The number of severely errored seconds during a period
        exceeds the associated threshold.

        D: At the start of a new period.

"
    ::= { mrtIfEntry 24 }

mrtIfBackgroundBlockErrors OBJECT-TYPE
    SYNTAX FaultStatus
    MAX-ACCESS  read-only
    STATUS      deprecated
    DESCRIPTION
        "Note: This attribute is deprecated!

        Background block errors (BBE) threshold exceeded.

        A: The number of errors during a period
        exceeds the associated threshold.

        D: At the start of a new period.

"
    ::= { mrtIfEntry 25 }

mrtIfUnavailableSeconds OBJECT-TYPE
    SYNTAX FaultStatus
    MAX-ACCESS  read-only
    STATUS      deprecated
    DESCRIPTION
        "Note: This attribute is deprecated!

        Unavailable seconds (UAS) threshold exceeded.

        A: The number of unavailable seconds during a period
        exceeds the associated threshold.

        D: At the start of a new period.

"
    ::= { mrtIfEntry 26 }

mrtIfLossOfFrame OBJECT-TYPE
    SYNTAX      FaultStatus
    MAX-ACCESS  read-only
    STATUS      current
    DESCRIPTION
        "Loss of frame.
        Applicable for SDH/Sonet signal formats.

        A: SDH frame can not be located.

        D: SDH frame is located.

"
    ::= { mrtIfEntry 27 }

mrtIfMsAlarmIndicationSignalC2W OBJECT-TYPE
    SYNTAX      FaultStatus
    MAX-ACCESS  read-only
    STATUS      current
    DESCRIPTION
        "MS Alarm indication signal (MS-AIS) on the
        client side.
        Applicable for SDH/Sonet signal formats.

        A: An 'all ones' SDH signal is detected.

        D: SDH signal recovered.

"
    ::= { mrtIfEntry 28 }

mrtIfRemoteDefectIndication OBJECT-TYPE
    SYNTAX      FaultStatus
    MAX-ACCESS  read-only
    STATUS      current
    DESCRIPTION
        "Remote defect indication.
        Applicable for SDH/Sonet signal formats.

        A: RDI indication (in SDH frame) active.

        D: RDI indication inactive.

"
    ::= { mrtIfEntry 29 }

mrtIfLossOfSync OBJECT-TYPE
    SYNTAX      FaultStatus
    MAX-ACCESS  read-only
    STATUS      current
    DESCRIPTION
        "Loss of sync (GbE).
        Applicable for GbE signal formats.

        A: GbE 'frame' can not be located.

        D: GbE 'frame' is located.
"
    ::= { mrtIfEntry 30 }

mrtIfBitrateMismatch OBJECT-TYPE
    SYNTAX      FaultStatus
    MAX-ACCESS  read-only
    STATUS      current
    DESCRIPTION
        "Bitrate mismatch (Other).
        Applicable for other signal formats.

        D: The interface is unable to lock to the
        inserted signal.

        D: The interface is able to lock to the
        inserted signal.

"
    ::= { mrtIfEntry 31 }

mrtIfLaserBias OBJECT-TYPE
    SYNTAX      Unsigned32
    MAX-ACCESS  read-only
    STATUS      current
    DESCRIPTION
        "Measures laser bias current value in tenths of
        mA (0.1 mA).

"
    ::= { mrtIfEntry 32 }

mrtIfLaserBiasThreshold OBJECT-TYPE
    SYNTAX      Unsigned32 (0..300)
    MAX-ACCESS  read-write
    STATUS      current
    DESCRIPTION
        "Sets the threshold for the laser bias alarm.
        in percentage relative to the value set during
        production.
        The preset value is 100%.

"
    DEFVAL { 200 }
    ::= { mrtIfEntry 33 }

mrtIfJ0PathTrace OBJECT-TYPE
    SYNTAX      OCTET STRING (SIZE (1 | 16))
    MAX-ACCESS  read-only
    STATUS      current
    DESCRIPTION
        "The recevied J0 path trace string.
        Applicable for SDH/Sonet signal formats.

"
    ::= { mrtIfEntry 34 }

mrtIfAuAlarmIndicationSignalW2C OBJECT-TYPE
    SYNTAX      FaultStatus
    MAX-ACCESS  read-only
    STATUS      current
    DESCRIPTION
        "Alarm indication signal (AIS) on the trunk-side.
        Applicable for SDH/Sonet signal formats.

        A: An 'all ones' SDH signal is detected.

        D: SDH signal recovered.
"
    ::= { mrtIfEntry 35 }

mrtIfAuLossOfPointerW2C OBJECT-TYPE
    SYNTAX      FaultStatus
    MAX-ACCESS  read-only
    STATUS      current
    DESCRIPTION
        "Loss of pointer detected on the trunk-side.
        Applicable for SDH/Sonet signal formats.

        A: A loss of pointer is detected.

        D: SDH signal recovered.

"
    ::= { mrtIfEntry 36 }

mrtIfTxSignalStatus OBJECT-TYPE
    SYNTAX      INTEGER {
                        down (1),
                        degraded (2),
                        up (3) }
    MAX-ACCESS  read-only
    STATUS      current
    DESCRIPTION
        "The operational state for outgoing (TX) signal
        of the interface.

        down - A fault that would lead to a protection
        switch has occurred.

        degraded - The signal quality is impaired.

        up - The signal is OK.

"
    ::= { mrtIfEntry 37 }

mrtIfTruncVc4 OBJECT-TYPE
    SYNTAX      Unsigned32 (0..16)
    MAX-ACCESS  read-write
    STATUS      current
    DESCRIPTION
        "States which VC4 in the STM-16 frame that the
        interface is connected to.

         0 means unconnected, i.e. the signal passes
         through. (This may cause a loop depending on
         network topology.)

         For an STM-1 interface the VC4 to be dropped
         is identified.

         For an STM-4 interface the the first VC4 in the
         'quartet' is identified.
         Legal values are 1, 5, 9, 13.

        This attribute can be written via SNMP.
"
    DEFVAL { 0 }
    ::= { mrtIfEntry 38 }

mrtIfAuAlarmIndicationSignalC2W OBJECT-TYPE
    SYNTAX      FaultStatus
    MAX-ACCESS  read-only
    STATUS      current
    DESCRIPTION
        "Alarm indication signal (AIS) on the
        client-side.
        Applicable for SDH/Sonet signal formats.

        A: An 'all ones' SDH signal is detected.

        D: SDH signal recovered.
"
    ::= { mrtIfEntry 39 }

mrtIfAuLossOfPointerC2W OBJECT-TYPE
    SYNTAX      FaultStatus
    MAX-ACCESS  read-only
    STATUS      current
    DESCRIPTION
        "Loss of pointer detected on the client-side.
        Applicable for SDH/Sonet signal formats.

        A: A loss of pointer is detected.

        D: SDH signal recovered.

"
    ::= { mrtIfEntry 40 }

mrtIfTraceIntrusionMode OBJECT-TYPE
    SYNTAX      INTEGER {
                    disabled (1),
                    enabled (2) }
    MAX-ACCESS  read-write
    STATUS      current
    DESCRIPTION
        "Indicates wether the trace identifier should be
        inserted in the transmitted signal.

        disabled - The trace identifier is taken from
        the recevied signal if possible.

        enabled -  The trace identifier set is inserted
        in the transmitted signal.

"
    DEFVAL { disabled }
    ::= { mrtIfEntry 41 }

mrtIfTraceTransmitted   OBJECT-TYPE
    SYNTAX      DisplayString (SIZE(0..15))
    MAX-ACCESS  read-write
    STATUS      current
    DESCRIPTION
        "The trace identifier to be transmitted from this
        interface.

        Set to empty string for default value:

        <IP address>:<subrack>:<slot>:<port>

        Note that only the last part of the address
        is used.
"
    DEFVAL { "" }
    ::= { mrtIfEntry 42 }

mrtIfTraceReceived OBJECT-TYPE
    SYNTAX      DisplayString (SIZE(0..15))
    MAX-ACCESS  read-only
    STATUS      current
    DESCRIPTION
        "The received trace identifier for this interface.

"
    ::= { mrtIfEntry 43 }

mrtIfTraceExpected OBJECT-TYPE
    SYNTAX      DisplayString (SIZE(0..15))
    MAX-ACCESS  read-write
    STATUS      current
    DESCRIPTION
        "Trace identifier used for matching against
        the received trace identifier.

"
    DEFVAL { "" }
    ::= { mrtIfEntry 44 }

mrtIfTraceAlarmMode OBJECT-TYPE
    SYNTAX      INTEGER {
                    disabled (1),
                    enabled (2) }
    MAX-ACCESS  read-write
    STATUS      current
    DESCRIPTION
        "Controls if the trace identifier mismatch alarm
        should be raised.

        disabled - The alarm is disabled.

        enabled - The alarm is raised if expected trace
        identifier differs from the received trace
        identifier.

"
    DEFVAL { disabled }
    ::= { mrtIfEntry 45 }

mrtIfTraceMismatch OBJECT-TYPE
    SYNTAX      FaultStatus
    MAX-ACCESS  read-only
    STATUS      current
    DESCRIPTION
        "Indicates if the expected trace identifier
        differs from the received trace identifier.

        A: The received trace identifier differs from
        the expected trace identifier.

        D: The identifiers match.

"
    ::= { mrtIfEntry 46 }

mrtIfTruncVc4Status OBJECT-TYPE
    SYNTAX      INTEGER {
                          undefined (0),
                          addDrop (1),
                          passThrough (2),
                          unconnected (3) }
    MAX-ACCESS  read-only
    STATUS      deprecated
    DESCRIPTION
        "Shows the status of the VC4(s) that this port is
        connected to.

         undefined - used when the port is not connected
         to any VC4. Also used when an STM4 port is VC4s
         that have conflicting modes.

         addDrop - the VC4 is connected to this port
         (normal)

         passThrough - Should not occur

         unconnected - the vc4 is unused. Set it to
         nodeUsed to complete the add/drop.

"
    ::= { mrtIfEntry 47 }

mrtIfMsAlarmIndicationSignalW2C OBJECT-TYPE
    SYNTAX      FaultStatus
    MAX-ACCESS  read-only
    STATUS      current
    DESCRIPTION
        "MS Alarm indication signal (MS-AIS) on the trunc
        side. Applicable for SDH/Sonet signal formats.

        A: An 'all ones' SDH signal is detected.

        D: SDH signal recovered.

"
    ::= { mrtIfEntry 48 }

mrtIfForwardAls OBJECT-TYPE
    SYNTAX      INTEGER {
                    disabled (1),
                    enabled (2) }
    MAX-ACCESS  read-write
    STATUS      current
    DESCRIPTION
        "Forward Automatic Laser Shut-down. Decides the
        behaviour of the client laser (W2C) when the
        trunc signal is defected.

        disabled - The laser is NOT turned off at failure.

        enabled - The laser is turned off at failure.

"
    DEFVAL { disabled }
    ::= { mrtIfEntry 49 }

mrtIfSuppressRemoteAlarms OBJECT-TYPE
    SYNTAX      INTEGER {
                    disabled (1),
                    enabled (2) }
    MAX-ACCESS  read-write
    STATUS      current
    DESCRIPTION
        "Suppress AIS and RDI in the alarm list.
        The fault status on the port object can, however,
        be seen.

        disabled - alarms are not suppressed.

        enabled - alarms are suppressed.

"
    DEFVAL { disabled }
    ::= { mrtIfEntry 50 }

mrtIfConfigurationCommand OBJECT-TYPE
    SYNTAX      CommandString
    MAX-ACCESS  read-only
    STATUS      current
    DESCRIPTION
        "Command to change the signal format and,
        if applicable, also the speed.

        Synopsis: configure [<format> [<speed>]]

        If no arguments are given, the user will be prompted.

        tpQMr, tpQMri, tpqmp: If speed is set manually, the
        Bitrate unavailable alarm will not appear even if the
        there is a difference between the transceiver speed
        and the chosen speed.

"
    ::= { mrtIfEntry 51 }

mrtIfTrxCodeMismatch OBJECT-TYPE
    SYNTAX      FaultStatus
    MAX-ACCESS  read-only
    STATUS      current
    DESCRIPTION
        "The inserted transceiver does not have a legal
        manufacturer code.

        A: A transceiver with illegal code is inserted.

        D: The transceiver with illegal code is removed.

"
    ::= { mrtIfEntry 52 }

mrtIfTrxBitrateUnavailable OBJECT-TYPE
    SYNTAX      FaultStatus
    MAX-ACCESS  read-only
    STATUS      current
    DESCRIPTION
        "The inserted transceiver does not support the requested
        bit rate.

        A: A transceiver with other supported bit rate than
           the requested bit rate is inserted.

        D: The transceiver with the non-requested bit rate is
           removed, or the object is reconfigured.

"
    ::= { mrtIfEntry 53 }

mrtIfTrxMissing OBJECT-TYPE
    SYNTAX      FaultStatus
    MAX-ACCESS  read-only
    STATUS      current
    DESCRIPTION
        "An expected transceiver is missing.

        A: An expected transceiver is missing.

        D: The missing transceiver is inserted.

"
    ::= { mrtIfEntry 54 }

mrtIfTrxClass OBJECT-TYPE
    SYNTAX      DisplayString
    MAX-ACCESS  read-only
    STATUS      current
    DESCRIPTION
        "String that describes the transceiver class.

"
    DEFVAL { "" }
    ::= { mrtIfEntry 55 }

mrtIfEntityId OBJECT-TYPE
    SYNTAX      Unsigned32 (1..2147483647)
    MAX-ACCESS  read-only
    STATUS      current
    DESCRIPTION
        "Index in entity table.

        -- Only used for notifications

"
    ::= { mrtIfEntry 56 }

mrtIfTransmitterFailed OBJECT-TYPE
    SYNTAX      FaultStatus
    MAX-ACCESS  read-only
    STATUS      current
    DESCRIPTION
        "The transceiver HW has detected a failure
         in the transmitter part.

        A: The transmitter has failed

        D: The transmitter is OK again


"
    ::= { mrtIfEntry 57 }

mrtIfReceiverSensitivity OBJECT-TYPE
    SYNTAX      Integer32
    MAX-ACCESS  read-only
    STATUS      current
    DESCRIPTION
        "The lowest power that the receiver is guaranteed
        to handle, in units of 0.1 dBm.

"
    ::= { mrtIfEntry 58 }

mrtIfPowerLevelLowRelativeThreshold OBJECT-TYPE
    SYNTAX      Integer32 (-50..100)
    MAX-ACCESS  read-write
    STATUS      current
    DESCRIPTION
        "The lower threshold for received power level in
        units of 0.1 dB, relative to the receiver
        sensitivity.

"
    DEFVAL { 30 }
    ::= { mrtIfEntry 59 }

mrtIfFarEndLoopback OBJECT-TYPE
    SYNTAX      INTEGER {
                    disabled (1),
                    enabled (2) }
    MAX-ACCESS  read-write
    STATUS      current
    DESCRIPTION
        "Loop the client TX signal back to the client RX.

        disabled - the signal is not looped

        enabled - the signal is looped.

"
    DEFVAL { disabled }
    ::= { mrtIfEntry 60 }

mrtIfConfigureModeCommand OBJECT-TYPE
    SYNTAX      CommandString
    MAX-ACCESS  read-only
    STATUS      current
    DESCRIPTION
        "Command to change the TRX mode: CLIENT or LINE.
         Also select the TRX media.

        Synopsis: configureMode [<trxMode>] [<trxMedia>]

        If no arguments are given, the user will be prompted.

"
    ::= { mrtIfEntry 61 }

mrtIfTrxMode OBJECT-TYPE
    SYNTAX      INTEGER {
                  client (1),
                  line (2) }
    MAX-ACCESS  read-create
    STATUS      current
    DESCRIPTION
        "Shows if the port is configured as:

         - normal CLIENT interface connected to non-Transmode
           or non-Infinera client equipment, with non-colored,
           or colored TRXes.

         - a LINE interface connected to other Transmode or
           Infinera equipment, typically with WDM TRXes.
           This should be used in cascade connections with
           tpQMR.

           Important1: Do not use 'line' mode unless you
           really have to.
           Important2: If this port constitute the edge of the
           Transmode/Infinera supplied network, and it is
           connected to other client equipment, then you must
           use 'client' mode in order to make use of the circuit
           supervision in TNM.

"
    DEFVAL { client }
    ::= { mrtIfEntry 62 }


mrtIfExpectedTxFrequency OBJECT-TYPE
    SYNTAX      LambdaFrequency
    MAX-ACCESS  read-write
    STATUS      current
    DESCRIPTION
        "The expected frequency given in hundreds of GHz
        (0.01 GHz).

"
    DEFVAL { 0 }
    ::= { mrtIfEntry 63 }

mrtIfTxFrequency OBJECT-TYPE
    SYNTAX      LambdaFrequency
    MAX-ACCESS  read-only
    STATUS      current
    DESCRIPTION
        "The transmitted frequency given in hundreds of
        GHz (0.01 GHz).

"
    ::= { mrtIfEntry 64 }

mrtIfUnexpectedTxFrequency OBJECT-TYPE
    SYNTAX      FaultStatus
    MAX-ACCESS  read-only
    STATUS      current
    DESCRIPTION
        "The actual frequency does not match the
        pre-configured frequency.

        A pre-configured frequency of '0' matches
        all actual frequencies.

        A: The configured frequency does not match the
        actual frequency.

        D: The configured frequency matches the actual
        frequency.

"
    ::= { mrtIfEntry 65 }

mrtIfIllegalFrequency OBJECT-TYPE
    SYNTAX      FaultStatus
    MAX-ACCESS  read-only
    STATUS      current
    DESCRIPTION
        "The frequency supported by the transceiver is not
        recognized by the system.

        A: Invalid or unknown frequency information is
           detected in the (pluggable) transceiver or
           board production data.

        D: The (pluggable) transceiver or board is
           replaced.

"
    ::= { mrtIfEntry 66 }

mrtIfTrxMedia OBJECT-TYPE
    SYNTAX      TrxMedia
    MAX-ACCESS  read-create
    STATUS      current
    DESCRIPTION
        "Defines the media and capability of the TRX.

"
    DEFVAL { optical }
    ::= { mrtIfEntry 67 }

mrtIfTrxMediaMismatch OBJECT-TYPE
    SYNTAX      FaultStatus
    MAX-ACCESS  read-only
    STATUS      current
    DESCRIPTION
        "The TRX media does not match the expected one.

        A: Invalid or mismatching trx media is
           detected.

        D: The (pluggable) transceiver or board is
           replaced, or the configuration is changed.

"
    ::= { mrtIfEntry 68 }

mrtIfLaserForcedOn OBJECT-TYPE
    SYNTAX      INTEGER {
                    disabled (1),
                    enabled (2) }
    MAX-ACCESS  read-write
    STATUS      current
    DESCRIPTION
        "When enabled, the laser is on regardless of whether
         there is a trunc signal present or not.

        disabled - the laser is only on when there is a
                   trunc signal.

        enabled  - the laser is always on. This is intended
                   to be used at installation to generate
                   light on the client side for the QMR board
                   to verify the connectivity.

"
    DEFVAL { disabled }
    ::= { mrtIfEntry 69 }

mrtIfTruncAutoNegotiationMode OBJECT-TYPE
    SYNTAX      INTEGER {
                    disabled (1),
                    enabled (2) }
    MAX-ACCESS  read-write
    STATUS      current
    DESCRIPTION
        "Decides whether auto negotiation shall
         be performed over the trunc connection.

         This is applicable when the terminating
         node at the other side of the
         trunc is configured as follows:

           - it has an optical client interface
           - its client equipment (e.g. a router)
             requires auto negotiation.

        disabled - Do not perform auto neg over the
                   trunc


        enabled  - Perform auto neg over the trunc.

"
    DEFVAL { disabled }
    ::= { mrtIfEntry 70 }

mrtIfObjectProperty OBJECT-TYPE
    SYNTAX      ObjectProperty
    MAX-ACCESS  read-only
    STATUS      current
    DESCRIPTION
        "Property mask.

"
    ::= { mrtIfEntry 71 }

mrtIfTxPowerLevel OBJECT-TYPE
    SYNTAX      Integer32
    MAX-ACCESS  read-only
    STATUS      current
    DESCRIPTION
        "The transmitted power level in units of 0.1 dBm.

"
    ::= { mrtIfEntry 72 }

mrtIfLaserTempActual OBJECT-TYPE
    SYNTAX      Integer32
    MAX-ACCESS  read-only
    STATUS      current
    DESCRIPTION
        "The actual laser temperature in units of
        0.1 degrees centigrade.

"
    ::= { mrtIfEntry 73 }

mrtIfHighSpeed2 OBJECT-TYPE
    SYNTAX      Gauge32 (12500..250000)
    MAX-ACCESS  read-write
    STATUS      current
    DESCRIPTION
        "The expected signal bit rate in units of
        1,000,000 bits (Mb) per second.
        The value is given with 2 decimals,
        so the resolution is 10 000 bits per second.

"
    DEFVAL { 250000 }
    ::= { mrtIfEntry 74 }

mrtIfRxSignalStatus OBJECT-TYPE
    SYNTAX      INTEGER {
                        down (1),
                        degraded (2),
                        up (3) }
    MAX-ACCESS  read-only
    STATUS      current
    DESCRIPTION
        "The operational state for incoming (RX) signal
        of the interface.

        down - A fault that would lead to a protection
        switch has occurred.

        degraded - The signal quality is impaired.

        up - The signal is OK.

"
    ::= { mrtIfEntry 75 }

-- ----------------------------------------------------
-- Notifications
-- ----------------------------------------------------

mrtNotifyPrefix OBJECT IDENTIFIER ::= { lumentisMrtNotifications 0 }

mrtIfTxSignalStatusDown NOTIFICATION-TYPE
    OBJECTS {
        mrtIfIndex,
        mrtIfName,
        mrtIfSubrack,
        mrtIfSlot,
        mrtIfTxPort,
        mrtIfRxPort,
        mrtIfEntityId,
        mrtIfTxSignalStatus }
    STATUS      current
    DESCRIPTION
        "Sent when the signal status attribute of an
        interface changes.

"
    ::= { mrtNotifyPrefix 1 }

mrtIfTxSignalStatusUp NOTIFICATION-TYPE
    OBJECTS {
        mrtIfIndex,
        mrtIfName,
        mrtIfSubrack,
        mrtIfSlot,
        mrtIfTxPort,
        mrtIfRxPort,
        mrtIfEntityId,
        mrtIfTxSignalStatus }
    STATUS      current
    DESCRIPTION
        "Sent when the signal status attribute of an
        interface changes.

"
    ::= { mrtNotifyPrefix 2 }

mrtIfTxSignalStatusDegraded NOTIFICATION-TYPE
    OBJECTS {
        mrtIfIndex,
        mrtIfName,
        mrtIfSubrack,
        mrtIfSlot,
        mrtIfTxPort,
        mrtIfRxPort,
        mrtIfEntityId,
        mrtIfTxSignalStatus }
    STATUS      current
    DESCRIPTION
        "Sent when the signal status attribute of an
        interface changes.

"
    ::= { mrtNotifyPrefix 3 }


-- ----------------------------------------------------
-- Object and event groups
-- ----------------------------------------------------

mrtGeneralGroup OBJECT-GROUP
    OBJECTS {
        mrtGeneralTestAndIncr,
        mrtGeneralMibSpecVersion,
        mrtGeneralMibImplVersion,
        mrtGeneralLastChangeTime }
    STATUS      deprecated
    DESCRIPTION
        "The general objects."
    ::= { lumMultirateGroups 1 }

mrtIfGroup OBJECT-GROUP
    OBJECTS {
        mrtIfIndex,
        mrtIfName,
        mrtIfDescr,
        mrtIfSubrack,
        mrtIfSlot,
        mrtIfTxPort,
        mrtIfRxPort,
        mrtIfInvPhysIndexOrZero,
        mrtIfFormat,
        mrtIfHighSpeed,
        mrtIfHighSpeedMin,
        mrtIfHighSpeedMax,
        mrtIfPowerLevel,
        mrtIfPowerLevelHighThreshold,
        mrtIfPowerLevelLowThreshold,
        mrtIfLaserStatus,
        mrtIfAdminStatus,
        mrtIfOperStatus,
        mrtIfLossOfSignal,
        mrtIfReceivedPowerHigh,
        mrtIfReceivedPowerLow,
        mrtIfLaserBiasHigh,
        mrtIfErroredSeconds,
        mrtIfSeverelyErroredSeconds,
        mrtIfBackgroundBlockErrors,
        mrtIfUnavailableSeconds,
        mrtIfLossOfFrame,
        mrtIfMsAlarmIndicationSignalC2W,
        mrtIfRemoteDefectIndication,
        mrtIfLossOfSync,
        mrtIfBitrateMismatch }
    STATUS      deprecated
    DESCRIPTION
        "The multirate interface objects."
    ::= { lumMultirateGroups 2 }

mrtGeneralGroupV2 OBJECT-GROUP
    OBJECTS {
        mrtGeneralLastChangeTime }
    STATUS      deprecated
    DESCRIPTION
        "The multirate general objects v2."
    ::= { lumMultirateGroups 3 }

mrtIfGroupV2 OBJECT-GROUP
    OBJECTS {
        mrtIfIndex,
        mrtIfName,
        mrtIfDescr,
        mrtIfSubrack,
        mrtIfSlot,
        mrtIfTxPort,
        mrtIfRxPort,
        mrtIfInvPhysIndexOrZero,
        mrtIfFormat,
        mrtIfHighSpeed,
        mrtIfHighSpeedMin,
        mrtIfHighSpeedMax,
        mrtIfPowerLevel,
        mrtIfPowerLevelHighThreshold,
        mrtIfPowerLevelLowThreshold,
        mrtIfLaserStatus,
        mrtIfAdminStatus,
        mrtIfOperStatus,
        mrtIfLossOfSignal,
        mrtIfReceivedPowerHigh,
        mrtIfReceivedPowerLow,
        mrtIfLaserBiasHigh,
        mrtIfErroredSeconds,
        mrtIfSeverelyErroredSeconds,
        mrtIfBackgroundBlockErrors,
        mrtIfUnavailableSeconds,
        mrtIfLossOfFrame,
        mrtIfMsAlarmIndicationSignalC2W,
        mrtIfRemoteDefectIndication,
        mrtIfLossOfSync,
        mrtIfBitrateMismatch,
        mrtIfLaserBias,
        mrtIfLaserBiasThreshold,
        mrtIfJ0PathTrace }
    STATUS      deprecated
    DESCRIPTION
        "The interface objects V2."
    ::= { lumMultirateGroups 4 }

mrtIfGroupV3 OBJECT-GROUP
    OBJECTS {
        mrtIfIndex,
        mrtIfName,
        mrtIfDescr,
        mrtIfSubrack,
        mrtIfSlot,
        mrtIfTxPort,
        mrtIfRxPort,
        mrtIfInvPhysIndexOrZero,
        mrtIfFormat,
        mrtIfHighSpeed,
        mrtIfHighSpeedMin,
        mrtIfHighSpeedMax,
        mrtIfPowerLevel,
        mrtIfPowerLevelHighThreshold,
        mrtIfPowerLevelLowThreshold,
        mrtIfLaserStatus,
        mrtIfAdminStatus,
        mrtIfOperStatus,
        mrtIfLossOfSignal,
        mrtIfReceivedPowerHigh,
        mrtIfReceivedPowerLow,
        mrtIfLaserBiasHigh,
        mrtIfErroredSeconds,
        mrtIfSeverelyErroredSeconds,
        mrtIfBackgroundBlockErrors,
        mrtIfUnavailableSeconds,
        mrtIfLossOfFrame,
        mrtIfMsAlarmIndicationSignalC2W,
        mrtIfRemoteDefectIndication,
        mrtIfLossOfSync,
        mrtIfBitrateMismatch,
        mrtIfLaserBias,
        mrtIfLaserBiasThreshold,
        mrtIfJ0PathTrace,
        mrtIfAuAlarmIndicationSignalW2C,
        mrtIfAuLossOfPointerW2C }
    STATUS      deprecated
    DESCRIPTION
        "The interface objects V3."
    ::= { lumMultirateGroups 5 }

mrtIfGroupV4 OBJECT-GROUP
    OBJECTS {
        mrtIfIndex,
        mrtIfName,
        mrtIfDescr,
        mrtIfSubrack,
        mrtIfSlot,
        mrtIfTxPort,
        mrtIfRxPort,
        mrtIfInvPhysIndexOrZero,
        mrtIfFormat,
        mrtIfHighSpeed,
        mrtIfHighSpeedMin,
        mrtIfHighSpeedMax,
        mrtIfPowerLevel,
        mrtIfPowerLevelHighThreshold,
        mrtIfPowerLevelLowThreshold,
        mrtIfLaserStatus,
        mrtIfAdminStatus,
        mrtIfOperStatus,
        mrtIfLossOfSignal,
        mrtIfReceivedPowerHigh,
        mrtIfReceivedPowerLow,
        mrtIfLaserBiasHigh,
        mrtIfLossOfFrame,
        mrtIfMsAlarmIndicationSignalC2W,
        mrtIfRemoteDefectIndication,
        mrtIfLossOfSync,
        mrtIfBitrateMismatch,
        mrtIfLaserBias,
        mrtIfLaserBiasThreshold,
        mrtIfJ0PathTrace,
        mrtIfAuAlarmIndicationSignalW2C,
        mrtIfAuLossOfPointerW2C,
        mrtIfTxSignalStatus }
    STATUS      deprecated
    DESCRIPTION
        "The interface objects V4."
    ::= { lumMultirateGroups 6 }

mrtNotificationGroup NOTIFICATION-GROUP
    NOTIFICATIONS {
        mrtIfTxSignalStatusDown,
        mrtIfTxSignalStatusUp }
    STATUS      deprecated
    DESCRIPTION
        "The multirate notifications."
    ::= { lumMultirateGroups 7 }

mrtGeneralGroupV3 OBJECT-GROUP
    OBJECTS {
        mrtGeneralLastChangeTime,
        mrtGeneralStateLastChangeTime }
    STATUS      deprecated
    DESCRIPTION
        "The multirate general objects v3."
    ::= { lumMultirateGroups 8 }

mrtIfGroupV5 OBJECT-GROUP
    OBJECTS {
        mrtIfIndex,
        mrtIfName,
        mrtIfDescr,
        mrtIfSubrack,
        mrtIfSlot,
        mrtIfTxPort,
        mrtIfRxPort,
        mrtIfInvPhysIndexOrZero,
        mrtIfFormat,
        mrtIfHighSpeed,
        mrtIfHighSpeedMin,
        mrtIfHighSpeedMax,
        mrtIfPowerLevel,
        mrtIfPowerLevelHighThreshold,
        mrtIfPowerLevelLowThreshold,
        mrtIfLaserStatus,
        mrtIfAdminStatus,
        mrtIfOperStatus,
        mrtIfLossOfSignal,
        mrtIfReceivedPowerHigh,
        mrtIfReceivedPowerLow,
        mrtIfLaserBiasHigh,
        mrtIfLossOfFrame,
        mrtIfMsAlarmIndicationSignalC2W,
        mrtIfRemoteDefectIndication,
        mrtIfLossOfSync,
        mrtIfBitrateMismatch,
        mrtIfLaserBias,
        mrtIfLaserBiasThreshold,
        mrtIfJ0PathTrace,
        mrtIfAuAlarmIndicationSignalW2C,
        mrtIfAuLossOfPointerW2C,
        mrtIfTxSignalStatus,
        mrtIfTruncVc4 }
    STATUS      deprecated
    DESCRIPTION
        "The interface objects V5."
    ::= { lumMultirateGroups 9 }

mrtIfGroupV6 OBJECT-GROUP
    OBJECTS {
        mrtIfIndex,
        mrtIfName,
        mrtIfDescr,
        mrtIfSubrack,
        mrtIfSlot,
        mrtIfTxPort,
        mrtIfRxPort,
        mrtIfInvPhysIndexOrZero,
        mrtIfFormat,
        mrtIfHighSpeed,
        mrtIfHighSpeedMin,
        mrtIfHighSpeedMax,
        mrtIfPowerLevel,
        mrtIfPowerLevelHighThreshold,
        mrtIfPowerLevelLowThreshold,
        mrtIfLaserStatus,
        mrtIfAdminStatus,
        mrtIfOperStatus,
        mrtIfLossOfSignal,
        mrtIfReceivedPowerHigh,
        mrtIfReceivedPowerLow,
        mrtIfLaserBiasHigh,
        mrtIfLossOfFrame,
        mrtIfMsAlarmIndicationSignalC2W,
        mrtIfRemoteDefectIndication,
        mrtIfLossOfSync,
        mrtIfBitrateMismatch,
        mrtIfLaserBias,
        mrtIfLaserBiasThreshold,
        mrtIfJ0PathTrace,
        mrtIfAuAlarmIndicationSignalW2C,
        mrtIfAuLossOfPointerW2C,
        mrtIfTxSignalStatus,
        mrtIfTruncVc4,
        mrtIfAuAlarmIndicationSignalC2W,
        mrtIfAuLossOfPointerC2W }
    STATUS      current
    DESCRIPTION
        "The interface objects V6."
    ::= { lumMultirateGroups 10 }

mrtIfGroupV7 OBJECT-GROUP
    OBJECTS {
        mrtIfIndex,
        mrtIfName,
        mrtIfDescr,
        mrtIfSubrack,
        mrtIfSlot,
        mrtIfTxPort,
        mrtIfRxPort,
        mrtIfInvPhysIndexOrZero,
        mrtIfFormat,
        mrtIfHighSpeed,
        mrtIfHighSpeedMin,
        mrtIfHighSpeedMax,
        mrtIfPowerLevel,
        mrtIfPowerLevelHighThreshold,
        mrtIfPowerLevelLowThreshold,
        mrtIfLaserStatus,
        mrtIfAdminStatus,
        mrtIfOperStatus,
        mrtIfLossOfSignal,
        mrtIfReceivedPowerHigh,
        mrtIfReceivedPowerLow,
        mrtIfLaserBiasHigh,
        mrtIfLossOfFrame,
        mrtIfMsAlarmIndicationSignalC2W,
        mrtIfRemoteDefectIndication,
        mrtIfLossOfSync,
        mrtIfBitrateMismatch,
        mrtIfLaserBias,
        mrtIfLaserBiasThreshold,
        mrtIfJ0PathTrace,
        mrtIfAuAlarmIndicationSignalW2C,
        mrtIfAuLossOfPointerW2C,
        mrtIfTxSignalStatus,
        mrtIfTruncVc4,
        mrtIfAuAlarmIndicationSignalC2W,
        mrtIfAuLossOfPointerC2W,
        mrtIfTraceIntrusionMode,
        mrtIfTraceTransmitted,
        mrtIfTraceReceived,
        mrtIfTraceExpected,
        mrtIfTraceAlarmMode,
        mrtIfTraceMismatch }
    STATUS      deprecated
    DESCRIPTION
        "The interface objects V7."
    ::= { lumMultirateGroups 11 }

mrtIfGroupV8 OBJECT-GROUP
    OBJECTS {
        mrtIfIndex,
        mrtIfName,
        mrtIfDescr,
        mrtIfSubrack,
        mrtIfSlot,
        mrtIfTxPort,
        mrtIfRxPort,
        mrtIfInvPhysIndexOrZero,
        mrtIfFormat,
        mrtIfHighSpeed,
        mrtIfHighSpeedMin,
        mrtIfHighSpeedMax,
        mrtIfPowerLevel,
        mrtIfPowerLevelHighThreshold,
        mrtIfPowerLevelLowThreshold,
        mrtIfLaserStatus,
        mrtIfAdminStatus,
        mrtIfOperStatus,
        mrtIfLossOfSignal,
        mrtIfReceivedPowerHigh,
        mrtIfReceivedPowerLow,
        mrtIfLaserBiasHigh,
        mrtIfLossOfFrame,
        mrtIfMsAlarmIndicationSignalC2W,
        mrtIfRemoteDefectIndication,
        mrtIfLossOfSync,
        mrtIfBitrateMismatch,
        mrtIfLaserBias,
        mrtIfLaserBiasThreshold,
        mrtIfJ0PathTrace,
        mrtIfAuAlarmIndicationSignalW2C,
        mrtIfAuLossOfPointerW2C,
        mrtIfTxSignalStatus,
        mrtIfTruncVc4,
        mrtIfAuAlarmIndicationSignalC2W,
        mrtIfAuLossOfPointerC2W,
        mrtIfTraceIntrusionMode,
        mrtIfTraceTransmitted,
        mrtIfTraceReceived,
        mrtIfTraceExpected,
        mrtIfTraceAlarmMode,
        mrtIfTraceMismatch,
        mrtIfTruncVc4Status }
    STATUS      deprecated
    DESCRIPTION
        "The interface objects V8."
    ::= { lumMultirateGroups 12 }

mrtIfGroupV9 OBJECT-GROUP
    OBJECTS {
        mrtIfIndex,
        mrtIfName,
        mrtIfDescr,
        mrtIfSubrack,
        mrtIfSlot,
        mrtIfTxPort,
        mrtIfRxPort,
        mrtIfInvPhysIndexOrZero,
        mrtIfFormat,
        mrtIfHighSpeed,
        mrtIfHighSpeedMin,
        mrtIfHighSpeedMax,
        mrtIfPowerLevel,
        mrtIfPowerLevelHighThreshold,
        mrtIfPowerLevelLowThreshold,
        mrtIfLaserStatus,
        mrtIfAdminStatus,
        mrtIfOperStatus,
        mrtIfLossOfSignal,
        mrtIfReceivedPowerHigh,
        mrtIfReceivedPowerLow,
        mrtIfLaserBiasHigh,
        mrtIfLossOfFrame,
        mrtIfMsAlarmIndicationSignalC2W,
        mrtIfRemoteDefectIndication,
        mrtIfLossOfSync,
        mrtIfBitrateMismatch,
        mrtIfLaserBias,
        mrtIfLaserBiasThreshold,
        mrtIfJ0PathTrace,
        mrtIfAuAlarmIndicationSignalW2C,
        mrtIfAuLossOfPointerW2C,
        mrtIfTxSignalStatus,
        mrtIfTruncVc4,
        mrtIfAuAlarmIndicationSignalC2W,
        mrtIfAuLossOfPointerC2W,
        mrtIfTraceIntrusionMode,
        mrtIfTraceTransmitted,
        mrtIfTraceReceived,
        mrtIfTraceExpected,
        mrtIfTraceAlarmMode,
        mrtIfTraceMismatch }
    STATUS      deprecated
    DESCRIPTION
        "The interface objects V9."
    ::= { lumMultirateGroups 13 }

mrtIfGroupV10 OBJECT-GROUP
    OBJECTS {
        mrtIfIndex,
        mrtIfName,
        mrtIfDescr,
        mrtIfSubrack,
        mrtIfSlot,
        mrtIfTxPort,
        mrtIfRxPort,
        mrtIfInvPhysIndexOrZero,
        mrtIfFormat,
        mrtIfHighSpeed,
        mrtIfHighSpeedMin,
        mrtIfHighSpeedMax,
        mrtIfPowerLevel,
        mrtIfPowerLevelHighThreshold,
        mrtIfPowerLevelLowThreshold,
        mrtIfLaserStatus,
        mrtIfAdminStatus,
        mrtIfOperStatus,
        mrtIfLossOfSignal,
        mrtIfReceivedPowerHigh,
        mrtIfReceivedPowerLow,
        mrtIfLaserBiasHigh,
        mrtIfLossOfFrame,
        mrtIfMsAlarmIndicationSignalC2W,
        mrtIfMsAlarmIndicationSignalW2C,
        mrtIfRemoteDefectIndication,
        mrtIfLossOfSync,
        mrtIfBitrateMismatch,
        mrtIfLaserBias,
        mrtIfLaserBiasThreshold,
        mrtIfJ0PathTrace,
        mrtIfAuAlarmIndicationSignalW2C,
        mrtIfAuLossOfPointerW2C,
        mrtIfTxSignalStatus,
        mrtIfTruncVc4,
        mrtIfAuAlarmIndicationSignalC2W,
        mrtIfAuLossOfPointerC2W,
        mrtIfTraceIntrusionMode,
        mrtIfTraceTransmitted,
        mrtIfTraceReceived,
        mrtIfTraceExpected,
        mrtIfTraceAlarmMode,
        mrtIfTraceMismatch,
        mrtIfForwardAls,
        mrtIfSuppressRemoteAlarms,
        mrtIfConfigurationCommand,
        mrtIfTrxCodeMismatch,
        mrtIfTrxBitrateUnavailable,
        mrtIfTrxMissing,
        mrtIfTrxClass,
        mrtIfEntityId,
        mrtIfTransmitterFailed,
        mrtIfReceiverSensitivity,
        mrtIfPowerLevelLowRelativeThreshold }
    STATUS      deprecated
    DESCRIPTION
        "The interface objects V10."
    ::= { lumMultirateGroups 14 }

mrtNotificationGroupV2 NOTIFICATION-GROUP
    NOTIFICATIONS {
        mrtIfTxSignalStatusDown,
        mrtIfTxSignalStatusUp,
        mrtIfTxSignalStatusDegraded }
    STATUS      current
    DESCRIPTION
        "The multirate notifications."
    ::= { lumMultirateGroups 15 }

mrtIfGroupV11 OBJECT-GROUP
    OBJECTS {
        mrtIfIndex,
        mrtIfName,
        mrtIfDescr,
        mrtIfSubrack,
        mrtIfSlot,
        mrtIfTxPort,
        mrtIfRxPort,
        mrtIfInvPhysIndexOrZero,
        mrtIfFormat,
        mrtIfHighSpeed,
        mrtIfHighSpeedMin,
        mrtIfHighSpeedMax,
        mrtIfPowerLevel,
        mrtIfPowerLevelHighThreshold,
        mrtIfPowerLevelLowThreshold,
        mrtIfLaserStatus,
        mrtIfAdminStatus,
        mrtIfOperStatus,
        mrtIfLossOfSignal,
        mrtIfReceivedPowerHigh,
        mrtIfReceivedPowerLow,
        mrtIfLaserBiasHigh,
        mrtIfLossOfFrame,
        mrtIfMsAlarmIndicationSignalC2W,
        mrtIfMsAlarmIndicationSignalW2C,
        mrtIfRemoteDefectIndication,
        mrtIfLossOfSync,
        mrtIfBitrateMismatch,
        mrtIfLaserBias,
        mrtIfLaserBiasThreshold,
        mrtIfJ0PathTrace,
        mrtIfAuAlarmIndicationSignalW2C,
        mrtIfAuLossOfPointerW2C,
        mrtIfTxSignalStatus,
        mrtIfTruncVc4,
        mrtIfAuAlarmIndicationSignalC2W,
        mrtIfAuLossOfPointerC2W,
        mrtIfTraceIntrusionMode,
        mrtIfTraceTransmitted,
        mrtIfTraceReceived,
        mrtIfTraceExpected,
        mrtIfTraceAlarmMode,
        mrtIfTraceMismatch,
        mrtIfForwardAls,
        mrtIfSuppressRemoteAlarms,
        mrtIfConfigurationCommand,
        mrtIfTrxCodeMismatch,
        mrtIfTrxBitrateUnavailable,
        mrtIfTrxMissing,
        mrtIfTrxClass,
        mrtIfEntityId,
        mrtIfTransmitterFailed,
        mrtIfReceiverSensitivity,
        mrtIfPowerLevelLowRelativeThreshold,
        mrtIfFarEndLoopback,
        mrtIfConfigureModeCommand,
        mrtIfTrxMode,
        mrtIfExpectedTxFrequency,
        mrtIfTxFrequency,
        mrtIfUnexpectedTxFrequency,
        mrtIfIllegalFrequency }
    STATUS      deprecated
    DESCRIPTION
        "The interface objects V11 (2.2)."
    ::= { lumMultirateGroups 16 }

mrtIfGroupV12 OBJECT-GROUP
    OBJECTS {
        mrtIfIndex,
        mrtIfName,
        mrtIfDescr,
        mrtIfSubrack,
        mrtIfSlot,
        mrtIfTxPort,
        mrtIfRxPort,
        mrtIfInvPhysIndexOrZero,
        mrtIfFormat,
        mrtIfHighSpeed,
        mrtIfHighSpeedMin,
        mrtIfHighSpeedMax,
        mrtIfPowerLevel,
        mrtIfPowerLevelHighThreshold,
        mrtIfPowerLevelLowThreshold,
        mrtIfLaserStatus,
        mrtIfAdminStatus,
        mrtIfOperStatus,
        mrtIfLossOfSignal,
        mrtIfReceivedPowerHigh,
        mrtIfReceivedPowerLow,
        mrtIfLaserBiasHigh,
        mrtIfLossOfFrame,
        mrtIfMsAlarmIndicationSignalC2W,
        mrtIfMsAlarmIndicationSignalW2C,
        mrtIfRemoteDefectIndication,
        mrtIfLossOfSync,
        mrtIfBitrateMismatch,
        mrtIfLaserBias,
        mrtIfLaserBiasThreshold,
        mrtIfJ0PathTrace,
        mrtIfAuAlarmIndicationSignalW2C,
        mrtIfAuLossOfPointerW2C,
        mrtIfTxSignalStatus,
        mrtIfTruncVc4,
        mrtIfAuAlarmIndicationSignalC2W,
        mrtIfAuLossOfPointerC2W,
        mrtIfTraceIntrusionMode,
        mrtIfTraceTransmitted,
        mrtIfTraceReceived,
        mrtIfTraceExpected,
        mrtIfTraceAlarmMode,
        mrtIfTraceMismatch,
        mrtIfForwardAls,
        mrtIfSuppressRemoteAlarms,
        mrtIfConfigurationCommand,
        mrtIfTrxCodeMismatch,
        mrtIfTrxBitrateUnavailable,
        mrtIfTrxMissing,
        mrtIfTrxClass,
        mrtIfEntityId,
        mrtIfTransmitterFailed,
        mrtIfReceiverSensitivity,
        mrtIfPowerLevelLowRelativeThreshold,
        mrtIfFarEndLoopback,
        mrtIfConfigureModeCommand,
        mrtIfTrxMode,
        mrtIfExpectedTxFrequency,
        mrtIfTxFrequency,
        mrtIfUnexpectedTxFrequency,
        mrtIfIllegalFrequency,
        mrtIfTrxMedia,
        mrtIfTrxMediaMismatch,
        mrtIfLaserForcedOn }
    STATUS      deprecated
    DESCRIPTION
        "The interface objects V12 (3.1)."
    ::= { lumMultirateGroups 17 }

mrtGeneralGroupV4 OBJECT-GROUP
    OBJECTS {
        mrtGeneralLastChangeTime,
        mrtGeneralStateLastChangeTime,
        mrtGeneralMrtIfTableSize }
    STATUS      current
    DESCRIPTION
        "The multirate general objects V4 (3.1)."
    ::= { lumMultirateGroups 18 }

mrtIfGroupV13 OBJECT-GROUP
    OBJECTS {
        mrtIfIndex,
        mrtIfName,
        mrtIfDescr,
        mrtIfSubrack,
        mrtIfSlot,
        mrtIfTxPort,
        mrtIfRxPort,
        mrtIfInvPhysIndexOrZero,
        mrtIfFormat,
        mrtIfHighSpeed,
        mrtIfHighSpeedMin,
        mrtIfHighSpeedMax,
        mrtIfPowerLevel,
        mrtIfPowerLevelHighThreshold,
        mrtIfPowerLevelLowThreshold,
        mrtIfLaserStatus,
        mrtIfAdminStatus,
        mrtIfOperStatus,
        mrtIfLossOfSignal,
        mrtIfReceivedPowerHigh,
        mrtIfReceivedPowerLow,
        mrtIfLaserBiasHigh,
        mrtIfLossOfFrame,
        mrtIfMsAlarmIndicationSignalC2W,
        mrtIfMsAlarmIndicationSignalW2C,
        mrtIfRemoteDefectIndication,
        mrtIfLossOfSync,
        mrtIfBitrateMismatch,
        mrtIfLaserBias,
        mrtIfLaserBiasThreshold,
        mrtIfJ0PathTrace,
        mrtIfAuAlarmIndicationSignalW2C,
        mrtIfAuLossOfPointerW2C,
        mrtIfTxSignalStatus,
        mrtIfTruncVc4,
        mrtIfAuAlarmIndicationSignalC2W,
        mrtIfAuLossOfPointerC2W,
        mrtIfTraceIntrusionMode,
        mrtIfTraceTransmitted,
        mrtIfTraceReceived,
        mrtIfTraceExpected,
        mrtIfTraceAlarmMode,
        mrtIfTraceMismatch,
        mrtIfForwardAls,
        mrtIfSuppressRemoteAlarms,
        mrtIfConfigurationCommand,
        mrtIfTrxCodeMismatch,
        mrtIfTrxBitrateUnavailable,
        mrtIfTrxMissing,
        mrtIfTrxClass,
        mrtIfEntityId,
        mrtIfTransmitterFailed,
        mrtIfReceiverSensitivity,
        mrtIfPowerLevelLowRelativeThreshold,
        mrtIfFarEndLoopback,
        mrtIfConfigureModeCommand,
        mrtIfTrxMode,
        mrtIfExpectedTxFrequency,
        mrtIfTxFrequency,
        mrtIfUnexpectedTxFrequency,
        mrtIfIllegalFrequency,
        mrtIfTrxMedia,
        mrtIfTrxMediaMismatch,
        mrtIfLaserForcedOn,
        mrtIfTruncAutoNegotiationMode }
    STATUS      deprecated
    DESCRIPTION
        "The interface objects V13 (3.2)."
    ::= { lumMultirateGroups 19 }

mrtIfGroupV14 OBJECT-GROUP
    OBJECTS {
        mrtIfIndex,
        mrtIfName,
        mrtIfDescr,
        mrtIfSubrack,
        mrtIfSlot,
        mrtIfTxPort,
        mrtIfRxPort,
        mrtIfInvPhysIndexOrZero,
        mrtIfFormat,
        mrtIfHighSpeed,
        mrtIfHighSpeedMin,
        mrtIfHighSpeedMax,
        mrtIfPowerLevel,
        mrtIfPowerLevelHighThreshold,
        mrtIfPowerLevelLowThreshold,
        mrtIfLaserStatus,
        mrtIfAdminStatus,
        mrtIfOperStatus,
        mrtIfLossOfSignal,
        mrtIfReceivedPowerHigh,
        mrtIfReceivedPowerLow,
        mrtIfLaserBiasHigh,
        mrtIfLossOfFrame,
        mrtIfMsAlarmIndicationSignalC2W,
        mrtIfMsAlarmIndicationSignalW2C,
        mrtIfRemoteDefectIndication,
        mrtIfLossOfSync,
        mrtIfBitrateMismatch,
        mrtIfLaserBias,
        mrtIfLaserBiasThreshold,
        mrtIfJ0PathTrace,
        mrtIfAuAlarmIndicationSignalW2C,
        mrtIfAuLossOfPointerW2C,
        mrtIfTxSignalStatus,
        mrtIfTruncVc4,
        mrtIfAuAlarmIndicationSignalC2W,
        mrtIfAuLossOfPointerC2W,
        mrtIfTraceIntrusionMode,
        mrtIfTraceTransmitted,
        mrtIfTraceReceived,
        mrtIfTraceExpected,
        mrtIfTraceAlarmMode,
        mrtIfTraceMismatch,
        mrtIfForwardAls,
        mrtIfSuppressRemoteAlarms,
        mrtIfConfigurationCommand,
        mrtIfTrxCodeMismatch,
        mrtIfTrxBitrateUnavailable,
        mrtIfTrxMissing,
        mrtIfTrxClass,
        mrtIfEntityId,
        mrtIfTransmitterFailed,
        mrtIfReceiverSensitivity,
        mrtIfPowerLevelLowRelativeThreshold,
        mrtIfFarEndLoopback,
        mrtIfConfigureModeCommand,
        mrtIfTrxMode,
        mrtIfExpectedTxFrequency,
        mrtIfTxFrequency,
        mrtIfUnexpectedTxFrequency,
        mrtIfIllegalFrequency,
        mrtIfTrxMedia,
        mrtIfTrxMediaMismatch,
        mrtIfLaserForcedOn,
        mrtIfTruncAutoNegotiationMode,
        mrtIfObjectProperty,
        mrtIfTxPowerLevel,
        mrtIfLaserTempActual }
    STATUS      deprecated
    DESCRIPTION
        "The interface objects V14 (4.0)."
    ::= { lumMultirateGroups 20 }

mrtIfGroupV15 OBJECT-GROUP
    OBJECTS {
        mrtIfIndex,
        mrtIfName,
        mrtIfDescr,
        mrtIfSubrack,
        mrtIfSlot,
        mrtIfTxPort,
        mrtIfRxPort,
        mrtIfInvPhysIndexOrZero,
        mrtIfFormat,
        mrtIfHighSpeed,
        mrtIfHighSpeedMin,
        mrtIfHighSpeedMax,
        mrtIfPowerLevel,
        mrtIfPowerLevelHighThreshold,
        mrtIfPowerLevelLowThreshold,
        mrtIfLaserStatus,
        mrtIfAdminStatus,
        mrtIfOperStatus,
        mrtIfLossOfSignal,
        mrtIfReceivedPowerHigh,
        mrtIfReceivedPowerLow,
        mrtIfLaserBiasHigh,
        mrtIfLossOfFrame,
        mrtIfMsAlarmIndicationSignalC2W,
        mrtIfMsAlarmIndicationSignalW2C,
        mrtIfRemoteDefectIndication,
        mrtIfLossOfSync,
        mrtIfBitrateMismatch,
        mrtIfLaserBias,
        mrtIfLaserBiasThreshold,
        mrtIfJ0PathTrace,
        mrtIfAuAlarmIndicationSignalW2C,
        mrtIfAuLossOfPointerW2C,
        mrtIfTxSignalStatus,
        mrtIfTruncVc4,
        mrtIfAuAlarmIndicationSignalC2W,
        mrtIfAuLossOfPointerC2W,
        mrtIfTraceIntrusionMode,
        mrtIfTraceTransmitted,
        mrtIfTraceReceived,
        mrtIfTraceExpected,
        mrtIfTraceAlarmMode,
        mrtIfTraceMismatch,
        mrtIfForwardAls,
        mrtIfSuppressRemoteAlarms,
        mrtIfConfigurationCommand,
        mrtIfTrxCodeMismatch,
        mrtIfTrxBitrateUnavailable,
        mrtIfTrxMissing,
        mrtIfTrxClass,
        mrtIfEntityId,
        mrtIfTransmitterFailed,
        mrtIfReceiverSensitivity,
        mrtIfPowerLevelLowRelativeThreshold,
        mrtIfFarEndLoopback,
        mrtIfConfigureModeCommand,
        mrtIfTrxMode,
        mrtIfExpectedTxFrequency,
        mrtIfTxFrequency,
        mrtIfUnexpectedTxFrequency,
        mrtIfIllegalFrequency,
        mrtIfTrxMedia,
        mrtIfTrxMediaMismatch,
        mrtIfLaserForcedOn,
        mrtIfTruncAutoNegotiationMode,
        mrtIfObjectProperty,
        mrtIfTxPowerLevel,
        mrtIfLaserTempActual }
    STATUS      deprecated
    DESCRIPTION
        "The interface objects V15 (6.0)."
    ::= { lumMultirateGroups 21 }

mrtIfGroupV16 OBJECT-GROUP
    OBJECTS {
        mrtIfIndex,
        mrtIfName,
        mrtIfDescr,
        mrtIfSubrack,
        mrtIfSlot,
        mrtIfTxPort,
        mrtIfRxPort,
        mrtIfInvPhysIndexOrZero,
        mrtIfFormat,
        mrtIfHighSpeed,
        mrtIfHighSpeedMin,
        mrtIfHighSpeedMax,
        mrtIfPowerLevel,
        mrtIfPowerLevelHighThreshold,
        mrtIfPowerLevelLowThreshold,
        mrtIfLaserStatus,
        mrtIfAdminStatus,
        mrtIfOperStatus,
        mrtIfLossOfSignal,
        mrtIfReceivedPowerHigh,
        mrtIfReceivedPowerLow,
        mrtIfLaserBiasHigh,
        mrtIfLossOfFrame,
        mrtIfMsAlarmIndicationSignalC2W,
        mrtIfMsAlarmIndicationSignalW2C,
        mrtIfRemoteDefectIndication,
        mrtIfLossOfSync,
        mrtIfBitrateMismatch,
        mrtIfLaserBias,
        mrtIfLaserBiasThreshold,
        mrtIfJ0PathTrace,
        mrtIfAuAlarmIndicationSignalW2C,
        mrtIfAuLossOfPointerW2C,
        mrtIfTxSignalStatus,
        mrtIfTruncVc4,
        mrtIfAuAlarmIndicationSignalC2W,
        mrtIfAuLossOfPointerC2W,
        mrtIfTraceIntrusionMode,
        mrtIfTraceTransmitted,
        mrtIfTraceReceived,
        mrtIfTraceExpected,
        mrtIfTraceAlarmMode,
        mrtIfTraceMismatch,
        mrtIfForwardAls,
        mrtIfSuppressRemoteAlarms,
        mrtIfConfigurationCommand,
        mrtIfTrxCodeMismatch,
        mrtIfTrxBitrateUnavailable,
        mrtIfTrxMissing,
        mrtIfTrxClass,
        mrtIfEntityId,
        mrtIfTransmitterFailed,
        mrtIfReceiverSensitivity,
        mrtIfPowerLevelLowRelativeThreshold,
        mrtIfFarEndLoopback,
        mrtIfConfigureModeCommand,
        mrtIfTrxMode,
        mrtIfExpectedTxFrequency,
        mrtIfTxFrequency,
        mrtIfUnexpectedTxFrequency,
        mrtIfIllegalFrequency,
        mrtIfTrxMedia,
        mrtIfTrxMediaMismatch,
        mrtIfLaserForcedOn,
        mrtIfTruncAutoNegotiationMode,
        mrtIfObjectProperty,
        mrtIfTxPowerLevel,
        mrtIfLaserTempActual,
        mrtIfHighSpeed2,
        mrtIfRxSignalStatus }
    STATUS      current
    DESCRIPTION
        "The interface objects V16 (7.0)."
    ::= { lumMultirateGroups 22 }


-- ----------------------------------------------------
-- Compliance
-- ----------------------------------------------------

lumMultirateBasicComplV1 MODULE-COMPLIANCE
    STATUS      deprecated
    DESCRIPTION
        "Basic implementation requirements for the multirate MIB V1."
    MODULE
        MANDATORY-GROUPS {
            mrtGeneralGroup,
            mrtIfGroup }
    ::= { lumMultirateCompl 1 }

lumMultirateBasicComplV2 MODULE-COMPLIANCE
    STATUS      deprecated
    DESCRIPTION
        "Basic implementation requirements for the multirate MIB V2."
    MODULE
        MANDATORY-GROUPS {
            mrtGeneralGroupV2,
            mrtIfGroup }
    ::= { lumMultirateCompl 2 }

lumMultirateBasicComplV3 MODULE-COMPLIANCE
    STATUS      deprecated
    DESCRIPTION
        "Basic implementation requirements for the multirate MIB V3."
    MODULE
        MANDATORY-GROUPS {
            mrtGeneralGroupV2,
            mrtIfGroupV2 }
    ::= { lumMultirateCompl 3 }

lumMultirateBasicComplV4 MODULE-COMPLIANCE
    STATUS      deprecated
    DESCRIPTION
        "Basic implementation requirements for the multirate MIB V4."
    MODULE
        MANDATORY-GROUPS {
            mrtGeneralGroupV2,
            mrtIfGroupV3 }
    ::= { lumMultirateCompl 4 }

lumMultirateBasicComplV5 MODULE-COMPLIANCE
    STATUS      deprecated
    DESCRIPTION
        "Basic implementation requirements for the multirate MIB V5."
    MODULE
        MANDATORY-GROUPS {
            mrtGeneralGroupV2,
            mrtIfGroupV4,
            mrtNotificationGroup }
    ::= { lumMultirateCompl 5 }

lumMultirateBasicComplV6 MODULE-COMPLIANCE
    STATUS      deprecated
    DESCRIPTION
        "Basic implementation requirements for the multirate MIB V6."
    MODULE
        MANDATORY-GROUPS {
            mrtGeneralGroupV3,
            mrtIfGroupV4,
            mrtNotificationGroup }
    ::= { lumMultirateCompl 6 }

lumMultirateBasicComplV7 MODULE-COMPLIANCE
    STATUS      deprecated
    DESCRIPTION
        "Basic implementation requirements for the multirate MIB V7."
    MODULE
        MANDATORY-GROUPS {
            mrtGeneralGroupV3,
            mrtIfGroupV5,
            mrtNotificationGroup }
    ::= { lumMultirateCompl 7 }

lumMultirateBasicComplV8 MODULE-COMPLIANCE
    STATUS      deprecated
    DESCRIPTION
        "Basic implementation requirements for the multirate MIB V8."
    MODULE
        MANDATORY-GROUPS {
            mrtGeneralGroupV3,
            mrtIfGroupV6,
            mrtNotificationGroup }
    ::= { lumMultirateCompl 8 }

lumMultirateBasicComplV9 MODULE-COMPLIANCE
    STATUS      deprecated
    DESCRIPTION
        "Basic implementation requirements for the multirate MIB V9."
    MODULE
        MANDATORY-GROUPS {
            mrtGeneralGroupV3,
            mrtIfGroupV7,
            mrtNotificationGroup }
    ::= { lumMultirateCompl 9 }

lumMultirateBasicComplV10 MODULE-COMPLIANCE
    STATUS      deprecated
    DESCRIPTION
        "Basic implementation requirements for the multirate MIB V10."
    MODULE
        MANDATORY-GROUPS {
            mrtGeneralGroupV3,
            mrtIfGroupV8,
            mrtNotificationGroup }
    ::= { lumMultirateCompl 10 }

lumMultirateBasicComplV11 MODULE-COMPLIANCE
    STATUS      deprecated
    DESCRIPTION
        "Basic implementation requirements for the multirate MIB V11."
    MODULE
        MANDATORY-GROUPS {
            mrtGeneralGroupV3,
            mrtIfGroupV9,
            mrtNotificationGroup }
    ::= { lumMultirateCompl 11 }

lumMultirateBasicComplV12 MODULE-COMPLIANCE
    STATUS      deprecated
    DESCRIPTION
        "Basic implementation requirements for the multirate MIB V12."
    MODULE
        MANDATORY-GROUPS {
            mrtGeneralGroupV3,
            mrtIfGroupV10,
            mrtNotificationGroupV2 }
    ::= { lumMultirateCompl 12 }

lumMultirateBasicComplV13 MODULE-COMPLIANCE
    STATUS      deprecated
    DESCRIPTION
        "Basic implementation requirements for the multirate MIB V13 (2.2)."
    MODULE
        MANDATORY-GROUPS {
            mrtGeneralGroupV3,
            mrtIfGroupV11,
            mrtNotificationGroupV2 }
    ::= { lumMultirateCompl 13 }

lumMultirateBasicComplV14 MODULE-COMPLIANCE
    STATUS      deprecated
    DESCRIPTION
        "Basic implementation requirements for the multirate MIB V14 (3.1)."
    MODULE
        MANDATORY-GROUPS {
            mrtGeneralGroupV4,
            mrtIfGroupV12,
            mrtNotificationGroupV2 }
    ::= { lumMultirateCompl 14 }

lumMultirateBasicComplV15 MODULE-COMPLIANCE
    STATUS      deprecated
    DESCRIPTION
        "Basic implementation requirements for the multirate MIB V15 (3.2)."
    MODULE
        MANDATORY-GROUPS {
            mrtGeneralGroupV4,
            mrtIfGroupV13,
            mrtNotificationGroupV2 }
    ::= { lumMultirateCompl 15 }

lumMultirateBasicComplV16 MODULE-COMPLIANCE
    STATUS      deprecated
    DESCRIPTION
        "Basic implementation requirements for the multirate MIB V16 (4.0)."
    MODULE
        MANDATORY-GROUPS {
            mrtGeneralGroupV4,
            mrtIfGroupV14,
            mrtNotificationGroupV2 }
    ::= { lumMultirateCompl 16 }

lumMultirateBasicComplV17 MODULE-COMPLIANCE
    STATUS      deprecated
    DESCRIPTION
        "Basic implementation requirements for the multirate MIB V17 (6.0)."
    MODULE
        MANDATORY-GROUPS {
            mrtGeneralGroupV4,
            mrtIfGroupV15,
            mrtNotificationGroupV2 }
    ::= { lumMultirateCompl 17 }

lumMultirateBasicComplV18 MODULE-COMPLIANCE
    STATUS      deprecated
    DESCRIPTION
        "Basic implementation requirements for the multirate MIB V18 (7.0)."
    MODULE
        MANDATORY-GROUPS {
            mrtGeneralGroupV4,
            mrtIfGroupV16,
            mrtNotificationGroupV2 }
    ::= { lumMultirateCompl 18 }

lumMultirateBasicComplV19 MODULE-COMPLIANCE
    STATUS      current
    DESCRIPTION
        "Basic implementation requirements for the multirate MIB V19 (17.0)."
    MODULE
        MANDATORY-GROUPS {
            mrtGeneralGroupV4,
            mrtIfGroupV16,
            mrtNotificationGroupV2 }
    ::= { lumMultirateCompl 19 }


END
