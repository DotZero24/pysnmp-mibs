-- *****************************************************************
-- INFINERA-TP-ODUKTCLIENTCTP-MIB
--
-- Copyright (c) 2008-2012 by Infinera Inc.
-- All rights reserved.
-- ****************************************************************

INFINERA-TP-ODUKTCLIENTCTP-MIB DEFINITIONS ::= BEGIN

IMPORTS
    MODULE-IDENTITY, OBJECT-TYPE,
    Integer32, Counter64                        FROM SNMPv2-SMI
    MODULE-COMPLIANCE, OBJECT-GROUP             FROM SNMPv2-CONF
    DisplayString, TruthValue                   FROM SNMPv2-TC
    ifIndex                                     FROM IF-MIB
    InfnServiceType,InfnArc,InfnEnableDisable,
    InfnMonitoringMode                          FROM INFINERA-TC-MIB
    terminationPoint                            FROM INFINERA-REG-MIB;


oduktClientCtpMIB MODULE-IDENTITY
    LAST-UPDATED  "200904200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "200904200000Z"
    DESCRIPTION
        "First Version"
    ::= { terminationPoint 24 }



oduktClientCtpTable OBJECT-TYPE
    SYNTAX      SEQUENCE OF OduktClientCtpEntry
    MAX-ACCESS  not-accessible
    STATUS      current
    DESCRIPTION
        "A list of OduktClientCtp entries. Each entry is uniquely identified by the value of ifIndex."
    ::= { oduktClientCtpMIB 1 }

oduktClientCtpEntry  OBJECT-TYPE
    SYNTAX      OduktClientCtpEntry
    MAX-ACCESS  not-accessible
    STATUS      current
    DESCRIPTION
        "A OduktClientCtp entry containing information pertaining to Infinera OduktClientCtp interfaces.
        Entries will exist in this table for interfaces of type oduktclientCtp."
    INDEX { ifIndex , oduktClientCtpTcmIdentifier}
    ::= { oduktClientCtpTable 1 }


OduktClientCtpEntry  ::= SEQUENCE {
    oduktClientCtpTcmIdentifier		            Integer32,
    oduktClientCtpSide		                    INTEGER,
    oduktClientCtpConfiguredServiceType         InfnServiceType,
    oduktClientCtpAlarmReportControl            InfnArc,
    oduktClientCtpSupportingCircuitIdList       DisplayString,
    oduktClientCtpMonitoringMode                InfnMonitoringMode,
    oduktClientCtpDSThreshold                   Integer32,
--    oduktClientCtpSDThreshold                   Integer32,
    oduktClientCtpTxTTI                         DisplayString,
    oduktClientCtpExpectedSAPI                  DisplayString,
    oduktClientCtpExpectedDAPI                  DisplayString,
    oduktClientCtpTimDetMode                    INTEGER,
    oduktClientCtpReceivedTTI                   DisplayString,
    oduktClientCtpPmHistStatsEnable             INTEGER,

    oduktClientCtpRxEb15MinutesTce              Integer32,
    oduktClientCtpRxEbDayTce                    Integer32,
    oduktClientCtpRxDs15MinutesTce              Integer32,
    oduktClientCtpRxDsDayTce                    Integer32,
    oduktClientCtpRxEbDayTceReporting           TruthValue,
    oduktClientCtpRxEb15MinutesTceReporting     TruthValue,
    oduktClientCtpRxDsDayTceReporting           TruthValue,
    oduktClientCtpRxDs15MinutesTceReporting     TruthValue,
    oduktClientCtpSDThreshold                   Integer32,
    oduktClientCtpRxBei15MinutesTce		Counter64,
    oduktClientCtpRxBeiDayTce			Counter64,
    oduktClientCtpRxBei15MinutesTceReporting    TruthValue,
    oduktClientCtpRxBeiDayTceReporting           TruthValue

}

oduktClientCtpTcmIdentifier  OBJECT-TYPE
    SYNTAX      Integer32 (1..12)
    MAX-ACCESS  read-only
    STATUS      current
    DESCRIPTION "The TCM field identifier for this Tandem Connection Monitoring point.
    This TCM identifier is used along with the Side identifier to explicitly formulate the AID of the
    ODUkT Client CTP.
    Note that out of the 6 values, a maximum of 3 can be active at any given time, each with one or both
    sides (facility and/or terminal) active (e.g., there can be up to 12 ODUkT CTP object instances, but
    only for 3 TCM IDs)."
    ::= { oduktClientCtpEntry  1 }

oduktClientCtpSide  OBJECT-TYPE
    SYNTAX  INTEGER {
    fac(1),
    term(2)
    }
    MAX-ACCESS  read-only
    STATUS      current
    DESCRIPTION "TThe TCM Side identifier for this Tandem Connection Monitoring point.
    This TCM Side identifier is used along with the TCM identifier to explicitly formulate the AID of the
    ODUkT Client CTP. For ODUk-based adaptation, TCMs can only be enabled on the Facility-side."
    ::= { oduktClientCtpEntry  2 }

oduktClientCtpConfiguredServiceType  OBJECT-TYPE
    SYNTAX  InfnServiceType
    MAX-ACCESS  read-only
    STATUS      current
    DESCRIPTION "The ODU Service type that is configured on this generic OduClientCtp managed object."
      ::= { oduktClientCtpEntry 3 }

oduktClientCtpAlarmReportControl  OBJECT-TYPE
    SYNTAX InfnArc
    MAX-ACCESS  read-write
    STATUS      current
    DESCRIPTION "  The Alarm Reporting Control Flag for the ODUkT Clients. "
    DEFVAL      { allowed }
    ::= { oduktClientCtpEntry  4 }


oduktClientCtpSupportingCircuitIdList   OBJECT-TYPE
    SYNTAX      DisplayString
    MAX-ACCESS  read-only
    STATUS      current
    DESCRIPTION "The Supporting Circuit ID List that is this client is using.  "
    ::= { oduktClientCtpEntry   5 }

oduktClientCtpMonitoringMode OBJECT-TYPE
    SYNTAX  InfnMonitoringMode
    MAX-ACCESS  read-write
    STATUS      current
    DESCRIPTION "Allowed Section Monitoring / Path  Monitoring / TCM Attribute Value(s)
        (For side corresponding to MonitoringMode) (Fac-Side/Term-Side)."
    ::= { oduktClientCtpEntry 6 }


oduktClientCtpDSThreshold OBJECT-TYPE
    SYNTAX      Integer32 (1..100)
    MAX-ACCESS  read-write
    STATUS      current
    DESCRIPTION " This attribute indicates the threshold level for declaring a performance monitoring (PM) Second to be bad.
    A PM Second is declared bad if the percentage of detected error blocks in that second is greater than or equal to the specified threshold level.
    This attribute maps to the DEGThr MIB of RFC-3591"
    DEFVAL      { 30 }
    ::= { oduktClientCtpEntry  7 }



oduktClientCtpTxTTI OBJECT-TYPE
    SYNTAX      DisplayString (SIZE(1..64))
    MAX-ACCESS  read-write
    STATUS      current
    DESCRIPTION
        " The TTI message that needs to be transmitted from Trib to Line direction.
        This message is inserted only when the TribInsertTTI field is set to Enabled."
    ::= { oduktClientCtpEntry  8 }

oduktClientCtpExpectedSAPI OBJECT-TYPE
    SYNTAX      DisplayString  (SIZE(1..16))
    MAX-ACCESS  read-write
    STATUS      current
    DESCRIPTION
        " The Source Access Point Identifier that is expected in the Trib to Line direction. "
    ::= { oduktClientCtpEntry   9 }

oduktClientCtpExpectedDAPI OBJECT-TYPE
    SYNTAX      DisplayString  (SIZE(1..16))
    MAX-ACCESS  read-write
    STATUS      current
    DESCRIPTION
        " The Destination Access Point Identifier that is expected in the Trib to Line direction. "
    ::= { oduktClientCtpEntry  10 }


oduktClientCtpTimDetMode  OBJECT-TYPE
    SYNTAX  INTEGER {
    off(1),
    sapi(2),
    dapi(3),
    sapidapi(4)
    }
    MAX-ACCESS  read-write
    STATUS      current
    DESCRIPTION "This attribute is used to configure if the TIM-S alarm shall be reported on mismatch of Expected and Received TTI message.
    The following are the values and their meaning:
        OFF: TIM-S is not reported.
        DAPI: TIM-S is reported only if the DAPI message mismatch occurs.
        SAPI: TIM-S is reported only if the SAPI message mismatch occurs.
        DAPISAPI: Either the DAPI or the SAPI messages are in a
        mismatch state."
    DEFVAL      { off }
    ::= { oduktClientCtpEntry 11 }

oduktClientCtpReceivedTTI  OBJECT-TYPE
    SYNTAX      DisplayString (SIZE(1..64))
    MAX-ACCESS  read-only
    STATUS      current
    DESCRIPTION "The TTI message received from the side indicated by the AID of the ODUkT CTP. "
    ::= { oduktClientCtpEntry  12 }

oduktClientCtpPmHistStatsEnable OBJECT-TYPE
    SYNTAX  INTEGER {
        enabled(1),
        disabled(2)
        }
    MAX-ACCESS  read-write
    STATUS      current
    DESCRIPTION " Flag to enable or disable the collection of PMs on the side indicated by the AID of the ODUkT CTP."
    DEFVAL      { enabled }
    ::= { oduktClientCtpEntry  13 }



oduktClientCtpRxEb15MinutesTce  OBJECT-TYPE
    SYNTAX      Integer32
    MAX-ACCESS  read-write
    STATUS      current
    DESCRIPTION "Number of Error Block in received direction during 15 minutes interval."
    DEFVAL      { 1500 }
    ::= { oduktClientCtpEntry  14 }


oduktClientCtpRxEbDayTce OBJECT-TYPE
    SYNTAX      Integer32
    MAX-ACCESS  read-write
    STATUS      current
    DESCRIPTION "Number of Error Block in received direction during 24 hours interval."
    DEFVAL      { 15000 }
    ::= { oduktClientCtpEntry  15 }


oduktClientCtpRxDs15MinutesTce  OBJECT-TYPE
    SYNTAX      Integer32
    MAX-ACCESS  read-write
    STATUS      current
    DESCRIPTION "Number of Defect Seconds in received direction during 15 minutes interval."
    DEFVAL      { 120 }
    ::= { oduktClientCtpEntry  16 }


oduktClientCtpRxDsDayTce OBJECT-TYPE
    SYNTAX      Integer32
    MAX-ACCESS  read-write
    STATUS      current
    DESCRIPTION "Number of Defect Seconds in receive direction during 24 hours interval."
    DEFVAL      { 1200 }
    ::= { oduktClientCtpEntry  17 }


oduktClientCtpRxEbDayTceReporting OBJECT-TYPE
    SYNTAX      TruthValue
    MAX-ACCESS  read-write
    STATUS      current
    DESCRIPTION " Flag that enables/disables the reporting of RxEbDayTce threshold crossing."
    DEFVAL      { false }
    ::= { oduktClientCtpEntry  18 }

oduktClientCtpRxEb15MinutesTceReporting OBJECT-TYPE
    SYNTAX      TruthValue
    MAX-ACCESS  read-write
    STATUS      current
    DESCRIPTION "  Flag that enables/disables the reporting of RxEb15MinutesTce threshold crossing."
    DEFVAL      { false }
    ::= { oduktClientCtpEntry  19 }

oduktClientCtpRxDsDayTceReporting OBJECT-TYPE
    SYNTAX      TruthValue
    MAX-ACCESS  read-write
    STATUS      current
    DESCRIPTION " Flag that enables/disables the reporting of RxDsDayTce threshold crossing."
    DEFVAL      { false }
    ::= { oduktClientCtpEntry  20 }

oduktClientCtpRxDs15MinutesTceReporting OBJECT-TYPE
    SYNTAX      TruthValue
    MAX-ACCESS  read-write
    STATUS      current
    DESCRIPTION " Flag that enables/disables the reporting of RxDs15MinutesTce threshold crossing."
    DEFVAL      { false }
    ::= { oduktClientCtpEntry  21 }

oduktClientCtpSDThreshold  OBJECT-TYPE
    SYNTAX      Integer32 (2..10)
    MAX-ACCESS  read-write
    STATUS      current
    DESCRIPTION "This attribute indicates the threshold level for declaring a Degraded  Signal defect.
    A Degraded Signal defect shall be declared if SDThreshold consecutive bad PM Seconds are detected.
    This attributes maps to the DEGM MIB of RFC-3591."
    DEFVAL      { 7 }
    ::= { oduktClientCtpEntry  22 }

oduktClientCtpRxBei15MinutesTce  OBJECT-TYPE
    SYNTAX     	Counter64
    MAX-ACCESS  read-write
    STATUS      current
    DESCRIPTION "This attribute indicates the threshold level for Received BEI counts for 15Min-interval"
    ::= { oduktClientCtpEntry  23 }

oduktClientCtpRxBeiDayTce  OBJECT-TYPE
    SYNTAX      Counter64
    MAX-ACCESS  read-write
    STATUS      current
    DESCRIPTION "This attribute indicates the threshold level for Received BEI counts for day-interval"
    ::= { oduktClientCtpEntry  24 }

oduktClientCtpRxBei15MinutesTceReporting OBJECT-TYPE
    SYNTAX      TruthValue
    MAX-ACCESS  read-write
    STATUS      current
    DESCRIPTION " Flag that enables/disables the reporting of RxBei15MinutesTce threshold crossing."
    DEFVAL      { false }
    ::= { oduktClientCtpEntry  25 }

oduktClientCtpRxBeiDayTceReporting OBJECT-TYPE
    SYNTAX      TruthValue
    MAX-ACCESS  read-write
    STATUS      current
    DESCRIPTION " Flag that enables/disables the reporting of RxBeiDay Tce threshold crossing."
    DEFVAL      { false }
    ::= { oduktClientCtpEntry  26 }



-- Conformance Statements
oduktClientCtpConformance    OBJECT IDENTIFIER ::= { oduktClientCtpMIB 3 }
oduktClientCtpCompliances    OBJECT IDENTIFIER ::= { oduktClientCtpConformance 1 }
oduktClientCtpGroups         OBJECT IDENTIFIER ::= { oduktClientCtpConformance 2 }

oduktClientCtpCompliance MODULE-COMPLIANCE
    STATUS current
    DESCRIPTION
    "Describes the requirements for conformance to the ODUKTCLIENTCTP-MIB"
    MODULE
        MANDATORY-GROUPS { oduktClientCtpGroup }
    ::= { oduktClientCtpCompliances 1 }

oduktClientCtpGroup OBJECT-GROUP
    OBJECTS {
    oduktClientCtpTcmIdentifier,
    oduktClientCtpSide,
    oduktClientCtpConfiguredServiceType,
    oduktClientCtpAlarmReportControl,
    oduktClientCtpSupportingCircuitIdList,
    oduktClientCtpMonitoringMode,
    oduktClientCtpDSThreshold,
    oduktClientCtpTxTTI      ,
    oduktClientCtpExpectedSAPI,
    oduktClientCtpExpectedDAPI,
    oduktClientCtpTimDetMode  ,
    oduktClientCtpReceivedTTI ,
    oduktClientCtpPmHistStatsEnable,

    oduktClientCtpRxEb15MinutesTce ,
    oduktClientCtpRxEbDayTce,

    oduktClientCtpRxDs15MinutesTce,
    oduktClientCtpRxDsDayTce,

    oduktClientCtpRxEbDayTceReporting,
    oduktClientCtpRxEb15MinutesTceReporting ,

    oduktClientCtpRxDsDayTceReporting,
    oduktClientCtpRxDs15MinutesTceReporting,
    oduktClientCtpSDThreshold,
    oduktClientCtpRxBei15MinutesTce,
    oduktClientCtpRxBeiDayTce,
    oduktClientCtpRxBei15MinutesTceReporting,
    oduktClientCtpRxBeiDayTceReporting
    }
    STATUS current
    DESCRIPTION
        " A collection of objects for managing the oduktClientCtp"
    ::= { oduktClientCtpGroups 1 }


END
