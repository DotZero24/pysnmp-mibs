-- *****************************************************************
-- INFINERA-TP-XOCGPTP-MIB
--
-- September 2014, Anusree Bhattacharjee
--
--
-- Copyright (c) 2014 by Infinera Inc.
-- All rights reserved.
-- ****************************************************************

INFINERA-TP-XOCGPTP-MIB DEFINITIONS ::= BEGIN

IMPORTS
    MODULE-IDENTITY, OBJECT-TYPE, Integer32     FROM SNMPv2-SMI
    MODULE-COMPLIANCE, OBJECT-GROUP             FROM SNMPv2-CONF
    DisplayString, TruthValue                   FROM SNMPv2-TC
    ifIndex                                     FROM IF-MIB
    terminationPoint                            FROM INFINERA-REG-MIB
    InfnModulation, InfnEncoding,
    InfnPicStatus, InfnChassisType, InfnAutoTunable,
    FloatHundredths, FloatTenths,
    InfnOperationalState, InfnEnableDisable     FROM INFINERA-TC-MIB;


xOcgPtpMIB MODULE-IDENTITY
    LAST-UPDATED  "200810200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "200810200000Z"
    DESCRIPTION
        "First Version"
    ::= { terminationPoint 51 }

xOcgPtpTable OBJECT-TYPE
    SYNTAX      SEQUENCE OF XOcgPtpEntry
    MAX-ACCESS  not-accessible
    STATUS      current
    DESCRIPTION
        "A list of XOcgPtp entries. Each entry is uniquely identified by the value of ifIndex."
    ::= { xOcgPtpMIB 1 }

xOcgPtpEntry  OBJECT-TYPE
    SYNTAX      XOcgPtpEntry
    MAX-ACCESS  not-accessible
    STATUS      current
    DESCRIPTION
        "A XOcgPtp entry containing information pertaining to Infinera XOcgPtp Interfaces.
        This table is a subclass of IfCommon. Entries will exist in this table only for
        interfaces of type OCG PTP."
    INDEX { ifIndex }
    ::= { xOcgPtpTable 1 }


XOcgPtpEntry  ::= SEQUENCE {
    xOcgPtpPmHistStatsEnable                   INTEGER,
    xOcgPtpOcgPowerControlLoop                 INTEGER,
    xOcgPtpTxPicState                          InfnPicStatus,
    xOcgPtpRxPicState                          InfnPicStatus,
    xOcgPtpDlmEqptTyp                          InfnChassisType,
	xOcgPtpChannelCount                        FloatTenths,
	xOcgPtpLineSystemMode                      INTEGER,
    xOcgPtpProvisionedPeerTp                   DisplayString,
    xOcgPtpDiscoveredPeerTp                    DisplayString,
    xOcgPtpAutoDiscoveryPeerLm                 INTEGER,
	xOcgPtpOpenwaveTargetTxOcgPower            FloatTenths,
	xOcgPtpProvisionedEncodingMode             InfnEncoding,
	xOcgPtpInstalledEncodingMode               InfnEncoding,
    xOcgPtpAutomaticTunable                    INTEGER,
    xOcgPtpAvailableTunableOcgNumbers          Integer32,
    xOcgPtpTunableOcgNumber                    Integer32,
    xOcgPtpRemainingTunabilityOperatingHours   Integer32,
    xOcgPtpCurOcgNumber                        Integer32,
    xOcgPtpGain                                FloatTenths,
    xOcgPtpMaxFruGain                          FloatHundredths,
    xOcgPtpRxEdfaOutputPowerTarget             FloatTenths,
    xOcgPtpOcgTxTTI                            DisplayString,
    xOcgPtpOcgExpectedTTI                      DisplayString,
    xOcgPtpOcgReceivedTTI                      DisplayString,
    xOcgPtpLoopback                            TruthValue,
    xOcgPtpBwQmax                              FloatTenths,
    xOcgPtpBwQused                             FloatTenths,
    xOcgPtpBwQlicensed                         FloatTenths
}


xOcgPtpPmHistStatsEnable OBJECT-TYPE
    SYNTAX INTEGER {
        enabled(1),
        disabled(2)
    }
    MAX-ACCESS  read-write
    STATUS      current
    DESCRIPTION ""
    DEFVAL      { enabled }
    ::= { xOcgPtpEntry 1 }



xOcgPtpOcgPowerControlLoop OBJECT-TYPE
    SYNTAX INTEGER {
        disabled(1),
        enabled(2),
        unknown(3)
    }
    MAX-ACCESS  read-write
    STATUS      current
    DESCRIPTION ""
    DEFVAL      { disabled }
    ::= { xOcgPtpEntry 2 }

xOcgPtpTxPicState OBJECT-TYPE
    SYNTAX      InfnPicStatus
    MAX-ACCESS  read-only
    STATUS      current
    DESCRIPTION ""
    ::= { xOcgPtpEntry 3 }

xOcgPtpRxPicState OBJECT-TYPE
    SYNTAX      InfnPicStatus
    MAX-ACCESS  read-only
    STATUS      current
    DESCRIPTION ""
    ::= { xOcgPtpEntry 4 }


xOcgPtpDlmEqptTyp OBJECT-TYPE
    SYNTAX      InfnChassisType
    MAX-ACCESS  read-only
    STATUS      current
    DESCRIPTION ""
    DEFVAL      { unknown }
    ::= { xOcgPtpEntry 5 }


xOcgPtpChannelCount OBJECT-TYPE
    SYNTAX      FloatTenths
    MAX-ACCESS  read-only
    STATUS      current
    DESCRIPTION ""
    ::= { xOcgPtpEntry 6 }


xOcgPtpLineSystemMode OBJECT-TYPE
    SYNTAX      INTEGER {
        modeocg(1),
        modeopenwave(2),
        modescg(3),
        modescgpassivemux-1(4)
    }
    MAX-ACCESS  read-only
    STATUS      current
    DESCRIPTION ""
    DEFVAL      { modeopenwave }
    ::= { xOcgPtpEntry 7 }



xOcgPtpProvisionedPeerTp OBJECT-TYPE
    SYNTAX      DisplayString
    MAX-ACCESS  read-write
    STATUS      current
    DESCRIPTION ""
    ::= { xOcgPtpEntry 8 }


xOcgPtpDiscoveredPeerTp OBJECT-TYPE
    SYNTAX      DisplayString
    MAX-ACCESS  read-only
    STATUS      current
    DESCRIPTION ""
    ::= { xOcgPtpEntry 9 }


xOcgPtpAutoDiscoveryPeerLm OBJECT-TYPE
    SYNTAX      InfnOperationalState
    MAX-ACCESS  read-write
    STATUS      current
    DESCRIPTION ""
    DEFVAL      { disabled }
    ::= { xOcgPtpEntry 10 }

xOcgPtpOpenwaveTargetTxOcgPower OBJECT-TYPE
    SYNTAX      FloatTenths
    MAX-ACCESS  read-write
    STATUS      current
    DESCRIPTION ""
    ::= { xOcgPtpEntry 11 }


xOcgPtpProvisionedEncodingMode OBJECT-TYPE
    SYNTAX      InfnEncoding
    MAX-ACCESS  read-write
    STATUS      current
    DESCRIPTION ""
    DEFVAL      { none }
    ::= { xOcgPtpEntry 12 }


xOcgPtpInstalledEncodingMode   OBJECT-TYPE
    SYNTAX      InfnEncoding
    MAX-ACCESS  read-only
    STATUS      current
    DESCRIPTION ""
    DEFVAL      { none }
    ::= { xOcgPtpEntry 13 }

xOcgPtpAutomaticTunable        OBJECT-TYPE
    SYNTAX      InfnAutoTunable
    MAX-ACCESS  read-write
    STATUS      current
    DESCRIPTION ""
    DEFVAL      { disabled }
    ::= { xOcgPtpEntry 14 }


xOcgPtpAvailableTunableOcgNumbers OBJECT-TYPE
    SYNTAX      Integer32
    MAX-ACCESS  read-only
    STATUS      current
    DESCRIPTION ""
    ::= { xOcgPtpEntry 15 }



xOcgPtpTunableOcgNumber           OBJECT-TYPE
    SYNTAX      Integer32
    MAX-ACCESS  read-write
    STATUS      current
    DESCRIPTION ""
    ::= { xOcgPtpEntry 16 }


xOcgPtpRemainingTunabilityOperatingHours  OBJECT-TYPE
    SYNTAX      Integer32
    MAX-ACCESS  read-only
    STATUS      current
    DESCRIPTION ""
    ::= { xOcgPtpEntry 17 }



xOcgPtpCurOcgNumber   OBJECT-TYPE
    SYNTAX      Integer32
    MAX-ACCESS  read-only
    STATUS      current
    DESCRIPTION ""
    ::= { xOcgPtpEntry 18 }


xOcgPtpGain   OBJECT-TYPE
    SYNTAX      FloatTenths
    MAX-ACCESS  read-write
    STATUS      current
    DESCRIPTION ""
    ::= { xOcgPtpEntry 19 }

xOcgPtpMaxFruGain  OBJECT-TYPE
    SYNTAX      FloatHundredths
    MAX-ACCESS  read-only
    STATUS      current
    DESCRIPTION ""
    ::= { xOcgPtpEntry 20 }

xOcgPtpRxEdfaOutputPowerTarget  OBJECT-TYPE
    SYNTAX      FloatTenths
    MAX-ACCESS  read-only
    STATUS      current
    DESCRIPTION ""
    ::= { xOcgPtpEntry 21 }

xOcgPtpOcgTxTTI OBJECT-TYPE
    SYNTAX      DisplayString
    MAX-ACCESS  read-write
    STATUS      current
    DESCRIPTION ""
    ::= { xOcgPtpEntry 22 }

xOcgPtpOcgExpectedTTI OBJECT-TYPE
    SYNTAX      DisplayString
    MAX-ACCESS  read-write
    STATUS      current
    DESCRIPTION ""
    ::= { xOcgPtpEntry 23 }

xOcgPtpOcgReceivedTTI OBJECT-TYPE
    SYNTAX      DisplayString
    MAX-ACCESS  read-only
    STATUS      current
    DESCRIPTION ""
    ::= { xOcgPtpEntry 24 }

xOcgPtpLoopback   OBJECT-TYPE
    SYNTAX      TruthValue
    MAX-ACCESS  read-write
    STATUS      current
    DESCRIPTION ""
    ::= { xOcgPtpEntry 25 }

xOcgPtpBwQmax  OBJECT-TYPE
    SYNTAX      FloatTenths
    MAX-ACCESS  read-only
    STATUS      current
    DESCRIPTION ""
    ::= { xOcgPtpEntry 26 }

xOcgPtpBwQused  OBJECT-TYPE
    SYNTAX      FloatTenths
    MAX-ACCESS  read-only
    STATUS      current
    DESCRIPTION ""
    ::= { xOcgPtpEntry 27 }

xOcgPtpBwQlicensed  OBJECT-TYPE
    SYNTAX      FloatTenths
    MAX-ACCESS  read-only
    STATUS      current
    DESCRIPTION ""
    ::= { xOcgPtpEntry 28 }

-- Conformance Statement
xOcgPtpConformance    OBJECT IDENTIFIER ::= { xOcgPtpMIB 3 }
xOcgPtpCompliances    OBJECT IDENTIFIER ::= { xOcgPtpConformance 1 }
xOcgPtpGroups         OBJECT IDENTIFIER ::= { xOcgPtpConformance 2 }

xOcgPtpCompliance MODULE-COMPLIANCE
    STATUS current
    DESCRIPTION
    "Describes the requirements for conformance to the XOCGPTP-MIB"
    MODULE
        MANDATORY-GROUPS { xOcgPtpGroup }
    ::= { xOcgPtpCompliances 1 }

xOcgPtpGroup OBJECT-GROUP
    OBJECTS {
        xOcgPtpPmHistStatsEnable,
        xOcgPtpOcgPowerControlLoop,
        xOcgPtpTxPicState,
        xOcgPtpRxPicState,
        xOcgPtpDlmEqptTyp,
        xOcgPtpChannelCount,
        xOcgPtpLineSystemMode,
        xOcgPtpProvisionedPeerTp,
        xOcgPtpDiscoveredPeerTp,
        xOcgPtpAutoDiscoveryPeerLm,
        xOcgPtpOpenwaveTargetTxOcgPower,
        xOcgPtpProvisionedEncodingMode,
        xOcgPtpInstalledEncodingMode,
        xOcgPtpAutomaticTunable,
        xOcgPtpAvailableTunableOcgNumbers,
        xOcgPtpTunableOcgNumber,
        xOcgPtpRemainingTunabilityOperatingHours,
        xOcgPtpCurOcgNumber,
        xOcgPtpGain,
        xOcgPtpMaxFruGain,
        xOcgPtpRxEdfaOutputPowerTarget,
        xOcgPtpOcgTxTTI,
        xOcgPtpOcgExpectedTTI,
        xOcgPtpOcgReceivedTTI,
        xOcgPtpLoopback,
        xOcgPtpBwQmax,
        xOcgPtpBwQused,
        xOcgPtpBwQlicensed
    }
    STATUS current
    DESCRIPTION
        " A collection of objects for managing the xOcgPtp"
    ::= { xOcgPtpGroups 1 }


END
