-- ***************************************************************
-- INFINERA-ENTITY-OMM-MIB
--
-- October 2008, Sharfuddin Syed / Narendra Gupta
--
--
-- Copyright (c) 2008-2012 by Infinera Inc.
-- All rights reserved.
-- ****************************************************************

INFINERA-ENTITY-OMM-MIB DEFINITIONS ::= BEGIN

IMPORTS
    OBJECT-TYPE, MODULE-IDENTITY           FROM SNMPv2-SMI
    OBJECT-GROUP, MODULE-COMPLIANCE        FROM SNMPv2-CONF
    RowStatus, TruthValue, DisplayString   FROM SNMPv2-TC
    entLPPhysicalIndex                     FROM ENTITY-MIB
    equipment                              FROM INFINERA-REG-MIB
    InfnEqptType                           FROM INFINERA-TC-MIB;

ommMIB MODULE-IDENTITY
    LAST-UPDATED  "200810200000Z"
    ORGANIZATION
        "INFINERA"
    CONTACT-INFO
        "Infinera
        169 Java Drive
        Sunnyvale, CA - 94089

        Contact : Technical Support
        Email   : support@infinera.com
        Phone   : 1-877-INF-5288"
    DESCRIPTION
        "This MIB is modeling for OMM equipment table."

::= { equipment 10 }

ommConformance       OBJECT IDENTIFIER ::= { ommMIB 3 }
ommCompliances       OBJECT IDENTIFIER ::= { ommConformance 1 }
ommGroups            OBJECT IDENTIFIER ::= { ommConformance 2 }

ommTable  OBJECT-TYPE
    SYNTAX SEQUENCE OF OmmEntry
    MAX-ACCESS not-accessible
    STATUS     current
    DESCRIPTION
        "This table contains all OMM modules that are currently present in a network element.
        "
    ::= { ommMIB 1 }

ommEntry  OBJECT-TYPE
    SYNTAX     OmmEntry
    MAX-ACCESS not-accessible
    STATUS     current
    DESCRIPTION
        "A row in the OMM table. Each row in the table is identified with a unique entPhysicalIndexID.
        "
    INDEX { entLPPhysicalIndex }
    ::= { ommTable 1 }

OmmEntry ::= SEQUENCE {
    ommMoId               DisplayString,
    ommProvType           InfnEqptType,
    ommRedundancyStatus   INTEGER,
    ommBrandingFault      TruthValue,
    ommRowStatus          RowStatus
}

ommMoId  OBJECT-TYPE
    SYNTAX     DisplayString
    MAX-ACCESS read-create
    STATUS     current
    DESCRIPTION
        "The object identifier."
    ::= { ommEntry 1 }

ommProvType  OBJECT-TYPE
    SYNTAX     InfnEqptType
    MAX-ACCESS read-create
    STATUS     current
    DESCRIPTION
        "The configured OMM type."
    ::= { ommEntry 2 }

ommRedundancyStatus  OBJECT-TYPE
    SYNTAX     INTEGER {
        none (1),
        single (2),
        active (3),
        standby (4),
        makeStandbyInProgress (5),
        oos (6),
        lock (7)
    }
    MAX-ACCESS read-only
    STATUS     current
    DESCRIPTION
        "Indicates whether the OMM is active or standby."
    ::= { ommEntry 3 }

ommBrandingFault  OBJECT-TYPE
    SYNTAX     TruthValue
    MAX-ACCESS read-only
    STATUS     current
    DESCRIPTION
        "Indicates OMM branding faults."
    ::= { ommEntry 4 }

ommRowStatus  OBJECT-TYPE
    SYNTAX     RowStatus
    MAX-ACCESS read-create
    STATUS     current
    DESCRIPTION
        "The row status of this OMM entry.
         Because rows in this table are indexed by entPhysicalIndex, to create a new row one must
         choose a value of entPhysicalIndex that is not already in use.

         A side-effect of the creation of a row in this table is the creation of a corresponding
         row in the eqptTable and the entPhysicalTable.

         The status may not be set to active if the ommMoId and ommProvEqptType are not set to valid values.

         This row may only be deleted if it was a pre-provisioned row and the hardware is not present.

         If this row is deleted, the associated row in the Eqpt Table and entPhysicalTable will be
         deleted by the agent."
    ::= { ommEntry 5 }

ommCompliance  MODULE-COMPLIANCE
    STATUS     current
    DESCRIPTION
        ""
    MODULE
        MANDATORY-GROUPS { ommGroup }
    ::= { ommCompliances 1 }

ommGroup  OBJECT-GROUP
    OBJECTS { ommBrandingFault,
        ommMoId,
        ommProvType,
        ommRedundancyStatus,
        ommRowStatus }
    STATUS     current
    DESCRIPTION
        ""
    ::= { ommGroups 1 }
END
