-- ***************************************************************
-- INFINERA-ENTITY-PXMSTATICMULTICASTFDB-MIB
--
-- May 2016, Kavitha Manjunatha / Divyank Rastogi
--
--
-- Copyright (c) 2008-2012 by Infinera Inc.
-- All rights reserved.
-- ****************************************************************
INFINERA-ENTITY-PXMSTATICMULTICASTFDB-MIB DEFINITIONS ::= BEGIN

IMPORTS
    OBJECT-TYPE, MODULE-IDENTITY, Unsigned32    FROM SNMPv2-SMI
    OBJECT-GROUP, MODULE-COMPLIANCE             FROM SNMPv2-CONF
    DisplayString                               FROM SNMPv2-TC
    ifIndex                                     FROM IF-MIB
    terminationPoint                            FROM INFINERA-REG-MIB;

pxmStaticMulticastFdbMIB MODULE-IDENTITY
    LAST-UPDATED  "201605200000Z"
    ORGANIZATION
        "INFINERA"
    CONTACT-INFO
        "Infinera
        169 Java Drive
        Sunnyvale, CA - 94089

        Contact : Technical Support
        Email   : support@infinera.com
        Phone   : 1-877-INF-5288"
    DESCRIPTION
        "This MIB is modeling for PXMSTATICMULTICASTFDB equipment table."
::= { terminationPoint 67 }

pxmStaticMulticastFdbConformance       OBJECT IDENTIFIER ::= { pxmStaticMulticastFdbMIB 3 }
pxmStaticMulticastFdbCompliances       OBJECT IDENTIFIER ::= { pxmStaticMulticastFdbConformance 1 }
pxmStaticMulticastFdbGroups            OBJECT IDENTIFIER ::= { pxmStaticMulticastFdbConformance 2 }

pxmStaticMulticastFdbTable  OBJECT-TYPE
    SYNTAX SEQUENCE OF PxmStaticMulticastFdbEntry
    MAX-ACCESS not-accessible
    STATUS     current
    DESCRIPTION
        "This table contains all PXMSTATICMULTICASTFDB  modules that are currently present
        in a network element."
    ::= { pxmStaticMulticastFdbMIB 1 }

pxmStaticMulticastFdbEntry  OBJECT-TYPE
    SYNTAX     PxmStaticMulticastFdbEntry
    MAX-ACCESS not-accessible
    STATUS     current
    DESCRIPTION
        "A row in the MEP table. Each row in the table is identified with a unique entPhysicalIndexID."
    INDEX { ifIndex }
    ::= { pxmStaticMulticastFdbTable 1 }

PxmStaticMulticastFdbEntry ::= SEQUENCE {
    pxmStaticMulticastFdbMacAddress         DisplayString
}

pxmStaticMulticastFdbMacAddress  OBJECT-TYPE
    SYNTAX     DisplayString
    MAX-ACCESS read-only
    STATUS     current
    DESCRIPTION
        ""
    ::= { pxmStaticMulticastFdbEntry 1 }

pxmStaticMulticastFdbCompliance  MODULE-COMPLIANCE
    STATUS     current
    DESCRIPTION ""
    MODULE
        MANDATORY-GROUPS { pxmStaticMulticastFdbGroup }
    ::= { pxmStaticMulticastFdbCompliances 1 }

pxmStaticMulticastFdbGroup  OBJECT-GROUP
    OBJECTS {
        pxmStaticMulticastFdbMacAddress
    }
    STATUS     current
    DESCRIPTION ""
    ::= { pxmStaticMulticastFdbGroups 1 }
END
