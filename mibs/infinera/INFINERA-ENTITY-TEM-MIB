-- ***************************************************************
-- INFINERA-ENTITY-BMM-MIB
--
-- October 2008, Sharfuddin Syed / Narendra Gupta
--
--
-- Copyright (c) 2008-2012 by Infinera Inc.
-- All rights reserved.
-- ****************************************************************

INFINERA-ENTITY-TEM-MIB DEFINITIONS ::= BEGIN

IMPORTS
    OBJECT-TYPE, MODULE-IDENTITY        FROM SNMPv2-SMI
    OBJECT-GROUP, MODULE-COMPLIANCE     FROM SNMPv2-CONF
    RowStatus, DisplayString            FROM SNMPv2-TC
    entLPPhysicalIndex                  FROM ENTITY-MIB
    equipment                           FROM INFINERA-REG-MIB
    InfnEqptType                        FROM INFINERA-TC-MIB;

temMIB MODULE-IDENTITY
    LAST-UPDATED  "200810200000Z"
    ORGANIZATION
        "INFINERA"
    CONTACT-INFO
        "Infinera
        169 Java Drive
        Sunnyvale, CA - 94089

        Contact : Technical Support
        Email   : support@infinera.com
        Phone   : 1-877-INF-5288"
    DESCRIPTION
        "This MIB is modeling for TEM equipment table."
::= { equipment 6 }

temConformance       OBJECT IDENTIFIER ::= { temMIB 3 }
temCompliances       OBJECT IDENTIFIER ::= { temConformance 1 }
temGroups            OBJECT IDENTIFIER ::= { temConformance 2 }

temTable  OBJECT-TYPE
    SYNTAX SEQUENCE OF TemEntry
    MAX-ACCESS not-accessible
    STATUS     current
    DESCRIPTION
        "This table contains all TEM modules that are currently present in a network element.
        "
    ::= { temMIB 1 }

temEntry  OBJECT-TYPE
    SYNTAX     TemEntry
    MAX-ACCESS not-accessible
    STATUS     current
    DESCRIPTION
        "A row in the TEM table. Each row in the table is identified with a unique entPhysicalIndexID.
        "
    INDEX { entLPPhysicalIndex }
    ::= { temTable 1 }

TemEntry ::= SEQUENCE {
    temMoId             DisplayString,
    temProvEqptType     InfnEqptType,
    temRowStatus        RowStatus
}

temMoId  OBJECT-TYPE
    SYNTAX     DisplayString
    MAX-ACCESS read-create
    STATUS     current
    DESCRIPTION
        "This is the primary Key of the objects e.g 1-A-3"
    ::= { temEntry 1 }

temProvEqptType  OBJECT-TYPE
    SYNTAX     InfnEqptType
    MAX-ACCESS read-create
    STATUS     current
    DESCRIPTION
        "The configured TEM type."
    ::= { temEntry 2 }

temRowStatus  OBJECT-TYPE
    SYNTAX     RowStatus
    MAX-ACCESS read-create
    STATUS     current
    DESCRIPTION
        "The row status of this TEM entry.
                Because rows in this table are indexed by entPhysicalIndex, to create a new row one must
                choose a value of entPhysicalIndex that is not already in use.

                A side-effect of the creation of a row in this table is the creation of a corresponding
                row in the eqptTable and the entPhysicalTable.

                The status may not be set to active if the temMoId and temProvEqptType are not set to valid values.

                This row may only be deleted if it was a pre-provisioned row and the hardware is not present.

                If this row is deleted, the associated row in the Eqpt Table and entPhysicalTable will be
                deleted by the agent.
                "
    ::= { temEntry 3 }

temCompliance  MODULE-COMPLIANCE
    STATUS     current
    DESCRIPTION
        ""
    MODULE
        MANDATORY-GROUPS { temGroup }
    ::= { temCompliances 1 }

temGroup  OBJECT-GROUP
    OBJECTS { temMoId,
        temProvEqptType,
        temRowStatus }
    STATUS     current
    DESCRIPTION
        ""
    ::= { temGroups 1 }
END
