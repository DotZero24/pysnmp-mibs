-- ***************************************************************
-- INFINERA-ENTITY-OTDM-MIB
--
-- Copyright (c) 2008-2015 by Infinera Inc.
-- All rights reserved.
-- ****************************************************************

INFINERA-ENTITY-OTDM-MIB DEFINITIONS ::= BEGIN

IMPORTS
    OBJECT-TYPE, MODULE-IDENTITY, Integer32        FROM SNMPv2-SMI
    OBJECT-GROUP, MODULE-COMPLIANCE                FROM SNMPv2-CONF
    TruthValue, DisplayString                      FROM SNMPv2-TC
    entPhysicalIndex                               FROM ENTITY-MIB
    equipment                                      FROM INFINERA-REG-MIB
    InfnEqptType                                   FROM INFINERA-TC-MIB;

otdmMIB MODULE-IDENTITY
    LAST-UPDATED  "201505100000Z"
    ORGANIZATION
        "Infinera"
    CONTACT-INFO
        "Infinera
                1322 Bordeaux Drive
                Sunnyvale, CA - 94089

                Contact : Technical Support
                Email   : support@infinera.com
                Phone   : 1-877-INF-5288"
    DESCRIPTION
        " "
::= { equipment 46 }


-- Conformance Statements

otdmConformance       OBJECT IDENTIFIER ::= { otdmMIB 3 }
otdmCompliances       OBJECT IDENTIFIER ::= { otdmConformance 1 }
otdmGroups            OBJECT IDENTIFIER ::= { otdmConformance 2 }

otdmTable  OBJECT-TYPE
    SYNTAX SEQUENCE OF OtdmEntry
    MAX-ACCESS not-accessible
    STATUS     current
    DESCRIPTION
        "A list of OTDM entries. Each entry is uniquely identified by the value
                of entPhysicalIndex."
    ::= { otdmMIB 1 }

otdmEntry  OBJECT-TYPE
    SYNTAX     OtdmEntry
    MAX-ACCESS not-accessible
    STATUS     current
    DESCRIPTION
        "A OTDM entry containing information pertaining to
            Infinera OTDM modules. Entries will exist in this table for
            entPhysicalEntries of type OTDM."
    INDEX { entPhysicalIndex }
    ::= { otdmTable 1 }

OtdmEntry ::= SEQUENCE {
    otdmMoId                      DisplayString,
    otdmProvEqptType              InfnEqptType
}

otdmMoId     OBJECT-TYPE
    SYNTAX      DisplayString
    MAX-ACCESS  read-write
    STATUS      current
    DESCRIPTION ""
    ::= { otdmEntry 1 }

otdmProvEqptType OBJECT-TYPE
    SYNTAX      InfnEqptType
    MAX-ACCESS  read-write
    STATUS      current
    DESCRIPTION ""
    ::= { otdmEntry 2 }

otdmCompliance  MODULE-COMPLIANCE
    STATUS     current
    DESCRIPTION
        "Describes the requirements for conformance to the OTDM-MIB"
    MODULE
        MANDATORY-GROUPS { otdmGroup }
    ::= { otdmCompliances 1 }

otdmGroup  OBJECT-GROUP
    OBJECTS {
        otdmMoId,
        otdmProvEqptType
    }
    STATUS     current
    DESCRIPTION
        " A collection of objects for managing a OTDM module"
    ::= { otdmGroups 1 }
END
