LUM-IFOPTICAL-MIB DEFINITIONS ::= BEGIN

IMPORTS
    MODULE-IDENTITY, OBJECT-TYPE, Unsigned32
        FROM SNMPv2-SMI
    OBJECT-GROUP, MODULE-COMPLIANCE
        FROM SNMPv2-CONF
    DateAndTime
        FROM SNMPv2-TC
    lumModules, lumIfOpticalMIB
        FROM LUM-REG
    Unsigned32WithNA, ResetWithNA, SignalStatusWithNA, FaultStatusWithNA, FaultStatus,
    EnabledDisabledWithNA, Signed32WithNA, LaserMode, OnOff, Frequency,
    MgmtNameString, FrequencyOnlyNotApplicable, FecType, BerLevelMTOSI,
    LaneFrequency, DispersionSearchLimit
        FROM LUM-TC;

lumIfOpticalMIBModule MODULE-IDENTITY
    LAST-UPDATED
        "201708300000Z" -- August 30th 2017
    ORGANIZATION
        "Infinera Corporation"
    CONTACT-INFO
        "techsupport@infinera.com"
    DESCRIPTION
        "The MIB module for management of optical parameters on port objects.

        This module describes the physical and channel layer in ITU-T
        Recommendation
        G.709.

        The tables contained in this MIB are:

        (1) The General group contains some general attributes as time stamps
            and tables sizes.

        (2) The opticalTransmission (ots) group contains information and
            configuration for the Ots (optical transmission section)
            layer objects.

        (3) The opticalChannel (och) group contains information and
            configuration for the Och (optical channel) layer
            objects.

        (4) The digital signal rate (dsr) group contains information and
            configuration for the Dsr (digital signal rate) layer
            objects.

        (5) The opticalTransportLaneCarrier (otlc) group contains information and
            configuration for the Otlc (optical transport lane carrier)
            layer objects.

        (6) The opticalTransportLaneCarrierGroup (otlcg) group contains
            information and configuration for the Otlcg (optical transport lane
            carrier group) layer objects.

"
    REVISION
        "201708300000Z" -- August 30th 2017
    DESCRIPTION
        "Changes made for release r29.1:
         - Added line coding attribute"
    REVISION
        "201706150000Z" -- June 15th 2017
    DESCRIPTION
        "Changes made for release r29.0:
         - Changed ORGANIZATION and CONTACT-INFO"
    REVISION
        "201704170000Z" -- April 17th 2017
    DESCRIPTION
        "Changes made for release r28.1:
        - Added lineOch LaserNotTuned.
        - Added lineOts LaserForcedOn.
        - Added fecDecModeMismatch alarm."
    REVISION
        "201611300000Z" -- November 30th 2016
    DESCRIPTION
        "Changes made for release r28:
        - Added tp100gotnii board."
    REVISION
        "201512220000Z" -- December 22nd 2015
    DESCRIPTION
        "Changes made for release r27:
        - Added fhau1 board
        - Added fha1u1 board"
    REVISION
        "201511300000Z" -- Nov 30th 2015
    DESCRIPTION
        "Changes made for release r26:
        - Added attribute dispersion search level
        - Added Trx Fec type unavailable alarm."
    REVISION
        "201409300000Z" -- September 30th 2014
    DESCRIPTION
        "Changes made for release r23.1:
        - Added mxp100gotn board."
    REVISION
        "201405160000Z" -- May 16th 2014
    DESCRIPTION
        "Changes made for release r23:
        - Moved CounterSesReset attribute to otlcg table.
        - Changed board name from tp10gotn to tphex10gotn.
        - Added tpmrHL16G board"
    REVISION
        "201311150000Z" -- November 15th 2013
    DESCRIPTION
        "Changes made for release r22:
        - Added tp10gotn and tp100gotn boards.
        - Added the otlc and otlcg tables"
    REVISION
        "201305310000Z" -- May 31st 2013
    DESCRIPTION
        "Added attribute RxPowerLevelLowAbsoluteThld."
    REVISION
        "201211200000Z" -- November 20th 2012
    DESCRIPTION
        "The initial revision of this module."
    ::= { lumModules 48 }


-- ----------------------------------------------------
-- Compliance area, containing groups and compliance
-- specifications.
-- ----------------------------------------------------

lumIfOpticalConfs OBJECT IDENTIFIER ::= { lumIfOpticalMIB 1 }
lumIfOpticalGroups OBJECT IDENTIFIER ::= { lumIfOpticalConfs 1 }
lumIfOpticalCompl OBJECT IDENTIFIER ::= { lumIfOpticalConfs 2 }

-- ----------------------------------------------------
-- Root for objects in the IFOPTICAL MIB
-- ----------------------------------------------------

lumIfOpticalMIBObjects OBJECT IDENTIFIER ::= { lumIfOpticalMIB 2 }

-- ----------------------------------------------------
-- This MIB contains the following groups:
-- ----------------------------------------------------

ifOpticalGeneral OBJECT IDENTIFIER ::= { lumIfOpticalMIBObjects 1 }
ifOpticalTransSectionList OBJECT IDENTIFIER ::= { lumIfOpticalMIBObjects 2 }
ifOpticalChannelList OBJECT IDENTIFIER ::= { lumIfOpticalMIBObjects 3 }
ifOpticalDigitalSignalRateList OBJECT IDENTIFIER ::= { lumIfOpticalMIBObjects 4 }
ifOpticalFecList OBJECT IDENTIFIER ::= { lumIfOpticalMIBObjects 5 }
ifOpticalTransLaneCarrierList OBJECT IDENTIFIER ::= { lumIfOpticalMIBObjects 6 }
ifOpticalTransLaneCarrierGroupList OBJECT IDENTIFIER ::= { lumIfOpticalMIBObjects 7 }

-- ----------------------------------------------------
-- General group
-- ----------------------------------------------------

ifOpticalGeneralConfigLastChangeTime OBJECT-TYPE
    SYNTAX      DateAndTime
    MAX-ACCESS  read-only
    STATUS      current
    DESCRIPTION
        "The time when the configuration of the MIB was
        last changed.

"
    ::= { ifOpticalGeneral 1 }

ifOpticalGeneralStateLastChangeTime OBJECT-TYPE
    SYNTAX      DateAndTime
    MAX-ACCESS  read-only
    STATUS      current
    DESCRIPTION
        "The time when the state and/or configuration of
    the MIB was last changed.

"
    ::= { ifOpticalGeneral 2 }

ifOpticalGeneralIfOpticalTransSectionTableSize OBJECT-TYPE
    SYNTAX      Unsigned32
    MAX-ACCESS  read-only
    STATUS      current
    DESCRIPTION
        "Size of optical section transmission table.

"
    ::= { ifOpticalGeneral 3 }

ifOpticalGeneralIfOpticalTransSectionConfigLastChangeTime OBJECT-TYPE
    SYNTAX      DateAndTime
    MAX-ACCESS  read-only
    STATUS      current
    DESCRIPTION
        "The time when the configuration of the table was
        last changed.

"
    ::= { ifOpticalGeneral 4 }

ifOpticalGeneralIfOpticalTransSectionStateLastChangeTime OBJECT-TYPE
   SYNTAX      DateAndTime
   MAX-ACCESS  read-only
   STATUS      current
   DESCRIPTION
       "The time when the state and/or configuration of the table
        was last changed.

"
   ::= { ifOpticalGeneral 5 }

ifOpticalGeneralIfOpticalChannelTableSize OBJECT-TYPE
    SYNTAX      Unsigned32
    MAX-ACCESS  read-only
    STATUS      current
    DESCRIPTION
        "Size of channel section table

"
    ::= { ifOpticalGeneral 6 }

ifOpticalGeneralIfOpticalChannelConfigLastChangeTime OBJECT-TYPE
    SYNTAX      DateAndTime
    MAX-ACCESS  read-only
    STATUS      current
    DESCRIPTION
        "The time when the configuration of the table was
        last changed.

"
    ::= { ifOpticalGeneral 7 }

ifOpticalGeneralIfOpticalChannelStateLastChangeTime OBJECT-TYPE
   SYNTAX      DateAndTime
   MAX-ACCESS  read-only
   STATUS      current
   DESCRIPTION
       "The time when the state and/or the configuration of the
       table was last changed.

"
   ::= { ifOpticalGeneral 8 }

ifOpticalGeneralIfOpticalDigitalSignalRateTableSize OBJECT-TYPE
    SYNTAX      Unsigned32
    MAX-ACCESS  read-only
    STATUS      current
    DESCRIPTION
        "Size of digital signal rate table

"
    ::= { ifOpticalGeneral 9 }

ifOpticalGeneralIfOpticalDigitalSignalRateConfigLastChangeTime OBJECT-TYPE
    SYNTAX      DateAndTime
    MAX-ACCESS  read-only
    STATUS      current
    DESCRIPTION
        "The time when the configuration of the table was
        last changed.

"
    ::= { ifOpticalGeneral 10 }

ifOpticalGeneralIfOpticalDigitalSignalRateStateLastChangeTime OBJECT-TYPE
   SYNTAX      DateAndTime
   MAX-ACCESS  read-only
   STATUS      current
   DESCRIPTION
       "The time when the state and/or configuration of the table was
       last changed.

"
   ::= { ifOpticalGeneral 11 }

ifOpticalGeneralIfOpticalFecTableSize OBJECT-TYPE
    SYNTAX      Unsigned32
    MAX-ACCESS  read-only
    STATUS      current
    DESCRIPTION
        "Size of Fec table

"
    ::= { ifOpticalGeneral 12 }

ifOpticalGeneralIfOpticalFecConfigLastChangeTime OBJECT-TYPE
    SYNTAX      DateAndTime
    MAX-ACCESS  read-only
    STATUS      current
    DESCRIPTION
        "The time when the configuration of the table was
        last changed.

"
    ::= { ifOpticalGeneral 13 }

ifOpticalGeneralIfOpticalFecStateLastChangeTime OBJECT-TYPE
   SYNTAX      DateAndTime
   MAX-ACCESS  read-only
   STATUS      current
   DESCRIPTION
       "The time when the state and/or configuration of the table was
       last changed.

"
   ::= { ifOpticalGeneral 14 }

ifOpticalGeneralIfOpticalTransLaneCarrierTableSize OBJECT-TYPE
    SYNTAX      Unsigned32
    MAX-ACCESS  read-only
    STATUS      current
    DESCRIPTION
        "Size of OpticalTransLaneCarrier table

"
    ::= { ifOpticalGeneral 15 }

ifOpticalGeneralIfOpticalTransLaneCarrierConfigLastChangeTime OBJECT-TYPE
    SYNTAX      DateAndTime
    MAX-ACCESS  read-only
    STATUS      current
    DESCRIPTION
        "The time when the configuration of the table was
        last changed.

"
    ::= { ifOpticalGeneral 16 }

ifOpticalGeneralIfOpticalTransLaneCarrierStateLastChangeTime OBJECT-TYPE
   SYNTAX      DateAndTime
   MAX-ACCESS  read-only
   STATUS      current
   DESCRIPTION
       "The time when the state and/or configuration of the table was
       last changed.

"
   ::= { ifOpticalGeneral 17 }

ifOpticalGeneralIfOpticalTransLaneCarrierGroupTableSize OBJECT-TYPE
    SYNTAX      Unsigned32
    MAX-ACCESS  read-only
    STATUS      current
    DESCRIPTION
        "Size of OpticalTransLaneCarrierGroup table

"
    ::= { ifOpticalGeneral 18 }

ifOpticalGeneralIfOpticalTransLaneCarrierGrConfigLastChangeTime OBJECT-TYPE
    SYNTAX      DateAndTime
    MAX-ACCESS  read-only
    STATUS      current
    DESCRIPTION
        "The time when the configuration of the table was
        last changed.

"
    ::= { ifOpticalGeneral 19 }

ifOpticalGeneralIfOpticalTransLaneCarrierGrStateLastChangeTime OBJECT-TYPE
   SYNTAX      DateAndTime
   MAX-ACCESS  read-only
   STATUS      current
   DESCRIPTION
       "The time when the state and/or configuration of the table was
       last changed.

"
   ::= { ifOpticalGeneral 20 }

-- ----------------------------------------------------
-- Optical transmission section group
-- ----------------------------------------------------

ifOpticalTransSectionTable  OBJECT-TYPE
    SYNTAX      SEQUENCE OF IfOpticalTransSectionEntry
    MAX-ACCESS  not-accessible
    STATUS      current
    DESCRIPTION
        "The if optical transmission section interface list."

    ::= { ifOpticalTransSectionList 1 }

ifOpticalTransSectionEntry OBJECT-TYPE
    SYNTAX      IfOpticalTransSectionEntry
    MAX-ACCESS  not-accessible
    STATUS      current
    DESCRIPTION
        "An entry in the ifOptical transmission section list.

"
    INDEX { ifOpticalTransSectionIndex }
    ::= { ifOpticalTransSectionTable 1 }

IfOpticalTransSectionEntry ::=
    SEQUENCE {
        ifOpticalTransSectionIndex                       Unsigned32,
        ifOpticalTransSectionName                        MgmtNameString,
        ifOpticalTransSectionConnIfBasicIfIndex          Unsigned32WithNA,
        ifOpticalTransSectionForwardAls                  EnabledDisabledWithNA,
        ifOpticalTransSectionRxPowerLevel                Signed32WithNA,
        ifOpticalTransSectionRxPowerLevelLowRelativeThld Signed32WithNA,
        ifOpticalTransSectionTxPowerLevel                Signed32WithNA,
        ifOpticalTransSectionLaserMode                   LaserMode,
        ifOpticalTransSectionLaserStatus                 OnOff,
        ifOpticalTransSectionReceiverSensitivity         Signed32WithNA,
        ifOpticalTransSectionTxSignalStatus              SignalStatusWithNA,
        ifOpticalTransSectionRxSignalStatus              SignalStatusWithNA,
        ifOpticalTransSectionLossOfSignal                FaultStatusWithNA,
        ifOpticalTransSectionRxPowerLevelLow             FaultStatusWithNA,
        ifOpticalTransSectionRxPowerLevelHigh            FaultStatusWithNA,
        ifOpticalTransSectionRxExcessiveInputPower       FaultStatusWithNA,
        ifOpticalTransSectionTxPowerLow                  FaultStatusWithNA,
        ifOpticalTransSectionRxPowerLevelLowAbsoluteThld Signed32WithNA,
        ifOpticalTransSectionLossThld                    Signed32WithNA,
        ifOpticalTransSectionLaserForcedOn               EnabledDisabledWithNA}

ifOpticalTransSectionIndex OBJECT-TYPE
    SYNTAX      Unsigned32
    MAX-ACCESS  read-only
    STATUS      current
    DESCRIPTION
        "An index assigned to each entry.

"
    ::= { ifOpticalTransSectionEntry 1 }

ifOpticalTransSectionName OBJECT-TYPE
    SYNTAX      MgmtNameString
    MAX-ACCESS  read-create
    STATUS      current
    DESCRIPTION
        "The management name of the optical transmission section,
        for example 'ots:1:2:1-2', where the first number indicates
        subrack, the second slot number and the third/fourth
        are the physical port numbers.

"
    ::= { ifOpticalTransSectionEntry 2 }

ifOpticalTransSectionConnIfBasicIfIndex OBJECT-TYPE
    SYNTAX      Unsigned32WithNA
    MAX-ACCESS  read-create
    STATUS      current
    DESCRIPTION
        "An index describing to which index in ifBasicIf table
        this object is related to.

"
    ::= { ifOpticalTransSectionEntry 3 }

ifOpticalTransSectionForwardAls OBJECT-TYPE
    SYNTAX      EnabledDisabledWithNA
    MAX-ACCESS  read-write
    STATUS      current
    DESCRIPTION
        "Forward Automatic Laser Shut-down. Decides if
        laser shutdown of the client should occur when
        a defect on the line or remote client is detected.

        disabled - The laser is NOT turned off at defect
        detection.

        enabled - The laser is turned off at defect
        detection.

"
    DEFVAL { disabled }
    ::= { ifOpticalTransSectionEntry 4 }

ifOpticalTransSectionRxPowerLevel OBJECT-TYPE
    SYNTAX      Signed32WithNA
    MAX-ACCESS  read-only
    STATUS      current
    DESCRIPTION
        "The received power level in units of 0.1 dBm.

"
    ::= { ifOpticalTransSectionEntry 5 }

ifOpticalTransSectionRxPowerLevelLowRelativeThld OBJECT-TYPE
    SYNTAX      Signed32WithNA (-50..100 | 2147483646 | 2147483647)
    MAX-ACCESS  read-only
    STATUS      current
    DESCRIPTION
        "The lower threshold for received power level in
        units of 0.1 dB, relative to the receiver
        sensitivity.

"
    DEFVAL { 30 }
    ::= { ifOpticalTransSectionEntry 6 }

ifOpticalTransSectionTxPowerLevel OBJECT-TYPE
    SYNTAX      Signed32WithNA
    MAX-ACCESS  read-only
    STATUS      current
    DESCRIPTION
        "The transmitted power level in units of 0.1 dBm.

"
    ::= { ifOpticalTransSectionEntry 7 }

ifOpticalTransSectionLaserMode OBJECT-TYPE
    SYNTAX      LaserMode
    MAX-ACCESS  read-write
    STATUS      current
    DESCRIPTION
        "The administrative state of the TX-side laser.

        als - Automatic Laser Shutdown/Turn-Off
        when lossOfSignal is detected on the RX side of
        the trunk interface.

        forcedOn - Laser is on even if lossOfSignal is
        active on the same interface

"
    DEFVAL { forcedOn }
    ::= { ifOpticalTransSectionEntry 8 }

ifOpticalTransSectionLaserStatus OBJECT-TYPE
    SYNTAX      OnOff
    MAX-ACCESS  read-only
    STATUS      current
    DESCRIPTION
        "The actual state of the TX-side laser.

        on - The laser is turned on.

        off - The laser is turned off.

"
    ::= { ifOpticalTransSectionEntry 9 }

ifOpticalTransSectionReceiverSensitivity OBJECT-TYPE
    SYNTAX      Signed32WithNA
    MAX-ACCESS  read-only
    STATUS      current
    DESCRIPTION
        "The lowest power that the receiver is guaranteed
        to handle, in units of 0.1 dBm.

"
    ::= { ifOpticalTransSectionEntry 10 }

ifOpticalTransSectionTxSignalStatus OBJECT-TYPE
    SYNTAX      SignalStatusWithNA
    MAX-ACCESS  read-only
    STATUS      current
    DESCRIPTION
        "The state for outgoing (TX) signal
        of the interface.

        down - A major fault has occurred.

        degraded - The signal quality is impaired.

        up - The signal is OK.

"
    ::= { ifOpticalTransSectionEntry 11 }


ifOpticalTransSectionRxSignalStatus OBJECT-TYPE
    SYNTAX      SignalStatusWithNA
    MAX-ACCESS  read-only
    STATUS      current
    DESCRIPTION
        "The state for incoming (RX) signal
        of the interface.

        down - A major fault has occurred.

        degraded - The signal quality is impaired.

        up - The signal is OK.

"
    ::= { ifOpticalTransSectionEntry 12 }

ifOpticalTransSectionLossOfSignal OBJECT-TYPE
    SYNTAX      FaultStatusWithNA
    MAX-ACCESS  read-only
    STATUS      current
    DESCRIPTION
        "Loss of signal (LOS).

        The received signal has disappeared.

        alarm - Loss of signal active

        ok - Loss of signal is not active

"
    ::= { ifOpticalTransSectionEntry 13 }

ifOpticalTransSectionRxPowerLevelLow OBJECT-TYPE
    SYNTAX      FaultStatusWithNA
    MAX-ACCESS  read-only
    STATUS      current
    DESCRIPTION
        "Low rx power.

        Received power level low threshold exceeded.

        Applicable for all signal formats.

        alarm: The received power level is below the
        associated threshold.

        ok: The received power level is at least 0.5 dB
        above the threshold.

"
    ::= { ifOpticalTransSectionEntry 14 }

ifOpticalTransSectionRxPowerLevelHigh OBJECT-TYPE
    SYNTAX      FaultStatusWithNA
    MAX-ACCESS  read-only
    STATUS      current
    DESCRIPTION
        "High rx power.

        Received power level is too high.

        Applicable for all signal formats.

        alarm: The received power level is too high.

        ok: The received power level is at least 0.5 dB
        below the overload threshold.

"
    ::= { ifOpticalTransSectionEntry 15 }

ifOpticalTransSectionRxExcessiveInputPower OBJECT-TYPE
    SYNTAX      FaultStatusWithNA
    MAX-ACCESS  read-only
    STATUS      current
    DESCRIPTION
        "Excessively high rx power.

        Received power level is excessively high.

        Applicable for all signal formats.

        alarm: The received power level is excessively high.

        ok: The received power level is normal.

"
    ::= { ifOpticalTransSectionEntry 16 }

ifOpticalTransSectionTxPowerLow OBJECT-TYPE
    SYNTAX      FaultStatusWithNA
    MAX-ACCESS  read-only
    STATUS      current
    DESCRIPTION
        "Low tx power.

        Transmit power is lower than the set threshold.

        Applicable for all signal formats.

        alarm: The transmit power level is lower than threshold.

        ok: The transmit power level is normal.

"
    ::= { ifOpticalTransSectionEntry 17 }

ifOpticalTransSectionRxPowerLevelLowAbsoluteThld OBJECT-TYPE
    SYNTAX      Signed32WithNA (-300..50 | 2147483646 | 2147483647)
    MAX-ACCESS  read-only
    STATUS      current
    DESCRIPTION
        "The lower threshold for received power level in
        units of 0.1 dB.

"
    DEFVAL { -140 }
    ::= { ifOpticalTransSectionEntry 18 }

ifOpticalTransSectionLossThld OBJECT-TYPE
    SYNTAX      Signed32WithNA (-420..60 | 2147483647)
    MAX-ACCESS  read-only
    STATUS      current
    DESCRIPTION
        "The threshold to declare LOS.

"
    DEFVAL { -350 }
    ::= { ifOpticalTransSectionEntry 19 }

ifOpticalTransSectionLaserForcedOn OBJECT-TYPE
    SYNTAX      EnabledDisabledWithNA
    MAX-ACCESS  read-write
    STATUS      current
    DESCRIPTION
        "When enabled, the laser is forced on regardless of
        circumstances. Be aware that enabling this mode might
        interfere with other functions and affect working traffic.
        When used with Y-cable (Optical coupler) protection it is
        expected that the TX fiber is manually removed prior to
        the command.

        disabled - The laser is controlled automatically by the system.

        enabled  - The laser is forced on.

"
    DEFVAL { disabled }
    ::= { ifOpticalTransSectionEntry 20 }


-- ----------------------------------------------------
-- Optical channel group
-- ----------------------------------------------------

ifOpticalChannelTable  OBJECT-TYPE
    SYNTAX      SEQUENCE OF IfOpticalChannelEntry
    MAX-ACCESS  not-accessible
    STATUS      current
    DESCRIPTION
        "The if optical channel interface list."
    ::= { ifOpticalChannelList 1 }

ifOpticalChannelEntry OBJECT-TYPE
    SYNTAX      IfOpticalChannelEntry
    MAX-ACCESS  not-accessible
    STATUS      current
    DESCRIPTION
        "An entry in the ifOptical channel list.
"
    INDEX { ifOpticalChannelIndex }
    ::= { ifOpticalChannelTable 1 }

IfOpticalChannelEntry ::=
    SEQUENCE {
        ifOpticalChannelIndex                       Unsigned32,
        ifOpticalChannelName                        MgmtNameString,
        ifOpticalChannelConnIfBasicIfIndex          Unsigned32WithNA,
        ifOpticalChannelTxFrequency                 Frequency,
        ifOpticalChannelExpectedTxFrequency         FrequencyOnlyNotApplicable,
        ifOpticalChannelTxSignalStatus              SignalStatusWithNA,
        ifOpticalChannelRxSignalStatus              SignalStatusWithNA,
        ifOpticalChannelIllegalTxFrequency          FaultStatusWithNA,
        ifOpticalChannelUnexpectedTxFrequency       FaultStatusWithNA,
        ifOpticalChannelNoTxFrequencySet            FaultStatusWithNA,
        ifOpticalChannelDispersionSearchLimit       DispersionSearchLimit,
        ifOpticalChannelLaserNotTuned               FaultStatusWithNA,
        ifOpticalChannelLineCoding                  INTEGER }

ifOpticalChannelIndex OBJECT-TYPE
    SYNTAX      Unsigned32
    MAX-ACCESS  read-only
    STATUS      current
    DESCRIPTION
        "An index assigned to each entry.

"
    ::= { ifOpticalChannelEntry 1 }

ifOpticalChannelName OBJECT-TYPE
    SYNTAX      MgmtNameString
    MAX-ACCESS  read-create
    STATUS      current
    DESCRIPTION
        "The management name of the optical channel,
        for example 'och:1:2:1-2', where the first number indicates
        subrack, the second slot number and the third/fourth
        are the physical port numbers.

"
    ::= { ifOpticalChannelEntry 2 }

ifOpticalChannelConnIfBasicIfIndex OBJECT-TYPE
    SYNTAX      Unsigned32WithNA
    MAX-ACCESS  read-create
    STATUS      current
    DESCRIPTION
        "An index describing to which index in ifBasicIf table
        this object is related to.

"
    ::= { ifOpticalChannelEntry 3 }

ifOpticalChannelTxFrequency OBJECT-TYPE
    SYNTAX      Frequency
    MAX-ACCESS  read-only
    STATUS      current
    DESCRIPTION
        "The transmitted frequency given in wavelength nm
        or as channels.
        E.g. ch871 means the frequency 187.1 THz.
        w1310 means the wavelength 1310 nm.

"
    ::= { ifOpticalChannelEntry 4 }

ifOpticalChannelExpectedTxFrequency OBJECT-TYPE
    SYNTAX      FrequencyOnlyNotApplicable
    MAX-ACCESS  read-write
    STATUS      current
    DESCRIPTION
        "The expected frequency given in wavelength nm
        or as channels.
        E.g. ch871 means the frequency 187.1 THz.
        w1310 means the wavelength 1310 nm.

"
    DEFVAL { 0 }
    ::= { ifOpticalChannelEntry 5 }

ifOpticalChannelTxSignalStatus OBJECT-TYPE
    SYNTAX      SignalStatusWithNA
    MAX-ACCESS  read-only
    STATUS      current
    DESCRIPTION
        "The state for outgoing (TX) signal
        of the interface.

        down - A major fault has occurred.

        degraded - The signal quality is impaired.

        up - The signal is OK.

"
    ::= { ifOpticalChannelEntry 6 }

ifOpticalChannelRxSignalStatus OBJECT-TYPE
    SYNTAX      SignalStatusWithNA
    MAX-ACCESS  read-only
    STATUS      current
    DESCRIPTION
        "The state for incoming (RX) signal
        of the interface.

        down - A major fault has occurred.

        degraded - The signal quality is impaired.

        up - The signal is OK.

"
    ::= { ifOpticalChannelEntry 7 }

ifOpticalChannelIllegalTxFrequency OBJECT-TYPE
    SYNTAX      FaultStatusWithNA
    MAX-ACCESS  read-only
    STATUS      current
    DESCRIPTION
        "Illegal tx frequency.

        The tx frequency supported by the transceiver is not
        recognized by the system.

        alarm: Invalid or unknown frequency information is
               detected in the (pluggable) transceiver or
               board production data.

        ok: The (pluggable) transceiver or board is
            replaced.

"
    ::= { ifOpticalChannelEntry 8 }

ifOpticalChannelUnexpectedTxFrequency OBJECT-TYPE
    SYNTAX      FaultStatusWithNA
    MAX-ACCESS  read-only
    STATUS      current
    DESCRIPTION
        "Unexpected transmitted frequency.

        The actual frequency does not match the
        pre-configured frequency.

        A pre-configured frequency of '0' matches
        all actual frequencies.

        alarm: The configured frequency does not match the
        actual frequency.

        ok: The configured frequency matches the actual
        frequency.

"
    ::= { ifOpticalChannelEntry 9 }

ifOpticalChannelNoTxFrequencySet OBJECT-TYPE
    SYNTAX      FaultStatusWithNA
    MAX-ACCESS  read-only
    STATUS      current
    DESCRIPTION
        "No tx frequency set.

        The tunable laser frequency has not been set.

        alarm: Tunable laser frequency is not set.

        ok: Tunable laser frequency is set.

"
    ::= { ifOpticalChannelEntry 10 }

ifOpticalChannelDispersionSearchLimit OBJECT-TYPE
    SYNTAX      DispersionSearchLimit
    MAX-ACCESS  read-only
    STATUS      current
    DESCRIPTION
        "The upper search limit for the module dispersion compensator. Medium
        = 22,500 ps/nm, which corresponds to approximately 1300 km standard
        fiber. High = 30,000 ps/nm, which corresponds to approximately 1700 km
        standard fiber. The default value is Medium.

"
    DEFVAL { medium }
    ::= { ifOpticalChannelEntry 11 }

ifOpticalChannelLaserNotTuned OBJECT-TYPE
    SYNTAX      FaultStatusWithNA
    MAX-ACCESS  read-only
    STATUS      current
    DESCRIPTION
        "Laser not tuned.

        The tunable laser is not tuned to set frequency yet.
        This alarm can be cleared by setting the attribute
        LaserForcedOn to enabled. Note that this can disturb
        traffic. See the help for LaserForcedOn in optical
        transsection for more information.

        alarm: Tunable laser is not tuned to set frequency.

        ok: Tunable laser is tuned to set frequency.

"
    ::= { ifOpticalChannelEntry 12 }

 ifOpticalChannelLineCoding OBJECT-TYPE
    SYNTAX      INTEGER {
        qam16         (1),
        dqpsk         (2),
        qpsk          (3),
        notApplicable (2147483647)
    }
    MAX-ACCESS  read-only
    STATUS      current
    DESCRIPTION
        "Line coding.

        qam16          - 16QAM
        dqpsk          - D-QPSK
        qpsk           - QPSK
        notApplicable  - 2147483647 is used to indicate that the attribute
        is not used on the board.

"
    DEFVAL { notApplicable }
    ::= { ifOpticalChannelEntry 13 }

-- ----------------------------------------------------
-- Optical digital signal rate group
-- ----------------------------------------------------

ifOpticalDigitalSignalRateTable  OBJECT-TYPE
    SYNTAX      SEQUENCE OF IfOpticalDigitalSignalRateEntry
    MAX-ACCESS  not-accessible
    STATUS      current
    DESCRIPTION
        "The if optical digital signal rate interface list."

    ::= { ifOpticalDigitalSignalRateList 1 }

ifOpticalDigitalSignalRateEntry OBJECT-TYPE
    SYNTAX      IfOpticalDigitalSignalRateEntry
    MAX-ACCESS  not-accessible
    STATUS      current
    DESCRIPTION
        "An entry in the ifOptical digital signal rate list.

"
    INDEX { ifOpticalDigitalSignalRateIndex }
    ::= { ifOpticalDigitalSignalRateTable 1 }

IfOpticalDigitalSignalRateEntry ::=
    SEQUENCE {
        ifOpticalDigitalSignalRateIndex                   Unsigned32,
        ifOpticalDigitalSignalRateName                    MgmtNameString,
        ifOpticalDigitalSignalRateConnIfBasicIfIndex      Unsigned32WithNA,
        ifOpticalDigitalSignalRateMaxBitRate              Unsigned32WithNA,
        ifOpticalDigitalSignalRateMinBitRate              Unsigned32WithNA,
        ifOpticalDigitalSignalRateTxSignalStatus          SignalStatusWithNA,
        ifOpticalDigitalSignalRateRxSignalStatus          SignalStatusWithNA,
        ifOpticalDigitalSignalRateLossOfLock              FaultStatusWithNA,
        ifOpticalDigitalSignalRateBitrateUnavailable      FaultStatusWithNA }

ifOpticalDigitalSignalRateIndex OBJECT-TYPE
    SYNTAX      Unsigned32
    MAX-ACCESS  read-only
    STATUS      current
    DESCRIPTION
        "An index assigned to each entry.

"
    ::= { ifOpticalDigitalSignalRateEntry 1 }

ifOpticalDigitalSignalRateName OBJECT-TYPE
    SYNTAX      MgmtNameString
    MAX-ACCESS  read-only
    STATUS      current
    DESCRIPTION
        "The management name of the optical channel,
        for example 'dsr:1:2:1-2', where the first number indicates
        subrack, the second slot number and the third/fourth
        are the physical port numbers.

"
    ::= { ifOpticalDigitalSignalRateEntry 2 }

ifOpticalDigitalSignalRateConnIfBasicIfIndex OBJECT-TYPE
    SYNTAX      Unsigned32WithNA
    MAX-ACCESS  read-only
    STATUS      current
    DESCRIPTION
        "An index describing to which index in ifBasicIf table
        this object is related to.

"
    ::= { ifOpticalDigitalSignalRateEntry 3 }

ifOpticalDigitalSignalRateMaxBitRate OBJECT-TYPE
    SYNTAX      Unsigned32WithNA
    MAX-ACCESS  read-only
    STATUS      current
    DESCRIPTION

        "The max signal bit rate in units of
        1,000 000 bits (mb) per second.

"
    ::= { ifOpticalDigitalSignalRateEntry 5 }

ifOpticalDigitalSignalRateMinBitRate OBJECT-TYPE
    SYNTAX      Unsigned32WithNA
    MAX-ACCESS  read-only
    STATUS      current
    DESCRIPTION

        "The min signal bit rate in units of
        1,000 000 bits (mb) per second.

"
    ::= { ifOpticalDigitalSignalRateEntry 6 }

ifOpticalDigitalSignalRateTxSignalStatus OBJECT-TYPE
    SYNTAX      SignalStatusWithNA
    MAX-ACCESS  read-only
    STATUS      current
    DESCRIPTION
        "The state for outgoing (TX) signal
        of the interface.

        down - A major fault has occurred.

        degraded - The signal quality is impaired.

        up - The signal is OK.

"
    ::= { ifOpticalDigitalSignalRateEntry 7 }

ifOpticalDigitalSignalRateRxSignalStatus OBJECT-TYPE
    SYNTAX      SignalStatusWithNA
    MAX-ACCESS  read-only
    STATUS      current
    DESCRIPTION
        "The state for incoming (RX) signal
        of the interface.

        down - A major fault has occurred.

        degraded - The signal quality is impaired.

        up - The signal is OK.

"
    ::= { ifOpticalDigitalSignalRateEntry 8 }

ifOpticalDigitalSignalRateLossOfLock OBJECT-TYPE
    SYNTAX      FaultStatusWithNA
    MAX-ACCESS  read-only
    STATUS      current
    DESCRIPTION
        "Loss of lock.

        The receiver could not lock to the rate of the incoming signal.

        alarm: The signal could not be locked.

        ok: The signal could be locked.

"
    ::= { ifOpticalDigitalSignalRateEntry 9 }

ifOpticalDigitalSignalRateBitrateUnavailable OBJECT-TYPE
    SYNTAX      FaultStatusWithNA
    MAX-ACCESS  read-only
    STATUS      current
    DESCRIPTION

        "Bitrate unavailable.

        The inserted transceiver does not support the
        requested bit rate.

        alarm: A transceiver with other supported bit rate than
               the requested bit rate is inserted.

        ok: The transceiver with the non-requested bit rate
            is removed, or the object is reconfigured.

"
    ::= { ifOpticalDigitalSignalRateEntry 10 }

-- ----------------------------------------------------
-- Optical FEC group
-- ----------------------------------------------------

ifOpticalFecTable  OBJECT-TYPE
    SYNTAX      SEQUENCE OF IfOpticalFecEntry
    MAX-ACCESS  not-accessible
    STATUS      current
    DESCRIPTION
        "The if optical Fec list."

    ::= { ifOpticalFecList 1 }

ifOpticalFecEntry OBJECT-TYPE
    SYNTAX      IfOpticalFecEntry
    MAX-ACCESS  not-accessible
    STATUS      current
    DESCRIPTION
        "An entry in the ifOptical Fec list.

"
    INDEX { ifOpticalFecIndex }
    ::= { ifOpticalFecTable 1 }

IfOpticalFecEntry ::=
    SEQUENCE {
        ifOpticalFecIndex                   Unsigned32,
        ifOpticalFecName                    MgmtNameString,
        ifOpticalFecConnIfBasicIfIndex      Unsigned32WithNA,
        ifOpticalFecType                    FecType,
        ifOpticalFecTxSignalStatus          SignalStatusWithNA,
        ifOpticalFecRxSignalStatus          SignalStatusWithNA,
        ifOpticalFecFailure                 FaultStatusWithNA,
        ifOpticalFecSignalDegraded          FaultStatusWithNA,
        ifOpticalFecSignalDegradeThreshold  BerLevelMTOSI,
        ifOpticalFecTypeUnavailable      FaultStatus,
        ifOpticalFecUId                     Unsigned32,
        ifOpticalFecDecModeMismatch         FaultStatusWithNA}

ifOpticalFecIndex OBJECT-TYPE
    SYNTAX      Unsigned32
    MAX-ACCESS  read-only
    STATUS      current
    DESCRIPTION
        "An index assigned to each entry.

"
    ::= { ifOpticalFecEntry 1 }

ifOpticalFecName OBJECT-TYPE
    SYNTAX      MgmtNameString
    MAX-ACCESS  read-create
    STATUS      current
    DESCRIPTION
        "The management name of the FEC object,
        for example 'lineFec:1:2:1-2', where the first number
        indicates subrack, the second slot number and the
        third/fourth are the physical port numbers.

"
    ::= { ifOpticalFecEntry 2 }

ifOpticalFecConnIfBasicIfIndex OBJECT-TYPE
    SYNTAX      Unsigned32WithNA
    MAX-ACCESS  read-create
    STATUS      current
    DESCRIPTION
        "An index describing to which index in ifBasicIf table
        this object is related to.

"
    ::= { ifOpticalFecEntry 3 }

ifOpticalFecType OBJECT-TYPE
    SYNTAX      FecType
    MAX-ACCESS  read-write
    STATUS      current
    DESCRIPTION
        "Set type of FEC.

        g709 -     1st generation FEC according to
                   ITU-T G.709 (near 6 dB coding gain).

        g9751I4 -  FEC according to G975.1 I.4. Outer code: RS(1023,1007),
           Inner code: BCH(2047,1952).

        g9751I7 -  FEC according to G975.1 I.7. Two orthogonally
           concatenated BCH codes.

        sdFec - Proprietary Soft Decision FEC scheme.

"
    DEFVAL { g709 }
    ::= { ifOpticalFecEntry 4 }

ifOpticalFecTxSignalStatus OBJECT-TYPE
    SYNTAX      SignalStatusWithNA
    MAX-ACCESS  read-only
    STATUS      current
    DESCRIPTION
        "The state for outgoing (TX) signal
        of the interface.

        down - A major fault has occurred.

        degraded - The signal quality is impaired.

        up - The signal is OK.

"
    ::= { ifOpticalFecEntry 5 }

ifOpticalFecRxSignalStatus OBJECT-TYPE
    SYNTAX      SignalStatusWithNA
    MAX-ACCESS  read-only
    STATUS      current
    DESCRIPTION
        "The state for incoming (RX) signal
        of the interface.

        down - A major fault has occurred.

        degraded - The signal quality is impaired.

        up - The signal is OK.

"
    ::= { ifOpticalFecEntry 6 }

ifOpticalFecFailure OBJECT-TYPE
    SYNTAX      FaultStatusWithNA
    MAX-ACCESS  read-only
    STATUS      current
    DESCRIPTION
        "FEC failure.

        Too many errors to get valid FEC statistics. It is not
         possible to run control loops based on FEC statistics.

        A: Too many errors to get valid FEC statistics.

        D: The FEC statistics is valid.

"
    ::= { ifOpticalFecEntry 7 }

ifOpticalFecSignalDegraded OBJECT-TYPE
    SYNTAX      FaultStatusWithNA
    MAX-ACCESS  read-only
    STATUS      current
    DESCRIPTION
        "Signal degraded (SD).

        Too many error corrected. If more errors are corrected
        it might effect the client signal in a negative way.

"
    ::= { ifOpticalFecEntry 8 }

ifOpticalFecSignalDegradeThreshold OBJECT-TYPE
    SYNTAX      BerLevelMTOSI
    MAX-ACCESS  read-write
    STATUS      current
    DESCRIPTION
        "Threshold for signal degraded alarm,
         based on BER value.

         Predefined levels

         rxBerLevel1 = 1E-12
         rxBerLevel2 = 1E-13
         rxBerLevel3 = 1E-15

         OSNRMargin1 = 0.5 dB margin with respect to FEC cliff
         OSNRMargin2 = 1.0 dB margin with respect to FEC cliff

"
    DEFVAL { rxBerLevel2 }
    ::= { ifOpticalFecEntry 9 }

ifOpticalFecTypeUnavailable OBJECT-TYPE
    SYNTAX      FaultStatus
    MAX-ACCESS  read-only
    STATUS      current
    DESCRIPTION
        " Fec type unavailable.

         The inserted transceiver does not support the
         requested fec type.

         alarm: A transceiver with other supported fec type
                han the requested bit rate is inserted.

         ok: The transceiver with the non-requested fec type
             is removed, or the object is reconfigured.

"
    ::= { ifOpticalFecEntry 10 }

ifOpticalFecUId OBJECT-TYPE
    SYNTAX      Unsigned32   (0..2147483647)
    MAX-ACCESS  read-create
    STATUS      current
    DESCRIPTION
        "Unique Identifier for the entry
"
    DEFVAL { 0  }
    ::= { ifOpticalFecEntry 11 }

ifOpticalFecDecModeMismatch OBJECT-TYPE
    SYNTAX      FaultStatusWithNA
    MAX-ACCESS  read-only
    STATUS      current
    DESCRIPTION
        "FEC decoding mode mismatch.

"
    ::= { ifOpticalFecEntry 12 }

-- ----------------------------------------------------
-- Optical Transport Lane Carrier group
-- ----------------------------------------------------

ifOpticalTransLaneCarrierTable  OBJECT-TYPE
    SYNTAX      SEQUENCE OF IfOpticalTransLaneCarrierEntry
    MAX-ACCESS  not-accessible
    STATUS      current
    DESCRIPTION
        "The if optical transport lane carrier list.
        Structure and nomenclature in table is derived
        from G.709 fig. 7-1B"

    ::= { ifOpticalTransLaneCarrierList 1 }

ifOpticalTransLaneCarrierEntry OBJECT-TYPE
    SYNTAX      IfOpticalTransLaneCarrierEntry
    MAX-ACCESS  not-accessible
    STATUS      current
    DESCRIPTION
        "An entry in the ifOptical transport lane carrier list.

"
    INDEX { ifOpticalTransLaneCarrierIndex }
    ::= { ifOpticalTransLaneCarrierTable 1 }

IfOpticalTransLaneCarrierEntry ::=
    SEQUENCE {
        ifOpticalTransLaneCarrierIndex                   Unsigned32,
        ifOpticalTransLaneCarrierName                    MgmtNameString,
        ifOpticalTransLaneCarrierConnIfBasicIfIndex      Unsigned32WithNA,
        ifOpticalTransLaneCarrierConnIfOpticalTransLaneCarrierGrIndex      Unsigned32WithNA,
        ifOpticalTransLaneCarrierLaneId                  Unsigned32,
        ifOpticalTransLaneCarrierTxSignalStatus          SignalStatusWithNA,
        ifOpticalTransLaneCarrierRxSignalStatus          SignalStatusWithNA,
        ifOpticalTransLaneCarrierRxPowerLevel            Signed32WithNA,
        ifOpticalTransLaneCarrierLossOfSignal            FaultStatusWithNA,
        ifOpticalTransLaneCarrierReceiverSensitivity     Signed32WithNA,
        ifOpticalTransLaneCarrierRxPowerLevelLow         FaultStatusWithNA,
        ifOpticalTransLaneCarrierTxFrequency             LaneFrequency,
        ifOpticalTransLaneCarrierCounterSes              Unsigned32WithNA,
        ifOpticalTransLaneCarrierCounterSesReset         ResetWithNA}

ifOpticalTransLaneCarrierIndex OBJECT-TYPE
    SYNTAX      Unsigned32
    MAX-ACCESS  read-only
    STATUS      current
    DESCRIPTION
        "An index assigned to each entry.

"
    ::= { ifOpticalTransLaneCarrierEntry 1 }

ifOpticalTransLaneCarrierName OBJECT-TYPE
    SYNTAX      MgmtNameString
    MAX-ACCESS  read-only
    STATUS      current
    DESCRIPTION
        "The management name of the OTLC object,
        for example 'lineOtlc:1:2:1-2:1', where the first number
        indicates subrack, the second slot number, the
        third/fourth are the physical port numbers and the last is lane number.

"
    ::= { ifOpticalTransLaneCarrierEntry 2 }

ifOpticalTransLaneCarrierConnIfBasicIfIndex OBJECT-TYPE
    SYNTAX      Unsigned32WithNA
    MAX-ACCESS  read-only
    STATUS      current
    DESCRIPTION
        "An index describing to which index in ifBasicIf table
        this object is related to.

"
    ::= { ifOpticalTransLaneCarrierEntry 3 }

ifOpticalTransLaneCarrierConnIfOpticalTransLaneCarrierGrIndex OBJECT-TYPE
    SYNTAX      Unsigned32WithNA
    MAX-ACCESS  read-only
    STATUS      current
    DESCRIPTION
        "An index describing to which index in ifOpticalTransLaneCarrierGroup table
        this object is related to.

"
    ::= { ifOpticalTransLaneCarrierEntry 4 }

ifOpticalTransLaneCarrierLaneId OBJECT-TYPE
    SYNTAX      Unsigned32
    MAX-ACCESS  read-only
    STATUS      current
    DESCRIPTION
        "Lane number.

"
    ::= { ifOpticalTransLaneCarrierEntry 5 }

ifOpticalTransLaneCarrierTxSignalStatus OBJECT-TYPE
    SYNTAX      SignalStatusWithNA
    MAX-ACCESS  read-only
    STATUS      current
    DESCRIPTION
        "The state for outgoing (TX) signal
        of the interface.

        down - A major fault has occurred.

        degraded - The signal quality is impaired.

        up - The signal is OK.

"
    ::= { ifOpticalTransLaneCarrierEntry 6 }

ifOpticalTransLaneCarrierRxSignalStatus OBJECT-TYPE
    SYNTAX      SignalStatusWithNA
    MAX-ACCESS  read-only
    STATUS      current
    DESCRIPTION
        "The state for incoming (RX) signal
        of the interface.

        down - A major fault has occurred.

        degraded - The signal quality is impaired.

        up - The signal is OK.

"
    ::= { ifOpticalTransLaneCarrierEntry 7 }

ifOpticalTransLaneCarrierRxPowerLevel OBJECT-TYPE
    SYNTAX      Signed32WithNA
    MAX-ACCESS  read-only
    STATUS      current
    DESCRIPTION
        "The received power level in units of 0.1 dBm.

"
    ::= { ifOpticalTransLaneCarrierEntry 8 }

ifOpticalTransLaneCarrierLossOfSignal OBJECT-TYPE
    SYNTAX      FaultStatusWithNA
    MAX-ACCESS  read-only
    STATUS      current
    DESCRIPTION
        "Loss of signal (LOS).

        The received signal has disappeared.

        alarm - Loss Of Signal active

        ok - Loss of signal is not active

"
    ::= { ifOpticalTransLaneCarrierEntry 9 }

ifOpticalTransLaneCarrierReceiverSensitivity OBJECT-TYPE
    SYNTAX      Signed32WithNA
    MAX-ACCESS  read-only
    STATUS      current
    DESCRIPTION
        "The lowest power that the receiver is guaranteed
        to handle, per lane, in units of 0.1 dBm.

"
    ::= { ifOpticalTransLaneCarrierEntry 10 }

ifOpticalTransLaneCarrierRxPowerLevelLow OBJECT-TYPE
    SYNTAX      FaultStatusWithNA
    MAX-ACCESS  read-only
    STATUS      current
    DESCRIPTION
        "Low rx power.

        Received power level low threshold exceeded.
        Relative to the threshold in the OTLCG table
        (Lane sensitivity + threshold).

        Applicable for all signal formats.

        alarm: The received power level is below the
        associated threshold.

        ok: The received power level is at least 0.5 dBm
        above the threshold.

"
    ::= { ifOpticalTransLaneCarrierEntry 11 }

ifOpticalTransLaneCarrierTxFrequency OBJECT-TYPE
    SYNTAX      LaneFrequency
    MAX-ACCESS  read-only
    STATUS      current
    DESCRIPTION
        "The transmitted frequency given in wavelength nm
        or as channels.
        E.g. ch871 means the frequency 187.1 THz.
        w1310 means the wavelength 1310 nm.

"
    ::= { ifOpticalTransLaneCarrierEntry 12 }

ifOpticalTransLaneCarrierCounterSes OBJECT-TYPE
    SYNTAX      Unsigned32WithNA
    MAX-ACCESS  read-only
    STATUS      current
    DESCRIPTION
        "Severely Errored Seconds.
        The counter associated with the number of
        errored seconds (seconds with LOS) in the interval per lane.

"
    ::= { ifOpticalTransLaneCarrierEntry 13 }

ifOpticalTransLaneCarrierCounterSesReset OBJECT-TYPE
    SYNTAX      ResetWithNA
    MAX-ACCESS  read-only
    STATUS      deprecated
    DESCRIPTION
        "Reset SES Counter.
        After a successful reset the default value
        (normal) is restored in this attribute.

"
    DEFVAL { normal }
    ::= { ifOpticalTransLaneCarrierEntry 14 }

-- ----------------------------------------------------
-- Optical Transport Lane Carrier Group group
-- ----------------------------------------------------

ifOpticalTransLaneCarrierGroupTable  OBJECT-TYPE
    SYNTAX      SEQUENCE OF IfOpticalTransLaneCarrierGroupEntry
    MAX-ACCESS  not-accessible
    STATUS      current
    DESCRIPTION
        "The if optical transport lane carrier group list."

    ::= { ifOpticalTransLaneCarrierGroupList 1 }

ifOpticalTransLaneCarrierGroupEntry OBJECT-TYPE
    SYNTAX      IfOpticalTransLaneCarrierGroupEntry
    MAX-ACCESS  not-accessible
    STATUS      current
    DESCRIPTION
        "An entry in the ifOptical transport lane carrier group list.

"
    INDEX { ifOpticalTransLaneCarrierGroupIndex }
    ::= { ifOpticalTransLaneCarrierGroupTable 1 }

IfOpticalTransLaneCarrierGroupEntry ::=
    SEQUENCE {
        ifOpticalTransLaneCarrierGroupIndex                 Unsigned32,
        ifOpticalTransLaneCarrierGroupName                  MgmtNameString,
        ifOpticalTransLaneCarrierGroupConnIfBasicIfIndex    Unsigned32WithNA,
        ifOpticalTransLaneCarrierGroupForwardAls            EnabledDisabledWithNA,
        ifOpticalTransLaneCarrierGroupLaserStatus           OnOff,
        ifOpticalTransLaneCarrierGroupTxPowerLevel          Signed32WithNA,
        ifOpticalTransLaneCarrierGroupRxSignalStatus        SignalStatusWithNA,
        ifOpticalTransLaneCarrierGroupRxPowerLevel          Signed32WithNA,
        ifOpticalTransLaneCarrierGroupTxSignalStatus        SignalStatusWithNA,
        ifOpticalTransLaneCarrierGroupLossOfSignal          FaultStatusWithNA,
        ifOpticalTransLaneCarrierGroupRxPowerLevelLowRelativeThld   Signed32WithNA,
        ifOpticalTransLaneCarrierGroupRxPowerLevelLow       FaultStatusWithNA,
        ifOpticalTransLaneCarrierGroupTxFrequency           Frequency,
        ifOpticalTransLaneCarrierGroupExpectedTxFrequency   FrequencyOnlyNotApplicable,
        ifOpticalTransLaneCarrierGroupUnexpectedTxFrequency FaultStatusWithNA,
        ifOpticalTransLaneCarrierGroupIllegalTxFrequency    FaultStatusWithNA,
        ifOpticalTransLaneCarrierGroupCounterSesReset       ResetWithNA,
        ifOpticalTransLaneCarrierGroupMinimumLaneRxPowerLevel Signed32WithNA,
        ifOpticalTransLaneCarrierGroupReceiverLaneSensitivity Signed32WithNA}

ifOpticalTransLaneCarrierGroupIndex OBJECT-TYPE
    SYNTAX      Unsigned32
    MAX-ACCESS  read-only
    STATUS      current
    DESCRIPTION
        "An index assigned to each entry.

"
    ::= { ifOpticalTransLaneCarrierGroupEntry 1 }

ifOpticalTransLaneCarrierGroupName OBJECT-TYPE
    SYNTAX      MgmtNameString
    MAX-ACCESS  read-create
    STATUS      current
    DESCRIPTION
        "The management name of the OTLCG object,
        for example 'lineOtlcg:1:2:1-2', where the first number
        indicates subrack, the second slot number, the
        third/fourth are the physical port numbers.

"
    ::= { ifOpticalTransLaneCarrierGroupEntry 2 }

ifOpticalTransLaneCarrierGroupConnIfBasicIfIndex OBJECT-TYPE
    SYNTAX      Unsigned32WithNA
    MAX-ACCESS  read-create
    STATUS      current
    DESCRIPTION
        "An index describing to which index in ifBasicIf table
        this object is related to.

"
    ::= { ifOpticalTransLaneCarrierGroupEntry 3 }

ifOpticalTransLaneCarrierGroupTxSignalStatus OBJECT-TYPE
    SYNTAX      SignalStatusWithNA
    MAX-ACCESS  read-only
    STATUS      current
    DESCRIPTION
        "The state for outgoing (TX) signal

        of the interface.

        down - A major fault has occurred.

        degraded - The signal quality is impaired.

        up - The signal is OK.

"
    ::= { ifOpticalTransLaneCarrierGroupEntry 4 }

ifOpticalTransLaneCarrierGroupRxSignalStatus OBJECT-TYPE
    SYNTAX      SignalStatusWithNA
    MAX-ACCESS  read-only
    STATUS      current
    DESCRIPTION
        "The state for incoming (RX) signal
        of the interface.

        down - A major fault has occurred.

        degraded - The signal quality is impaired.

        up - The signal is OK.

"
    ::= { ifOpticalTransLaneCarrierGroupEntry 5 }

ifOpticalTransLaneCarrierGroupForwardAls OBJECT-TYPE
    SYNTAX      EnabledDisabledWithNA
    MAX-ACCESS  read-write
    STATUS      current
    DESCRIPTION
        "Forward Automatic Laser Shut-down. Decides if
        laser shutdown of the client should occur when
        a defect on the line or remote client is detected.

        disabled - The laser is NOT turned off at defect
        detection.

        enabled - The laser is turned off at defect
        detection.

"
    DEFVAL { disabled }
    ::= { ifOpticalTransLaneCarrierGroupEntry 6 }

ifOpticalTransLaneCarrierGroupLaserStatus OBJECT-TYPE
    SYNTAX      OnOff
    MAX-ACCESS  read-only
    STATUS      current
    DESCRIPTION
        "The actual state of the TX-side laser.

        on - The laser is turned on.

        off - The laser is turned off.

"
    ::= { ifOpticalTransLaneCarrierGroupEntry 7 }

ifOpticalTransLaneCarrierGroupTxPowerLevel OBJECT-TYPE
    SYNTAX      Signed32WithNA
    MAX-ACCESS  read-only
    STATUS      current
    DESCRIPTION
        "The total transmitted power level, including all lanes,
        in units of 0.1 dBm.

"
    ::= { ifOpticalTransLaneCarrierGroupEntry 8 }

ifOpticalTransLaneCarrierGroupRxPowerLevel OBJECT-TYPE
    SYNTAX      Signed32WithNA
    MAX-ACCESS  read-only
    STATUS      current
    DESCRIPTION
        "The total received power level, including all lanes,
        in units of 0.1 dBm.

"
    ::= { ifOpticalTransLaneCarrierGroupEntry 9 }

ifOpticalTransLaneCarrierGroupLossOfSignal OBJECT-TYPE
    SYNTAX      FaultStatusWithNA
    MAX-ACCESS  read-only
    STATUS      current
    DESCRIPTION
        "Loss of signal (LOS).

        The received signal has disappeared.

        alarm - Loss Of Signal active

        ok - Loss of signal is not active

"
    ::= { ifOpticalTransLaneCarrierGroupEntry 10 }

ifOpticalTransLaneCarrierGroupRxPowerLevelLowRelativeThld OBJECT-TYPE
    SYNTAX      Signed32WithNA (-50..100 | 2147483646 | 2147483647)
    MAX-ACCESS  read-only
    STATUS      current
    DESCRIPTION
        "The lower threshold for received power level in
        units of 0.1 dB, relative to the receiver
        sensitivity.
        If multi lane transceiver is used this threshold
        is used on all lanes.

"
    DEFVAL { 30 }
    ::= { ifOpticalTransLaneCarrierGroupEntry 11 }

ifOpticalTransLaneCarrierGroupRxPowerLevelLow OBJECT-TYPE
    SYNTAX      FaultStatusWithNA
    MAX-ACCESS  read-only
    STATUS      current
    DESCRIPTION
        "Low rx power.

        Received power level low threshold exceeded.
        If multi lane transceiver is used the threshold
        is exceeded on at least one lane.

        Applicable for all signal formats.

        alarm: The received power level is below the
        associated threshold.

        ok: The received power level is at least 0.5 dBm
        above the threshold.

"
    ::= { ifOpticalTransLaneCarrierGroupEntry 12 }

ifOpticalTransLaneCarrierGroupTxFrequency OBJECT-TYPE
    SYNTAX      Frequency
    MAX-ACCESS  read-only
    STATUS      current
    DESCRIPTION
        "The transmitted frequency given in wavelength nm
        or as channels, in case of multi lambda lane transciever
        this is the base frequency.
        E.g. ch871 means the frequency 187.1 THz.
        w1310 means the wavelength 1310 nm.

"
    ::= { ifOpticalTransLaneCarrierGroupEntry 13 }

ifOpticalTransLaneCarrierGroupExpectedTxFrequency OBJECT-TYPE
    SYNTAX      FrequencyOnlyNotApplicable
    MAX-ACCESS  read-only
    STATUS      current
    DESCRIPTION
        "The expected frequency given in wavelength nm
        or as channels.
        E.g. ch871 means the frequency 187.1 THz.
        w1310 means the wavelength 1310 nm.

"
    DEFVAL { 0 }
    ::= { ifOpticalTransLaneCarrierGroupEntry 14 }

ifOpticalTransLaneCarrierGroupUnexpectedTxFrequency OBJECT-TYPE
    SYNTAX      FaultStatusWithNA
    MAX-ACCESS  read-only
    STATUS      current
    DESCRIPTION
        "Unexpected transmitted frequency.

        The actual frequency does not match the
        pre-configured frequency.

        A pre-configured frequency of '0' matches
        all actual frequencies.

        alarm: The configured frequency does not match the
        actual frequency.

        ok: The configured frequency matches the actual
        frequency.

"
    ::= { ifOpticalTransLaneCarrierGroupEntry 15 }

ifOpticalTransLaneCarrierGroupIllegalTxFrequency OBJECT-TYPE
    SYNTAX      FaultStatusWithNA
    MAX-ACCESS  read-only
    STATUS      current
    DESCRIPTION
        "Illegal tx frequency.

        The tx frequency supported by the transceiver is not
        recognized by the system.

        alarm: Invalid or unknown frequency information is
               detected in the (pluggable) transceiver or
               board production data.

        ok: The (pluggable) transceiver or board is
            replaced.

"
    ::= { ifOpticalTransLaneCarrierGroupEntry 16 }

ifOpticalTransLaneCarrierGroupCounterSesReset OBJECT-TYPE
    SYNTAX      ResetWithNA
    MAX-ACCESS  read-only
    STATUS      current
    DESCRIPTION
        "Reset SES Counter.
        After a successful reset the default value
        (normal) is restored in this attribute.

"
    DEFVAL { normal }
    ::= { ifOpticalTransLaneCarrierGroupEntry 17 }

ifOpticalTransLaneCarrierGroupMinimumLaneRxPowerLevel OBJECT-TYPE
    SYNTAX      Signed32WithNA
    MAX-ACCESS  read-only
    STATUS      current
    DESCRIPTION
        "The minimum received power level on any lane in units of 0.1 dBm.

"
    ::= { ifOpticalTransLaneCarrierGroupEntry 18 }

ifOpticalTransLaneCarrierGroupReceiverLaneSensitivity OBJECT-TYPE
    SYNTAX      Signed32WithNA
    MAX-ACCESS  read-only
    STATUS      current
    DESCRIPTION
        "The lowest power that the receiver is guaranteed
        to handle, on a single lane, in units of 0.1 dBm.

"
    ::= { ifOpticalTransLaneCarrierGroupEntry 19 }

-- ----------------------------------------------------
-- Notifications
-- ----------------------------------------------------


-- ----------------------------------------------------
-- Object and event groups
-- ----------------------------------------------------

ifOpticalGeneralGroupV1 OBJECT-GROUP
    OBJECTS {
        ifOpticalGeneralConfigLastChangeTime,
        ifOpticalGeneralStateLastChangeTime,
        ifOpticalGeneralIfOpticalTransSectionTableSize,
        ifOpticalGeneralIfOpticalTransSectionConfigLastChangeTime,
        ifOpticalGeneralIfOpticalTransSectionStateLastChangeTime,
        ifOpticalGeneralIfOpticalChannelTableSize,
        ifOpticalGeneralIfOpticalChannelConfigLastChangeTime,
        ifOpticalGeneralIfOpticalChannelStateLastChangeTime,
        ifOpticalGeneralIfOpticalDigitalSignalRateTableSize,
        ifOpticalGeneralIfOpticalDigitalSignalRateConfigLastChangeTime,
        ifOpticalGeneralIfOpticalDigitalSignalRateStateLastChangeTime }

    STATUS      deprecated
    DESCRIPTION
        "The general objects."
    ::= { lumIfOpticalGroups 1 }

ifOpticalTransSectionGroupV1 OBJECT-GROUP
    OBJECTS {
        ifOpticalTransSectionIndex,
        ifOpticalTransSectionName,
        ifOpticalTransSectionConnIfBasicIfIndex,
        ifOpticalTransSectionForwardAls,
        ifOpticalTransSectionRxPowerLevel,
        ifOpticalTransSectionRxPowerLevelLowRelativeThld,
        ifOpticalTransSectionTxPowerLevel,
        ifOpticalTransSectionLaserMode,
        ifOpticalTransSectionLaserStatus,
        ifOpticalTransSectionReceiverSensitivity,
        ifOpticalTransSectionTxSignalStatus,
        ifOpticalTransSectionRxSignalStatus,
        ifOpticalTransSectionLossOfSignal,
        ifOpticalTransSectionRxPowerLevelLow,
        ifOpticalTransSectionRxPowerLevelHigh,
        ifOpticalTransSectionRxExcessiveInputPower,
        ifOpticalTransSectionTxPowerLow }
    STATUS      deprecated
    DESCRIPTION
        "The ifOptical transmission section objects (R20.0)."
    ::= { lumIfOpticalGroups 2 }

ifOpticalChannelGroupV1 OBJECT-GROUP
    OBJECTS {
        ifOpticalChannelIndex,
        ifOpticalChannelName,
        ifOpticalChannelConnIfBasicIfIndex,
        ifOpticalChannelTxFrequency,
        ifOpticalChannelExpectedTxFrequency,
        ifOpticalChannelTxSignalStatus,
        ifOpticalChannelRxSignalStatus,
        ifOpticalChannelIllegalTxFrequency,
        ifOpticalChannelUnexpectedTxFrequency,
        ifOpticalChannelNoTxFrequencySet }
    STATUS      deprecated
    DESCRIPTION
        "The ifOptical channel objects (R20.0)."
    ::= { lumIfOpticalGroups 3 }

ifOpticalDigitalSignalRateGroupV1 OBJECT-GROUP
    OBJECTS {
        ifOpticalDigitalSignalRateIndex,
        ifOpticalDigitalSignalRateName,
        ifOpticalDigitalSignalRateConnIfBasicIfIndex,
        ifOpticalDigitalSignalRateMaxBitRate,
        ifOpticalDigitalSignalRateMinBitRate,
        ifOpticalDigitalSignalRateTxSignalStatus,
        ifOpticalDigitalSignalRateRxSignalStatus,
        ifOpticalDigitalSignalRateLossOfLock,
        ifOpticalDigitalSignalRateBitrateUnavailable }

    STATUS      current
    DESCRIPTION
        "The ifOptical digital signal rate objects (R20.0)."
    ::= { lumIfOpticalGroups 4 }

ifOpticalFecGroupV1 OBJECT-GROUP
    OBJECTS {
        ifOpticalFecIndex,
        ifOpticalFecName,
        ifOpticalFecConnIfBasicIfIndex,
        ifOpticalFecType,
        ifOpticalFecTxSignalStatus,
        ifOpticalFecRxSignalStatus,
        ifOpticalFecFailure,
        ifOpticalFecSignalDegraded,
        ifOpticalFecSignalDegradeThreshold }

    STATUS      deprecated
    DESCRIPTION
        "The ifOptical Fec objects (R21.0)."
    ::= { lumIfOpticalGroups 5 }

ifOpticalGeneralGroupV2 OBJECT-GROUP
    OBJECTS {
        ifOpticalGeneralConfigLastChangeTime,
        ifOpticalGeneralStateLastChangeTime,
        ifOpticalGeneralIfOpticalTransSectionTableSize,
        ifOpticalGeneralIfOpticalTransSectionConfigLastChangeTime,
        ifOpticalGeneralIfOpticalTransSectionStateLastChangeTime,
        ifOpticalGeneralIfOpticalChannelTableSize,
        ifOpticalGeneralIfOpticalChannelConfigLastChangeTime,
        ifOpticalGeneralIfOpticalChannelStateLastChangeTime,
        ifOpticalGeneralIfOpticalDigitalSignalRateTableSize,
        ifOpticalGeneralIfOpticalDigitalSignalRateConfigLastChangeTime,
        ifOpticalGeneralIfOpticalDigitalSignalRateStateLastChangeTime,
        ifOpticalGeneralIfOpticalFecTableSize,
        ifOpticalGeneralIfOpticalFecConfigLastChangeTime,
        ifOpticalGeneralIfOpticalFecStateLastChangeTime}

    STATUS      deprecated
    DESCRIPTION
        "The general objects."
    ::= { lumIfOpticalGroups 6 }

ifOpticalTransSectionGroupV2 OBJECT-GROUP
    OBJECTS {
        ifOpticalTransSectionIndex,
        ifOpticalTransSectionName,
        ifOpticalTransSectionConnIfBasicIfIndex,
        ifOpticalTransSectionForwardAls,
        ifOpticalTransSectionRxPowerLevel,
        ifOpticalTransSectionRxPowerLevelLowRelativeThld,
        ifOpticalTransSectionTxPowerLevel,
        ifOpticalTransSectionLaserMode,
        ifOpticalTransSectionLaserStatus,
        ifOpticalTransSectionReceiverSensitivity,
        ifOpticalTransSectionTxSignalStatus,
        ifOpticalTransSectionRxSignalStatus,
        ifOpticalTransSectionLossOfSignal,
        ifOpticalTransSectionRxPowerLevelLow,
        ifOpticalTransSectionRxPowerLevelHigh,
        ifOpticalTransSectionRxExcessiveInputPower,
        ifOpticalTransSectionTxPowerLow,
        ifOpticalTransSectionRxPowerLevelLowAbsoluteThld }
    STATUS      deprecated
    DESCRIPTION
        "The ifOptical transmission section objects (R21.0)."
    ::= { lumIfOpticalGroups 7 }

ifOpticalGeneralGroupV3 OBJECT-GROUP
    OBJECTS {
        ifOpticalGeneralConfigLastChangeTime,
        ifOpticalGeneralStateLastChangeTime,
        ifOpticalGeneralIfOpticalTransSectionTableSize,
        ifOpticalGeneralIfOpticalTransSectionConfigLastChangeTime,
        ifOpticalGeneralIfOpticalTransSectionStateLastChangeTime,
        ifOpticalGeneralIfOpticalChannelTableSize,
        ifOpticalGeneralIfOpticalChannelConfigLastChangeTime,
        ifOpticalGeneralIfOpticalChannelStateLastChangeTime,
        ifOpticalGeneralIfOpticalDigitalSignalRateTableSize,
        ifOpticalGeneralIfOpticalDigitalSignalRateConfigLastChangeTime,
        ifOpticalGeneralIfOpticalDigitalSignalRateStateLastChangeTime,
        ifOpticalGeneralIfOpticalFecTableSize,
        ifOpticalGeneralIfOpticalFecConfigLastChangeTime,
        ifOpticalGeneralIfOpticalFecStateLastChangeTime,
        ifOpticalGeneralIfOpticalTransLaneCarrierTableSize,
        ifOpticalGeneralIfOpticalTransLaneCarrierConfigLastChangeTime,
        ifOpticalGeneralIfOpticalTransLaneCarrierStateLastChangeTime,
        ifOpticalGeneralIfOpticalTransLaneCarrierGroupTableSize,
        ifOpticalGeneralIfOpticalTransLaneCarrierGrConfigLastChangeTime,
        ifOpticalGeneralIfOpticalTransLaneCarrierGrStateLastChangeTime }

    STATUS      current
    DESCRIPTION
        "The general objects."
    ::= { lumIfOpticalGroups 8 }

ifOpticalTransLaneCarrierGroupV1 OBJECT-GROUP
    OBJECTS {
        ifOpticalTransLaneCarrierIndex,
        ifOpticalTransLaneCarrierName,
        ifOpticalTransLaneCarrierConnIfBasicIfIndex,
        ifOpticalTransLaneCarrierConnIfOpticalTransLaneCarrierGrIndex,
        ifOpticalTransLaneCarrierLaneId,
        ifOpticalTransLaneCarrierTxSignalStatus,
        ifOpticalTransLaneCarrierRxSignalStatus,
        ifOpticalTransLaneCarrierRxPowerLevel,
        ifOpticalTransLaneCarrierLossOfSignal,
        ifOpticalTransLaneCarrierReceiverSensitivity,
        ifOpticalTransLaneCarrierRxPowerLevelLow,
        ifOpticalTransLaneCarrierTxFrequency,
        ifOpticalTransLaneCarrierCounterSes,
        ifOpticalTransLaneCarrierCounterSesReset }

    STATUS      current
    DESCRIPTION
        "The ifOptical otlc objects (R22.0)."
    ::= { lumIfOpticalGroups 9 }

ifOpticalTransLaneCarrierGroupGroupV1 OBJECT-GROUP
    OBJECTS {
        ifOpticalTransLaneCarrierGroupIndex,
        ifOpticalTransLaneCarrierGroupName,
        ifOpticalTransLaneCarrierGroupConnIfBasicIfIndex,
        ifOpticalTransLaneCarrierGroupForwardAls,
        ifOpticalTransLaneCarrierGroupLaserStatus,
        ifOpticalTransLaneCarrierGroupTxPowerLevel,
        ifOpticalTransLaneCarrierGroupRxSignalStatus,
        ifOpticalTransLaneCarrierGroupRxPowerLevel,
        ifOpticalTransLaneCarrierGroupTxSignalStatus,
        ifOpticalTransLaneCarrierGroupLossOfSignal,
        ifOpticalTransLaneCarrierGroupRxPowerLevelLowRelativeThld,
        ifOpticalTransLaneCarrierGroupRxPowerLevelLow,
        ifOpticalTransLaneCarrierGroupTxFrequency,
        ifOpticalTransLaneCarrierGroupExpectedTxFrequency,
        ifOpticalTransLaneCarrierGroupUnexpectedTxFrequency,
        ifOpticalTransLaneCarrierGroupIllegalTxFrequency}

    STATUS      deprecated
    DESCRIPTION
        "The ifOptical otlcg objects (R22.0)."
    ::= { lumIfOpticalGroups 10 }


ifOpticalTransLaneCarrierGroupGroupV2 OBJECT-GROUP
    OBJECTS {
        ifOpticalTransLaneCarrierGroupIndex,
        ifOpticalTransLaneCarrierGroupName,
        ifOpticalTransLaneCarrierGroupConnIfBasicIfIndex,
        ifOpticalTransLaneCarrierGroupForwardAls,
        ifOpticalTransLaneCarrierGroupLaserStatus,
        ifOpticalTransLaneCarrierGroupTxPowerLevel,
        ifOpticalTransLaneCarrierGroupRxSignalStatus,
        ifOpticalTransLaneCarrierGroupRxPowerLevel,
        ifOpticalTransLaneCarrierGroupTxSignalStatus,
        ifOpticalTransLaneCarrierGroupLossOfSignal,
        ifOpticalTransLaneCarrierGroupRxPowerLevelLowRelativeThld,
        ifOpticalTransLaneCarrierGroupRxPowerLevelLow,
        ifOpticalTransLaneCarrierGroupTxFrequency,
        ifOpticalTransLaneCarrierGroupExpectedTxFrequency,
        ifOpticalTransLaneCarrierGroupUnexpectedTxFrequency,
        ifOpticalTransLaneCarrierGroupIllegalTxFrequency,
        ifOpticalTransLaneCarrierGroupCounterSesReset}

    STATUS      deprecated
    DESCRIPTION
        "The ifOptical otlcg objects (R23.0)."
    ::= { lumIfOpticalGroups 11 }


ifOpticalTransLaneCarrierGroupGroupV3 OBJECT-GROUP
    OBJECTS {
        ifOpticalTransLaneCarrierGroupIndex,
        ifOpticalTransLaneCarrierGroupName,
        ifOpticalTransLaneCarrierGroupConnIfBasicIfIndex,
        ifOpticalTransLaneCarrierGroupForwardAls,
        ifOpticalTransLaneCarrierGroupLaserStatus,
        ifOpticalTransLaneCarrierGroupTxPowerLevel,
        ifOpticalTransLaneCarrierGroupRxSignalStatus,
        ifOpticalTransLaneCarrierGroupRxPowerLevel,
        ifOpticalTransLaneCarrierGroupTxSignalStatus,
        ifOpticalTransLaneCarrierGroupLossOfSignal,
        ifOpticalTransLaneCarrierGroupRxPowerLevelLowRelativeThld,
        ifOpticalTransLaneCarrierGroupRxPowerLevelLow,
        ifOpticalTransLaneCarrierGroupTxFrequency,
        ifOpticalTransLaneCarrierGroupExpectedTxFrequency,
        ifOpticalTransLaneCarrierGroupUnexpectedTxFrequency,
        ifOpticalTransLaneCarrierGroupIllegalTxFrequency,
        ifOpticalTransLaneCarrierGroupCounterSesReset,
        ifOpticalTransLaneCarrierGroupMinimumLaneRxPowerLevel,
        ifOpticalTransLaneCarrierGroupReceiverLaneSensitivity}

    STATUS      current
    DESCRIPTION
        "The ifOptical otlcg objects (R25.0)."
    ::= { lumIfOpticalGroups 12 }

ifOpticalTransSectionGroupV3 OBJECT-GROUP
    OBJECTS {
        ifOpticalTransSectionIndex,
        ifOpticalTransSectionName,
        ifOpticalTransSectionConnIfBasicIfIndex,
        ifOpticalTransSectionForwardAls,
        ifOpticalTransSectionRxPowerLevel,
        ifOpticalTransSectionRxPowerLevelLowRelativeThld,
        ifOpticalTransSectionTxPowerLevel,
        ifOpticalTransSectionLaserMode,
        ifOpticalTransSectionLaserStatus,
        ifOpticalTransSectionReceiverSensitivity,
        ifOpticalTransSectionTxSignalStatus,
        ifOpticalTransSectionRxSignalStatus,
        ifOpticalTransSectionLossOfSignal,
        ifOpticalTransSectionRxPowerLevelLow,
        ifOpticalTransSectionRxPowerLevelHigh,
        ifOpticalTransSectionRxExcessiveInputPower,
        ifOpticalTransSectionTxPowerLow,
        ifOpticalTransSectionRxPowerLevelLowAbsoluteThld,
        ifOpticalTransSectionLossThld}

    STATUS      deprecated
    DESCRIPTION
        "The ifOptical transmission section objects (R26.0)."
    ::= { lumIfOpticalGroups 13 }

ifOpticalChannelGroupV2 OBJECT-GROUP
    OBJECTS {
        ifOpticalChannelIndex,
        ifOpticalChannelName,
        ifOpticalChannelConnIfBasicIfIndex,
        ifOpticalChannelTxFrequency,
        ifOpticalChannelExpectedTxFrequency,
        ifOpticalChannelTxSignalStatus,
        ifOpticalChannelRxSignalStatus,
        ifOpticalChannelIllegalTxFrequency,
        ifOpticalChannelUnexpectedTxFrequency,
        ifOpticalChannelNoTxFrequencySet,
        ifOpticalChannelDispersionSearchLimit }
    STATUS      deprecated
    DESCRIPTION
        "The ifOptical channel objects (R26.0)."
    ::= { lumIfOpticalGroups 14 }

ifOpticalFecGroupV2 OBJECT-GROUP
    OBJECTS {
        ifOpticalFecIndex,
        ifOpticalFecName,
        ifOpticalFecConnIfBasicIfIndex,
        ifOpticalFecType,
        ifOpticalFecTxSignalStatus,
        ifOpticalFecRxSignalStatus,
        ifOpticalFecFailure,
        ifOpticalFecSignalDegraded,
        ifOpticalFecSignalDegradeThreshold,
        ifOpticalFecTypeUnavailable,
        ifOpticalFecUId}

    STATUS      deprecated
    DESCRIPTION
        "The ifOptical Fec objects (R26.0)."
    ::= { lumIfOpticalGroups 15 }

ifOpticalFecGroupV3 OBJECT-GROUP
    OBJECTS {
        ifOpticalFecIndex,
        ifOpticalFecName,
        ifOpticalFecConnIfBasicIfIndex,
        ifOpticalFecType,
        ifOpticalFecTxSignalStatus,
        ifOpticalFecRxSignalStatus,
        ifOpticalFecFailure,
        ifOpticalFecSignalDegraded,
        ifOpticalFecSignalDegradeThreshold,
        ifOpticalFecTypeUnavailable,
        ifOpticalFecUId,
        ifOpticalFecDecModeMismatch}

    STATUS      current
    DESCRIPTION
        "The ifOptical Fec objects (R28.1)."
    ::= { lumIfOpticalGroups 16 }

ifOpticalChannelGroupV3 OBJECT-GROUP
    OBJECTS {
        ifOpticalChannelIndex,
        ifOpticalChannelName,
        ifOpticalChannelConnIfBasicIfIndex,
        ifOpticalChannelTxFrequency,
        ifOpticalChannelExpectedTxFrequency,
        ifOpticalChannelTxSignalStatus,
        ifOpticalChannelRxSignalStatus,
        ifOpticalChannelIllegalTxFrequency,
        ifOpticalChannelUnexpectedTxFrequency,
        ifOpticalChannelNoTxFrequencySet,
        ifOpticalChannelDispersionSearchLimit,
        ifOpticalChannelLaserNotTuned }
    STATUS      deprecated
    DESCRIPTION
        "The ifOptical channel objects (R28.1)."
    ::= { lumIfOpticalGroups 17 }

ifOpticalTransSectionGroupV4 OBJECT-GROUP
    OBJECTS {
        ifOpticalTransSectionIndex,
        ifOpticalTransSectionName,
        ifOpticalTransSectionConnIfBasicIfIndex,
        ifOpticalTransSectionForwardAls,
        ifOpticalTransSectionRxPowerLevel,
        ifOpticalTransSectionRxPowerLevelLowRelativeThld,
        ifOpticalTransSectionTxPowerLevel,
        ifOpticalTransSectionLaserMode,
        ifOpticalTransSectionLaserStatus,
        ifOpticalTransSectionReceiverSensitivity,
        ifOpticalTransSectionTxSignalStatus,
        ifOpticalTransSectionRxSignalStatus,
        ifOpticalTransSectionLossOfSignal,
        ifOpticalTransSectionRxPowerLevelLow,
        ifOpticalTransSectionRxPowerLevelHigh,
        ifOpticalTransSectionRxExcessiveInputPower,
        ifOpticalTransSectionTxPowerLow,
        ifOpticalTransSectionRxPowerLevelLowAbsoluteThld,
        ifOpticalTransSectionLossThld,
        ifOpticalTransSectionLaserForcedOn}

    STATUS      current
    DESCRIPTION
        "The ifOptical transmission section objects (R28.1)."
    ::= { lumIfOpticalGroups 18 }

ifOpticalChannelGroupV4 OBJECT-GROUP
    OBJECTS {
        ifOpticalChannelIndex,
        ifOpticalChannelName,
        ifOpticalChannelConnIfBasicIfIndex,
        ifOpticalChannelTxFrequency,
        ifOpticalChannelExpectedTxFrequency,
        ifOpticalChannelTxSignalStatus,
        ifOpticalChannelRxSignalStatus,
        ifOpticalChannelIllegalTxFrequency,
        ifOpticalChannelUnexpectedTxFrequency,
        ifOpticalChannelNoTxFrequencySet,
        ifOpticalChannelDispersionSearchLimit,
        ifOpticalChannelLaserNotTuned,
        ifOpticalChannelLineCoding }
    STATUS      current
    DESCRIPTION
        "The ifOptical channel objects (R29.1)."
    ::= { lumIfOpticalGroups 19 }

-- ----------------------------------------------------
-- Compliance
-- ----------------------------------------------------

lumIfOpticalComplV1 MODULE-COMPLIANCE
    STATUS      deprecated
    DESCRIPTION
        "Basic implementation requirements for the ifOptical MIB. (R20.0)"
    MODULE
        MANDATORY-GROUPS {
            ifOpticalGeneralGroupV1,
            ifOpticalTransSectionGroupV1,
            ifOpticalChannelGroupV1,
            ifOpticalDigitalSignalRateGroupV1 }
    ::= { lumIfOpticalCompl 1 }

lumIfOpticalComplV2 MODULE-COMPLIANCE
    STATUS      deprecated
    DESCRIPTION
        "Basic implementation requirements for the ifOptical MIB v2. (R21.0)"
    MODULE
        MANDATORY-GROUPS {
            ifOpticalGeneralGroupV2,
            ifOpticalTransSectionGroupV2,
            ifOpticalChannelGroupV1,
            ifOpticalDigitalSignalRateGroupV1,
            ifOpticalFecGroupV1 }
    ::= { lumIfOpticalCompl 2 }

lumIfOpticalComplV3 MODULE-COMPLIANCE
    STATUS      deprecated
    DESCRIPTION
        "Basic implementation requirements for the ifOptical MIB v2. (R22.0)"
    MODULE
        MANDATORY-GROUPS {
            ifOpticalGeneralGroupV3,
            ifOpticalTransSectionGroupV2,
            ifOpticalChannelGroupV1,
            ifOpticalDigitalSignalRateGroupV1,
            ifOpticalFecGroupV1,
            ifOpticalTransLaneCarrierGroupV1,
            ifOpticalTransLaneCarrierGroupGroupV1 }
    ::= { lumIfOpticalCompl 3 }

lumIfOpticalComplV4 MODULE-COMPLIANCE
    STATUS      deprecated
    DESCRIPTION
        "Basic implementation requirements for the ifOptical MIB v2. (R23.0)"
    MODULE
        MANDATORY-GROUPS {
            ifOpticalGeneralGroupV3,
            ifOpticalTransSectionGroupV2,
            ifOpticalChannelGroupV1,
            ifOpticalDigitalSignalRateGroupV1,
            ifOpticalFecGroupV1,
            ifOpticalTransLaneCarrierGroupV1,
            ifOpticalTransLaneCarrierGroupGroupV2 }
    ::= { lumIfOpticalCompl 4 }

lumIfOpticalComplV5 MODULE-COMPLIANCE
    STATUS      deprecated
    DESCRIPTION
        "Basic implementation requirements for the ifOptical MIB v2. (R23.0)"
    MODULE
        MANDATORY-GROUPS {
            ifOpticalGeneralGroupV3,
            ifOpticalTransSectionGroupV2,
            ifOpticalChannelGroupV1,
            ifOpticalDigitalSignalRateGroupV1,
            ifOpticalFecGroupV1,
            ifOpticalTransLaneCarrierGroupV1,
            ifOpticalTransLaneCarrierGroupGroupV3 }
    ::= { lumIfOpticalCompl 5 }

lumIfOpticalComplV6 MODULE-COMPLIANCE
    STATUS      deprecated
    DESCRIPTION
        "Basic implementation requirements for the ifOptical MIB v2. (R26.0)"
    MODULE
        MANDATORY-GROUPS {
            ifOpticalGeneralGroupV3,
            ifOpticalTransSectionGroupV3,
            ifOpticalChannelGroupV1,
            ifOpticalDigitalSignalRateGroupV1,
            ifOpticalFecGroupV1,
            ifOpticalTransLaneCarrierGroupV1,
            ifOpticalTransLaneCarrierGroupGroupV3 }
    ::= { lumIfOpticalCompl 6 }

lumIfOpticalComplV7 MODULE-COMPLIANCE
    STATUS      deprecated
    DESCRIPTION
        "Basic implementation requirements for the ifOptical MIB v2. (R26.0)"
    MODULE
        MANDATORY-GROUPS {
            ifOpticalGeneralGroupV3,
            ifOpticalTransSectionGroupV3,
            ifOpticalChannelGroupV1,
            ifOpticalDigitalSignalRateGroupV1,
            ifOpticalFecGroupV2,
            ifOpticalTransLaneCarrierGroupV1,
            ifOpticalTransLaneCarrierGroupGroupV3 }
    ::= { lumIfOpticalCompl 7 }

lumIfOpticalComplV8 MODULE-COMPLIANCE
    STATUS      deprecated
    DESCRIPTION
        "Basic implementation requirements for the ifOptical MIB v2. (R28.1)"
    MODULE
        MANDATORY-GROUPS {
            ifOpticalGeneralGroupV3,
            ifOpticalTransSectionGroupV4,
            ifOpticalChannelGroupV1,
            ifOpticalDigitalSignalRateGroupV1,
            ifOpticalFecGroupV3,
            ifOpticalTransLaneCarrierGroupV1,
            ifOpticalTransLaneCarrierGroupGroupV3 }
    ::= { lumIfOpticalCompl 8 }

lumIfOpticalComplV9 MODULE-COMPLIANCE
    STATUS      deprecated
    DESCRIPTION
        "Basic implementation requirements for the ifOptical MIB v2. (R29.1)"
    MODULE
        MANDATORY-GROUPS {
            ifOpticalGeneralGroupV3,
            ifOpticalTransSectionGroupV4,
            ifOpticalChannelGroupV4,
            ifOpticalDigitalSignalRateGroupV1,
            ifOpticalFecGroupV3,
            ifOpticalTransLaneCarrierGroupV1,
            ifOpticalTransLaneCarrierGroupGroupV3 }
    ::= { lumIfOpticalCompl 9 }

lumIfOpticalComplV10 MODULE-COMPLIANCE
    STATUS      current
    DESCRIPTION
        "Basic implementation requirements for the ifOptical MIB v2. (R30.1)"
    MODULE
        MANDATORY-GROUPS {
            ifOpticalGeneralGroupV3,
            ifOpticalTransSectionGroupV4,
            ifOpticalChannelGroupV4,
            ifOpticalDigitalSignalRateGroupV1,
            ifOpticalFecGroupV3,
            ifOpticalTransLaneCarrierGroupV1,
            ifOpticalTransLaneCarrierGroupGroupV3 }
    ::= { lumIfOpticalCompl 10 }

END
