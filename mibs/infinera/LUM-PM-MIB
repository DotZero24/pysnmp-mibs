LUM-PM-MIB DEFINITIONS ::= BEGIN

IMPORTS
    MODULE-IDENTITY, OBJECT-TYPE, Unsigned32, NOTIFICATION-TYPE,
    Integer32, Gauge32, Counter32, Counter64
        FROM SNMPv2-SMI
    OBJECT-GROUP, NOTIFICATION-GROUP, MODULE-COMPLIANCE
        FROM SNMPv2-CONF
    TEXTUAL-CONVENTION, DateAndTime, TruthValue, DisplayString
        FROM SNMPv2-TC
    lumModules, lumPmMIB
        FROM LUM-REG
    SubrackNumber, SlotNumber, PortNumber, MgmtNameString, FaultStatus,
    BoardOrInterfaceOperStatus, BoardOrInterfaceAdminStatus,
    CommandString, ObjectProperty, OnOff
        FROM LUM-TC;

lumPmMIBModule MODULE-IDENTITY
    LAST-UPDATED
        "201812210000Z" -- Dec 21st 2018
    ORGANIZATION
        "Infinera Corporation"
    CONTACT-INFO
        "techsupport@infinera.com"
    DESCRIPTION
        "The performance measurement MIB.

        - General

        - 15 minute interval measurements per
        measurement point

        - 24 hour interval measurements per
        measurement point

        - Current meters and configuration per
        interface

"
    REVISION
        "201812210000Z" -- Dec 21st 2018
    DESCRIPTION
        "Changes made for release r32.0:
         - added new PM drop and egress counters"
    REVISION
        "201709010000Z" -- September 1st 2017
    DESCRIPTION
        "Changes made for release r30.0:
         - added the emxp440 board"
    REVISION
        "201706150000Z" -- June 15th 2017
    DESCRIPTION
        "Changes made for release r29.0:
         - Changed ORGANIZATION and CONTACT-INFO"
    REVISION
        "201605240000Z" -- May 24th 2016
    DESCRIPTION
        "Corrected pmMpoLanes table."
    REVISION
        "201604290000Z" -- April 29th 2016
    DESCRIPTION
        "Added ifno and upPortid in pmDrop."
    REVISION
        "201601110000Z" -- Jan 11th 2016
    DESCRIPTION
        "Added default value notPresent for operStatus."
    REVISION
        "201512030000Z" -- May 16th 2014
    DESCRIPTION
        "Added ifno and upportid in pmEthTd and pmIf."
    REVISION
        "201405160000Z" -- May 16th 2014
    DESCRIPTION
        "Improved descriptions for pmEthTd attributes."
    REVISION
        "201303270000Z" -- March 27th 2013
    DESCRIPTION
        "Added vlanId as attribute in pmEthTd.
         Added alarmClearDelay annotation for ES, SES and UAS."
    REVISION
        "201110030000Z" -- October 3rd 2011
    DESCRIPTION
        "Changed longalias for Gbe utilization."
    REVISION
        "201103010000Z" -- March 1st 2011
    DESCRIPTION
        "Pm Interval tables to deprecated + some layer 2."
    REVISION
        "200803180000Z" -- March 18th 2008
    DESCRIPTION
        "Added ethernet traffic data, mgmt and OAM PM counters."
    REVISION
        "200709170000Z" -- September 17th 2007
    DESCRIPTION
        "Added last sequence numbers for PM files."
    REVISION
        "200503090000Z" -- March 9th 2005
    DESCRIPTION
        "Added support for PM log retrieval."
    REVISION
        "200410270000Z" -- October 27th 2004
    DESCRIPTION
        "Added maximimum GbE utilization for
        24 hour and 15 minute intervals."
    REVISION
        "200406020000Z" -- June 2nd 2004
    DESCRIPTION
        "Added rxPowerLevel sample in 24h interval."
    REVISION
        "200209230000Z" -- September 23rd 2002
    DESCRIPTION
        "Added isSuspect15/24 for current values."
    REVISION
        "200208090000Z" -- August 9th 2002
    DESCRIPTION
        "Added sequence number for 15 min and 24 h pm files."
    REVISION
        "200205310000Z" -- May 31st 2002
    DESCRIPTION
        "Added pmIfRxPort."
    REVISION
        "200205170000Z" -- May 17th 2002
    DESCRIPTION
        "Added threshold configuration and pm log file tables.
        Moved alarms from the wdm and multirate mibs."
    REVISION
        "200201170000Z" -- January 17th 2002
    DESCRIPTION
        "Removed the valid flag.
        Invalid reports will return read error."
    REVISION
        "200201110000Z" -- January 11th 2002
    DESCRIPTION
        "The initial revision of this module."
    ::= { lumModules 16 }


-- ----------------------------------------------------
-- Conformance area, containing groups and compliance
-- specifications.
-- ----------------------------------------------------

lumPmConfs OBJECT IDENTIFIER ::= { lumPmMIB 1 }
lumPmGroups OBJECT IDENTIFIER ::= { lumPmConfs 1 }
lumPmCompl OBJECT IDENTIFIER ::= { lumPmConfs 2 }


-- ----------------------------------------------------
-- Root for objects in the pm MIB
-- ----------------------------------------------------

lumPmMIBObjects OBJECT IDENTIFIER ::= { lumPmMIB 2 }


-- ----------------------------------------------------
-- This MIB contains the following groups:
-- ----------------------------------------------------

pmGeneral OBJECT IDENTIFIER ::= { lumPmMIBObjects 1 }
pmInterval OBJECT IDENTIFIER ::= { lumPmMIBObjects 2 }
pmInterval24h OBJECT IDENTIFIER ::= { lumPmMIBObjects 3 }
lumentisPmNotifications  OBJECT IDENTIFIER ::= { lumPmMIBObjects 4 }
pmFile OBJECT IDENTIFIER ::= { lumPmMIBObjects 5 }
pmIfList OBJECT IDENTIFIER ::= { lumPmMIBObjects 6 }
pmLogGeneral OBJECT IDENTIFIER ::= { lumPmMIBObjects 7 }
pmFile24h OBJECT IDENTIFIER ::= { lumPmMIBObjects 8 }
pmControl OBJECT IDENTIFIER ::= { lumPmMIBObjects 9 }
pmEthTdList OBJECT IDENTIFIER ::= { lumPmMIBObjects 10 }
pmEthTmList OBJECT IDENTIFIER ::= { lumPmMIBObjects 11 }
pmEthOamList OBJECT IDENTIFIER ::= { lumPmMIBObjects 12 }
pmEthDropList OBJECT IDENTIFIER ::= { lumPmMIBObjects 13 }
pmEthClassificationList OBJECT IDENTIFIER ::= { lumPmMIBObjects 14 }
pmMpoLanesList OBJECT IDENTIFIER ::= { lumPmMIBObjects 15 }
pmEthEgressList OBJECT IDENTIFIER ::= { lumPmMIBObjects 16 }

-- ----------------------------------------------------
-- Textual Conventions
-- ----------------------------------------------------

PmInterval15mNumber ::= TEXTUAL-CONVENTION
    DISPLAY-HINT "d"
    STATUS      current
    DESCRIPTION
        "A number which identifies the interval for which
        the set of statistics is available.
        The interval identified by 1 is the most recently
        completed interval, and the interval identified
        by N is the interval immediately preceding the
        one identified by N-1."
    SYNTAX Unsigned32 (1..96)

PmInterval24hNumber ::= TEXTUAL-CONVENTION
    DISPLAY-HINT "d"
    STATUS      current
    DESCRIPTION
        "A number which identifies the interval for which
        the set of statistics is available.
        The interval identified by 1 is the most recently
        completed interval, and the interval identified
        by N is the interval immediately preceding the
        one identified by N-1."
    SYNTAX Unsigned32 (1..40)


-- ----------------------------------------------------
-- General group
-- ----------------------------------------------------

pmGeneralLastChangeTime OBJECT-TYPE
    SYNTAX      DateAndTime
    MAX-ACCESS  read-only
    STATUS      current
    DESCRIPTION
        "The time when the configuration of the MIB was
        last changed.

"
    ::= { pmGeneral 1 }

pmGeneralStateLastChangeTime OBJECT-TYPE
    SYNTAX      DateAndTime
    MAX-ACCESS  read-only
    STATUS      current
    DESCRIPTION
        "The time when the state of the MIB was last
        changed.

"
    ::= { pmGeneral 2 }

pmGeneralPmIfTableSize OBJECT-TYPE
    SYNTAX      Unsigned32
    MAX-ACCESS  read-only
    STATUS      current
    DESCRIPTION
        "Size of table.

"
    ::= { pmGeneral 3 }

pmGeneralPmEthTdTableSize OBJECT-TYPE
    SYNTAX      Unsigned32
    MAX-ACCESS  read-only
    STATUS      current
    DESCRIPTION
        "Size of table.

"
    ::= { pmGeneral 4 }

pmGeneralPmEthTmTableSize OBJECT-TYPE
    SYNTAX      Unsigned32
    MAX-ACCESS  read-only
    STATUS      obsolete
    DESCRIPTION
        "Size of table.

"
    ::= { pmGeneral 5 }

pmGeneralPmEthOamTableSize OBJECT-TYPE
    SYNTAX      Unsigned32
    MAX-ACCESS  read-only
    STATUS      obsolete
    DESCRIPTION
        "Size of table.

"
    ::= { pmGeneral 6 }

pmGeneralPmEthDropTableSize OBJECT-TYPE
    SYNTAX      Unsigned32
    MAX-ACCESS  read-only
    STATUS      current
    DESCRIPTION
        "Size of table.

"
    ::= { pmGeneral 7 }

pmGeneralPmEthClassificationTableSize OBJECT-TYPE
    SYNTAX      Unsigned32
    MAX-ACCESS  read-only
    STATUS      current
    DESCRIPTION
        "Size of table.

"
    ::= { pmGeneral 8 }

pmGeneralPmMpoLanesTableSize OBJECT-TYPE
    SYNTAX      Unsigned32
    MAX-ACCESS  read-only
    STATUS      current
    DESCRIPTION
        "Size of table.

"
    ::= { pmGeneral 9 }

-- ----------------------------------------------------
-- General log parameters group
-- ----------------------------------------------------

pmLogGeneralLastChangeTime OBJECT-TYPE
    SYNTAX      DateAndTime
    MAX-ACCESS  read-only
    STATUS      current
    DESCRIPTION
        "The time when the PM log was last changed.

"
    ::= { pmLogGeneral 1 }

pmLogGeneralSize OBJECT-TYPE
    SYNTAX      Unsigned32 (0..96)
    MAX-ACCESS  read-write
    STATUS      current
    DESCRIPTION
        "Number of logged 15 minute intervals.

"
    DEFVAL { 32 }
    ::= { pmLogGeneral 2 }

pmLogGeneralSize24h OBJECT-TYPE
    SYNTAX      Unsigned32 (0..40)
    MAX-ACCESS  read-write
    STATUS      current
    DESCRIPTION
        "Number of logged 24 hour intervals.

"
    DEFVAL { 7 }
    ::= { pmLogGeneral 3 }

pmLogGeneralFileTableSize OBJECT-TYPE
    SYNTAX      Unsigned32
    MAX-ACCESS  read-only
    STATUS      current
    DESCRIPTION
        "Number of rows available in the
        15 minute file table.

"
    ::= { pmLogGeneral 4 }

pmLogGeneralFile24hTableSize OBJECT-TYPE
    SYNTAX      Unsigned32
    MAX-ACCESS  read-only
    STATUS      current
    DESCRIPTION
        "Number of rows available in the
        24 hour file table.

"
    ::= { pmLogGeneral 5 }

pmLogGeneralInterval15mTableSize OBJECT-TYPE
    SYNTAX      Unsigned32
    MAX-ACCESS  read-only
    STATUS      deprecated
    DESCRIPTION
        "Number of rows available in the
        15 minute interval table.

"
    ::= { pmLogGeneral 6 }

pmLogGeneralInterval24hTableSize OBJECT-TYPE
    SYNTAX      Unsigned32
    MAX-ACCESS  read-only
    STATUS      deprecated
    DESCRIPTION
        "Number of rows available in the
        24 hour interval table.

"
    ::= { pmLogGeneral 7 }

pmLogGeneralInterval15mShowNonZeroOnly OBJECT-TYPE
    SYNTAX      INTEGER {
                    off (1),
                    on (2) }
    MAX-ACCESS  read-write
    STATUS      deprecated
    DESCRIPTION
        "Show only non zero intervals.

"
    DEFVAL { on }
    ::= { pmLogGeneral 8 }

pmLogGeneralInterval24hShowNonZeroOnly OBJECT-TYPE
    SYNTAX      INTEGER {
                    off (1),
                    on (2) }
    MAX-ACCESS  read-write
    STATUS      deprecated
    DESCRIPTION
        "Show only non zero intervals.

"
    DEFVAL { on }
    ::= { pmLogGeneral 9 }

pmLogGeneralFile15mLastSeqNumber OBJECT-TYPE
    SYNTAX      Counter32
    MAX-ACCESS  read-only
    STATUS      current
    DESCRIPTION
        "Last sequence number for 15 minute files.

"
    ::= { pmLogGeneral 10 }

pmLogGeneralFile24hLastSeqNumber OBJECT-TYPE
    SYNTAX      Counter32
    MAX-ACCESS  read-only
    STATUS      current
    DESCRIPTION
        "Last sequence number for the 24 hour files.

"
    ::= { pmLogGeneral 11 }


-- ----------------------------------------------------
-- PM 15 minute interval log files
-- ----------------------------------------------------

pmFileTable OBJECT-TYPE
    SYNTAX  SEQUENCE OF PmFileEntry
    MAX-ACCESS  not-accessible
    STATUS  current
    DESCRIPTION
     "The line tx 15 min interval table."
::= { pmFile 1 }

pmFileEntry OBJECT-TYPE
    SYNTAX  PmFileEntry
    MAX-ACCESS  not-accessible
    STATUS  current
    DESCRIPTION
        "An entry in the 15 minute log file table.

"
    INDEX { pmFileIndex }
    ::= { pmFileTable 1 }

PmFileEntry ::=
    SEQUENCE {
        pmFileIndex             PmInterval15mNumber,
        pmFileName              DisplayString,
        pmFileCreatedTime       DateAndTime,
        pmFileSeqNumber         Counter32,
        pmFileStartTime         DateAndTime,
        pmFileStopTime          DateAndTime,
        pmFileUrl               DisplayString }

pmFileIndex OBJECT-TYPE
    SYNTAX  PmInterval15mNumber
    MAX-ACCESS read-only
    STATUS  current
    DESCRIPTION
        "A number which identifies the interval for which
        the set of statistics is available.
        The interval identified by 1 is the most recently
        completed interval, and the interval identified
        by N is the interval immediately preceding the
        one identified by N-1.

"
     ::= { pmFileEntry 1 }

pmFileName OBJECT-TYPE
    SYNTAX      DisplayString
    MAX-ACCESS  read-only
    STATUS      current
    DESCRIPTION
        "The name of the file.

"
    ::= { pmFileEntry 2 }

pmFileCreatedTime OBJECT-TYPE
    SYNTAX      DateAndTime
    MAX-ACCESS  read-only
    STATUS      current
    DESCRIPTION
        "The time when the file was created.

"
    ::= { pmFileEntry 3 }

pmFileSeqNumber OBJECT-TYPE
    SYNTAX      Counter32
    MAX-ACCESS  read-only
    STATUS      current
    DESCRIPTION
        "The last sequence number used when issuing
        a notification for this file.

"
    ::= { pmFileEntry 4 }

pmFileStartTime OBJECT-TYPE
    SYNTAX      DateAndTime
    MAX-ACCESS  read-only
    STATUS      current
    DESCRIPTION
        "The time when collection started for this file.

"
    ::= { pmFileEntry 5 }

pmFileStopTime OBJECT-TYPE
    SYNTAX      DateAndTime
    MAX-ACCESS  read-only
    STATUS      current
    DESCRIPTION
        "The time when collection stopped for this file.

"
    ::= { pmFileEntry 6 }

pmFileUrl OBJECT-TYPE
    SYNTAX      DisplayString
    MAX-ACCESS  read-only
    STATUS      current
    DESCRIPTION
        "The full path indicating where the file
        can be found on the network element.

"
    ::= { pmFileEntry 7 }

-- ----------------------------------------------------
-- PM 15 minute intervals
-- ----------------------------------------------------

pmIntervalTable OBJECT-TYPE
    SYNTAX  SEQUENCE OF PmIntervalEntry
    MAX-ACCESS  not-accessible
    STATUS  deprecated
    DESCRIPTION
     "The line tx 15 min interval table."
::= { pmInterval 1 }

pmIntervalEntry OBJECT-TYPE
    SYNTAX  PmIntervalEntry
    MAX-ACCESS  not-accessible
    STATUS  deprecated
    DESCRIPTION
        "An entry in the interval table.

"
    INDEX   { pmIntervalNumber,
              pmIntervalSubrack,
              pmIntervalSlot,
              pmIntervalPort }
    ::= { pmIntervalTable 1 }

PmIntervalEntry ::=
    SEQUENCE {
        pmIntervalSubrack               SubrackNumber,
        pmIntervalSlot                  SlotNumber,
        pmIntervalPort                  PortNumber,
        pmIntervalNumber                Unsigned32,
        pmIntervalStartTime             DateAndTime,
        pmIntervalIsSuspect             TruthValue,
        pmIntervalRxES                  Gauge32,
        pmIntervalRxSES                 Gauge32,
        pmIntervalRxBBE                 Gauge32,
        pmIntervalRxUAS                 Gauge32,
        pmIntervalTxES                  Gauge32,
        pmIntervalTxSES                 Gauge32,
        pmIntervalTxBBE                 Gauge32,
        pmIntervalTxUAS                 Gauge32,
        pmIntervalName                  MgmtNameString,
        pmIntervalRxPowerLevel          Integer32,
        pmIntervalGbeMaxUtilization     Unsigned32,
        pmIntervalTxPowerLevel          Integer32,
        pmIntervalStopTime              DateAndTime,

        -- Ethernet traffic data
        pmIntervalRxUndersizedFrames    Counter64,
        pmIntervalRxOversizedFrames     Counter64,
        pmIntervalRxFragments           Counter64,
        pmIntervalRxFcsErrors           Counter64,
        pmIntervalRxInvalidCeVlanId     Counter64,
        pmIntervalTxOctets              Counter64,
        pmIntervalTxFrames              Counter64,
        pmIntervalTxUnicastFrames       Counter64,
        pmIntervalTxMulticastFrames     Counter64,
        pmIntervalTxBroadcastFrames     Counter64,
        pmIntervalRxOctets              Counter64,
        pmIntervalRxFrames              Counter64,
        pmIntervalRxUnicastFrames       Counter64,
        pmIntervalRxMulticastFrames     Counter64,
        pmIntervalRxBroadcastFrames     Counter64,
        pmIntervalRxEthMaxUtilization   Unsigned32,
        pmIntervalTxEthMaxUtilization   Unsigned32,

        -- Ethernet traffic mgmt
        pmIntervalIngressGreenFrameCount Counter64,
        pmIntervalIngressYellowFrameCount Counter64,
        pmIntervalIngressRedFrameCount  Counter64,
        pmIntervalIngressGreenOctetCount Counter64,
        pmIntervalIngressYellowOctetCount Counter64,
        pmIntervalIngressRedOctetCount  Counter64,
        pmIntervalEgressGreenFrameCount Counter64,
        pmIntervalEgressGreenOctetCount Counter64,
        pmIntervalGreenFrameDiscards    Counter64,
        pmIntervalYellowFrameDiscards   Counter64,
        pmIntervalGreenOctetDiscards    Counter64,
        pmIntervalYellowOctetDiscards   Counter64,

        -- Ethernet OAM
        pmIntervalTwoWayFrameDelay           Gauge32,
        pmIntervalTwoWayFrameDelayVariation  Gauge32,
        pmIntervalFrameLossRatioNearEnd      Gauge32,
        pmIntervalFrameLossRatioFarEnd       Gauge32,
        pmIntervalUnavailabilityNearEnd      Gauge32,
        pmIntervalUnavailabilityFarEnd       Gauge32,
        pmIntervalOneWayFrameDelayVariation  Gauge32 }

pmIntervalSubrack OBJECT-TYPE
    SYNTAX  SubrackNumber
    MAX-ACCESS read-only
    STATUS  current
    DESCRIPTION
        "The subrack number for the interface in question.

"
     ::= { pmIntervalEntry 1 }

pmIntervalSlot OBJECT-TYPE
    SYNTAX  SlotNumber
    MAX-ACCESS read-only
    STATUS  current
    DESCRIPTION
         "The slot number for the interface in question.

"
     ::= { pmIntervalEntry 2 }

pmIntervalPort OBJECT-TYPE
    SYNTAX  PortNumber
    MAX-ACCESS read-only
    STATUS  current
    DESCRIPTION
        "The port number for the interface in question.

"
     ::= { pmIntervalEntry 3 }

pmIntervalNumber OBJECT-TYPE
    SYNTAX  Unsigned32 (1..40)
    MAX-ACCESS read-only
    STATUS  current
    DESCRIPTION
        "A number between 1 and 40, which identifies the
        interval for which the set of statistics is
        available. The interval identified by 1 is the
        most recently completed 24 hour interval, and the
        interval identified by N is the interval
        immediately preceding the one identified by N-1.

"
     ::= { pmIntervalEntry 4 }

pmIntervalIsSuspect OBJECT-TYPE
    SYNTAX  TruthValue
    MAX-ACCESS  read-only
    STATUS  current
    DESCRIPTION
       "This variable indicates if the data for this
        interval is suspect. The interval may for example
        contain measurements for a part of the interval.

"
    ::= { pmIntervalEntry 5 }

pmIntervalRxES OBJECT-TYPE
    SYNTAX  Gauge32
    MAX-ACCESS  read-only
    STATUS  current
    DESCRIPTION
       "The counter associated with the number of
       Errored Seconds in a particular 15 min interval
       during the past 15 min intervals.

"
     ::= { pmIntervalEntry 6 }

pmIntervalRxSES OBJECT-TYPE
    SYNTAX  Gauge32
    MAX-ACCESS  read-only
    STATUS  current
    DESCRIPTION
       "The counter associated with the number of
       Severely Errored Seconds in a particular 15 min
       interval during the past 15 min intervals.

"
    ::= { pmIntervalEntry 7 }

pmIntervalRxBBE OBJECT-TYPE
    SYNTAX  Gauge32
    MAX-ACCESS  read-only
    STATUS  current
    DESCRIPTION
       "The counter associated with the number of
       Background Block Errors in a particular 15 min
       interval.

"
    ::= { pmIntervalEntry 8 }

pmIntervalRxUAS OBJECT-TYPE
    SYNTAX  Gauge32
    MAX-ACCESS  read-only
    STATUS  current
    DESCRIPTION
       "The counter associated with the number of
       Unavailable Seconds in a particular 15 min
       interval.

"
    ::= { pmIntervalEntry 9 }

pmIntervalTxES OBJECT-TYPE
    SYNTAX  Gauge32
    MAX-ACCESS  read-only
    STATUS  current
    DESCRIPTION
       "The counter associated with the number of
       Errored Seconds in a particular 15 min interval.

"
     ::= { pmIntervalEntry 10 }

pmIntervalTxSES OBJECT-TYPE
    SYNTAX  Gauge32
    MAX-ACCESS  read-only
    STATUS  current
    DESCRIPTION
       "The counter associated with the number of
       Severely Errored Seconds in a particular 15 min
       interval.

"
    ::= { pmIntervalEntry 11 }

pmIntervalTxBBE OBJECT-TYPE
    SYNTAX  Gauge32
    MAX-ACCESS  read-only
    STATUS  current
    DESCRIPTION
       "The counter associated with the number of
       Background Block Errors in the current 15 min
       interval.

"
    ::= { pmIntervalEntry 12 }

pmIntervalTxUAS OBJECT-TYPE
    SYNTAX  Gauge32
    MAX-ACCESS  read-only
    STATUS  current
    DESCRIPTION
       "The counter associated with the number of
       Unavailable Seconds in a particular 15 min
       interval.

"
    ::= { pmIntervalEntry 13 }

pmIntervalName OBJECT-TYPE
    SYNTAX  MgmtNameString
    MAX-ACCESS  read-only
    STATUS  current
    DESCRIPTION
       "The name of the interface.

"
    ::= { pmIntervalEntry 14 }

pmIntervalRxPowerLevel OBJECT-TYPE
    SYNTAX  Integer32
    MAX-ACCESS  read-only
    STATUS  current
    DESCRIPTION
       "The received power level in units of 0.1 dBm
       sampled some time during a particular 15 minute
       interval.

"
    ::= { pmIntervalEntry 15 }

pmIntervalGbeMaxUtilization OBJECT-TYPE
    SYNTAX  Unsigned32
    MAX-ACCESS  read-only
    STATUS  current
    DESCRIPTION
       "The maximum bandwidth utilization of the
       GbE signal during a particular 15 minute interval.

"
    ::= { pmIntervalEntry 16 }

pmIntervalTxPowerLevel OBJECT-TYPE
    SYNTAX  Integer32
    MAX-ACCESS  read-only
    STATUS  current
    DESCRIPTION
       "The transmitted power level in units of 0.1 dBm
       sampled some time during a particular 15 minute
       interval.

"
    ::= { pmIntervalEntry 17 }

pmIntervalRxUndersizedFrames OBJECT-TYPE
     SYNTAX Counter64
     MAX-ACCESS read-only
     STATUS current
     DESCRIPTION
        "The amount of undersized frames
        during a particular 15 minute interval.

"
    ::= { pmIntervalEntry 18 }

pmIntervalRxOversizedFrames OBJECT-TYPE
     SYNTAX Counter64
     MAX-ACCESS read-only
     STATUS current
     DESCRIPTION
        "The amount of oversized frames
        during a particular 15 minute interval.

"
    ::= { pmIntervalEntry 19 }

pmIntervalRxFragments OBJECT-TYPE
     SYNTAX Counter64
     MAX-ACCESS read-only
     STATUS current
     DESCRIPTION
        "The amount of fragments
        during a particular 15 minute interval.

"
    ::= { pmIntervalEntry 20 }

pmIntervalRxFcsErrors OBJECT-TYPE
     SYNTAX Counter64
     MAX-ACCESS read-only
     STATUS current
     DESCRIPTION
        "The amount of frames with FCS or alignment errors
        during a particular 15 minute interval.

"
    ::= { pmIntervalEntry 21 }

pmIntervalRxInvalidCeVlanId OBJECT-TYPE
     SYNTAX Counter64
     MAX-ACCESS read-only
     STATUS current
     DESCRIPTION
        "The amount of frames with invalid CE-VLAN id
        during a particular 15 minute interval.

"
    ::= { pmIntervalEntry 22 }

pmIntervalTxOctets OBJECT-TYPE
     SYNTAX Counter64
     MAX-ACCESS read-only
     STATUS current
     DESCRIPTION
        "The amount of octets transmitted OK
        during a particular 15 minute interval.

"
    ::= { pmIntervalEntry 23 }

pmIntervalTxFrames OBJECT-TYPE
     SYNTAX Counter64
     MAX-ACCESS read-only
     STATUS current
     DESCRIPTION
        "The amount of frames transmitted OK
        during a particular 15 minute interval.

"
    ::= { pmIntervalEntry 24 }

pmIntervalTxUnicastFrames OBJECT-TYPE
     SYNTAX Counter64
     MAX-ACCESS read-only
     STATUS current
     DESCRIPTION
        "The amount of unicast frames transmitted OK
        during a particular 15 minute interval.

"
    ::= { pmIntervalEntry 25 }

pmIntervalTxMulticastFrames OBJECT-TYPE
     SYNTAX Counter64
     MAX-ACCESS read-only
     STATUS current
     DESCRIPTION
        "The amount of multicast frames transmitted OK
        during a particular 15 minute interval.

"
    ::= { pmIntervalEntry 26 }

pmIntervalTxBroadcastFrames OBJECT-TYPE
     SYNTAX Counter64
     MAX-ACCESS read-only
     STATUS current
     DESCRIPTION
        "The amount of broadcast frames transmitted OK
        during a particular 15 minute interval.

"
    ::= { pmIntervalEntry 27 }

pmIntervalRxOctets OBJECT-TYPE
     SYNTAX Counter64
     MAX-ACCESS read-only
     STATUS current
     DESCRIPTION
        "The amount of octets received OK
        during a particular 15 minute interval.

"
    ::= { pmIntervalEntry 28 }

pmIntervalRxFrames OBJECT-TYPE
     SYNTAX Counter64
     MAX-ACCESS read-only
     STATUS current
     DESCRIPTION
        "The amount of frames received OK
        during a particular 15 minute interval.

"
    ::= { pmIntervalEntry 29 }

pmIntervalRxUnicastFrames OBJECT-TYPE
     SYNTAX Counter64
     MAX-ACCESS read-only
     STATUS current
     DESCRIPTION
        "The amount of unicast frames received OK
        during a particular 15 minute interval.

"
    ::= { pmIntervalEntry 30 }

pmIntervalRxMulticastFrames OBJECT-TYPE
     SYNTAX Counter64
     MAX-ACCESS read-only
     STATUS current
     DESCRIPTION
        "The amount of multicast frames received OK
        during a particular 15 minute interval.

"
    ::= { pmIntervalEntry 31 }

pmIntervalRxBroadcastFrames OBJECT-TYPE
     SYNTAX Counter64
     MAX-ACCESS read-only
     STATUS current
     DESCRIPTION
        "The amount of broadcast frames received OK
        during a particular 15 minute interval.

"
    ::= { pmIntervalEntry 32 }

pmIntervalIngressGreenFrameCount OBJECT-TYPE
    SYNTAX Counter64
    MAX-ACCESS read-only
    STATUS current
    DESCRIPTION
        "The amount of green frames sent by the ingress UNI
        during a particular 15 minute interval.
"
    ::= { pmIntervalEntry 33 }

pmIntervalIngressYellowFrameCount OBJECT-TYPE
    SYNTAX Counter64
    MAX-ACCESS read-only
    STATUS current
    DESCRIPTION
        "The amount of yellow frames sent by the ingress UNI
        during a particular 15 minute interval.
"
    ::= { pmIntervalEntry 34 }

pmIntervalIngressRedFrameCount OBJECT-TYPE
    SYNTAX Counter64
    MAX-ACCESS read-only
    STATUS current
    DESCRIPTION
        "The amount of red frames sent by the ingress UNI
        during a particular 15 minute interval.
"
    ::= { pmIntervalEntry 35 }

pmIntervalIngressGreenOctetCount OBJECT-TYPE
    SYNTAX Counter64
    MAX-ACCESS read-only
    STATUS current
    DESCRIPTION
        "The amount of green octets sent by the ingress UNI
        during a particular 15 minute interval.
"
    ::= { pmIntervalEntry 36 }

pmIntervalIngressYellowOctetCount OBJECT-TYPE
    SYNTAX Counter64
    MAX-ACCESS read-only
    STATUS current
    DESCRIPTION
        "The amount of yellow octets sent by the ingress UNI
        during a particular 15 minute interval.
"
    ::= { pmIntervalEntry 37 }

pmIntervalIngressRedOctetCount OBJECT-TYPE
    SYNTAX Counter64
    MAX-ACCESS read-only
    STATUS current
    DESCRIPTION
        "The amount of red octects sent by the ingress UNI
        during a particular 15 minute interval.
"
    ::= { pmIntervalEntry 38 }

pmIntervalEgressGreenFrameCount OBJECT-TYPE
    SYNTAX Counter64
    MAX-ACCESS read-only
    STATUS current
    DESCRIPTION
        "The amount of green frames received by the egress UNI
        during a particular 15 minute interval.
"
    ::= { pmIntervalEntry 39 }

pmIntervalEgressGreenOctetCount OBJECT-TYPE
    SYNTAX Counter64
    MAX-ACCESS read-only
    STATUS current
    DESCRIPTION
        "The amount of green octets received by the egress UNI
        during a particular 15 minute interval.
"
    ::= { pmIntervalEntry 40 }

pmIntervalGreenFrameDiscards OBJECT-TYPE
    SYNTAX Counter64
    MAX-ACCESS read-only
    STATUS current
    DESCRIPTION
        "The amount of green frames discarded due to congestion
        during a particular 15 minute interval.
"
    ::= { pmIntervalEntry 41 }

pmIntervalYellowFrameDiscards OBJECT-TYPE
    SYNTAX Counter64
    MAX-ACCESS read-only
    STATUS current
    DESCRIPTION
        "The amount of yellow frames discarded due to congestion
        during a particular 15 minute interval.
"
    ::= { pmIntervalEntry 42 }

pmIntervalGreenOctetDiscards OBJECT-TYPE
    SYNTAX Counter64
    MAX-ACCESS read-only
    STATUS current
    DESCRIPTION
        "The amount of green octets discarded due to congestion
        during a particular 15 minute interval.
"
    ::= { pmIntervalEntry 43 }

pmIntervalYellowOctetDiscards OBJECT-TYPE
    SYNTAX Counter64
    MAX-ACCESS read-only
    STATUS current
    DESCRIPTION
        "The amount of yellow octets discarded due to congestion
        during a particular 15 minute interval.
"
    ::= { pmIntervalEntry 44 }

pmIntervalTwoWayFrameDelay OBJECT-TYPE
    SYNTAX Gauge32
    MAX-ACCESS read-only
    STATUS current
    DESCRIPTION
        "The time required to transmit a service frame from source to destination
        during a particular 15 minute interval.
"
    ::= { pmIntervalEntry 45 }

pmIntervalTwoWayFrameDelayVariation OBJECT-TYPE
    SYNTAX  Gauge32
    MAX-ACCESS read-only
    STATUS current
    DESCRIPTION
        "The difference in delay between two service frames
        during a particular 15 minute interval.
"
    ::= { pmIntervalEntry 46 }

pmIntervalFrameLossRatioNearEnd OBJECT-TYPE
    SYNTAX      Gauge32
    MAX-ACCESS read-only
    STATUS current
    DESCRIPTION
        "The number of service frames not delivered divided by the total number of service frames at near end
        during a particular 15 minute interval.
"
    ::= { pmIntervalEntry 47 }

pmIntervalFrameLossRatioFarEnd OBJECT-TYPE
    SYNTAX       Gauge32
    MAX-ACCESS read-only
    STATUS current
    DESCRIPTION
        "The number of service frames not delivered divided
        by the total number of service frames at far end
        during a particular 15 minute interval.
"
    ::= { pmIntervalEntry 48 }

pmIntervalUnavailabilityNearEnd OBJECT-TYPE
    SYNTAX      Gauge32
    MAX-ACCESS read-only
    STATUS current
    DESCRIPTION
        "The @todo
        during a particular 15 minute interval.
"
    ::= { pmIntervalEntry 49 }

pmIntervalUnavailabilityFarEnd OBJECT-TYPE
    SYNTAX       Gauge32
    MAX-ACCESS read-only
    STATUS current
    DESCRIPTION
        "The @todo
        during a particular 15 minute interval.
"
    ::= { pmIntervalEntry 50 }

pmIntervalOneWayFrameDelayVariation OBJECT-TYPE
    SYNTAX  Gauge32
    MAX-ACCESS read-only
    STATUS current
    DESCRIPTION
        "The difference in delay between two service frames
        during a particular 15 minute interval.
"
    ::= { pmIntervalEntry 51 }

pmIntervalTxEthMaxUtilization OBJECT-TYPE
    SYNTAX  Unsigned32
    MAX-ACCESS  read-only
    STATUS  current
    DESCRIPTION
       "The maximum layer 2 bandwidth utilization of the
       transmitted ethernet signal during a particular 15 minute interval.

"
    ::= { pmIntervalEntry 52 }

pmIntervalRxEthMaxUtilization OBJECT-TYPE
    SYNTAX  Unsigned32
    MAX-ACCESS  read-only
    STATUS  current
    DESCRIPTION
       "The maximum layer 2 bandwidth utilization of the
       received ethernet signal during a particular 15 minute interval.

"
    ::= { pmIntervalEntry 53 }

pmIntervalStartTime OBJECT-TYPE
    SYNTAX      DateAndTime
    MAX-ACCESS  read-only
    STATUS      current
    DESCRIPTION
        "The start time of the quarter where
         PM-reports are generated

"
    ::= { pmIntervalEntry 54 }

pmIntervalStopTime OBJECT-TYPE
    SYNTAX      DateAndTime
    MAX-ACCESS  read-only
    STATUS      current
    DESCRIPTION
        "The end time of the quarter where
         PM-reports are generated

"
    ::= { pmIntervalEntry 55 }

-- ----------------------------------------------------
-- PM 24 hour interval log files
-- ----------------------------------------------------

pmFile24hTable OBJECT-TYPE
    SYNTAX  SEQUENCE OF Pm24hFileEntry
    MAX-ACCESS  not-accessible
    STATUS  current
    DESCRIPTION
        "The line tx 24 hour interval table."
::= { pmFile24h 1 }

pmFile24hEntry OBJECT-TYPE
    SYNTAX  Pm24hFileEntry
    MAX-ACCESS  not-accessible
    STATUS  current
    DESCRIPTION
        "An entry in the 24 hour log file table.

"
    INDEX   { pmFile24hIndex }
    ::= { pmFile24hTable 1 }

Pm24hFileEntry ::=
    SEQUENCE {
        pmFile24hIndex          PmInterval24hNumber,
        pmFile24hName           DisplayString,
        pmFile24hCreatedTime    DateAndTime,
        pmFile24hSeqNumber      Counter32,
        pmFile24hStartTime      DateAndTime,
        pmFile24hStopTime       DateAndTime,
        pmFile24hUrl            DisplayString }

pmFile24hIndex OBJECT-TYPE
    SYNTAX  PmInterval24hNumber
    MAX-ACCESS read-only
    STATUS  current
    DESCRIPTION
        "A number which identifies the interval for which
        the set of statistics is available.
        The interval identified by 1 is the most recently
        completed interval, and the interval identified
        by N is the interval immediately preceding the
        one identified by N-1.

"
     ::= { pmFile24hEntry 1 }

pmFile24hName OBJECT-TYPE
    SYNTAX      DisplayString
    MAX-ACCESS  read-only
    STATUS      current
    DESCRIPTION
        "The name of the file.

"
    ::= { pmFile24hEntry 2 }

pmFile24hCreatedTime OBJECT-TYPE
    SYNTAX      DateAndTime
    MAX-ACCESS  read-only
    STATUS      current
    DESCRIPTION
        "The time when the file was created.

"
    ::= { pmFile24hEntry 3 }

pmFile24hSeqNumber OBJECT-TYPE
    SYNTAX      Counter32
    MAX-ACCESS  read-only
    STATUS      current
    DESCRIPTION
        "The last sequence number used when issuing
        a notification for this file.

"
    ::= { pmFile24hEntry 4 }

pmFile24hStartTime OBJECT-TYPE
    SYNTAX      DateAndTime
    MAX-ACCESS  read-only
    STATUS      current
    DESCRIPTION
        "The time when collection started for this file.

"
    ::= { pmFile24hEntry 5 }

pmFile24hStopTime OBJECT-TYPE
    SYNTAX      DateAndTime
    MAX-ACCESS  read-only
    STATUS      current
    DESCRIPTION
        "The time when collection stopped for this file.

"
    ::= { pmFile24hEntry 6 }

pmFile24hUrl OBJECT-TYPE
    SYNTAX      DisplayString
    MAX-ACCESS  read-only
    STATUS      current
    DESCRIPTION
        "The full path indicating where the file
        can be found on the network element.

"
    ::= { pmFile24hEntry 7 }


-- ----------------------------------------------------
-- PM 24 hour intervals
-- ----------------------------------------------------

pmInterval24hTable OBJECT-TYPE
    SYNTAX  SEQUENCE OF PmInterval24hEntry
    MAX-ACCESS  not-accessible
    STATUS  deprecated
    DESCRIPTION
     "The line tx 24 hour interval table."
::= { pmInterval24h 1 }

pmInterval24hEntry OBJECT-TYPE
    SYNTAX  PmInterval24hEntry
    MAX-ACCESS  not-accessible
    STATUS  deprecated
    DESCRIPTION
        "An entry in the interval table.

"
    INDEX   { pmInterval24hNumber,
              pmInterval24hSubrack,
              pmInterval24hSlot,
              pmInterval24hPort }
    ::= { pmInterval24hTable 1 }

PmInterval24hEntry ::=
    SEQUENCE {
        pmInterval24hSubrack            SubrackNumber,
        pmInterval24hSlot               SlotNumber,
        pmInterval24hPort               PortNumber,
        pmInterval24hNumber             PmInterval24hNumber,
        pmInterval24hStartTime          DateAndTime,
        pmInterval24hIsSuspect          TruthValue,
        pmInterval24hRxES               Gauge32,
        pmInterval24hRxSES              Gauge32,
        pmInterval24hRxBBE              Gauge32,
        pmInterval24hRxUAS              Gauge32,
        pmInterval24hTxES               Gauge32,
        pmInterval24hTxSES              Gauge32,
        pmInterval24hTxBBE              Gauge32,
        pmInterval24hTxUAS              Gauge32,
        pmInterval24hName               MgmtNameString,
        pmInterval24hRxPowerLevel       Integer32,
        pmInterval24hGbeMaxUtilization  Unsigned32,
        pmInterval24hTxPowerLevel       Integer32,
        pmInterval24hStopTime           DateAndTime,

        -- Ethernet traffic data
        pmInterval24hRxUndersizedFrames Counter64,
        pmInterval24hRxOversizedFrames  Counter64,
        pmInterval24hRxFragments        Counter64,
        pmInterval24hRxFcsErrors        Counter64,
        pmInterval24hRxInvalidCeVlanId  Counter64,
        pmInterval24hTxOctets           Counter64,
        pmInterval24hTxFrames           Counter64,
        pmInterval24hTxUnicastFrames    Counter64,
        pmInterval24hTxMulticastFrames  Counter64,
        pmInterval24hTxBroadcastFrames  Counter64,
        pmInterval24hRxOctets           Counter64,
        pmInterval24hRxFrames           Counter64,
        pmInterval24hRxUnicastFrames    Counter64,
        pmInterval24hRxMulticastFrames  Counter64,
        pmInterval24hRxBroadcastFrames  Counter64,
        pmInterval24hTxEthMaxUtilization        Unsigned32,
        pmInterval24hRxEthMaxUtilization        Unsigned32,

        -- Ethernet traffic mgmt
        pmInterval24hIngressGreenFrameCount     Counter64,
        pmInterval24hIngressYellowFrameCount    Counter64,
        pmInterval24hIngressRedFrameCount       Counter64,
        pmInterval24hIngressGreenOctetCount     Counter64,
        pmInterval24hIngressYellowOctetCount    Counter64,
        pmInterval24hIngressRedOctetCount       Counter64,
        pmInterval24hEgressGreenFrameCount      Counter64,
        pmInterval24hEgressGreenOctetCount      Counter64,
        pmInterval24hGreenFrameDiscards Counter64,
        pmInterval24hYellowFrameDiscards        Counter64,
        pmInterval24hGreenOctetDiscards Counter64,
        pmInterval24hYellowOctetDiscards        Counter64,

        -- Ethernet OAM
        pmInterval24hTwoWayFrameDelay           Gauge32,
        pmInterval24hTwoWayFrameDelayVariation  Gauge32,
        pmInterval24hFrameLossRatioNearEnd      Gauge32,
        pmInterval24hFrameLossRatioFarEnd       Gauge32,
        pmInterval24hUnavailabilityNearEnd      Gauge32,
        pmInterval24hUnavailabilityFarEnd       Gauge32,
        pmInterval24hOneWayFrameDelayVariation  Gauge32 }

pmInterval24hSubrack OBJECT-TYPE
    SYNTAX  SubrackNumber
    MAX-ACCESS read-only
    STATUS  current
    DESCRIPTION
        "The subrack number for the interface in question.

"
     ::= { pmInterval24hEntry 1 }

pmInterval24hSlot OBJECT-TYPE
    SYNTAX  SlotNumber
    MAX-ACCESS read-only
    STATUS  current
    DESCRIPTION
         "The slot number for the interface in question.

"
     ::= { pmInterval24hEntry 2 }

pmInterval24hPort OBJECT-TYPE
    SYNTAX  PortNumber
    MAX-ACCESS read-only
    STATUS  current
    DESCRIPTION
        "The port number for the interface in question.

"
     ::= { pmInterval24hEntry 3 }

pmInterval24hNumber OBJECT-TYPE
    SYNTAX  PmInterval24hNumber
    MAX-ACCESS read-only
    STATUS  current
    DESCRIPTION
      "A number between 1 and 40, which identifies the
      interval for which the set of statistics is
      available. The interval identified by 1 is the most
      recently completed 24 hour interval, and the
      interval identified by N is the interval
      immediately preceding the one identified by N-1.

"
     ::= { pmInterval24hEntry 4 }

pmInterval24hIsSuspect OBJECT-TYPE
    SYNTAX  TruthValue
    MAX-ACCESS  read-only
    STATUS  current
    DESCRIPTION
       "This variable indicates if the data for this
        interval is suspect. The interval may for example
        contain measurements for a part of the interval.

"
    ::= { pmInterval24hEntry 5 }

pmInterval24hRxES OBJECT-TYPE
    SYNTAX  Gauge32
    MAX-ACCESS  read-only
    STATUS  current
    DESCRIPTION
       "The counter associated with the number of
       Errored Seconds in a particular 24 hour interval.

"
     ::= { pmInterval24hEntry 6 }

pmInterval24hRxSES OBJECT-TYPE
    SYNTAX  Gauge32
    MAX-ACCESS  read-only
    STATUS  current
    DESCRIPTION
       "The counter associated with the number of
       Severely Errored Seconds in a particular 24 hour
       interval.

"
    ::= { pmInterval24hEntry 7 }

pmInterval24hRxBBE OBJECT-TYPE
    SYNTAX  Gauge32
    MAX-ACCESS  read-only
    STATUS  current
    DESCRIPTION
       "The counter associated with the number of
       Background Block Errors in a particular 24 hour
       interval.

"
    ::= { pmInterval24hEntry 8 }

pmInterval24hRxUAS OBJECT-TYPE
    SYNTAX  Gauge32
    MAX-ACCESS  read-only
    STATUS  current
    DESCRIPTION
       "The counter associated with the number of
       Unavailable Seconds in a particular 24 hour
       interval.

"
    ::= { pmInterval24hEntry 9 }

pmInterval24hTxES OBJECT-TYPE
    SYNTAX  Gauge32
    MAX-ACCESS  read-only
    STATUS  current
    DESCRIPTION
       "The counter associated with the number of
       Errored Seconds in a particular 24 hour interval.

"
     ::= { pmInterval24hEntry 10 }

pmInterval24hTxSES OBJECT-TYPE
    SYNTAX  Gauge32
    MAX-ACCESS  read-only
    STATUS  current
    DESCRIPTION
       "The counter associated with the number of
       Severely Errored Seconds in a particular 24 hour
       interval.

"
    ::= { pmInterval24hEntry 11 }

pmInterval24hTxBBE OBJECT-TYPE
    SYNTAX  Gauge32
    MAX-ACCESS  read-only
    STATUS  current
    DESCRIPTION
       "The counter associated with the number of
       Background Block Errors in a particular 24 hour
       interval.

"
    ::= { pmInterval24hEntry 12 }

pmInterval24hTxUAS OBJECT-TYPE
    SYNTAX  Gauge32
    MAX-ACCESS  read-only
    STATUS  current
    DESCRIPTION
       "The counter associated with the number of
       Unavailable Seconds in a particular 24 hour
       interval.

"
    ::= { pmInterval24hEntry 13 }

pmInterval24hName OBJECT-TYPE
    SYNTAX  MgmtNameString
    MAX-ACCESS  read-only
    STATUS  current
    DESCRIPTION
       "The name of the interface.

"
    ::= { pmInterval24hEntry 14 }

pmInterval24hRxPowerLevel OBJECT-TYPE
    SYNTAX  Integer32
    MAX-ACCESS  read-only
    STATUS  current
    DESCRIPTION
       "The received power level in units of 0.1 dBm
       sampled some time during a particular 24 hour
       interval.

"
    ::= { pmInterval24hEntry 15 }

pmInterval24hGbeMaxUtilization OBJECT-TYPE
    SYNTAX  Unsigned32
    MAX-ACCESS  read-only
    STATUS  current
    DESCRIPTION
       "The maximum bandwidth utilization of the
       GbE signal during a particular 24 hour interval.

"
    ::= { pmInterval24hEntry 16 }

pmInterval24hTxPowerLevel OBJECT-TYPE
    SYNTAX  Integer32
    MAX-ACCESS  read-only
    STATUS  current
    DESCRIPTION
       "The transmitted power level in units of 0.1 dBm
       sampled some time during a particular 24 hour
       interval.

"
    ::= { pmInterval24hEntry 17 }

pmInterval24hRxUndersizedFrames OBJECT-TYPE
     SYNTAX Counter64
     MAX-ACCESS read-only
     STATUS current
     DESCRIPTION
        "The amount of undersized frames
        during a particular 24 hour interval.

"
    ::= {pmInterval24hEntry 18 }

pmInterval24hRxOversizedFrames OBJECT-TYPE
     SYNTAX Counter64
     MAX-ACCESS read-only
     STATUS current
     DESCRIPTION
        "The amount of oversized frames
        during a particular 24 hour interval.

"
    ::= {pmInterval24hEntry 19 }

pmInterval24hRxFragments OBJECT-TYPE
     SYNTAX Counter64
     MAX-ACCESS read-only
     STATUS current
     DESCRIPTION
        "The amount of fragments
        during a particular 24 hour interval.

"
    ::= {pmInterval24hEntry 20 }

pmInterval24hRxFcsErrors OBJECT-TYPE
     SYNTAX Counter64
     MAX-ACCESS read-only
     STATUS current
     DESCRIPTION
        "The amount of frames with FCS or alignment errors
        during a particular 24 hour interval.

"
    ::= {pmInterval24hEntry 21 }

pmInterval24hRxInvalidCeVlanId OBJECT-TYPE
     SYNTAX Counter64
     MAX-ACCESS read-only
     STATUS current
     DESCRIPTION
        "The amount of frames with invalid CE-VLAN id
        during a particular 24 hour interval.

"
    ::= {pmInterval24hEntry 22 }

pmInterval24hTxOctets OBJECT-TYPE
     SYNTAX Counter64
     MAX-ACCESS read-only
     STATUS current
     DESCRIPTION
        "The amount of octets transmitted OK
        during a particular 24 hour interval.

"
    ::= {pmInterval24hEntry 23 }

pmInterval24hTxFrames OBJECT-TYPE
     SYNTAX Counter64
     MAX-ACCESS read-only
     STATUS current
     DESCRIPTION
        "The amount of frames transmitted OK
        during a particular 24 hour interval.

"
    ::= {pmInterval24hEntry 24 }

pmInterval24hTxUnicastFrames OBJECT-TYPE
     SYNTAX Counter64
     MAX-ACCESS read-only
     STATUS current
     DESCRIPTION
        "The amount of unicast frames transmitted OK
        during a particular 24 hour interval.

"
    ::= {pmInterval24hEntry 25 }

pmInterval24hTxMulticastFrames OBJECT-TYPE
     SYNTAX Counter64
     MAX-ACCESS read-only
     STATUS current
     DESCRIPTION
        "The amount of multicast frames transmitted OK
        during a particular 24 hour interval.

"
    ::= {pmInterval24hEntry 26 }

pmInterval24hTxBroadcastFrames OBJECT-TYPE
     SYNTAX Counter64
     MAX-ACCESS read-only
     STATUS current
     DESCRIPTION
        "The amount of multicast frames transmitted OK
        during a particular 24 hour interval.

"
    ::= {pmInterval24hEntry 27 }

pmInterval24hRxOctets OBJECT-TYPE
     SYNTAX Counter64
     MAX-ACCESS read-only
     STATUS current
     DESCRIPTION
        "The amount of octets received OK
        during a particular 24 hour interval.

"
    ::= {pmInterval24hEntry 28 }

pmInterval24hRxFrames OBJECT-TYPE
     SYNTAX Counter64
     MAX-ACCESS read-only
     STATUS current
     DESCRIPTION
        "The amount of frames received OK
        during a particular 24 hour interval.

"
    ::= {pmInterval24hEntry 29 }

pmInterval24hRxUnicastFrames OBJECT-TYPE
     SYNTAX Counter64
     MAX-ACCESS read-only
     STATUS current
     DESCRIPTION
        "The amount of unicast frames received OK
        during a particular 24 hour interval.

"
    ::= {pmInterval24hEntry 30 }

pmInterval24hRxMulticastFrames OBJECT-TYPE
     SYNTAX Counter64
     MAX-ACCESS read-only
     STATUS current
     DESCRIPTION
        "The amount of multicast frames received OK
        during a particular 24 hour interval.

"
    ::= {pmInterval24hEntry 31 }

pmInterval24hRxBroadcastFrames OBJECT-TYPE
     SYNTAX Counter64
     MAX-ACCESS read-only
     STATUS current
     DESCRIPTION
        "The amount of broadcast frames received OK
        during a particular 24 hour interval.

"
    ::= {pmInterval24hEntry 32 }

pmInterval24hIngressGreenFrameCount OBJECT-TYPE
    SYNTAX Counter64
    MAX-ACCESS read-only
    STATUS current
    DESCRIPTION
        "The amount of green frames sent by ingress UNI
        during a particular 24 hour interval.
"
    ::= { pmInterval24hEntry 33 }

pmInterval24hIngressYellowFrameCount OBJECT-TYPE
    SYNTAX Counter64
    MAX-ACCESS read-only
    STATUS current
    DESCRIPTION
        "The amount of yellow frames sent by ingress UNI
        during a particular 24 hour interval.
"
    ::= { pmInterval24hEntry 34 }

pmInterval24hIngressRedFrameCount OBJECT-TYPE
    SYNTAX Counter64
    MAX-ACCESS read-only
    STATUS current
    DESCRIPTION
        "The amount of red frames sent by ingress UNI
        during a particular 24 hour interval.
"
    ::= { pmInterval24hEntry 35 }

pmInterval24hIngressGreenOctetCount OBJECT-TYPE
    SYNTAX Counter64
    MAX-ACCESS read-only
    STATUS current
    DESCRIPTION
        "The amount of green octets sent by ingress UNI
        during a particular 24 hour interval.
"
    ::= { pmInterval24hEntry 36 }

pmInterval24hIngressYellowOctetCount OBJECT-TYPE
    SYNTAX Counter64
    MAX-ACCESS read-only
    STATUS current
    DESCRIPTION
        "The amount of yellow octets sent by ingress UNI
        during a particular 24 hour interval.
"
    ::= { pmInterval24hEntry 37 }

pmInterval24hIngressRedOctetCount OBJECT-TYPE
    SYNTAX Counter64
    MAX-ACCESS read-only
    STATUS current
    DESCRIPTION
        "The amount of red octets sent by ingress UNI
        during a particular 24 hour interval.
"
    ::= { pmInterval24hEntry 38 }

pmInterval24hEgressGreenFrameCount OBJECT-TYPE
    SYNTAX Counter64
    MAX-ACCESS read-only
    STATUS current
    DESCRIPTION
        "The amount of green frames received by egress UNI
        during a particular 24 hour interval.
"
    ::= { pmInterval24hEntry 39 }

pmInterval24hEgressGreenOctetCount OBJECT-TYPE
    SYNTAX Counter64
    MAX-ACCESS read-only
    STATUS current
    DESCRIPTION
        "The amount of green octets received by egress UNI
        during a particular 24 hour interval.
"
    ::= { pmInterval24hEntry 40 }

pmInterval24hGreenFrameDiscards OBJECT-TYPE
    SYNTAX Counter64
    MAX-ACCESS read-only
    STATUS current
    DESCRIPTION
        "The amount of green frames discarded due to congestion
        during a particular 24 hour interval.
"
    ::= { pmInterval24hEntry 41 }

pmInterval24hYellowFrameDiscards OBJECT-TYPE
    SYNTAX Counter64
    MAX-ACCESS read-only
    STATUS current
    DESCRIPTION
        "The amount of yellow frames discarded due to congestion
        during a particular 24 hour interval.
"
    ::= { pmInterval24hEntry 42 }

pmInterval24hGreenOctetDiscards OBJECT-TYPE
    SYNTAX Counter64
    MAX-ACCESS read-only
    STATUS current
    DESCRIPTION
        "The amount of green octets discarded due to congestion
        during a particular 24 hour interval.
"
    ::= { pmInterval24hEntry 43 }

pmInterval24hYellowOctetDiscards OBJECT-TYPE
    SYNTAX Counter64
    MAX-ACCESS read-only
    STATUS current
    DESCRIPTION
        "The amount of yellow octets discarded due to congestion
        during a particular 24 hour interval.
"
    ::= { pmInterval24hEntry 44 }

pmInterval24hTwoWayFrameDelay OBJECT-TYPE
    SYNTAX Gauge32
    MAX-ACCESS read-only
    STATUS current
    DESCRIPTION
        "The time required to transmit a service frame from
        source to destination during a particular 24 hour
        interval.
"
    ::= { pmInterval24hEntry 45 }

pmInterval24hTwoWayFrameDelayVariation OBJECT-TYPE
    SYNTAX Gauge32
    MAX-ACCESS read-only
    STATUS current
    DESCRIPTION
        "The difference in delay of two service frames
        during a particular 24 hour interval.
"
    ::= { pmInterval24hEntry 46 }

pmInterval24hFrameLossRatioNearEnd OBJECT-TYPE
    SYNTAX Gauge32
    MAX-ACCESS read-only
    STATUS current
    DESCRIPTION
        "The number of service frames not delivered divided
        by the total number of service frames at near end
        during a particular 24 hour interval.
"
    ::= { pmInterval24hEntry 47 }

pmInterval24hFrameLossRatioFarEnd OBJECT-TYPE
    SYNTAX Gauge32
    MAX-ACCESS read-only
    STATUS current
    DESCRIPTION
        "The number of service frames not delivered divided
        by the total number of service frames at far end
        during a particular 24 hour interval.
"
    ::= { pmInterval24hEntry 48 }

pmInterval24hUnavailabilityNearEnd OBJECT-TYPE
    SYNTAX Gauge32
    MAX-ACCESS read-only
    STATUS current
    DESCRIPTION
        "The @todo
        during a particular 24 hour interval.
"
    ::= { pmInterval24hEntry 49 }

pmInterval24hUnavailabilityFarEnd OBJECT-TYPE
    SYNTAX Gauge32
    MAX-ACCESS read-only
    STATUS current
    DESCRIPTION
        "The @todo
        during a particular 24 hour interval.
"
    ::= { pmInterval24hEntry 50 }

pmInterval24hOneWayFrameDelayVariation OBJECT-TYPE
    SYNTAX Gauge32
    MAX-ACCESS read-only
    STATUS current
    DESCRIPTION
        "The difference in delay of two service frames
        during a particular 24 hour interval.
"
    ::= { pmInterval24hEntry 51 }

pmInterval24hTxEthMaxUtilization OBJECT-TYPE
    SYNTAX  Unsigned32
    MAX-ACCESS  read-only
    STATUS  current
    DESCRIPTION
       "The maximum layer 2 bandwidth utilization of the
       transmitted ethernet signal during a particular 24
       hour interval.

"
    ::= { pmInterval24hEntry 52 }

pmInterval24hRxEthMaxUtilization OBJECT-TYPE
    SYNTAX  Unsigned32
    MAX-ACCESS  read-only
    STATUS  current
    DESCRIPTION
       "The maximum layer 2 bandwidth utilization of the
       received ethernet signal during a particular 24 hour
       interval.

"
    ::= { pmInterval24hEntry 53 }

pmInterval24hStartTime OBJECT-TYPE
    SYNTAX      DateAndTime
    MAX-ACCESS  read-only
    STATUS      current
    DESCRIPTION
        "The start time of the quarter where
         PM-reports are generated

"
    ::= { pmInterval24hEntry 54 }

pmInterval24hStopTime OBJECT-TYPE
    SYNTAX      DateAndTime
    MAX-ACCESS  read-only
    STATUS      current
    DESCRIPTION
        "The end time of the quarter where
         PM-reports are generated

"
    ::= { pmInterval24hEntry 55 }

-- ----------------------------------------------------
-- PM configuration and current meters
-- ----------------------------------------------------

pmIfTable OBJECT-TYPE
    SYNTAX  SEQUENCE OF PmIfEntry
    MAX-ACCESS  not-accessible
    STATUS  current
    DESCRIPTION
     "The pm interface table."
::= { pmIfList 1 }

pmIfEntry OBJECT-TYPE
    SYNTAX  PmIfEntry
    MAX-ACCESS  not-accessible
    STATUS  current
    DESCRIPTION
        "An entry in interface table.

"
    INDEX   { pmIfIndex }
::= { pmIfTable 1 }

PmIfEntry ::=
    SEQUENCE {
        pmIfIndex               Unsigned32,
        pmIfName                MgmtNameString,
        pmIfSubrack             SubrackNumber,
        pmIfSlot                SlotNumber,
        pmIfPort                PortNumber,
        pmIfPmReportMode        INTEGER,
        pmIfRxCurrentES         Gauge32,
        pmIfRxCurrentSES        Gauge32,
        pmIfRxCurrentBBE        Gauge32,
        pmIfRxCurrentUAS        Gauge32,
        pmIfTxCurrentES         Gauge32,
        pmIfTxCurrentSES        Gauge32,
        pmIfTxCurrentBBE        Gauge32,
        pmIfTxCurrentUAS        Gauge32,
        pmIfRx24hCurrentES      Gauge32,
        pmIfRx24hCurrentSES     Gauge32,
        pmIfRx24hCurrentBBE     Gauge32,
        pmIfRx24hCurrentUAS     Gauge32,
        pmIfTx24hCurrentES      Gauge32,
        pmIfTx24hCurrentSES     Gauge32,
        pmIfTx24hCurrentBBE     Gauge32,
        pmIfTx24hCurrentUAS     Gauge32,
        pmIfRxESThreshold       Unsigned32,
        pmIfRxSESThreshold      Unsigned32,
        pmIfRxBBEThreshold      Unsigned32,
        pmIfRxUASThreshold      Unsigned32,
        pmIfTxESThreshold       Unsigned32,
        pmIfTxSESThreshold      Unsigned32,
        pmIfTxBBEThreshold      Unsigned32,
        pmIfTxUASThreshold      Unsigned32,
        pmIfRx24hESThreshold    Unsigned32,
        pmIfRx24hSESThreshold   Unsigned32,
        pmIfRx24hBBEThreshold   Unsigned32,
        pmIfRx24hUASThreshold   Unsigned32,
        pmIfTx24hESThreshold    Unsigned32,
        pmIfTx24hSESThreshold   Unsigned32,
        pmIfTx24hBBEThreshold   Unsigned32,
        pmIfTx24hUASThreshold   Unsigned32,
        pmIfRxES                FaultStatus,
        pmIfRxSES               FaultStatus,
        pmIfRxBBE               FaultStatus,
        pmIfRxUAS               FaultStatus,
        pmIfTxES                FaultStatus,
        pmIfTxSES               FaultStatus,
        pmIfTxBBE               FaultStatus,
        pmIfTxUAS               FaultStatus,
        pmIfRx24hES             FaultStatus,
        pmIfRx24hSES            FaultStatus,
        pmIfRx24hBBE            FaultStatus,
        pmIfRx24hUAS            FaultStatus,
        pmIfTx24hES             FaultStatus,
        pmIfTx24hSES            FaultStatus,
        pmIfTx24hBBE            FaultStatus,
        pmIfTx24hUAS            FaultStatus,
        pmIfRxPort              PortNumber,
        pmIfReset15Min          INTEGER,
        pmIfReset24H            INTEGER,
        pmIfAdminStatus         BoardOrInterfaceAdminStatus,
        pmIfOperStatus          BoardOrInterfaceOperStatus,
        pmIfIsSuspect15Min      TruthValue,
        pmIfIsSuspect24H        TruthValue,
        pmIfInstallCommand      CommandString,
        pmIfRxPowerLevel        Integer32,
        pmIfInitialPowerLevel   Integer32,
        pmIfRxGbeMaxUtilization Gauge32,
        pmIfRx24hGbeMaxUtilization Gauge32,
        pmIfTxPowerLevel        Integer32,
        pmIfObjectProperty      ObjectProperty,
        pmIfDelay               Gauge32,
        pmIfRxBEREstimation     Unsigned32,
        pmIfIfNo				PortNumber,
        pmIfUpPortId 		    Integer32
        }

pmIfIndex OBJECT-TYPE
    SYNTAX      Unsigned32 (1..2147483647)
    MAX-ACCESS  read-only
    STATUS      current
    DESCRIPTION
        "An arbitrary index assigned to each if entry.

"
    ::= { pmIfEntry 1 }

pmIfName OBJECT-TYPE
    SYNTAX      MgmtNameString
    MAX-ACCESS  read-only
    STATUS      current
    DESCRIPTION
        "The management name of the interface, for
        example 'mrt:1:2:1-2'.

"
    ::= { pmIfEntry 2 }

pmIfSubrack OBJECT-TYPE
    SYNTAX      SubrackNumber
    MAX-ACCESS  read-create
    STATUS      current
    DESCRIPTION
        "The number of the subrack where the interface
        is located.

"
    ::= { pmIfEntry 3 }

pmIfSlot OBJECT-TYPE
    SYNTAX      SlotNumber
    MAX-ACCESS  read-create
    STATUS      current
    DESCRIPTION
        "The number of the slot where the interface is
        located.

"
    ::= { pmIfEntry 4 }

pmIfPort OBJECT-TYPE
    SYNTAX      PortNumber
    MAX-ACCESS  read-create
    STATUS      current
    DESCRIPTION
        "The number of the TX port for the interface.

"
    ::= { pmIfEntry 5 }

pmIfPmReportMode OBJECT-TYPE
    SYNTAX      INTEGER {
                    off (1),
                    on (2) }
    MAX-ACCESS  read-write
    STATUS      current
    DESCRIPTION
        "The mode PM reporting on the interface.

        off - PM reporting is inactive.

        on - PM reporting is activated.

"
    DEFVAL { on }
    ::= { pmIfEntry 6 }

pmIfRxCurrentES OBJECT-TYPE
    SYNTAX  Gauge32
    MAX-ACCESS  read-only
    STATUS  current
    DESCRIPTION
       "The counter associated with the number of
       Errored Seconds in the current 15 minute interval.

"
     ::= { pmIfEntry 7 }

pmIfRxCurrentSES OBJECT-TYPE
    SYNTAX  Gauge32
    MAX-ACCESS  read-only
    STATUS  current
    DESCRIPTION
       "The counter associated with the number of
       Severely Errored Seconds in the current 15 minute
       interval.

"
    ::= { pmIfEntry 8 }

pmIfRxCurrentBBE OBJECT-TYPE
    SYNTAX  Gauge32
    MAX-ACCESS  read-only
    STATUS  current
    DESCRIPTION
       "The counter associated with the number of
       Background Block Errors in the current 15 minute
       interval.

"
    ::= { pmIfEntry 9 }

pmIfRxCurrentUAS OBJECT-TYPE
    SYNTAX  Gauge32
    MAX-ACCESS  read-only
    STATUS  current
    DESCRIPTION
       "The counter associated with the number of
       Unavailable Seconds in the current 15 minute
       interval.

"
    ::= { pmIfEntry 10 }

pmIfTxCurrentES OBJECT-TYPE
    SYNTAX  Gauge32
    MAX-ACCESS  read-only
    STATUS  current
    DESCRIPTION
       "The counter associated with the number of
       Errored Seconds in the current 15 minute interval.

"
     ::= { pmIfEntry 11 }

pmIfTxCurrentSES OBJECT-TYPE
    SYNTAX  Gauge32
    MAX-ACCESS  read-only
    STATUS  current
    DESCRIPTION
       "The counter associated with the number of
       Severely Errored Seconds in the current 15 minute
       interval.

"
    ::= { pmIfEntry 12 }

pmIfTxCurrentBBE OBJECT-TYPE
    SYNTAX  Gauge32
    MAX-ACCESS  read-only
    STATUS  current
    DESCRIPTION
       "The counter associated with the number of
       Background Block Errors in in the current
       15 minute interval.

"
    ::= { pmIfEntry 13 }

pmIfTxCurrentUAS OBJECT-TYPE
    SYNTAX  Gauge32
    MAX-ACCESS  read-only
    STATUS  current
    DESCRIPTION
       "The counter associated with the number of
       Unavailable Seconds encountered in the current
       15 minute interval.

"
    ::= { pmIfEntry 14 }

pmIfRx24hCurrentES OBJECT-TYPE
    SYNTAX  Gauge32
    MAX-ACCESS  read-only
    STATUS  current
    DESCRIPTION
       "The counter associated with the number of
       Errored Seconds in the current 24 hour interval.

"
     ::= { pmIfEntry 15 }

pmIfRx24hCurrentSES OBJECT-TYPE
    SYNTAX  Gauge32
    MAX-ACCESS  read-only
    STATUS  current
    DESCRIPTION
       "The counter associated with the number of
       Severely Errored Seconds in the current 24 hour
       interval.

"
    ::= { pmIfEntry 16 }

pmIfRx24hCurrentBBE OBJECT-TYPE
    SYNTAX  Gauge32
    MAX-ACCESS  read-only
    STATUS  current
    DESCRIPTION
       "The counter associated with the number of
       Background Block Errors in the current 24 hour
       interval.

"
    ::= { pmIfEntry 17 }

pmIfRx24hCurrentUAS OBJECT-TYPE
    SYNTAX  Gauge32
    MAX-ACCESS  read-only
    STATUS  current
    DESCRIPTION
       "The counter associated with the number of
       Unavailable Seconds encountered in the current
       24 hour interval.

"
    ::= { pmIfEntry 18 }

pmIfTx24hCurrentES OBJECT-TYPE
    SYNTAX  Gauge32
    MAX-ACCESS  read-only
    STATUS  current
    DESCRIPTION
       "The counter associated with the number of
       Errored Seconds in the current 24 hour interval.

"
     ::= { pmIfEntry 19 }

pmIfTx24hCurrentSES OBJECT-TYPE
    SYNTAX  Gauge32
    MAX-ACCESS  read-only
    STATUS  current
    DESCRIPTION
       "The counter associated with the number of
       Severely Errored Seconds in the current 24 hour
       interval.

"
    ::= { pmIfEntry 20 }

pmIfTx24hCurrentBBE OBJECT-TYPE
    SYNTAX  Gauge32
    MAX-ACCESS  read-only
    STATUS  current
    DESCRIPTION
       "The counter associated with the number of
       Background Block Errors in the current 24 hour
       interval.

"
    ::= { pmIfEntry 21 }

pmIfTx24hCurrentUAS OBJECT-TYPE
    SYNTAX  Gauge32
    MAX-ACCESS  read-only
    STATUS  current
    DESCRIPTION
       "The counter associated with the number of
       Unavailable Seconds encountered in the current
       24 hour interval.

"
    ::= { pmIfEntry 22 }

pmIfRxESThreshold  OBJECT-TYPE
    SYNTAX      Unsigned32 (0..900)
    MAX-ACCESS  read-write
    STATUS      current
    DESCRIPTION
        "Sets the threshold in seconds for the
        errored seconds alarm.

"
    DEFVAL { 20 }
    ::= { pmIfEntry 23 }

pmIfRxSESThreshold OBJECT-TYPE
    SYNTAX      Unsigned32 (0..900)
    MAX-ACCESS  read-write
    STATUS      current
    DESCRIPTION
        "Sets the threshold in seconds for the
        severely errored seconds alarm.

"
    DEFVAL { 10 }
    ::= { pmIfEntry 24 }

pmIfRxBBEThreshold OBJECT-TYPE
    SYNTAX      Unsigned32 (0..4294967295)
    MAX-ACCESS  read-write
    STATUS      current
    DESCRIPTION
        "Sets the threshold in seconds for the
        background block errors alarms.

"
    DEFVAL { 100000 }
    ::= { pmIfEntry 25 }

pmIfRxUASThreshold OBJECT-TYPE
    SYNTAX      Unsigned32 (0..900)
    MAX-ACCESS  read-write
    STATUS      current
    DESCRIPTION
        "Sets the threshold in seconds for the
        unavailable seconds alarm.

"
    DEFVAL { 30 }
    ::= { pmIfEntry 26 }

pmIfTxESThreshold  OBJECT-TYPE
    SYNTAX      Unsigned32 (0..900)
    MAX-ACCESS  read-write
    STATUS      current
    DESCRIPTION
        "Sets the threshold in seconds for the
        errored seconds alarm.

"
    DEFVAL { 20 }
    ::= { pmIfEntry 27 }

pmIfTxSESThreshold OBJECT-TYPE
    SYNTAX      Unsigned32 (0..900)
    MAX-ACCESS  read-write
    STATUS      current
    DESCRIPTION
        "Sets the threshold in seconds for the
        severely errored seconds alarm.

"
    DEFVAL { 10 }
    ::= { pmIfEntry 28 }

pmIfTxBBEThreshold OBJECT-TYPE
    SYNTAX      Unsigned32 (0..4294967295)
    MAX-ACCESS  read-write
    STATUS      current
    DESCRIPTION
        "Sets the threshold in seconds for the
        background block errors alarms.

"
    DEFVAL { 100000 }
    ::= { pmIfEntry 29 }

pmIfTxUASThreshold OBJECT-TYPE
    SYNTAX      Unsigned32 (0..900)
    MAX-ACCESS  read-write
    STATUS      current
    DESCRIPTION
        "Sets the threshold in seconds for the
        unavailable seconds alarm.

"
    DEFVAL { 30 }
    ::= { pmIfEntry 30 }

pmIfRx24hESThreshold  OBJECT-TYPE
    SYNTAX      Unsigned32 (0..86400)
    MAX-ACCESS  read-write
    STATUS      current
    DESCRIPTION
        "Sets the threshold in seconds for the
        errored seconds alarm.

"
    DEFVAL { 200 }
    ::= { pmIfEntry 31 }

pmIfRx24hSESThreshold OBJECT-TYPE
    SYNTAX      Unsigned32 (0..86400)
    MAX-ACCESS  read-write
    STATUS      current
    DESCRIPTION
        "Sets the threshold in seconds for the
        severely errored seconds alarm.

"
    DEFVAL { 100 }
    ::= { pmIfEntry 32 }

pmIfRx24hBBEThreshold OBJECT-TYPE
    SYNTAX      Unsigned32 (0..4294967295)
    MAX-ACCESS  read-write
    STATUS      current
    DESCRIPTION
        "Sets the threshold in seconds for the
        background block errors alarms.

"
    DEFVAL { 1000000 }
    ::= { pmIfEntry 33 }

pmIfRx24hUASThreshold OBJECT-TYPE
    SYNTAX      Unsigned32 (0..86400)
    MAX-ACCESS  read-write
    STATUS      current
    DESCRIPTION
        "Sets the threshold in seconds for the
        unavailable seconds alarm.

"
    DEFVAL { 300 }
    ::= { pmIfEntry 34 }

pmIfTx24hESThreshold  OBJECT-TYPE
    SYNTAX      Unsigned32 (0..86400)
    MAX-ACCESS  read-write
    STATUS      current
    DESCRIPTION
        "Sets the threshold in seconds for the
        errored seconds alarm.

"
    DEFVAL { 200 }
    ::= { pmIfEntry 35 }

pmIfTx24hSESThreshold OBJECT-TYPE
    SYNTAX      Unsigned32 (0..86400)
    MAX-ACCESS  read-write
    STATUS      current
    DESCRIPTION
        "Sets the threshold in seconds for the
        severely errored seconds alarm.

"
    DEFVAL { 100 }
    ::= { pmIfEntry 36 }

pmIfTx24hBBEThreshold OBJECT-TYPE
    SYNTAX      Unsigned32 (0..4294967295)
    MAX-ACCESS  read-write
    STATUS      current
    DESCRIPTION
        "Sets the threshold in seconds for the
        background block errors alarms.

"
    DEFVAL { 1000000 }
    ::= { pmIfEntry 37 }

pmIfTx24hUASThreshold OBJECT-TYPE
    SYNTAX      Unsigned32 (0..86400)
    MAX-ACCESS  read-write
    STATUS      current
    DESCRIPTION
        "Sets the threshold in seconds for the
        unavailable seconds alarm.

"
    DEFVAL { 300 }
    ::= { pmIfEntry 38 }

pmIfRxES OBJECT-TYPE
    SYNTAX      FaultStatus
    MAX-ACCESS  read-only
    STATUS      current
    DESCRIPTION
        "Errored seconds (ES) Rx 15 min threshold
        exceeded.

        A: The number of errored seconds during a period
        exceeds the associated threshold.

        D: At the start of a new 15 minute period the
        associated ES counter is reset to zero, by
        definition. At the same time the fault status
        is cleared. The corresponding active alarm in
        the alarm list, if any, is not cleared for
        another 30 seconds to avoid unneccesary toggling
        in the alarm list and log.

"
    ::= { pmIfEntry 39 }

pmIfRxSES OBJECT-TYPE
    SYNTAX      FaultStatus
    MAX-ACCESS  read-only
    STATUS      current
    DESCRIPTION
        "Severely errored seconds (SES) Rx 15 min
        threshold exceeded.

        A: The number of severely errored seconds during
        a period exceeds the associated threshold.

        D: At the start of a new 15 minute period the
        associated SES counter is reset to zero, by
        definition. At the same time the fault status
        is cleared. The corresponding active alarm in
        the alarm list, if any, is not cleared for
        another 20 seconds to avoid unneccesary toggling
        in the alarm list and log.

"
    ::= { pmIfEntry 40 }

pmIfRxBBE OBJECT-TYPE
    SYNTAX      FaultStatus
    MAX-ACCESS  read-only
    STATUS      current
    DESCRIPTION
        "Background block errors (BBE) Rx 15 min
        threshold exceeded.

        A: The number of background block errors
        during a period exceeds the associated threshold.

        D: At the start of a new 15 minute period the
        associated BBE counter is reset to zero, by
        definition. At the same time the fault status
        is cleared.

"
    ::= { pmIfEntry 41 }

pmIfRxUAS OBJECT-TYPE
    SYNTAX      FaultStatus
    MAX-ACCESS  read-only
    STATUS      current
    DESCRIPTION
        "Unavailable seconds (UAS) Rx 15 min threshold
        exceeded.

        A: The number of unavailable seconds during a
        period exceeds the associated threshold.

        D: At the start of a new 15 minute period the
        associated UAS counter is reset to zero, by
        definition. At the same time the fault status
        is cleared. The corresponding active alarm in
        the alarm list, if any, is not cleared for
        another 45 seconds to avoid unneccesary toggling
        in the alarm list and log.

"
    ::= { pmIfEntry 42 }

pmIfTxES OBJECT-TYPE
    SYNTAX      FaultStatus
    MAX-ACCESS  read-only
    STATUS      current
    DESCRIPTION
        "Errored seconds (ES) Tx 15 min threshold
        exceeded.

        A: The number of errored seconds during a period
        exceeds the associated threshold.

        D: At the start of a new 15 minute period the
        associated ES counter is reset to zero, by
        definition. At the same time the fault status
        is cleared. The corresponding active alarm in
        the alarm list, if any, is not cleared for
        another 30 seconds to avoid unneccesary toggling
        in the alarm list and log.

"
    ::= { pmIfEntry 43 }

pmIfTxSES OBJECT-TYPE
    SYNTAX      FaultStatus
    MAX-ACCESS  read-only
    STATUS      current
    DESCRIPTION
        "Severely errored seconds (SES) Tx 15 min
        threshold exceeded.

        A: The number of severely errored seconds during
        a period exceeds the associated threshold.

        D: At the start of a new 15 minute period the
        associated SES counter is reset to zero, by
        definition. At the same time the fault status
        is cleared. The corresponding active alarm in
        the alarm list, if any, is not cleared for
        another 20 seconds to avoid unneccesary toggling
        in the alarm list and log.

"
    ::= { pmIfEntry 44 }

pmIfTxBBE OBJECT-TYPE
    SYNTAX      FaultStatus
    MAX-ACCESS  read-only
    STATUS      current
    DESCRIPTION
        "Background block errors (BBE) Tx 15 min
        threshold exceeded.

        A: The number of background block errors
        during a period exceeds the associated threshold.

        D: At the start of a new 15 minute period the
        associated BBE counter is reset to zero, by
        definition. At the same time the fault status
        is cleared.

"
    ::= { pmIfEntry 45 }

pmIfTxUAS OBJECT-TYPE
    SYNTAX      FaultStatus
    MAX-ACCESS  read-only
    STATUS      current
    DESCRIPTION
        "Unavailable seconds (UAS) Tx 15 min threshold
        exceeded.

        A: The number of unavailable seconds during a period
        exceeds the associated threshold.

        D: At the start of a new 15 minute period the
        associated UAS counter is reset to zero, by
        definition. At the same time the fault status
        is cleared. The corresponding active alarm in
        the alarm list, if any, is not cleared for
        another 45 seconds to avoid unneccesary toggling
        in the alarm list and log.

"
    ::= { pmIfEntry 46 }

pmIfRx24hES OBJECT-TYPE
    SYNTAX      FaultStatus
    MAX-ACCESS  read-only
    STATUS      current
    DESCRIPTION
        "Errored seconds (ES) Rx 24 hour threshold
        exceeded.

        A: The number of errored seconds during a period
        exceeds the associated threshold.

        D: At the start of a new 24 hour period the
        associated ES counter is reset to zero, by
        definition. At the same time the fault status
        is cleared. The corresponding active alarm in
        the alarm list, if any, is not cleared for
        another 300 seconds to avoid unneccesary toggling
        in the alarm list and log.

"
    ::= { pmIfEntry 47 }

pmIfRx24hSES OBJECT-TYPE
    SYNTAX      FaultStatus
    MAX-ACCESS  read-only
    STATUS      current
    DESCRIPTION
        "Severely errored seconds (SES) Rx 24 hour
        threshold exceeded.

        A: The number of severely errored seconds during
        a period exceeds the associated threshold.

        D: At the start of a new 24 hour period the
        associated SES counter is reset to zero, by
        definition. At the same time the fault status
        is cleared. The corresponding active alarm in
        the alarm list, if any, is not cleared for
        another 150 seconds to avoid unneccesary toggling
        in the alarm list and log.


"
    ::= { pmIfEntry 48 }

pmIfRx24hBBE OBJECT-TYPE
    SYNTAX      FaultStatus
    MAX-ACCESS  read-only
    STATUS      current
    DESCRIPTION
        "Background block errors (BBE) Rx 24 hour
        threshold exceeded.

        A: The number of background block errors
        during a period exceeds the associated threshold.

        D: At the start of a new 24 hour period the
        associated BBE counter is reset to zero, by
        definition. At the same time the fault status
        is cleared.

"
    ::= { pmIfEntry 49 }

pmIfRx24hUAS OBJECT-TYPE
    SYNTAX      FaultStatus
    MAX-ACCESS  read-only
    STATUS      current
    DESCRIPTION
        "Unavailable seconds (UAS) Rx 24 hour threshold
        exceeded.

        A: The number of unavailable seconds during a period
        exceeds the associated threshold.

        D: At the start of a new 24 hour period the
        associated UAS counter is reset to zero, by
        definition. At the same time the fault status
        is cleared. The corresponding active alarm in
        the alarm list, if any, is not cleared for
        another 400 seconds to avoid unneccesary toggling
        in the alarm list and log.

"
    ::= { pmIfEntry 50 }

pmIfTx24hES OBJECT-TYPE
    SYNTAX      FaultStatus
    MAX-ACCESS  read-only
    STATUS      current
    DESCRIPTION
        "Errored seconds Tx (ES) 24 hour threshold
        exceeded.

        A: The number of errored seconds during a period
        exceeds the associated threshold.

        D: At the start of a new 24 hour period the
        associated ES counter is reset to zero, by
        definition. At the same time the fault status
        is cleared. The corresponding active alarm in
        the alarm list, if any, is not cleared for
        another 300 seconds to avoid unneccesary toggling
        in the alarm list and log.

"
    ::= { pmIfEntry 51 }

pmIfTx24hSES OBJECT-TYPE
    SYNTAX      FaultStatus
    MAX-ACCESS  read-only
    STATUS      current
    DESCRIPTION
        "Severely errored seconds (SES) Tx 24 hour
        threshold exceeded.

        A: The number of severely errored seconds during
        a period exceeds the associated threshold.

        D: At the start of a new 24 hour period the
        associated SES counter is reset to zero, by
        definition. At the same time the fault status
        is cleared. The corresponding active alarm in
        the alarm list, if any, is not cleared for
        another 150 seconds to avoid unneccesary toggling
        in the alarm list and log.

"
    ::= { pmIfEntry 52 }

pmIfTx24hBBE OBJECT-TYPE
    SYNTAX      FaultStatus
    MAX-ACCESS  read-only
    STATUS      current
    DESCRIPTION
        "Background block errors (BBE) Tx 24 hour
        threshold exceeded.

        A: The number of background block errors
        during a period exceeds the associated threshold.

        D: At the start of a new 24 hour period the
        associated BBE counter is reset to zero, by
        definition. At the same time the fault status
        is cleared.

"
    ::= { pmIfEntry 53 }

pmIfTx24hUAS OBJECT-TYPE
    SYNTAX      FaultStatus
    MAX-ACCESS  read-only
    STATUS      current
    DESCRIPTION
        "Unavailable seconds (UAS) Tx 24 hour threshold
        exceeded.

        A: The number of unavailable seconds during a
        period exceeds the associated threshold.

        D: At the start of a new 24 hour period the
        associated UAS counter is reset to zero, by
        definition. At the same time the fault status
        is cleared. The corresponding active alarm in
        the alarm list, if any, is not cleared for
        another 400 seconds to avoid unneccesary toggling
        in the alarm list and log.

"
    ::= { pmIfEntry 54 }

pmIfRxPort OBJECT-TYPE
    SYNTAX      PortNumber
    MAX-ACCESS  read-create
    STATUS      current
    DESCRIPTION
        "The number of the RX port for the interface.

"
    ::= { pmIfEntry 55 }

pmIfReset15Min OBJECT-TYPE
    SYNTAX      INTEGER {
                    normal (1),
                    reset (2) }
    MAX-ACCESS  read-write
    STATUS      current
    DESCRIPTION
        "Reset the 15 minute PM counters for the
        interface.

        After a successful reset the default value
        (normal) is restored in this action attribute.

        Usage: set reset15m reset

"
    DEFVAL { normal }
    ::= { pmIfEntry 56 }

pmIfReset24H OBJECT-TYPE
    SYNTAX      INTEGER {
                    normal (1),
                    reset (2) }
    MAX-ACCESS  read-write
    STATUS      current
    DESCRIPTION
        "Reset the 24 hour PM counters for the interface.

        After a successful reset the default value
        (normal) is restored in this action attribute.

        Usage: set reset24h reset

"
    DEFVAL { normal }
    ::= {    pmIfEntry 57 }

pmIfAdminStatus OBJECT-TYPE
    SYNTAX  BoardOrInterfaceAdminStatus
    MAX-ACCESS read-write
    STATUS  current
    DESCRIPTION
         "Administrative state for the PM object.

         down - Alarms are not sent.

         up - Alarms are sent

         service - Alarms are not sent

"
     DEFVAL { up }
     ::= { pmIfEntry 58 }

pmIfOperStatus OBJECT-TYPE
    SYNTAX  BoardOrInterfaceOperStatus
    MAX-ACCESS read-only
    STATUS  current
    DESCRIPTION
         "The operational state for the PM object.

         notPresent - The physical resource is not available.

         down - The object is disabled.

         up - The object is enabled.

"
     DEFVAL { notPresent }
     ::= { pmIfEntry 59 }

pmIfIsSuspect15Min OBJECT-TYPE
    SYNTAX  TruthValue
    MAX-ACCESS  read-only
    STATUS  current
    DESCRIPTION
       "This variable indicates if the data for this
        interface is suspect. The current interval may
        for example contain measurements for a part of
        the interval.

"
    ::= { pmIfEntry 60 }

pmIfIsSuspect24H OBJECT-TYPE
    SYNTAX  TruthValue
    MAX-ACCESS  read-only
    STATUS  current
    DESCRIPTION
       "This variable indicates if the data for this
        interface is suspect. The current interval may
        for example contain measurements for a part of
        the interval.

"
    ::= { pmIfEntry 61 }


pmIfInstallCommand OBJECT-TYPE
    SYNTAX      CommandString
    MAX-ACCESS  read-only
    STATUS      current
    DESCRIPTION
        "Generic command to perform installation tasks.

        Tasks:

           rxPower - measure the received power


"
    ::= { pmIfEntry 62 }

pmIfRxPowerLevel OBJECT-TYPE
    SYNTAX      Integer32
    MAX-ACCESS  read-only
    STATUS      current
    DESCRIPTION
        "The received power level in units of 0.1 dBm

"
    ::= { pmIfEntry 63 }

pmIfInitialPowerLevel OBJECT-TYPE
    SYNTAX      Integer32 (-10000..10000)
    MAX-ACCESS  read-create
    STATUS      current
    DESCRIPTION
        "The received power level in units of 0.1 dBm
         measured at installation of the link.

"
        DEFVAL { -10000 }
    ::= { pmIfEntry 64 }

pmIfRxGbeMaxUtilization OBJECT-TYPE
    SYNTAX  Gauge32
    MAX-ACCESS  read-only
    STATUS  current
    DESCRIPTION
       "The maximum bandwidth utilization of the
        ethernet signal during the current 15 min
        interval.

"
    ::= { pmIfEntry 65 }

pmIfRx24hGbeMaxUtilization OBJECT-TYPE
    SYNTAX  Gauge32
    MAX-ACCESS  read-only
    STATUS  current
    DESCRIPTION
       "The maximum bandwidth utilization of the
        ethernet signal during the current 24 h
        interval.

"
    ::= { pmIfEntry 66 }

pmIfTxPowerLevel OBJECT-TYPE
    SYNTAX      Integer32
    MAX-ACCESS  read-only
    STATUS      current
    DESCRIPTION
        "The transmitted power level in units of 0.1 dBm

"
    ::= { pmIfEntry 67 }

pmIfObjectProperty  OBJECT-TYPE
    SYNTAX      ObjectProperty
    MAX-ACCESS  read-only
    STATUS      current
    DESCRIPTION
        "Property mask.

"
    ::= { pmIfEntry 68 }

pmIfDelay OBJECT-TYPE
    SYNTAX  Gauge32
    MAX-ACCESS  read-only
    STATUS  current
    DESCRIPTION
       "The delay of the signal.

"
    ::= { pmIfEntry 69 }

pmIfRxBEREstimation OBJECT-TYPE
    SYNTAX      Unsigned32
    MAX-ACCESS  read-only
    STATUS      current
    DESCRIPTION
        "The estimated Bit Error Rate after FEC.

"
    ::= { pmIfEntry 70 }

pmIfIfNo OBJECT-TYPE
    SYNTAX      PortNumber
    MAX-ACCESS  read-create
    STATUS      current
    DESCRIPTION
        "The interface number of the port.

"
    ::= { pmIfEntry 71 }


pmIfUpPortId OBJECT-TYPE
    SYNTAX      Integer32   (-1..2147483647)
    MAX-ACCESS  read-create
    STATUS      current
    DESCRIPTION
        "Internal port reference for traffic unit.
"
    DEFVAL { -1 }
    ::= { pmIfEntry 72 }

-- ----------------------------------------------------
-- PM configuration and current meters
-- ----------------------------------------------------

pmMpoLanesTable OBJECT-TYPE
    SYNTAX  SEQUENCE OF PmMpoLanesEntry
    MAX-ACCESS  not-accessible
    STATUS  current
    DESCRIPTION
     "The pm interface table."
::= { pmMpoLanesList 1 }

pmMpoLanesEntry OBJECT-TYPE
    SYNTAX  PmMpoLanesEntry
    MAX-ACCESS  not-accessible
    STATUS  current
    DESCRIPTION
        "An entry in interface table.

"
    INDEX   { pmMpoLanesIndex }
::= { pmMpoLanesTable 1 }

PmMpoLanesEntry ::=
    SEQUENCE {
        pmMpoLanesIndex               Unsigned32,
        pmMpoLanesName                MgmtNameString,
        pmMpoLanesSubrack             SubrackNumber,
        pmMpoLanesSlot                SlotNumber,
        pmMpoLanesLaneId              Unsigned32,
        pmMpoLanesAdminStatus         BoardOrInterfaceAdminStatus,
        pmMpoLanesOperStatus          BoardOrInterfaceOperStatus,
        pmMpoLanesIsSuspect15Min      TruthValue,
        pmMpoLanesIsSuspect24H        TruthValue,
        pmMpoLanesPmReportMode        OnOff,
        pmMpoLanesRxCurrentES         Gauge32,
        pmMpoLanesRxCurrentSES        Gauge32,
        pmMpoLanesRxCurrentBBE        Gauge32,
        pmMpoLanesRxCurrentUAS        Gauge32,
        pmMpoLanesTxCurrentES         Gauge32,
        pmMpoLanesTxCurrentSES        Gauge32,
        pmMpoLanesTxCurrentBBE        Gauge32,
        pmMpoLanesTxCurrentUAS        Gauge32,
        pmMpoLanesRx24hCurrentES      Gauge32,
        pmMpoLanesRx24hCurrentSES     Gauge32,
        pmMpoLanesRx24hCurrentBBE     Gauge32,
        pmMpoLanesRx24hCurrentUAS     Gauge32,
        pmMpoLanesTx24hCurrentES      Gauge32,
        pmMpoLanesTx24hCurrentSES     Gauge32,
        pmMpoLanesTx24hCurrentBBE     Gauge32,
        pmMpoLanesTx24hCurrentUAS     Gauge32,
        pmMpoLanesRxESThreshold       Unsigned32,
        pmMpoLanesRxSESThreshold      Unsigned32,
        pmMpoLanesRxBBEThreshold      Unsigned32,
        pmMpoLanesRxUASThreshold      Unsigned32,
        pmMpoLanesTxESThreshold       Unsigned32,
        pmMpoLanesTxSESThreshold      Unsigned32,
        pmMpoLanesTxBBEThreshold      Unsigned32,
        pmMpoLanesTxUASThreshold      Unsigned32,
        pmMpoLanesRx24hESThreshold    Unsigned32,
        pmMpoLanesRx24hSESThreshold   Unsigned32,
        pmMpoLanesRx24hBBEThreshold   Unsigned32,
        pmMpoLanesRx24hUASThreshold   Unsigned32,
        pmMpoLanesTx24hESThreshold    Unsigned32,
        pmMpoLanesTx24hSESThreshold   Unsigned32,
        pmMpoLanesTx24hBBEThreshold   Unsigned32,
        pmMpoLanesTx24hUASThreshold   Unsigned32,
        pmMpoLanesRxES                FaultStatus,
        pmMpoLanesRxSES               FaultStatus,
        pmMpoLanesRxBBE               FaultStatus,
        pmMpoLanesRxUAS               FaultStatus,
        pmMpoLanesTxES                FaultStatus,
        pmMpoLanesTxSES               FaultStatus,
        pmMpoLanesTxBBE               FaultStatus,
        pmMpoLanesTxUAS               FaultStatus,
        pmMpoLanesRx24hES             FaultStatus,
        pmMpoLanesRx24hSES            FaultStatus,
        pmMpoLanesRx24hBBE            FaultStatus,
        pmMpoLanesRx24hUAS            FaultStatus,
        pmMpoLanesTx24hES             FaultStatus,
        pmMpoLanesTx24hSES            FaultStatus,
        pmMpoLanesTx24hBBE            FaultStatus,
        pmMpoLanesTx24hUAS            FaultStatus,
        pmMpoLanesReset15Min          INTEGER,
        pmMpoLanesReset24H            INTEGER,
        pmMpoLanesRxPowerLevel        Integer32,
        pmMpoLanesTxPowerLevel        Integer32,
        pmMpoLanesObjectProperty      ObjectProperty,
        pmMpoLanesIfNo				  PortNumber,
        pmMpoLanesUpPortId 		      Integer32
        }

pmMpoLanesIndex OBJECT-TYPE
    SYNTAX      Unsigned32 (1..2147483647)
    MAX-ACCESS  read-only
    STATUS      current
    DESCRIPTION
        "An arbitrary index assigned to each if entry.

"
    ::= { pmMpoLanesEntry 1 }

pmMpoLanesName OBJECT-TYPE
    SYNTAX      MgmtNameString
    MAX-ACCESS  read-only
    STATUS      current
    DESCRIPTION
        "The management name of the interface, for
        example 'mrt:1:2:1-2'.

"
    ::= { pmMpoLanesEntry 2 }

pmMpoLanesSubrack OBJECT-TYPE
    SYNTAX      SubrackNumber
    MAX-ACCESS  read-create
    STATUS      current
    DESCRIPTION
        "The number of the subrack where the interface
        is located.

"
    ::= { pmMpoLanesEntry 3 }

pmMpoLanesSlot OBJECT-TYPE
    SYNTAX      SlotNumber
    MAX-ACCESS  read-create
    STATUS      current
    DESCRIPTION
        "The number of the slot where the interface is
        located.

"
    ::= { pmMpoLanesEntry 4 }

pmMpoLanesLaneId OBJECT-TYPE
    SYNTAX      Unsigned32 (1..16)
    MAX-ACCESS  read-create
    STATUS      current
    DESCRIPTION
        "The id of the lane within.

"
    ::= { pmMpoLanesEntry 5 }

pmMpoLanesAdminStatus OBJECT-TYPE
    SYNTAX  BoardOrInterfaceAdminStatus
    MAX-ACCESS read-write
    STATUS  current
    DESCRIPTION
         "Administrative state for the PM object.

         down - Alarms are not sent.

         up - Alarms are sent

         service - Alarms are not sent

"
     DEFVAL { up }
     ::= { pmMpoLanesEntry 6 }

pmMpoLanesOperStatus OBJECT-TYPE
    SYNTAX  BoardOrInterfaceOperStatus
    MAX-ACCESS read-only
    STATUS  current
    DESCRIPTION
         "The operational state for the PM object.

         notPresent - The physical resource is not available.

         down - The object is disabled.

         up - The object is enabled.

"
     DEFVAL { notPresent }
     ::= { pmMpoLanesEntry 7 }

pmMpoLanesPmReportMode OBJECT-TYPE
    SYNTAX      OnOff
    MAX-ACCESS  read-write
    STATUS      current
    DESCRIPTION
        "The mode PM reporting on the interface.

        off - PM reporting is inactive.

        on - PM reporting is activated.

"
    DEFVAL { on }
    ::= { pmMpoLanesEntry 8 }

pmMpoLanesIsSuspect15Min OBJECT-TYPE
    SYNTAX  TruthValue
    MAX-ACCESS  read-only
    STATUS  current
    DESCRIPTION
       "This variable indicates if the data for this
        interface is suspect. The current interval may
        for example contain measurements for a part of
        the interval.

"
    ::= { pmMpoLanesEntry 9 }

pmMpoLanesIsSuspect24H OBJECT-TYPE
    SYNTAX  TruthValue
    MAX-ACCESS  read-only
    STATUS  current
    DESCRIPTION
       "This variable indicates if the data for this
        interface is suspect. The current interval may
        for example contain measurements for a part of
        the interval.

"
    ::= { pmMpoLanesEntry 10 }

pmMpoLanesRxCurrentES OBJECT-TYPE
    SYNTAX  Gauge32
    MAX-ACCESS  read-only
    STATUS  current
    DESCRIPTION
       "The counter associated with the number of
       Errored Seconds in the current 15 minute interval.

"
     ::= { pmMpoLanesEntry 11 }

pmMpoLanesRxCurrentSES OBJECT-TYPE
    SYNTAX  Gauge32
    MAX-ACCESS  read-only
    STATUS  current
    DESCRIPTION
       "The counter associated with the number of
       Severely Errored Seconds in the current 15 minute
       interval.

"
    ::= { pmMpoLanesEntry 12 }

pmMpoLanesRxCurrentBBE OBJECT-TYPE
    SYNTAX  Gauge32
    MAX-ACCESS  read-only
    STATUS  current
    DESCRIPTION
       "The counter associated with the number of
       Background Block Errors in the current 15 minute
       interval.

"
    ::= { pmMpoLanesEntry 13 }

pmMpoLanesRxCurrentUAS OBJECT-TYPE
    SYNTAX  Gauge32
    MAX-ACCESS  read-only
    STATUS  current
    DESCRIPTION
       "The counter associated with the number of
       Unavailable Seconds in the current 15 minute
       interval.

"
    ::= { pmMpoLanesEntry 14 }

pmMpoLanesTxCurrentES OBJECT-TYPE
    SYNTAX  Gauge32
    MAX-ACCESS  read-only
    STATUS  current
    DESCRIPTION
       "The counter associated with the number of
       Errored Seconds in the current 15 minute interval.

"
     ::= { pmMpoLanesEntry 15 }

pmMpoLanesTxCurrentSES OBJECT-TYPE
    SYNTAX  Gauge32
    MAX-ACCESS  read-only
    STATUS  current
    DESCRIPTION
       "The counter associated with the number of
       Severely Errored Seconds in the current 15 minute
       interval.

"
    ::= { pmMpoLanesEntry 16 }

pmMpoLanesTxCurrentBBE OBJECT-TYPE
    SYNTAX  Gauge32
    MAX-ACCESS  read-only
    STATUS  current
    DESCRIPTION
       "The counter associated with the number of
       Background Block Errors in in the current
       15 minute interval.

"
    ::= { pmMpoLanesEntry 17 }

pmMpoLanesTxCurrentUAS OBJECT-TYPE
    SYNTAX  Gauge32
    MAX-ACCESS  read-only
    STATUS  current
    DESCRIPTION
       "The counter associated with the number of
       Unavailable Seconds encountered in the current
       15 minute interval.

"
    ::= { pmMpoLanesEntry 18 }

pmMpoLanesRx24hCurrentES OBJECT-TYPE
    SYNTAX  Gauge32
    MAX-ACCESS  read-only
    STATUS  current
    DESCRIPTION
       "The counter associated with the number of
       Errored Seconds in the current 24 hour interval.

"
     ::= { pmMpoLanesEntry 19 }

pmMpoLanesRx24hCurrentSES OBJECT-TYPE
    SYNTAX  Gauge32
    MAX-ACCESS  read-only
    STATUS  current
    DESCRIPTION
       "The counter associated with the number of
       Severely Errored Seconds in the current 24 hour
       interval.

"
    ::= { pmMpoLanesEntry 20 }

pmMpoLanesRx24hCurrentBBE OBJECT-TYPE
    SYNTAX  Gauge32
    MAX-ACCESS  read-only
    STATUS  current
    DESCRIPTION
       "The counter associated with the number of
       Background Block Errors in the current 24 hour
       interval.

"
    ::= { pmMpoLanesEntry 21 }

pmMpoLanesRx24hCurrentUAS OBJECT-TYPE
    SYNTAX  Gauge32
    MAX-ACCESS  read-only
    STATUS  current
    DESCRIPTION
       "The counter associated with the number of
       Unavailable Seconds encountered in the current
       24 hour interval.

"
    ::= { pmMpoLanesEntry 22 }

pmMpoLanesTx24hCurrentES OBJECT-TYPE
    SYNTAX  Gauge32
    MAX-ACCESS  read-only
    STATUS  current
    DESCRIPTION
       "The counter associated with the number of
       Errored Seconds in the current 24 hour interval.

"
     ::= { pmMpoLanesEntry 23 }

pmMpoLanesTx24hCurrentSES OBJECT-TYPE
    SYNTAX  Gauge32
    MAX-ACCESS  read-only
    STATUS  current
    DESCRIPTION
       "The counter associated with the number of
       Severely Errored Seconds in the current 24 hour
       interval.

"
    ::= { pmMpoLanesEntry 24 }

pmMpoLanesTx24hCurrentBBE OBJECT-TYPE
    SYNTAX  Gauge32
    MAX-ACCESS  read-only
    STATUS  current
    DESCRIPTION
       "The counter associated with the number of
       Background Block Errors in the current 24 hour
       interval.

"
    ::= { pmMpoLanesEntry 25 }

pmMpoLanesTx24hCurrentUAS OBJECT-TYPE
    SYNTAX  Gauge32
    MAX-ACCESS  read-only
    STATUS  current
    DESCRIPTION
       "The counter associated with the number of
       Unavailable Seconds encountered in the current
       24 hour interval.

"
    ::= { pmMpoLanesEntry 26 }

pmMpoLanesRxESThreshold  OBJECT-TYPE
    SYNTAX      Unsigned32 (0..900)
    MAX-ACCESS  read-write
    STATUS      current
    DESCRIPTION
        "Sets the threshold in seconds for the
        errored seconds alarm.

"
    DEFVAL { 20 }
    ::= { pmMpoLanesEntry 27 }

pmMpoLanesRxSESThreshold OBJECT-TYPE
    SYNTAX      Unsigned32 (0..900)
    MAX-ACCESS  read-write
    STATUS      current
    DESCRIPTION
        "Sets the threshold in seconds for the
        severely errored seconds alarm.

"
    DEFVAL { 10 }
    ::= { pmMpoLanesEntry 28 }

pmMpoLanesRxBBEThreshold OBJECT-TYPE
    SYNTAX      Unsigned32 (0..4294967295)
    MAX-ACCESS  read-write
    STATUS      current
    DESCRIPTION
        "Sets the threshold in seconds for the
        background block errors alarms.

"
    DEFVAL { 100000 }
    ::= { pmMpoLanesEntry 29 }

pmMpoLanesRxUASThreshold OBJECT-TYPE
    SYNTAX      Unsigned32 (0..900)
    MAX-ACCESS  read-write
    STATUS      current
    DESCRIPTION
        "Sets the threshold in seconds for the
        unavailable seconds alarm.

"
    DEFVAL { 30 }
    ::= { pmMpoLanesEntry 30 }

pmMpoLanesTxESThreshold  OBJECT-TYPE
    SYNTAX      Unsigned32 (0..900)
    MAX-ACCESS  read-write
    STATUS      current
    DESCRIPTION
        "Sets the threshold in seconds for the
        errored seconds alarm.

"
    DEFVAL { 20 }
    ::= { pmMpoLanesEntry 31 }

pmMpoLanesTxSESThreshold OBJECT-TYPE
    SYNTAX      Unsigned32 (0..900)
    MAX-ACCESS  read-write
    STATUS      current
    DESCRIPTION
        "Sets the threshold in seconds for the
        severely errored seconds alarm.

"
    DEFVAL { 10 }
    ::= { pmMpoLanesEntry 32 }

pmMpoLanesTxBBEThreshold OBJECT-TYPE
    SYNTAX      Unsigned32 (0..4294967295)
    MAX-ACCESS  read-write
    STATUS      current
    DESCRIPTION
        "Sets the threshold in seconds for the
        background block errors alarms.

"
    DEFVAL { 100000 }
    ::= { pmMpoLanesEntry 33 }

pmMpoLanesTxUASThreshold OBJECT-TYPE
    SYNTAX      Unsigned32 (0..900)
    MAX-ACCESS  read-write
    STATUS      current
    DESCRIPTION
        "Sets the threshold in seconds for the
        unavailable seconds alarm.

"
    DEFVAL { 30 }
    ::= { pmMpoLanesEntry 34 }

pmMpoLanesRx24hESThreshold  OBJECT-TYPE
    SYNTAX      Unsigned32 (0..86400)
    MAX-ACCESS  read-write
    STATUS      current
    DESCRIPTION
        "Sets the threshold in seconds for the
        errored seconds alarm.

"
    DEFVAL { 200 }
    ::= { pmMpoLanesEntry 35 }

pmMpoLanesRx24hSESThreshold OBJECT-TYPE
    SYNTAX      Unsigned32 (0..86400)
    MAX-ACCESS  read-write
    STATUS      current
    DESCRIPTION
        "Sets the threshold in seconds for the
        severely errored seconds alarm.

"
    DEFVAL { 100 }
    ::= { pmMpoLanesEntry 36 }

pmMpoLanesRx24hBBEThreshold OBJECT-TYPE
    SYNTAX      Unsigned32 (0..4294967295)
    MAX-ACCESS  read-write
    STATUS      current
    DESCRIPTION
        "Sets the threshold in seconds for the
        background block errors alarms.

"
    DEFVAL { 1000000 }
    ::= { pmMpoLanesEntry 37 }

pmMpoLanesRx24hUASThreshold OBJECT-TYPE
    SYNTAX      Unsigned32 (0..86400)
    MAX-ACCESS  read-write
    STATUS      current
    DESCRIPTION
        "Sets the threshold in seconds for the
        unavailable seconds alarm.

"
    DEFVAL { 300 }
    ::= { pmMpoLanesEntry 38 }

pmMpoLanesTx24hESThreshold  OBJECT-TYPE
    SYNTAX      Unsigned32 (0..86400)
    MAX-ACCESS  read-write
    STATUS      current
    DESCRIPTION
        "Sets the threshold in seconds for the
        errored seconds alarm.

"
    DEFVAL { 200 }
    ::= { pmMpoLanesEntry 39 }

pmMpoLanesTx24hSESThreshold OBJECT-TYPE
    SYNTAX      Unsigned32 (0..86400)
    MAX-ACCESS  read-write
    STATUS      current
    DESCRIPTION
        "Sets the threshold in seconds for the
        severely errored seconds alarm.

"
    DEFVAL { 100 }
    ::= { pmMpoLanesEntry 40 }

pmMpoLanesTx24hBBEThreshold OBJECT-TYPE
    SYNTAX      Unsigned32 (0..4294967295)
    MAX-ACCESS  read-write
    STATUS      current
    DESCRIPTION
        "Sets the threshold in seconds for the
        background block errors alarms.

"
    DEFVAL { 1000000 }
    ::= { pmMpoLanesEntry 41 }

pmMpoLanesTx24hUASThreshold OBJECT-TYPE
    SYNTAX      Unsigned32 (0..86400)
    MAX-ACCESS  read-write
    STATUS      current
    DESCRIPTION
        "Sets the threshold in seconds for the
        unavailable seconds alarm.

"
    DEFVAL { 300 }
    ::= { pmMpoLanesEntry 42 }

pmMpoLanesRxES OBJECT-TYPE
    SYNTAX      FaultStatus
    MAX-ACCESS  read-only
    STATUS      current
    DESCRIPTION
        "Errored seconds (ES) Rx 15 min threshold
        exceeded.

        A: The number of errored seconds during a period
        exceeds the associated threshold.

        D: At the start of a new 15 minute period the
        associated ES counter is reset to zero, by
        definition. At the same time the fault status
        is cleared. The corresponding active alarm in
        the alarm list, if any, is not cleared for
        another 30 seconds to avoid unneccesary toggling
        in the alarm list and log.

"
    ::= { pmMpoLanesEntry 43 }

pmMpoLanesRxSES OBJECT-TYPE
    SYNTAX      FaultStatus
    MAX-ACCESS  read-only
    STATUS      current
    DESCRIPTION
        "Severely errored seconds (SES) Rx 15 min
        threshold exceeded.

        A: The number of severely errored seconds during
        a period exceeds the associated threshold.

        D: At the start of a new 15 minute period the
        associated SES counter is reset to zero, by
        definition. At the same time the fault status
        is cleared. The corresponding active alarm in
        the alarm list, if any, is not cleared for
        another 20 seconds to avoid unneccesary toggling
        in the alarm list and log.

"
    ::= { pmMpoLanesEntry 44 }

pmMpoLanesRxBBE OBJECT-TYPE
    SYNTAX      FaultStatus
    MAX-ACCESS  read-only
    STATUS      current
    DESCRIPTION
        "Background block errors (BBE) Rx 15 min
        threshold exceeded.

        A: The number of background block errors
        during a period exceeds the associated threshold.

        D: At the start of a new 15 minute period the
        associated BBE counter is reset to zero, by
        definition. At the same time the fault status
        is cleared.

"
    ::= { pmMpoLanesEntry 45 }

pmMpoLanesRxUAS OBJECT-TYPE
    SYNTAX      FaultStatus
    MAX-ACCESS  read-only
    STATUS      current
    DESCRIPTION
        "Unavailable seconds (UAS) Rx 15 min threshold
        exceeded.

        A: The number of unavailable seconds during a
        period exceeds the associated threshold.

        D: At the start of a new 15 minute period the
        associated UAS counter is reset to zero, by
        definition. At the same time the fault status
        is cleared. The corresponding active alarm in
        the alarm list, if any, is not cleared for
        another 45 seconds to avoid unneccesary toggling
        in the alarm list and log.

"
    ::= { pmMpoLanesEntry 46 }

pmMpoLanesTxES OBJECT-TYPE
    SYNTAX      FaultStatus
    MAX-ACCESS  read-only
    STATUS      current
    DESCRIPTION
        "Errored seconds (ES) Tx 15 min threshold
        exceeded.

        A: The number of errored seconds during a period
        exceeds the associated threshold.

        D: At the start of a new 15 minute period the
        associated ES counter is reset to zero, by
        definition. At the same time the fault status
        is cleared. The corresponding active alarm in
        the alarm list, if any, is not cleared for
        another 30 seconds to avoid unneccesary toggling
        in the alarm list and log.

"
    ::= { pmMpoLanesEntry 47 }

pmMpoLanesTxSES OBJECT-TYPE
    SYNTAX      FaultStatus
    MAX-ACCESS  read-only
    STATUS      current
    DESCRIPTION
        "Severely errored seconds (SES) Tx 15 min
        threshold exceeded.

        A: The number of severely errored seconds during
        a period exceeds the associated threshold.

        D: At the start of a new 15 minute period the
        associated SES counter is reset to zero, by
        definition. At the same time the fault status
        is cleared. The corresponding active alarm in
        the alarm list, if any, is not cleared for
        another 20 seconds to avoid unneccesary toggling
        in the alarm list and log.

"
    ::= { pmMpoLanesEntry 48 }

pmMpoLanesTxBBE OBJECT-TYPE
    SYNTAX      FaultStatus
    MAX-ACCESS  read-only
    STATUS      current
    DESCRIPTION
        "Background block errors (BBE) Tx 15 min
        threshold exceeded.

        A: The number of background block errors
        during a period exceeds the associated threshold.

        D: At the start of a new 15 minute period the
        associated BBE counter is reset to zero, by
        definition. At the same time the fault status
        is cleared.

"
    ::= { pmMpoLanesEntry 49 }

pmMpoLanesTxUAS OBJECT-TYPE
    SYNTAX      FaultStatus
    MAX-ACCESS  read-only
    STATUS      current
    DESCRIPTION
        "Unavailable seconds (UAS) Tx 15 min threshold
        exceeded.

        A: The number of unavailable seconds during a period
        exceeds the associated threshold.

        D: At the start of a new 15 minute period the
        associated UAS counter is reset to zero, by
        definition. At the same time the fault status
        is cleared. The corresponding active alarm in
        the alarm list, if any, is not cleared for
        another 45 seconds to avoid unneccesary toggling
        in the alarm list and log.

"
    ::= { pmMpoLanesEntry 50 }

pmMpoLanesRx24hES OBJECT-TYPE
    SYNTAX      FaultStatus
    MAX-ACCESS  read-only
    STATUS      current
    DESCRIPTION
        "Errored seconds (ES) Rx 24 hour threshold
        exceeded.

        A: The number of errored seconds during a period
        exceeds the associated threshold.

        D: At the start of a new 24 hour period the
        associated ES counter is reset to zero, by
        definition. At the same time the fault status
        is cleared. The corresponding active alarm in
        the alarm list, if any, is not cleared for
        another 300 seconds to avoid unneccesary toggling
        in the alarm list and log.

"
    ::= { pmMpoLanesEntry 51 }

pmMpoLanesRx24hSES OBJECT-TYPE
    SYNTAX      FaultStatus
    MAX-ACCESS  read-only
    STATUS      current
    DESCRIPTION
        "Severely errored seconds (SES) Rx 24 hour
        threshold exceeded.

        A: The number of severely errored seconds during
        a period exceeds the associated threshold.

        D: At the start of a new 24 hour period the
        associated SES counter is reset to zero, by
        definition. At the same time the fault status
        is cleared. The corresponding active alarm in
        the alarm list, if any, is not cleared for
        another 150 seconds to avoid unneccesary toggling
        in the alarm list and log.


"
    ::= { pmMpoLanesEntry 52 }

pmMpoLanesRx24hBBE OBJECT-TYPE
    SYNTAX      FaultStatus
    MAX-ACCESS  read-only
    STATUS      current
    DESCRIPTION
        "Background block errors (BBE) Rx 24 hour
        threshold exceeded.

        A: The number of background block errors
        during a period exceeds the associated threshold.

        D: At the start of a new 24 hour period the
        associated BBE counter is reset to zero, by
        definition. At the same time the fault status
        is cleared.

"
    ::= { pmMpoLanesEntry 53 }

pmMpoLanesRx24hUAS OBJECT-TYPE
    SYNTAX      FaultStatus
    MAX-ACCESS  read-only
    STATUS      current
    DESCRIPTION
        "Unavailable seconds (UAS) Rx 24 hour threshold
        exceeded.

        A: The number of unavailable seconds during a period
        exceeds the associated threshold.

        D: At the start of a new 24 hour period the
        associated UAS counter is reset to zero, by
        definition. At the same time the fault status
        is cleared. The corresponding active alarm in
        the alarm list, if any, is not cleared for
        another 400 seconds to avoid unneccesary toggling
        in the alarm list and log.

"
    ::= { pmMpoLanesEntry 54 }

pmMpoLanesTx24hES OBJECT-TYPE
    SYNTAX      FaultStatus
    MAX-ACCESS  read-only
    STATUS      current
    DESCRIPTION
        "Errored seconds Tx (ES) 24 hour threshold
        exceeded.

        A: The number of errored seconds during a period
        exceeds the associated threshold.

        D: At the start of a new 24 hour period the
        associated ES counter is reset to zero, by
        definition. At the same time the fault status
        is cleared. The corresponding active alarm in
        the alarm list, if any, is not cleared for
        another 300 seconds to avoid unneccesary toggling
        in the alarm list and log.

"
    ::= { pmMpoLanesEntry 55 }

pmMpoLanesTx24hSES OBJECT-TYPE
    SYNTAX      FaultStatus
    MAX-ACCESS  read-only
    STATUS      current
    DESCRIPTION
        "Severely errored seconds (SES) Tx 24 hour
        threshold exceeded.

        A: The number of severely errored seconds during
        a period exceeds the associated threshold.

        D: At the start of a new 24 hour period the
        associated SES counter is reset to zero, by
        definition. At the same time the fault status
        is cleared. The corresponding active alarm in
        the alarm list, if any, is not cleared for
        another 150 seconds to avoid unneccesary toggling
        in the alarm list and log.

"
    ::= { pmMpoLanesEntry 56 }

pmMpoLanesTx24hBBE OBJECT-TYPE
    SYNTAX      FaultStatus
    MAX-ACCESS  read-only
    STATUS      current
    DESCRIPTION
        "Background block errors (BBE) Tx 24 hour
        threshold exceeded.

        A: The number of background block errors
        during a period exceeds the associated threshold.

        D: At the start of a new 24 hour period the
        associated BBE counter is reset to zero, by
        definition. At the same time the fault status
        is cleared.

"
    ::= { pmMpoLanesEntry 57 }

pmMpoLanesTx24hUAS OBJECT-TYPE
    SYNTAX      FaultStatus
    MAX-ACCESS  read-only
    STATUS      current
    DESCRIPTION
        "Unavailable seconds (UAS) Tx 24 hour threshold
        exceeded.

        A: The number of unavailable seconds during a
        period exceeds the associated threshold.

        D: At the start of a new 24 hour period the
        associated UAS counter is reset to zero, by
        definition. At the same time the fault status
        is cleared. The corresponding active alarm in
        the alarm list, if any, is not cleared for
        another 400 seconds to avoid unneccesary toggling
        in the alarm list and log.

"
    ::= { pmMpoLanesEntry 58 }

pmMpoLanesReset15Min OBJECT-TYPE
    SYNTAX      INTEGER {
                    normal (1),
                    reset (2) }
    MAX-ACCESS  read-write
    STATUS      current
    DESCRIPTION
        "Reset the 15 minute PM counters for the
        interface.

        After a successful reset the default value
        (normal) is restored in this action attribute.

        Usage: set reset15m reset

"
    DEFVAL { normal }
    ::= { pmMpoLanesEntry 59 }

pmMpoLanesReset24H OBJECT-TYPE
    SYNTAX      INTEGER {
                    normal (1),
                    reset (2) }
    MAX-ACCESS  read-write
    STATUS      current
    DESCRIPTION
        "Reset the 24 hour PM counters for the interface.

        After a successful reset the default value
        (normal) is restored in this action attribute.

        Usage: set reset24h reset

"
    DEFVAL { normal }
    ::= {    pmMpoLanesEntry 60 }

pmMpoLanesRxPowerLevel OBJECT-TYPE
    SYNTAX      Integer32
    MAX-ACCESS  read-only
    STATUS      current
    DESCRIPTION
        "The received power level in units of 0.1 dBm

"
    ::= { pmMpoLanesEntry 61 }

pmMpoLanesTxPowerLevel OBJECT-TYPE
    SYNTAX      Integer32
    MAX-ACCESS  read-only
    STATUS      current
    DESCRIPTION
        "The transmitted power level in units of 0.1 dBm

"
    ::= { pmMpoLanesEntry 62 }

pmMpoLanesObjectProperty  OBJECT-TYPE
    SYNTAX      ObjectProperty
    MAX-ACCESS  read-only
    STATUS      current
    DESCRIPTION
        "Property mask.

"
    ::= { pmMpoLanesEntry 63 }

pmMpoLanesIfNo OBJECT-TYPE
    SYNTAX      PortNumber
    MAX-ACCESS  read-create
    STATUS      current
    DESCRIPTION
        "The interface number of the port.

"
    ::= { pmMpoLanesEntry 64 }


pmMpoLanesUpPortId OBJECT-TYPE
    SYNTAX      Integer32   (-1..2147483647)
    MAX-ACCESS  read-create
    STATUS      current
    DESCRIPTION
        "Internal port reference for traffic unit.
"
    DEFVAL { -1 }
    ::= { pmMpoLanesEntry 65 }

-- ----------------------------------------------------
-- Notifications
-- ----------------------------------------------------

pmNotifyPrefix OBJECT IDENTIFIER ::= { lumentisPmNotifications 0 }

pmFileAdded NOTIFICATION-TYPE
    OBJECTS {
        pmFileIndex,
        pmFileName,
        pmFileCreatedTime,
        pmFileSeqNumber }
    STATUS      current
    DESCRIPTION
        "Sent when a new 15 minute interval log file is
        available.

"
    ::= { pmNotifyPrefix 1 }

pmFile24hAdded NOTIFICATION-TYPE
    OBJECTS {
        pmFile24hIndex,
        pmFile24hName,
        pmFile24hCreatedTime,
        pmFile24hSeqNumber }
    STATUS      current
    DESCRIPTION
        "Sent when a new 24 hour interval log file is
        available.

"
    ::= { pmNotifyPrefix 2 }


-- ----------------------------------------------------
-- Control parameters group
-- ----------------------------------------------------

pmControlReset15Min OBJECT-TYPE
    SYNTAX      INTEGER {
                    normal (1),
                    reset (2) }
    MAX-ACCESS  read-write
    STATUS      current
    DESCRIPTION
        "Reset all 15 minute counters in the node.

        After a successful reset the default value
        (normal) is restored in this action attribute.

        Usage: set reset15m reset

"
    DEFVAL { normal }
    ::= { pmControl 1 }

pmControlReset24H OBJECT-TYPE
    SYNTAX      INTEGER {
                    normal (1),
                    reset (2) }
    MAX-ACCESS  read-write
    STATUS      current
    DESCRIPTION
        "Reset all 24 hour counters in the node.

        After a successful reset the default value
        (normal) is restored in this action attribute.

        Usage: set reset24h reset

"
    DEFVAL { normal }
    ::= { pmControl 2 }

pmControlResetCont OBJECT-TYPE
    SYNTAX      INTEGER {
                    normal (1),
                    reset (2) }
    MAX-ACCESS  read-write
    STATUS      current
    DESCRIPTION
        "Reset all continuous (free running) counters in the node.

        After a successful reset the default value
        (normal) is restored in this action attribute.

        Usage: set resetCont reset

"
    DEFVAL { normal }
    ::= { pmControl 3 }

-- ----------------------------------------------------
-- Ethernet Traffic Data
-- ----------------------------------------------------

pmEthTdTable OBJECT-TYPE
    SYNTAX  SEQUENCE OF PmEthTdEntry
    MAX-ACCESS  not-accessible
    STATUS  current
    DESCRIPTION
     "The pm interface table."
::= { pmEthTdList 1 }

pmEthTdEntry OBJECT-TYPE
    SYNTAX  PmEthTdEntry
    MAX-ACCESS  not-accessible
    STATUS  current
    DESCRIPTION
        "An entry in interface table.

"
    INDEX   { pmEthTdIndex }
::= { pmEthTdTable 1 }

PmEthTdEntry ::=
    SEQUENCE {
        pmEthTdIndex               Unsigned32,
        pmEthTdName                MgmtNameString,
        pmEthTdSubrack             SubrackNumber,
        pmEthTdSlot                SlotNumber,
        pmEthTdPort                PortNumber,
        pmEthTdPmReportMode        INTEGER,
        pmEthTdRxPort              PortNumber,
        pmEthTdReset15Min          INTEGER,
        pmEthTdReset24H            INTEGER,
        pmEthTdAdminStatus         INTEGER,
        pmEthTdOperStatus          INTEGER,
        pmEthTdIsSuspect15Min      TruthValue,
        pmEthTdIsSuspect24h        TruthValue,



        -- Ethernet traffic data 15m
        pmEthTdCurrentRxUndersizedFrames Counter64,
        pmEthTdCurrentRxOversizedFrames Counter64,
        pmEthTdCurrentRxFragments       Counter64,
        pmEthTdCurrentRxFcsErrors       Counter64,
        pmEthTdCurrentRxInvalidCeVlanId Counter64,
        pmEthTdCurrentTxOctets  Counter64,
        pmEthTdCurrentTxFrames  Counter64,
        pmEthTdCurrentTxUnicastFrames Counter64,
        pmEthTdCurrentTxMulticastFrames Counter64,
        pmEthTdCurrentTxBroadcastFrames Counter64,
        pmEthTdCurrentRxOctets  Counter64,
        pmEthTdCurrentRxFrames  Counter64,
        pmEthTdCurrentRxUnicastFrames Counter64,
        pmEthTdCurrentRxMulticastFrames Counter64,
        pmEthTdCurrentRxBroadcastFrames Counter64,
        pmEthTdCurrentTxEthMaxUtilization Gauge32,
        pmEthTdCurrentRxEthMaxUtilization Gauge32,

        -- Ethernet traffic data 24h
        pmEthTdCurrent24hRxUndersizedFrames Counter64,
        pmEthTdCurrent24hRxOversizedFrames Counter64,
        pmEthTdCurrent24hRxFragments Counter64,
        pmEthTdCurrent24hRxFcsErrors Counter64,
        pmEthTdCurrent24hRxInvalidCeVlanId      Counter64,
        pmEthTdCurrent24hTxOctets       Counter64,
        pmEthTdCurrent24hTxFrames Counter64,
        pmEthTdCurrent24hTxUnicastFrames Counter64,
        pmEthTdCurrent24hTxMulticastFrames      Counter64,
        pmEthTdCurrent24hTxBroadcastFrames Counter64,
        pmEthTdCurrent24hRxOctets       Counter64,
        pmEthTdCurrent24hRxFrames       Counter64,
        pmEthTdCurrent24hRxUnicastFrames Counter64,
        pmEthTdCurrent24hRxMulticastFrames      Counter64,
        pmEthTdCurrent24hRxBroadcastFrames      Counter64,
        pmEthTdCurrent24hTxEthMaxUtilization Gauge32,
        pmEthTdCurrent24hRxEthMaxUtilization Gauge32,

        pmEthTdObjectProperty   ObjectProperty,

        -- Ethernet traffic threshold 15m
        pmEthTdRxUndersizedFramesThreshold Counter64,
        pmEthTdRxOversizedFramesThreshold Counter64,
        pmEthTdRxFragmentsThreshold     Counter64,
        pmEthTdRxFcsErrorsThreshold     Counter64,
        pmEthTdRxInvalidCeVlanIdThreshold Counter64,

        -- Ethernet traffic threshold 24h
        pmEthTd24hRxUndersizedFramesThreshold Counter64,
        pmEthTd24hRxOversizedFramesThreshold Counter64,
        pmEthTd24hRxFragmentsThreshold Counter64,
        pmEthTd24hRxFcsErrorsThreshold Counter64,
        pmEthTd24hRxInvalidCeVlanIdThreshold    Counter64,

        -- Ethernet traffic faultstatus 15m
        pmEthTdRxUndersizedFrames FaultStatus,
        pmEthTdRxOversizedFrames FaultStatus,
        pmEthTdRxFragments      FaultStatus,
        pmEthTdRxFcsErrors      FaultStatus,
        pmEthTdRxInvalidCeVlanId FaultStatus,

        -- Ethernet traffic faultstatus 24h
        pmEthTd24hRxUndersizedFrames FaultStatus,
        pmEthTd24hRxOversizedFrames FaultStatus,
        pmEthTd24hRxFragments FaultStatus,
        pmEthTd24hRxFcsErrors FaultStatus,
        pmEthTd24hRxInvalidCeVlanId     FaultStatus,

        -- Ethernet traffic data free running
        pmEthTdResetCont            INTEGER,
        pmEthTdCurrentContRxUndersizedFrames Counter64,
        pmEthTdCurrentContRxOversizedFrames Counter64,
        pmEthTdCurrentContRxFragments   Counter64,
        pmEthTdCurrentContRxFcsErrors   Counter64,
        pmEthTdCurrentContRxInvalidCeVlanId Counter64,
        pmEthTdCurrentContTxOctets      Counter64,
        pmEthTdCurrentContTxFrames      Counter64,
        pmEthTdCurrentContTxUnicastFrames Counter64,
        pmEthTdCurrentContTxMulticastFrames Counter64,
        pmEthTdCurrentContTxBroadcastFrames Counter64,
        pmEthTdCurrentContRxOctets      Counter64,
        pmEthTdCurrentContRxFrames      Counter64,
        pmEthTdCurrentContRxUnicastFrames Counter64,
        pmEthTdCurrentContRxMulticastFrames Counter64,
        pmEthTdCurrentContRxBroadcastFrames Counter64,
        pmEthTdVlanId 			Integer32,
        pmEthTdIfNo				PortNumber,
		pmEthTdUpPortId 		    Integer32
	}

pmEthTdIndex OBJECT-TYPE
    SYNTAX      Unsigned32 (1..2147483647)
    MAX-ACCESS  read-only
    STATUS      current
    DESCRIPTION
        "An arbitrary index assigned to each if entry.
        The index is read-only and persistent, i.e the index
        is kept over reboot and backed up by stable storage.

"
    ::= { pmEthTdEntry 1 }

pmEthTdName OBJECT-TYPE
    SYNTAX      MgmtNameString
    MAX-ACCESS  read-only
    STATUS      current
    DESCRIPTION
        "The management name of the interface, for
        example 'mrt:1:2:1-2'.

"
    ::= { pmEthTdEntry 2 }

pmEthTdSubrack OBJECT-TYPE
    SYNTAX      SubrackNumber
    MAX-ACCESS  read-create
    STATUS      current
    DESCRIPTION
        "The number of the subrack where the interface
        is located.

"
    ::= { pmEthTdEntry 3 }

pmEthTdSlot OBJECT-TYPE
    SYNTAX      SlotNumber
    MAX-ACCESS  read-create
    STATUS      current
    DESCRIPTION
        "The number of the slot where the interface is
        located.

"
    ::= { pmEthTdEntry 4 }

pmEthTdPort OBJECT-TYPE
    SYNTAX      PortNumber
    MAX-ACCESS  read-create
    STATUS      current
    DESCRIPTION
        "The number of the Tx port for the interface.

"
    ::= { pmEthTdEntry 5 }

pmEthTdPmReportMode OBJECT-TYPE
    SYNTAX      INTEGER {
                    off (1),
                    on (2) }
    MAX-ACCESS  read-write
    STATUS      current
    DESCRIPTION
        "The mode PM reporting on the interface.

        off - PM reporting is inactive.

        on - PM reporting is activated.

"
    DEFVAL { on }
    ::= { pmEthTdEntry 6 }

pmEthTdRxPort OBJECT-TYPE
    SYNTAX      PortNumber
    MAX-ACCESS  read-create
    STATUS      current
    DESCRIPTION
        "The number of the Rx port for the interface.

"
    ::= { pmEthTdEntry 7 }

pmEthTdReset15Min OBJECT-TYPE
    SYNTAX      INTEGER {
                    normal (1),
                    reset (2) }
    MAX-ACCESS  read-write
    STATUS      current
    DESCRIPTION
        "Reset the 15 minute PM counters for the
        interface.

        After a successful reset the default value
        (normal) is restored in this action attribute.

        Usage: set reset15m reset

"
    DEFVAL { normal }
    ::= { pmEthTdEntry 8 }

pmEthTdReset24H OBJECT-TYPE
    SYNTAX      INTEGER {
                    normal (1),
                    reset (2) }
    MAX-ACCESS  read-write
    STATUS      current
    DESCRIPTION
        "Reset the 24 hour PM counters for the interface.

        After a successful reset the default value
        (normal) is restored in this action attribute.

        Usage: set reset24h reset

"
    DEFVAL { normal }
    ::= {    pmEthTdEntry 9 }

pmEthTdAdminStatus OBJECT-TYPE
    SYNTAX  INTEGER {
        down (1),
        service (2),
        up (3) }
    MAX-ACCESS read-write
    STATUS  current
    DESCRIPTION
         "Administrative state for the PM object.

         down - Alarms are not sent.

         up - Alarms are sent

         service - Alarms are not sent

"
     DEFVAL { up }
     ::= { pmEthTdEntry 10 }

pmEthTdOperStatus OBJECT-TYPE
    SYNTAX  INTEGER {
        notPresent (1),
        down (2),
        up (3) }
    MAX-ACCESS read-only
    STATUS  current
    DESCRIPTION
         "The operational state for the PM object.

         notPresent - The physical resource is not available.

         down - The object is disabled.

         up - The object is enabled.

"
     DEFVAL { notPresent }
     ::= { pmEthTdEntry 11 }

pmEthTdIsSuspect15Min OBJECT-TYPE
    SYNTAX  TruthValue
    MAX-ACCESS  read-only
    STATUS  current
    DESCRIPTION
       "This variable indicates if the data for this
        interface is suspect. The current interval may
        for example contain measurements for a part of
        the interval.

"
    ::= { pmEthTdEntry 12 }

pmEthTdIsSuspect24h OBJECT-TYPE
    SYNTAX  TruthValue
    MAX-ACCESS  read-only
    STATUS  current
    DESCRIPTION
       "This variable indicates if the data for this
        interface is suspect. The current interval may
        for example contain measurements for a part of
        the interval.

"
    ::= { pmEthTdEntry 13 }

pmEthTdCurrentRxUndersizedFrames OBJECT-TYPE
     SYNTAX Counter64
     MAX-ACCESS read-only
     STATUS current
     DESCRIPTION
        "The amount of undersized frames
        during a particular 15 minute interval.

"
    ::= {pmEthTdEntry 14 }

pmEthTdCurrentRxOversizedFrames OBJECT-TYPE
     SYNTAX Counter64
     MAX-ACCESS read-only
     STATUS current
     DESCRIPTION
        "The amount of oversized frames
        during a particular 15 minute interval.

"
    ::= {pmEthTdEntry 15 }

pmEthTdCurrentRxFragments OBJECT-TYPE
     SYNTAX Counter64
     MAX-ACCESS read-only
     STATUS current
     DESCRIPTION
        "The amount of fragments
        during a particular 15 minute interval.

"
    ::= {pmEthTdEntry 16 }

pmEthTdCurrentRxFcsErrors OBJECT-TYPE
     SYNTAX Counter64
     MAX-ACCESS read-only
     STATUS current
     DESCRIPTION
        "The amount of frames with FCS or alignment errors
        during a particular 15 minute interval.

"
    ::= {pmEthTdEntry 17 }

pmEthTdCurrentRxInvalidCeVlanId OBJECT-TYPE
     SYNTAX Counter64
     MAX-ACCESS read-only
     STATUS current
     DESCRIPTION
        "The amount of frames with invalid CE-VLAN id
        during a particular 15 minute interval.

"
    ::= {pmEthTdEntry 18 }

pmEthTdCurrentTxOctets OBJECT-TYPE
     SYNTAX Counter64
     MAX-ACCESS read-only
     STATUS current
     DESCRIPTION
        "The amount of octets transmitted OK
        during a particular 15 minute interval.

"
    ::= {pmEthTdEntry 19 }

pmEthTdCurrentTxFrames OBJECT-TYPE
     SYNTAX Counter64
     MAX-ACCESS read-only
     STATUS current
     DESCRIPTION
        "The amount of frames transmitted OK
        during a particular 15 minute interval.

"
    ::= {pmEthTdEntry 20 }

pmEthTdCurrentTxUnicastFrames OBJECT-TYPE
     SYNTAX Counter64
     MAX-ACCESS read-only
     STATUS current
     DESCRIPTION
        "The amount of unicast frames transmitted OK
        during a particular 15 minute interval.

"
    ::= {pmEthTdEntry 21 }

pmEthTdCurrentTxMulticastFrames OBJECT-TYPE
     SYNTAX Counter64
     MAX-ACCESS read-only
     STATUS current
     DESCRIPTION
        "The amount of multicast frames transmitted OK
        during a particular 15 minute interval.

"
    ::= {pmEthTdEntry 22 }

pmEthTdCurrentTxBroadcastFrames OBJECT-TYPE
     SYNTAX Counter64
     MAX-ACCESS read-only
     STATUS current
     DESCRIPTION
        "The amount of broadcast frames transmitted OK
        during a particular 15 minute interval.

"
    ::= {pmEthTdEntry 23 }

pmEthTdCurrentRxOctets OBJECT-TYPE
     SYNTAX Counter64
     MAX-ACCESS read-only
     STATUS current
     DESCRIPTION
        "The amount of octets received OK
        during a particular 15 minute interval.

"
    ::= {pmEthTdEntry 24 }

pmEthTdCurrentRxFrames OBJECT-TYPE
     SYNTAX Counter64
     MAX-ACCESS read-only
     STATUS current
     DESCRIPTION
        "The amount of frames received OK
        during a particular 15 minute interval.

"
    ::= {pmEthTdEntry 25 }

pmEthTdCurrentRxUnicastFrames OBJECT-TYPE
     SYNTAX Counter64
     MAX-ACCESS read-only
     STATUS current
     DESCRIPTION
        "The amount of unicast frames received OK
        during a particular 15 minute interval.

"
    ::= {pmEthTdEntry 26 }

pmEthTdCurrentRxMulticastFrames OBJECT-TYPE
     SYNTAX Counter64
     MAX-ACCESS read-only
     STATUS current
     DESCRIPTION
        "The amount of multicast frames received OK
        during a particular 15 minute interval.

"
    ::= {pmEthTdEntry 27 }

pmEthTdCurrentRxBroadcastFrames OBJECT-TYPE
     SYNTAX Counter64
     MAX-ACCESS read-only
     STATUS current
     DESCRIPTION
        "The amount of broadcast frames received OK
        during a particular 15 minute interval.

"
    ::= {pmEthTdEntry 28 }

pmEthTdCurrent24hRxUndersizedFrames OBJECT-TYPE
     SYNTAX Counter64
     MAX-ACCESS read-only
     STATUS current
     DESCRIPTION
        "The amount of undersized frames
        during a particular 24 hour interval.

"
    ::= {pmEthTdEntry 29 }

pmEthTdCurrent24hRxOversizedFrames OBJECT-TYPE
     SYNTAX Counter64
     MAX-ACCESS read-only
     STATUS current
     DESCRIPTION
        "The amount of oversized frames
        during a particular 24 hour interval.

"
    ::= {pmEthTdEntry 30 }

pmEthTdCurrent24hRxFragments OBJECT-TYPE
     SYNTAX Counter64
     MAX-ACCESS read-only
     STATUS current
     DESCRIPTION
        "The amount of fragments
        during a particular 24 hour interval.

"
    ::= {pmEthTdEntry 31 }

pmEthTdCurrent24hRxFcsErrors OBJECT-TYPE
     SYNTAX Counter64
     MAX-ACCESS read-only
     STATUS current
     DESCRIPTION
        "The amount of frames with FCS or alignment errors
        during a particular 24 hour interval.

"
    ::= {pmEthTdEntry 32 }

pmEthTdCurrent24hRxInvalidCeVlanId OBJECT-TYPE
     SYNTAX Counter64
     MAX-ACCESS read-only
     STATUS current
     DESCRIPTION
        "The amount of frames with invalid CE-VLAN id
        during a particular 24 hour interval.

"
    ::= {pmEthTdEntry 33 }

pmEthTdCurrent24hTxOctets OBJECT-TYPE
     SYNTAX Counter64
     MAX-ACCESS read-only
     STATUS current
     DESCRIPTION
        "The amount of octets transmitted OK
        during a particular 24 hour interval.

"
    ::= {pmEthTdEntry 34 }

pmEthTdCurrent24hTxFrames OBJECT-TYPE
     SYNTAX Counter64
     MAX-ACCESS read-only
     STATUS current
     DESCRIPTION
        "The amount of frames transmitted OK
        during a particular 24 hour interval.

"
    ::= {pmEthTdEntry 35 }

pmEthTdCurrent24hTxUnicastFrames OBJECT-TYPE
     SYNTAX Counter64
     MAX-ACCESS read-only
     STATUS current
     DESCRIPTION
        "The amount of unicast frames transmitted OK
        during a particular 24 hour interval.

"
    ::= {pmEthTdEntry 36 }

pmEthTdCurrent24hTxMulticastFrames OBJECT-TYPE
     SYNTAX Counter64
     MAX-ACCESS read-only
     STATUS current
     DESCRIPTION
        "The amount of multicast frames transmitted OK
        during a particular 24 hour interval.

"
    ::= {pmEthTdEntry 37 }

pmEthTdCurrent24hTxBroadcastFrames OBJECT-TYPE
     SYNTAX Counter64
     MAX-ACCESS read-only
     STATUS current
     DESCRIPTION
        "The amount of broadcast frames transmitted OK
        during a particular 24 hour interval.

"
    ::= {pmEthTdEntry 38 }

pmEthTdCurrent24hRxOctets OBJECT-TYPE
     SYNTAX Counter64
     MAX-ACCESS read-only
     STATUS current
     DESCRIPTION
        "The amount of octets received OK
        during a particular 24 hour interval.

"
    ::= {pmEthTdEntry 39 }

pmEthTdCurrent24hRxFrames OBJECT-TYPE
     SYNTAX Counter64
     MAX-ACCESS read-only
     STATUS current
     DESCRIPTION
        "The amount of frames received OK
        during a particular 24 hour interval.

"
    ::= {pmEthTdEntry 40 }

pmEthTdCurrent24hRxUnicastFrames OBJECT-TYPE
     SYNTAX Counter64
     MAX-ACCESS read-only
     STATUS current
     DESCRIPTION
        "The amount of unicast frames received OK
        during a particular 24 hour interval.

"
    ::= {pmEthTdEntry 41 }

pmEthTdCurrent24hRxMulticastFrames OBJECT-TYPE
     SYNTAX Counter64
     MAX-ACCESS read-only
     STATUS current
     DESCRIPTION
        "The amount of multicast frames received OK
        during a particular 24 hour interval.

"
    ::= {pmEthTdEntry 42 }

pmEthTdCurrent24hRxBroadcastFrames OBJECT-TYPE
     SYNTAX Counter64
     MAX-ACCESS read-only
     STATUS current
     DESCRIPTION
        "The amount of broadcast frames received OK
        during a particular 24 hour interval.

"
    ::= {pmEthTdEntry 43 }

pmEthTdObjectProperty  OBJECT-TYPE
    SYNTAX      ObjectProperty
    MAX-ACCESS  read-only
    STATUS      current
    DESCRIPTION
        "Property mask.

"
    ::= { pmEthTdEntry 44 }

pmEthTdRxUndersizedFramesThreshold  OBJECT-TYPE
    SYNTAX      Counter64
    MAX-ACCESS  read-write
    STATUS      current
    DESCRIPTION
        "Sets the threshold for the alarm,
        (in no. of frames).

        Default value 10
"
    DEFVAL { 10 }
    ::= { pmEthTdEntry 45 }

pmEthTdRxOversizedFramesThreshold  OBJECT-TYPE
    SYNTAX      Counter64
    MAX-ACCESS  read-write
    STATUS      current
    DESCRIPTION
        "Sets the threshold for the alarm,
        (in no. of frames).

        Default value 10
"
    DEFVAL { 10 }
    ::= { pmEthTdEntry 46 }

pmEthTdRxFragmentsThreshold  OBJECT-TYPE
    SYNTAX      Counter64
    MAX-ACCESS  read-write
    STATUS      current
    DESCRIPTION
        "Sets the threshold for the alarm,
        (in no. of frames).

        Default value 10
"
    DEFVAL { 10 }
    ::= { pmEthTdEntry 47 }

pmEthTdRxFcsErrorsThreshold  OBJECT-TYPE
    SYNTAX      Counter64
    MAX-ACCESS  read-write
    STATUS      current
    DESCRIPTION
        "Sets the threshold for the alarm,
        (in no. of frames).

        Default value 10
"
    DEFVAL { 10 }
    ::= { pmEthTdEntry 48 }

pmEthTdRxInvalidCeVlanIdThreshold  OBJECT-TYPE
    SYNTAX      Counter64
    MAX-ACCESS  read-write
    STATUS      current
    DESCRIPTION
        "Sets the threshold for the alarm,
        (in no. of frames).

        Default value 10

        A value of 0 (zero) will disable the alarm.
"
    DEFVAL { 10 }
    ::= { pmEthTdEntry 49 }

pmEthTd24hRxUndersizedFramesThreshold  OBJECT-TYPE
    SYNTAX      Counter64
    MAX-ACCESS  read-write
    STATUS      current
    DESCRIPTION
        "Sets the threshold for the alarm,
        (in no. of frames).

        Default value 10
"
    DEFVAL { 10 }
    ::= { pmEthTdEntry 50 }

pmEthTd24hRxOversizedFramesThreshold  OBJECT-TYPE
    SYNTAX      Counter64
    MAX-ACCESS  read-write
    STATUS      current
    DESCRIPTION
        "Sets the threshold for the alarm,
        (in no. of frames).

        Default value 10
"
    DEFVAL { 10 }
    ::= { pmEthTdEntry 51 }

pmEthTd24hRxFragmentsThreshold  OBJECT-TYPE
    SYNTAX      Counter64
    MAX-ACCESS  read-write
    STATUS      current
    DESCRIPTION
        "Sets the threshold for the alarm,
        (in no. of frames).

        Default value 10
"
    DEFVAL { 10 }
    ::= { pmEthTdEntry 52 }

pmEthTd24hRxFcsErrorsThreshold  OBJECT-TYPE
    SYNTAX      Counter64
    MAX-ACCESS  read-write
    STATUS      current
    DESCRIPTION
        "Sets the threshold for the alarm,
        (in no. of frames).

        Default value 10
"
    DEFVAL { 10 }
    ::= { pmEthTdEntry 53 }

pmEthTd24hRxInvalidCeVlanIdThreshold  OBJECT-TYPE
    SYNTAX      Counter64
    MAX-ACCESS  read-write
    STATUS      current
    DESCRIPTION
        "Sets the threshold for the alarm,
        (in no. of frames).

        Default value 10

        A value of 0 (zero) will disable the alarm.
"
    DEFVAL { 10 }
    ::= { pmEthTdEntry 54 }

pmEthTdRxUndersizedFrames  OBJECT-TYPE
    SYNTAX      FaultStatus
    MAX-ACCESS  read-only
    STATUS      current
    DESCRIPTION
        "Rx undersized frames threshold exceeded.

        A: The number of undersized frames during a
        period exceeds the associated threshold.

        D: At the start of a new 15 minute period the
        associated undersized frames counter is reset to
        zero. At the same time the fault
        status is cleared.

"
    ::= { pmEthTdEntry 55 }

pmEthTdRxOversizedFrames OBJECT-TYPE
    SYNTAX      FaultStatus
    MAX-ACCESS  read-only
    STATUS      current
    DESCRIPTION
        "Rx oversized frames threshold exceeded.

        A: The number of oversized frames during a
        period exceeds the associated threshold.

        D: At the start of a new 15 minute period the
        associated oversized frames counter is reset to
        zero. At the same time the fault
        status is cleared.

"
    ::= { pmEthTdEntry 56 }

pmEthTdRxFragments  OBJECT-TYPE
    SYNTAX      FaultStatus
    MAX-ACCESS  read-only
    STATUS      current
    DESCRIPTION
        "Rx fragments threshold exceeded.

        A: The number of fragmented frames during a
        period exceeds the associated threshold.

        D: At the start of a new 15 minute period the
        associated fragmented frames counter is reset to
        zero. At the same time the fault status is cleared.

"
    ::= { pmEthTdEntry 57 }

pmEthTdRxFcsErrors  OBJECT-TYPE
    SYNTAX      FaultStatus
    MAX-ACCESS  read-only
    STATUS      current
    DESCRIPTION
        "Rx FCS errors threshold exceeded.

        A: The number of FCS or alignment errors during a
        period exceeds the associated threshold.

        D: At the start of a new 15 minute period the
        associated FCS error counter is reset to
        zero. At the same time the fault
        status is cleared.

"
    ::= { pmEthTdEntry 58 }

pmEthTdRxInvalidCeVlanId OBJECT-TYPE
    SYNTAX      FaultStatus
    MAX-ACCESS  read-only
    STATUS      current
    DESCRIPTION
        "Rx invalid CE VLAN id threshold exceeded.

        A: The number of invalid CE VLAN id during a
        period exceeds the associated threshold.

        D: At the start of a new 15 minute period the
        associated invalid CE VLAN id counter is reset to
        zero. At the same time the fault
        status is cleared.

"
    ::= { pmEthTdEntry 59 }

pmEthTd24hRxUndersizedFrames OBJECT-TYPE
    SYNTAX      FaultStatus
    MAX-ACCESS  read-only
    STATUS      current
    DESCRIPTION
        "Rx undersized frames 24h threshold exceeded.

        A: The number of undersized frames during a
        period exceeds the associated threshold.

        D: At the start of a new 24 hour period the
        associated undersized frames counter is reset to
        zero. At the same time the fault
        status is cleared.

"
    ::= { pmEthTdEntry 60 }

pmEthTd24hRxOversizedFrames OBJECT-TYPE
    SYNTAX      FaultStatus
    MAX-ACCESS  read-only
    STATUS      current
    DESCRIPTION
        "Rx oversized frames 24h threshold exceeded.

        A: The number of oversized frames during a
        period exceeds the associated threshold.

        D: At the start of a new 24 hour period the
        associated oversized frames counter is reset
        to zero. At the same time the fault
        status is cleared.

"
    ::= { pmEthTdEntry 61 }

pmEthTd24hRxFragments OBJECT-TYPE
    SYNTAX      FaultStatus
    MAX-ACCESS  read-only
    STATUS      current
    DESCRIPTION
        "Rx fragments 24h threshold exceeded.

        A: The number of fragmented frames during a
        period exceeds the associated threshold.

        D: At the start of a new 24 hour period the
        associated fragmented frames counter is reset
        to zero. At the same time the fault
        status is cleared.

"
    ::= { pmEthTdEntry 62 }

pmEthTd24hRxFcsErrors OBJECT-TYPE
    SYNTAX      FaultStatus
    MAX-ACCESS  read-only
    STATUS      current
    DESCRIPTION
        "Rx FCS errors 24h threshold exceeded.

        A: The number of FCS or alignment errors during a
        period exceeds the associated threshold.

        D: At the start of a new 24 hour period the
        associated FCS error counter is reset to
        zero. At the same time the fault
        status is cleared.

"
    ::= { pmEthTdEntry 63 }

pmEthTd24hRxInvalidCeVlanId OBJECT-TYPE
    SYNTAX      FaultStatus
    MAX-ACCESS  read-only
    STATUS      current
    DESCRIPTION
        "Rx invalid CE VLAN id 24h threshold exceeded.

        A: The number of invalid CE VLAN id during a
        period exceeds the associated threshold.

        D: At the start of a new 24 hour period the
        associated invalid CE VLAN id counter is reset
        to zero. At the same time the fault
        status is cleared.

"
    ::= { pmEthTdEntry 64 }

pmEthTdCurrentTxEthMaxUtilization OBJECT-TYPE
    SYNTAX  Gauge32
    MAX-ACCESS  read-only
    STATUS  current
    DESCRIPTION
       "The maximum layer 2 bandwidth utilization of the
        ethernet signal during the current 15 min
        interval.

"
    ::= { pmEthTdEntry 65 }

pmEthTdCurrentRxEthMaxUtilization OBJECT-TYPE
    SYNTAX  Gauge32
    MAX-ACCESS  read-only
    STATUS  current
    DESCRIPTION
       "The maximum layer 2 bandwidth utilization of the
        ethernet signal during the current 15 min
        interval.

"
    ::= { pmEthTdEntry 66 }

pmEthTdCurrent24hTxEthMaxUtilization OBJECT-TYPE
    SYNTAX  Gauge32
    MAX-ACCESS  read-only
    STATUS  current
    DESCRIPTION
       "The maximum layer 2 bandwidth utilization of the
        ethernet signal during the current 24 h
        interval.

"
    ::= { pmEthTdEntry 67 }

pmEthTdCurrent24hRxEthMaxUtilization OBJECT-TYPE
    SYNTAX  Gauge32
    MAX-ACCESS  read-only
    STATUS  current
    DESCRIPTION
       "The maximum layer 2 bandwidth utilization of the
        ethernet signal during the current 24 h
        interval.

"
    ::= { pmEthTdEntry 68 }

pmEthTdResetCont OBJECT-TYPE
    SYNTAX      INTEGER {
                    normal (1),
                    reset (2) }
    MAX-ACCESS  read-write
    STATUS      current
    DESCRIPTION
        "Reset the free running PM counters for the
        interface.

        After a successful reset the default value
        (normal) is restored in this action attribute.

        Usage: set resetCont reset

"
    DEFVAL { normal }
    ::= { pmEthTdEntry 69 }

pmEthTdCurrentContRxUndersizedFrames OBJECT-TYPE
     SYNTAX Counter64
     MAX-ACCESS read-only
     STATUS current
     DESCRIPTION
        "The amount of undersized frames. Free running counter.

"
    ::= {pmEthTdEntry 70 }

pmEthTdCurrentContRxOversizedFrames OBJECT-TYPE
     SYNTAX Counter64
     MAX-ACCESS read-only
     STATUS current
     DESCRIPTION
        "The amount of oversized frames. Free running counter.

"
    ::= {pmEthTdEntry 71 }

pmEthTdCurrentContRxFragments OBJECT-TYPE
     SYNTAX Counter64
     MAX-ACCESS read-only
     STATUS current
     DESCRIPTION
        "The amount of fragments. Free running counter.

"
    ::= {pmEthTdEntry 72 }

pmEthTdCurrentContRxFcsErrors OBJECT-TYPE
     SYNTAX Counter64
     MAX-ACCESS read-only
     STATUS current
     DESCRIPTION
        "The amount of frames with FCS or alignment errors.
        Free running counter.

"
    ::= {pmEthTdEntry 73 }

pmEthTdCurrentContRxInvalidCeVlanId OBJECT-TYPE
     SYNTAX Counter64
     MAX-ACCESS read-only
     STATUS current
     DESCRIPTION
        "The amount of frames with invalid CE-VLAN id.
        Free running counter.

"
    ::= {pmEthTdEntry 74 }

pmEthTdCurrentContTxOctets OBJECT-TYPE
     SYNTAX Counter64
     MAX-ACCESS read-only
     STATUS current
     DESCRIPTION
        "The amount of octets transmitted OK. Free running
        counter.

"
    ::= {pmEthTdEntry 75 }

pmEthTdCurrentContTxFrames OBJECT-TYPE
     SYNTAX Counter64
     MAX-ACCESS read-only
     STATUS current
     DESCRIPTION
        "The amount of frames transmitted OK. Free running counter.

"
    ::= {pmEthTdEntry 76 }

pmEthTdCurrentContTxUnicastFrames OBJECT-TYPE
     SYNTAX Counter64
     MAX-ACCESS read-only
     STATUS current
     DESCRIPTION
        "The amount of unicast frames transmitted OK. Free running
        counter.

"
    ::= {pmEthTdEntry 77 }

pmEthTdCurrentContTxMulticastFrames OBJECT-TYPE
     SYNTAX Counter64
     MAX-ACCESS read-only
     STATUS current
     DESCRIPTION
        "The amount of multicast frames transmitted OK. Free running
        counter.

"
    ::= {pmEthTdEntry 78 }

pmEthTdCurrentContTxBroadcastFrames OBJECT-TYPE
     SYNTAX Counter64
     MAX-ACCESS read-only
     STATUS current
     DESCRIPTION
        "The amount of broadcast frames transmitted OK. Free running
        counter.

"
    ::= {pmEthTdEntry 79 }

pmEthTdCurrentContRxOctets OBJECT-TYPE
     SYNTAX Counter64
     MAX-ACCESS read-only
     STATUS current
     DESCRIPTION
        "The amount of octets received OK. Free running counter.

"
    ::= {pmEthTdEntry 80 }

pmEthTdCurrentContRxFrames OBJECT-TYPE
     SYNTAX Counter64
     MAX-ACCESS read-only
     STATUS current
     DESCRIPTION
        "The amount of frames received OK. Free running counter.

"
    ::= {pmEthTdEntry 81 }

pmEthTdCurrentContRxUnicastFrames OBJECT-TYPE
     SYNTAX Counter64
     MAX-ACCESS read-only
     STATUS current
     DESCRIPTION
        "The amount of unicast frames received OK. Free running counter.

"
    ::= {pmEthTdEntry 82 }

pmEthTdCurrentContRxMulticastFrames OBJECT-TYPE
     SYNTAX Counter64
     MAX-ACCESS read-only
     STATUS current
     DESCRIPTION
        "The amount of multicast frames received OK. Free running
        counter.

"
    ::= {pmEthTdEntry 83 }

pmEthTdCurrentContRxBroadcastFrames OBJECT-TYPE
     SYNTAX Counter64
     MAX-ACCESS read-only
     STATUS current
     DESCRIPTION
        "The amount of broadcast frames received OK. Free running
        counter.

"
    ::= {pmEthTdEntry 84 }

pmEthTdVlanId OBJECT-TYPE
    SYNTAX      Integer32(-1..4094)
    MAX-ACCESS  read-only
    STATUS      current
    DESCRIPTION
        "User specified VLAN ID, which is last number in the
        port device ID.
        If no VLAN ID is specified then VLAN ID -1 is assumed.

"
    DEFVAL { -1 }
    ::= {pmEthTdEntry 85 }


pmEthTdIfNo OBJECT-TYPE
    SYNTAX      PortNumber
    MAX-ACCESS  read-create
    STATUS      current
    DESCRIPTION
        "The interface number of the port.

"
    ::= { pmEthTdEntry 86 }

pmEthTdUpPortId OBJECT-TYPE
    SYNTAX      Integer32   (-1..2147483647)
    MAX-ACCESS  read-create
    STATUS      current
    DESCRIPTION
        "Internal port reference for traffic unit.
"
    DEFVAL { -1 }
    ::= { pmEthTdEntry 87 }


-- ----------------------------------------------------
-- Ethernet Traffic Management PM
-- ----------------------------------------------------

pmEthTmTable OBJECT-TYPE
    SYNTAX  SEQUENCE OF PmEthTmEntry
    MAX-ACCESS  not-accessible
    STATUS  obsolete
    DESCRIPTION
     "The pm interface table."
::= { pmEthTmList 1 }

pmEthTmEntry OBJECT-TYPE
    SYNTAX  PmEthTmEntry
    MAX-ACCESS  not-accessible
    STATUS  current
    DESCRIPTION
        "An entry in interface table.

"
    INDEX   { pmEthTmIndex }
::= { pmEthTmTable 1 }

PmEthTmEntry ::=
    SEQUENCE {
        pmEthTmIndex               Unsigned32,
        pmEthTmName                MgmtNameString,
        pmEthTmSubrack             SubrackNumber,
        pmEthTmSlot                SlotNumber,
        pmEthTmPort                PortNumber,
        pmEthTmPmReportMode        INTEGER,
        pmEthTmRxPort              PortNumber,
        pmEthTmReset15Min          INTEGER,
        pmEthTmReset24H            INTEGER,
        pmEthTmAdminStatus         INTEGER,
        pmEthTmOperStatus          INTEGER,
        pmEthTmIsSuspect15Min      TruthValue,
        pmEthTmIsSuspect24h        TruthValue,

        -- Ethernet traffic mgmt 15m
        pmEthTmCurrentIngressGreenFrameCount    Counter64,
        pmEthTmCurrentIngressYellowFrameCount   Counter64,
        pmEthTmCurrentIngressRedFrameCount      Counter64,
        pmEthTmCurrentIngressGreenOctetCount    Counter64,
        pmEthTmCurrentIngressYellowOctetCount   Counter64,
        pmEthTmCurrentIngressRedOctetCount      Counter64,
        pmEthTmCurrentEgressGreenFrameCount     Counter64,
        pmEthTmCurrentEgressGreenOctetCount     Counter64,
        pmEthTmCurrentGreenFrameDiscards        Counter64,
        pmEthTmCurrentYellowFrameDiscards       Counter64,
        pmEthTmCurrentGreenOctetDiscards        Counter64,
        pmEthTmCurrentYellowOctetDiscards       Counter64,

        -- Ethernet traffic mgmt 24h
        pmEthTmCurrent24hIngressGreenFrameCount Counter64,
        pmEthTmCurrent24hIngressYellowFrameCount        Counter64,
        pmEthTmCurrent24hIngressRedFrameCount   Counter64,
        pmEthTmCurrent24hIngressGreenOctetCount Counter64,
        pmEthTmCurrent24hIngressYellowOctetCount        Counter64,
        pmEthTmCurrent24hIngressRedOctetCount   Counter64,
        pmEthTmCurrent24hEgressGreenFrameCount  Counter64,
        pmEthTmCurrent24hEgressGreenOctetCount  Counter64,
        pmEthTmCurrent24hGreenFrameDiscards     Counter64,
        pmEthTmCurrent24hYellowFrameDiscards    Counter64,
        pmEthTmCurrent24hGreenOctetDiscards     Counter64,
        pmEthTmCurrent24hYellowOctetDiscards    Counter64,

        pmEthTmObjectProperty   ObjectProperty,
        pmEthTmInternalReference Unsigned32,

        pmEthTmIdentifier DisplayString }

pmEthTmIndex OBJECT-TYPE
    SYNTAX      Unsigned32 (1..2147483647)
    MAX-ACCESS  read-only
    STATUS      current
    DESCRIPTION
        "An arbitrary index assigned to each if entry.

"
    ::= { pmEthTmEntry 1 }

pmEthTmName OBJECT-TYPE
    SYNTAX      MgmtNameString
    MAX-ACCESS  read-only
    STATUS      current
    DESCRIPTION
        "The management name of the interface, for
        example 'mrt:1:2:1-2'.

"
    ::= { pmEthTmEntry 2 }

pmEthTmSubrack OBJECT-TYPE
    SYNTAX      SubrackNumber
    MAX-ACCESS  read-only
    STATUS      current
    DESCRIPTION
        "The number of the subrack where the interface
        is located.

"
    ::= { pmEthTmEntry 3 }

pmEthTmSlot OBJECT-TYPE
    SYNTAX      SlotNumber
    MAX-ACCESS  read-only
    STATUS      current
    DESCRIPTION
        "The number of the slot where the interface is
        located.

"
    ::= { pmEthTmEntry 4 }

pmEthTmPort OBJECT-TYPE
    SYNTAX      PortNumber
    MAX-ACCESS  read-only
    STATUS      current
    DESCRIPTION
        "The number of the TX port for the interface.

"
    ::= { pmEthTmEntry 5 }

pmEthTmPmReportMode OBJECT-TYPE
    SYNTAX      INTEGER {
                    off (1),
                    on (2) }
    MAX-ACCESS  read-write
    STATUS      current
    DESCRIPTION
        "The mode PM reporting on the interface.

        off - PM reporting is inactive.

        on - PM reporting is activated.

"
    DEFVAL { on }
    ::= { pmEthTmEntry 6 }

pmEthTmRxPort OBJECT-TYPE
    SYNTAX      PortNumber
    MAX-ACCESS  read-only
    STATUS      current
    DESCRIPTION
        "The number of the RX port for the interface.

"
    ::= { pmEthTmEntry 7 }

pmEthTmReset15Min OBJECT-TYPE
    SYNTAX      INTEGER {
                    normal (1),
                    reset (2) }
    MAX-ACCESS  read-write
    STATUS      current
    DESCRIPTION
        "Reset the 15 minute PM counters for the
        interface.

        After a successful reset the default value
        (normal) is restored in this action attribute.

        Usage: set reset15m reset

"
    DEFVAL { normal }
    ::= { pmEthTmEntry 8 }

pmEthTmReset24H OBJECT-TYPE
    SYNTAX      INTEGER {
                    normal (1),
                    reset (2) }
    MAX-ACCESS  read-write
    STATUS      current
    DESCRIPTION
        "Reset the 24 hour PM counters for the interface.

        After a successful reset the default value
        (normal) is restored in this action attribute.

        Usage: set reset24h reset

"
    DEFVAL { normal }
    ::= {    pmEthTmEntry 9 }

pmEthTmAdminStatus OBJECT-TYPE
    SYNTAX  INTEGER {
        down (1),
        service (2),
        up (3) }
    MAX-ACCESS read-write
    STATUS  current
    DESCRIPTION
         "Administrative state for the PM object.

         down - Alarms are not sent.

         up - Alarms are sent

         service - Alarms are not sent

"
     DEFVAL { up }
     ::= { pmEthTmEntry 10 }

pmEthTmOperStatus OBJECT-TYPE
    SYNTAX  INTEGER {
        notPresent (1),
        down (2),
        up (3) }
    MAX-ACCESS read-only
    STATUS  current
    DESCRIPTION
         "The operational state for the PM object.

         notPresent - The physical resource is not available.

         down - The object is disabled.

         up - The object is enabled.

"
     DEFVAL { notPresent }
     ::= { pmEthTmEntry 11 }

pmEthTmIsSuspect15Min OBJECT-TYPE
    SYNTAX  TruthValue
    MAX-ACCESS  read-only
    STATUS  current
    DESCRIPTION
       "This variable indicates if the data for this
        interface is suspect. The current interval may
        for example contain measurements for a part of
        the interval.

"
    ::= { pmEthTmEntry 12 }

pmEthTmIsSuspect24h OBJECT-TYPE
    SYNTAX  TruthValue
    MAX-ACCESS  read-only
    STATUS  current
    DESCRIPTION
       "This variable indicates if the data for this
        interface is suspect. The current interval may
        for example contain measurements for a part of
        the interval.

"
    ::= { pmEthTmEntry 13 }

pmEthTmCurrentIngressGreenFrameCount OBJECT-TYPE
    SYNTAX Counter64
    MAX-ACCESS read-only
    STATUS current
    DESCRIPTION
        "The amount of green frames sent by the ingress UNI
        during a particular 15 minute interval.
"
    ::= {pmEthTmEntry 14 }

pmEthTmCurrentIngressYellowFrameCount OBJECT-TYPE
    SYNTAX Counter64
    MAX-ACCESS read-only
    STATUS current
    DESCRIPTION
        "The amount of yellow frames sent by the ingress UNI
        during a particular 15 minute interval.
"
    ::= {pmEthTmEntry 15 }

pmEthTmCurrentIngressRedFrameCount OBJECT-TYPE
    SYNTAX Counter64
    MAX-ACCESS read-only
    STATUS current
    DESCRIPTION
        "The amount of red frames sent by the ingress UNI
        during a particular 15 minute interval.
"
    ::= {pmEthTmEntry 16 }

pmEthTmCurrentIngressGreenOctetCount OBJECT-TYPE
    SYNTAX Counter64
    MAX-ACCESS read-only
    STATUS current
    DESCRIPTION
        "The amount of green octets sent by the ingress UNI
        during a particular 15 minute interval.
"
    ::= {pmEthTmEntry 17 }

pmEthTmCurrentIngressYellowOctetCount OBJECT-TYPE
    SYNTAX Counter64
    MAX-ACCESS read-only
    STATUS current
    DESCRIPTION
        "The amount of yellow octets sent by the ingress UNI
        during a particular 15 minute interval.
"
    ::= {pmEthTmEntry 18 }

pmEthTmCurrentIngressRedOctetCount OBJECT-TYPE
    SYNTAX Counter64
    MAX-ACCESS read-only
    STATUS current
    DESCRIPTION
        "The amount of red octets sent by the ingress UNI
        during a particular 15 minute interval.
"
    ::= {pmEthTmEntry 19 }

pmEthTmCurrentEgressGreenFrameCount OBJECT-TYPE
    SYNTAX Counter64
    MAX-ACCESS read-only
    STATUS current
    DESCRIPTION
        "The amount of green frames received by the egress UNI
        during a particular 15 minute interval.
"
    ::= {pmEthTmEntry 20 }

pmEthTmCurrentEgressGreenOctetCount OBJECT-TYPE
    SYNTAX Counter64
    MAX-ACCESS read-only
    STATUS current
    DESCRIPTION
        "The amount of green octets received by the egress UNI
        during a particular 15 minute interval.
"
    ::= {pmEthTmEntry 21 }

pmEthTmCurrentGreenFrameDiscards OBJECT-TYPE
    SYNTAX Counter64
    MAX-ACCESS read-only
    STATUS current
    DESCRIPTION
        "The amount of green frames discarded due to congestion
        during a particular 15 minute interval.
"
    ::= {pmEthTmEntry 22 }

pmEthTmCurrentYellowFrameDiscards OBJECT-TYPE
    SYNTAX Counter64
    MAX-ACCESS read-only
    STATUS current
    DESCRIPTION
        "The amount of yellow frames discarded due to congestion
        during a particular 15 minute interval.
"
    ::= {pmEthTmEntry 23 }

pmEthTmCurrentGreenOctetDiscards OBJECT-TYPE
    SYNTAX Counter64
    MAX-ACCESS read-only
    STATUS current
    DESCRIPTION
        "The amount of green octets discarded due to congestion
        during a particular 15 minute interval.
"
    ::= {pmEthTmEntry 24 }

pmEthTmCurrentYellowOctetDiscards OBJECT-TYPE
    SYNTAX Counter64
    MAX-ACCESS read-only
    STATUS current
    DESCRIPTION
        "The amount of yellow octets discarded due to congestion
        during a particular 15 minute interval.
"
    ::= {pmEthTmEntry 25 }

pmEthTmCurrent24hIngressGreenFrameCount OBJECT-TYPE
    SYNTAX Counter64
    MAX-ACCESS read-only
    STATUS current
    DESCRIPTION
        "The amount of green frames sent by the ingress UNI
        during a particular 24 hour interval.
"
    ::= {pmEthTmEntry 26 }

pmEthTmCurrent24hIngressYellowFrameCount OBJECT-TYPE
    SYNTAX Counter64
    MAX-ACCESS read-only
    STATUS current
    DESCRIPTION
        "The amount of yellow frames sent by the ingress UNI
        during a particular 24 hour interval.
"
    ::= {pmEthTmEntry 27 }

pmEthTmCurrent24hIngressRedFrameCount OBJECT-TYPE
    SYNTAX Counter64
    MAX-ACCESS read-only
    STATUS current
    DESCRIPTION
        "The amount of red frames sent by the ingress UNI
        during a particular 24 hour interval.
"
    ::= {pmEthTmEntry 28 }

pmEthTmCurrent24hIngressGreenOctetCount OBJECT-TYPE
    SYNTAX Counter64
    MAX-ACCESS read-only
    STATUS current
    DESCRIPTION
        "The amount of green octets sent by the ingress UNI
        during a particular 24 hour interval.
"
    ::= {pmEthTmEntry 29 }

pmEthTmCurrent24hIngressYellowOctetCount OBJECT-TYPE
    SYNTAX Counter64
    MAX-ACCESS read-only
    STATUS current
    DESCRIPTION
        "The amount of yellow octets sent by the ingress UNI
        during a particular 24 hour interval.
"
    ::= {pmEthTmEntry 30 }

pmEthTmCurrent24hIngressRedOctetCount OBJECT-TYPE
    SYNTAX Counter64
    MAX-ACCESS read-only
    STATUS current
    DESCRIPTION
        "The amount of red octets sent by the ingress UNI
        during a particular 24 hour interval.
"
    ::= {pmEthTmEntry 31 }

pmEthTmCurrent24hEgressGreenFrameCount OBJECT-TYPE
    SYNTAX Counter64
    MAX-ACCESS read-only
    STATUS current
    DESCRIPTION
        "The amount of green frames received by the egress UNI
        during a particular 24 hour interval.
"
    ::= {pmEthTmEntry 32 }

pmEthTmCurrent24hEgressGreenOctetCount OBJECT-TYPE
    SYNTAX Counter64
    MAX-ACCESS read-only
    STATUS current
    DESCRIPTION
        "The amount of green octets received by the egress UNI
        during a particular 24 hour interval.
"
    ::= {pmEthTmEntry 33 }

pmEthTmCurrent24hGreenFrameDiscards OBJECT-TYPE
    SYNTAX Counter64
    MAX-ACCESS read-only
    STATUS current
    DESCRIPTION
        "The amount of green frames discarded due to congestion
        during a particular 24 hour interval.
"
    ::= {pmEthTmEntry 34 }

pmEthTmCurrent24hYellowFrameDiscards OBJECT-TYPE
    SYNTAX Counter64
    MAX-ACCESS read-only
    STATUS current
    DESCRIPTION
        "The amount of yellow frames discarded due to congestion
        during a particular 24 hour interval.
"
    ::= {pmEthTmEntry 35 }

pmEthTmCurrent24hGreenOctetDiscards OBJECT-TYPE
    SYNTAX Counter64
    MAX-ACCESS read-only
    STATUS current
    DESCRIPTION
        "The amount of green octets discarded due to congestion
        during a particular 24 hour interval.
"
    ::= {pmEthTmEntry 36 }

pmEthTmCurrent24hYellowOctetDiscards OBJECT-TYPE
    SYNTAX Counter64
    MAX-ACCESS read-only
    STATUS current
    DESCRIPTION
        "The amount of yellow octets discarded due to congestion
        during a particular 24 hour interval.
"
    ::= {pmEthTmEntry 37 }

pmEthTmObjectProperty  OBJECT-TYPE
    SYNTAX      ObjectProperty
    MAX-ACCESS  read-only
    STATUS      current
    DESCRIPTION
        "Property mask.

"
    ::= { pmEthTmEntry 38 }

pmEthTmInternalReference OBJECT-TYPE
    SYNTAX      Unsigned32 (0..2147483647)
    MAX-ACCESS  read-create
    STATUS      current
    DESCRIPTION
        "For internal use only.

"
    DEFVAL { 0 }
    ::= { pmEthTmEntry 39 }

pmEthTmIdentifier OBJECT-TYPE
    SYNTAX      DisplayString
    MAX-ACCESS  read-create
    STATUS      current
    DESCRIPTION
        "Unique identifier for the EVC.

"
    DEFVAL { "" }
    ::= { pmEthTmEntry 40 }

-- ----------------------------------------------------
-- Ethernet OAM PM
-- ----------------------------------------------------

pmEthOamTable OBJECT-TYPE
    SYNTAX  SEQUENCE OF PmEthOamEntry
    MAX-ACCESS  not-accessible
    STATUS  obsolete
    DESCRIPTION
     "The pm interface table."
::= { pmEthOamList 1 }

pmEthOamEntry OBJECT-TYPE
    SYNTAX  PmEthOamEntry
    MAX-ACCESS  not-accessible
    STATUS  current
    DESCRIPTION
        "An entry in interface table.

"
    INDEX   { pmEthOamIndex }
::= { pmEthOamTable 1 }

PmEthOamEntry ::=
    SEQUENCE {
        pmEthOamIndex               Unsigned32,
        pmEthOamName                MgmtNameString,
        pmEthOamSubrack             SubrackNumber,
        pmEthOamSlot                SlotNumber,
        pmEthOamPort                PortNumber,
        pmEthOamPmReportMode        INTEGER,
        pmEthOamRxPort              PortNumber,
        pmEthOamReset15Min          INTEGER,
        pmEthOamReset24H            INTEGER,
        pmEthOamAdminStatus         INTEGER,
        pmEthOamOperStatus          INTEGER,
        pmEthOamIsSuspect15Min      TruthValue,
        pmEthOamIsSuspect24h        TruthValue,

        -- Ethernet OAM 15m
        pmEthOamCurrentTwoWayFrameDelay Gauge32,
        pmEthOamCurrentTwoWayFrameDelayVariation        Gauge32,
        pmEthOamCurrentFrameLossRatioNearEnd    Gauge32,
        pmEthOamCurrentFrameLossRatioFarEnd     Gauge32,
        pmEthOamCurrentUnavailabilityNearEnd    Gauge32,
        pmEthOamCurrentUnavailabilityFarEnd     Gauge32,

        -- Ethernet OAM 24h
        pmEthOamCurrent24hTwoWayFrameDelay      Gauge32,
        pmEthOamCurrent24hTwoWayFrameDelayVariation     Gauge32,
        pmEthOamCurrent24hFrameLossRatioNearEnd Gauge32,
        pmEthOamCurrent24hFrameLossRatioFarEnd  Gauge32,
        pmEthOamCurrent24hUnavailabilityNearEnd Gauge32,
        pmEthOamCurrent24hUnavailabilityFarEnd  Gauge32,

        pmEthOamObjectProperty  ObjectProperty,
        pmEthOamInternalReference Unsigned32,

        pmEthOamIdentifier DisplayString,
        pmEthOamUsedPercentOfFrames Unsigned32,
        pmEthOamFrameLossRatioUnavailableThreshold Unsigned32,

        -- Ethernet OAM 15m
        pmEthOamCurrentOneWayFrameDelayVariation Gauge32,

        -- Ethernet OAM 24h
        pmEthOamCurrent24hOneWayFrameDelayVariation Gauge32 }


pmEthOamIndex OBJECT-TYPE
    SYNTAX      Unsigned32 (1..2147483647)
    MAX-ACCESS  read-only
    STATUS      current
    DESCRIPTION
        "An arbitrary index assigned to each if entry.

"
    ::= { pmEthOamEntry 1 }

pmEthOamName OBJECT-TYPE
    SYNTAX      MgmtNameString
    MAX-ACCESS  read-only
    STATUS      current
    DESCRIPTION
        "The management name of the interface, for
        example 'mrt:1:2:1-2'.

"
    ::= { pmEthOamEntry 2 }

pmEthOamSubrack OBJECT-TYPE
    SYNTAX      SubrackNumber
    MAX-ACCESS  read-only
    STATUS      current
    DESCRIPTION
        "The number of the subrack where the interface
        is located.

"
    ::= { pmEthOamEntry 3 }

pmEthOamSlot OBJECT-TYPE
    SYNTAX      SlotNumber
    MAX-ACCESS  read-only
    STATUS      current
    DESCRIPTION
        "The number of the slot where the interface is
        located.

"
    ::= { pmEthOamEntry 4 }

pmEthOamPort OBJECT-TYPE
    SYNTAX      PortNumber
    MAX-ACCESS  read-only
    STATUS      current
    DESCRIPTION
        "The number of the TX port for the interface.

"
    ::= { pmEthOamEntry 5 }

pmEthOamPmReportMode OBJECT-TYPE
    SYNTAX      INTEGER {
                    off (1),
                    on (2) }
    MAX-ACCESS  read-write
    STATUS      current
    DESCRIPTION
        "The mode PM reporting on the interface.

        off - PM reporting is inactive.

        on - PM reporting is activated.

"
    DEFVAL { on }
    ::= { pmEthOamEntry 6 }

pmEthOamRxPort OBJECT-TYPE
    SYNTAX      PortNumber
    MAX-ACCESS  read-only
    STATUS      current
    DESCRIPTION
        "The number of the RX port for the interface.

"
    ::= { pmEthOamEntry 7 }

pmEthOamReset15Min OBJECT-TYPE
    SYNTAX      INTEGER {
                    normal (1),
                    reset (2) }
    MAX-ACCESS  read-write
    STATUS      current
    DESCRIPTION
        "Reset the 15 minute PM counters for the
        interface.

        After a successful reset the default value
        (normal) is restored in this action attribute.

        Usage: set reset15m reset

"
    DEFVAL { normal }
    ::= { pmEthOamEntry 8 }

pmEthOamReset24H OBJECT-TYPE
    SYNTAX      INTEGER {
                    normal (1),
                    reset (2) }
    MAX-ACCESS  read-write
    STATUS      current
    DESCRIPTION
        "Reset the 24 hour PM counters for the interface.

        After a successful reset the default value
        (normal) is restored in this action attribute.

        Usage: set reset24h reset

"
    DEFVAL { normal }
    ::= {    pmEthOamEntry 9 }

pmEthOamAdminStatus OBJECT-TYPE
    SYNTAX  INTEGER {
        down (1),
        service (2),
        up (3) }
    MAX-ACCESS read-write
    STATUS  current
    DESCRIPTION
         "Administrative state for the PM object.

         down - Alarms are not sent.

         up - Alarms are sent

         service - Alarms are not sent

"
     DEFVAL { up }
     ::= { pmEthOamEntry 10 }

pmEthOamOperStatus OBJECT-TYPE
    SYNTAX  INTEGER {
        notPresent (1),
        down (2),
        up (3) }
    MAX-ACCESS read-only
    STATUS  current
    DESCRIPTION
         "The operational state for the PM object.

         notPresent - The physical resource is not available.

         down - The object is disabled.

         up - The object is enabled.

"
     DEFVAL { notPresent }
     ::= { pmEthOamEntry 11 }

pmEthOamIsSuspect15Min OBJECT-TYPE
    SYNTAX  TruthValue
    MAX-ACCESS  read-only
    STATUS  current
    DESCRIPTION
       "This variable indicates if the data for this
        interface is suspect. The current interval may
        for example contain measurements for a part of
        the interval.

"
    ::= { pmEthOamEntry 12 }

pmEthOamIsSuspect24h OBJECT-TYPE
    SYNTAX  TruthValue
    MAX-ACCESS  read-only
    STATUS  current
    DESCRIPTION
       "This variable indicates if the data for this
        interface is suspect. The current interval may
        for example contain measurements for a part of
        the interval.

"
    ::= { pmEthOamEntry 13 }

pmEthOamCurrentTwoWayFrameDelay OBJECT-TYPE
    SYNTAX Gauge32
    MAX-ACCESS read-only
    STATUS current
    DESCRIPTION
        "The time requeired to transmit a service frame from source to destination
        during a particular 15 minute interval.
"
    ::= {pmEthOamEntry 14 }

pmEthOamCurrentTwoWayFrameDelayVariation OBJECT-TYPE
    SYNTAX Gauge32
    MAX-ACCESS read-only
    STATUS current
    DESCRIPTION
        "The difference in delay between two service frames
        during a particular 15 minute interval.
"
    ::= {pmEthOamEntry 15 }

pmEthOamCurrentFrameLossRatioNearEnd OBJECT-TYPE
    SYNTAX Gauge32
    MAX-ACCESS read-only
    STATUS current
    DESCRIPTION
        "The number of service frames not delivered divided by the total number of service frames at near end
        during a particular 15 minute interval.
"
    ::= {pmEthOamEntry 16 }

pmEthOamCurrentFrameLossRatioFarEnd OBJECT-TYPE
    SYNTAX Gauge32
    MAX-ACCESS read-only
    STATUS current
    DESCRIPTION
        "The number of service frames not delivered divided by the total number of service frames at far end
        during a particular 15 minute interval.
"
    ::= {pmEthOamEntry 17 }

pmEthOamCurrentUnavailabilityNearEnd OBJECT-TYPE
    SYNTAX Gauge32
    MAX-ACCESS read-only
    STATUS current
    DESCRIPTION
        "The @todo
        during a particular 15 minute interval.
"
    ::= {pmEthOamEntry 18 }

pmEthOamCurrentUnavailabilityFarEnd OBJECT-TYPE
    SYNTAX Gauge32
    MAX-ACCESS read-only
    STATUS current
    DESCRIPTION
        "The @todo
        during a particular 15 minute interval.
"
    ::= {pmEthOamEntry 19 }

pmEthOamCurrent24hTwoWayFrameDelay OBJECT-TYPE
    SYNTAX Gauge32
    MAX-ACCESS read-only
    STATUS current
    DESCRIPTION
        "The time required to transmit a servic frame source to destination
        during a particular 24 hour interval.
"
    ::= {pmEthOamEntry 20 }

pmEthOamCurrent24hTwoWayFrameDelayVariation OBJECT-TYPE
    SYNTAX Gauge32
    MAX-ACCESS read-only
    STATUS current
    DESCRIPTION
        "The difference in delay of two service frames
        during a particular 24 hour interval.
"
    ::= {pmEthOamEntry 21 }

pmEthOamCurrent24hFrameLossRatioNearEnd OBJECT-TYPE
    SYNTAX Gauge32
    MAX-ACCESS read-only
    STATUS current
    DESCRIPTION
        "The number of service frames not delivered divided by the total number of service frames at near end
        during a particular 24 hour interval.
"
    ::= {pmEthOamEntry 22 }

pmEthOamCurrent24hFrameLossRatioFarEnd OBJECT-TYPE
    SYNTAX Gauge32
    MAX-ACCESS read-only
    STATUS current
    DESCRIPTION
        "The number of service frames not delivered divided by the total number of service frames at far end
        during a particular 24 hour interval.
"
    ::= {pmEthOamEntry 23 }

pmEthOamCurrent24hUnavailabilityNearEnd OBJECT-TYPE
    SYNTAX Gauge32
    MAX-ACCESS read-only
    STATUS current
    DESCRIPTION
        "The @todo
        during a particular 24 hour interval.
"
    ::= {pmEthOamEntry 24 }

pmEthOamCurrent24hUnavailabilityFarEnd OBJECT-TYPE
    SYNTAX Gauge32
    MAX-ACCESS read-only
    STATUS current
    DESCRIPTION
        "The @todo
        during a particular 24 hour interval.
"
    ::= {pmEthOamEntry 25 }

pmEthOamObjectProperty  OBJECT-TYPE
    SYNTAX      ObjectProperty
    MAX-ACCESS  read-only
    STATUS      current
    DESCRIPTION
        "Property mask.

"
    ::= { pmEthOamEntry 26 }

pmEthOamInternalReference OBJECT-TYPE
    SYNTAX      Unsigned32 (0..2147483647)
    MAX-ACCESS  read-create
    STATUS      current
    DESCRIPTION
        "For internal use only.

"
    DEFVAL { 0 }
    ::= { pmEthOamEntry 27 }

pmEthOamIdentifier OBJECT-TYPE
    SYNTAX      DisplayString
    MAX-ACCESS  read-create
    STATUS      current
    DESCRIPTION
        "Unique identifier for the EVC.

"
    DEFVAL { "" }
    ::= { pmEthOamEntry 28 }

pmEthOamUsedPercentOfFrames OBJECT-TYPE
    SYNTAX      Unsigned32 (0..100)
    MAX-ACCESS  read-write
    STATUS      current
    DESCRIPTION
        ".

"
    DEFVAL { 95 }
    ::= { pmEthOamEntry 29 }

pmEthOamFrameLossRatioUnavailableThreshold OBJECT-TYPE
    SYNTAX      Unsigned32 (0..1000000)
    MAX-ACCESS  read-write
    STATUS      current
    DESCRIPTION
        ".

"
    DEFVAL { 10000 }
    ::= { pmEthOamEntry 30 }

pmEthOamCurrentOneWayFrameDelayVariation OBJECT-TYPE
    SYNTAX Gauge32
    MAX-ACCESS read-only
    STATUS current
    DESCRIPTION
        "The difference in delay between two service frames
        during a particular 15 minute interval.
"
    ::= {pmEthOamEntry 31 }

pmEthOamCurrent24hOneWayFrameDelayVariation OBJECT-TYPE
    SYNTAX Gauge32
    MAX-ACCESS read-only
    STATUS current
    DESCRIPTION
        "The difference in delay of two service frames
        during a particular 24 hour interval.
"
    ::= {pmEthOamEntry 32 }


-- ----------------------------------------------------
-- Ethernet Drop
-- ----------------------------------------------------

pmEthDropTable OBJECT-TYPE
    SYNTAX  SEQUENCE OF PmEthDropEntry
    MAX-ACCESS  not-accessible
    STATUS  current
    DESCRIPTION
     "The ethernet drop counters table. Each port has a number of continuous
     (free running) drop counters. The counters are reset when the traffic
     unit reboots or when the attribute resetCont are set to reset."
::= { pmEthDropList 1 }

pmEthDropEntry OBJECT-TYPE
    SYNTAX  PmEthDropEntry
    MAX-ACCESS  not-accessible
    STATUS  current
    DESCRIPTION
        "An entry in interface table.

"
    INDEX   { pmEthDropIndex }
::= { pmEthDropTable 1 }

PmEthDropEntry ::=
    SEQUENCE {
        pmEthDropIndex               Unsigned32,
        pmEthDropName                MgmtNameString,
        pmEthDropSubrack             SubrackNumber,
        pmEthDropSlot                SlotNumber,
        pmEthDropPort                PortNumber,
        pmEthDropRxPort              PortNumber,
        pmEthDropResetCont           INTEGER,

        pmEthDropFrames              Counter64,
        pmEthDropBytes               Counter64,
        pmEthDropYellowFrames        Counter64,
        pmEthDropRedFrames           Counter64,
        pmEthDropFrames15m           Counter64,
        pmEthDropBytes15m            Counter64,
        pmEthDropYellowFrames15m     Counter64,
        pmEthDropRedFrames15m        Counter64,
        pmEthDropFrames24h           Counter64,
        pmEthDropBytes24h            Counter64,
        pmEthDropYellowFrames24h     Counter64,
        pmEthDropRedFrames24h        Counter64,
        pmEthDropFramesQ1            Counter64,
        pmEthDropBytesQ1             Counter64,
        pmEthDropFramesQ2            Counter64,
        pmEthDropBytesQ2             Counter64,
        pmEthDropFramesQ3            Counter64,
        pmEthDropBytesQ3             Counter64,
        pmEthDropFramesQ4            Counter64,
        pmEthDropBytesQ4             Counter64,
        pmEthDropFramesQ5            Counter64,
        pmEthDropBytesQ5             Counter64,
        pmEthDropFramesQ6            Counter64,
        pmEthDropBytesQ6             Counter64,
        pmEthDropFramesQ7            Counter64,
        pmEthDropBytesQ7             Counter64,
        pmEthDropFramesQ8            Counter64,
        pmEthDropBytesQ8             Counter64,
        pmEthDropFrames15mQ1         Counter64,
        pmEthDropBytes15mQ1          Counter64,
        pmEthDropFrames15mQ2         Counter64,
        pmEthDropBytes15mQ2          Counter64,
        pmEthDropFrames15mQ3         Counter64,
        pmEthDropBytes15mQ3          Counter64,
        pmEthDropFrames15mQ4         Counter64,
        pmEthDropBytes15mQ4          Counter64,
        pmEthDropFrames15mQ5         Counter64,
        pmEthDropBytes15mQ5          Counter64,
        pmEthDropFrames15mQ6         Counter64,
        pmEthDropBytes15mQ6          Counter64,
        pmEthDropFrames15mQ7         Counter64,
        pmEthDropBytes15mQ7          Counter64,
        pmEthDropFrames15mQ8         Counter64,
        pmEthDropBytes15mQ8          Counter64,
        pmEthDropFrames24hQ1         Counter64,
        pmEthDropBytes24hQ1          Counter64,
        pmEthDropFrames24hQ2         Counter64,
        pmEthDropBytes24hQ2          Counter64,
        pmEthDropFrames24hQ3         Counter64,
        pmEthDropBytes24hQ3          Counter64,
        pmEthDropFrames24hQ4         Counter64,
        pmEthDropBytes24hQ4          Counter64,
        pmEthDropFrames24hQ5         Counter64,
        pmEthDropBytes24hQ5          Counter64,
        pmEthDropFrames24hQ6         Counter64,
        pmEthDropBytes24hQ6          Counter64,
        pmEthDropFrames24hQ7         Counter64,
        pmEthDropBytes24hQ7          Counter64,
        pmEthDropFrames24hQ8         Counter64,
        pmEthDropBytes24hQ8          Counter64,
        pmEthDropIfNo                PortNumber,
        pmEthDropUpPortId            Integer32,
        pmEthDropReset15m            INTEGER,
        pmEthDropReset24h            INTEGER,
        pmEthDropReportMode          INTEGER,
        pmEthDropIsSuspect15Min      TruthValue,
        pmEthDropIsSuspect24H        TruthValue}

pmEthDropIndex OBJECT-TYPE
    SYNTAX      Unsigned32 (1..2147483647)
    MAX-ACCESS  read-only
    STATUS      current
    DESCRIPTION
        "An arbitrary index assigned to each if entry.

"
    ::= { pmEthDropEntry 1 }

pmEthDropName OBJECT-TYPE
    SYNTAX      MgmtNameString
    MAX-ACCESS  read-only
    STATUS      current
    DESCRIPTION
        "The management name of the interface, for
        example 'port:1:2:1-2'.
        (port:[subrack]:[slot]:[Tx port]-[Rx port]).

"
    ::= { pmEthDropEntry 2 }

pmEthDropSubrack OBJECT-TYPE
    SYNTAX      SubrackNumber
    MAX-ACCESS  read-only
    STATUS      current
    DESCRIPTION
        "The number of the subrack where the interface
        is located.

"
    ::= { pmEthDropEntry 3 }

pmEthDropSlot OBJECT-TYPE
    SYNTAX      SlotNumber
    MAX-ACCESS  read-only
    STATUS      current
    DESCRIPTION
        "The number of the slot where the interface is
        located.

"
    ::= { pmEthDropEntry 4 }

pmEthDropPort OBJECT-TYPE
    SYNTAX      PortNumber
    MAX-ACCESS  read-only
    STATUS      current
    DESCRIPTION
        "The number of the Tx port for the interface.

"
    ::= { pmEthDropEntry 5 }

pmEthDropRxPort OBJECT-TYPE
    SYNTAX      PortNumber
    MAX-ACCESS  read-only
    STATUS      current
    DESCRIPTION
        "The number of the Rx port for the interface.

"
    ::= { pmEthDropEntry 6 }

pmEthDropResetCont OBJECT-TYPE
    SYNTAX      INTEGER {
                    normal (1),
                    reset (2) }
    MAX-ACCESS  read-write
    STATUS      current
    DESCRIPTION
        "Reset the continuous (free running) drop counters.

        After a successful reset the default value
        (normal) is restored in this action attribute.

        Usage: set reset24h reset

"
    DEFVAL { normal }
    ::= { pmEthDropEntry 7 }

pmEthDropFrames OBJECT-TYPE
     SYNTAX Counter64
     MAX-ACCESS read-only
     STATUS current
     DESCRIPTION
        "The total number of dropped continuous frames on the port.

"
    ::= { pmEthDropEntry 8 }

pmEthDropBytes OBJECT-TYPE
     SYNTAX Counter64
     MAX-ACCESS read-only
     STATUS current
     DESCRIPTION
        "The total number of dropped continuous bytes on the port.

"
    ::= { pmEthDropEntry 9 }

pmEthDropYellowFrames OBJECT-TYPE
     SYNTAX Counter64
     MAX-ACCESS read-only
     STATUS current
     DESCRIPTION
        "The total number of dropped continuous yellow frames on the port.

"
    ::= { pmEthDropEntry 10 }

pmEthDropRedFrames OBJECT-TYPE
     SYNTAX Counter64
     MAX-ACCESS read-only
     STATUS current
     DESCRIPTION
        "The total number of dropped continuous red frames on the port.

"
    ::= { pmEthDropEntry 11 }

pmEthDropFramesQ1 OBJECT-TYPE
     SYNTAX Counter64
     MAX-ACCESS read-only
     STATUS current
     DESCRIPTION
        "The number of dropped continuous frames for queue 1 on the port.

"
    ::= { pmEthDropEntry 12 }

pmEthDropBytesQ1 OBJECT-TYPE
     SYNTAX Counter64
     MAX-ACCESS read-only
     STATUS current
     DESCRIPTION
        "The number of dropped continuous bytes for queue 1 on the port.

"
    ::= { pmEthDropEntry 13 }

pmEthDropFramesQ2 OBJECT-TYPE
     SYNTAX Counter64
     MAX-ACCESS read-only
     STATUS current
     DESCRIPTION
        "The number of dropped continuous frames for queue 2 on the port.

"
    ::= { pmEthDropEntry 14 }

pmEthDropBytesQ2 OBJECT-TYPE
     SYNTAX Counter64
     MAX-ACCESS read-only
     STATUS current
     DESCRIPTION
        "The number of dropped continuous bytes for queue 2 on the port.

"
    ::= { pmEthDropEntry 15 }

pmEthDropFramesQ3 OBJECT-TYPE
     SYNTAX Counter64
     MAX-ACCESS read-only
     STATUS current
     DESCRIPTION
        "The number of dropped continuous frames for queue 3 on the port.

"
    ::= { pmEthDropEntry 16 }

pmEthDropBytesQ3 OBJECT-TYPE
     SYNTAX Counter64
     MAX-ACCESS read-only
     STATUS current
     DESCRIPTION
        "The number of dropped continuous bytes for queue 3 on the port.

"
    ::= { pmEthDropEntry 17 }

pmEthDropFramesQ4 OBJECT-TYPE
     SYNTAX Counter64
     MAX-ACCESS read-only
     STATUS current
     DESCRIPTION
        "The number of dropped continuous frames for queue 4 on the port.

"
    ::= { pmEthDropEntry 18 }

pmEthDropBytesQ4 OBJECT-TYPE
     SYNTAX Counter64
     MAX-ACCESS read-only
     STATUS current
     DESCRIPTION
        "The number of dropped continuous bytes for queue 4 on the port.

"
    ::= { pmEthDropEntry 19 }

pmEthDropFramesQ5 OBJECT-TYPE
     SYNTAX Counter64
     MAX-ACCESS read-only
     STATUS current
     DESCRIPTION
        "The number of dropped continuous frames for queue 5 on the port.

"
    ::= { pmEthDropEntry 20 }

pmEthDropBytesQ5 OBJECT-TYPE
     SYNTAX Counter64
     MAX-ACCESS read-only
     STATUS current
     DESCRIPTION
        "The number of dropped continuous bytes for queue 5 on the port.

"
    ::= { pmEthDropEntry 21 }

pmEthDropFramesQ6 OBJECT-TYPE
     SYNTAX Counter64
     MAX-ACCESS read-only
     STATUS current
     DESCRIPTION
        "The number of dropped continuous frames for queue 6 on the port.

"
    ::= { pmEthDropEntry 22 }

pmEthDropBytesQ6 OBJECT-TYPE
     SYNTAX Counter64
     MAX-ACCESS read-only
     STATUS current
     DESCRIPTION
        "The number of dropped continuous bytes for queue 6 on the port.

"
    ::= { pmEthDropEntry 23 }

pmEthDropFramesQ7 OBJECT-TYPE
     SYNTAX Counter64
     MAX-ACCESS read-only
     STATUS current
     DESCRIPTION
        "The number of dropped continuous frames for queue 7 on the port.

"
    ::= { pmEthDropEntry 24 }

pmEthDropBytesQ7 OBJECT-TYPE
     SYNTAX Counter64
     MAX-ACCESS read-only
     STATUS current
     DESCRIPTION
        "The number of dropped continuous bytes for queue 7 on the port.

"
    ::= { pmEthDropEntry 25 }

pmEthDropFramesQ8 OBJECT-TYPE
     SYNTAX Counter64
     MAX-ACCESS read-only
     STATUS current
     DESCRIPTION
        "The number of dropped continuous frames for queue 8 on the port.

"
    ::= { pmEthDropEntry 26 }

pmEthDropBytesQ8 OBJECT-TYPE
     SYNTAX Counter64
     MAX-ACCESS read-only
     STATUS current
     DESCRIPTION
        "The number of dropped continuous bytes for queue 8 on the port.

"
    ::= { pmEthDropEntry 27 }

pmEthDropIfNo OBJECT-TYPE
    SYNTAX      PortNumber
    MAX-ACCESS  read-only
    STATUS      current
    DESCRIPTION
        "The interface number of the port.

"
    ::= { pmEthDropEntry 28 }

pmEthDropUpPortId OBJECT-TYPE
    SYNTAX      Integer32   (-1..2147483647)
    MAX-ACCESS  read-only
    STATUS      current
    DESCRIPTION
        "Internal port reference for traffic unit.
"
    ::= { pmEthDropEntry 29 }

pmEthDropFrames15m OBJECT-TYPE
     SYNTAX Counter64
     MAX-ACCESS read-only
     STATUS current
     DESCRIPTION
        "The number of dropped 15m frames on the port.
        The 15m period is fixed, a new period is started four times every hour: 00m, 15m, 30m, and 45m.

"
    ::= { pmEthDropEntry 30 }

pmEthDropBytes15m OBJECT-TYPE
     SYNTAX Counter64
     MAX-ACCESS read-only
     STATUS current
     DESCRIPTION
        "The number of dropped 15m bytes on the port.
        The 15m period is fixed, a new period is started four times every hour: 00m, 15m, 30m, and 45m.

"
    ::= { pmEthDropEntry 31 }

pmEthDropYellowFrames15m OBJECT-TYPE
     SYNTAX Counter64
     MAX-ACCESS read-only
     STATUS current
     DESCRIPTION
        "The number of dropped 15m yellow frames on the port.
        The 15m period is fixed, a new period is started four times every hour: 00m, 15m, 30m, and 45m.

"
    ::= { pmEthDropEntry 32 }

pmEthDropRedFrames15m OBJECT-TYPE
     SYNTAX Counter64
     MAX-ACCESS read-only
     STATUS current
     DESCRIPTION
        "The number of dropped 15m red frames on the port.
        The 15m period is fixed, a new period is started four times every hour: 00m, 15m, 30m, and 45m.

"
    ::= { pmEthDropEntry 33 }

pmEthDropFrames24h OBJECT-TYPE
     SYNTAX Counter64
     MAX-ACCESS read-only
     STATUS current
     DESCRIPTION
        "The number of dropped 24h frames on the port.
        The 24h period is fixed, a new period starts at midnight, 12:00 a.m., 00.00.

"
    ::= { pmEthDropEntry 34 }

pmEthDropBytes24h OBJECT-TYPE
     SYNTAX Counter64
     MAX-ACCESS read-only
     STATUS current
     DESCRIPTION
        "The number of dropped 24h bytes on the port.
        The 24h period is fixed, a new period starts at midnight, 12:00 a.m., 00.00.

"
    ::= { pmEthDropEntry 35 }

pmEthDropYellowFrames24h OBJECT-TYPE
     SYNTAX Counter64
     MAX-ACCESS read-only
     STATUS current
     DESCRIPTION
        "The number of dropped 24h yellow frames on the port.
        The 24h period is fixed, a new period starts at midnight, 12:00 a.m., 00.00.

"
    ::= { pmEthDropEntry 36 }

pmEthDropRedFrames24h OBJECT-TYPE
     SYNTAX Counter64
     MAX-ACCESS read-only
     STATUS current
     DESCRIPTION
        "The number of dropped 24h red frames on the port.
        The 24h period is fixed, a new period starts at midnight, 12:00 a.m., 00.00.

"
    ::= { pmEthDropEntry 37 }

pmEthDropFrames15mQ1 OBJECT-TYPE
     SYNTAX Counter64
     MAX-ACCESS read-only
     STATUS current
     DESCRIPTION
        "The number of dropped frames for 15m queue 1 on the port.
        The 15m period is fixed, a new period is started four times every hour: 00m, 15m, 30m, and 45m.

"
    ::= { pmEthDropEntry 38 }

pmEthDropBytes15mQ1 OBJECT-TYPE
     SYNTAX Counter64
     MAX-ACCESS read-only
     STATUS current
     DESCRIPTION
        "The number of dropped bytes for 15m queue 1 on the port.
        The 15m period is fixed, a new period is started four times every hour: 00m, 15m, 30m, and 45m.

"
    ::= { pmEthDropEntry 39 }

pmEthDropFrames24hQ1 OBJECT-TYPE
     SYNTAX Counter64
     MAX-ACCESS read-only
     STATUS current
     DESCRIPTION
        "The number of dropped frames for 24h queue 1 on the port.
        The 24h period is fixed, a new period starts at midnight, 12:00 a.m., 00.00.

"
    ::= { pmEthDropEntry 40 }

pmEthDropBytes24hQ1 OBJECT-TYPE
     SYNTAX Counter64
     MAX-ACCESS read-only
     STATUS current
     DESCRIPTION
        "The number of dropped bytes for 24h queue 1 on the port.
        The 24h period is fixed, a new period starts at midnight, 12:00 a.m., 00.00.

"
    ::= { pmEthDropEntry 41 }

pmEthDropFrames15mQ2 OBJECT-TYPE
     SYNTAX Counter64
     MAX-ACCESS read-only
     STATUS current
     DESCRIPTION
        "The number of dropped frames for 15m queue 2 on the port.
        The 15m period is fixed, a new period is started four times every hour: 00m, 15m, 30m, and 45m.

"
    ::= { pmEthDropEntry 42 }

pmEthDropBytes15mQ2 OBJECT-TYPE
     SYNTAX Counter64
     MAX-ACCESS read-only
     STATUS current
     DESCRIPTION
        "The number of dropped bytes for 15m queue 2 on the port.
        The 15m period is fixed, a new period is started four times every hour: 00m, 15m, 30m, and 45m.

"
    ::= { pmEthDropEntry 43 }

pmEthDropFrames24hQ2 OBJECT-TYPE
     SYNTAX Counter64
     MAX-ACCESS read-only
     STATUS current
     DESCRIPTION
        "The number of dropped frames for 24h queue 2 on the port.
        The 24h period is fixed, a new period starts at midnight, 12:00 a.m., 00.00.

"
    ::= { pmEthDropEntry 44 }

pmEthDropBytes24hQ2 OBJECT-TYPE
     SYNTAX Counter64
     MAX-ACCESS read-only
     STATUS current
     DESCRIPTION
        "The number of dropped bytes for 24h queue 2 on the port.
        The 24h period is fixed, a new period starts at midnight, 12:00 a.m., 00.00.

"
    ::= { pmEthDropEntry 45 }

pmEthDropFrames15mQ3 OBJECT-TYPE
     SYNTAX Counter64
     MAX-ACCESS read-only
     STATUS current
     DESCRIPTION
        "The number of dropped frames for 15m queue 3 on the port.
        The 15m period is fixed, a new period is started four times every hour: 00m, 15m, 30m, and 45m.

"
    ::= { pmEthDropEntry 46 }

pmEthDropBytes15mQ3 OBJECT-TYPE
     SYNTAX Counter64
     MAX-ACCESS read-only
     STATUS current
     DESCRIPTION
        "The number of dropped bytes for 15m queue 3 on the port.
        The 15m period is fixed, a new period is started four times every hour: 00m, 15m, 30m, and 45m.

"
    ::= { pmEthDropEntry 47 }

pmEthDropFrames24hQ3 OBJECT-TYPE
     SYNTAX Counter64
     MAX-ACCESS read-only
     STATUS current
     DESCRIPTION
        "The number of dropped frames for 24h queue 3 on the port.
        The 24h period is fixed, a new period starts at midnight, 12:00 a.m., 00.00.

"
    ::= { pmEthDropEntry 48 }

pmEthDropBytes24hQ3 OBJECT-TYPE
     SYNTAX Counter64
     MAX-ACCESS read-only
     STATUS current
     DESCRIPTION
        "The number of dropped bytes for 24h queue 3 on the port.
        The 24h period is fixed, a new period starts at midnight, 12:00 a.m., 00.00.

"
    ::= { pmEthDropEntry 49 }

pmEthDropFrames15mQ4 OBJECT-TYPE
     SYNTAX Counter64
     MAX-ACCESS read-only
     STATUS current
     DESCRIPTION
        "The number of dropped frames for 15m queue 4 on the port.
        The 15m period is fixed, a new period is started four times every hour: 00m, 15m, 30m, and 45m.

"
    ::= { pmEthDropEntry 50 }

pmEthDropBytes15mQ4 OBJECT-TYPE
     SYNTAX Counter64
     MAX-ACCESS read-only
     STATUS current
     DESCRIPTION
        "The number of dropped bytes for 15m queue 4 on the port.
        The 15m period is fixed, a new period is started four times every hour: 00m, 15m, 30m, and 45m.

"
    ::= { pmEthDropEntry 51 }

pmEthDropFrames24hQ4 OBJECT-TYPE
     SYNTAX Counter64
     MAX-ACCESS read-only
     STATUS current
     DESCRIPTION
        "The number of dropped frames for 24h queue 4 on the port.
        The 24h period is fixed, a new period starts at midnight, 12:00 a.m., 00.00.

"
    ::= { pmEthDropEntry 52 }

pmEthDropBytes24hQ4 OBJECT-TYPE
     SYNTAX Counter64
     MAX-ACCESS read-only
     STATUS current
     DESCRIPTION
        "The number of dropped bytes for 24h queue 4 on the port.
        The 24h period is fixed, a new period starts at midnight, 12:00 a.m., 00.00.

"
    ::= { pmEthDropEntry 53 }

pmEthDropFrames15mQ5 OBJECT-TYPE
     SYNTAX Counter64
     MAX-ACCESS read-only
     STATUS current
     DESCRIPTION
        "The number of dropped frames for 15m queue 5 on the port.
        The 15m period is fixed, a new period is started four times every hour: 00m, 15m, 30m, and 45m.

"
    ::= { pmEthDropEntry 54 }

pmEthDropBytes15mQ5 OBJECT-TYPE
     SYNTAX Counter64
     MAX-ACCESS read-only
     STATUS current
     DESCRIPTION
        "The number of dropped bytes for 15m queue 5 on the port.
        The 15m period is fixed, a new period is started four times every hour: 00m, 15m, 30m, and 45m.

"
    ::= { pmEthDropEntry 55 }

pmEthDropFrames24hQ5 OBJECT-TYPE
     SYNTAX Counter64
     MAX-ACCESS read-only
     STATUS current
     DESCRIPTION
        "The number of dropped frames for 24h queue 5 on the port.
        The 24h period is fixed, a new period starts at midnight, 12:00 a.m., 00.00.

"
    ::= { pmEthDropEntry 56 }

pmEthDropBytes24hQ5 OBJECT-TYPE
     SYNTAX Counter64
     MAX-ACCESS read-only
     STATUS current
     DESCRIPTION
        "The number of dropped bytes for 24h queue 5 on the port.
        The 24h period is fixed, a new period starts at midnight, 12:00 a.m., 00.00.

"
    ::= { pmEthDropEntry 57 }

pmEthDropFrames15mQ6 OBJECT-TYPE
     SYNTAX Counter64
     MAX-ACCESS read-only
     STATUS current
     DESCRIPTION
        "The number of dropped frames for 15m queue 6 on the port.
        The 15m period is fixed, a new period is started four times every hour: 00m, 15m, 30m, and 45m.

"
    ::= { pmEthDropEntry 58 }

pmEthDropBytes15mQ6 OBJECT-TYPE
     SYNTAX Counter64
     MAX-ACCESS read-only
     STATUS current
     DESCRIPTION
        "The number of dropped bytes for 15m queue 6 on the port.
        The 15m period is fixed, a new period is started four times every hour: 00m, 15m, 30m, and 45m.

"
    ::= { pmEthDropEntry 59 }

pmEthDropFrames24hQ6 OBJECT-TYPE
     SYNTAX Counter64
     MAX-ACCESS read-only
     STATUS current
     DESCRIPTION
        "The number of dropped frames for 24h queue 6 on the port.
        The 24h period is fixed, a new period starts at midnight, 12:00 a.m., 00.00.

"
    ::= { pmEthDropEntry 60 }

pmEthDropBytes24hQ6 OBJECT-TYPE
     SYNTAX Counter64
     MAX-ACCESS read-only
     STATUS current
     DESCRIPTION
        "The number of dropped bytes for 24h queue 6 on the port.
        The 24h period is fixed, a new period starts at midnight, 12:00 a.m., 00.00.

"
    ::= { pmEthDropEntry 61 }

pmEthDropFrames15mQ7 OBJECT-TYPE
     SYNTAX Counter64
     MAX-ACCESS read-only
     STATUS current
     DESCRIPTION
        "The number of dropped frames for 15m queue 7 on the port.
        The 15m period is fixed, a new period is started four times every hour: 00m, 15m, 30m, and 45m.

"
    ::= { pmEthDropEntry 62 }

pmEthDropBytes15mQ7 OBJECT-TYPE
     SYNTAX Counter64
     MAX-ACCESS read-only
     STATUS current
     DESCRIPTION
        "The number of dropped bytes for 15m queue 7 on the port.
        The 15m period is fixed, a new period is started four times every hour: 00m, 15m, 30m, and 45m.

"
    ::= { pmEthDropEntry 63 }

pmEthDropFrames24hQ7 OBJECT-TYPE
     SYNTAX Counter64
     MAX-ACCESS read-only
     STATUS current
     DESCRIPTION
        "The number of dropped frames for 24h queue 7 on the port.
        The 24h period is fixed, a new period starts at midnight, 12:00 a.m., 00.00.

"
    ::= { pmEthDropEntry 64 }

pmEthDropBytes24hQ7 OBJECT-TYPE
     SYNTAX Counter64
     MAX-ACCESS read-only
     STATUS current
     DESCRIPTION
        "The number of dropped bytes for 24h queue 7 on the port.
        The 24h period is fixed, a new period starts at midnight, 12:00 a.m., 00.00.

"
    ::= { pmEthDropEntry 65 }

pmEthDropFrames15mQ8 OBJECT-TYPE
     SYNTAX Counter64
     MAX-ACCESS read-only
     STATUS current
     DESCRIPTION
        "The number of dropped frames for 15m queue 8 on the port.
        The 15m period is fixed, a new period is started four times every hour: 00m, 15m, 30m, and 45m.

"
    ::= { pmEthDropEntry 66 }

pmEthDropBytes15mQ8 OBJECT-TYPE
     SYNTAX Counter64
     MAX-ACCESS read-only
     STATUS current
     DESCRIPTION
        "The number of dropped bytes for 15m queue 8 on the port.
        The 15m period is fixed, a new period is started four times every hour: 00m, 15m, 30m, and 45m.

"
    ::= { pmEthDropEntry 67 }

pmEthDropFrames24hQ8 OBJECT-TYPE
     SYNTAX Counter64
     MAX-ACCESS read-only
     STATUS current
     DESCRIPTION
        "The number of dropped frames for 24h queue 8 on the port.
        The 24h period is fixed, a new period starts at midnight, 12:00 a.m., 00.00.

"
    ::= { pmEthDropEntry 68 }

pmEthDropBytes24hQ8 OBJECT-TYPE
     SYNTAX Counter64
     MAX-ACCESS read-only
     STATUS current
     DESCRIPTION
        "The number of dropped bytes for 24h queue 8 on the port.
        The 24h period is fixed, a new period starts at midnight, 12:00 a.m., 00.00.

"
    ::= { pmEthDropEntry 69 }

pmEthDropReset15m OBJECT-TYPE
    SYNTAX      INTEGER {
                    normal (1),
                    reset (2) }
    MAX-ACCESS  read-write
    STATUS      current
    DESCRIPTION
        "Reset the 15 minutes drop counters.

        After a successful reset the default value
        (normal) is restored in this action attribute.

        Usage: set reset15m reset

"
    DEFVAL { normal }
    ::= { pmEthDropEntry 70 }

pmEthDropReset24h OBJECT-TYPE
    SYNTAX      INTEGER {
                    normal (1),
                    reset (2) }
    MAX-ACCESS  read-write
    STATUS      current
    DESCRIPTION
        "Reset the 24 hours drop counters.

        After a successful reset the default value
        (normal) is restored in this action attribute.

        Usage: set reset24h reset

"
    DEFVAL { normal }
    ::= { pmEthDropEntry 71 }

pmEthDropReportMode OBJECT-TYPE
    SYNTAX      INTEGER {
                    off (1),
                    on (2) }
    MAX-ACCESS  read-write
    STATUS      current
    DESCRIPTION
        "The mode for PM reporting to file on the interface.

        off - PM reporting is inactive.

        on - PM reporting is activated.


"
    DEFVAL { on }
    ::= { pmEthDropEntry 72 }

pmEthDropIsSuspect15Min OBJECT-TYPE
    SYNTAX  TruthValue
    MAX-ACCESS  read-only
    STATUS  current
    DESCRIPTION
       "This variable indicates if the data for this
        interface is suspect. The current interval may
        for example only contain measurements for a part of
        the interval.

"
    ::= { pmEthDropEntry 73 }

pmEthDropIsSuspect24H OBJECT-TYPE
    SYNTAX  TruthValue
    MAX-ACCESS  read-only
    STATUS  current
    DESCRIPTION
       "This variable indicates if the data for this
        interface is suspect. The current interval may
        for example only contain measurements for a part of
        the interval.

"
    ::= { pmEthDropEntry 74 }


-- ----------------------------------------------------
-- Ethernet Egress
-- ----------------------------------------------------

pmEthEgressTable OBJECT-TYPE
    SYNTAX  SEQUENCE OF PmEthEgressEntry
    MAX-ACCESS  not-accessible
    STATUS  current
    DESCRIPTION
     "The ethernet egress counters table. Each port has a number of continuous
     (free running) counters. The counters are reset when the traffic
     unit reboots or when the attribute resetCont, reset15m or reset24h are set to reset."
::= { pmEthEgressList 1 }

pmEthEgressEntry OBJECT-TYPE
    SYNTAX  PmEthEgressEntry
    MAX-ACCESS  not-accessible
    STATUS  current
    DESCRIPTION
        "An entry in interface table.

"
    INDEX   { pmEthEgressIndex }
::= { pmEthEgressTable 1 }

PmEthEgressEntry ::=
    SEQUENCE {
        pmEthEgressIndex             Unsigned32,
        pmEthEgressName              MgmtNameString,
        pmEthEgressSubrack           SubrackNumber,
        pmEthEgressSlot              SlotNumber,
        pmEthEgressIfNo              PortNumber,
        pmEthEgressPort              PortNumber,
        pmEthEgressRxPort            PortNumber,
        pmEthEgressUpPortId          Integer32,

        pmEthEgressResetCont         INTEGER,
        pmEthEgressReset15m          INTEGER,
        pmEthEgressReset24h          INTEGER,

        pmEthEgressFramesQ1          Counter64,
        pmEthEgressBytesQ1           Counter64,
        pmEthEgressBandwidthQ1       Counter64,
        pmEthEgressFrames15mQ1       Counter64,
        pmEthEgressBytes15mQ1        Counter64,
        pmEthEgressFrames24hQ1       Counter64,
        pmEthEgressBytes24hQ1        Counter64,

        pmEthEgressFramesQ2          Counter64,
        pmEthEgressBytesQ2           Counter64,
        pmEthEgressBandwidthQ2       Counter64,
        pmEthEgressFrames15mQ2       Counter64,
        pmEthEgressBytes15mQ2        Counter64,
        pmEthEgressFrames24hQ2       Counter64,
        pmEthEgressBytes24hQ2        Counter64,

        pmEthEgressFramesQ3          Counter64,
        pmEthEgressBytesQ3           Counter64,
        pmEthEgressBandwidthQ3       Counter64,
        pmEthEgressFrames15mQ3       Counter64,
        pmEthEgressBytes15mQ3        Counter64,
        pmEthEgressFrames24hQ3       Counter64,
        pmEthEgressBytes24hQ3        Counter64,

        pmEthEgressFramesQ4          Counter64,
        pmEthEgressBytesQ4           Counter64,
        pmEthEgressBandwidthQ4       Counter64,
        pmEthEgressFrames15mQ4       Counter64,
        pmEthEgressBytes15mQ4        Counter64,
        pmEthEgressFrames24hQ4       Counter64,
        pmEthEgressBytes24hQ4        Counter64,

        pmEthEgressFramesQ5          Counter64,
        pmEthEgressBytesQ5           Counter64,
        pmEthEgressBandwidthQ5       Counter64,
        pmEthEgressFrames15mQ5       Counter64,
        pmEthEgressBytes15mQ5        Counter64,
        pmEthEgressFrames24hQ5       Counter64,
        pmEthEgressBytes24hQ5        Counter64,

        pmEthEgressFramesQ6          Counter64,
        pmEthEgressBytesQ6           Counter64,
        pmEthEgressBandwidthQ6       Counter64,
        pmEthEgressFrames15mQ6       Counter64,
        pmEthEgressBytes15mQ6        Counter64,
        pmEthEgressFrames24hQ6       Counter64,
        pmEthEgressBytes24hQ6        Counter64,

        pmEthEgressFramesQ7          Counter64,
        pmEthEgressBytesQ7           Counter64,
        pmEthEgressBandwidthQ7       Counter64,
        pmEthEgressFrames15mQ7       Counter64,
        pmEthEgressBytes15mQ7        Counter64,
        pmEthEgressFrames24hQ7       Counter64,
        pmEthEgressBytes24hQ7        Counter64,

        pmEthEgressFramesQ8          Counter64,
        pmEthEgressBytesQ8           Counter64,
        pmEthEgressBandwidthQ8       Counter64,
        pmEthEgressFrames15mQ8       Counter64,
        pmEthEgressBytes15mQ8        Counter64,
        pmEthEgressFrames24hQ8       Counter64,
        pmEthEgressBytes24hQ8        Counter64,
        pmEthEgressReportMode        INTEGER,
        pmEthEgressIsSuspect15Min    TruthValue,
        pmEthEgressIsSuspect24H      TruthValue}

pmEthEgressIndex OBJECT-TYPE
    SYNTAX      Unsigned32 (1..2147483647)
    MAX-ACCESS  read-only
    STATUS      current
    DESCRIPTION
        "An arbitrary index assigned to each if entry.

"
    ::= { pmEthEgressEntry 1 }

pmEthEgressName OBJECT-TYPE
    SYNTAX      MgmtNameString
    MAX-ACCESS  read-only
    STATUS      current
    DESCRIPTION
        "The management name of the interface, for
        example 'port:1:2:1-2'.
        (port:[subrack]:[slot]:[Tx port]-[Rx port]).

"
    ::= { pmEthEgressEntry 2 }

pmEthEgressSubrack OBJECT-TYPE
    SYNTAX      SubrackNumber
    MAX-ACCESS  read-only
    STATUS      current
    DESCRIPTION
        "The number of the subrack where the interface
        is located.

"
    ::= { pmEthEgressEntry 3 }

pmEthEgressSlot OBJECT-TYPE
    SYNTAX      SlotNumber
    MAX-ACCESS  read-only
    STATUS      current
    DESCRIPTION
        "The number of the slot where the interface is
        located.

"
    ::= { pmEthEgressEntry 4 }

pmEthEgressIfNo OBJECT-TYPE
    SYNTAX      PortNumber
    MAX-ACCESS  read-only
    STATUS      current
    DESCRIPTION
        "The interface number of the port.

"
    ::= { pmEthEgressEntry 5 }

pmEthEgressPort OBJECT-TYPE
    SYNTAX      PortNumber
    MAX-ACCESS  read-only
    STATUS      current
    DESCRIPTION
        "The number of the Tx port for the interface.

"
    ::= { pmEthEgressEntry 6 }

pmEthEgressRxPort OBJECT-TYPE
    SYNTAX      PortNumber
    MAX-ACCESS  read-only
    STATUS      current
    DESCRIPTION
        "The number of the Rx port for the interface.

"
    ::= { pmEthEgressEntry 7 }

pmEthEgressUpPortId OBJECT-TYPE
    SYNTAX      Integer32   (-1..2147483647)
    MAX-ACCESS  read-only
    STATUS      current
    DESCRIPTION
        "Internal port reference for traffic unit.
"
    ::= { pmEthEgressEntry 8 }

pmEthEgressResetCont OBJECT-TYPE
    SYNTAX      INTEGER {
                    normal (1),
                    reset (2) }
    MAX-ACCESS  read-write
    STATUS      current
    DESCRIPTION
        "Reset the continuous (free running) egress counters.

        After a successful reset the default value
        (normal) is restored in this action attribute.

        Usage: set resetCont reset

"
    DEFVAL { normal }
    ::= { pmEthEgressEntry 9 }

pmEthEgressReset15m OBJECT-TYPE
    SYNTAX      INTEGER {
                    normal (1),
                    reset (2) }
    MAX-ACCESS  read-write
    STATUS      current
    DESCRIPTION
        "Reset the 15m egress counters.

        After a successful reset the default value
        (normal) is restored in this action attribute.

        Usage: set reset15m reset

"
    DEFVAL { normal }
    ::= { pmEthEgressEntry 10 }

pmEthEgressReset24h OBJECT-TYPE
    SYNTAX      INTEGER {
                    normal (1),
                    reset (2) }
    MAX-ACCESS  read-write
    STATUS      current
    DESCRIPTION
        "Reset the 24h egress counters.

        After a successful reset the default value
        (normal) is restored in this action attribute.

        Usage: set reset24hm reset

"
    DEFVAL { normal }
    ::= { pmEthEgressEntry 11 }

pmEthEgressFramesQ1 OBJECT-TYPE
     SYNTAX Counter64
     MAX-ACCESS read-only
     STATUS current
     DESCRIPTION
        "The number of continuous egress frames for queue 1 on the port.

"
    ::= { pmEthEgressEntry 12 }

pmEthEgressBytesQ1 OBJECT-TYPE
     SYNTAX Counter64
     MAX-ACCESS read-only
     STATUS current
     DESCRIPTION
        "The number of continuous egress bytes for queue 1 on the port.

"
    ::= { pmEthEgressEntry 13 }

pmEthEgressBandwidthQ1 OBJECT-TYPE
     SYNTAX Counter64
     MAX-ACCESS read-only
     STATUS current
     DESCRIPTION
        "The data rate bandwidth for queue 1 on the port, in kbps.

"
    ::= { pmEthEgressEntry 14 }

pmEthEgressFrames15mQ1 OBJECT-TYPE
     SYNTAX Counter64
     MAX-ACCESS read-only
     STATUS current
     DESCRIPTION
        "The number of 15m egress frames for queue 1 on the port.
        The 15m period is fixed, a new period is started four times every hour: 00m, 15m, 30m, and 45m.

"
    ::= { pmEthEgressEntry 15 }

pmEthEgressBytes15mQ1 OBJECT-TYPE
     SYNTAX Counter64
     MAX-ACCESS read-only
     STATUS current
     DESCRIPTION
        "The number of 15m egress bytes for queue 1 on the port.
        The 15m period is fixed, a new period is started four times every hour: 00m, 15m, 30m, and 45m.

"
    ::= { pmEthEgressEntry 16 }

pmEthEgressFrames24hQ1 OBJECT-TYPE
     SYNTAX Counter64
     MAX-ACCESS read-only
     STATUS current
     DESCRIPTION
        "The number of 24h egress frames for queue 1 on the port.
        The 24h period is fixed, a new period starts at midnight, 12:00 a.m., 00.00.

"
    ::= { pmEthEgressEntry 17 }

pmEthEgressBytes24hQ1 OBJECT-TYPE
     SYNTAX Counter64
     MAX-ACCESS read-only
     STATUS current
     DESCRIPTION
        "The number of 24h egress bytes for queue 1 on the port.
        The 24h period is fixed, a new period starts at midnight, 12:00 a.m., 00.00.

"
    ::= { pmEthEgressEntry 18 }

pmEthEgressFramesQ2 OBJECT-TYPE
     SYNTAX Counter64
     MAX-ACCESS read-only
     STATUS current
     DESCRIPTION
        "The number of continuous egress frames for queue 2 on the port.

"
    ::= { pmEthEgressEntry 19 }

pmEthEgressBytesQ2 OBJECT-TYPE
     SYNTAX Counter64
     MAX-ACCESS read-only
     STATUS current
     DESCRIPTION
        "The number of continuous egress bytes for queue 2 on the port.

"
    ::= { pmEthEgressEntry 20 }

pmEthEgressBandwidthQ2 OBJECT-TYPE
     SYNTAX Counter64
     MAX-ACCESS read-only
     STATUS current
     DESCRIPTION
        "The data rate bandwidth for queue 2 on the port, in kbps.

"
    ::= { pmEthEgressEntry 21 }

pmEthEgressFrames15mQ2 OBJECT-TYPE
     SYNTAX Counter64
     MAX-ACCESS read-only
     STATUS current
     DESCRIPTION
        "The number of 15m egress frames for queue 2 on the port.
        The 15m period is fixed, a new period is started four times every hour: 00m, 15m, 30m, and 45m.

"
    ::= { pmEthEgressEntry 22 }

pmEthEgressBytes15mQ2 OBJECT-TYPE
     SYNTAX Counter64
     MAX-ACCESS read-only
     STATUS current
     DESCRIPTION
        "The number of 15m egress bytes for queue 2 on the port.
        The 15m period is fixed, a new period is started four times every hour: 00m, 15m, 30m, and 45m.

"
    ::= { pmEthEgressEntry 23 }

pmEthEgressFrames24hQ2 OBJECT-TYPE
     SYNTAX Counter64
     MAX-ACCESS read-only
     STATUS current
     DESCRIPTION
        "The number of 24h egress frames for queue 2 on the port.
        The 24h period is fixed, a new period starts at midnight, 12:00 a.m., 00.00.

"
    ::= { pmEthEgressEntry 24 }

pmEthEgressBytes24hQ2 OBJECT-TYPE
     SYNTAX Counter64
     MAX-ACCESS read-only
     STATUS current
     DESCRIPTION
        "The number of 24h egress bytes for queue 2 on the port.
        The 24h period is fixed, a new period starts at midnight, 12:00 a.m., 00.00.

"
    ::= { pmEthEgressEntry 25 }

pmEthEgressFramesQ3 OBJECT-TYPE
     SYNTAX Counter64
     MAX-ACCESS read-only
     STATUS current
     DESCRIPTION
        "The number of continuous egress frames for queue 3 on the port.

"
    ::= { pmEthEgressEntry 26 }

pmEthEgressBytesQ3 OBJECT-TYPE
     SYNTAX Counter64
     MAX-ACCESS read-only
     STATUS current
     DESCRIPTION
        "The number of continuous egress bytes for queue 3 on the port.

"
    ::= { pmEthEgressEntry 27 }

pmEthEgressBandwidthQ3 OBJECT-TYPE
     SYNTAX Counter64
     MAX-ACCESS read-only
     STATUS current
     DESCRIPTION
        "The data rate bandwidth for queue 3 on the port, in kbps.

"
    ::= { pmEthEgressEntry 28 }

pmEthEgressFrames15mQ3 OBJECT-TYPE
     SYNTAX Counter64
     MAX-ACCESS read-only
     STATUS current
     DESCRIPTION
        "The number of 15m egress frames for queue 3 on the port.
        The 15m period is fixed, a new period is started four times every hour: 00m, 15m, 30m, and 45m.

"
    ::= { pmEthEgressEntry 29 }

pmEthEgressBytes15mQ3 OBJECT-TYPE
     SYNTAX Counter64
     MAX-ACCESS read-only
     STATUS current
     DESCRIPTION
        "The number of 15m egress bytes for queue 3 on the port.
        The 15m period is fixed, a new period is started four times every hour: 00m, 15m, 30m, and 45m.

"
    ::= { pmEthEgressEntry 30 }

pmEthEgressFrames24hQ3 OBJECT-TYPE
     SYNTAX Counter64
     MAX-ACCESS read-only
     STATUS current
     DESCRIPTION
        "The number of 24h egress frames for queue 3 on the port.
        The 24h period is fixed, a new period starts at midnight, 12:00 a.m., 00.00.

"
    ::= { pmEthEgressEntry 31 }

pmEthEgressBytes24hQ3 OBJECT-TYPE
     SYNTAX Counter64
     MAX-ACCESS read-only
     STATUS current
     DESCRIPTION
        "The number of 24h egress bytes for queue 3 on the port.
        The 24h period is fixed, a new period starts at midnight, 12:00 a.m., 00.00.

"
    ::= { pmEthEgressEntry 32 }

pmEthEgressFramesQ4 OBJECT-TYPE
     SYNTAX Counter64
     MAX-ACCESS read-only
     STATUS current
     DESCRIPTION
        "The number of continuous egress frames for queue 4 on the port.

"
    ::= { pmEthEgressEntry 33 }

pmEthEgressBytesQ4 OBJECT-TYPE
     SYNTAX Counter64
     MAX-ACCESS read-only
     STATUS current
     DESCRIPTION
        "The number of continuous egress bytes for queue 4 on the port.

"
    ::= { pmEthEgressEntry 34 }

pmEthEgressBandwidthQ4 OBJECT-TYPE
     SYNTAX Counter64
     MAX-ACCESS read-only
     STATUS current
     DESCRIPTION
        "The data rate bandwidth for queue 4 on the port, in kbps.

"
    ::= { pmEthEgressEntry 35 }

pmEthEgressFrames15mQ4 OBJECT-TYPE
     SYNTAX Counter64
     MAX-ACCESS read-only
     STATUS current
     DESCRIPTION
        "The number of 15m egress frames for queue 4 on the port.
        The 15m period is fixed, a new period is started four times every hour: 00m, 15m, 30m, and 45m.

"
    ::= { pmEthEgressEntry 36 }

pmEthEgressBytes15mQ4 OBJECT-TYPE
     SYNTAX Counter64
     MAX-ACCESS read-only
     STATUS current
     DESCRIPTION
        "The number of 15m egress bytes for queue 4 on the port.
        The 15m period is fixed, a new period is started four times every hour: 00m, 15m, 30m, and 45m.

"
    ::= { pmEthEgressEntry 37 }

pmEthEgressFrames24hQ4 OBJECT-TYPE
     SYNTAX Counter64
     MAX-ACCESS read-only
     STATUS current
     DESCRIPTION
        "The number of 24h egress frames for queue 4 on the port.
        The 24h period is fixed, a new period starts at midnight, 12:00 a.m., 00.00.

"
    ::= { pmEthEgressEntry 38 }

pmEthEgressBytes24hQ4 OBJECT-TYPE
     SYNTAX Counter64
     MAX-ACCESS read-only
     STATUS current
     DESCRIPTION
        "The number of 24h egress bytes for queue 4 on the port.
        The 24h period is fixed, a new period starts at midnight, 12:00 a.m., 00.00.

"
    ::= { pmEthEgressEntry 39 }

pmEthEgressFramesQ5 OBJECT-TYPE
     SYNTAX Counter64
     MAX-ACCESS read-only
     STATUS current
     DESCRIPTION
        "The number of continuous egress frames for queue 5 on the port.

"
    ::= { pmEthEgressEntry 40 }

pmEthEgressBytesQ5 OBJECT-TYPE
     SYNTAX Counter64
     MAX-ACCESS read-only
     STATUS current
     DESCRIPTION
        "The number of continuous egress bytes for queue 5 on the port.

"
    ::= { pmEthEgressEntry 41 }

pmEthEgressBandwidthQ5 OBJECT-TYPE
     SYNTAX Counter64
     MAX-ACCESS read-only
     STATUS current
     DESCRIPTION
        "The data rate bandwidth for queue 5 on the port, in kbps.

"
    ::= { pmEthEgressEntry 42 }

pmEthEgressFrames15mQ5 OBJECT-TYPE
     SYNTAX Counter64
     MAX-ACCESS read-only
     STATUS current
     DESCRIPTION
        "The number of 15m egress frames for queue 5 on the port.
        The 15m period is fixed, a new period is started four times every hour: 00m, 15m, 30m, and 45m.

"
    ::= { pmEthEgressEntry 43 }

pmEthEgressBytes15mQ5 OBJECT-TYPE
     SYNTAX Counter64
     MAX-ACCESS read-only
     STATUS current
     DESCRIPTION
        "The number of 15m egress bytes for queue 5 on the port.
        The 15m period is fixed, a new period is started four times every hour: 00m, 15m, 30m, and 45m.

"
    ::= { pmEthEgressEntry 44 }

pmEthEgressFrames24hQ5 OBJECT-TYPE
     SYNTAX Counter64
     MAX-ACCESS read-only
     STATUS current
     DESCRIPTION
        "The number of 24h egress frames for queue 5 on the port.
        The 24h period is fixed, a new period starts at midnight, 12:00 a.m., 00.00.

"
    ::= { pmEthEgressEntry 45 }

pmEthEgressBytes24hQ5 OBJECT-TYPE
     SYNTAX Counter64
     MAX-ACCESS read-only
     STATUS current
     DESCRIPTION
        "The number of 24h egress bytes for queue 5 on the port.
        The 24h period is fixed, a new period starts at midnight, 12:00 a.m., 00.00.

"
    ::= { pmEthEgressEntry 46 }

pmEthEgressFramesQ6 OBJECT-TYPE
     SYNTAX Counter64
     MAX-ACCESS read-only
     STATUS current
     DESCRIPTION
        "The number of continuous egress frames for queue 6 on the port.

"
    ::= { pmEthEgressEntry 47 }

pmEthEgressBytesQ6 OBJECT-TYPE
     SYNTAX Counter64
     MAX-ACCESS read-only
     STATUS current
     DESCRIPTION
        "The number of continuous egress bytes for queue 6 on the port.

"
    ::= { pmEthEgressEntry 48 }

pmEthEgressBandwidthQ6 OBJECT-TYPE
     SYNTAX Counter64
     MAX-ACCESS read-only
     STATUS current
     DESCRIPTION
        "The data rate bandwidth for queue 6 on the port, in kbps.

"
    ::= { pmEthEgressEntry 49 }

pmEthEgressFrames15mQ6 OBJECT-TYPE
     SYNTAX Counter64
     MAX-ACCESS read-only
     STATUS current
     DESCRIPTION
        "The number of 15m egress frames for queue 6 on the port.
        The 15m period is fixed, a new period is started four times every hour: 00m, 15m, 30m, and 45m.

"
    ::= { pmEthEgressEntry 50 }

pmEthEgressBytes15mQ6 OBJECT-TYPE
     SYNTAX Counter64
     MAX-ACCESS read-only
     STATUS current
     DESCRIPTION
        "The number of 15m egress bytes for queue 6 on the port.
        The 15m period is fixed, a new period is started four times every hour: 00m, 15m, 30m, and 45m.

"
    ::= { pmEthEgressEntry 51 }

pmEthEgressFrames24hQ6 OBJECT-TYPE
     SYNTAX Counter64
     MAX-ACCESS read-only
     STATUS current
     DESCRIPTION
        "The number of 24h egress frames for queue 6 on the port.
        The 24h period is fixed, a new period starts at midnight, 12:00 a.m., 00.00.

"
    ::= { pmEthEgressEntry 52 }

pmEthEgressBytes24hQ6 OBJECT-TYPE
     SYNTAX Counter64
     MAX-ACCESS read-only
     STATUS current
     DESCRIPTION
        "The number of 24h egress bytes for queue 6 on the port.
        The 24h period is fixed, a new period starts at midnight, 12:00 a.m., 00.00.

"
    ::= { pmEthEgressEntry 53 }

pmEthEgressFramesQ7 OBJECT-TYPE
     SYNTAX Counter64
     MAX-ACCESS read-only
     STATUS current
     DESCRIPTION
        "The number of continuous egress frames for queue 7 on the port.

"
    ::= { pmEthEgressEntry 54 }

pmEthEgressBytesQ7 OBJECT-TYPE
     SYNTAX Counter64
     MAX-ACCESS read-only
     STATUS current
     DESCRIPTION
        "The number of continuous egress bytes for queue 7 on the port.

"
    ::= { pmEthEgressEntry 55 }

pmEthEgressBandwidthQ7 OBJECT-TYPE
     SYNTAX Counter64
     MAX-ACCESS read-only
     STATUS current
     DESCRIPTION
        "The data rate bandwidth for queue 7 on the port, in kbps.

"
    ::= { pmEthEgressEntry 56 }

pmEthEgressFrames15mQ7 OBJECT-TYPE
     SYNTAX Counter64
     MAX-ACCESS read-only
     STATUS current
     DESCRIPTION
        "The number of 15m egress frames for queue 7 on the port.
        The 15m period is fixed, a new period is started four times every hour: 00m, 15m, 30m, and 45m.

"
    ::= { pmEthEgressEntry 57 }

pmEthEgressBytes15mQ7 OBJECT-TYPE
     SYNTAX Counter64
     MAX-ACCESS read-only
     STATUS current
     DESCRIPTION
        "The number of 15m egress bytes for queue 7 on the port.
        The 15m period is fixed, a new period is started four times every hour: 00m, 15m, 30m, and 45m.

"
    ::= { pmEthEgressEntry 58 }

pmEthEgressFrames24hQ7 OBJECT-TYPE
     SYNTAX Counter64
     MAX-ACCESS read-only
     STATUS current
     DESCRIPTION
        "The number of 24h egress frames for queue 7 on the port.
        The 24h period is fixed, a new period starts at midnight, 12:00 a.m., 00.00.

"
    ::= { pmEthEgressEntry 59 }

pmEthEgressBytes24hQ7 OBJECT-TYPE
     SYNTAX Counter64
     MAX-ACCESS read-only
     STATUS current
     DESCRIPTION
        "The number of 24h egress bytes for queue 7 on the port.
        The 24h period is fixed, a new period starts at midnight, 12:00 a.m., 00.00.

"
    ::= { pmEthEgressEntry 60 }

pmEthEgressFramesQ8 OBJECT-TYPE
     SYNTAX Counter64
     MAX-ACCESS read-only
     STATUS current
     DESCRIPTION
        "The number of continuous egress frames for queue 8 on the port.

"
    ::= { pmEthEgressEntry 61 }

pmEthEgressBytesQ8 OBJECT-TYPE
     SYNTAX Counter64
     MAX-ACCESS read-only
     STATUS current
     DESCRIPTION
        "The number of continuous egress bytes for queue 8 on the port.

"
    ::= { pmEthEgressEntry 62 }

pmEthEgressBandwidthQ8 OBJECT-TYPE
     SYNTAX Counter64
     MAX-ACCESS read-only
     STATUS current
     DESCRIPTION
        "The data rate bandwidth for queue 8 on the port, in kbps.

"
    ::= { pmEthEgressEntry 63 }

pmEthEgressFrames15mQ8 OBJECT-TYPE
     SYNTAX Counter64
     MAX-ACCESS read-only
     STATUS current
     DESCRIPTION
        "The number of 15m egress frames for queue 8 on the port.
        The 15m period is fixed, a new period is started four times every hour: 00m, 15m, 30m, and 45m.

"
    ::= { pmEthEgressEntry 64 }

pmEthEgressBytes15mQ8 OBJECT-TYPE
     SYNTAX Counter64
     MAX-ACCESS read-only
     STATUS current
     DESCRIPTION
        "The number of 15m egress bytes for queue 8 on the port.
        The 15m period is fixed, a new period is started four times every hour: 00m, 15m, 30m, and 45m.

"
    ::= { pmEthEgressEntry 65 }

pmEthEgressFrames24hQ8 OBJECT-TYPE
     SYNTAX Counter64
     MAX-ACCESS read-only
     STATUS current
     DESCRIPTION
        "The number of 24h egress frames for queue 8 on the port.
        The 24h period is fixed, a new period starts at midnight, 12:00 a.m., 00.00.

"
    ::= { pmEthEgressEntry 66 }

pmEthEgressBytes24hQ8 OBJECT-TYPE
     SYNTAX Counter64
     MAX-ACCESS read-only
     STATUS current
     DESCRIPTION
        "The number of 24h egress bytes for queue 8 on the port.
        The 24h period is fixed, a new period starts at midnight, 12:00 a.m., 00.00.

"
    ::= { pmEthEgressEntry 67 }

pmEthEgressReportMode OBJECT-TYPE
    SYNTAX      INTEGER {
                    off (1),
                    on (2) }
    MAX-ACCESS  read-write
    STATUS      current
    DESCRIPTION
        "The mode for PM reporting to file on the interface.

        off - PM reporting is inactive.

        on - PM reporting is activated.

"
    DEFVAL { on }
    ::= { pmEthEgressEntry 68 }

pmEthEgressIsSuspect15Min OBJECT-TYPE
    SYNTAX  TruthValue
    MAX-ACCESS  read-only
    STATUS  current
    DESCRIPTION
       "This variable indicates if the data for this
        interface is suspect. The current interval may
        for example only contain measurements for a part of
        the interval.

"
    ::= { pmEthEgressEntry 69 }

pmEthEgressIsSuspect24H OBJECT-TYPE
    SYNTAX  TruthValue
    MAX-ACCESS  read-only
    STATUS  current
    DESCRIPTION
       "This variable indicates if the data for this
        interface is suspect. The current interval may
        for example only contain measurements for a part of
        the interval.

"
    ::= { pmEthEgressEntry 70 }


-- ----------------------------------------------------
-- Ethernet classification
-- ----------------------------------------------------

pmEthClassificationTable OBJECT-TYPE
    SYNTAX  SEQUENCE OF PmEthClassificationEntry
    MAX-ACCESS  not-accessible
    STATUS  current
    DESCRIPTION
     "The ethernet classification counters table. Each classification has two
     continuous (free running) counters. The counters are reset when the traffic
     unit reboots or when the attribute resetCont are set to reset."
::= { pmEthClassificationList 1 }

pmEthClassificationEntry OBJECT-TYPE
    SYNTAX  PmEthClassificationEntry
    MAX-ACCESS  not-accessible
    STATUS  current
    DESCRIPTION
        "An entry in interface table.
"
    INDEX   { pmEthClassificationIndex }
::= { pmEthClassificationTable 1 }

PmEthClassificationEntry ::=
    SEQUENCE {
        pmEthClassificationIndex               Unsigned32,
        pmEthClassificationName                MgmtNameString,
        pmEthClassificationSubrack             SubrackNumber,
        pmEthClassificationSlot                SlotNumber,
        pmEthClassificationIdentifier          DisplayString,
        pmEthClassificationResetCont           INTEGER,
        pmEthClassificationInternalReference   Unsigned32,

        pmEthClassificationCounter1          Counter64,
        pmEthClassificationCounter2          Counter64,
        pmEthClassificationCounter3          Counter64,
        pmEthClassificationCounter4          Counter64 }

pmEthClassificationIndex OBJECT-TYPE
    SYNTAX      Unsigned32 (1..2147483647)
    MAX-ACCESS  read-only
    STATUS      current
    DESCRIPTION
        "An arbitrary index assigned to each classification entry.
"
    ::= { pmEthClassificationEntry 1 }

pmEthClassificationName OBJECT-TYPE
    SYNTAX      MgmtNameString
    MAX-ACCESS  read-only
    STATUS      current
    DESCRIPTION
        "The management name of the interface, for
        example 'class:1:2:id1'.
        (class:[subrack]:[slot]:[identifier]).
"
    ::= { pmEthClassificationEntry 2 }

pmEthClassificationSubrack OBJECT-TYPE
    SYNTAX      SubrackNumber
    MAX-ACCESS  read-only
    STATUS      current
    DESCRIPTION
        "The number of the subrack where the interface is located.
"
    ::= { pmEthClassificationEntry 3 }

pmEthClassificationSlot OBJECT-TYPE
    SYNTAX      SlotNumber
    MAX-ACCESS  read-only
    STATUS      current
    DESCRIPTION
        "The number of the slot where the interface is located.
"
    ::= { pmEthClassificationEntry 4 }

pmEthClassificationIdentifier OBJECT-TYPE
    SYNTAX      DisplayString
    MAX-ACCESS  read-only
    STATUS      current
    DESCRIPTION
        "A unique identifier for the classification.
"
    ::= { pmEthClassificationEntry 5 }

pmEthClassificationResetCont OBJECT-TYPE
    SYNTAX      INTEGER {
                    normal (1),
                    reset (2) }
    MAX-ACCESS  read-write
    STATUS      current
    DESCRIPTION
        "Reset the continuous (free running) classification counters.

        After a successful reset the default value
        (normal) is restored in this action attribute.
"
    DEFVAL { normal }
    ::= { pmEthClassificationEntry 6 }

pmEthClassificationInternalReference OBJECT-TYPE
    SYNTAX      Unsigned32 (0..2147483647)
    MAX-ACCESS  read-create
    STATUS      current
    DESCRIPTION
        "For internal use only.
"
    DEFVAL { 0 }
    ::= { pmEthClassificationEntry 7 }

pmEthClassificationCounter1 OBJECT-TYPE
     SYNTAX Counter64
     MAX-ACCESS read-only
     STATUS current
     DESCRIPTION
        "Number of green and yellow frames in the classification.
"
    ::= { pmEthClassificationEntry 8 }

pmEthClassificationCounter2 OBJECT-TYPE
     SYNTAX Counter64
     MAX-ACCESS read-only
     STATUS current
     DESCRIPTION
        "Number of red (not delivered) frames in the classification.
"
    ::= { pmEthClassificationEntry 9 }

pmEthClassificationCounter3 OBJECT-TYPE
     SYNTAX Counter64
     MAX-ACCESS read-only
     STATUS current
     DESCRIPTION
        "Number of green and yellow bytes in the classification.
"
    ::= { pmEthClassificationEntry 10 }

pmEthClassificationCounter4 OBJECT-TYPE
     SYNTAX Counter64
     MAX-ACCESS read-only
     STATUS current
     DESCRIPTION
        "Number of red (not delivered) bytes in the classification.
"
    ::= { pmEthClassificationEntry 11 }

-- ----------------------------------------------------
-- Object and event groups
-- ----------------------------------------------------

pmGeneralGroup OBJECT-GROUP
    OBJECTS {
        pmGeneralLastChangeTime }
    STATUS      deprecated
    DESCRIPTION
        "The general objects."
    ::= { lumPmGroups 1 }

pmIntervalGroup OBJECT-GROUP
    OBJECTS {
        pmIntervalSubrack,
        pmIntervalSlot,
        pmIntervalPort,
        pmIntervalNumber,
        pmIntervalIsSuspect,
        pmIntervalRxES,
        pmIntervalRxSES,
        pmIntervalRxBBE,
        pmIntervalRxUAS,
        pmIntervalTxES,
        pmIntervalTxSES,
        pmIntervalTxBBE,
        pmIntervalTxUAS,
        pmIntervalName }
    STATUS      deprecated
    DESCRIPTION
        "The 15 minute interval objects."
    ::= { lumPmGroups 3 }

pmInterval24hGroup OBJECT-GROUP
    OBJECTS {
        pmInterval24hSubrack,
        pmInterval24hSlot,
        pmInterval24hPort,
        pmInterval24hNumber,
        pmInterval24hIsSuspect,
        pmInterval24hRxES,
        pmInterval24hRxSES,
        pmInterval24hRxBBE,
        pmInterval24hRxUAS,
        pmInterval24hTxES,
        pmInterval24hTxSES,
        pmInterval24hTxBBE,
        pmInterval24hTxUAS,
        pmInterval24hName }
    STATUS      deprecated
    DESCRIPTION
        "The 24 hour interval objects."
    ::= { lumPmGroups 5 }

pmIfGroup OBJECT-GROUP
    OBJECTS {
        pmIfIndex,
        pmIfName,
        pmIfSubrack,
        pmIfSlot,
        pmIfPort,
        pmIfPmReportMode,
        pmIfRxCurrentES,
        pmIfRxCurrentSES,
        pmIfRxCurrentBBE,
        pmIfRxCurrentUAS,
        pmIfTxCurrentES,
        pmIfTxCurrentSES,
        pmIfTxCurrentBBE,
        pmIfTxCurrentUAS,
        pmIfRx24hCurrentES,
        pmIfRx24hCurrentSES,
        pmIfRx24hCurrentBBE,
        pmIfRx24hCurrentUAS,
        pmIfTx24hCurrentES,
        pmIfTx24hCurrentSES,
        pmIfTx24hCurrentBBE,
        pmIfTx24hCurrentUAS }
    STATUS      deprecated
    DESCRIPTION
        "The pm interface configuration and current meters objects."
    ::= { lumPmGroups 6 }

pmLogGeneralGroup OBJECT-GROUP
    OBJECTS {
        pmLogGeneralLastChangeTime,
        pmLogGeneralSize,
        pmLogGeneralSize24h }
    STATUS      deprecated
    DESCRIPTION
        "The general log object."
    ::= { lumPmGroups 7 }

pmFileGroup OBJECT-GROUP
    OBJECTS {
        pmFileIndex,
        pmFileName,
        pmFileCreatedTime }
    STATUS      deprecated
    DESCRIPTION
        "The 15 minute interval file objects."
    ::= { lumPmGroups 8 }

pmFile24hGroup OBJECT-GROUP
    OBJECTS {
        pmFile24hIndex,
        pmFile24hName,
        pmFile24hCreatedTime }
    STATUS      deprecated
    DESCRIPTION
        "The 24 hour interval file objects."
    ::= { lumPmGroups 9 }

pmNotificationGroup NOTIFICATION-GROUP
    NOTIFICATIONS {
        pmFileAdded,
        pmFile24hAdded }
    STATUS      current
    DESCRIPTION
        "The pm notifications."
    ::= { lumPmGroups 10 }

pmIfGroupV2 OBJECT-GROUP
    OBJECTS {
        pmIfIndex,
        pmIfName,
        pmIfSubrack,
        pmIfSlot,
        pmIfPort,
        pmIfPmReportMode,
        pmIfRxCurrentES,
        pmIfRxCurrentSES,
        pmIfRxCurrentBBE,
        pmIfRxCurrentUAS,
        pmIfTxCurrentES,
        pmIfTxCurrentSES,
        pmIfTxCurrentBBE,
        pmIfTxCurrentUAS,
        pmIfRx24hCurrentES,
        pmIfRx24hCurrentSES,
        pmIfRx24hCurrentBBE,
        pmIfRx24hCurrentUAS,
        pmIfTx24hCurrentES,
        pmIfTx24hCurrentSES,
        pmIfTx24hCurrentBBE,
        pmIfTx24hCurrentUAS,
        pmIfRxESThreshold,
        pmIfRxSESThreshold,
        pmIfRxBBEThreshold,
        pmIfRxUASThreshold,
        pmIfTxESThreshold,
        pmIfTxSESThreshold,
        pmIfTxBBEThreshold,
        pmIfTxUASThreshold,
        pmIfRx24hESThreshold,
        pmIfRx24hSESThreshold,
        pmIfRx24hBBEThreshold,
        pmIfRx24hUASThreshold,
        pmIfTx24hESThreshold,
        pmIfTx24hSESThreshold,
        pmIfTx24hBBEThreshold,
        pmIfTx24hUASThreshold,
        pmIfRxES,
        pmIfRxSES,
        pmIfRxBBE,
        pmIfRxUAS,
        pmIfTxES,
        pmIfTxSES,
        pmIfTxBBE,
        pmIfTxUAS,
        pmIfRx24hES,
        pmIfRx24hSES,
        pmIfRx24hBBE,
        pmIfRx24hUAS,
        pmIfTx24hES,
        pmIfTx24hSES,
        pmIfTx24hBBE,
        pmIfTx24hUAS,
        pmIfRxPort }
    STATUS      deprecated
    DESCRIPTION
        "The pm interface configuration and current meters objects V2."
    ::= { lumPmGroups 11 }

pmGeneralGroupV2 OBJECT-GROUP
    OBJECTS {
        pmGeneralLastChangeTime,
        pmGeneralStateLastChangeTime }
    STATUS      deprecated
    DESCRIPTION
        "The general objects."
    ::= { lumPmGroups 12 }

pmControlGroup OBJECT-GROUP
    OBJECTS {
        pmControlReset15Min,
        pmControlReset24H }
    STATUS      deprecated
    DESCRIPTION
        "The control group."
    ::= { lumPmGroups 13 }

pmIfGroupV3 OBJECT-GROUP
    OBJECTS {
        pmIfIndex,
        pmIfName,
        pmIfSubrack,
        pmIfSlot,
        pmIfPort,
        pmIfPmReportMode,
        pmIfRxCurrentES,
        pmIfRxCurrentSES,
        pmIfRxCurrentBBE,
        pmIfRxCurrentUAS,
        pmIfTxCurrentES,
        pmIfTxCurrentSES,
        pmIfTxCurrentBBE,
        pmIfTxCurrentUAS,
        pmIfRx24hCurrentES,
        pmIfRx24hCurrentSES,
        pmIfRx24hCurrentBBE,
        pmIfRx24hCurrentUAS,
        pmIfTx24hCurrentES,
        pmIfTx24hCurrentSES,
        pmIfTx24hCurrentBBE,
        pmIfTx24hCurrentUAS,
        pmIfRxESThreshold,
        pmIfRxSESThreshold,
        pmIfRxBBEThreshold,
        pmIfRxUASThreshold,
        pmIfTxESThreshold,
        pmIfTxSESThreshold,
        pmIfTxBBEThreshold,
        pmIfTxUASThreshold,
        pmIfRx24hESThreshold,
        pmIfRx24hSESThreshold,
        pmIfRx24hBBEThreshold,
        pmIfRx24hUASThreshold,
        pmIfTx24hESThreshold,
        pmIfTx24hSESThreshold,
        pmIfTx24hBBEThreshold,
        pmIfTx24hUASThreshold,
        pmIfRxES,
        pmIfRxSES,
        pmIfRxBBE,
        pmIfRxUAS,
        pmIfTxES,
        pmIfTxSES,
        pmIfTxBBE,
        pmIfTxUAS,
        pmIfRx24hES,
        pmIfRx24hSES,
        pmIfRx24hBBE,
        pmIfRx24hUAS,
        pmIfTx24hES,
        pmIfTx24hSES,
        pmIfTx24hBBE,
        pmIfTx24hUAS,
        pmIfRxPort,
        pmIfReset15Min,
        pmIfReset24H }
    STATUS      current
    DESCRIPTION
        "The pm interface configuration and current meters objects V3."
    ::= { lumPmGroups 14 }

pmFileGroupV2 OBJECT-GROUP
    OBJECTS {
        pmFileIndex,
        pmFileName,
        pmFileCreatedTime,
        pmFileSeqNumber }
    STATUS      current
    DESCRIPTION
        "The 15 minute interval file objects V2."
    ::= { lumPmGroups 15 }

pmFile24hGroupV2 OBJECT-GROUP
    OBJECTS {
        pmFile24hIndex,
        pmFile24hName,
        pmFile24hCreatedTime,
        pmFile24hSeqNumber }
    STATUS      current
    DESCRIPTION
        "The 24 hour interval file objects V2."
    ::= { lumPmGroups 16 }

pmIfGroupV4 OBJECT-GROUP
    OBJECTS {
        pmIfIndex,
        pmIfName,
        pmIfSubrack,
        pmIfSlot,
        pmIfPort,
        pmIfPmReportMode,
        pmIfRxCurrentES,
        pmIfRxCurrentSES,
        pmIfRxCurrentBBE,
        pmIfRxCurrentUAS,
        pmIfTxCurrentES,
        pmIfTxCurrentSES,
        pmIfTxCurrentBBE,
        pmIfTxCurrentUAS,
        pmIfRx24hCurrentES,
        pmIfRx24hCurrentSES,
        pmIfRx24hCurrentBBE,
        pmIfRx24hCurrentUAS,
        pmIfTx24hCurrentES,
        pmIfTx24hCurrentSES,
        pmIfTx24hCurrentBBE,
        pmIfTx24hCurrentUAS,
        pmIfRxESThreshold,
        pmIfRxSESThreshold,
        pmIfRxBBEThreshold,
        pmIfRxUASThreshold,
        pmIfTxESThreshold,
        pmIfTxSESThreshold,
        pmIfTxBBEThreshold,
        pmIfTxUASThreshold,
        pmIfRx24hESThreshold,
        pmIfRx24hSESThreshold,
        pmIfRx24hBBEThreshold,
        pmIfRx24hUASThreshold,
        pmIfTx24hESThreshold,
        pmIfTx24hSESThreshold,
        pmIfTx24hBBEThreshold,
        pmIfTx24hUASThreshold,
        pmIfRxES,
        pmIfRxSES,
        pmIfRxBBE,
        pmIfRxUAS,
        pmIfTxES,
        pmIfTxSES,
        pmIfTxBBE,
        pmIfTxUAS,
        pmIfRx24hES,
        pmIfRx24hSES,
        pmIfRx24hBBE,
        pmIfRx24hUAS,
        pmIfTx24hES,
        pmIfTx24hSES,
        pmIfTx24hBBE,
        pmIfTx24hUAS,
        pmIfRxPort,
        pmIfReset15Min,
        pmIfReset24H,
        pmIfAdminStatus,
        pmIfOperStatus }
    STATUS      deprecated
    DESCRIPTION
        "The pm interface configuration and current meters objects V4."
    ::= { lumPmGroups 17 }

pmIfGroupV5 OBJECT-GROUP
    OBJECTS {
        pmIfIndex,
        pmIfName,
        pmIfSubrack,
        pmIfSlot,
        pmIfPort,
        pmIfPmReportMode,
        pmIfRxCurrentES,
        pmIfRxCurrentSES,
        pmIfRxCurrentBBE,
        pmIfRxCurrentUAS,
        pmIfTxCurrentES,
        pmIfTxCurrentSES,
        pmIfTxCurrentBBE,
        pmIfTxCurrentUAS,
        pmIfRx24hCurrentES,
        pmIfRx24hCurrentSES,
        pmIfRx24hCurrentBBE,
        pmIfRx24hCurrentUAS,
        pmIfTx24hCurrentES,
        pmIfTx24hCurrentSES,
        pmIfTx24hCurrentBBE,
        pmIfTx24hCurrentUAS,
        pmIfRxESThreshold,
        pmIfRxSESThreshold,
        pmIfRxBBEThreshold,
        pmIfRxUASThreshold,
        pmIfTxESThreshold,
        pmIfTxSESThreshold,
        pmIfTxBBEThreshold,
        pmIfTxUASThreshold,
        pmIfRx24hESThreshold,
        pmIfRx24hSESThreshold,
        pmIfRx24hBBEThreshold,
        pmIfRx24hUASThreshold,
        pmIfTx24hESThreshold,
        pmIfTx24hSESThreshold,
        pmIfTx24hBBEThreshold,
        pmIfTx24hUASThreshold,
        pmIfRxES,
        pmIfRxSES,
        pmIfRxBBE,
        pmIfRxUAS,
        pmIfTxES,
        pmIfTxSES,
        pmIfTxBBE,
        pmIfTxUAS,
        pmIfRx24hES,
        pmIfRx24hSES,
        pmIfRx24hBBE,
        pmIfRx24hUAS,
        pmIfTx24hES,
        pmIfTx24hSES,
        pmIfTx24hBBE,
        pmIfTx24hUAS,
        pmIfRxPort,
        pmIfReset15Min,
        pmIfReset24H,
        pmIfAdminStatus,
        pmIfOperStatus,
        pmIfIsSuspect15Min,
        pmIfIsSuspect24H }
    STATUS      deprecated
    DESCRIPTION
        "The pm interface configuration and current meters objects V4."
    ::= { lumPmGroups 18 }

pmFileGroupV3 OBJECT-GROUP
    OBJECTS {
        pmFileIndex,
        pmFileName,
        pmFileCreatedTime,
        pmFileSeqNumber,
        pmFileStartTime,
        pmFileStopTime }
    STATUS      deprecated
    DESCRIPTION
        "The 15 minute interval file objects V3."
    ::= { lumPmGroups 19 }

pmFile24hGroupV3 OBJECT-GROUP
    OBJECTS {
        pmFile24hIndex,
        pmFile24hName,
        pmFile24hCreatedTime,
        pmFile24hSeqNumber,
        pmFile24hStartTime,
        pmFile24hStopTime }
    STATUS      deprecated
    DESCRIPTION
        "The 24 hour interval file objects V3."
    ::= { lumPmGroups 20 }

pmFileGroupV4 OBJECT-GROUP
    OBJECTS {
        pmFileIndex,
        pmFileName,
        pmFileCreatedTime,
        pmFileSeqNumber,
        pmFileStartTime,
        pmFileStopTime,
        pmFileUrl }
    STATUS      current
    DESCRIPTION
        "The 15 minute interval file objects V4."
    ::= { lumPmGroups 21 }

pmFile24hGroupV4 OBJECT-GROUP
    OBJECTS {
        pmFile24hIndex,
        pmFile24hName,
        pmFile24hCreatedTime,
        pmFile24hSeqNumber,
        pmFile24hStartTime,
        pmFile24hStopTime,
        pmFile24hUrl }
    STATUS      current
    DESCRIPTION
        "The 24 hour interval file objects V4."
    ::= { lumPmGroups 22 }

pmIntervalGroupV2 OBJECT-GROUP
    OBJECTS {
        pmIntervalSubrack,
        pmIntervalSlot,
        pmIntervalPort,
        pmIntervalNumber,
        pmIntervalIsSuspect,
        pmIntervalRxES,
        pmIntervalRxSES,
        pmIntervalRxBBE,
        pmIntervalRxUAS,
        pmIntervalTxES,
        pmIntervalTxSES,
        pmIntervalTxBBE,
        pmIntervalTxUAS,
        pmIntervalName,
        pmIntervalRxPowerLevel }
    STATUS      deprecated
    DESCRIPTION
        "The 15 minute interval objects V2."
    ::= { lumPmGroups 23 }

pmInterval24hGroupV2 OBJECT-GROUP
    OBJECTS {
        pmInterval24hSubrack,
        pmInterval24hSlot,
        pmInterval24hPort,
        pmInterval24hNumber,
        pmInterval24hIsSuspect,
        pmInterval24hRxES,
        pmInterval24hRxSES,
        pmInterval24hRxBBE,
        pmInterval24hRxUAS,
        pmInterval24hTxES,
        pmInterval24hTxSES,
        pmInterval24hTxBBE,
        pmInterval24hTxUAS,
        pmInterval24hName,
        pmInterval24hRxPowerLevel }
    STATUS      deprecated
    DESCRIPTION
        "The 24 hour interval objects V2."
    ::= { lumPmGroups 24 }

pmIfGroupV6 OBJECT-GROUP
    OBJECTS {
        pmIfIndex,
        pmIfName,
        pmIfSubrack,
        pmIfSlot,
        pmIfPort,
        pmIfPmReportMode,
        pmIfRxCurrentES,
        pmIfRxCurrentSES,
        pmIfRxCurrentBBE,
        pmIfRxCurrentUAS,
        pmIfTxCurrentES,
        pmIfTxCurrentSES,
        pmIfTxCurrentBBE,
        pmIfTxCurrentUAS,
        pmIfRx24hCurrentES,
        pmIfRx24hCurrentSES,
        pmIfRx24hCurrentBBE,
        pmIfRx24hCurrentUAS,
        pmIfTx24hCurrentES,
        pmIfTx24hCurrentSES,
        pmIfTx24hCurrentBBE,
        pmIfTx24hCurrentUAS,
        pmIfRxESThreshold,
        pmIfRxSESThreshold,
        pmIfRxBBEThreshold,
        pmIfRxUASThreshold,
        pmIfTxESThreshold,
        pmIfTxSESThreshold,
        pmIfTxBBEThreshold,
        pmIfTxUASThreshold,
        pmIfRx24hESThreshold,
        pmIfRx24hSESThreshold,
        pmIfRx24hBBEThreshold,
        pmIfRx24hUASThreshold,
        pmIfTx24hESThreshold,
        pmIfTx24hSESThreshold,
        pmIfTx24hBBEThreshold,
        pmIfTx24hUASThreshold,
        pmIfRxES,
        pmIfRxSES,
        pmIfRxBBE,
        pmIfRxUAS,
        pmIfTxES,
        pmIfTxSES,
        pmIfTxBBE,
        pmIfTxUAS,
        pmIfRx24hES,
        pmIfRx24hSES,
        pmIfRx24hBBE,
        pmIfRx24hUAS,
        pmIfTx24hES,
        pmIfTx24hSES,
        pmIfTx24hBBE,
        pmIfTx24hUAS,
        pmIfRxPort,
        pmIfReset15Min,
        pmIfReset24H,
        pmIfAdminStatus,
        pmIfOperStatus,
        pmIfIsSuspect15Min,
        pmIfIsSuspect24H,
        pmIfInstallCommand,
        pmIfRxPowerLevel,
        pmIfInitialPowerLevel }
    STATUS      deprecated
    DESCRIPTION
        "The pm interface configuration and current meters objects V6."
    ::= { lumPmGroups 25 }

pmLogGeneralGroupV2 OBJECT-GROUP
    OBJECTS {
        pmLogGeneralLastChangeTime,
        pmLogGeneralSize,
        pmLogGeneralSize24h,
        pmLogGeneralFileTableSize,
        pmLogGeneralFile24hTableSize }
    STATUS      deprecated
    DESCRIPTION
        "The general log object."
    ::= { lumPmGroups 26 }

pmIntervalGroupV3 OBJECT-GROUP
    OBJECTS {
        pmIntervalSubrack,
        pmIntervalSlot,
        pmIntervalPort,
        pmIntervalNumber,
        pmIntervalIsSuspect,
        pmIntervalRxES,
        pmIntervalRxSES,
        pmIntervalRxBBE,
        pmIntervalRxUAS,
        pmIntervalTxES,
        pmIntervalTxSES,
        pmIntervalTxBBE,
        pmIntervalTxUAS,
        pmIntervalName,
        pmIntervalRxPowerLevel,
        pmIntervalGbeMaxUtilization }
    STATUS      deprecated
    DESCRIPTION
        "The 15 minute interval objects V3."
    ::= { lumPmGroups 27 }

pmInterval24hGroupV3 OBJECT-GROUP
    OBJECTS {
        pmInterval24hSubrack,
        pmInterval24hSlot,
        pmInterval24hPort,
        pmInterval24hNumber,
        pmInterval24hIsSuspect,
        pmInterval24hRxES,
        pmInterval24hRxSES,
        pmInterval24hRxBBE,
        pmInterval24hRxUAS,
        pmInterval24hTxES,
        pmInterval24hTxSES,
        pmInterval24hTxBBE,
        pmInterval24hTxUAS,
        pmInterval24hName,
        pmInterval24hRxPowerLevel,
        pmInterval24hGbeMaxUtilization }
    STATUS      deprecated
    DESCRIPTION
        "The 24 hour interval objects V3."
    ::= { lumPmGroups 28 }

pmIfGroupV7 OBJECT-GROUP
    OBJECTS {
        pmIfIndex,
        pmIfName,
        pmIfSubrack,
        pmIfSlot,
        pmIfPort,
        pmIfPmReportMode,
        pmIfRxCurrentES,
        pmIfRxCurrentSES,
        pmIfRxCurrentBBE,
        pmIfRxCurrentUAS,
        pmIfTxCurrentES,
        pmIfTxCurrentSES,
        pmIfTxCurrentBBE,
        pmIfTxCurrentUAS,
        pmIfRx24hCurrentES,
        pmIfRx24hCurrentSES,
        pmIfRx24hCurrentBBE,
        pmIfRx24hCurrentUAS,
        pmIfTx24hCurrentES,
        pmIfTx24hCurrentSES,
        pmIfTx24hCurrentBBE,
        pmIfTx24hCurrentUAS,
        pmIfRxESThreshold,
        pmIfRxSESThreshold,
        pmIfRxBBEThreshold,
        pmIfRxUASThreshold,
        pmIfTxESThreshold,
        pmIfTxSESThreshold,
        pmIfTxBBEThreshold,
        pmIfTxUASThreshold,
        pmIfRx24hESThreshold,
        pmIfRx24hSESThreshold,
        pmIfRx24hBBEThreshold,
        pmIfRx24hUASThreshold,
        pmIfTx24hESThreshold,
        pmIfTx24hSESThreshold,
        pmIfTx24hBBEThreshold,
        pmIfTx24hUASThreshold,
        pmIfRxES,
        pmIfRxSES,
        pmIfRxBBE,
        pmIfRxUAS,
        pmIfTxES,
        pmIfTxSES,
        pmIfTxBBE,
        pmIfTxUAS,
        pmIfRx24hES,
        pmIfRx24hSES,
        pmIfRx24hBBE,
        pmIfRx24hUAS,
        pmIfTx24hES,
        pmIfTx24hSES,
        pmIfTx24hBBE,
        pmIfTx24hUAS,
        pmIfRxPort,
        pmIfReset15Min,
        pmIfReset24H,
        pmIfAdminStatus,
        pmIfOperStatus,
        pmIfIsSuspect15Min,
        pmIfIsSuspect24H,
        pmIfInstallCommand,
        pmIfRxPowerLevel,
        pmIfInitialPowerLevel,
        pmIfRxGbeMaxUtilization,
        pmIfRx24hGbeMaxUtilization }
    STATUS      deprecated
    DESCRIPTION
        "The pm interface configuration and current meters objects V7 (3.1)."
    ::= { lumPmGroups 29 }

pmGeneralGroupV3 OBJECT-GROUP
    OBJECTS {
        pmGeneralLastChangeTime,
        pmGeneralStateLastChangeTime,
        pmGeneralPmIfTableSize }
    STATUS      deprecated
    DESCRIPTION
        "The general objects. (3.1)"
    ::= { lumPmGroups 30 }

pmLogGeneralGroupV3 OBJECT-GROUP
    OBJECTS {
        pmLogGeneralLastChangeTime,
        pmLogGeneralSize,
        pmLogGeneralSize24h,
        pmLogGeneralFileTableSize,
        pmLogGeneralFile24hTableSize,
        pmLogGeneralInterval15mTableSize,
        pmLogGeneralInterval24hTableSize,
        pmLogGeneralInterval15mShowNonZeroOnly,
        pmLogGeneralInterval24hShowNonZeroOnly }
    STATUS      deprecated
    DESCRIPTION
        "The general log object."
    ::= { lumPmGroups 31 }

pmIntervalGroupV4 OBJECT-GROUP
    OBJECTS {
        pmIntervalSubrack,
        pmIntervalSlot,
        pmIntervalPort,
        pmIntervalNumber,
        pmIntervalIsSuspect,
        pmIntervalRxES,
        pmIntervalRxSES,
        pmIntervalRxBBE,
        pmIntervalRxUAS,
        pmIntervalTxES,
        pmIntervalTxSES,
        pmIntervalTxBBE,
        pmIntervalTxUAS,
        pmIntervalName,
        pmIntervalGbeMaxUtilization }
    STATUS      deprecated
    DESCRIPTION
        "The 15 minute interval objects V4."
    ::= { lumPmGroups 32 }

pmInterval24hGroupV4 OBJECT-GROUP
    OBJECTS {
        pmInterval24hSubrack,
        pmInterval24hSlot,
        pmInterval24hPort,
        pmInterval24hNumber,
        pmInterval24hIsSuspect,
        pmInterval24hRxES,
        pmInterval24hRxSES,
        pmInterval24hRxBBE,
        pmInterval24hRxUAS,
        pmInterval24hTxES,
        pmInterval24hTxSES,
        pmInterval24hTxBBE,
        pmInterval24hTxUAS,
        pmInterval24hName,
        pmInterval24hGbeMaxUtilization }
    STATUS      deprecated
    DESCRIPTION
        "The 24 hour interval objects V4."
    ::= { lumPmGroups 33 }

pmIfGroupV8 OBJECT-GROUP
    OBJECTS {
        pmIfIndex,
        pmIfName,
        pmIfSubrack,
        pmIfSlot,
        pmIfPort,
        pmIfPmReportMode,
        pmIfRxCurrentES,
        pmIfRxCurrentSES,
        pmIfRxCurrentBBE,
        pmIfRxCurrentUAS,
        pmIfTxCurrentES,
        pmIfTxCurrentSES,
        pmIfTxCurrentBBE,
        pmIfTxCurrentUAS,
        pmIfRx24hCurrentES,
        pmIfRx24hCurrentSES,
        pmIfRx24hCurrentBBE,
        pmIfRx24hCurrentUAS,
        pmIfTx24hCurrentES,
        pmIfTx24hCurrentSES,
        pmIfTx24hCurrentBBE,
        pmIfTx24hCurrentUAS,
        pmIfRxESThreshold,
        pmIfRxSESThreshold,
        pmIfRxBBEThreshold,
        pmIfRxUASThreshold,
        pmIfTxESThreshold,
        pmIfTxSESThreshold,
        pmIfTxBBEThreshold,
        pmIfTxUASThreshold,
        pmIfRx24hESThreshold,
        pmIfRx24hSESThreshold,
        pmIfRx24hBBEThreshold,
        pmIfRx24hUASThreshold,
        pmIfTx24hESThreshold,
        pmIfTx24hSESThreshold,
        pmIfTx24hBBEThreshold,
        pmIfTx24hUASThreshold,
        pmIfRxES,
        pmIfRxSES,
        pmIfRxBBE,
        pmIfRxUAS,
        pmIfTxES,
        pmIfTxSES,
        pmIfTxBBE,
        pmIfTxUAS,
        pmIfRx24hES,
        pmIfRx24hSES,
        pmIfRx24hBBE,
        pmIfRx24hUAS,
        pmIfTx24hES,
        pmIfTx24hSES,
        pmIfTx24hBBE,
        pmIfTx24hUAS,
        pmIfRxPort,
        pmIfReset15Min,
        pmIfReset24H,
        pmIfAdminStatus,
        pmIfOperStatus,
        pmIfIsSuspect15Min,
        pmIfIsSuspect24H,
        pmIfInstallCommand,
        pmIfRxPowerLevel,
        pmIfInitialPowerLevel,
        pmIfRxGbeMaxUtilization,
        pmIfRx24hGbeMaxUtilization,
        pmIfTxPowerLevel }
    STATUS      deprecated
    DESCRIPTION
        "The pm interface configuration and current meters objects V8 (6.0)."
    ::= { lumPmGroups 34 }

pmIntervalGroupV5 OBJECT-GROUP
    OBJECTS {
        pmIntervalSubrack,
        pmIntervalSlot,
        pmIntervalPort,
        pmIntervalNumber,
        pmIntervalIsSuspect,
        pmIntervalRxES,
        pmIntervalRxSES,
        pmIntervalRxBBE,
        pmIntervalRxUAS,
        pmIntervalTxES,
        pmIntervalTxSES,
        pmIntervalTxBBE,
        pmIntervalTxUAS,
        pmIntervalName,
        pmIntervalRxPowerLevel,
        pmIntervalGbeMaxUtilization,
        pmIntervalTxPowerLevel }
    STATUS      deprecated
    DESCRIPTION
        "The 15 minute interval objects V5. (6.0)"
    ::= { lumPmGroups 35 }

pmInterval24hGroupV5 OBJECT-GROUP
    OBJECTS {
        pmInterval24hSubrack,
        pmInterval24hSlot,
        pmInterval24hPort,
        pmInterval24hNumber,
        pmInterval24hIsSuspect,
        pmInterval24hRxES,
        pmInterval24hRxSES,
        pmInterval24hRxBBE,
        pmInterval24hRxUAS,
        pmInterval24hTxES,
        pmInterval24hTxSES,
        pmInterval24hTxBBE,
        pmInterval24hTxUAS,
        pmInterval24hName,
        pmInterval24hRxPowerLevel,
        pmInterval24hGbeMaxUtilization,
        pmInterval24hTxPowerLevel }
    STATUS      deprecated
    DESCRIPTION
        "The 24 hour interval objects V5. (6.0)"
    ::= { lumPmGroups 36 }

pmLogGeneralGroupV4 OBJECT-GROUP
    OBJECTS {
        pmLogGeneralLastChangeTime,
        pmLogGeneralSize,
        pmLogGeneralSize24h,
        pmLogGeneralFileTableSize,
        pmLogGeneralFile24hTableSize,
        pmLogGeneralInterval15mTableSize,
        pmLogGeneralInterval24hTableSize,
        pmLogGeneralInterval15mShowNonZeroOnly,
        pmLogGeneralInterval24hShowNonZeroOnly,
        pmLogGeneralFile15mLastSeqNumber,
        pmLogGeneralFile24hLastSeqNumber }
    STATUS      deprecated
    DESCRIPTION
        "The general log object v4 (10.0)."
    ::= { lumPmGroups 37 }

pmIfGroupV9 OBJECT-GROUP
    OBJECTS {
        pmIfIndex,
        pmIfName,
        pmIfSubrack,
        pmIfSlot,
        pmIfPort,
        pmIfPmReportMode,
        pmIfRxCurrentES,
        pmIfRxCurrentSES,
        pmIfRxCurrentBBE,
        pmIfRxCurrentUAS,
        pmIfTxCurrentES,
        pmIfTxCurrentSES,
        pmIfTxCurrentBBE,
        pmIfTxCurrentUAS,
        pmIfRx24hCurrentES,
        pmIfRx24hCurrentSES,
        pmIfRx24hCurrentBBE,
        pmIfRx24hCurrentUAS,
        pmIfTx24hCurrentES,
        pmIfTx24hCurrentSES,
        pmIfTx24hCurrentBBE,
        pmIfTx24hCurrentUAS,
        pmIfRxESThreshold,
        pmIfRxSESThreshold,
        pmIfRxBBEThreshold,
        pmIfRxUASThreshold,
        pmIfTxESThreshold,
        pmIfTxSESThreshold,
        pmIfTxBBEThreshold,
        pmIfTxUASThreshold,
        pmIfRx24hESThreshold,
        pmIfRx24hSESThreshold,
        pmIfRx24hBBEThreshold,
        pmIfRx24hUASThreshold,
        pmIfTx24hESThreshold,
        pmIfTx24hSESThreshold,
        pmIfTx24hBBEThreshold,
        pmIfTx24hUASThreshold,
        pmIfRxES,
        pmIfRxSES,
        pmIfRxBBE,
        pmIfRxUAS,
        pmIfTxES,
        pmIfTxSES,
        pmIfTxBBE,
        pmIfTxUAS,
        pmIfRx24hES,
        pmIfRx24hSES,
        pmIfRx24hBBE,
        pmIfRx24hUAS,
        pmIfTx24hES,
        pmIfTx24hSES,
        pmIfTx24hBBE,
        pmIfTx24hUAS,
        pmIfRxPort,
        pmIfReset15Min,
        pmIfReset24H,
        pmIfAdminStatus,
        pmIfOperStatus,
        pmIfIsSuspect15Min,
        pmIfIsSuspect24H,
        pmIfInstallCommand,
        pmIfRxPowerLevel,
        pmIfInitialPowerLevel,
        pmIfRxGbeMaxUtilization,
        pmIfRx24hGbeMaxUtilization,
        pmIfTxPowerLevel,
        pmIfObjectProperty}
    STATUS      deprecated
    DESCRIPTION
        "The pm interface configuration and current meters objects V9 (11.0)."
    ::= { lumPmGroups 38 }

pmIntervalGroupV6 OBJECT-GROUP
    OBJECTS {
        pmIntervalSubrack,
        pmIntervalSlot,
        pmIntervalPort,
        pmIntervalNumber,
        pmIntervalIsSuspect,
        pmIntervalRxES,
        pmIntervalRxSES,
        pmIntervalRxBBE,
        pmIntervalRxUAS,
        pmIntervalTxES,
        pmIntervalTxSES,
        pmIntervalTxBBE,
        pmIntervalTxUAS,
        pmIntervalName,
        pmIntervalRxPowerLevel,
        pmIntervalGbeMaxUtilization,
        pmIntervalTxPowerLevel,
        pmIntervalRxUndersizedFrames,
        pmIntervalRxOversizedFrames,
        pmIntervalRxFragments,
        pmIntervalRxFcsErrors,
        pmIntervalRxInvalidCeVlanId,
        pmIntervalTxOctets,
        pmIntervalTxFrames,
        pmIntervalTxUnicastFrames,
        pmIntervalTxMulticastFrames,
        pmIntervalTxBroadcastFrames,
        pmIntervalRxOctets,
        pmIntervalRxFrames,
        pmIntervalRxUnicastFrames,
        pmIntervalRxMulticastFrames,
        pmIntervalRxBroadcastFrames,
        pmIntervalIngressGreenFrameCount,
        pmIntervalIngressYellowFrameCount,
        pmIntervalIngressRedFrameCount,
        pmIntervalIngressGreenOctetCount,
        pmIntervalIngressYellowOctetCount,
        pmIntervalIngressRedOctetCount,
        pmIntervalEgressGreenFrameCount,
        pmIntervalEgressGreenOctetCount,
        pmIntervalGreenFrameDiscards,
        pmIntervalYellowFrameDiscards,
        pmIntervalGreenOctetDiscards,
        pmIntervalYellowOctetDiscards,
        pmIntervalTwoWayFrameDelay,
        pmIntervalTwoWayFrameDelayVariation,
        pmIntervalFrameLossRatioNearEnd,
        pmIntervalFrameLossRatioFarEnd,
        pmIntervalUnavailabilityNearEnd,
        pmIntervalUnavailabilityFarEnd,
        pmIntervalOneWayFrameDelayVariation }
-- @todo objectclass?
    STATUS      deprecated
    DESCRIPTION
        "The 15 minute interval objects V6. (11.0)"
    ::= { lumPmGroups 39 }


pmInterval24hGroupV6 OBJECT-GROUP
    OBJECTS {
        pmInterval24hSubrack,
        pmInterval24hSlot,
        pmInterval24hPort,
        pmInterval24hNumber,
        pmInterval24hIsSuspect,
        pmInterval24hRxES,
        pmInterval24hRxSES,
        pmInterval24hRxBBE,
        pmInterval24hRxUAS,
        pmInterval24hTxES,
        pmInterval24hTxSES,
        pmInterval24hTxBBE,
        pmInterval24hTxUAS,
        pmInterval24hName,
        pmInterval24hRxPowerLevel,
        pmInterval24hGbeMaxUtilization,
        pmInterval24hTxPowerLevel,
        pmInterval24hRxUndersizedFrames,
        pmInterval24hRxOversizedFrames,
        pmInterval24hRxFragments,
        pmInterval24hRxFcsErrors,
        pmInterval24hRxInvalidCeVlanId,
        pmInterval24hTxOctets,
        pmInterval24hTxFrames,
        pmInterval24hTxUnicastFrames,
        pmInterval24hTxMulticastFrames,
        pmInterval24hTxBroadcastFrames,
        pmInterval24hRxOctets,
        pmInterval24hRxFrames,
        pmInterval24hRxUnicastFrames,
        pmInterval24hRxMulticastFrames,
        pmInterval24hRxBroadcastFrames,
        pmInterval24hIngressGreenFrameCount,
        pmInterval24hIngressYellowFrameCount,
        pmInterval24hIngressRedFrameCount,
        pmInterval24hIngressGreenOctetCount,
        pmInterval24hIngressYellowOctetCount,
        pmInterval24hIngressRedOctetCount,
        pmInterval24hEgressGreenFrameCount,
        pmInterval24hEgressGreenOctetCount,
        pmInterval24hGreenFrameDiscards,
        pmInterval24hYellowFrameDiscards,
        pmInterval24hGreenOctetDiscards,
        pmInterval24hYellowOctetDiscards,
        pmInterval24hTwoWayFrameDelay,
        pmInterval24hTwoWayFrameDelayVariation,
        pmInterval24hFrameLossRatioNearEnd,
        pmInterval24hFrameLossRatioFarEnd,
        pmInterval24hUnavailabilityNearEnd,
        pmInterval24hUnavailabilityFarEnd,
        pmInterval24hOneWayFrameDelayVariation }
-- @todo objectclass?
    STATUS      deprecated
    DESCRIPTION
        "The 24 hour interval objects V6. (11.0)"
    ::= { lumPmGroups 40 }

pmEthTdGroup OBJECT-GROUP
    OBJECTS {
        pmEthTdIndex,
        pmEthTdName,
        pmEthTdSubrack,
        pmEthTdSlot,
        pmEthTdPort,
        pmEthTdPmReportMode,
        pmEthTdRxPort,
        pmEthTdReset15Min,
        pmEthTdReset24H,
        pmEthTdAdminStatus,
        pmEthTdOperStatus,
        pmEthTdIsSuspect15Min,
        pmEthTdIsSuspect24h,
        pmEthTdCurrentRxUndersizedFrames,
        pmEthTdCurrentRxOversizedFrames,
        pmEthTdCurrentRxFragments,
        pmEthTdCurrentRxFcsErrors,
        pmEthTdCurrentRxInvalidCeVlanId,
        pmEthTdCurrentTxOctets,
        pmEthTdCurrentTxFrames,
        pmEthTdCurrentTxUnicastFrames,
        pmEthTdCurrentTxMulticastFrames,
        pmEthTdCurrentTxBroadcastFrames,
        pmEthTdCurrentRxOctets,
        pmEthTdCurrentRxFrames,
        pmEthTdCurrentRxUnicastFrames,
        pmEthTdCurrentRxMulticastFrames,
        pmEthTdCurrentRxBroadcastFrames,
        pmEthTdCurrent24hRxUndersizedFrames,
        pmEthTdCurrent24hRxOversizedFrames,
        pmEthTdCurrent24hRxFragments,
        pmEthTdCurrent24hRxFcsErrors,
        pmEthTdCurrent24hRxInvalidCeVlanId,
        pmEthTdCurrent24hTxOctets,
        pmEthTdCurrent24hTxFrames,
        pmEthTdCurrent24hTxUnicastFrames,
        pmEthTdCurrent24hTxMulticastFrames,
        pmEthTdCurrent24hTxBroadcastFrames,
        pmEthTdCurrent24hRxOctets,
        pmEthTdCurrent24hRxFrames,
        pmEthTdCurrent24hRxUnicastFrames,
        pmEthTdCurrent24hRxMulticastFrames,
        pmEthTdCurrent24hRxBroadcastFrames,
        pmEthTdObjectProperty,
        pmEthTdRxUndersizedFramesThreshold,
        pmEthTdRxOversizedFramesThreshold,
        pmEthTdRxFragmentsThreshold,
        pmEthTdRxFcsErrorsThreshold,
        pmEthTdRxInvalidCeVlanIdThreshold,
        pmEthTd24hRxUndersizedFramesThreshold,
        pmEthTd24hRxOversizedFramesThreshold,
        pmEthTd24hRxFragmentsThreshold,
        pmEthTd24hRxFcsErrorsThreshold,
        pmEthTd24hRxInvalidCeVlanIdThreshold,
        pmEthTdRxUndersizedFrames,
        pmEthTdRxOversizedFrames,
        pmEthTdRxFragments,
        pmEthTdRxFcsErrors,
        pmEthTdRxInvalidCeVlanId,
        pmEthTd24hRxUndersizedFrames,
        pmEthTd24hRxOversizedFrames,
        pmEthTd24hRxFragments,
        pmEthTd24hRxFcsErrors,
        pmEthTd24hRxInvalidCeVlanId  }
    STATUS      deprecated
    DESCRIPTION
        "The Ethernet Traffic Data PM configuration and current meters objects V1 (11.0)."
    ::= { lumPmGroups 41 }

pmEthTmGroup OBJECT-GROUP
    OBJECTS {
        pmEthTmIndex,
        pmEthTmName,
        pmEthTmSubrack,
        pmEthTmSlot,
        pmEthTmPort,
        pmEthTmPmReportMode,
        pmEthTmRxPort,
        pmEthTmReset15Min,
        pmEthTmReset24H,
        pmEthTmAdminStatus,
        pmEthTmOperStatus,
        pmEthTmIsSuspect15Min,
        pmEthTmIsSuspect24h,
        pmEthTmCurrentIngressGreenFrameCount,
        pmEthTmCurrentIngressYellowFrameCount,
        pmEthTmCurrentIngressRedFrameCount,
        pmEthTmCurrentIngressGreenOctetCount,
        pmEthTmCurrentIngressYellowOctetCount,
        pmEthTmCurrentIngressRedOctetCount,
        pmEthTmCurrentEgressGreenFrameCount,
        pmEthTmCurrentEgressGreenOctetCount,
        pmEthTmCurrentGreenFrameDiscards,
        pmEthTmCurrentYellowFrameDiscards,
        pmEthTmCurrentGreenOctetDiscards,
        pmEthTmCurrentYellowOctetDiscards,
        pmEthTmCurrent24hIngressGreenFrameCount,
        pmEthTmCurrent24hIngressYellowFrameCount,
        pmEthTmCurrent24hIngressRedFrameCount,
        pmEthTmCurrent24hIngressGreenOctetCount,
        pmEthTmCurrent24hIngressYellowOctetCount,
        pmEthTmCurrent24hIngressRedOctetCount,
        pmEthTmCurrent24hEgressGreenFrameCount,
        pmEthTmCurrent24hEgressGreenOctetCount,
        pmEthTmCurrent24hGreenFrameDiscards,
        pmEthTmCurrent24hYellowFrameDiscards,
        pmEthTmCurrent24hGreenOctetDiscards,
        pmEthTmCurrent24hYellowOctetDiscards,
        pmEthTmObjectProperty,
        pmEthTmInternalReference,
        pmEthTmIdentifier }
    STATUS      current
    DESCRIPTION
        "The Ethernet Traffic Management PM configuration and current meters objects V1 (11.0)."
    ::= { lumPmGroups 42 }

pmEthOamGroup OBJECT-GROUP
    OBJECTS {
        pmEthOamIndex,
        pmEthOamName,
        pmEthOamSubrack,
        pmEthOamSlot,
        pmEthOamPort,
        pmEthOamPmReportMode,
        pmEthOamRxPort,
        pmEthOamReset15Min,
        pmEthOamReset24H,
        pmEthOamAdminStatus,
        pmEthOamOperStatus,
        pmEthOamIsSuspect15Min,
        pmEthOamIsSuspect24h,
        pmEthOamCurrentTwoWayFrameDelay,
        pmEthOamCurrentTwoWayFrameDelayVariation,
        pmEthOamCurrentFrameLossRatioNearEnd,
        pmEthOamCurrentFrameLossRatioFarEnd,
        pmEthOamCurrentUnavailabilityNearEnd,
        pmEthOamCurrentUnavailabilityFarEnd,
        pmEthOamCurrent24hTwoWayFrameDelay,
        pmEthOamCurrent24hTwoWayFrameDelayVariation,
        pmEthOamCurrent24hFrameLossRatioNearEnd,
        pmEthOamCurrent24hFrameLossRatioFarEnd,
        pmEthOamCurrent24hUnavailabilityNearEnd,
        pmEthOamCurrent24hUnavailabilityFarEnd,
        pmEthOamObjectProperty,
        pmEthOamInternalReference,
        pmEthOamIdentifier,
        pmEthOamUsedPercentOfFrames,
        pmEthOamFrameLossRatioUnavailableThreshold,
        pmEthOamCurrentOneWayFrameDelayVariation,
        pmEthOamCurrent24hOneWayFrameDelayVariation }
    STATUS      current
    DESCRIPTION
        "The Ethernet OAM PM configuration and current meters objects V1 (11.0)."
    ::= { lumPmGroups 43 }

pmGeneralGroupV4 OBJECT-GROUP
    OBJECTS {
        pmGeneralLastChangeTime,
        pmGeneralStateLastChangeTime,
        pmGeneralPmIfTableSize,
        pmGeneralPmEthTdTableSize,
        pmGeneralPmEthTmTableSize,
        pmGeneralPmEthOamTableSize }
    STATUS      deprecated
    DESCRIPTION
        "The general objects. (11.0)"
    ::= { lumPmGroups 44 }

pmEthTdGroupV2 OBJECT-GROUP
    OBJECTS {
        pmEthTdIndex,
        pmEthTdName,
        pmEthTdSubrack,
        pmEthTdSlot,
        pmEthTdPort,
        pmEthTdPmReportMode,
        pmEthTdRxPort,
        pmEthTdReset15Min,
        pmEthTdReset24H,
        pmEthTdAdminStatus,
        pmEthTdOperStatus,
        pmEthTdIsSuspect15Min,
        pmEthTdIsSuspect24h,
        pmEthTdCurrentRxUndersizedFrames,
        pmEthTdCurrentRxOversizedFrames,
        pmEthTdCurrentRxFragments,
        pmEthTdCurrentRxFcsErrors,
        pmEthTdCurrentRxInvalidCeVlanId,
        pmEthTdCurrentTxOctets,
        pmEthTdCurrentTxFrames,
        pmEthTdCurrentTxUnicastFrames,
        pmEthTdCurrentTxMulticastFrames,
        pmEthTdCurrentTxBroadcastFrames,
        pmEthTdCurrentRxOctets,
        pmEthTdCurrentRxFrames,
        pmEthTdCurrentRxUnicastFrames,
        pmEthTdCurrentRxMulticastFrames,
        pmEthTdCurrentRxBroadcastFrames,
        pmEthTdCurrentTxEthMaxUtilization,
        pmEthTdCurrentRxEthMaxUtilization,
        pmEthTdCurrent24hRxUndersizedFrames,
        pmEthTdCurrent24hRxOversizedFrames,
        pmEthTdCurrent24hRxFragments,
        pmEthTdCurrent24hRxFcsErrors,
        pmEthTdCurrent24hRxInvalidCeVlanId,
        pmEthTdCurrent24hTxOctets,
        pmEthTdCurrent24hTxFrames,
        pmEthTdCurrent24hTxUnicastFrames,
        pmEthTdCurrent24hTxMulticastFrames,
        pmEthTdCurrent24hTxBroadcastFrames,
        pmEthTdCurrent24hRxOctets,
        pmEthTdCurrent24hRxFrames,
        pmEthTdCurrent24hRxUnicastFrames,
        pmEthTdCurrent24hRxMulticastFrames,
        pmEthTdCurrent24hRxBroadcastFrames,
        pmEthTdCurrent24hTxEthMaxUtilization,
        pmEthTdCurrent24hRxEthMaxUtilization,
        pmEthTdObjectProperty,
        pmEthTdRxUndersizedFramesThreshold,
        pmEthTdRxOversizedFramesThreshold,
        pmEthTdRxFragmentsThreshold,
        pmEthTdRxFcsErrorsThreshold,
        pmEthTdRxInvalidCeVlanIdThreshold,
        pmEthTd24hRxUndersizedFramesThreshold,
        pmEthTd24hRxOversizedFramesThreshold,
        pmEthTd24hRxFragmentsThreshold,
        pmEthTd24hRxFcsErrorsThreshold,
        pmEthTd24hRxInvalidCeVlanIdThreshold,
        pmEthTdRxUndersizedFrames,
        pmEthTdRxOversizedFrames,
        pmEthTdRxFragments,
        pmEthTdRxFcsErrors,
        pmEthTdRxInvalidCeVlanId,
        pmEthTd24hRxUndersizedFrames,
        pmEthTd24hRxOversizedFrames,
        pmEthTd24hRxFragments,
        pmEthTd24hRxFcsErrors,
        pmEthTd24hRxInvalidCeVlanId  }
    STATUS      deprecated
    DESCRIPTION
        "The Ethernet Traffic Data PM configuration and current meters objects V1 (12.0)."
    ::= { lumPmGroups 45 }

pmIntervalGroupV7 OBJECT-GROUP
    OBJECTS {
        pmIntervalSubrack,
        pmIntervalSlot,
        pmIntervalPort,
        pmIntervalNumber,
        pmIntervalIsSuspect,
        pmIntervalRxES,
        pmIntervalRxSES,
        pmIntervalRxBBE,
        pmIntervalRxUAS,
        pmIntervalTxES,
        pmIntervalTxSES,
        pmIntervalTxBBE,
        pmIntervalTxUAS,
        pmIntervalName,
        pmIntervalRxPowerLevel,
        pmIntervalGbeMaxUtilization,
        pmIntervalTxPowerLevel,
        pmIntervalTxEthMaxUtilization,
        pmIntervalRxEthMaxUtilization }
    STATUS      deprecated
    DESCRIPTION
        "The 15 minute interval objects V7. (12.0)"
    ::= { lumPmGroups 46 }

pmInterval24hGroupV7 OBJECT-GROUP
    OBJECTS {
        pmInterval24hSubrack,
        pmInterval24hSlot,
        pmInterval24hPort,
        pmInterval24hNumber,
        pmInterval24hIsSuspect,
        pmInterval24hRxES,
        pmInterval24hRxSES,
        pmInterval24hRxBBE,
        pmInterval24hRxUAS,
        pmInterval24hTxES,
        pmInterval24hTxSES,
        pmInterval24hTxBBE,
        pmInterval24hTxUAS,
        pmInterval24hName,
        pmInterval24hRxPowerLevel,
        pmInterval24hGbeMaxUtilization,
        pmInterval24hTxPowerLevel,
        pmInterval24hTxEthMaxUtilization,
        pmInterval24hRxEthMaxUtilization }
    STATUS      deprecated
    DESCRIPTION
        "The 24 hour interval objects V7. (12.0)"
    ::= { lumPmGroups 47 }

pmIntervalGroupV8 OBJECT-GROUP
    OBJECTS {
        pmIntervalSubrack,
        pmIntervalSlot,
        pmIntervalPort,
        pmIntervalNumber,
        pmIntervalIsSuspect,
        pmIntervalRxES,
        pmIntervalRxSES,
        pmIntervalRxBBE,
        pmIntervalRxUAS,
        pmIntervalTxES,
        pmIntervalTxSES,
        pmIntervalTxBBE,
        pmIntervalTxUAS,
        pmIntervalName,
        pmIntervalRxPowerLevel,
        pmIntervalGbeMaxUtilization,
        pmIntervalTxPowerLevel,
        pmIntervalTxEthMaxUtilization,
        pmIntervalRxEthMaxUtilization,
        pmIntervalStartTime,
        pmIntervalStopTime }
    STATUS      deprecated
    DESCRIPTION
        "The 15 minute interval objects V8. (13.0)"
    ::= { lumPmGroups 48 }

pmInterval24hGroupV8 OBJECT-GROUP
    OBJECTS {
        pmInterval24hSubrack,
        pmInterval24hSlot,
        pmInterval24hPort,
        pmInterval24hNumber,
        pmInterval24hIsSuspect,
        pmInterval24hRxES,
        pmInterval24hRxSES,
        pmInterval24hRxBBE,
        pmInterval24hRxUAS,
        pmInterval24hTxES,
        pmInterval24hTxSES,
        pmInterval24hTxBBE,
        pmInterval24hTxUAS,
        pmInterval24hName,
        pmInterval24hRxPowerLevel,
        pmInterval24hGbeMaxUtilization,
        pmInterval24hTxPowerLevel,
        pmInterval24hTxEthMaxUtilization,
        pmInterval24hRxEthMaxUtilization,
        pmInterval24hStartTime,
        pmInterval24hStopTime }
    STATUS      deprecated
    DESCRIPTION
        "The 24 hour interval objects V8. (13.0)"
    ::= { lumPmGroups 49 }

pmIfGroupV10 OBJECT-GROUP
    OBJECTS {
        pmIfIndex,
        pmIfName,
        pmIfSubrack,
        pmIfSlot,
        pmIfPort,
        pmIfPmReportMode,
        pmIfRxCurrentES,
        pmIfRxCurrentSES,
        pmIfRxCurrentBBE,
        pmIfRxCurrentUAS,
        pmIfTxCurrentES,
        pmIfTxCurrentSES,
        pmIfTxCurrentBBE,
        pmIfTxCurrentUAS,
        pmIfRx24hCurrentES,
        pmIfRx24hCurrentSES,
        pmIfRx24hCurrentBBE,
        pmIfRx24hCurrentUAS,
        pmIfTx24hCurrentES,
        pmIfTx24hCurrentSES,
        pmIfTx24hCurrentBBE,
        pmIfTx24hCurrentUAS,
        pmIfRxESThreshold,
        pmIfRxSESThreshold,
        pmIfRxBBEThreshold,
        pmIfRxUASThreshold,
        pmIfTxESThreshold,
        pmIfTxSESThreshold,
        pmIfTxBBEThreshold,
        pmIfTxUASThreshold,
        pmIfRx24hESThreshold,
        pmIfRx24hSESThreshold,
        pmIfRx24hBBEThreshold,
        pmIfRx24hUASThreshold,
        pmIfTx24hESThreshold,
        pmIfTx24hSESThreshold,
        pmIfTx24hBBEThreshold,
        pmIfTx24hUASThreshold,
        pmIfRxES,
        pmIfRxSES,
        pmIfRxBBE,
        pmIfRxUAS,
        pmIfTxES,
        pmIfTxSES,
        pmIfTxBBE,
        pmIfTxUAS,
        pmIfRx24hES,
        pmIfRx24hSES,
        pmIfRx24hBBE,
        pmIfRx24hUAS,
        pmIfTx24hES,
        pmIfTx24hSES,
        pmIfTx24hBBE,
        pmIfTx24hUAS,
        pmIfRxPort,
        pmIfReset15Min,
        pmIfReset24H,
        pmIfAdminStatus,
        pmIfOperStatus,
        pmIfIsSuspect15Min,
        pmIfIsSuspect24H,
        pmIfInstallCommand,
        pmIfRxPowerLevel,
        pmIfInitialPowerLevel,
        pmIfRxGbeMaxUtilization,
        pmIfRx24hGbeMaxUtilization,
        pmIfTxPowerLevel,
        pmIfObjectProperty,
        pmIfDelay }
    STATUS      deprecated
    DESCRIPTION
        "The pm interface configuration and current meters objects V10 (15.0)."
    ::= { lumPmGroups 50 }

pmIfGroupV11 OBJECT-GROUP
    OBJECTS {
        pmIfIndex,
        pmIfName,
        pmIfSubrack,
        pmIfSlot,
        pmIfPort,
        pmIfPmReportMode,
        pmIfRxCurrentES,
        pmIfRxCurrentSES,
        pmIfRxCurrentBBE,
        pmIfRxCurrentUAS,
        pmIfTxCurrentES,
        pmIfTxCurrentSES,
        pmIfTxCurrentBBE,
        pmIfTxCurrentUAS,
        pmIfRx24hCurrentES,
        pmIfRx24hCurrentSES,
        pmIfRx24hCurrentBBE,
        pmIfRx24hCurrentUAS,
        pmIfTx24hCurrentES,
        pmIfTx24hCurrentSES,
        pmIfTx24hCurrentBBE,
        pmIfTx24hCurrentUAS,
        pmIfRxESThreshold,
        pmIfRxSESThreshold,
        pmIfRxBBEThreshold,
        pmIfRxUASThreshold,
        pmIfTxESThreshold,
        pmIfTxSESThreshold,
        pmIfTxBBEThreshold,
        pmIfTxUASThreshold,
        pmIfRx24hESThreshold,
        pmIfRx24hSESThreshold,
        pmIfRx24hBBEThreshold,
        pmIfRx24hUASThreshold,
        pmIfTx24hESThreshold,
        pmIfTx24hSESThreshold,
        pmIfTx24hBBEThreshold,
        pmIfTx24hUASThreshold,
        pmIfRxES,
        pmIfRxSES,
        pmIfRxBBE,
        pmIfRxUAS,
        pmIfTxES,
        pmIfTxSES,
        pmIfTxBBE,
        pmIfTxUAS,
        pmIfRx24hES,
        pmIfRx24hSES,
        pmIfRx24hBBE,
        pmIfRx24hUAS,
        pmIfTx24hES,
        pmIfTx24hSES,
        pmIfTx24hBBE,
        pmIfTx24hUAS,
        pmIfRxPort,
        pmIfReset15Min,
        pmIfReset24H,
        pmIfAdminStatus,
        pmIfOperStatus,
        pmIfIsSuspect15Min,
        pmIfIsSuspect24H,
        pmIfInstallCommand,
        pmIfRxPowerLevel,
        pmIfInitialPowerLevel,
        pmIfRxGbeMaxUtilization,
        pmIfRx24hGbeMaxUtilization,
        pmIfTxPowerLevel,
        pmIfObjectProperty,
        pmIfDelay,
        pmIfRxBEREstimation }
    STATUS      deprecated
    DESCRIPTION
        "The pm interface configuration and current meters objects V11 (16.0)."
    ::= { lumPmGroups 51 }

pmEthTdGroupV3 OBJECT-GROUP
    OBJECTS {
        pmEthTdIndex,
        pmEthTdName,
        pmEthTdSubrack,
        pmEthTdSlot,
        pmEthTdPort,
        pmEthTdPmReportMode,
        pmEthTdRxPort,
        pmEthTdReset15Min,
        pmEthTdReset24H,
        pmEthTdAdminStatus,
        pmEthTdOperStatus,
        pmEthTdIsSuspect15Min,
        pmEthTdIsSuspect24h,
        pmEthTdCurrentRxUndersizedFrames,
        pmEthTdCurrentRxOversizedFrames,
        pmEthTdCurrentRxFragments,
        pmEthTdCurrentRxFcsErrors,
        pmEthTdCurrentRxInvalidCeVlanId,
        pmEthTdCurrentTxOctets,
        pmEthTdCurrentTxFrames,
        pmEthTdCurrentTxUnicastFrames,
        pmEthTdCurrentTxMulticastFrames,
        pmEthTdCurrentTxBroadcastFrames,
        pmEthTdCurrentRxOctets,
        pmEthTdCurrentRxFrames,
        pmEthTdCurrentRxUnicastFrames,
        pmEthTdCurrentRxMulticastFrames,
        pmEthTdCurrentRxBroadcastFrames,
        pmEthTdCurrentTxEthMaxUtilization,
        pmEthTdCurrentRxEthMaxUtilization,
        pmEthTdCurrent24hRxUndersizedFrames,
        pmEthTdCurrent24hRxOversizedFrames,
        pmEthTdCurrent24hRxFragments,
        pmEthTdCurrent24hRxFcsErrors,
        pmEthTdCurrent24hRxInvalidCeVlanId,
        pmEthTdCurrent24hTxOctets,
        pmEthTdCurrent24hTxFrames,
        pmEthTdCurrent24hTxUnicastFrames,
        pmEthTdCurrent24hTxMulticastFrames,
        pmEthTdCurrent24hTxBroadcastFrames,
        pmEthTdCurrent24hRxOctets,
        pmEthTdCurrent24hRxFrames,
        pmEthTdCurrent24hRxUnicastFrames,
        pmEthTdCurrent24hRxMulticastFrames,
        pmEthTdCurrent24hRxBroadcastFrames,
        pmEthTdCurrent24hTxEthMaxUtilization,
        pmEthTdCurrent24hRxEthMaxUtilization,
        pmEthTdObjectProperty,
        pmEthTdRxUndersizedFramesThreshold,
        pmEthTdRxOversizedFramesThreshold,
        pmEthTdRxFragmentsThreshold,
        pmEthTdRxFcsErrorsThreshold,
        pmEthTdRxInvalidCeVlanIdThreshold,
        pmEthTd24hRxUndersizedFramesThreshold,
        pmEthTd24hRxOversizedFramesThreshold,
        pmEthTd24hRxFragmentsThreshold,
        pmEthTd24hRxFcsErrorsThreshold,
        pmEthTd24hRxInvalidCeVlanIdThreshold,
        pmEthTdRxUndersizedFrames,
        pmEthTdRxOversizedFrames,
        pmEthTdRxFragments,
        pmEthTdRxFcsErrors,
        pmEthTdRxInvalidCeVlanId,
        pmEthTd24hRxUndersizedFrames,
        pmEthTd24hRxOversizedFrames,
        pmEthTd24hRxFragments,
        pmEthTd24hRxFcsErrors,
        pmEthTd24hRxInvalidCeVlanId,
        pmEthTdResetCont,
        pmEthTdCurrentContRxUndersizedFrames,
        pmEthTdCurrentContRxOversizedFrames,
        pmEthTdCurrentContRxFragments,
        pmEthTdCurrentContRxFcsErrors,
        pmEthTdCurrentContRxInvalidCeVlanId,
        pmEthTdCurrentContTxOctets,
        pmEthTdCurrentContTxFrames,
        pmEthTdCurrentContTxUnicastFrames,
        pmEthTdCurrentContTxMulticastFrames,
        pmEthTdCurrentContTxBroadcastFrames,
        pmEthTdCurrentContRxOctets,
        pmEthTdCurrentContRxFrames,
        pmEthTdCurrentContRxUnicastFrames,
        pmEthTdCurrentContRxMulticastFrames,
        pmEthTdCurrentContRxBroadcastFrames  }
    STATUS      deprecated
    DESCRIPTION
        "The Ethernet Traffic Data PM configuration and current meters objects V3 (16.0)."
    ::= { lumPmGroups 52 }

pmControlGroupV2 OBJECT-GROUP
    OBJECTS {
        pmControlReset15Min,
        pmControlReset24H,
        pmControlResetCont }
    STATUS      current
    DESCRIPTION
        "The control group (16.0)."
    ::= { lumPmGroups 53 }

pmEthDropGroup OBJECT-GROUP
    OBJECTS {
        pmEthDropIndex,
        pmEthDropName,
        pmEthDropSubrack,
        pmEthDropSlot,
        pmEthDropPort,
        pmEthDropRxPort,
        pmEthDropResetCont,
        pmEthDropFrames,
        pmEthDropBytes,
        pmEthDropYellowFrames,
        pmEthDropRedFrames,
        pmEthDropFramesQ1,
        pmEthDropBytesQ1,
        pmEthDropFramesQ2,
        pmEthDropBytesQ2,
        pmEthDropFramesQ3,
        pmEthDropBytesQ3,
        pmEthDropFramesQ4,
        pmEthDropBytesQ4,
        pmEthDropFramesQ5,
        pmEthDropBytesQ5,
        pmEthDropFramesQ6,
        pmEthDropBytesQ6,
        pmEthDropFramesQ7,
        pmEthDropBytesQ7,
        pmEthDropFramesQ8,
        pmEthDropBytesQ8 }
    STATUS      deprecated
    DESCRIPTION
        "The Ethernet drop counters configuration and current meters objects (16.0)."
    ::= { lumPmGroups 54 }

pmEthClassificationGroup OBJECT-GROUP
    OBJECTS {
        pmEthClassificationIndex,
        pmEthClassificationName,
        pmEthClassificationSubrack,
        pmEthClassificationSlot,
        pmEthClassificationIdentifier,
        pmEthClassificationResetCont,
        pmEthClassificationInternalReference,
        pmEthClassificationCounter1,
        pmEthClassificationCounter2 }
    STATUS      current
    DESCRIPTION
        "The Ethernet classification counters configuration and current meters objects (16.0)."
    ::= { lumPmGroups 55 }

pmLogGeneralGroupV5 OBJECT-GROUP
    OBJECTS {
        pmLogGeneralLastChangeTime,
        pmLogGeneralSize,
        pmLogGeneralSize24h,
        pmLogGeneralFileTableSize,
        pmLogGeneralFile24hTableSize,
        pmLogGeneralFile15mLastSeqNumber,
        pmLogGeneralFile24hLastSeqNumber }
    STATUS      current
    DESCRIPTION
        "The general log object v5 (18.0)."
    ::= { lumPmGroups 56 }

pmEthClassificationGroupV2 OBJECT-GROUP
    OBJECTS {
        pmEthClassificationIndex,
        pmEthClassificationName,
        pmEthClassificationSubrack,
        pmEthClassificationSlot,
        pmEthClassificationIdentifier,
        pmEthClassificationResetCont,
        pmEthClassificationInternalReference,
        pmEthClassificationCounter1,
        pmEthClassificationCounter2,
        pmEthClassificationCounter3,
        pmEthClassificationCounter4 }
    STATUS      current
    DESCRIPTION
        "The Ethernet classification counters configuration and current meters objects V2 (18.0)."
    ::= { lumPmGroups 57 }


pmEthTdGroupV4 OBJECT-GROUP
    OBJECTS {
        pmEthTdIndex,
        pmEthTdName,
        pmEthTdSubrack,
        pmEthTdSlot,
        pmEthTdPort,
        pmEthTdPmReportMode,
        pmEthTdRxPort,
        pmEthTdReset15Min,
        pmEthTdReset24H,
        pmEthTdAdminStatus,
        pmEthTdOperStatus,
        pmEthTdIsSuspect15Min,
        pmEthTdIsSuspect24h,
        pmEthTdCurrentRxUndersizedFrames,
        pmEthTdCurrentRxOversizedFrames,
        pmEthTdCurrentRxFragments,
        pmEthTdCurrentRxFcsErrors,
        pmEthTdCurrentRxInvalidCeVlanId,
        pmEthTdCurrentTxOctets,
        pmEthTdCurrentTxFrames,
        pmEthTdCurrentTxUnicastFrames,
        pmEthTdCurrentTxMulticastFrames,
        pmEthTdCurrentTxBroadcastFrames,
        pmEthTdCurrentRxOctets,
        pmEthTdCurrentRxFrames,
        pmEthTdCurrentRxUnicastFrames,
        pmEthTdCurrentRxMulticastFrames,
        pmEthTdCurrentRxBroadcastFrames,
        pmEthTdCurrentTxEthMaxUtilization,
        pmEthTdCurrentRxEthMaxUtilization,
        pmEthTdCurrent24hRxUndersizedFrames,
        pmEthTdCurrent24hRxOversizedFrames,
        pmEthTdCurrent24hRxFragments,
        pmEthTdCurrent24hRxFcsErrors,
        pmEthTdCurrent24hRxInvalidCeVlanId,
        pmEthTdCurrent24hTxOctets,
        pmEthTdCurrent24hTxFrames,
        pmEthTdCurrent24hTxUnicastFrames,
        pmEthTdCurrent24hTxMulticastFrames,
        pmEthTdCurrent24hTxBroadcastFrames,
        pmEthTdCurrent24hRxOctets,
        pmEthTdCurrent24hRxFrames,
        pmEthTdCurrent24hRxUnicastFrames,
        pmEthTdCurrent24hRxMulticastFrames,
        pmEthTdCurrent24hRxBroadcastFrames,
        pmEthTdCurrent24hTxEthMaxUtilization,
        pmEthTdCurrent24hRxEthMaxUtilization,
        pmEthTdObjectProperty,
        pmEthTdRxUndersizedFramesThreshold,
        pmEthTdRxOversizedFramesThreshold,
        pmEthTdRxFragmentsThreshold,
        pmEthTdRxFcsErrorsThreshold,
        pmEthTdRxInvalidCeVlanIdThreshold,
        pmEthTd24hRxUndersizedFramesThreshold,
        pmEthTd24hRxOversizedFramesThreshold,
        pmEthTd24hRxFragmentsThreshold,
        pmEthTd24hRxFcsErrorsThreshold,
        pmEthTd24hRxInvalidCeVlanIdThreshold,
        pmEthTdRxUndersizedFrames,
        pmEthTdRxOversizedFrames,
        pmEthTdRxFragments,
        pmEthTdRxFcsErrors,
        pmEthTdRxInvalidCeVlanId,
        pmEthTd24hRxUndersizedFrames,
        pmEthTd24hRxOversizedFrames,
        pmEthTd24hRxFragments,
        pmEthTd24hRxFcsErrors,
        pmEthTd24hRxInvalidCeVlanId,
        pmEthTdResetCont,
        pmEthTdCurrentContRxUndersizedFrames,
        pmEthTdCurrentContRxOversizedFrames,
        pmEthTdCurrentContRxFragments,
        pmEthTdCurrentContRxFcsErrors,
        pmEthTdCurrentContRxInvalidCeVlanId,
        pmEthTdCurrentContTxOctets,
        pmEthTdCurrentContTxFrames,
        pmEthTdCurrentContTxUnicastFrames,
        pmEthTdCurrentContTxMulticastFrames,
        pmEthTdCurrentContTxBroadcastFrames,
        pmEthTdCurrentContRxOctets,
        pmEthTdCurrentContRxFrames,
        pmEthTdCurrentContRxUnicastFrames,
        pmEthTdCurrentContRxMulticastFrames,
        pmEthTdCurrentContRxBroadcastFrames,
        pmEthTdVlanId
  }
    STATUS      deprecated
    DESCRIPTION
        "The Ethernet Traffic Data PM configuration and current meters objects V4 (R21 ??)."
    ::= { lumPmGroups 58 }

pmEthTdGroupV5 OBJECT-GROUP
    OBJECTS {
        pmEthTdIndex,
        pmEthTdName,
        pmEthTdSubrack,
        pmEthTdSlot,
        pmEthTdPort,
        pmEthTdPmReportMode,
        pmEthTdRxPort,
        pmEthTdReset15Min,
        pmEthTdReset24H,
        pmEthTdAdminStatus,
        pmEthTdOperStatus,
        pmEthTdIsSuspect15Min,
        pmEthTdIsSuspect24h,
        pmEthTdCurrentRxUndersizedFrames,
        pmEthTdCurrentRxOversizedFrames,
        pmEthTdCurrentRxFragments,
        pmEthTdCurrentRxFcsErrors,
        pmEthTdCurrentRxInvalidCeVlanId,
        pmEthTdCurrentTxOctets,
        pmEthTdCurrentTxFrames,
        pmEthTdCurrentTxUnicastFrames,
        pmEthTdCurrentTxMulticastFrames,
        pmEthTdCurrentTxBroadcastFrames,
        pmEthTdCurrentRxOctets,
        pmEthTdCurrentRxFrames,
        pmEthTdCurrentRxUnicastFrames,
        pmEthTdCurrentRxMulticastFrames,
        pmEthTdCurrentRxBroadcastFrames,
        pmEthTdCurrentTxEthMaxUtilization,
        pmEthTdCurrentRxEthMaxUtilization,
        pmEthTdCurrent24hRxUndersizedFrames,
        pmEthTdCurrent24hRxOversizedFrames,
        pmEthTdCurrent24hRxFragments,
        pmEthTdCurrent24hRxFcsErrors,
        pmEthTdCurrent24hRxInvalidCeVlanId,
        pmEthTdCurrent24hTxOctets,
        pmEthTdCurrent24hTxFrames,
        pmEthTdCurrent24hTxUnicastFrames,
        pmEthTdCurrent24hTxMulticastFrames,
        pmEthTdCurrent24hTxBroadcastFrames,
        pmEthTdCurrent24hRxOctets,
        pmEthTdCurrent24hRxFrames,
        pmEthTdCurrent24hRxUnicastFrames,
        pmEthTdCurrent24hRxMulticastFrames,
        pmEthTdCurrent24hRxBroadcastFrames,
        pmEthTdCurrent24hTxEthMaxUtilization,
        pmEthTdCurrent24hRxEthMaxUtilization,
        pmEthTdObjectProperty,
        pmEthTdRxUndersizedFramesThreshold,
        pmEthTdRxOversizedFramesThreshold,
        pmEthTdRxFragmentsThreshold,
        pmEthTdRxFcsErrorsThreshold,
        pmEthTdRxInvalidCeVlanIdThreshold,
        pmEthTd24hRxUndersizedFramesThreshold,
        pmEthTd24hRxOversizedFramesThreshold,
        pmEthTd24hRxFragmentsThreshold,
        pmEthTd24hRxFcsErrorsThreshold,
        pmEthTd24hRxInvalidCeVlanIdThreshold,
        pmEthTdRxUndersizedFrames,
        pmEthTdRxOversizedFrames,
        pmEthTdRxFragments,
        pmEthTdRxFcsErrors,
        pmEthTdRxInvalidCeVlanId,
        pmEthTd24hRxUndersizedFrames,
        pmEthTd24hRxOversizedFrames,
        pmEthTd24hRxFragments,
        pmEthTd24hRxFcsErrors,
        pmEthTd24hRxInvalidCeVlanId,
        pmEthTdResetCont,
        pmEthTdCurrentContRxUndersizedFrames,
        pmEthTdCurrentContRxOversizedFrames,
        pmEthTdCurrentContRxFragments,
        pmEthTdCurrentContRxFcsErrors,
        pmEthTdCurrentContRxInvalidCeVlanId,
        pmEthTdCurrentContTxOctets,
        pmEthTdCurrentContTxFrames,
        pmEthTdCurrentContTxUnicastFrames,
        pmEthTdCurrentContTxMulticastFrames,
        pmEthTdCurrentContTxBroadcastFrames,
        pmEthTdCurrentContRxOctets,
        pmEthTdCurrentContRxFrames,
        pmEthTdCurrentContRxUnicastFrames,
        pmEthTdCurrentContRxMulticastFrames,
        pmEthTdCurrentContRxBroadcastFrames,
        pmEthTdVlanId,
		pmEthTdIfNo,
		pmEthTdUpPortId
  }
    STATUS      current
    DESCRIPTION
        "The Ethernet Traffic Data PM configuration and current meters objects V5 (R26.1)."
    ::= { lumPmGroups 59 }


pmIfGroupV12 OBJECT-GROUP
    OBJECTS {
        pmIfIndex,
        pmIfName,
        pmIfSubrack,
        pmIfSlot,
        pmIfPort,
        pmIfPmReportMode,
        pmIfRxCurrentES,
        pmIfRxCurrentSES,
        pmIfRxCurrentBBE,
        pmIfRxCurrentUAS,
        pmIfTxCurrentES,
        pmIfTxCurrentSES,
        pmIfTxCurrentBBE,
        pmIfTxCurrentUAS,
        pmIfRx24hCurrentES,
        pmIfRx24hCurrentSES,
        pmIfRx24hCurrentBBE,
        pmIfRx24hCurrentUAS,
        pmIfTx24hCurrentES,
        pmIfTx24hCurrentSES,
        pmIfTx24hCurrentBBE,
        pmIfTx24hCurrentUAS,
        pmIfRxESThreshold,
        pmIfRxSESThreshold,
        pmIfRxBBEThreshold,
        pmIfRxUASThreshold,
        pmIfTxESThreshold,
        pmIfTxSESThreshold,
        pmIfTxBBEThreshold,
        pmIfTxUASThreshold,
        pmIfRx24hESThreshold,
        pmIfRx24hSESThreshold,
        pmIfRx24hBBEThreshold,
        pmIfRx24hUASThreshold,
        pmIfTx24hESThreshold,
        pmIfTx24hSESThreshold,
        pmIfTx24hBBEThreshold,
        pmIfTx24hUASThreshold,
        pmIfRxES,
        pmIfRxSES,
        pmIfRxBBE,
        pmIfRxUAS,
        pmIfTxES,
        pmIfTxSES,
        pmIfTxBBE,
        pmIfTxUAS,
        pmIfRx24hES,
        pmIfRx24hSES,
        pmIfRx24hBBE,
        pmIfRx24hUAS,
        pmIfTx24hES,
        pmIfTx24hSES,
        pmIfTx24hBBE,
        pmIfTx24hUAS,
        pmIfRxPort,
        pmIfReset15Min,
        pmIfReset24H,
        pmIfAdminStatus,
        pmIfOperStatus,
        pmIfIsSuspect15Min,
        pmIfIsSuspect24H,
        pmIfInstallCommand,
        pmIfRxPowerLevel,
        pmIfInitialPowerLevel,
        pmIfRxGbeMaxUtilization,
        pmIfRx24hGbeMaxUtilization,
        pmIfTxPowerLevel,
        pmIfObjectProperty,
        pmIfDelay,
        pmIfRxBEREstimation,
        pmIfIfNo,
        pmIfUpPortId
        }
    STATUS      current
    DESCRIPTION
        "The pm interface configuration and current meters objects V12 (R26.1)."
    ::= { lumPmGroups 60 }

pmGeneralGroupV5 OBJECT-GROUP
    OBJECTS {
        pmGeneralLastChangeTime,
        pmGeneralStateLastChangeTime,
        pmGeneralPmIfTableSize,
        pmGeneralPmEthTdTableSize,
        pmGeneralPmEthTmTableSize,
        pmGeneralPmEthOamTableSize,
        pmGeneralPmMpoLanesTableSize
        }
    STATUS      current
    DESCRIPTION
        "The general objects. (27.0)"
    ::= { lumPmGroups 61 }

pmEthDropGroupV2 OBJECT-GROUP
    OBJECTS {
        pmEthDropIndex,
        pmEthDropName,
        pmEthDropSubrack,
        pmEthDropSlot,
        pmEthDropPort,
        pmEthDropRxPort,
        pmEthDropResetCont,
        pmEthDropFrames,
        pmEthDropBytes,
        pmEthDropYellowFrames,
        pmEthDropRedFrames,
        pmEthDropFramesQ1,
        pmEthDropBytesQ1,
        pmEthDropFramesQ2,
        pmEthDropBytesQ2,
        pmEthDropFramesQ3,
        pmEthDropBytesQ3,
        pmEthDropFramesQ4,
        pmEthDropBytesQ4,
        pmEthDropFramesQ5,
        pmEthDropBytesQ5,
        pmEthDropFramesQ6,
        pmEthDropBytesQ6,
        pmEthDropFramesQ7,
        pmEthDropBytesQ7,
        pmEthDropFramesQ8,
        pmEthDropBytesQ8,
        pmEthDropIfNo,
        pmEthDropUpPortId }
    STATUS      deprecated
    DESCRIPTION
        "The Ethernet drop counters configuration and current meters objects (27.0)."
    ::= { lumPmGroups 62 }

pmEthDropGroupV3 OBJECT-GROUP
    OBJECTS {
        pmEthDropIndex,
        pmEthDropName,
        pmEthDropSubrack,
        pmEthDropSlot,
        pmEthDropPort,
        pmEthDropRxPort,
        pmEthDropResetCont,
        pmEthDropFrames,
        pmEthDropBytes,
        pmEthDropYellowFrames,
        pmEthDropRedFrames,
        pmEthDropFramesQ1,
        pmEthDropBytesQ1,
        pmEthDropFramesQ2,
        pmEthDropBytesQ2,
        pmEthDropFramesQ3,
        pmEthDropBytesQ3,
        pmEthDropFramesQ4,
        pmEthDropBytesQ4,
        pmEthDropFramesQ5,
        pmEthDropBytesQ5,
        pmEthDropFramesQ6,
        pmEthDropBytesQ6,
        pmEthDropFramesQ7,
        pmEthDropBytesQ7,
        pmEthDropFramesQ8,
        pmEthDropBytesQ8,
        pmEthDropIfNo,
        pmEthDropUpPortId,
        pmEthDropReset15m,
        pmEthDropReset24h,
        pmEthDropReportMode,
        pmEthDropIsSuspect15Min,
        pmEthDropIsSuspect24H}
    STATUS      current
    DESCRIPTION
        "The Ethernet drop counters configuration and current meters objects (32.0)."
    ::= { lumPmGroups 63 }

pmEthEgressGroup OBJECT-GROUP
    OBJECTS {
        pmEthEgressIndex,
        pmEthEgressName,
        pmEthEgressSubrack,
        pmEthEgressSlot,
        pmEthEgressPort,
        pmEthEgressFramesQ1,
        pmEthEgressBytesQ1,
        pmEthEgressBandwidthQ1,
        pmEthEgressFrames15mQ1,
        pmEthEgressBytes15mQ1,
        pmEthEgressFrames24hQ1,
        pmEthEgressBytes24hQ1,
        pmEthEgressFramesQ2,
        pmEthEgressBytesQ2,
        pmEthEgressBandwidthQ2,
        pmEthEgressFrames15mQ2,
        pmEthEgressBytes15mQ2,
        pmEthEgressFrames24hQ2,
        pmEthEgressBytes24hQ2,
        pmEthEgressFramesQ3,
        pmEthEgressBytesQ3,
        pmEthEgressBandwidthQ3,
        pmEthEgressFrames15mQ3,
        pmEthEgressBytes15mQ3,
        pmEthEgressFrames24hQ3,
        pmEthEgressBytes24hQ3,
        pmEthEgressFramesQ4,
        pmEthEgressBytesQ4,
        pmEthEgressBandwidthQ4,
        pmEthEgressFrames15mQ4,
        pmEthEgressBytes15mQ4,
        pmEthEgressFrames24hQ4,
        pmEthEgressBytes24hQ4,
        pmEthEgressFramesQ5,
        pmEthEgressBytesQ5,
        pmEthEgressBandwidthQ5,
        pmEthEgressFrames15mQ5,
        pmEthEgressBytes15mQ5,
        pmEthEgressFrames24hQ5,
        pmEthEgressBytes24hQ5,
        pmEthEgressFramesQ6,
        pmEthEgressBytesQ6,
        pmEthEgressBandwidthQ6,
        pmEthEgressFrames15mQ6,
        pmEthEgressBytes15mQ6,
        pmEthEgressFrames24hQ6,
        pmEthEgressBytes24hQ6,
        pmEthEgressFramesQ7,
        pmEthEgressBytesQ7,
        pmEthEgressBandwidthQ7,
        pmEthEgressFrames15mQ7,
        pmEthEgressBytes15mQ7,
        pmEthEgressFrames24hQ7,
        pmEthEgressBytes24hQ7,
        pmEthEgressFramesQ8,
        pmEthEgressBytesQ8,
        pmEthEgressBandwidthQ8,
        pmEthEgressFrames15mQ8,
        pmEthEgressBytes15mQ8,
        pmEthEgressFrames24hQ8,
        pmEthEgressBytes24hQ8,
        pmEthEgressResetCont,
        pmEthEgressReset15m,
        pmEthEgressReset24h,
        pmEthEgressReportMode,
        pmEthEgressIsSuspect15Min,
        pmEthEgressIsSuspect24H}

    STATUS      current
    DESCRIPTION
        "The Ethernet egress counters configuration and current meters objects (32.0)."
    ::= { lumPmGroups 64 }


-- ----------------------------------------------------
-- Compliance
-- ----------------------------------------------------

lumPmBasicComplV1 MODULE-COMPLIANCE
    STATUS      deprecated
    DESCRIPTION
        "Basic implementation requirements for the PM MIB."
    MODULE
        MANDATORY-GROUPS {
            pmGeneralGroup,
            pmIfGroup}
    ::= { lumPmCompl 1 }

lumPmBasicComplV2 MODULE-COMPLIANCE
    STATUS      deprecated
    DESCRIPTION
        "Basic implementation requirements for the PM MIB V2."
    MODULE
        MANDATORY-GROUPS {
            pmGeneralGroup,
            pmIfGroupV2,
            pmIntervalGroup,
            pmInterval24hGroup,
            pmLogGeneralGroup,
            pmFileGroup,
            pmFile24hGroup,
            pmNotificationGroup }
    ::= { lumPmCompl 2 }

lumPmBasicComplV3 MODULE-COMPLIANCE
    STATUS      deprecated
    DESCRIPTION
        "Basic implementation requirements for the PM MIB V3."
    MODULE
        MANDATORY-GROUPS {
            pmGeneralGroupV2,
            pmIfGroupV2,
            pmIntervalGroup,
            pmInterval24hGroup,
            pmLogGeneralGroup,
            pmFileGroup,
            pmFile24hGroup,
            pmNotificationGroup }
    ::= { lumPmCompl 3 }

lumPmBasicComplV4 MODULE-COMPLIANCE
    STATUS      deprecated
    DESCRIPTION
        "Basic implementation requirements for the PM MIB V4."
    MODULE
        MANDATORY-GROUPS {
            pmGeneralGroupV2,
            pmIfGroupV3,
            pmIntervalGroup,
            pmInterval24hGroup,
            pmLogGeneralGroup,
            pmFileGroup,
            pmFile24hGroup,
            pmNotificationGroup,
            pmControlGroup }
    ::= { lumPmCompl 4 }

lumPmBasicComplV5 MODULE-COMPLIANCE
    STATUS      deprecated
    DESCRIPTION
        "Basic implementation requirements for the PM MIB V5."
    MODULE
        MANDATORY-GROUPS {
            pmGeneralGroupV2,
            pmIfGroupV3,
            pmIntervalGroup,
            pmInterval24hGroup,
            pmLogGeneralGroup,
            pmFileGroupV2,
            pmFile24hGroupV2,
            pmNotificationGroup,
            pmControlGroup }
    ::= { lumPmCompl 5 }

lumPmBasicComplV6 MODULE-COMPLIANCE
    STATUS      deprecated
    DESCRIPTION
        "Basic implementation requirements for the PM MIB V6."
    MODULE
        MANDATORY-GROUPS {
            pmGeneralGroupV2,
            pmIfGroupV4,
            pmIntervalGroup,
            pmInterval24hGroup,
            pmLogGeneralGroup,
            pmFileGroupV2,
            pmFile24hGroupV2,
            pmNotificationGroup,
            pmControlGroup }
    ::= { lumPmCompl 6 }

lumPmBasicComplV7 MODULE-COMPLIANCE
    STATUS      deprecated
    DESCRIPTION
        "Basic implementation requirements for the PM MIB V7."
    MODULE
        MANDATORY-GROUPS {
            pmGeneralGroupV2,
            pmIfGroupV5,
            pmIntervalGroup,
            pmInterval24hGroup,
            pmLogGeneralGroup,
            pmFileGroupV3,
            pmFile24hGroupV3,
            pmNotificationGroup,
            pmControlGroup }
    ::= { lumPmCompl 7 }

lumPmBasicComplV8 MODULE-COMPLIANCE
    STATUS      deprecated
    DESCRIPTION
        "Basic implementation requirements for the PM MIB V8."
    MODULE
        MANDATORY-GROUPS {
            pmGeneralGroupV2,
            pmIfGroupV5,
            pmIntervalGroup,
            pmInterval24hGroup,
            pmLogGeneralGroup,
            pmFileGroupV4,
            pmFile24hGroupV4,
            pmNotificationGroup,
            pmControlGroup }
    ::= { lumPmCompl 8 }

lumPmBasicComplV9 MODULE-COMPLIANCE
    STATUS      deprecated
    DESCRIPTION
        "Basic implementation requirements for the PM MIB V9 (3.0)."
    MODULE
        MANDATORY-GROUPS {
            pmGeneralGroupV2,
            pmIfGroupV6,
            pmIntervalGroupV2,
            pmInterval24hGroupV2,
            pmLogGeneralGroup,
            pmFileGroupV4,
            pmFile24hGroupV4,
            pmNotificationGroup,
            pmControlGroup }
    ::= { lumPmCompl 9 }

lumPmBasicComplV10 MODULE-COMPLIANCE
    STATUS      deprecated
    DESCRIPTION
        "Basic implementation requirements for the PM MIB V10 (3.1)."
    MODULE
        MANDATORY-GROUPS {
            pmGeneralGroupV3,
            pmIfGroupV7,
            pmIntervalGroupV3,
            pmInterval24hGroupV3,
            pmLogGeneralGroupV2,
            pmFileGroupV4,
            pmFile24hGroupV4,
            pmNotificationGroup,
            pmControlGroup }
    ::= { lumPmCompl 10 }

lumPmBasicComplV11 MODULE-COMPLIANCE
    STATUS      deprecated
    DESCRIPTION
        "Basic implementation requirements for the PM MIB V11 (3.2)."
    MODULE
        MANDATORY-GROUPS {
            pmGeneralGroupV3,
            pmIfGroupV7,
            pmIntervalGroupV4,
            pmInterval24hGroupV4,
            pmLogGeneralGroupV3,
            pmFileGroupV4,
            pmFile24hGroupV4,
            pmNotificationGroup,
            pmControlGroup }
    ::= { lumPmCompl 11 }

lumPmBasicComplV12 MODULE-COMPLIANCE
    STATUS      deprecated
    DESCRIPTION
        "Basic implementation requirements for the PM MIB V12 (6.0)."
    MODULE
        MANDATORY-GROUPS {
            pmGeneralGroupV3,
            pmIfGroupV8,
            pmIntervalGroupV5,
            pmInterval24hGroupV5,
            pmLogGeneralGroupV3,
            pmFileGroupV4,
            pmFile24hGroupV4,
            pmNotificationGroup,
            pmControlGroup }
    ::= { lumPmCompl 12 }

lumPmBasicComplV13 MODULE-COMPLIANCE
    STATUS      deprecated
    DESCRIPTION
        "Basic implementation requirements for the PM MIB V13 (10.0)."
    MODULE
        MANDATORY-GROUPS {
            pmGeneralGroupV3,
            pmIfGroupV8,
            pmIntervalGroupV5,
            pmInterval24hGroupV5,
            pmLogGeneralGroupV4,
            pmFileGroupV4,
            pmFile24hGroupV4,
            pmNotificationGroup,
            pmControlGroup }
    ::= { lumPmCompl 13 }

lumPmBasicComplV14 MODULE-COMPLIANCE
    STATUS      deprecated
    DESCRIPTION
        "Basic implementation requirements for the PM MIB V14 (11.0)."
    MODULE
        MANDATORY-GROUPS {
            pmGeneralGroupV4,
            pmIfGroupV9,
            pmEthTdGroup,
            pmEthTmGroup,
            pmEthOamGroup,
            pmIntervalGroupV5,
            pmInterval24hGroupV5,
            pmLogGeneralGroupV4,
            pmFileGroupV4,
            pmFile24hGroupV4,
            pmNotificationGroup,
            pmControlGroup }
    ::= { lumPmCompl 14 }

lumPmBasicComplV15 MODULE-COMPLIANCE
    STATUS      deprecated
    DESCRIPTION
        "Basic implementation requirements for the PM MIB V15 (12.0)."
    MODULE
        MANDATORY-GROUPS {
            pmGeneralGroupV4,
            pmIfGroupV9,
            pmEthTdGroupV2,
            pmEthTmGroup,
            pmEthOamGroup,
            pmIntervalGroupV7,
            pmInterval24hGroupV7,
            pmLogGeneralGroupV4,
            pmFileGroupV4,
            pmFile24hGroupV4,
            pmNotificationGroup,
            pmControlGroup }
    ::= { lumPmCompl 15 }

lumPmBasicComplV16 MODULE-COMPLIANCE
    STATUS      deprecated
    DESCRIPTION
        "Basic implementation requirements for the PM MIB V16 (15.0)."
    MODULE
        MANDATORY-GROUPS {
            pmGeneralGroupV4,
            pmIfGroupV10,
            pmEthTdGroupV2,
            pmEthTmGroup,
            pmEthOamGroup,
            pmIntervalGroupV7,
            pmInterval24hGroupV7,
            pmLogGeneralGroupV4,
            pmFileGroupV4,
            pmFile24hGroupV4,
            pmNotificationGroup,
            pmControlGroup }
    ::= { lumPmCompl 16 }

lumPmBasicComplV17 MODULE-COMPLIANCE
    STATUS      deprecated
    DESCRIPTION
        "Basic implementation requirements for the PM MIB V17 (16.0)."
    MODULE
        MANDATORY-GROUPS {
            pmGeneralGroupV4,
            pmIfGroupV11,
            pmEthTdGroupV3,
            pmEthTmGroup,
            pmEthOamGroup,
            pmIntervalGroupV8,
            pmInterval24hGroupV8,
            pmLogGeneralGroupV4,
            pmFileGroupV4,
            pmFile24hGroupV4,
            pmNotificationGroup,
            pmControlGroupV2,
            pmEthDropGroup,
            pmEthClassificationGroup }
    ::= { lumPmCompl 17 }

lumPmBasicComplV18 MODULE-COMPLIANCE
    STATUS      deprecated
    DESCRIPTION
        "Basic implementation requirements for the PM MIB V18 (17.0)."
    MODULE
        MANDATORY-GROUPS {
            pmGeneralGroupV4,
            pmIfGroupV11,
            pmEthTdGroupV3,
--          pmEthTmGroup,
--          pmEthOamGroup,
--          pmIntervalGroupV8,
--          pmInterval24hGroupV8,
            pmLogGeneralGroupV4,
            pmFileGroupV4,
            pmFile24hGroupV4,
            pmNotificationGroup,
            pmControlGroupV2,
            pmEthDropGroup,
            pmEthClassificationGroup }
    ::= { lumPmCompl 18 }

lumPmBasicComplV19 MODULE-COMPLIANCE
    STATUS      deprecated
    DESCRIPTION
        "Basic implementation requirements for the PM MIB V19 (17.0)."
    MODULE
        MANDATORY-GROUPS {
            pmGeneralGroupV4,
            pmIfGroupV11,
            pmEthTdGroupV3,
--          pmEthTmGroup,
--          pmEthOamGroup,
--          pmIntervalGroupV8,
--          pmInterval24hGroupV8,
            pmLogGeneralGroupV5,
            pmFileGroupV4,
            pmFile24hGroupV4,
            pmNotificationGroup,
            pmControlGroupV2,
            pmEthDropGroup,
            pmEthClassificationGroup }
    ::= { lumPmCompl 19 }

lumPmBasicComplV20 MODULE-COMPLIANCE
    STATUS      deprecated
    DESCRIPTION
        "Basic implementation requirements for the PM MIB V20 (18.0)."
    MODULE
        MANDATORY-GROUPS {
            pmGeneralGroupV4,
            pmIfGroupV11,
            pmEthTdGroupV3,
--          pmEthTmGroup,
--          pmEthOamGroup,
--          pmIntervalGroupV8,
--          pmInterval24hGroupV8,
            pmLogGeneralGroupV5,
            pmFileGroupV4,
            pmFile24hGroupV4,
            pmNotificationGroup,
            pmControlGroupV2,
            pmEthDropGroup,
            pmEthClassificationGroupV2 }
    ::= { lumPmCompl 20 }

lumPmBasicComplV21 MODULE-COMPLIANCE
    STATUS      deprecated
    DESCRIPTION
        "Basic implementation requirements for the PM MIB V21 (R21.0)."
    MODULE
        MANDATORY-GROUPS {
            pmGeneralGroupV4,
            pmIfGroupV11,
            pmEthTdGroupV4,
--          pmEthTmGroup,
--          pmEthOamGroup,
--          pmIntervalGroupV8,
--          pmInterval24hGroupV8,
            pmLogGeneralGroupV5,
            pmFileGroupV4,
            pmFile24hGroupV4,
            pmNotificationGroup,
            pmControlGroupV2,
            pmEthDropGroup,
            pmEthClassificationGroupV2 }
    ::= { lumPmCompl 21 }


lumPmBasicComplV22 MODULE-COMPLIANCE
    STATUS      deprecated
    DESCRIPTION
        "Basic implementation requirements for the PM MIB V22 (R26.1)."
    MODULE
        MANDATORY-GROUPS {
            pmGeneralGroupV4,
            pmIfGroupV11,
            pmEthTdGroupV5,
--          pmEthTmGroup,
--          pmEthOamGroup,
--          pmIntervalGroupV8,
--          pmInterval24hGroupV8,
            pmLogGeneralGroupV5,
            pmFileGroupV4,
            pmFile24hGroupV4,
            pmNotificationGroup,
            pmControlGroupV2,
            pmEthDropGroup,
            pmEthClassificationGroupV2 }
    ::= { lumPmCompl 22 }


lumPmBasicComplV23 MODULE-COMPLIANCE
    STATUS      deprecated
    DESCRIPTION
        "Basic implementation requirements for the PM MIB V23 (R27.0)."
    MODULE
        MANDATORY-GROUPS {
            pmGeneralGroupV5,
            pmIfGroupV11,
            pmEthTdGroupV5,
--          pmEthTmGroup,
--          pmEthOamGroup,
--          pmIntervalGroupV8,
--          pmInterval24hGroupV8,
            pmLogGeneralGroupV5,
            pmFileGroupV4,
            pmFile24hGroupV4,
            pmNotificationGroup,
            pmControlGroupV2,
            pmEthDropGroupV2,
            pmEthClassificationGroupV2 }
    ::= { lumPmCompl 23 }

lumPmBasicComplV24 MODULE-COMPLIANCE
    STATUS      current
    DESCRIPTION
        "Basic implementation requirements for the PM MIB V24 (R32.0)."
    MODULE
        MANDATORY-GROUPS {
            pmGeneralGroupV5,
            pmIfGroupV11,
            pmEthTdGroupV5,
--          pmEthTmGroup,
--          pmEthOamGroup,
--          pmIntervalGroupV8,
--          pmInterval24hGroupV8,
            pmLogGeneralGroupV5,
            pmFileGroupV4,
            pmFile24hGroupV4,
            pmNotificationGroup,
            pmControlGroupV2,
            pmEthDropGroupV3,
            pmEthClassificationGroupV2,
            pmEthEgressGroup }
    ::= { lumPmCompl 24 }


END
