-- *****************************************************************
-- INFINERA-TP-CHANNELCTP-MIB
--
-- October 2008, Sharfuddin Syed / Narendra Gupta
--
--
-- Copyright (c) 2008-2012 by Infinera Inc.
-- All rights reserved.
-- ****************************************************************

INFINERA-TP-CHANNELCTP-MIB DEFINITIONS ::= BEGIN

IMPORTS
    MODULE-IDENTITY, OBJECT-TYPE,
    Integer32                                   FROM SNMPv2-SMI
    MODULE-COMPLIANCE, OBJECT-GROUP             FROM SNMPv2-CONF
    DisplayString, TruthValue                   FROM SNMPv2-TC
    ifIndex                                     FROM IF-MIB
    terminationPoint                            FROM INFINERA-REG-MIB;


channelCtpMIB MODULE-IDENTITY
    LAST-UPDATED  "200810200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "200810200000Z"
    DESCRIPTION
        "First Version"
    ::= { terminationPoint 4 }



channelCtpTable OBJECT-TYPE
    SYNTAX      SEQUENCE OF ChannelCtpEntry
    MAX-ACCESS  not-accessible
    STATUS      current
    DESCRIPTION
        "A list of ChannelCtp entries. Each entry is uniquely identified by the value of ifIndex."
    ::= { channelCtpMIB 1 }

channelCtpEntry  OBJECT-TYPE
    SYNTAX      ChannelCtpEntry
    MAX-ACCESS  not-accessible
    STATUS      current
    DESCRIPTION
        "A ChannelCtp entry containing information pertaining to Infinera ChannelCtp interfaces.
        This table is a subclass of IfCommon.
        Entries will exist in this table only for interfaces of type ChannelCtp.
        The Channel CTP models the termination point that corresponds to the individual lambda or wavelength."
    INDEX { ifIndex }
    ::= { channelCtpTable 1 }


ChannelCtpEntry  ::= SEQUENCE {
    channelCtpPreFecThresholdOrder           Integer32,
    channelCtpPreFecThresholdMantissa        Integer32,
    channelCtpSignalDegradeReporting         INTEGER,
    channelCtpInsertDtsTti                   TruthValue,
    channelCtpDtsTtiAlarmReporting           INTEGER,
    channelCtpTxDtsTti                       DisplayString,
    channelCtpExpectedDtsTti                 DisplayString,
    channelCtpRxDtsTti                       DisplayString,
    channelCtpDtsCv15MinutesTce              Integer32,
    channelCtpDtsEs15MinutesTce              Integer32,
    channelCtpDtsSes15MinutesTce             Integer32,
    channelCtpDtsCvDayTce                    Integer32,
    channelCtpDtsEsDayTce                    Integer32,
    channelCtpDtsSesDayTce                   Integer32,
    channelCtpDtsCv15MinutesTceReporting     TruthValue,
    channelCtpDtsEs15MinutesTceReporting     TruthValue,
    channelCtpDtsSes15MinutesTceReporting    TruthValue,
    channelCtpDtsCvDayTceReporting           TruthValue,
    channelCtpDtsEsDayTceReporting           TruthValue,
    channelCtpDtsSesDayTceReporting          TruthValue,
    channelCtpPrbsGenerationMode             INTEGER,
    channelCtpPrbsMonitoringMode             INTEGER,
    channelCtpTEEnabled                      TruthValue,
    channelCtpPmHistStatsEnable              INTEGER
}

channelCtpPreFecThresholdOrder OBJECT-TYPE
    SYNTAX      Integer32
    MAX-ACCESS  read-write
    STATUS      current
    DESCRIPTION "Pre-FEC BER threshold exponent."
    DEFVAL      { -4 }
    ::= { channelCtpEntry  1 }


channelCtpPreFecThresholdMantissa OBJECT-TYPE
    SYNTAX      Integer32
    MAX-ACCESS  read-write
    STATUS      current
    DESCRIPTION "Pre-FEC BER threshold matissa range."
    DEFVAL      { 1 }
    ::= { channelCtpEntry  2 }


channelCtpSignalDegradeReporting OBJECT-TYPE
    SYNTAX  INTEGER {
        disabled(1),
        enabled(2)
    }
    MAX-ACCESS  read-write
    STATUS      current
    DESCRIPTION
        "When enabled and when the channel is in signal degraded state, the Signal Degrade alarm
        is raised. If the value is disabled, the alarm is not raised (even under SD condition)."
    DEFVAL      { enabled }
    ::= { channelCtpEntry  3 }


channelCtpInsertDtsTti OBJECT-TYPE
    SYNTAX      TruthValue
    MAX-ACCESS  read-write
    STATUS      current
    DESCRIPTION "Flag that enables the TTI string to be entered and monitored at the far end."
    DEFVAL      { false }
    ::= { channelCtpEntry  4 }


channelCtpDtsTtiAlarmReporting OBJECT-TYPE
    SYNTAX  INTEGER {
        disabled(1),
        enabled(2)
    }
    MAX-ACCESS  read-write
    STATUS      current
    DESCRIPTION
        "Controls whether DTS Trail Trace Identifier will be transmitted."
    DEFVAL      { disabled }
    ::= { channelCtpEntry  5 }


channelCtpTxDtsTti OBJECT-TYPE
    SYNTAX      DisplayString
    MAX-ACCESS  read-write
    STATUS      current
    DESCRIPTION
        "The transmitted Dts trail trace identifier."
    ::= { channelCtpEntry  6 }


channelCtpExpectedDtsTti OBJECT-TYPE
    SYNTAX      DisplayString
    MAX-ACCESS  read-write
    STATUS      current
    DESCRIPTION
        "The Expected DTS TTI. If this is not equal to the zero-length string and it doesn't match
        the recived TTI, an alarm will be raised."
    ::= { channelCtpEntry  7 }


channelCtpRxDtsTti OBJECT-TYPE
    SYNTAX      DisplayString
    MAX-ACCESS  read-only
    STATUS      current
    DESCRIPTION
        "The received Dts trail trace identifier."
    ::= { channelCtpEntry  8 }


channelCtpDtsCv15MinutesTce OBJECT-TYPE
    SYNTAX      Integer32
    MAX-ACCESS  read-write
    STATUS      current
    DESCRIPTION "Count of BIP errors detected at the DTF Path layer. Up to 8 path BIP errors can be detected per frame, with each error incrementing the DTFDLM- CV-S current register."
    DEFVAL      { 1500 }
    ::= { channelCtpEntry  9 }


channelCtpDtsEs15MinutesTce OBJECT-TYPE
    SYNTAX      Integer32
    MAX-ACCESS  read-write
    STATUS      current
    DESCRIPTION "Count of the number of seconds during which (at any point during the second) at least one DTF Path layer BIP error was detected or an AISP, DTPLOF or POST FEC SF BER defect was present."
    DEFVAL      { 120 }
    ::= { channelCtpEntry  10 }


channelCtpDtsSes15MinutesTce OBJECT-TYPE
    SYNTAX      Integer32
    MAX-ACCESS  read-write
    STATUS      current
    DESCRIPTION "Count of the seconds during which K (= 2,400 as specified in GR-253-CORE Issue 3 specification) or more DTF Path layer BIP errors were detected or an AIS-P, DTPLOF or POST FEC SF BER defect was present."
    DEFVAL      { 3 }
    ::= { channelCtpEntry  11 }


channelCtpDtsCvDayTce OBJECT-TYPE
    SYNTAX      Integer32
    MAX-ACCESS  read-write
    STATUS      current
    DESCRIPTION "Count of BIP errors detected at the DTF Path layer. Up to 8 path BIP errors can be detected per frame, with each error incrementing the DTFDLM-CV-S current register."
    DEFVAL      { 15000 }
    ::= { channelCtpEntry  12 }


channelCtpDtsEsDayTce OBJECT-TYPE
    SYNTAX      Integer32
    MAX-ACCESS  read-write
    STATUS      current
    DESCRIPTION "Count of the number of seconds during which (at any point during the second) at least one DTF Path layer BIP error was detected or an AIS-P, DTPLOF or POST FEC SF BER defect was present."
    DEFVAL      { 1200 }
    ::= { channelCtpEntry  13 }


channelCtpDtsSesDayTce OBJECT-TYPE
    SYNTAX      Integer32
    MAX-ACCESS  read-write
    STATUS      current
    DESCRIPTION "Count of the seconds during which K (= 2,400 as specified in GR-253-CORE Issue 3 specification) or more DTF Path layer BIP errors were detected or an AIS-P, DTP-LOF or POST FEC SF BER defect was present."
    DEFVAL      { 7 }
    ::= { channelCtpEntry  14 }


channelCtpDtsCv15MinutesTceReporting OBJECT-TYPE
    SYNTAX      TruthValue
    MAX-ACCESS  read-write
    STATUS      current
    DESCRIPTION "Flag that enables the reporting of DtsCv15MinutesTce crossing."
    DEFVAL      { false }
    ::= { channelCtpEntry  15 }


channelCtpDtsEs15MinutesTceReporting OBJECT-TYPE
    SYNTAX      TruthValue
    MAX-ACCESS  read-write
    STATUS      current
    DESCRIPTION "Flag that enables the reporting of DtsEs15MinutesTce crossing."
    DEFVAL      { false }
    ::= { channelCtpEntry  16 }


channelCtpDtsSes15MinutesTceReporting OBJECT-TYPE
    SYNTAX      TruthValue
    MAX-ACCESS  read-write
    STATUS      current
    DESCRIPTION "Flag that enables the reporting of DtsSes15MinutesTce crossing."
    DEFVAL      { false }
    ::= { channelCtpEntry  17 }


channelCtpDtsCvDayTceReporting OBJECT-TYPE
    SYNTAX      TruthValue
    MAX-ACCESS  read-write
    STATUS      current
    DESCRIPTION "Flag that enables the reporting of DtsCvDayTce crossing."
    DEFVAL      { false }
    ::= { channelCtpEntry  18 }


channelCtpDtsEsDayTceReporting OBJECT-TYPE
    SYNTAX      TruthValue
    MAX-ACCESS  read-write
    STATUS      current
    DESCRIPTION "Flag that enables the reporting of DtsEsDayTce crossing."
    DEFVAL      { false }
    ::= { channelCtpEntry  19 }


channelCtpDtsSesDayTceReporting OBJECT-TYPE
    SYNTAX      TruthValue
    MAX-ACCESS  read-write
    STATUS      current
    DESCRIPTION "Flag that enables the reporting of DtsSesDayTce crossing."
    DEFVAL      { false }
    ::= { channelCtpEntry  20 }


channelCtpPrbsGenerationMode OBJECT-TYPE
    SYNTAX  INTEGER {
        disabled(1),
        enabled(2)
    }
    MAX-ACCESS  read-write
    STATUS      current
    DESCRIPTION
        "When enabled, this object starts generating PRBS data on the transmit side."
    DEFVAL      { disabled }
    ::= { channelCtpEntry  21 }


channelCtpPrbsMonitoringMode OBJECT-TYPE
    SYNTAX  INTEGER {
        disabled(1),
        enabled(2)
    }
    MAX-ACCESS  read-write
    STATUS      current
    DESCRIPTION "Flag which enables the monitoring of bit errors."
    DEFVAL      { disabled }
    ::= { channelCtpEntry  22 }


channelCtpTEEnabled OBJECT-TYPE
    SYNTAX      TruthValue
    MAX-ACCESS  read-write
    STATUS      current
    DESCRIPTION "Controls whether this channel's bandwidth should be advertized/used for SNC creation"
    DEFVAL      { true }
    ::= { channelCtpEntry  23 }


channelCtpPmHistStatsEnable OBJECT-TYPE
    SYNTAX  INTEGER {
        enabled(1),
        disabled(2)
    }
    MAX-ACCESS  read-write
    STATUS      current
    DESCRIPTION "PmHistStatsEnable"
    DEFVAL      { enabled }
    ::= { channelCtpEntry  24 }

-- Conformance Statements
channelCtpConformance    OBJECT IDENTIFIER ::= { channelCtpMIB 3 }
channelCtpCompliances    OBJECT IDENTIFIER ::= { channelCtpConformance 1 }
channelCtpGroups         OBJECT IDENTIFIER ::= { channelCtpConformance 2 }

channelCtpCompliance MODULE-COMPLIANCE
    STATUS current
    DESCRIPTION
    "Describes the requirements for conformance to the CHANNELCTP-MIB"
    MODULE
        MANDATORY-GROUPS { channelCtpGroup }
    ::= { channelCtpCompliances 1 }

channelCtpGroup OBJECT-GROUP
    OBJECTS {
        channelCtpPreFecThresholdOrder,
        channelCtpPreFecThresholdMantissa,
        channelCtpSignalDegradeReporting,
        channelCtpInsertDtsTti,
        channelCtpDtsTtiAlarmReporting,
        channelCtpTxDtsTti,
        channelCtpExpectedDtsTti,
        channelCtpRxDtsTti,
        channelCtpDtsCv15MinutesTce,
        channelCtpDtsEs15MinutesTce,
        channelCtpDtsSes15MinutesTce,
        channelCtpDtsCvDayTce,
        channelCtpDtsEsDayTce,
        channelCtpDtsSesDayTce,
        channelCtpDtsCv15MinutesTceReporting,
        channelCtpDtsEs15MinutesTceReporting,
        channelCtpDtsSes15MinutesTceReporting,
        channelCtpDtsCvDayTceReporting,
        channelCtpDtsEsDayTceReporting,
        channelCtpDtsSesDayTceReporting,
        channelCtpPrbsGenerationMode,
        channelCtpPrbsMonitoringMode,
        channelCtpTEEnabled,
        channelCtpPmHistStatsEnable
    }
    STATUS current
    DESCRIPTION
        " A collection of objects for managing the channelCtp"
    ::= { channelCtpGroups 1 }


END
