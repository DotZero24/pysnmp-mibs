LUM-PORTDEVICE-MIB DEFINITIONS ::= BEGIN

IMPORTS
    MODULE-IDENTITY, OBJECT-TYPE, Unsigned32, Counter64
        FROM SNMPv2-SMI
    OBJECT-GROUP, MODULE-COMPLIANCE
        FROM SNMPv2-CONF
    DisplayString, DateAndTime, RowStatus, MacAddress, TEXTUAL-CONVENTION
        FROM SNMPv2-TC
    lumModules, lumPortdeviceMIB
        FROM LUM-REG
    MgmtNameString, SubrackNumber, SlotNumber, BoardOrInterfaceOperStatus,
    CommandString, FaultStatus, AdminStatus, EnableDisable
        FROM LUM-TC;

lumPortdeviceMIBModule MODULE-IDENTITY
    LAST-UPDATED
        "201706150000Z" -- June 15th 2017
    ORGANIZATION
        "Infinera Corporation"
    CONTACT-INFO
        "techsupport@infinera.com"
    DESCRIPTION
        "The equipment configuration MIB module for port device.

        Then tables contained in this MIB are:

        (1) The General group contains some general attributes as time stamps
            and tables sizes.

        (2) The Generic group contains generic information and configurations
            applicable to all port devices.

        (3) The Equipment group contains information and configurations for
            each port device.

        (4) Then Firmware group contains configuration, status and commands for
            firmware upgrade and other maintenance operations for each port device.

"
    REVISION
        "201706150000Z" -- June 15th 2017
    DESCRIPTION
        "Changes made for release r29.0:
         - Changed ORGANIZATION and CONTACT-INFO"
    REVISION
        "201507070000Z" -- July 7th 2015
    DESCRIPTION
        "Changes made for release r26:
        - Added attributes for Channelized Isfp, channel, vlan.."
    REVISION
        "201405160000Z" -- May 16th 2014
    DESCRIPTION
        "Changes made for release r23:
        - Removed misleading text about SelectedPort-mode: Auto  "
    REVISION
        "201305310000Z" -- May 31st 2013
    DESCRIPTION
        "The initial revision of this module."
    ::= { lumModules 57 }

-- ----------------------------------------------------
-- Conformance area, containing groups and compliance
-- specifications.
-- ----------------------------------------------------

lumPortdeviceConfs OBJECT IDENTIFIER ::= { lumPortdeviceMIB 1 }
lumPortdeviceGroups OBJECT IDENTIFIER ::= { lumPortdeviceConfs 1 }
lumPortdeviceCompl OBJECT IDENTIFIER ::= { lumPortdeviceConfs 2 }

-- ----------------------------------------------------
-- Root for objects in the portdevice MIB
-- ----------------------------------------------------

lumPortdeviceMIBObjects OBJECT IDENTIFIER ::= { lumPortdeviceMIB 2 }

-- ----------------------------------------------------
-- This MIB contains the following groups:
-- ----------------------------------------------------

portDevGeneral OBJECT IDENTIFIER ::= { lumPortdeviceMIBObjects 1 }
portDevGenericList OBJECT IDENTIFIER ::= { lumPortdeviceMIBObjects 2 }
portDevEquipmentList OBJECT IDENTIFIER ::= { lumPortdeviceMIBObjects 3 }
portDevFwList OBJECT IDENTIFIER ::= { lumPortdeviceMIBObjects 4 }
portDevIwfList OBJECT IDENTIFIER ::= { lumPortdeviceMIBObjects 5 }
portDevIwfPmList OBJECT IDENTIFIER ::= { lumPortdeviceMIBObjects 6 }

-- ----------------------------------------------------
-- Textual Conventions
-- ----------------------------------------------------

PortDeviceEquipmentType ::= TEXTUAL-CONVENTION
    STATUS current
    DESCRIPTION
        "The functional type of the port device.
        At least one type is defined for each combination of
        the following properties of the port device:

        1 - number of interfaces

        2 - type of interfaces

        3 - the functionality of the port device (can usually be inferred from
        the types of interfaces)

        The application should be able to determine which and how many
        interfaces should be instantiated from the type.

        Functional types defined so far:

        nidGe - Gigabit Ethernet Network Interface Device

        iSFP-155 - iSFP synchronous transport module 155Mbps

        iSFP-622 - iSFP synchronous transport module 622Mbps"

    SYNTAX INTEGER {
        undefined (0),
        nidGe (1),   -- Gigabit Ethernet Network Interface Device
        iSfp155 (2), -- iSFP synchronous transport module 155Mbps
        iSfp622 (3), -- iSFP synchronous transport module 622Mbps
        iSfpVc12 (4),-- STM-1 Channelized iSFP
        iSfp2488 (5) -- iSFP synchronous transport module 2488Mbps
        }


PortDeviceVersionType ::= TEXTUAL-CONVENTION
    STATUS current
    DESCRIPTION
        "The version type of the port device.
        undefined (0), -- Device type unknown
        tpmrPmR11S (1), -- Service OAM Smart SFP
        ex12NidR22S (3), -- EX12 Transport NID
        tsop155GeConvPmR12 (4), -- Transparant SONET/SDH over Packet (TSoP) Smart SFP STM-1
        tsop622GeConvPmR12 (5), -- Transparant SONET/SDH over Packet (TSoP) Smart SFP STM-4
        tpmrPmR15RespS (8), -- Service OAM Smart SFP Responder
        tpmrPmR15InitS (10), -- Service OAM Smart SFP Initiator
        ex14NidR10S (11), -- EX14 Transport NID
        tpmrPmR11L (12), -- Link OAM Smart SFP
        tsop155GeConvPmR15 (24), -- TSoP Smart SFP OC-3/STM-1
        tsop622GeConvPmR15 (25), -- TSoP Smart SFP OC-12/STM-4
        ex14NidR20S (31), -- EX14 Transport NID R2.0
        ex14NidR40S (32), -- EX14 Transport NID R4.0
        tsopStm1eGeConvPmR15 (258), --  TSoP Smart SFP OC-3/STM-1E
        tpmrPmR20TranspS (259) --  Service OAM Smart SFP Transparant"

    SYNTAX INTEGER {
        undefined (0), -- Device type unknown
        tpmrPmR11S (1), -- Service OAM Smart SFP
        ex12NidR22S (3), -- EX12 Transport NID
        tsop155GeConvPmR12 (4), -- Transparant SONET/SDH over Packet (TSoP) Smart SFP STM-1
        tsop622GeConvPmR12 (5), -- Transparant SONET/SDH over Packet (TSoP) Smart SFP STM-4
        tpmrPmR15RespS (8), -- Service OAM Smart SFP Responder
        tpmrPmR15InitS (10), -- Service OAM Smart SFP Initiator
        ex14NidR10S (11), -- EX14 Transport NID
        tpmrPmR11L (12), -- Link OAM Smart SFP
        tsop155GeConvPmR15 (24), -- TSoP Smart SFP OC-3/STM-1
        tsop622GeConvPmR15 (25), -- TSoP Smart SFP OC-12/STM-4
        ex14NidR20S (31), -- EX14 Transport NID R2.0
        ex14NidR40S (32), -- EX14 Transport NID R4.0
        tsopStm1eGeConvPmR15 (258), --  TSoP Smart SFP OC-3/STM-1E
        tpmrPmR20TranspS (259) --  Service OAM Smart SFP Transparant
   }

PortDevFwImgState ::=  TEXTUAL-CONVENTION
    STATUS current
    DESCRIPTION
        "The states of the firware image on port device.
        unknown  - Can not get image information from port device
        inactive - Image stored but not activated
        active - Image stored and activated
        empty - No image stored"

    SYNTAX INTEGER {
        unknown (0),
        inactive (1),
        active (2),
        empty (3)
    }

PortSelection ::= TEXTUAL-CONVENTION
    STATUS current
    DESCRIPTION
       "Selection of active port and alarm suppression
        Auto(0)            Active port is automatically selected
                           based on LOS.
        CifA(1)            CifA active port (Optical),
                           alarms for CifB suppressed.
        CifB(2)            CifB active port (Electrical),
                           alarms for CifA suppressed.
       "
    SYNTAX INTEGER {
             cifa (0),
             cifb (1),
             auto (2)
           }

-- ----------------------------------------------------
-- General group
-- ----------------------------------------------------

portDevGeneralLastChangeTime OBJECT-TYPE
    SYNTAX      DateAndTime
    MAX-ACCESS  read-only
    STATUS      current
    DESCRIPTION
        "The time when the configuration of the MIB was last
        changed.

"
    ::= { portDevGeneral 1 }

portDevGeneralStateLastChangeTime OBJECT-TYPE
    SYNTAX      DateAndTime
    MAX-ACCESS  read-only
    STATUS      current
    DESCRIPTION
        "The time when the state of the MIB was last changed.

"
    ::= { portDevGeneral 2 }

portDevGeneralGenericTableSize OBJECT-TYPE
    SYNTAX      Unsigned32
    MAX-ACCESS  read-only
    STATUS      current
    DESCRIPTION
        "Size of generic table

"
    ::= { portDevGeneral 3 }

portDevGeneralEquipmentTableSize OBJECT-TYPE
    SYNTAX      Unsigned32
    MAX-ACCESS  read-only
    STATUS      current
    DESCRIPTION
        "Size of equipment table

"
    ::= { portDevGeneral 4 }

portDevGeneralFwTableSize OBJECT-TYPE
    SYNTAX      Unsigned32
    MAX-ACCESS  read-only
    STATUS      current
    DESCRIPTION
        "Size of firmware table
"
    ::= { portDevGeneral 5 }

portDevGeneralIwfTableSize OBJECT-TYPE
    SYNTAX      Unsigned32
    MAX-ACCESS  read-only
    STATUS      current
    DESCRIPTION
        "Size of IWF configuration table
"
    ::= { portDevGeneral 6 }

portDevGeneralIwfPmTableSize OBJECT-TYPE
    SYNTAX      Unsigned32
    MAX-ACCESS  read-only
    STATUS      current
    DESCRIPTION
        "Size of IWF PM table
"
    ::= { portDevGeneral 7 }

-- ----------------------------------------------------
-- Generic group
-- ----------------------------------------------------

portDevGenericTable  OBJECT-TYPE
    SYNTAX      SEQUENCE OF PortDevGenericEntry
    MAX-ACCESS  not-accessible
    STATUS      current
    DESCRIPTION
        "The generic list."
    ::= { portDevGenericList 1 }

portDevGenericEntry OBJECT-TYPE
    SYNTAX      PortDevGenericEntry
    MAX-ACCESS  not-accessible
    STATUS      current
    DESCRIPTION
        "An entry in the generic list.
"
    INDEX { portDevGenericIndex }
    ::= { portDevGenericTable 1 }

PortDevGenericEntry ::=
    SEQUENCE {
        portDevGenericIndex                       Unsigned32,
        portDevGenericName                        MgmtNameString,
        portDevGenericSubrack                     Unsigned32,
        portDevGenericSlot                        Unsigned32,
        portDevGenericAutoDiscoverInterval        Unsigned32,
        portDevGenericCreateNewPortDevice         CommandString,
        portDevGenericRestartPortDevice           CommandString,
        portDevGenericCreateMep                   CommandString,
        portDevGenericCreateMeg                   CommandString,
        portDevGenericCreateNewPortDeviceAdvanced CommandString }

portDevGenericIndex OBJECT-TYPE
    SYNTAX      Unsigned32 (1..2147483647)
    MAX-ACCESS  read-only
    STATUS      current
    DESCRIPTION
        "An arbitrary index assigned to each entry.
"
    ::= { portDevGenericEntry 1 }

portDevGenericName OBJECT-TYPE
    SYNTAX      MgmtNameString
    MAX-ACCESS  read-only
    STATUS      current
    DESCRIPTION
        "The management name of the interface, for example
        'generic:1:2', where the first number indicates
        subrack, the second slot number.
"
    ::= { portDevGenericEntry 2 }

portDevGenericSubrack OBJECT-TYPE
    SYNTAX      Unsigned32 (1..2147483647)
    MAX-ACCESS  read-only
    STATUS      current
    DESCRIPTION
        "The subrack that this port device belongs to.
"
    ::= { portDevGenericEntry 3 }

portDevGenericSlot OBJECT-TYPE
    SYNTAX      Unsigned32 (1..2147483647)
    MAX-ACCESS  read-only
    STATUS      current
    DESCRIPTION
        "The slot that this port device belongs to.
"
    ::= { portDevGenericEntry 4 }

portDevGenericAutoDiscoverInterval OBJECT-TYPE
    SYNTAX      Unsigned32 (0..300)
    MAX-ACCESS  read-write
    STATUS      current
    DESCRIPTION
        "Interval at which the auto discovery of port devices runs.
        0 to disable auto discovery.
        The auto discover interval is configured for all port devices
        of the board.
        Unit: second.
"
    DEFVAL { 0 }
    ::= { portDevGenericEntry 5 }

portDevGenericCreateNewPortDevice OBJECT-TYPE
    SYNTAX      CommandString
    MAX-ACCESS  read-only
    STATUS      current
    DESCRIPTION
        "Internal command for creating a port device.
         Device type   - type of port device to be created.
         Port          - port of the EMXP board on which to add a port device.
         VLAN ID       - VLAN ID prepended. (NID-GE only)
         Administrative
         status        - The initial administrative status setting of all
                         channels of this iSFP. (iSFP-VC12 only)
         Base VLAN ID  - The first VLAN ID in a range that will be applied
                         to the channels. The chosen value will be used as
                         VLAN ID on channel 1 and the next VLAN ID  in the
                         range will be used on channel 2 and so on.
                         (iSFP-VC12 only)
         Ether type    - Specifies the ether type to be used for the VLAN of
                         each channel on this iSFP. (iSFP-VC12 only)
         VLAN priority - Specifies the Vlan priority (PCP) of each channel on this iSFP.
                         (iSFP-VC12 only)
"
    ::= { portDevGenericEntry 6 }

portDevGenericRestartPortDevice OBJECT-TYPE
    SYNTAX      CommandString
    MAX-ACCESS  read-only
    STATUS      current
    DESCRIPTION
        "Internal command for restarting a port device.

        Port device - select the device to restart.

        Restart type - type of restart.
          Cold  Traffic disturbing restart.
          Warm  Non-traffic disturbing restart.

"
    ::= { portDevGenericEntry 7 }

portDevGenericCreateMep OBJECT-TYPE
    SYNTAX      CommandString
    MAX-ACCESS  read-only
    STATUS      current
    DESCRIPTION
        "Command for creating a Mep object.
         MEG            - Identifies to which Meg the Mep will be added.
         Mep type       - Local or Remote.
         MEP identifier - Identifier for the Mep (range 1-8191)
         Portdevice - The selected Portdevice.
"
    ::= { portDevGenericEntry 8 }

portDevGenericCreateMeg OBJECT-TYPE
    SYNTAX      CommandString
    MAX-ACCESS  read-only
    STATUS      current
    DESCRIPTION
        "Create and associate a MEG (MAID) for a Portdevice

        Identifier - A unique user defined identifier for the MEG.

        Level - Maintenance domain level.

        CCM interval - Interval between CCM transmissions to be used by all MEPs in the MA.
          invalid  No CCMs are sent
          3.33 ms  CCMs are sent every 3 1/3 milliseconds (300Hz)
          10 ms    CCMs are sent every 10 milliseconds
          100 ms   CCMs are sent every 100 milliseconds
          1 s      CCMs are sent every 1 second

          The supported CCM intervals for Nid (down) MEPs are: 3.33 ms,10 ms, 100 ms, 1 s.

        Domain format - The format of the domain. none, dnsLikeName, macAddressAndUint and charString are supported.

        Domain name - Applicable for the format dnsLikeName and charString.

        MAC - MAC address. Only applicable if domain format is macAddrAndUint.

        Uint - Unsigned integer. Only applicable if domain format is macAddrAndUint.

        Association format - The format of the association. primaryVid, charString, unsignedInt16, rfc2865VpnId and ICC are supported.

        Association name - Applicable for the formats charString and ICC.

        VPN OUI - VPN authority Organizationally Unique Indentifier. Only applicable if association format is rfc2865VpnId. Example of an VPN OUI is 0A:12:BF.

        VPN index - VPN index. Only applicable if association format is rfc2865VpnId. Example of an VPN index is 0A:12:BF:11.

        Uint - Unsigned integer. Only applicable if association format is unsignedInt16.

        VLAN ID - Primary VLAN ID. Only applicable if association format is primaryVid.
"
    ::= { portDevGenericEntry 9 }

portDevGenericCreateNewPortDeviceAdvanced OBJECT-TYPE
    SYNTAX      CommandString
    MAX-ACCESS  read-only
    STATUS      current
    DESCRIPTION
        "Internal command for creating a port device.
         Device type   - type of port device to be created.
         Port          - port of the EMXP board on which to add a port device.
         VLAN ID       - VLAN ID prepended. (NID-GE only)
         Administrative
         status        - The initial administrative status setting of all
                         channels of this iSFP. (iSFP-VC12 only)
         Base VLAN ID  - The first VLAN ID in a range that will be applied
                         to the channels. The chosen value will be used as
                         VLAN ID on channel 1 and the next VLAN ID  in the
                         range will be used on channel 2 and so on.
                         (iSFP-VC12 only)
         Ether type    - Specifies the ether type to be used for the VLAN of
                         each channel on this iSFP. (iSFP-VC12 only)
         VLAN priority - Specifies the Vlan priority (PCP) of each channel on this iSFP.
                         (iSFP-VC12 only)
"
    ::= { portDevGenericEntry 10 }
-- ----------------------------------------------------
-- Equipment information of port device
-- ----------------------------------------------------

portDevEquipmentTable  OBJECT-TYPE
    SYNTAX      SEQUENCE OF PortDevEquipmentEntry
    MAX-ACCESS  not-accessible
    STATUS      current
    DESCRIPTION
        "The equipment list."
    ::= { portDevEquipmentList 1 }

portDevEquipmentEntry OBJECT-TYPE
    SYNTAX      PortDevEquipmentEntry
    MAX-ACCESS  not-accessible
    STATUS      current
    DESCRIPTION
        "An entry in the board list.
        One entry for each slot.
"
    INDEX { portDevEquipmentIndex }
    ::= { portDevEquipmentTable 1 }

PortDevEquipmentEntry ::=
    SEQUENCE {
        portDevEquipmentIndex                     Unsigned32,
        portDevEquipmentName                      MgmtNameString,
        portDevEquipmentDescr                     DisplayString,
        portDevEquipmentLocation                  DisplayString,
        portDevEquipmentAdminStatus               AdminStatus,
        portDevEquipmentOperStatus                BoardOrInterfaceOperStatus,
        portDevEquipmentExpectedType              PortDeviceEquipmentType,
        portDevEquipmentActualType                PortDeviceEquipmentType,
        portDevEquipmentFwVersion                 DisplayString,
        portDevEquipmentFwUpgradeStatus           DisplayString,
        portDevEquipmentLinkPassThrough           EnableDisable,

        portDevEquipmentSubrack                   SubrackNumber,
        portDevEquipmentSlot                      SlotNumber,
        portDevEquipmentVlanId                    Unsigned32,
        portDevEquipmentRowStatus                 RowStatus,
        portDevEquipmentNoDeviceFound             FaultStatus,
        portDevEquipmentMultiDeviceFound          FaultStatus,
        portDevEquipmentDeviceNotManageable       FaultStatus,
        portDevEquipmentDeviceNotReachable        FaultStatus,
        portDevEquipmentConfigurationFault        FaultStatus,
        portDevEquipmentPowerAMissing             FaultStatus,
        portDevEquipmentPowerBMissing             FaultStatus,
        portDevEquipmentInternalReference         Unsigned32,
        portDevEquipmentMacAddress                DisplayString,
        portDevEquipmentLocalPortIndex            Unsigned32,
        portDevEquipmentAdminPowerA               AdminStatus,
        portDevEquipmentAdminPowerB               AdminStatus,
        portDevEquipmentSelectedPort              PortSelection,
        portDevEquipmentDestMacAddress            MacAddress,
        portDevEquipmentDestMacAddressCheck       INTEGER,
        portDevEquipmentDeviceVersionType         PortDeviceVersionType,
        portDevEquipmentActivePort                PortSelection,
        portDevEquipmentDyingGasp                 FaultStatus,
	    portDevEquipmentLosCsf                    EnableDisable}

portDevEquipmentIndex OBJECT-TYPE
    SYNTAX      Unsigned32 (1..2147483647)
    MAX-ACCESS  read-only
    STATUS      current
    DESCRIPTION
        "An arbitrary index assigned to each
        port device entry.
"
    ::= { portDevEquipmentEntry 1 }

portDevEquipmentName OBJECT-TYPE
    SYNTAX      MgmtNameString
    MAX-ACCESS  read-only
    STATUS      current
    DESCRIPTION
        "The name of the port device, for example 'nidGe:1:2:1-2:1'
        where the four numbers indicate in which physical port that
        the port device is add to and the last number indicates the VLAN ID.

        The generated name if the port device is an iSFP can for example
        be 'iSFP:1:2:1-2' where the numbers after 'iSFP:' indicate the
        port the device is created for.
"
    ::= { portDevEquipmentEntry 2 }

portDevEquipmentDescr OBJECT-TYPE
    SYNTAX      DisplayString
    MAX-ACCESS  read-write
    STATUS      current
    DESCRIPTION
        "User configurable label for the port device.
"
    DEFVAL { "" }
    ::= { portDevEquipmentEntry 3 }

portDevEquipmentLocation OBJECT-TYPE
    SYNTAX      DisplayString
    MAX-ACCESS  read-write
    STATUS      current
    DESCRIPTION
        "The location of the port device.
"
    DEFVAL { "" }
    ::= { portDevEquipmentEntry 4 }

portDevEquipmentAdminStatus OBJECT-TYPE
    SYNTAX      AdminStatus
    MAX-ACCESS  read-write
    STATUS      current
    DESCRIPTION
        "The administrative state of the port device.

        down - The device should be inactive.
        Alarms are suppressed.

        up - The device should be activated when
        it becomes available. Alarms are not suppressed.
"
    DEFVAL { up }
    ::= { portDevEquipmentEntry 5 }

portDevEquipmentOperStatus OBJECT-TYPE
    SYNTAX      BoardOrInterfaceOperStatus
    MAX-ACCESS  read-only
    STATUS      current
    DESCRIPTION
        "The operational state of the port device.

        notPresent - The physical resources are not
        available.

        down - The interface is de-activated or the are
        faults preventing it from going to the 'up'-state.

        up - The interface is operational.


"
    DEFVAL { up }
    ::= { portDevEquipmentEntry 6 }

portDevEquipmentExpectedType OBJECT-TYPE
    SYNTAX      PortDeviceEquipmentType
    MAX-ACCESS  read-create
    STATUS      current
    DESCRIPTION
        "The expected port device type.
"
    DEFVAL { undefined }
    ::= { portDevEquipmentEntry 7 }

portDevEquipmentActualType OBJECT-TYPE
    SYNTAX      PortDeviceEquipmentType
    MAX-ACCESS  read-only
    STATUS      current
    DESCRIPTION
        "The actual device type. If an unexpected device
        has been detected this variable can be used to
        see what type of board has been detected.
"
    ::= { portDevEquipmentEntry 8 }

portDevEquipmentFwVersion OBJECT-TYPE
    SYNTAX      DisplayString
    MAX-ACCESS  read-only
    STATUS      current
    DESCRIPTION
        "The version of the firmware installed on port device.
"
    ::= { portDevEquipmentEntry 9 }

portDevEquipmentFwUpgradeStatus OBJECT-TYPE
    SYNTAX      DisplayString
    MAX-ACCESS  read-only
    STATUS      current
    DESCRIPTION
        "The progress status of the firmware installation and activation.
"
    ::= { portDevEquipmentEntry 10 }

portDevEquipmentLinkPassThrough OBJECT-TYPE
    SYNTAX      EnableDisable
    MAX-ACCESS  read-write
    STATUS      current
    DESCRIPTION
        "Indicates whether Link Pass-Through is enabled, i.e. whether the
         other interface of the Two-Port MAC Relay relays defects to this
         interface.
"
    DEFVAL { disabled }
    ::= { portDevEquipmentEntry 11 }

portDevEquipmentSubrack OBJECT-TYPE
    SYNTAX      SubrackNumber
    MAX-ACCESS  read-create
    STATUS      current
    DESCRIPTION
        "The number of the subrack where the port device is
        located.
"
    ::= { portDevEquipmentEntry 12 }

portDevEquipmentSlot OBJECT-TYPE
    SYNTAX      SlotNumber
    MAX-ACCESS  read-create
    STATUS      current
    DESCRIPTION
        "The slot where the port device is located.
"
    ::= { portDevEquipmentEntry 13 }

portDevEquipmentVlanId OBJECT-TYPE
    SYNTAX      Unsigned32(1..4094)
    MAX-ACCESS  read-create
    STATUS      current
    DESCRIPTION
        "User specified VLAN ID, which is last number in the
        port device ID.
        If no VLAN ID is specified then VLAN ID 0 is assumed.

"
    ::= { portDevEquipmentEntry 14 }

portDevEquipmentRowStatus OBJECT-TYPE
    SYNTAX      RowStatus
    MAX-ACCESS  read-create
    STATUS      current
    DESCRIPTION
        "Manages creation and deletion of conceptual rows.
        See also SNMPv2-TC.

"
    ::= { portDevEquipmentEntry 15 }

portDevEquipmentNoDeviceFound OBJECT-TYPE
    SYNTAX      FaultStatus
    MAX-ACCESS  read-only
    STATUS      current
    DESCRIPTION
        "There is no device present where the expected device
        type is defined.

        A(ctivation): Absence of expected device.

        D(e-activation): Insert expected device.

"
    ::= { portDevEquipmentEntry 16 }

portDevEquipmentMultiDeviceFound OBJECT-TYPE
    SYNTAX      FaultStatus
    MAX-ACCESS  read-only
    STATUS      current
    DESCRIPTION
        "There is more than one device present where the
        expected device type is defined.

        A(ctivation): More than one device is detected.

        D(e-activation): One device is found or no device
        is present.

"
    ::= { portDevEquipmentEntry 17 }

portDevEquipmentDeviceNotManageable OBJECT-TYPE
    SYNTAX      FaultStatus
    MAX-ACCESS  read-only
    STATUS      current
    DESCRIPTION
        "The firmware on the device is not supported
        by the current software version.

"
    ::= { portDevEquipmentEntry 18 }

portDevEquipmentDeviceNotReachable OBJECT-TYPE
    SYNTAX      FaultStatus
    MAX-ACCESS  read-only
    STATUS      current
    DESCRIPTION
        "The portdevice is not reachable by the traffic unit.

        A(ctivation): When the traffic unit loses contact with the
        port device.

        D(e-activation): When the connection is restored.

"
    ::= {portDevEquipmentEntry 19 }

portDevEquipmentConfigurationFault OBJECT-TYPE
    SYNTAX      FaultStatus
    MAX-ACCESS  read-only
    STATUS      current
    DESCRIPTION
        "The configuration stage of the portdevice setup
        did not successfully finish.

        A(ctivation): Configuration failure.

        D(e-activation): Configuration successful.


"
    ::= { portDevEquipmentEntry 20 }

portDevEquipmentPowerAMissing OBJECT-TYPE
    SYNTAX      FaultStatus
    MAX-ACCESS  read-only
    STATUS      current
    DESCRIPTION
        "Lost connection to power module A

        A(ctivation): When the port device loses contact with the
        power module A.

        D(e-activation): When the connection is restored.

"
    ::= {portDevEquipmentEntry 21 }

portDevEquipmentPowerBMissing OBJECT-TYPE
    SYNTAX      FaultStatus
    MAX-ACCESS  read-only
    STATUS      current
    DESCRIPTION
        "Lost connection to power module B

        A(ctivation): When the port device loses contact with the
        power module B.

        D(e-activation): When the connection is restored.

"
    ::= {portDevEquipmentEntry 22 }

portDevEquipmentInternalReference OBJECT-TYPE
    SYNTAX      Unsigned32 (0..2147483647)
    MAX-ACCESS  read-create
    STATUS      current
    DESCRIPTION
        "For internal use only.
"
    DEFVAL { 0 }
    ::= {portDevEquipmentEntry 23 }

portDevEquipmentMacAddress OBJECT-TYPE
    SYNTAX      DisplayString
    MAX-ACCESS  read-only
    STATUS      current
    DESCRIPTION
        "The mac address of the port device.
"
    ::= { portDevEquipmentEntry 24 }

portDevEquipmentLocalPortIndex OBJECT-TYPE
    SYNTAX      Unsigned32 (1..2147483647)
    MAX-ACCESS  read-create
    STATUS      current
    DESCRIPTION
        "The index of the port that this device is connected to.
"
    ::= { portDevEquipmentEntry 25 }

portDevEquipmentAdminPowerA OBJECT-TYPE
    SYNTAX      AdminStatus
    MAX-ACCESS  read-write
    STATUS      current
    DESCRIPTION
        "Alarms relating to power module A
        are suppressed.

        down - Alarms relating to power module A
        are suppressed.

"
    DEFVAL { down }
    ::= { portDevEquipmentEntry 26 }

portDevEquipmentAdminPowerB OBJECT-TYPE
    SYNTAX      AdminStatus
    MAX-ACCESS  read-write
    STATUS      current
    DESCRIPTION
        "Alarms relating to power module B
        are suppressed.

        down - Alarms relating to power module B
        are suppressed.

"
    DEFVAL { down }
    ::= { portDevEquipmentEntry 27 }

portDevEquipmentSelectedPort OBJECT-TYPE
    SYNTAX PortSelection
    MAX-ACCESS read-write
    STATUS current
    DESCRIPTION
       "Selected active port on the customer interface of the nid.
       Alarms on non selected ports are suppressed.

"
    DEFVAL { auto }
    ::= { portDevEquipmentEntry 28 }

portDevEquipmentDestMacAddress OBJECT-TYPE
    SYNTAX      MacAddress
    MAX-ACCESS  read-write
    STATUS      deprecated
    DESCRIPTION
        "The destination MAC address inserted into the transmitted packets.
"
    ::= { portDevEquipmentEntry 29 }

portDevEquipmentDestMacAddressCheck OBJECT-TYPE
    SYNTAX      INTEGER {
                disabled (1),
                enabled (2)}
    MAX-ACCESS  read-write
    STATUS      current
    DESCRIPTION
        "If enabled, for each received packet the destination MAC address
         is compared with the device MAC address. In case the addresses
         are not equal, the packet is not processed.

"
    DEFVAL { disabled }
    ::= { portDevEquipmentEntry 30 }

portDevEquipmentDeviceVersionType OBJECT-TYPE
    SYNTAX      PortDeviceVersionType
    MAX-ACCESS  read-only
    STATUS      current
    DESCRIPTION
        "The device version type. This variable can be used to
        see what version of the board has been detected.
"
    ::= { portDevEquipmentEntry 31 }

portDevEquipmentActivePort OBJECT-TYPE
    SYNTAX PortSelection
    MAX-ACCESS read-only
    STATUS current
    DESCRIPTION
       "Active port on the customer interface of the nid.
       Alarms on non selected ports are suppressed.

"
    DEFVAL { auto }
    ::= { portDevEquipmentEntry 32 }

portDevEquipmentDyingGasp OBJECT-TYPE
    SYNTAX      FaultStatus
    MAX-ACCESS  read-only
    STATUS      current
    DESCRIPTION
        "A Dying Gasp is signalled when power is going to be lost on the device. This could possibly indicate a power loss.

        A(ctivation): A Dying Gasp was received

        D(e-activation): Communication with the port device was succesfully established

"
    ::= { portDevEquipmentEntry 33 }


portDevEquipmentLosCsf OBJECT-TYPE
    SYNTAX      EnableDisable
    MAX-ACCESS  read-write
    STATUS      current
    DESCRIPTION
        "Indicates whether Los Csf is enabled.
"
    DEFVAL { disabled }
    ::= { portDevEquipmentEntry 34 }


-- ----------------------------------------------------
-- Firmware group
-- ----------------------------------------------------

portDevFwTable  OBJECT-TYPE
    SYNTAX      SEQUENCE OF PortDevFwEntry
    MAX-ACCESS  not-accessible
    STATUS      current
    DESCRIPTION
        "The firmware list."
    ::= { portDevFwList 1 }

portDevFwEntry OBJECT-TYPE
    SYNTAX      PortDevFwEntry
    MAX-ACCESS  not-accessible
    STATUS      current
    DESCRIPTION
        "An entry in the firmware list.
"
    INDEX { portDevFwIndex }
    ::= { portDevFwTable 1 }

PortDevFwEntry ::=
    SEQUENCE {
        portDevFwIndex                        Unsigned32,
        portDevFwSubrack                      Unsigned32,
        portDevFwSlot                         Unsigned32,
        portDevFwName                         DisplayString,
        portDevFwPortDevId                    Unsigned32,
        portDevFwImgSlotOneNr                 Unsigned32,
        portDevFwImgSlotOneVersion            DisplayString,
        portDevFwImgSlotOneState              PortDevFwImgState,
        portDevFwImgSlotOneDate               DisplayString,
        portDevFwImgSlotTwoNr                 Unsigned32,
        portDevFwImgSlotTwoVersion            DisplayString,
        portDevFwImgSlotTwoState              PortDevFwImgState,
        portDevFwImgSlotTwoDate               DisplayString,
        portDevFwInstallFw                    CommandString,
        portDevFwActivateFw                   CommandString,
        portDevFwGetAllFiles                  CommandString,
        portDevFwUpgradeStatus                DisplayString }

portDevFwIndex OBJECT-TYPE
    SYNTAX      Unsigned32 (1..2147483647)
    MAX-ACCESS  read-only
    STATUS      current
    DESCRIPTION
        "An arbitrary index assigned to each entry.
"
    ::= { portDevFwEntry 1 }

portDevFwSubrack OBJECT-TYPE
    SYNTAX      Unsigned32 (1..2147483647)
    MAX-ACCESS  read-only
    STATUS      current
    DESCRIPTION
        "The subrack that the port device belongs to.
"
    ::= { portDevFwEntry 2 }

portDevFwSlot OBJECT-TYPE
    SYNTAX      Unsigned32 (1..2147483647)
    MAX-ACCESS  read-only
    STATUS      current
    DESCRIPTION
        "The slot that the port device belongs to.
"
    ::= { portDevFwEntry 3 }

portDevFwName OBJECT-TYPE
    SYNTAX      DisplayString
    MAX-ACCESS  read-only
    STATUS      current
    DESCRIPTION
        "The name of the firmware entry, same as the port device name
        where the firmware is stored.
"
    ::= { portDevFwEntry 4 }

portDevFwPortDevId OBJECT-TYPE
    SYNTAX      Unsigned32 (1..2147483647)
    MAX-ACCESS  read-only
    STATUS      current
    DESCRIPTION
        "An arbitrary index(aka sdId) assigned to the local device
        entry, where the firmware is stored in.
"
    ::= { portDevFwEntry 5 }

portDevFwImgSlotOneNr OBJECT-TYPE
    SYNTAX      Unsigned32 (1..2147483647)
    MAX-ACCESS  read-only
    STATUS      current
    DESCRIPTION
        "The slot number of the stored firmware.
"
    DEFVAL { 1 }
    ::= { portDevFwEntry 6 }

portDevFwImgSlotOneVersion OBJECT-TYPE
    SYNTAX      DisplayString
    MAX-ACCESS  read-only
    STATUS      current
    DESCRIPTION
        "The version of the firmware that is in slot one.
"
    ::= { portDevFwEntry 7 }

portDevFwImgSlotOneState OBJECT-TYPE
    SYNTAX     PortDevFwImgState
    MAX-ACCESS  read-only
    STATUS      current
    DESCRIPTION
        "The state of the firmware that is in slot one.
"
    ::= { portDevFwEntry 8}

portDevFwImgSlotOneDate OBJECT-TYPE
    SYNTAX      DisplayString
    MAX-ACCESS  read-only
    STATUS      current
    DESCRIPTION
        "The date of the firmware that is in slot one.
"
    ::= { portDevFwEntry 9 }

portDevFwImgSlotTwoNr OBJECT-TYPE
    SYNTAX      Unsigned32 (1..2147483647)
    MAX-ACCESS  read-only
    STATUS      current
    DESCRIPTION
        "The slot number of the stored firmware.
"
    DEFVAL { 2 }
    ::= { portDevFwEntry 10 }

portDevFwImgSlotTwoVersion OBJECT-TYPE
    SYNTAX      DisplayString
    MAX-ACCESS  read-only
    STATUS      current
    DESCRIPTION
        "The version of the firmware that is in slot two.
"
    ::= { portDevFwEntry 11 }

portDevFwImgSlotTwoState OBJECT-TYPE
    SYNTAX     PortDevFwImgState
    MAX-ACCESS  read-only
    STATUS      current
    DESCRIPTION
        "The state of the firmware that is in slot two.
"
    ::= { portDevFwEntry 12 }

portDevFwImgSlotTwoDate OBJECT-TYPE
    SYNTAX      DisplayString
    MAX-ACCESS  read-only
    STATUS      current
    DESCRIPTION
        "The date of the firmware that is in slot two.
"
    ::= { portDevFwEntry 13 }

portDevFwInstallFw OBJECT-TYPE
    SYNTAX      CommandString
    MAX-ACCESS  read-only
    STATUS      current
    DESCRIPTION
        "Install firmware on a port device.

        Portdevice - Select the portdevice to upgrade

        The Active/Inactive sections show information about firmware
        available in the two software memory banks,
        there is one active and one inactive bank.

        Active firmware - Information about currently active firmware, release and build date.

        Inactive firmware - Information about firmware in the inactive bank.

        Action - Install new software, installing new software will upload
                 from the emxp board and install it in the inactive bank.

                 Activate will activate the software that is currently in the inactive bank.

                 Install and Activate will do both, install new software and activate it.

        File - Select a firmware image to install.
               The available firmware images are included in the emxp board software package.

"
    ::= { portDevFwEntry 14 }

portDevFwActivateFw OBJECT-TYPE
    SYNTAX      CommandString
    MAX-ACCESS  read-only
    STATUS      current
    DESCRIPTION
        "Activate a firmware on a device.
"
    ::= { portDevFwEntry 15 }

portDevFwGetAllFiles OBJECT-TYPE
    SYNTAX      CommandString
    MAX-ACCESS  read-only
    STATUS      current
    DESCRIPTION
        "List all availabe firmware files on the board.
"
    ::= { portDevFwEntry 16 }

portDevFwUpgradeStatus OBJECT-TYPE
    SYNTAX      DisplayString
    MAX-ACCESS  read-only
    STATUS      current
    DESCRIPTION
        "The status of the firmware installation and activation.
"
    ::= { portDevFwEntry 17 }


-- ----------------------------------------------------
-- IWF configuration for iSFP
-- ----------------------------------------------------

portDevIwfTable  OBJECT-TYPE
    SYNTAX      SEQUENCE OF PortDevIwfEntry
    MAX-ACCESS  not-accessible
    STATUS      current
    DESCRIPTION
        "The iwf port device list."
    ::= { portDevIwfList 1 }

portDevIwfEntry OBJECT-TYPE
    SYNTAX      PortDevIwfEntry
    MAX-ACCESS  not-accessible
    STATUS      current
    DESCRIPTION
        "An entry in the board list.
        One entry for each slot.
"
    INDEX { portDevIwfIndex }
    ::= { portDevIwfTable 1 }

PortDevIwfEntry ::=
    SEQUENCE {
        portDevIwfIndex                     Unsigned32,
        portDevIwfName                      MgmtNameString,
        portDevIwfRtpClockSource            INTEGER,
        portDevIwfJitterBufferRecenter      INTEGER,
        portDevIwfInternalReference         Unsigned32,
        portDevIwfLocalPortIndex            Unsigned32,
        portDevIwfLossOfSignal              FaultStatus,
        portDevIwfLossOfFrame               FaultStatus,
        portDevIwfEquipmentFailure          FaultStatus,
        portDevIwfNoTdmPayload              FaultStatus,
        portDevIwfRemotePacketLost          FaultStatus,
        portDevIwfLocalPacketLost           FaultStatus,
        portDevIwfTributaryUnitAlarm        FaultStatus,
        portDevIwfMultiplexSectionAlarm     FaultStatus,
        portDevIwfMultiplexSectionRDI       FaultStatus,

        portDevIwfAdminStatus               AdminStatus,
        portDevIwfOperStatus                BoardOrInterfaceOperStatus,
        portDevIwfDescr                     DisplayString,
        portDevIwfEtherType                 INTEGER,
        portDevIwfSignalFormat              INTEGER,
        portDevIwfVlanId                    Unsigned32,
        portDevIwfVlanPriority              Unsigned32,
        portDevIwfE1ChannelId               Unsigned32,
	    portDevIwfE1ChannelKLM              DisplayString,
        portDevIwfDestMacAddress            MacAddress }

portDevIwfIndex OBJECT-TYPE
    SYNTAX      Unsigned32 (1..2147483647)
    MAX-ACCESS  read-only
    STATUS      current
    DESCRIPTION
        "An arbitrary index assigned to each
        port device entry.
"
    ::= { portDevIwfEntry 1 }

portDevIwfName OBJECT-TYPE
    SYNTAX      MgmtNameString
    MAX-ACCESS  read-only
    STATUS      current
    DESCRIPTION
        "The management name of the IWF entry. The generated name
        can for example be 'iSFP:1:2:1-2'where the numbers after
        'iSFP:' indicate the port the device is created for.
"
    ::= { portDevIwfEntry 2 }

portDevIwfRtpClockSource OBJECT-TYPE
    SYNTAX      INTEGER {
                ethernet (1),
                tdm (2)}
    MAX-ACCESS  read-write
    STATUS      current
    DESCRIPTION
        "The clock source expected to be used for the Real-Time Protocol header timestamps.
"
    ::= { portDevIwfEntry 3 }

portDevIwfJitterBufferRecenter OBJECT-TYPE
    SYNTAX      INTEGER {
                normal (1),
                recenter (2)}
    MAX-ACCESS  read-write
    STATUS      current
    DESCRIPTION
        "Function to re-center position of jitter buffer. Setting of this
         object triggers recentering of the jitter buffer to the default position.

         Recentering the jitter buffer is a service-affecting operation.

         This object is merely used to invoke the recentering of the
         jitter buffer, and its actual value has no meaning.
"
    DEFVAL{ normal }
    ::= { portDevIwfEntry 4 }

portDevIwfInternalReference OBJECT-TYPE
    SYNTAX      Unsigned32 (0..2147483647)
    MAX-ACCESS  read-create
    STATUS      current
    DESCRIPTION
        "For internal use only.
"
    DEFVAL { 0 }
    ::= {portDevIwfEntry 5 }

portDevIwfLocalPortIndex OBJECT-TYPE
    SYNTAX      Unsigned32 (1..2147483647)
    MAX-ACCESS  read-create
    STATUS      current
    DESCRIPTION
        "The index of the port that this device is connected to.
"
    ::= {portDevIwfEntry 6 }

portDevIwfLossOfSignal OBJECT-TYPE
    SYNTAX      FaultStatus
    MAX-ACCESS  read-only
    STATUS      current
    DESCRIPTION
        "Loss of signal.
        Applicable for all signal formats.

        A(ctivation): Active loss of signal HW
        indication.

        D(e-activation): Inactive loss of signal HW
        indication.

"
    ::= { portDevIwfEntry 7 }

portDevIwfLossOfFrame OBJECT-TYPE
    SYNTAX      FaultStatus
    MAX-ACCESS  read-only
    STATUS      current
    DESCRIPTION
        "Loss of frame.

"
    ::= { portDevIwfEntry 8 }

portDevIwfEquipmentFailure OBJECT-TYPE
    SYNTAX      FaultStatus
    MAX-ACCESS  read-only
    STATUS      current
    DESCRIPTION
        "Equipment failure. Catastrophic failure of the
        hardware of the iSFP device. Replace the faulty hardware.
"
    ::= { portDevIwfEntry 9 }

portDevIwfNoTdmPayload OBJECT-TYPE
    SYNTAX      FaultStatus
    MAX-ACCESS  read-only
    STATUS      current
    DESCRIPTION
        "This alarm is generated when the device receives a packet stream
         with the L-bit set in the Control Word. This bit is set in the far end
         upon a LOS/LOF/AIS condition.
"
    ::= { portDevIwfEntry 10 }

portDevIwfRemotePacketLost OBJECT-TYPE
    SYNTAX      FaultStatus
    MAX-ACCESS  read-only
    STATUS      current
    DESCRIPTION
        "Remote Packet Lost. Remote end is sending packets
        but is not recieving any. Local encapsulation may be
        disabled or local destination MAC address may be wrong
        or packets are blocked or dropped in network.
"
    ::= { portDevIwfEntry 11 }

portDevIwfLocalPacketLost OBJECT-TYPE
    SYNTAX      FaultStatus
    MAX-ACCESS  read-only
    STATUS      current
    DESCRIPTION
        "Local Packet Lost.  No packets are received.
        Remote encapsulation may be disabled or
        remote destination MAC address may be wrong
        or packets are blocked or dropped in network.
"
    ::= { portDevIwfEntry 12 }


-- CSOP Stuff , remember to add compliance


portDevIwfAdminStatus OBJECT-TYPE
    SYNTAX      AdminStatus
    MAX-ACCESS  read-write
    STATUS      current
    DESCRIPTION
        "The administrative state of the port device IWF.

        down - The device should be inactive.
        Alarms are suppressed.

        up - The device should be activated when
        it becomes available. Alarms are not suppressed.
"
    DEFVAL { up }
    ::= { portDevIwfEntry 13 }

portDevIwfOperStatus OBJECT-TYPE
    SYNTAX      BoardOrInterfaceOperStatus
    MAX-ACCESS  read-only
    STATUS      current
    DESCRIPTION
        "The operational state of the IWF.

        notPresent - The physical resources are not
        available.

        down - The interface is de-activated or the are
        faults preventing it from going to the 'up'-state.

        up - The interface is operational.


"
    DEFVAL { up }
    ::= { portDevIwfEntry 14 }

portDevIwfDescr OBJECT-TYPE
    SYNTAX      DisplayString
    MAX-ACCESS  read-write
    STATUS      current
    DESCRIPTION
        "User configurable label for the port device iwf.
"
    DEFVAL { "" }
    ::= { portDevIwfEntry 15 }

portDevIwfSignalFormat OBJECT-TYPE
    SYNTAX INTEGER {
        other  (1),
        stm1   (2),
        stm4   (3),
        stm16  (4),
        e1     (39)}
    MAX-ACCESS  read-only
    STATUS      current
    DESCRIPTION
        "The signal format.
"
    DEFVAL { other }
    ::= { portDevIwfEntry 16 }

portDevIwfEtherType OBJECT-TYPE
    SYNTAX      INTEGER {
                    qTag0x8100 (1),
                    sTag0x88a8 (2)}
    MAX-ACCESS  read-write
    STATUS      current
    DESCRIPTION
        "Specifies the ether type of the VLAN.

        qTag0x8100      - 802.1Q
        sTag0x88a8      - 802.1ad Service tag

"
    DEFVAL { sTag0x88a8 }
    ::= { portDevIwfEntry 17 }

portDevIwfVlanId OBJECT-TYPE
    SYNTAX      Unsigned32(0..4094)
    MAX-ACCESS  read-write
    STATUS      current
    DESCRIPTION
        "User specified VLAN ID, used to map E1 channel to Vlan.
        If no VLAN ID is specified then VLAN ID 0 is assumed.
"
    DEFVAL { 0 }
    ::= { portDevIwfEntry 18 }

portDevIwfVlanPriority OBJECT-TYPE
    SYNTAX      Unsigned32 (0..7)
    MAX-ACCESS  read-write
    STATUS      current
    DESCRIPTION
        "Priority for the Vlan.

"
    DEFVAL { 0 }
    ::= { portDevIwfEntry 19 }

portDevIwfE1ChannelId OBJECT-TYPE
    SYNTAX      Unsigned32(0..63)
    MAX-ACCESS  read-create
    STATUS      current
    DESCRIPTION
        "User specified ChannelId, used to map E1 channel to Vlan.
        If no Channel ID is specified then 0 is assumed.
"
    DEFVAL { 0 }
    ::= {portDevIwfEntry 20}

portDevIwfE1ChannelKLM OBJECT-TYPE
    SYNTAX      DisplayString
    MAX-ACCESS  read-only
    STATUS      current
    DESCRIPTION
        "K,L,M numbering indicates a fixed mapping of a physical IWF-channel
         to each VC12.
"
    DEFVAL { "" }
    ::= { portDevIwfEntry 21 }

portDevIwfDestMacAddress OBJECT-TYPE
    SYNTAX      MacAddress
    MAX-ACCESS  read-write
    STATUS      current
    DESCRIPTION
        "The destination MAC address inserted into the transmitted packets.
"
    ::= { portDevIwfEntry 22 }

portDevIwfTributaryUnitAlarm OBJECT-TYPE
    SYNTAX      FaultStatus
    MAX-ACCESS  read-only
    STATUS      current
    DESCRIPTION
        "alarm: An  TU-AIS signal is detected.
         ok:    The TU-AIS is cleared.
"
    ::= { portDevIwfEntry 23 }


portDevIwfMultiplexSectionAlarm OBJECT-TYPE
    SYNTAX      FaultStatus
    MAX-ACCESS  read-only
    STATUS      current
    DESCRIPTION
        "alarm: An  MS-AIS signal is detected.
         ok:    The MS-AIS is cleared.
"
    ::= { portDevIwfEntry 24 }

portDevIwfMultiplexSectionRDI OBJECT-TYPE
    SYNTAX      FaultStatus
    MAX-ACCESS  read-only
    STATUS      current
    DESCRIPTION
        "alarm: An  MS-RDI signal is detected.
         ok:    The MS-RDI is cleared.
"
    ::= { portDevIwfEntry 25 }


-- -------------------------------------------------------------
-- IWF PM data for iSFP
-- -------------------------------------------------------------

portDevIwfPmTable OBJECT-TYPE
    SYNTAX      SEQUENCE OF PortDevIwfPmEntry
    MAX-ACCESS  not-accessible
    STATUS      current
    DESCRIPTION
        "A table containing the counters of IWF channels of the iSFP."
    ::= { portDevIwfPmList 1 }

portDevIwfPmEntry OBJECT-TYPE
    SYNTAX      PortDevIwfPmEntry
    MAX-ACCESS  not-accessible
    STATUS      current
    DESCRIPTION
        "A list of objects containing the counters of an IWF channel.
"
    INDEX  { portDevIwfPmIndex }
    ::= { portDevIwfPmTable 1 }

PortDevIwfPmEntry ::=
    SEQUENCE {
        portDevIwfPmIndex                     Unsigned32,
        portDevIwfPmName                      MgmtNameString,
        portDevIwfPmRxPackets                 Counter64,
        portDevIwfPmTxPackets                 Counter64,
        portDevIwfPmMalformedPackets          Counter64,
        portDevIwfPmReorderedPackets          Counter64,
        portDevIwfPmMisorderedDroppedPackets  Counter64,
        portDevIwfPmMissingPackets            Counter64,
        portDevIwfPmPlayedOutPackets          Counter64,
        portDevIwfPmJbOverrun                 Counter64,
        portDevIwfPmJbUnderrun                Counter64,
        portDevIwfPmReset                     INTEGER,
        portDevIwfPmInternalReference         Unsigned32,
        portDevIwfPmE1ChannelId               Unsigned32
        }

portDevIwfPmIndex OBJECT-TYPE
    SYNTAX      Unsigned32 (1..2147483647)
    MAX-ACCESS  read-only
    STATUS      current
    DESCRIPTION
        "An arbitrary index assigned to each entry.
"
    ::= { portDevIwfPmEntry 1 }

portDevIwfPmName OBJECT-TYPE
    SYNTAX      MgmtNameString
    MAX-ACCESS  read-only
    STATUS      current
    DESCRIPTION
        "The management name of the IWF PM entry. The generated name
        can for example be 'iSFP:1:2:1-2'where the numbers after
        'iSFP:' indicate the port the device is created for.
"
    ::= { portDevIwfPmEntry 2 }

portDevIwfPmRxPackets OBJECT-TYPE
    SYNTAX      Counter64
    MAX-ACCESS  read-only
    STATUS      current
    DESCRIPTION
        "Number of received packets.
"
    ::= { portDevIwfPmEntry 3 }

portDevIwfPmTxPackets OBJECT-TYPE
    SYNTAX      Counter64
    MAX-ACCESS  read-only
    STATUS      current
    DESCRIPTION
        "Number of transmitted packets.
"
    ::= { portDevIwfPmEntry 4 }

portDevIwfPmMalformedPackets OBJECT-TYPE
    SYNTAX      Counter64
    MAX-ACCESS  read-only
    STATUS      current
    DESCRIPTION
        "Number of malformed packets.
"
    ::= { portDevIwfPmEntry 5 }

portDevIwfPmReorderedPackets OBJECT-TYPE
    SYNTAX      Counter64
    MAX-ACCESS  read-only
    STATUS      current
    DESCRIPTION
        "Number of reordered packets.
"
    ::= { portDevIwfPmEntry 6 }

portDevIwfPmMisorderedDroppedPackets OBJECT-TYPE
    SYNTAX      Counter64
    MAX-ACCESS  read-only
    STATUS      current
    DESCRIPTION
        "Number of dropped misordered packets.
"
    ::= { portDevIwfPmEntry 7 }

portDevIwfPmMissingPackets OBJECT-TYPE
    SYNTAX      Counter64
    MAX-ACCESS  read-only
    STATUS      current
    DESCRIPTION
        "Number of missing packets.
"
::= { portDevIwfPmEntry 8 }

portDevIwfPmPlayedOutPackets OBJECT-TYPE
    SYNTAX      Counter64
    MAX-ACCESS  read-only
    STATUS      current
    DESCRIPTION
        "Number of packets of which TDM payload is transmitted as received.
"
    ::= { portDevIwfPmEntry 9 }

portDevIwfPmJbOverrun OBJECT-TYPE
    SYNTAX      Counter64
    MAX-ACCESS  read-only
    STATUS      current
    DESCRIPTION
        "Number of jitter buffer overrun packets.
"
    ::= { portDevIwfPmEntry 10 }

portDevIwfPmJbUnderrun OBJECT-TYPE
    SYNTAX      Counter64
    MAX-ACCESS  read-only
    STATUS      current
    DESCRIPTION
        "Number of jitter buffer underrun packets.
"
    ::= { portDevIwfPmEntry 11 }

portDevIwfPmReset OBJECT-TYPE
    SYNTAX      INTEGER {
                normal (1),
                reset (2)}
    MAX-ACCESS  read-write
    STATUS      current
    DESCRIPTION
        "Setting of this object to 'reset' invokes a reset of the counters
         for this IWF channel.

         This object is merely used to invoke a reset, and its actual
         value has no meaning.
"
    ::= { portDevIwfPmEntry 12 }

portDevIwfPmInternalReference OBJECT-TYPE
    SYNTAX      Unsigned32 (0..2147483647)
    MAX-ACCESS  read-only
    STATUS      current
    DESCRIPTION
        "For internal use only.
"
    DEFVAL { 0 }
    ::= {portDevIwfPmEntry 13 }

portDevIwfPmE1ChannelId OBJECT-TYPE
    SYNTAX      Unsigned32(0..63)
    MAX-ACCESS  read-create
    STATUS      current
    DESCRIPTION
        "User specified ChannelId, used to map E1 channel to Vlan.
        If no Channel ID is specified then 0 is assumed.
"
    DEFVAL { 0 }
    ::= {portDevIwfPmEntry 14 }



-- ----------------------------------------------------
-- Notifications
-- ----------------------------------------------------

-- ----------------------------------------------------
-- Object and event groups
-- ----------------------------------------------------

portDevGeneralGroupV1 OBJECT-GROUP
    OBJECTS {
        portDevGeneralLastChangeTime,
        portDevGeneralStateLastChangeTime,
        portDevGeneralGenericTableSize,
        portDevGeneralEquipmentTableSize,
        portDevGeneralFwTableSize,
        portDevGeneralIwfTableSize,
        portDevGeneralIwfPmTableSize}
    STATUS      current
    DESCRIPTION
        "The general objects."
    ::= { lumPortdeviceGroups 1 }

portDevGenericGroupV1 OBJECT-GROUP
    OBJECTS {
        portDevGenericIndex,
        portDevGenericName,
        portDevGenericSubrack,
        portDevGenericSlot,
        portDevGenericAutoDiscoverInterval,
        portDevGenericCreateNewPortDevice,
        portDevGenericCreateMep,
        portDevGenericCreateMeg,
        portDevGenericCreateNewPortDevice,
        portDevGenericRestartPortDevice  }
    STATUS      deprecated
    DESCRIPTION
        "The generic objects (R21.0)."
    ::= { lumPortdeviceGroups 2 }

portDevGenericGroupV2 OBJECT-GROUP
    OBJECTS {
        portDevGenericIndex,
        portDevGenericName,
        portDevGenericSubrack,
        portDevGenericSlot,
        portDevGenericAutoDiscoverInterval,
        portDevGenericCreateNewPortDevice,
        portDevGenericCreateMep,
        portDevGenericCreateMeg,
        portDevGenericCreateNewPortDevice,
        portDevGenericRestartPortDevice,
        portDevGenericCreateNewPortDeviceAdvanced }
    STATUS      current
    DESCRIPTION
        "The generic objects (R30.1)."
    ::= { lumPortdeviceGroups 13 }

portDevEquipmentGroupV1 OBJECT-GROUP
    OBJECTS {
        portDevEquipmentIndex,
        portDevEquipmentName,
        portDevEquipmentDescr,
        portDevEquipmentLocation,
        portDevEquipmentAdminStatus,
        portDevEquipmentOperStatus,
        portDevEquipmentExpectedType,
        portDevEquipmentActualType,
        portDevEquipmentFwVersion,
        portDevEquipmentLinkPassThrough,
        portDevEquipmentSelectedPort,
        portDevEquipmentSubrack,
        portDevEquipmentSlot,
        portDevEquipmentVlanId,
        portDevEquipmentRowStatus,
        portDevEquipmentNoDeviceFound,
        portDevEquipmentMultiDeviceFound,
        portDevEquipmentDeviceNotManageable,
        portDevEquipmentDeviceNotReachable,
        portDevEquipmentConfigurationFault,
        portDevEquipmentPowerAMissing,
        portDevEquipmentPowerBMissing,
        portDevEquipmentInternalReference,
        portDevEquipmentMacAddress,
        portDevEquipmentLocalPortIndex,
        portDevEquipmentAdminPowerA,
        portDevEquipmentAdminPowerB,
        portDevEquipmentDestMacAddress,
        portDevEquipmentDestMacAddressCheck,
        portDevEquipmentFwUpgradeStatus}
    STATUS      deprecated
    DESCRIPTION
        "The equipment objects (R21.0)."
    ::= { lumPortdeviceGroups 3 }

portDevFwGroupV1 OBJECT-GROUP
    OBJECTS {
        portDevFwIndex,
        portDevFwSubrack,
        portDevFwSlot,
        portDevFwName,
        portDevFwPortDevId,
        portDevFwImgSlotOneNr,
        portDevFwImgSlotOneVersion,
        portDevFwImgSlotOneState,
        portDevFwImgSlotOneDate,
        portDevFwImgSlotTwoNr,
        portDevFwImgSlotTwoVersion,
        portDevFwImgSlotTwoState,
        portDevFwImgSlotTwoDate,
        portDevFwInstallFw,
        portDevFwActivateFw,
        portDevFwGetAllFiles,
        portDevFwUpgradeStatus}
    STATUS      current
    DESCRIPTION
        "The firmware objects (R21.0)."
    ::= { lumPortdeviceGroups 4 }

portDevIwfGroupV1 OBJECT-GROUP
    OBJECTS {
        portDevIwfIndex,
        portDevIwfName,
        portDevIwfRtpClockSource,
        portDevIwfJitterBufferRecenter,
        portDevIwfInternalReference,
        portDevIwfLocalPortIndex,
        portDevIwfLossOfSignal,
        portDevIwfLossOfFrame,
        portDevIwfEquipmentFailure,
        portDevIwfNoTdmPayload,
        portDevIwfRemotePacketLost,
        portDevIwfLocalPacketLost }
    STATUS      deprecated
    DESCRIPTION
        "The Port Device IWF objects (R21.0)."
    ::= { lumPortdeviceGroups 5 }


portDevIwfPmGroupV1 OBJECT-GROUP
    OBJECTS {
        portDevIwfPmIndex,
        portDevIwfPmName,
        portDevIwfPmRxPackets,
        portDevIwfPmTxPackets,
        portDevIwfPmMalformedPackets,
        portDevIwfPmReorderedPackets,
        portDevIwfPmMisorderedDroppedPackets,
        portDevIwfPmMissingPackets,
        portDevIwfPmPlayedOutPackets,
        portDevIwfPmJbOverrun,
        portDevIwfPmJbUnderrun,
        portDevIwfPmReset,
        portDevIwfPmInternalReference}
    STATUS      deprecated
    DESCRIPTION
        "The Port Device IWF PM objects (R21.0)."
    ::= { lumPortdeviceGroups 6 }

portDevEquipmentGroupV2 OBJECT-GROUP
    OBJECTS {
        portDevEquipmentIndex,
        portDevEquipmentName,
        portDevEquipmentDescr,
        portDevEquipmentLocation,
        portDevEquipmentAdminStatus,
        portDevEquipmentOperStatus,
        portDevEquipmentExpectedType,
        portDevEquipmentActualType,
        portDevEquipmentFwVersion,
        portDevEquipmentLinkPassThrough,
        portDevEquipmentSubrack,
        portDevEquipmentSlot,
        portDevEquipmentVlanId,
        portDevEquipmentRowStatus,
        portDevEquipmentNoDeviceFound,
        portDevEquipmentMultiDeviceFound,
        portDevEquipmentDeviceNotManageable,
        portDevEquipmentDeviceNotReachable,
        portDevEquipmentConfigurationFault,
        portDevEquipmentPowerAMissing,
        portDevEquipmentPowerBMissing,
        portDevEquipmentInternalReference,
        portDevEquipmentMacAddress,
        portDevEquipmentLocalPortIndex,
        portDevEquipmentAdminPowerA,
        portDevEquipmentAdminPowerB,
        portDevEquipmentDestMacAddress,
        portDevEquipmentDestMacAddressCheck,
        portDevEquipmentFwUpgradeStatus,
        portDevEquipmentDeviceVersionType,
        portDevEquipmentSelectedPort,
        portDevEquipmentActivePort}
    STATUS      deprecated
    DESCRIPTION
        "The equipment objects (R22.0)."
    ::= { lumPortdeviceGroups 7 }

portDevEquipmentGroupV3 OBJECT-GROUP
    OBJECTS {
        portDevEquipmentIndex,
        portDevEquipmentName,
        portDevEquipmentDescr,
        portDevEquipmentLocation,
        portDevEquipmentAdminStatus,
        portDevEquipmentOperStatus,
        portDevEquipmentExpectedType,
        portDevEquipmentActualType,
        portDevEquipmentFwVersion,
        portDevEquipmentFwUpgradeStatus,
        portDevEquipmentLinkPassThrough,
        portDevEquipmentSubrack,
        portDevEquipmentSlot,
        portDevEquipmentVlanId,
        portDevEquipmentRowStatus,
        portDevEquipmentNoDeviceFound,
        portDevEquipmentMultiDeviceFound,
        portDevEquipmentDeviceNotManageable,
        portDevEquipmentDeviceNotReachable,
        portDevEquipmentConfigurationFault,
        portDevEquipmentPowerAMissing,
        portDevEquipmentPowerBMissing,
        portDevEquipmentInternalReference,
        portDevEquipmentMacAddress,
        portDevEquipmentLocalPortIndex,
        portDevEquipmentAdminPowerA,
        portDevEquipmentAdminPowerB,
        portDevEquipmentSelectedPort,
        portDevEquipmentDestMacAddress,
        portDevEquipmentDestMacAddressCheck,
        portDevEquipmentDeviceVersionType,
        portDevEquipmentActivePort,
        portDevEquipmentDyingGasp}
    STATUS      deprecated
    DESCRIPTION
        "The equipment objects (R23.0)."
    ::= { lumPortdeviceGroups 8 }

portDevIwfGroupV2 OBJECT-GROUP
    OBJECTS {
        portDevIwfIndex,
        portDevIwfName,
        portDevIwfRtpClockSource,
        portDevIwfJitterBufferRecenter,
        portDevIwfInternalReference,
        portDevIwfLocalPortIndex,
        portDevIwfLossOfSignal,
        portDevIwfLossOfFrame,
        portDevIwfEquipmentFailure,
        portDevIwfNoTdmPayload,
        portDevIwfRemotePacketLost,
        portDevIwfLocalPacketLost,
        portDevIwfTributaryUnitAlarm,
        portDevIwfMultiplexSectionAlarm,
        portDevIwfMultiplexSectionRDI,
        portDevIwfAdminStatus,
        portDevIwfOperStatus,
        portDevIwfDescr,
        portDevIwfEtherType,
        portDevIwfSignalFormat,
        portDevIwfVlanId,
        portDevIwfVlanPriority,
        portDevIwfE1ChannelId,
	    portDevIwfE1ChannelKLM,
        portDevIwfDestMacAddress }
    STATUS      current
    DESCRIPTION
        "The Port Device IWF objects (R26.0)."
    ::= { lumPortdeviceGroups 9 }

portDevIwfPmGroupV2 OBJECT-GROUP
    OBJECTS {
        portDevIwfPmIndex,
        portDevIwfPmName,
        portDevIwfPmRxPackets,
        portDevIwfPmTxPackets,
        portDevIwfPmMalformedPackets,
        portDevIwfPmReorderedPackets,
        portDevIwfPmMisorderedDroppedPackets,
        portDevIwfPmMissingPackets,
        portDevIwfPmPlayedOutPackets,
        portDevIwfPmJbOverrun,
        portDevIwfPmJbUnderrun,
        portDevIwfPmReset,
        portDevIwfPmInternalReference,
        portDevIwfPmE1ChannelId}
    STATUS      current
    DESCRIPTION
        "The Port Device IWF PM objects (R26.0)."
    ::= { lumPortdeviceGroups 10 }

portDevEquipmentGroupV4 OBJECT-GROUP
    OBJECTS {
        portDevEquipmentIndex,
        portDevEquipmentName,
        portDevEquipmentDescr,
        portDevEquipmentLocation,
        portDevEquipmentAdminStatus,
        portDevEquipmentOperStatus,
        portDevEquipmentExpectedType,
        portDevEquipmentActualType,
        portDevEquipmentFwVersion,
        portDevEquipmentFwUpgradeStatus,
        portDevEquipmentLinkPassThrough,
        portDevEquipmentSubrack,
        portDevEquipmentSlot,
        portDevEquipmentVlanId,
        portDevEquipmentRowStatus,
        portDevEquipmentNoDeviceFound,
        portDevEquipmentMultiDeviceFound,
        portDevEquipmentDeviceNotManageable,
        portDevEquipmentDeviceNotReachable,
        portDevEquipmentConfigurationFault,
        portDevEquipmentPowerAMissing,
        portDevEquipmentPowerBMissing,
        portDevEquipmentInternalReference,
        portDevEquipmentMacAddress,
        portDevEquipmentLocalPortIndex,
        portDevEquipmentAdminPowerA,
        portDevEquipmentAdminPowerB,
        portDevEquipmentSelectedPort,
        portDevEquipmentDestMacAddressCheck,
        portDevEquipmentDeviceVersionType,
        portDevEquipmentActivePort,
        portDevEquipmentDyingGasp}
    STATUS     deprecated
    DESCRIPTION
        "The equipment objects (R26.0)."
    ::= { lumPortdeviceGroups 11 }

portDevEquipmentGroupV5 OBJECT-GROUP
    OBJECTS {
        portDevEquipmentIndex,
        portDevEquipmentName,
        portDevEquipmentDescr,
        portDevEquipmentLocation,
        portDevEquipmentAdminStatus,
        portDevEquipmentOperStatus,
        portDevEquipmentExpectedType,
        portDevEquipmentActualType,
        portDevEquipmentFwVersion,
        portDevEquipmentFwUpgradeStatus,
        portDevEquipmentLinkPassThrough,
        portDevEquipmentSubrack,
        portDevEquipmentSlot,
        portDevEquipmentVlanId,
        portDevEquipmentRowStatus,
        portDevEquipmentNoDeviceFound,
        portDevEquipmentMultiDeviceFound,
        portDevEquipmentDeviceNotManageable,
        portDevEquipmentDeviceNotReachable,
        portDevEquipmentConfigurationFault,
        portDevEquipmentPowerAMissing,
        portDevEquipmentPowerBMissing,
        portDevEquipmentInternalReference,
        portDevEquipmentMacAddress,
        portDevEquipmentLocalPortIndex,
        portDevEquipmentAdminPowerA,
        portDevEquipmentAdminPowerB,
        portDevEquipmentSelectedPort,
        portDevEquipmentDestMacAddressCheck,
        portDevEquipmentDeviceVersionType,
        portDevEquipmentActivePort,
        portDevEquipmentDyingGasp,
	    portDevEquipmentLosCsf}
    STATUS    current
    DESCRIPTION
        "The equipment objects (R28.0)."
    ::= { lumPortdeviceGroups 12 }


-- ----------------------------------------------------
-- Compliance
-- ----------------------------------------------------

lumPortdeviceBasicComplV1 MODULE-COMPLIANCE
    STATUS      deprecated
    DESCRIPTION
        "Basic implementation requirements for the port device MIB. (R21.0)."
    MODULE
        MANDATORY-GROUPS {
            portDevGeneralGroupV1,
            portDevGenericGroupV1,
            portDevEquipmentGroupV1,
            portDevFwGroupV1,
            portDevIwfGroupV1,
            portDevIwfPmGroupV1 }
    ::= { lumPortdeviceCompl 1 }

lumPortdeviceBasicComplV2 MODULE-COMPLIANCE
    STATUS      deprecated
    DESCRIPTION
        "Basic implementation requirements for the port device MIB. (R22.0)."
    MODULE
        MANDATORY-GROUPS {
            portDevGeneralGroupV1,
            portDevGenericGroupV1,
            portDevEquipmentGroupV2,
            portDevFwGroupV1,
            portDevIwfGroupV1,
            portDevIwfPmGroupV1 }
    ::= { lumPortdeviceCompl 2 }

lumPortdeviceBasicComplV3 MODULE-COMPLIANCE
    STATUS      deprecated
    DESCRIPTION
        "Basic implementation requirements for the port device MIB. (R23.0)."
    MODULE
        MANDATORY-GROUPS {
            portDevGeneralGroupV1,
            portDevGenericGroupV1,
            portDevEquipmentGroupV3,
            portDevFwGroupV1,
            portDevIwfGroupV1,
            portDevIwfPmGroupV1 }
    ::= { lumPortdeviceCompl 3 }

lumPortdeviceBasicComplV4 MODULE-COMPLIANCE
    STATUS      deprecated
    DESCRIPTION
        "Basic implementation requirements for the port device MIB. (R26.0)."
    MODULE
        MANDATORY-GROUPS {
            portDevGeneralGroupV1,
            portDevGenericGroupV1,
            portDevEquipmentGroupV4,
            portDevFwGroupV1,
            portDevIwfGroupV2,
            portDevIwfPmGroupV2 }
	    ::= { lumPortdeviceCompl 4 }

lumPortdeviceBasicComplV5 MODULE-COMPLIANCE
    STATUS      deprecated
    DESCRIPTION
        "Basic implementation requirements for the port device MIB. (R28.0)."
    MODULE
        MANDATORY-GROUPS {
            portDevGeneralGroupV1,
            portDevGenericGroupV1,
            portDevEquipmentGroupV5,
            portDevFwGroupV1,
            portDevIwfGroupV2,
            portDevIwfPmGroupV2 }
    ::= { lumPortdeviceCompl 5 }

lumPortdeviceBasicComplV6 MODULE-COMPLIANCE
    STATUS      current
    DESCRIPTION
        "Basic implementation requirements for the port device MIB. (R30.1)."
    MODULE
        MANDATORY-GROUPS {
            portDevGeneralGroupV1,
            portDevGenericGroupV2,
            portDevEquipmentGroupV5,
            portDevFwGroupV1,
            portDevIwfGroupV2,
            portDevIwfPmGroupV2 }
    ::= { lumPortdeviceCompl 6 }


END
