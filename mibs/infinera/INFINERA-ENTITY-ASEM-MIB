-- ***************************************************************
-- INFINERA-ENTITY-ASEM-MIB
-- Copyright (c) 2008-2017 by Infinera Inc.
-- All rights reserved.
-- ****************************************************************

INFINERA-ENTITY-ASEM-MIB DEFINITIONS ::= BEGIN

IMPORTS
    OBJECT-TYPE, MODULE-IDENTITY, Integer32        FROM SNMPv2-SMI
    OBJECT-GROUP, MODULE-COMPLIANCE                FROM SNMPv2-CONF
    TruthValue, DisplayString                      FROM SNMPv2-TC
    entPhysicalIndex                               FROM ENTITY-MIB
    equipment                                      FROM INFINERA-REG-MIB
	InfnEqptType                                   FROM INFINERA-TC-MIB;

asemMIB MODULE-IDENTITY
    LAST-UPDATED  "201703210000Z"
    ORGANIZATION
        "Infinera"
    CONTACT-INFO
        "Infinera
                1322 Bordeaux Drive
                Sunnyvale, CA - 94089
                Contact : Technical Support
                Email   : support@infinera.com
                Phone   : 1-877-INF-5288"
    DESCRIPTION
        " "
::= { equipment 56 }

-- Conformance Statements

asemConformance       OBJECT IDENTIFIER ::= { asemMIB 3 }
asemCompliances       OBJECT IDENTIFIER ::= { asemConformance 1 }
asemGroups            OBJECT IDENTIFIER ::= { asemConformance 2 }

asemTable  OBJECT-TYPE
    SYNTAX SEQUENCE OF AsemEntry
    MAX-ACCESS not-accessible
    STATUS     current
    DESCRIPTION
        "A list of ASEM entries. Each entry is uniquely identified by the value
                of entPhysicalIndex."
    ::= { asemMIB 1 }

asemEntry  OBJECT-TYPE
    SYNTAX     AsemEntry
    MAX-ACCESS not-accessible
    STATUS     current
    DESCRIPTION
        "A ASEM entry containing information pertaining to
            Infinera ASEM modules. Entries will exist in this table for
            entPhysicalEntries of type ASEM."
    INDEX { entPhysicalIndex }
    ::= { asemTable 1 }

AsemEntry ::= SEQUENCE {
    asemMoId                      DisplayString,
    asemProvEqptType              InfnEqptType
}

asemMoId     OBJECT-TYPE
    SYNTAX      DisplayString
    MAX-ACCESS  read-write
    STATUS      current
    DESCRIPTION ""
    ::= { asemEntry 1 }

asemProvEqptType OBJECT-TYPE
    SYNTAX      InfnEqptType
    MAX-ACCESS  read-write
    STATUS      current
    DESCRIPTION ""
    ::= { asemEntry 2 }


asemCompliance  MODULE-COMPLIANCE
    STATUS     current
    DESCRIPTION
        "Describes the requirements for conformance to the FMMC-MIB"
    MODULE
        MANDATORY-GROUPS { asemGroup }
    ::= { asemCompliances 1 }


asemGroup  OBJECT-GROUP
    OBJECTS {
        asemMoId,
        asemProvEqptType
    }
    STATUS     current
    DESCRIPTION
        " A collection of objects for managing a FMMC module"
    ::= { asemGroups 1 }


END
