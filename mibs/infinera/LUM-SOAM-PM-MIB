LUM-SOAM-PM-MIB DEFINITIONS ::= BEGIN
  IMPORTS
    MODULE-IDENTITY, OBJECT-TYPE, Unsigned32, Counter64
             FROM SNMPv2-SMI         -- RFC 2578
    TruthValue, MacAddress, DateAndTime, RowStatus, TimeInterval, DisplayString
             FROM SNMPv2-TC          -- RFC 2579
    OBJECT-GROUP, MODULE-COMPLIANCE
             FROM SNMPv2-CONF        -- RFC 2580
    Dot1agCfmMepIdOrZero
             FROM IEEE8021-CFM-MIB
    IEEE8021PriorityValue
            FROM IEEE8021-TC-MIB    -- IEEE 802.1ap
    MefSoamTcSessionType, MefSoamTcStatusType
             FROM MEF-SOAM-TC-MIB
    lumModules, lumSoamPmMIB
            FROM LUM-REG
    MgmtNameString, SubrackNumber, SlotNumber, FaultStatus,
    Unsigned32WithNA, BoardOrInterfaceOperStatus, BoardOrInterfaceAdminStatus, CommandString
            FROM LUM-TC;


lumSoamPmMIBModule MODULE-IDENTITY
    LAST-UPDATED
        "201706150000Z" -- June 15th 2017
    ORGANIZATION
        "Infinera Corporation"
    CONTACT-INFO
        "techsupport@infinera.com"
    DESCRIPTION
        "This MIB module contains the management objects for the
        management of Ethernet Services Operations, Administration
        and Maintenance for Performance Monitoring (SOAM-PM).
"
    REVISION
        "201706150000Z" -- June 15th 2017
    DESCRIPTION
        "Changes made for release r29.0:
         - Changed ORGANIZATION and CONTACT-INFO"
    REVISION
        "201601110000Z" -- Jan 11th 2016
    DESCRIPTION
        "Added default value notPresent for operStatus."
    REVISION
        "201501140000Z" -- Jan 14th 2015
    DESCRIPTION
        "Updated for revision R25:
         -Added emxp240iie"
    REVISION
        "201405160000Z" -- May 16th 2014
    DESCRIPTION
        "Updated for revision R23."
    ::= { lumModules 60 }

-- ----------------------------------------------------
-- Compliance area, containing groups and compliance
-- specifications.
-- ----------------------------------------------------

lumSoamPmConfs OBJECT IDENTIFIER ::= { lumSoamPmMIB 1 }

-- *****************************************************************************
-- SOAM-PM MIB Module - Conformance Information
-- *****************************************************************************

lumSoamPmGroups      OBJECT IDENTIFIER ::= { lumSoamPmConfs 1 }
lumSoamPmCompliances OBJECT IDENTIFIER ::= { lumSoamPmConfs 2 }

-- *****************************************************************************
-- Object definitions in the SOAM PM MIB Module
-- *****************************************************************************
lumSoamPmMIBObjects     OBJECT IDENTIFIER ::= { lumSoamPmMIB 2 }

-- *****************************************************************************
-- Groups in the SOAM PM MIB Module
-- *****************************************************************************

soamPmGeneral OBJECT IDENTIFIER ::= { lumSoamPmMIBObjects 1 }
soamPmLmObjects OBJECT IDENTIFIER ::= { lumSoamPmMIBObjects 2 }
soamPmDmObjects OBJECT IDENTIFIER ::= { lumSoamPmMIBObjects 3 }

-- --------------------------------------------------
-- General group
-- --------------------------------------------------

soamPmGeneralLastChangeTime OBJECT-TYPE
    SYNTAX      DateAndTime
    MAX-ACCESS  read-only
    STATUS      current
    DESCRIPTION
        "The time when the configuration of the MIB was
        last changed.
"
    ::= { soamPmGeneral 1 }

soamPmGeneralLmStateLastChangeTime OBJECT-TYPE
   SYNTAX      DateAndTime
   MAX-ACCESS  read-only
   STATUS      current
   DESCRIPTION
       "The time when the state of the MIB was last
       changed.
"
   ::= { soamPmGeneral 2 }

soamPmGeneralLmObjectsTableSize OBJECT-TYPE
    SYNTAX      Unsigned32
    MAX-ACCESS  read-only
    STATUS      current
    DESCRIPTION
        "Size of ethernet service OAM LM objects table
"
    ::= { soamPmGeneral 3 }

soamPmGeneralDmObjectsTableSize OBJECT-TYPE
    SYNTAX      Unsigned32
    MAX-ACCESS  read-only
    STATUS      current
    DESCRIPTION
        "Size of ethernet service OAM DM objects table
"
    ::= { soamPmGeneral 4 }

-- ***************************************************************************
-- Ethernet Loss Measurement Configuration Table
-- ***************************************************************************

soamPmLmCfgTable OBJECT-TYPE
    SYNTAX      SEQUENCE OF SoamPmLmCfgEntry
    MAX-ACCESS  not-accessible
    STATUS      current
    DESCRIPTION
       "This table includes configuration objects and operations for the
        Frame Loss Measurement function defined in [Y.1731] and [MEF SOAM-PM].

        Each row in the table represents a Loss Measurement session for
        the defined remote MEP."

    REFERENCE
       "[MEF SOAM-PM] R68; [Y.1731]"
    ::= { soamPmLmObjects 1 }

soamPmLmCfgEntry OBJECT-TYPE
    SYNTAX      SoamPmLmCfgEntry
    MAX-ACCESS  not-accessible
    STATUS      current
    DESCRIPTION
            "The conceptual row of soamPmLmCfgTable.
"
    INDEX { soamPmLmCfgIndex }
    ::= { soamPmLmCfgTable 1 }

SoamPmLmCfgEntry ::=
    SEQUENCE {

    soamPmLmCfgIndex                Unsigned32,
    soamPmLmCfgName                 MgmtNameString,
    soamPmLmCfgDescr                DisplayString,
    soamPmLmCfgSubrack              SubrackNumber,
    soamPmLmCfgSlot                 SlotNumber,
    soamPmLmCfgEnabled              TruthValue,
    soamPmLmCfgMessagePeriod        INTEGER,
    soamPmLmCfgDestMacAddress       MacAddress,
    soamPmLmCfgMepName              DisplayString,
    soamPmLmCfgMaidIdentifier       DisplayString,
    soamPmLmCfgDestMepId            Dot1agCfmMepIdOrZero,
    soamPmLmCfgDestIsMepId          TruthValue,
    soamPmLmCfgInternalReference    Unsigned32,
    soamPmLmCfgLocalDeviceType      INTEGER,
    soamPmLmCfgType                 INTEGER,
    soamPmLmCfgPriority             IEEE8021PriorityValue,
    soamPmLmCfgAvailabilityFlrThreshold  Unsigned32,
    soamPmLmCfgAvailabilityUasAlarmThreshold  Unsigned32,
    soamPmLmCfgSessionType          MefSoamTcSessionType,
    soamPmLmCfgSessionStatus        MefSoamTcStatusType,
    soamPmLmCfgCosAwareness         INTEGER,
    soamPmLmCfgRowStatus            RowStatus,
    soamPmLmCfgAdminStatus          BoardOrInterfaceAdminStatus,
    soamPmLmCfgOperStatus           BoardOrInterfaceOperStatus,
    soamPmLmCfgStats                CommandString }

soamPmLmCfgIndex OBJECT-TYPE
    SYNTAX      Unsigned32(1..4294967295)
    MAX-ACCESS  read-only
    STATUS      current
    DESCRIPTION
       "An index to the Loss Measurement Configuration table which indicates
        the specific measurement session for the MEP.
        The index is not persistent and may be reused between restarts.
"
    ::= { soamPmLmCfgEntry 1 }

soamPmLmCfgName OBJECT-TYPE
    SYNTAX      MgmtNameString
    MAX-ACCESS  read-only
    STATUS      current
    DESCRIPTION
        "The name of the LM session.
        The name has the same structure as the name of the remote mep.
        LM:megname:slot:subrack:mepid:<priority>
        The priority is not used for NID.
"
    ::= { soamPmLmCfgEntry 2 }

soamPmLmCfgDescr OBJECT-TYPE
    SYNTAX      DisplayString
    MAX-ACCESS  read-write
    STATUS      current
    DESCRIPTION
        "User configurable label for the LM session.
"
    DEFVAL { "" }
    ::= { soamPmLmCfgEntry 3 }

soamPmLmCfgSubrack OBJECT-TYPE
    SYNTAX      SubrackNumber
    MAX-ACCESS  read-create
    STATUS      current
    DESCRIPTION
        "The number of the subrack where this OAM object is defined
"
    ::= { soamPmLmCfgEntry 4 }

soamPmLmCfgSlot OBJECT-TYPE
    SYNTAX      SlotNumber
    MAX-ACCESS  read-create
    STATUS      current
    DESCRIPTION
        "The slot where this OAM Object is defined.
"
    ::= { soamPmLmCfgEntry 5 }

 soamPmLmCfgEnabled OBJECT-TYPE
     SYNTAX      TruthValue
     MAX-ACCESS  read-create
     STATUS      current
     DESCRIPTION
        "This object specifies whether the Loss Measurement session
         is enabled.
         This Attribute is only used for NID,
         Admin status and oper status are used in EMXP.
"
     REFERENCE
        "[MEF SOAM-PM] R4, R5, R6, O1, R12, R14"
     DEFVAL { true }
     ::= { soamPmLmCfgEntry 6 }

soamPmLmCfgMessagePeriod OBJECT-TYPE
    SYNTAX      INTEGER {
                    interval100ms (0),
                    interval1s (1),
                    interval10s (2)
                   }
    MAX-ACCESS  read-create
    STATUS      current
    DESCRIPTION
       "This object specifies the interval between Loss Measurement
        OAM message transmission. For Loss Measurement monitoring
        applications the default value is 1 sec.

        This object can only be written at creation time and cannot be
        modified once it has been created.
"
    REFERENCE
       "[MEF SOAM-PM] R76, R77, D29, D30"
    DEFVAL { interval1s }
    ::= { soamPmLmCfgEntry 7 }


soamPmLmCfgDestMacAddress OBJECT-TYPE
    SYNTAX      MacAddress
    MAX-ACCESS  read-create
    STATUS      current
    DESCRIPTION
       "The Target or Destination MAC Address Field to be transmitted.

        This address will be used if the value of the object
        soamPmLmDestIsMepId is 'false'.

        This object can only be written at creation time and cannot be
        modified once it has been created.
"
    REFERENCE
       "[MEF SOAM-PM] R70, R104"
    ::= { soamPmLmCfgEntry 8 }

soamPmLmCfgMepName OBJECT-TYPE
    SYNTAX      DisplayString
    MAX-ACCESS  read-only
    STATUS      current
    DESCRIPTION
        "The identifier of the MEP this LM session belongs to.
        Persistent cross-reference to MEP table.
"
    ::= { soamPmLmCfgEntry 9 }


soamPmLmCfgMaidIdentifier OBJECT-TYPE
    SYNTAX      DisplayString
    MAX-ACCESS  read-create
    STATUS      current
    DESCRIPTION
        "A unique user definied identifier for the MEG.

"
    DEFVAL { "" }
    ::= { soamPmLmCfgEntry 10 }

soamPmLmCfgDestMepId OBJECT-TYPE
    SYNTAX      Dot1agCfmMepIdOrZero
    MAX-ACCESS  read-create
    STATUS      current
    DESCRIPTION
       "The Maintenance Association End Point Identifier of
        another MEP in the same Maintenance Association to which
        the SOAM LM frame is to be sent.

        This address will be used if the value of the column
        soamPmLmDestIsMepId is 'true'. A value of zero
        means that the destination MEP ID has not been configured.

        This object can only be written at creation time and cannot be
        modified once it has been created.
"
    REFERENCE
       "[MEF SOAM-PM] R70, R104"
    DEFVAL { 0 }
    ::= { soamPmLmCfgEntry 11 }

soamPmLmCfgDestIsMepId OBJECT-TYPE
    SYNTAX      TruthValue
    MAX-ACCESS  read-create
    STATUS      current
    DESCRIPTION
       "A value of 'true' indicates that MEPID of the target MEP is used for
        SOAM LM frame transmission.

        A value of 'false' indicates that the MAC address of the
        target MEP is used for SOAM LM frame transmission.

        This object can only be written at creation time and cannot be
        modified once it has been created.
"
    REFERENCE
       "[MEF SOAM-PM] R70, R104"
    DEFVAL { true }
    ::= { soamPmLmCfgEntry 12 }

soamPmLmCfgInternalReference OBJECT-TYPE
    SYNTAX      Unsigned32 (0..2147483647)
    MAX-ACCESS  read-create
    STATUS      current
    DESCRIPTION
        "For internal use only.
"
    DEFVAL { 0 }
    ::= {soamPmLmCfgEntry 13 }

soamPmLmCfgLocalDeviceType OBJECT-TYPE
    SYNTAX      INTEGER {
                    emxp  (1),
                    nidGe (2) }
    MAX-ACCESS  read-create
    STATUS      current
    DESCRIPTION
        "The type of device the LM is created and associated.
"
    DEFVAL { emxp }
    ::= { soamPmLmCfgEntry 14 }

soamPmLmCfgType OBJECT-TYPE
    SYNTAX      INTEGER {
                    lmLmm   (1),
                    lmSlm   (2),
                    lmCcm   (3)
                    }
    MAX-ACCESS  read-create
    STATUS      current
    DESCRIPTION
       "This object specifies what type of Loss Measurement
        will be performed.

        lmLmm(1)        LMM SOAM PDU generated and received LMR responses tracked
        lmSlm(2)        SLM SOAM PDU generated and received SLR responses tracked
        lmCcm(3)        CCM SOAM PDU generated and received CCM PDUs tracked

        The lmSlm value is required. The lmLmm and lmCcm values are optional.

        The lmCcm loss measurement values are only valid for a point-to-point
        MEG. Multipoint MEGs may give unreliable loss measurements.

        Only lmLmm is supported.

        This object can only be written at creation time and cannot be
        modified once it has been created.
"
    REFERENCE
       "[Y.1731] [MEF SOAM-PM] R51, R68, O7, R102"
    DEFVAL { lmLmm }
    ::= { soamPmLmCfgEntry 15 }

soamPmLmCfgPriority OBJECT-TYPE
    SYNTAX      IEEE8021PriorityValue
    MAX-ACCESS  read-create
    STATUS      current
    DESCRIPTION
       "This object specifies the Loss Measurement OAM message priority
        as well as the priority of the service/OAM traffic to be monitored.

        If the session attibute soamPmLmCfgCosAwareness is 'priorityAware'
        then only frames of the same Class of Service are counted.
        If the Session is 'priorityBlind' then all frames
        for all Class of Service combined are counted.

        This object can only be written at creation time and cannot be
        modified once it has been created.
"
    REFERENCE
       "[MEF SOAM-PM] R1, R2, R71, D28, R72, R73, R105-R109, D45;
        [MEF 10.2.1] Section 6.8"
    DEFVAL { 0 }
    ::= { soamPmLmCfgEntry 16 }

soamPmLmCfgAvailabilityFlrThreshold OBJECT-TYPE
    SYNTAX      Unsigned32 (0..100000)
    MAX-ACCESS  read-create
    STATUS      current
    DESCRIPTION
       "This object specifies a configurable availability threshold to be
        used in evaluating the availability/unavailability status of an
        availability indicator per MEF 10.2.1. The availability threshold range
        of 0.000 through 100.000 is supported. This parameter is
        equivalent to the Availability parameter of 'C' as specified by
        MEF 10.2.1.

        For SNMP, units are in millipercent (percent with 3 decimals).

        This object can only be written at creation time and cannot be
        modified once it has been created.
"
    REFERENCE
       "[MEF 10.2.1] Section 7.9.8; [MEF SOAM-PM] R81, R82, D34"
    DEFVAL { 1 }
    ::= { soamPmLmCfgEntry 17 }

soamPmLmCfgAvailabilityUasAlarmThreshold OBJECT-TYPE
    SYNTAX      Unsigned32 (0..900)
    MAX-ACCESS  read-create
    STATUS      current
    DESCRIPTION
       " This object specifies the configurable number of seconds
       the session shall be determined to be unavailable before raising
       an alarm.
"
    DEFVAL { 5 }
    ::= { soamPmLmCfgEntry 18 }

soamPmLmCfgSessionType OBJECT-TYPE
    SYNTAX      MefSoamTcSessionType
    MAX-ACCESS  read-create
    STATUS      current
    DESCRIPTION
       "This object indicates whether the current session is defined to
        be 'Proactive' or 'On-Demand'. A value of 'proactive'
        indicates the current session is 'Proactive'. A value of 'onDemand'
        indicates the current session is 'On-Demand'.

        Only Proactive sessions are supported.

        This object can only be written at creation time and cannot be
        modified once it has been created.
"
    REFERENCE
       "[MEF SOAM-PM] R3"
    DEFVAL { proactive }
    ::= { soamPmLmCfgEntry 19 }

soamPmLmCfgSessionStatus OBJECT-TYPE
    SYNTAX      MefSoamTcStatusType
    MAX-ACCESS  read-only
    STATUS      current
    DESCRIPTION
       "This object indicates the current status of the LM session. A value
        of 'active' indicates the current LM session is active, i.e. the current
        time lies between the start time and the stop time, and
        soamPmLmCfgEnabled is true. A value of 'notActive' indicates the
        current LM session is not active, i.e. it has not started yet, has
        stopped upon reaching the stop time, or is disabled.
"
    ::= { soamPmLmCfgEntry 20 }

soamPmLmCfgCosAwareness OBJECT-TYPE
    SYNTAX      INTEGER {
                        priorityBlind (1),
                        priorityAware (2) }
    MAX-ACCESS read-create
    STATUS current
    DESCRIPTION
        "Define CoS awareness for the LM initiator.
         A CoS aware LM Initiater will send counters associated with the priority of the sent LMM packets.

         priorityBlind - LM Initiator is Cos unaware (counters for all priorities are aggregated.)

         priorityAware - LM Responder is CoS aware (use counters associated with the priority of sent LMM packet).
"
    DEFVAL { priorityBlind }
    ::= { soamPmLmCfgEntry 21 }

soamPmLmCfgRowStatus OBJECT-TYPE
    SYNTAX      RowStatus
    MAX-ACCESS  read-create
    STATUS      current
    DESCRIPTION
        "Manages creation and deletion of conceptual rows.
        See also SNMPv2-TC.

        Note: The newly created object will not necessarily
        receive the same index as used in the create
        procedure.
        This attribute can be written via SNMP.

"
    ::=  { soamPmLmCfgEntry 22 }

soamPmLmCfgAdminStatus OBJECT-TYPE
    SYNTAX      BoardOrInterfaceAdminStatus
    MAX-ACCESS  read-write
    STATUS      current
    DESCRIPTION
        "The administrative state for an LM Session.

        down - The LM session should be inactive.

        service - The LM session is activated but
        alarms are suppressed. Intended for use during
        service or re-configuration. When service is
        concluded adminStatus should be set to 'up'
        again.

        up - The session should be activated when
        it becomes available. Alarms are not suppressed.

        notApplicable - used to tell that attribute
        is not used in current configuration.
"
    DEFVAL { up }
    ::=  { soamPmLmCfgEntry 23 }

soamPmLmCfgOperStatus OBJECT-TYPE
    SYNTAX      BoardOrInterfaceOperStatus
    MAX-ACCESS  read-only
    STATUS      current
    DESCRIPTION
        "The operational state for the object.

        notPresent - The object is not available.

        down - The object is de-activated or there are
        faults preventing its transition to the 'up' state.

        up - The object is active.
"
    DEFVAL { notPresent }
    ::= { soamPmLmCfgEntry 24 }

soamPmLmCfgStats OBJECT-TYPE
    SYNTAX      CommandString
    MAX-ACCESS  read-only
    STATUS      current
    DESCRIPTION
        "View current statistics for the LM session.
"
    ::= { soamPmLmCfgEntry 25 }

 -- **************************************************************************
 --  Ethernet Loss Measurement Current Statistic Table
 -- **************************************************************************

soamPmLmStatsTable OBJECT-TYPE
    SYNTAX      SEQUENCE OF SoamPmLmStatsEntry
    MAX-ACCESS  not-accessible
    STATUS      current
    DESCRIPTION
       "This table contains the results for the current Measurement
        Interval in a SOAM Loss Measurement session gathered during the interval
        indicated by soamPmLmCfgMeasurementInterval.

        A row in this table is created automatically
        by the SNMP Agent when the Loss Measurement session is configured."

    REFERENCE
       "[MEF SOAM-PM] R7, R15, D9, D18"
    ::= { soamPmLmObjects 2 }

soamPmLmStatsEntry OBJECT-TYPE
    SYNTAX      SoamPmLmStatsEntry
    MAX-ACCESS  not-accessible
    STATUS      current
    DESCRIPTION
        "The conceptual row of soamPmLmStatsTable
"
    INDEX      { soamPmLmStatsIndex }
    ::= { soamPmLmStatsTable 1 }

SoamPmLmStatsEntry ::=
    SEQUENCE {
    soamPmLmStatsIndex                                  Unsigned32,
    soamPmLmStatsLocalDeviceType                        INTEGER,
    soamPmLmStatsName                                   MgmtNameString,
    soamPmLmStatsSubrack                                SubrackNumber,
    soamPmLmStatsSlot                                   SlotNumber,
    soamPmLmStatsMaidIdentifier                         DisplayString,
    soamPmLmStatsDestMepId                              Dot1agCfmMepIdOrZero,
    soamPmLmStatsInternalReference                      Unsigned32,
    soamPmLmStatsMepName                                DisplayString,
    soamPmLmStatsSuspect15Min                           TruthValue,
    soamPmLmStatsSuspectPrevious15Min                   TruthValue,
    soamPmLmStatsSuspect24H                             TruthValue,
    soamPmLmStatsReset15Min                             INTEGER,
    soamPmLmStatsReset24H                               INTEGER,
    soamPmLmStatsStartTime15Min                         DateAndTime,
    soamPmLmStatsElapsedTime15Min                       TimeInterval,
    soamPmLmStatsForwardTransmittedFrames15Min          Counter64,
    soamPmLmStatsForwardReceivedFrames15Min             Counter64,
    soamPmLmStatsForwardMinFlr15Min                     Unsigned32WithNA,
    soamPmLmStatsForwardMaxFlr15Min                     Unsigned32,
    soamPmLmStatsForwardAvgFlr15Min                     Unsigned32,
    soamPmLmStatsForwardHighLoss15Min                   Unsigned32,
    soamPmLmStatsBackwardTransmittedFrames15Min         Counter64,
    soamPmLmStatsBackwardReceivedFrames15Min            Counter64,
    soamPmLmStatsBackwardMinFlr15Min                    Unsigned32WithNA,
    soamPmLmStatsBackwardMaxFlr15Min                    Unsigned32,
    soamPmLmStatsBackwardAvgFlr15Min                    Unsigned32,
    soamPmLmStatsBackwardHighLoss15Min                  Unsigned32,
    soamPmLmStatsUnavailableSeconds15Min                Unsigned32,
    soamPmLmStatsStartTimePrevious15Min                 DateAndTime,
    soamPmLmStatsElapsedTimePrevious15Min               TimeInterval,
    soamPmLmStatsForwardTransmittedFramesPrevious15Min  Counter64,
    soamPmLmStatsForwardReceivedFramesPrevious15Min     Counter64,
    soamPmLmStatsForwardMinFlrPrevious15Min             Unsigned32WithNA,
    soamPmLmStatsForwardMaxFlrPrevious15Min             Unsigned32,
    soamPmLmStatsForwardAvgFlrPrevious15Min             Unsigned32,
    soamPmLmStatsForwardHighLossPrevious15Min           Unsigned32,
    soamPmLmStatsBackwardTransmittedFramesPrevious15Min Counter64,
    soamPmLmStatsBackwardReceivedFramesPrevious15Min    Counter64,
    soamPmLmStatsBackwardMinFlrPrevious15Min            Unsigned32WithNA,
    soamPmLmStatsBackwardMaxFlrPrevious15Min            Unsigned32,
    soamPmLmStatsBackwardAvgFlrPrevious15Min            Unsigned32,
    soamPmLmStatsBackwardHighLossPrevious15Min          Unsigned32,
    soamPmLmStatsStartTime24H                           DateAndTime,
    soamPmLmStatsElapsedTime24H                         TimeInterval,
    soamPmLmStatsForwardTransmittedFrames24H            Counter64,
    soamPmLmStatsForwardReceivedFrames24H               Counter64,
    soamPmLmStatsForwardMinFlr24H                       Unsigned32WithNA,
    soamPmLmStatsForwardMaxFlr24H                       Unsigned32,
    soamPmLmStatsForwardAvgFlr24H                       Unsigned32,
    soamPmLmStatsForwardHighLoss24H                     Unsigned32,
    soamPmLmStatsBackwardTransmittedFrames24H           Counter64,
    soamPmLmStatsBackwardReceivedFrames24H              Counter64,
    soamPmLmStatsBackwardMinFlr24H                      Unsigned32WithNA,
    soamPmLmStatsBackwardMaxFlr24H                      Unsigned32,
    soamPmLmStatsBackwardAvgFlr24H                      Unsigned32,
    soamPmLmStatsBackwardHighLoss24H                    Unsigned32,
    soamPmLmStatsUas                                    FaultStatus,
    soamPmLmStatsPriority                               IEEE8021PriorityValue }

soamPmLmStatsIndex OBJECT-TYPE
    SYNTAX      Unsigned32
    MAX-ACCESS  read-only
    STATUS      current
    DESCRIPTION
       "The index for the current Measurement Interval for this
        PM session.
        The index is the same as for the configuration, i.e soamPmLmCfgIndex
        and is not persistent and may be reused between restarts.
"
    ::= { soamPmLmStatsEntry 1 }

soamPmLmStatsLocalDeviceType OBJECT-TYPE
    SYNTAX      INTEGER {
                    emxp  (1),
                    nidGe (2) }
    MAX-ACCESS  read-only
    STATUS      current
    DESCRIPTION
        "The type of device the LM is created and associated.
"
    DEFVAL { emxp }
    ::= { soamPmLmStatsEntry 2 }

soamPmLmStatsName OBJECT-TYPE
    SYNTAX      MgmtNameString
    MAX-ACCESS  read-only
    STATUS      current
    DESCRIPTION
        "The name of the LM session, same as the name of remote MEP
        that this LM session is associated with.
"
    ::= { soamPmLmStatsEntry 3  }

soamPmLmStatsSubrack OBJECT-TYPE
    SYNTAX      SubrackNumber
    MAX-ACCESS  read-only
    STATUS      current
    DESCRIPTION
        "The number of the subrack where this OAM object is defined
"
    ::= { soamPmLmStatsEntry 4 }

soamPmLmStatsSlot OBJECT-TYPE
    SYNTAX      SlotNumber
    MAX-ACCESS  read-only
    STATUS      current
    DESCRIPTION
        "The slot where this OAM Object is defined.
"
    ::= { soamPmLmStatsEntry 5 }

soamPmLmStatsMaidIdentifier OBJECT-TYPE
    SYNTAX      DisplayString
    MAX-ACCESS  read-only
    STATUS      current
    DESCRIPTION
        "A unique user definied identifier for the MEG.

"
    DEFVAL { "" }
    ::= { soamPmLmStatsEntry 6 }

soamPmLmStatsDestMepId OBJECT-TYPE
    SYNTAX      Dot1agCfmMepIdOrZero
    MAX-ACCESS  read-only
    STATUS      current
    DESCRIPTION
       "The Maintenance Association End Point Identifier of
        another MEP in the same Maintenance Association to which
        the SOAM LM frame is to be sent.

        This address will be used if the value of the column
        soamPmLmDestIsMepId is 'true'. A value of zero
        means that the destination MEP ID has not been configured.

        This object is only valid for the entity transmitting the Loss
        Measurement frames, types 'lmLmm' and 'lmSlm'. It is not applicable for
        the 'lmCcm' type.

        This object can only be written at creation time and cannot be
        modified once it has been created.
"
    REFERENCE
       "[MEF SOAM-PM] R70, R104"
    DEFVAL { 0 }
    ::= { soamPmLmStatsEntry 7 }

soamPmLmStatsInternalReference OBJECT-TYPE
    SYNTAX      Unsigned32 (0..2147483647)
    MAX-ACCESS  read-only
    STATUS      current
    DESCRIPTION
        "For internal use only.
"
    DEFVAL { 0 }
    ::= { soamPmLmStatsEntry 8  }

soamPmLmStatsMepName OBJECT-TYPE
    SYNTAX      DisplayString
    MAX-ACCESS  read-only
    STATUS      current
    DESCRIPTION
        "The identifier of the MEP this LM session belongs to.
        Persistent cross-reference to MEP table.
"
    ::= { soamPmLmStatsEntry 9  }

soamPmLmStatsSuspect15Min OBJECT-TYPE
    SYNTAX      TruthValue
    MAX-ACCESS  read-only
    STATUS      current
    DESCRIPTION
       "Whether the Measurement Interval has been marked as suspect.

        The object is set to false at the start of a measurement
        interval. It is set to true when there is a discontinuity in the
        performance measurements during the Measurement Interval.  Conditions
        for a discontinuity include, but are not limited to the following:

        1 - The local time-of-day clock is adjusted by at least 10 seconds
        2 - The conducting of a performance measurement is halted before the
            current Measurement Interval is completed
        3 - A local test, failure, or reconfiguration that disrupts service
"
    REFERENCE
       "[MEF SOAM-PM] R39, R40, R41"
    ::= { soamPmLmStatsEntry 10 }

soamPmLmStatsSuspectPrevious15Min OBJECT-TYPE
    SYNTAX      TruthValue
    MAX-ACCESS  read-only
    STATUS      current
    DESCRIPTION
       "Whether the Measurement Interval has been marked as suspect.

        The object is set to false at the start of a measurement
        interval. It is set to true when there is a discontinuity in the
        performance measurements during the Measurement Interval.  Conditions
        for a discontinuity include, but are not limited to the following:

        1 - The local time-of-day clock is adjusted by at least 10 seconds
        2 - The conducting of a performance measurement is halted before the
            current Measurement Interval is completed
        3 - A local test, failure, or reconfiguration that disrupts service
"
    REFERENCE
       "[MEF SOAM-PM] R39, R40, R41"
    ::= { soamPmLmStatsEntry 11 }

soamPmLmStatsSuspect24H OBJECT-TYPE
    SYNTAX      TruthValue
    MAX-ACCESS  read-only
    STATUS      current
    DESCRIPTION
       "Whether the Measurement Interval has been marked as suspect.

        The object is set to false at the start of a measurement
        interval. It is set to true when there is a discontinuity in the
        performance measurements during the Measurement Interval.  Conditions
        for a discontinuity include, but are not limited to the following:

        1 - The local time-of-day clock is adjusted by at least 10 seconds
        2 - The conducting of a performance measurement is halted before the
            current Measurement Interval is completed
        3 - A local test, failure, or reconfiguration that disrupts service
"
    REFERENCE
       "[MEF SOAM-PM] R39, R40, R41"
    ::= { soamPmLmStatsEntry 12 }

soamPmLmStatsReset15Min OBJECT-TYPE
    SYNTAX      INTEGER {
                    normal (1),
                    reset (2) }
    MAX-ACCESS  read-write
    STATUS      current
    DESCRIPTION
        "Reset the 15 minute counters for the
        LM session.

        After a successful reset the default value
        (normal) is restored in this action attribute.

"
    DEFVAL { normal }
    ::= { soamPmLmStatsEntry 13 }

soamPmLmStatsReset24H OBJECT-TYPE
    SYNTAX      INTEGER {
                    normal (1),
                    reset (2) }
    MAX-ACCESS  read-write
    STATUS      current
    DESCRIPTION
        "Reset the 24 hour counters for the LM session.

        After a successful reset the default value
        (normal) is restored in this action attribute.

"
    DEFVAL { normal }
    ::= { soamPmLmStatsEntry 14 }

soamPmLmStatsStartTime15Min OBJECT-TYPE
    SYNTAX      DateAndTime
    MAX-ACCESS  read-only
    STATUS      current
    DESCRIPTION
       "The time that the current Measurement Interval started.
"
    REFERENCE
       "[MEF SOAM-PM] R22, R87, R112"
    ::= { soamPmLmStatsEntry 15 }

soamPmLmStatsElapsedTime15Min OBJECT-TYPE
    SYNTAX      TimeInterval
    MAX-ACCESS  read-only
    STATUS      current
    DESCRIPTION
       "The time that the current Measurement Interval has been running, in seconds.
"
    REFERENCE
       "[MEF SOAM-PM] R24, R87, R112"
    ::= { soamPmLmStatsEntry 16 }

soamPmLmStatsForwardTransmittedFrames15Min OBJECT-TYPE
    SYNTAX      Counter64
    MAX-ACCESS  read-only
    STATUS      current
    DESCRIPTION
       "This object contains the number of frames transmitted in the
        forward direction by this MEP.

        For a PM Session of types lmLmm and lmCcm this includes Ethernet
        Service Frames and SOAM PDUs that are in a higher MEG level only.

        For a PM Session of type lmSlm this includes the count of SOAM
        ETH-SLM frames only.
"
    REFERENCE
       "[MEF SOAM-PM] R69, R87, R112"
    ::= { soamPmLmStatsEntry 17 }

soamPmLmStatsForwardReceivedFrames15Min OBJECT-TYPE
    SYNTAX      Counter64
    MAX-ACCESS  read-only
    STATUS      current
    DESCRIPTION
       "This object contains the number of frames received in the
        forward direction by this MEP.

        For a PM Session of types lmLmm and lmCcm this includes Ethernet
        Service Frames and SOAM PDUs that are in a higher MEG level only.

        For a PM Session of types lmSlm this includes the count of SOAM
        ETH-SLM frames only.
"
    REFERENCE
       "[MEF SOAM-PM] R69, R87, R112"
    ::= { soamPmLmStatsEntry 18 }

soamPmLmStatsForwardMinFlr15Min OBJECT-TYPE
    SYNTAX      Unsigned32WithNA (0..100000 | 4294967294)
    MAX-ACCESS  read-only
    STATUS      current
    DESCRIPTION
       "This object contains the minimum one-way frame loss
        ratio (FLR) in the forward direction calculated by this MEP for this
        Measurement Interval. The FLR value is a ratio that is expressed in
        percent with a value of 0.000 through 100.000. Precision is in millipercent
"
    REFERENCE
       "[MEF SOAM-PM] D37"
    DEFVAL { 4294967294 }
    ::= { soamPmLmStatsEntry 19 }

soamPmLmStatsForwardMaxFlr15Min OBJECT-TYPE
    SYNTAX      Unsigned32 (0..100000)
    MAX-ACCESS  read-only
    STATUS      current
    DESCRIPTION
       "This object contains the maximum one-way frame loss
        ratio (FLR) in the forward direction calculated by this MEP for this
        Measurement Interval. The FLR value is a ratio that is expressed in
        percent with a value of 0.000 through 100.000. Precision is in millipercent
"
    REFERENCE
       "[MEF SOAM-PM] D37"
    ::= { soamPmLmStatsEntry 20 }

soamPmLmStatsForwardAvgFlr15Min OBJECT-TYPE
    SYNTAX      Unsigned32 (0..100000)
    MAX-ACCESS  read-only
    STATUS      current
    DESCRIPTION
       "This object contains the average one-way frame loss
        ratio (FLR) in the forward direction calculated by this MEP for this
        Measurement Interval. The FLR value is a ratio that is expressed in
        percent with a value of 0.000 through 100.000. Precision is in millipercent
"
    REFERENCE
       "[MEF SOAM-PM] D37"
    ::= { soamPmLmStatsEntry 21 }

soamPmLmStatsForwardHighLoss15Min OBJECT-TYPE
     SYNTAX      Unsigned32
     MAX-ACCESS  read-only
     STATUS      current
     DESCRIPTION
        "This object is the number of high loss intervals (HLI) over
         time in the forward direction.

         The value starts at 0 and increments for every HLI that occurs.
         This parameter is equivalent to 'L Sub T' found in MEF 10.2.1.
"
     REFERENCE
        "[MEF 10.2.1] 6.9.9; [MEF SOAM-PM] R87"
     ::= { soamPmLmStatsEntry 22 }

soamPmLmStatsBackwardTransmittedFrames15Min OBJECT-TYPE
    SYNTAX      Counter64
    MAX-ACCESS  read-only
    STATUS      current
    DESCRIPTION
       "This object contains the number of frames transmitted in the
        backward direction by this MEP.

        For a PM Session of type lmLmm and lmCcm this includes Ethernet
        Service Frames and SOAM PDUs that are in a higher MEG level only.

        For a PM Session of type lmSlm this includes the count of SOAM
        ETH-SLM frames only.
"
    REFERENCE
       "[MEF SOAM-PM] R69, R87, R112"
    ::= { soamPmLmStatsEntry 23 }

soamPmLmStatsBackwardReceivedFrames15Min OBJECT-TYPE
    SYNTAX      Counter64
    MAX-ACCESS  read-only
    STATUS      current
    DESCRIPTION
       "This object contains the number of frames received in the
        backward direction by this MEP.

        For a PM Session of type lmLmm this includes Ethernet
        Service Frames and SOAM PDUs that are in a higher MEG level only.

        For a PM Session of type lmSlm this includes the count of SOAM
        ETH-SLM frames only.
"
    REFERENCE
       "[MEF SOAM-PM] R69, R87, R112"
    ::= { soamPmLmStatsEntry 24 }

soamPmLmStatsBackwardMinFlr15Min OBJECT-TYPE
    SYNTAX      Unsigned32WithNA (0..100000 | 4294967294)
    MAX-ACCESS  read-only
    STATUS      current
    DESCRIPTION
       "This object contains the minimum one-way frame loss
        ratio (FLR) in the backward direction calculated by this MEP for
        this Measurement Interval. The FLR value is a ratio that is expressed in
        percent with a value of 0.000 through 100.000. Precision is in millipercent
"
    REFERENCE
       "[MEF SOAM-PM] D37"
    DEFVAL { 4294967294 }
    ::= { soamPmLmStatsEntry 25 }

soamPmLmStatsBackwardMaxFlr15Min OBJECT-TYPE
    SYNTAX      Unsigned32 (0..100000)
    MAX-ACCESS  read-only
    STATUS      current
    DESCRIPTION
       "This object contains the maximum one-way frame loss
        ratio (FLR) in the backward direction calculated by this MEP for
        this Measurement Interval. The FLR value is a ratio that is expressed in
        percent with a value of 0.000 through 100.000. Precision is in millipercent
"
    REFERENCE
       "[MEF SOAM-PM] D37"
    ::= { soamPmLmStatsEntry 26 }

soamPmLmStatsBackwardAvgFlr15Min OBJECT-TYPE
    SYNTAX      Unsigned32 (0..100000 | 4294967295)
    MAX-ACCESS  read-only
    STATUS      current
    DESCRIPTION
       "This object contains the average one-way frame loss
        ratio (FLR) in the backward direction calculated by this MEP for
        this Measurement Interval. The FLR value is a ratio that is expressed in
        percent with a value of 0.000 through 100.000. Precision is in millipercent
"
    REFERENCE
       "[MEF SOAM-PM] D37"
    ::= { soamPmLmStatsEntry 27 }

soamPmLmStatsBackwardHighLoss15Min OBJECT-TYPE
     SYNTAX      Unsigned32
     MAX-ACCESS  read-only
     STATUS      current
     DESCRIPTION
        "This object is the number of high loss intervals (HLI) over
         time in the backwards direction.

         The value starts at 0 and increments for every HLI that occurs.
         This parameter is equivalent to 'L Sub T' found in MEF 10.2.1.
"
     REFERENCE
        "[MEF 10.2.1] 6.9.9; [MEF SOAM-PM] R87"
    ::= { soamPmLmStatsEntry 28 }

soamPmLmStatsUnavailableSeconds15Min OBJECT-TYPE
    SYNTAX      Unsigned32
    MAX-ACCESS  read-only
    STATUS      current
    DESCRIPTION
       "This object contains the number if seconds the service has been
        been unavailable during the 15 min interval.

        The service has been unavailable when the FLR threshold is exceeded
        in either the forward or backward direction.

"
    ::= { soamPmLmStatsEntry 29 }

soamPmLmStatsStartTimePrevious15Min OBJECT-TYPE
    SYNTAX      DateAndTime
    MAX-ACCESS  read-only
    STATUS      current
    DESCRIPTION
       "The time that the current Measurement Interval started.
"
    REFERENCE
       "[MEF SOAM-PM] R22, R87, R112"
    ::= { soamPmLmStatsEntry 30 }

soamPmLmStatsElapsedTimePrevious15Min OBJECT-TYPE
    SYNTAX      TimeInterval
    MAX-ACCESS  read-only
    STATUS      current
    DESCRIPTION
       "The time that the current Measurement Interval has been running, in seconds.
"
    REFERENCE
       "[MEF SOAM-PM] R24, R87, R112"
    ::= { soamPmLmStatsEntry 31 }

soamPmLmStatsForwardTransmittedFramesPrevious15Min OBJECT-TYPE
    SYNTAX      Counter64
    MAX-ACCESS  read-only
    STATUS      current
    DESCRIPTION
       "This object contains the number of frames transmitted in the
        forward direction by this MEP.

        For a PM Session of types lmLmm and lmCcm this includes Ethernet
        Service Frames and SOAM PDUs that are in a higher MEG level only.

        For a PM Session of type lmSlm this includes the count of SOAM
        ETH-SLM frames only.
"
    REFERENCE
       "[MEF SOAM-PM] R69, R87, R112"
    ::= { soamPmLmStatsEntry 32 }

soamPmLmStatsForwardReceivedFramesPrevious15Min OBJECT-TYPE
    SYNTAX      Counter64
    MAX-ACCESS  read-only
    STATUS      current
    DESCRIPTION
       "This object contains the number of frames received in the
        forward direction by this MEP.

        For a PM Session of types lmLmm and lmCcm this includes Ethernet
        Service Frames and SOAM PDUs that are in a higher MEG level only.

        For a PM Session of types lmSlm this includes the count of SOAM
        ETH-SLM frames only.
"
    REFERENCE
       "[MEF SOAM-PM] R69, R87, R112"
    ::= { soamPmLmStatsEntry 33 }

soamPmLmStatsForwardMinFlrPrevious15Min OBJECT-TYPE
    SYNTAX      Unsigned32WithNA (0..100000 | 4294967294)
    MAX-ACCESS  read-only
    STATUS      current
    DESCRIPTION
       "This object contains the minimum one-way frame loss
        ratio (FLR) in the forward direction calculated by this MEP for this
        Measurement Interval. The FLR value is a ratio that is expressed in
        percent with a value of 0.000 through 100.000. Precision is in millipercent
"
    REFERENCE
       "[MEF SOAM-PM] D37"
    DEFVAL { 4294967294 }
    ::= { soamPmLmStatsEntry 34 }

soamPmLmStatsForwardMaxFlrPrevious15Min OBJECT-TYPE
    SYNTAX      Unsigned32 (0..100000)
    MAX-ACCESS  read-only
    STATUS      current
    DESCRIPTION
       "This object contains the maximum one-way frame loss
        ratio (FLR) in the forward direction calculated by this MEP for this
        Measurement Interval. The FLR value is a ratio that is expressed in
        percent with a value of 0.000 through 100.000. Precision is in millipercent
"
    REFERENCE
       "[MEF SOAM-PM] D37"
    ::= { soamPmLmStatsEntry 35 }

soamPmLmStatsForwardAvgFlrPrevious15Min OBJECT-TYPE
    SYNTAX      Unsigned32 (0..100000)
    MAX-ACCESS  read-only
    STATUS      current
    DESCRIPTION
       "This object contains the average one-way frame loss
        ratio (FLR) in the forward direction calculated by this MEP for this
        Measurement Interval. The FLR value is a ratio that is expressed in
        percent with a value of 0.000 through 100.000. Precision is in millipercent
"
    REFERENCE
       "[MEF SOAM-PM] D37"
    ::= { soamPmLmStatsEntry 36 }

soamPmLmStatsForwardHighLossPrevious15Min OBJECT-TYPE
     SYNTAX      Unsigned32
     MAX-ACCESS  read-only
     STATUS      current
     DESCRIPTION
        "This object is the number of high loss intervals (HLI) over
         time in the forward direction.

         The value starts at 0 and increments for every HLI that occurs.
         This parameter is equivalent to 'L Sub T' found in MEF 10.2.1.
"
     REFERENCE
        "[MEF 10.2.1] 6.9.9; [MEF SOAM-PM] R87"
     ::= { soamPmLmStatsEntry 37 }

soamPmLmStatsBackwardTransmittedFramesPrevious15Min OBJECT-TYPE
    SYNTAX      Counter64
    MAX-ACCESS  read-only
    STATUS      current
    DESCRIPTION
       "This object contains the number of frames transmitted in the
        backward direction by this MEP.

        For a PM Session of type lmLmm and lmCcm this includes Ethernet
        Service Frames and SOAM PDUs that are in a higher MEG level only.

        For a PM Session of type lmSlm this includes the count of SOAM
        ETH-SLM frames only.
"
    REFERENCE
       "[MEF SOAM-PM] R69, R87, R112"
    ::= { soamPmLmStatsEntry 38 }

soamPmLmStatsBackwardReceivedFramesPrevious15Min OBJECT-TYPE
    SYNTAX      Counter64
    MAX-ACCESS  read-only
    STATUS      current
    DESCRIPTION
       "This object contains the number of frames received in the
        backward direction by this MEP.

        For a PM Session of type lmLmm this includes Ethernet
        Service Frames and SOAM PDUs that are in a higher MEG level only.

        For a PM Session of type lmSlm this includes the count of SOAM
        ETH-SLM frames only.
"
    REFERENCE
       "[MEF SOAM-PM] R69, R87, R112"
    ::= { soamPmLmStatsEntry 39 }

soamPmLmStatsBackwardMinFlrPrevious15Min OBJECT-TYPE
    SYNTAX      Unsigned32WithNA (0..100000 | 4294967294)
    MAX-ACCESS  read-only
    STATUS      current
    DESCRIPTION
       "This object contains the minimum one-way frame loss
        ratio (FLR) in the backward direction calculated by this MEP for
        this Measurement Interval. The FLR value is a ratio that is expressed in
        percent with a value of 0.000 through 100.000. Precision is in millipercent
"
    REFERENCE
       "[MEF SOAM-PM] D37"
    DEFVAL { 4294967294 }
    ::= { soamPmLmStatsEntry 40 }

soamPmLmStatsBackwardMaxFlrPrevious15Min OBJECT-TYPE
    SYNTAX      Unsigned32 (0..100000)
    MAX-ACCESS  read-only
    STATUS      current
    DESCRIPTION
       "This object contains the maximum one-way frame loss
        ratio (FLR) in the backward direction calculated by this MEP for
        this Measurement Interval. The FLR value is a ratio that is expressed
        percent with a value of 0.000 through 100.000. Precision is in millipercent
"
    REFERENCE
       "[MEF SOAM-PM] D37"
    ::= { soamPmLmStatsEntry 41 }

soamPmLmStatsBackwardAvgFlrPrevious15Min OBJECT-TYPE
    SYNTAX      Unsigned32 (0..100000)
    MAX-ACCESS  read-only
    STATUS      current
    DESCRIPTION
       "This object contains the average one-way frame loss
        ratio (FLR) in the backward direction calculated by this MEP for
        this Measurement Interval. The FLR value is a ratio that is expressed in
        percent with a value of 0.000 through 100.000. Precision is in millipercent
"
    REFERENCE
       "[MEF SOAM-PM] D37"
    ::= { soamPmLmStatsEntry 42 }

soamPmLmStatsBackwardHighLossPrevious15Min OBJECT-TYPE
     SYNTAX      Unsigned32
     MAX-ACCESS  read-only
     STATUS      current
     DESCRIPTION
        "This object is the number of high loss intervals (HLI) over
         time in the backwards direction.

         The value starts at 0 and increments for every HLI that occurs.
         This parameter is equivalent to 'L Sub T' found in MEF 10.2.1.
"
     REFERENCE
        "[MEF 10.2.1] 6.9.9; [MEF SOAM-PM] R87"
    ::= { soamPmLmStatsEntry 43 }

soamPmLmStatsStartTime24H OBJECT-TYPE
    SYNTAX      DateAndTime
    MAX-ACCESS  read-only
    STATUS      current
    DESCRIPTION
       "The time that the current Measurement Interval started.
"
    REFERENCE
       "[MEF SOAM-PM] R22, R87, R112"
    ::= { soamPmLmStatsEntry 44 }

soamPmLmStatsElapsedTime24H OBJECT-TYPE
    SYNTAX      TimeInterval
    MAX-ACCESS  read-only
    STATUS      current
    DESCRIPTION
       "The time that the current Measurement Interval has been running, in seconds.
"
    REFERENCE
       "[MEF SOAM-PM] R24, R87, R112"
    ::= { soamPmLmStatsEntry 45 }

soamPmLmStatsForwardTransmittedFrames24H OBJECT-TYPE
    SYNTAX      Counter64
    MAX-ACCESS  read-only
    STATUS      current
    DESCRIPTION
       "This object contains the number of frames transmitted in the
        forward direction by this MEP.

        For a PM Session of types lmLmm and lmCcm this includes Ethernet
        Service Frames and SOAM PDUs that are in a higher MEG level only.

        For a PM Session of type lmSlm this includes the count of SOAM
        ETH-SLM frames only.
"
    REFERENCE
       "[MEF SOAM-PM] R69, R87, R112"
    ::= { soamPmLmStatsEntry 46 }

soamPmLmStatsForwardReceivedFrames24H OBJECT-TYPE
    SYNTAX      Counter64
    MAX-ACCESS  read-only
    STATUS      current
    DESCRIPTION
       "This object contains the number of frames received in the
        forward direction by this MEP.

        For a PM Session of types lmLmm and lmCcm this includes Ethernet
        Service Frames and SOAM PDUs that are in a higher MEG level only.

        For a PM Session of types lmSlm this includes the count of SOAM
        ETH-SLM frames only.
"
    REFERENCE
       "[MEF SOAM-PM] R69, R87, R112"
    ::= { soamPmLmStatsEntry 47 }

soamPmLmStatsForwardMinFlr24H OBJECT-TYPE
    SYNTAX      Unsigned32WithNA (0..100000 | 4294967294)
    MAX-ACCESS  read-only
    STATUS      current
    DESCRIPTION
       "This object contains the minimum one-way frame loss
        ratio (FLR) in the forward direction calculated by this MEP for this
        Measurement Interval. The FLR value is a ratio that is expressed in
        percent with a value of 0.000 through 100.000. Precision is in millipercent
"
    REFERENCE
       "[MEF SOAM-PM] D37"
    DEFVAL { 4294967294 }
    ::= { soamPmLmStatsEntry 48 }

soamPmLmStatsForwardMaxFlr24H OBJECT-TYPE
    SYNTAX      Unsigned32 (0..100000)
    MAX-ACCESS  read-only
    STATUS      current
    DESCRIPTION
       "This object contains the maximum one-way frame loss
        ratio (FLR) in the forward direction calculated by this MEP for this
        Measurement Interval. The FLR value is a ratio that is expressed in
        percent with a value of 0.000 through 100.000. Precision is in millipercent
"
    REFERENCE
       "[MEF SOAM-PM] D37"
    ::= { soamPmLmStatsEntry 49 }

soamPmLmStatsForwardAvgFlr24H OBJECT-TYPE
    SYNTAX      Unsigned32 (0..100000)
    MAX-ACCESS  read-only
    STATUS      current
    DESCRIPTION
       "This object contains the average one-way frame loss
        ratio (FLR) in the forward direction calculated by this MEP for this
        Measurement Interval. The FLR value is a ratio that is expressed in
        percent with a value of 0.000 through 100.000. Precision is in millipercent
"
    REFERENCE
       "[MEF SOAM-PM] D37"
    ::= { soamPmLmStatsEntry 50 }

soamPmLmStatsForwardHighLoss24H OBJECT-TYPE
     SYNTAX      Unsigned32
     MAX-ACCESS  read-only
     STATUS      current
     DESCRIPTION
        "This object is the number of high loss intervals (HLI) over
         time in the forward direction.

         The value starts at 0 and increments for every HLI that occurs.
         This parameter is equivalent to 'L Sub T' found in MEF 10.2.1.
"
     REFERENCE
        "[MEF 10.2.1] 6.9.9; [MEF SOAM-PM] R87"
     ::= { soamPmLmStatsEntry 51 }

soamPmLmStatsBackwardTransmittedFrames24H OBJECT-TYPE
    SYNTAX      Counter64
    MAX-ACCESS  read-only
    STATUS      current
    DESCRIPTION
       "This object contains the number of frames transmitted in the
        backward direction by this MEP.

        For a PM Session of type lmLmm and lmCcm this includes Ethernet
        Service Frames and SOAM PDUs that are in a higher MEG level only.

        For a PM Session of type lmSlm this includes the count of SOAM
        ETH-SLM frames only.
"
    REFERENCE
       "[MEF SOAM-PM] R69, R87, R112"
    ::= { soamPmLmStatsEntry 52 }

soamPmLmStatsBackwardReceivedFrames24H OBJECT-TYPE
    SYNTAX      Counter64
    MAX-ACCESS  read-only
    STATUS      current
    DESCRIPTION
       "This object contains the number of frames received in the
        backward direction by this MEP.

        For a PM Session of type lmLmm this includes Ethernet
        Service Frames and SOAM PDUs that are in a higher MEG level only.

        For a PM Session of type lmSlm this includes the count of SOAM
        ETH-SLM frames only.
"
    REFERENCE
       "[MEF SOAM-PM] R69, R87, R112"
    ::= { soamPmLmStatsEntry 53 }

soamPmLmStatsBackwardMinFlr24H OBJECT-TYPE
    SYNTAX      Unsigned32WithNA (0..100000 | 4294967294)
    MAX-ACCESS  read-only
    STATUS      current
    DESCRIPTION
       "This object contains the minimum one-way frame loss
        ratio (FLR) in the backward direction calculated by this MEP for
        this Measurement Interval. The FLR value is a ratio that is expressed in
        percent with a value of 0.000 through 100.000. Precision is in millipercent
"
    REFERENCE
       "[MEF SOAM-PM] D37"
    DEFVAL { 4294967294 }
    ::= { soamPmLmStatsEntry 54 }

soamPmLmStatsBackwardMaxFlr24H OBJECT-TYPE
    SYNTAX      Unsigned32 (0..100000)
    MAX-ACCESS  read-only
    STATUS      current
    DESCRIPTION
       "This object contains the maximum one-way frame loss
        ratio (FLR) in the backward direction calculated by this MEP for
        this Measurement Interval. The FLR value is a ratio that is expressed
        percent with a value of 0.000 through 100.000. Precision is in millipercent
"
    REFERENCE
       "[MEF SOAM-PM] D37"
    ::= { soamPmLmStatsEntry 55 }

soamPmLmStatsBackwardAvgFlr24H OBJECT-TYPE
    SYNTAX      Unsigned32 (0..100000)
    MAX-ACCESS  read-only
    STATUS      current
    DESCRIPTION
       "This object contains the average one-way frame loss
        ratio (FLR) in the backward direction calculated by this MEP for
        this Measurement Interval. The FLR value is a ratio that is expressed in
        percent with a value of 0.000 through 100.000. Precision is in millipercent
"
    REFERENCE
       "[MEF SOAM-PM] D37"
    ::= { soamPmLmStatsEntry 56 }

soamPmLmStatsBackwardHighLoss24H OBJECT-TYPE
     SYNTAX      Unsigned32
     MAX-ACCESS  read-only
     STATUS      current
     DESCRIPTION
        "This object is the number of high loss intervals (HLI) over
         time in the backwards direction.

         The value starts at 0 and increments for every HLI that occurs.
         This parameter is equivalent to 'L Sub T' found in MEF 10.2.1.
"
     REFERENCE
        "[MEF 10.2.1] 6.9.9; [MEF SOAM-PM] R87"
    ::= { soamPmLmStatsEntry 57 }

soamPmLmStatsUas OBJECT-TYPE
    SYNTAX FaultStatus
    MAX-ACCESS  read-only
    STATUS      current
    DESCRIPTION
        "Unavailable seconds (UAS) 15 min threshold
        exceeded.

        A: The number of unavailable seconds during a
       period exceeds the associated threshold.

        D: At the start of a new 15 minute period the
        associated UAS counter is reset to zero, by
        definition. At the same time the fault status
       is cleared.

"
    ::= { soamPmLmStatsEntry 58 }

soamPmLmStatsPriority OBJECT-TYPE
    SYNTAX      IEEE8021PriorityValue
    MAX-ACCESS  read-only
    STATUS      current
    DESCRIPTION
       "This object specifies the Loss Measurement OAM message priority
        as well as the priority of the service/OAM traffic to be monitored.
        Only frames of the same Class of Service are counted.

        The default value is to be the value which yields the lowest frame
        loss.

        This object is not applicable if soamPmLmCfgType is set to lmCcm.

        This object can only be written at creation time and cannot be
        modified once it has been created.
"
    REFERENCE
       "[MEF SOAM-PM] R1, R2, R71, D28, R72, R73, R105-R109, D45;
        [MEF 10.2.1] Section 6.8"
    DEFVAL { 0 }
    ::= { soamPmLmStatsEntry 59 }



-- **************************************************************************
-- Ethernet Delay Measurement Configuration Table
-- **************************************************************************

soamPmDmCfgTable OBJECT-TYPE
    SYNTAX      SEQUENCE OF SoamPmDmCfgEntry
    MAX-ACCESS  not-accessible
    STATUS      current
    DESCRIPTION
       "This table includes configuration objects and operations for the
        Delay Measurement function.

        Each row in the table represents a Delay Measurement session for
        the defined remote MEP."
    REFERENCE
       "[MEF SOAM-PM] R50; [Y.1731]"
    ::= { soamPmDmObjects 1 }

soamPmDmCfgEntry OBJECT-TYPE
    SYNTAX      SoamPmDmCfgEntry
    MAX-ACCESS  not-accessible
    STATUS      current
    DESCRIPTION
        "The conceptual row of soamPmDmCfgTable.
"
    INDEX      { soamPmDmCfgIndex }
    ::= { soamPmDmCfgTable 1 }

SoamPmDmCfgEntry ::=
    SEQUENCE {
    soamPmDmCfgIndex                Unsigned32,
    soamPmDmCfgName                 MgmtNameString,
    soamPmDmCfgDescr                DisplayString,
    soamPmDmCfgSubrack              SubrackNumber,
    soamPmDmCfgSlot                 SlotNumber,
    soamPmDmCfgInternalReference    Unsigned32,
    soamPmDmCfgLocalDeviceType      INTEGER,
    soamPmDmCfgDropEligible         TruthValue,
    soamPmDmCfgType                 INTEGER,
    soamPmDmCfgEnabled              TruthValue,
    soamPmDmCfgMessagePeriod        INTEGER,
    soamPmDmCfgPriority             IEEE8021PriorityValue,
    soamPmDmCfgDestMacAddress       MacAddress,
    soamPmDmCfgMepName              DisplayString,
    soamPmDmCfgMaidIdentifier       DisplayString,
    soamPmDmCfgDestMepId            Dot1agCfmMepIdOrZero,
    soamPmDmCfgDestIsMepId          TruthValue,
    soamPmDmCfgSessionType          MefSoamTcSessionType,
    soamPmDmCfgSessionStatus        MefSoamTcStatusType,
    soamPmDmCfgRowStatus            RowStatus,
    soamPmDmCfgAdminStatus          BoardOrInterfaceAdminStatus,
    soamPmDmCfgOperStatus           BoardOrInterfaceOperStatus,
    soamPmDmCfgStats                CommandString}

soamPmDmCfgIndex OBJECT-TYPE
    SYNTAX      Unsigned32(1..4294967295)
    MAX-ACCESS  read-only
    STATUS      current
    DESCRIPTION
       "An index to the Delay Measurement Configuration table which indicates
        the specific measurement session for the MEP.

        The index is not persistent and may be reused between restarts.
"
    ::= { soamPmDmCfgEntry 1 }

soamPmDmCfgName OBJECT-TYPE
    SYNTAX      MgmtNameString
    MAX-ACCESS  read-only
    STATUS      current
    DESCRIPTION
        "The name of the DM session.
        The name has the same structure as the name of the remote mep.
        DM:megname:slot:subrack:mepid:<priority>
        The priority is not used for NID.
"
    ::= { soamPmDmCfgEntry 2 }

soamPmDmCfgDescr OBJECT-TYPE
    SYNTAX      DisplayString
    MAX-ACCESS  read-write
    STATUS      current
    DESCRIPTION
        "User configurable label for the DM session.
"
    DEFVAL { "" }
    ::= { soamPmDmCfgEntry 3 }

soamPmDmCfgSubrack OBJECT-TYPE
    SYNTAX      SubrackNumber
    MAX-ACCESS  read-create
    STATUS      current
    DESCRIPTION
        "The number of the subrack where this OAM object is defined
"
    ::= { soamPmDmCfgEntry 4 }

soamPmDmCfgSlot OBJECT-TYPE
    SYNTAX      SlotNumber
    MAX-ACCESS  read-create
    STATUS      current
    DESCRIPTION
        "The slot where this OAM Object is defined.
"
    ::= { soamPmDmCfgEntry 5 }

soamPmDmCfgInternalReference OBJECT-TYPE
    SYNTAX      Unsigned32 (0..4294967295)
    MAX-ACCESS  read-create
    STATUS      current
    DESCRIPTION
        "For internal use only.
"
    DEFVAL { 0 }
    ::= {soamPmDmCfgEntry 6 }

soamPmDmCfgLocalDeviceType OBJECT-TYPE
    SYNTAX      INTEGER {
                    emxp  (1),
                    nidGe (2) }
    MAX-ACCESS  read-create
    STATUS      current
    DESCRIPTION
        "The type of device the DM is created and associated.
"
    DEFVAL { emxp }
    ::= { soamPmDmCfgEntry 7 }

soamPmDmCfgDropEligible OBJECT-TYPE
     SYNTAX      TruthValue
     MAX-ACCESS  read-create
     STATUS      current
     DESCRIPTION
        "This object specifies the drop eligibility of a specific OAM frame.
         Frames with ETH-DM information are always marked as drop ineligible.
"
     REFERENCE
        "[MEF SOAM-PM] R4, R5, R6, O1, R12, R14"
     DEFVAL { false }
     ::= { soamPmDmCfgEntry 8 }

soamPmDmCfgType OBJECT-TYPE
    SYNTAX      INTEGER {
                  dmDmm   (1),
                  dm1DmTx (2),
                  dm1DmRx (3)
                }
    MAX-ACCESS  read-create
    STATUS      current
    DESCRIPTION
       "This object indicates what type of Delay Measurement is to
        be performed.

        dmDmm(1)         DMM SOAM PDU generated, DMR responses received
                         (one-way or two-way measurements)
        dm1DmTx(2)       1DM SOAM PDU generated (one-way measurements are made by
                         the receiver)
        dm1DmRx(3)       1DM SOAM PDU received and tracked (one-way measurements)

        The exact PDUs to use are specified by this object in combination with
        soamPmDmCfgVersion.

        The value dmDMM is required. The values dm1DmTx and dm1DmRx are optional.

        Only mmDmm is supported.

        This object can only be written at creation time and cannot be
        modified once it has been created.
"
    REFERENCE
       "[MEF SOAM-PM] R52, R53, R54, O5, R88"
   DEFVAL { dmDmm }
    ::= { soamPmDmCfgEntry 9 }

soamPmDmCfgEnabled OBJECT-TYPE
    SYNTAX      TruthValue
    MAX-ACCESS  read-create
    STATUS      current
    DESCRIPTION
       "This object specifies whether the Delay Measurement session is
        enabled.

        This Attribute is only used for NID,
        Admin status and oper status are used in EMXP.

"
    REFERENCE
       "[MEF SOAM-PM] R4, R5, R6, O1, R12, R14"
    DEFVAL { true }
    ::= { soamPmDmCfgEntry 10 }

soamPmDmCfgMessagePeriod OBJECT-TYPE
    SYNTAX      INTEGER {
                    interval100ms (0),
                    interval1s (1),
                    interval10s (2)
                   }
    MAX-ACCESS  read-create
    STATUS      current
    DESCRIPTION
       "This object specifies the interval between Delay Measurement
        OAM message transmission. For Delay Measurement monitoring
        applications, the default value is 100ms s.

        This object can only be written at creation time and cannot be
        modified once it has been created.
"
    REFERENCE
       "[MEF SOAM-PM] R61, R62, D22, R95, R96, D39"
    DEFVAL { interval100ms }
    ::= { soamPmDmCfgEntry 11 }

soamPmDmCfgPriority OBJECT-TYPE
    SYNTAX      IEEE8021PriorityValue
    MAX-ACCESS  read-create
    STATUS      current
    DESCRIPTION
       "This object specifies the priority of frames with
        Delay Measurement OAM message information.

        This object can only be written at creation time and cannot be
        modified once it has been created.
"
    REFERENCE
       "[MEF SOAM-PM] R1, R2, R56, D21, R57, R58, R90-R94, D28;
        [MEF 10.2.1] Section 6.8"
    DEFVAL { 0 }
    ::= { soamPmDmCfgEntry 12 }

soamPmDmCfgDestMacAddress OBJECT-TYPE
    SYNTAX      MacAddress
    MAX-ACCESS  read-create
    STATUS      current
    DESCRIPTION
       "The Target or Destination MAC Address Field to be transmitted.

        This object can only be written at creation time and cannot be
        modified once it has been created.
"
    REFERENCE
       "[MEF SOAM-PM] R55, R89"
    ::= { soamPmDmCfgEntry 13 }

soamPmDmCfgMepName OBJECT-TYPE
    SYNTAX      DisplayString
    MAX-ACCESS  read-only
    STATUS      current
    DESCRIPTION
        "The identifier of the MEP this DM session belongs to.
        Persistent cross-reference to MEP table.
"
    ::= { soamPmDmCfgEntry 14 }

soamPmDmCfgMaidIdentifier OBJECT-TYPE
    SYNTAX      DisplayString
    MAX-ACCESS  read-create
    STATUS      current
    DESCRIPTION
        "A unique user definied identifier for the MEG.

"
    DEFVAL { "" }
    ::= { soamPmDmCfgEntry 15 }

soamPmDmCfgDestMepId OBJECT-TYPE
    SYNTAX      Dot1agCfmMepIdOrZero
    MAX-ACCESS  read-create
    STATUS      current
    DESCRIPTION
       "The Maintenance Association End Point Identifier of
        another MEP in the same Maintenance Association to which
        the SOAM DM frame is to be sent.

        This address will be used if the value of the column
        soamPmDmDestIsMepId is 'true'. A value of zero
        means that the destination MEP ID has not been configured.

        This object can only be written at creation time and cannot be
        modified once it has been created.
"
    REFERENCE
       "[MEF SOAM-PM] R55, R89"
    DEFVAL { 0 }
    ::= { soamPmDmCfgEntry 16 }

soamPmDmCfgDestIsMepId OBJECT-TYPE
    SYNTAX      TruthValue
    MAX-ACCESS  read-create
    STATUS      current
    DESCRIPTION
       "A value of 'true' indicates that MEPID of the target MEP is used for
        SOAM DM frame transmission.

        A value of 'false' indicates that the destination MAC address of the
        target MEP is used for SOAM DM frame transmission.

        This object can only be written at creation time and cannot be
        modified once it has been created.
"
    REFERENCE
       "[MEF SOAM-PM] R55, R89"
    DEFVAL { true }
    ::= { soamPmDmCfgEntry 17 }

soamPmDmCfgSessionType OBJECT-TYPE
    SYNTAX      MefSoamTcSessionType
    MAX-ACCESS  read-create
    STATUS      current
    DESCRIPTION
       "This object indicates whether the current session is defined to
        be 'Proactive' or 'On-Demand'. A value of 'proactive'
        indicates the current session is 'Proactive'. A value of 'onDemand'
        indicates the current session is 'On-Demand'.

        Only Proactive is supported.
        This object can only be written at creation time and cannot be
        modified once it has been created.
"
    REFERENCE
       "[MEF SOAM-PM] R3"
    DEFVAL { proactive }
    ::= { soamPmDmCfgEntry 18 }

soamPmDmCfgSessionStatus OBJECT-TYPE
    SYNTAX      MefSoamTcStatusType
    MAX-ACCESS  read-only
    STATUS      current
    DESCRIPTION
       "This object indicates the current status of the DM session. A value
        of 'active' indicates the current DM session is active.
        A value of 'notActive' indicates the
        current DM session is not active.
        This attibute is only supported for NID.
        For EXMP, admin and operstatus attyributes are used.

"
    ::= { soamPmDmCfgEntry 19 }


soamPmDmCfgRowStatus OBJECT-TYPE
    SYNTAX      RowStatus
    MAX-ACCESS  read-create
    STATUS      current
    DESCRIPTION
        "Manages creation and deletion of conceptual rows.
        See also SNMPv2-TC.

        Note: The newly created object will not necessarily
        receive the same index as used in the create
        procedure.
        This attribute can be written via SNMP.

"
    ::=  { soamPmDmCfgEntry 20 }

soamPmDmCfgAdminStatus OBJECT-TYPE
    SYNTAX      BoardOrInterfaceAdminStatus
    MAX-ACCESS  read-write
    STATUS      current
    DESCRIPTION
        "The administrative state for a DM Session.

        down - The DM session should be inactive.

        service - The DM session is activated but
        alarms are suppressed. Intended for use during
        service or re-configuration. When service is
        concluded adminStatus should be set to 'up'
        again.

        up - The session should be activated when
        it becomes available. Alarms are not suppressed.

        notApplicable - used to tell that attribute
        is not used in current configuration.
"
    DEFVAL { up }
    ::=  { soamPmDmCfgEntry 21 }

soamPmDmCfgOperStatus OBJECT-TYPE
    SYNTAX      BoardOrInterfaceOperStatus
    MAX-ACCESS  read-only
    STATUS      current
    DESCRIPTION
        "The operational state for the object.

        notPresent - The object is not available.

        down - The object is de-activated or there are
        faults preventing its transition to the 'up' state.

        up - The object is active.

"
    ::= { soamPmDmCfgEntry 22 }

soamPmDmCfgStats OBJECT-TYPE
    SYNTAX      CommandString
    MAX-ACCESS  read-only
    STATUS      current
    DESCRIPTION
        "View current statistics for the DM session.
"
    ::= { soamPmDmCfgEntry 23 }

-- **************************************************************************
-- Ethernet Delay Measurement Current Statistic Table
-- **************************************************************************

soamPmDmStatsTable OBJECT-TYPE
    SYNTAX      SEQUENCE OF SoamPmDmStatsEntry
    MAX-ACCESS  not-accessible
    STATUS      current
    DESCRIPTION
       "This table contains the results for the current Measurement
        Interval in a SOAM Delay Measurement session gathered during the interval
        indicated by soamPmLmCfgMeasurementInterval.

        A row in this table is created automatically
        by the SNMP Agent when the Delay Measurement session is configured."

    REFERENCE
       "[MEF SOAM-PM] R7, R15, D9, D18"
    ::= { soamPmDmObjects 2 }

soamPmDmStatsEntry OBJECT-TYPE
    SYNTAX      SoamPmDmStatsEntry
    MAX-ACCESS  not-accessible
    STATUS      current
    DESCRIPTION
            "The conceptual row of soamPmDmStatsTable
"
    INDEX      { soamPmDmStatsIndex }
    ::= { soamPmDmStatsTable 1 }

SoamPmDmStatsEntry ::=
    SEQUENCE {
    soamPmDmStatsIndex                               Unsigned32,
    soamPmDmStatsLocalDeviceType                     INTEGER,
    soamPmDmStatsName                                MgmtNameString,
    soamPmDmStatsSubrack                             SubrackNumber,
    soamPmDmStatsSlot                                SlotNumber,
    soamPmDmStatsMaidIdentifier                      DisplayString,
    soamPmDmStatsDestMepId                           Dot1agCfmMepIdOrZero,
    soamPmDmStatsInternalReference                   Unsigned32,
    soamPmDmStatsMepName                             DisplayString,
    soamPmDmStatsSuspect15Min                        TruthValue,
    soamPmDmStatsSuspectPrevious15Min                TruthValue,
    soamPmDmStatsSuspect24H                          TruthValue,
    soamPmDmStatsReset15Min                          INTEGER,
    soamPmDmStatsReset24H                            INTEGER,
    soamPmDmStatsStartTime15Min                      DateAndTime,
    soamPmDmStatsElapsedTime15Min                    TimeInterval,
    soamPmDmStatsFrameDelayTwoWayMin15Min            Unsigned32WithNA,
    soamPmDmStatsFrameDelayTwoWayMax15Min            Unsigned32,
    soamPmDmStatsFrameDelayTwoWayAvg15Min            Unsigned32,
    soamPmDmStatsIfdvTwoWayMin15Min                  Unsigned32WithNA,
    soamPmDmStatsIfdvTwoWayMax15Min                  Unsigned32,
    soamPmDmStatsIfdvTwoWayAvg15Min                  Unsigned32,
    soamPmDmStatsStartTimePrevious15Min              DateAndTime,
    soamPmDmStatsElapsedTimePrevious15Min            TimeInterval,
    soamPmDmStatsFrameDelayTwoWayMinPrevious15Min    Unsigned32WithNA,
    soamPmDmStatsFrameDelayTwoWayMaxPrevious15Min    Unsigned32,
    soamPmDmStatsFrameDelayTwoWayAvgPrevious15Min    Unsigned32,
    soamPmDmStatsIfdvTwoWayMinPrevious15Min          Unsigned32WithNA,
    soamPmDmStatsIfdvTwoWayMaxPrevious15Min          Unsigned32,
    soamPmDmStatsIfdvTwoWayAvgPrevious15Min          Unsigned32,
    soamPmDmStatsStartTime24H                        DateAndTime,
    soamPmDmStatsElapsedTime24H                      TimeInterval,
    soamPmDmStatsFrameDelayTwoWayMin24H              Unsigned32WithNA,
    soamPmDmStatsFrameDelayTwoWayMax24H              Unsigned32,
    soamPmDmStatsFrameDelayTwoWayAvg24H              Unsigned32,
    soamPmDmStatsIfdvTwoWayMin24H                    Unsigned32WithNA,
    soamPmDmStatsIfdvTwoWayMax24H                    Unsigned32,
    soamPmDmStatsIfdvTwoWayAvg24H                    Unsigned32,
    soamPmDmStatsPriority                            IEEE8021PriorityValue }

soamPmDmStatsIndex OBJECT-TYPE
    SYNTAX      Unsigned32
    MAX-ACCESS  read-only
    STATUS      current
    DESCRIPTION
       "The index for the current Measurement Interval for this
        PM session.

        The index is the same as for the configuration, i.e soamPmDmCfgIndex
        and is not persistent and may be reused between restarts.

"
    ::= { soamPmDmStatsEntry 1 }

soamPmDmStatsLocalDeviceType OBJECT-TYPE
    SYNTAX      INTEGER {
                    emxp  (1),
                    nidGe (2) }
    MAX-ACCESS  read-only
    STATUS      current
    DESCRIPTION
        "The type of device the DM is created and associated.
"
    DEFVAL { emxp }
    ::= { soamPmDmStatsEntry 2 }

soamPmDmStatsName OBJECT-TYPE
    SYNTAX      MgmtNameString
    MAX-ACCESS  read-only
    STATUS      current
    DESCRIPTION
        "The name of the DM session, same as the name of remote MEP
        that this DM session is associated with.
"
    ::= { soamPmDmStatsEntry 3  }

soamPmDmStatsSubrack OBJECT-TYPE
    SYNTAX      SubrackNumber
    MAX-ACCESS  read-only
    STATUS      current
    DESCRIPTION
        "The number of the subrack where this OAM object is defined
"
    ::= { soamPmDmStatsEntry 4 }

soamPmDmStatsSlot OBJECT-TYPE
    SYNTAX      SlotNumber
    MAX-ACCESS  read-only
    STATUS      current
    DESCRIPTION
        "The slot where this OAM Object is defined.
"
    ::= { soamPmDmStatsEntry 5 }

soamPmDmStatsMaidIdentifier OBJECT-TYPE
    SYNTAX      DisplayString
    MAX-ACCESS  read-only
    STATUS      current
    DESCRIPTION
        "A unique user definied identifier for the MEG.

"
    DEFVAL { "" }
    ::= { soamPmDmStatsEntry 6 }

soamPmDmStatsDestMepId OBJECT-TYPE
    SYNTAX      Dot1agCfmMepIdOrZero
    MAX-ACCESS  read-only
    STATUS      current
    DESCRIPTION
       "The Maintenance Association End Point Identifier of
        another MEP in the same Maintenance Association to which
        the SOAM LM frame is to be sent.

        This address will be used if the value of the column
        soamPmLmDestIsMepId is 'true'. A value of zero
        means that the destination MEP ID has not been configured.

        This object is only valid for the entity transmitting the Loss
        Measurement frames, types 'lmLmm' and 'lmSlm'. It is not applicable for
        the 'lmCcm' type.

        This object can only be written at creation time and cannot be
        modified once it has been created.
"
    REFERENCE
       "[MEF SOAM-PM] R70, R104"
    DEFVAL { 0 }
    ::= { soamPmDmStatsEntry 7 }

soamPmDmStatsInternalReference OBJECT-TYPE
    SYNTAX      Unsigned32 (0..4294967295)
    MAX-ACCESS  read-only
    STATUS      current
    DESCRIPTION
        "For internal use only.
"
    DEFVAL { 0 }
    ::= { soamPmDmStatsEntry 8  }

soamPmDmStatsMepName OBJECT-TYPE
    SYNTAX      DisplayString
    MAX-ACCESS  read-only
    STATUS      current
    DESCRIPTION
        "The identifier of the MEP this DM session belongs to.
        Persistent cross-reference to MEP table.
"
    ::= { soamPmDmStatsEntry 9  }

soamPmDmStatsSuspect15Min OBJECT-TYPE
    SYNTAX      TruthValue
    MAX-ACCESS  read-only
    STATUS      current
    DESCRIPTION
       "Whether the Measurement Interval has been marked as suspect.

        The object is to be set to false at the start of a measurement
        interval. It is set to true when there is a discontinuity in the
        performance measurements during the Measurement Interval.  Conditions
        for a discontinuity include, but are not limited to the following:

        1 - The local time-of-day clock is adjusted by at least 10 seconds
        2 - The conducting of a performance measurement is halted before the
            current Measurement Interval is completed
        3 - A local test, failure, or reconfiguration that disrupts service
"
    REFERENCE
       "[MEF SOAM-PM] R39, R40, R41"
    ::= { soamPmDmStatsEntry 10 }

soamPmDmStatsSuspectPrevious15Min OBJECT-TYPE
    SYNTAX      TruthValue
    MAX-ACCESS  read-only
    STATUS      current
    DESCRIPTION
       "Whether the Measurement Interval has been marked as suspect.

        The object is to be set to false at the start of a measurement
        interval. It is set to true when there is a discontinuity in the
        performance measurements during the Measurement Interval.  Conditions
        for a discontinuity include, but are not limited to the following:

        1 - The local time-of-day clock is adjusted by at least 10 seconds
        2 - The conducting of a performance measurement is halted before the
            current Measurement Interval is completed
        3 - A local test, failure, or reconfiguration that disrupts service
"
    REFERENCE
       "[MEF SOAM-PM] R39, R40, R41"
    ::= { soamPmDmStatsEntry 11 }

soamPmDmStatsSuspect24H OBJECT-TYPE
    SYNTAX      TruthValue
    MAX-ACCESS  read-only
    STATUS      current
    DESCRIPTION
       "Whether the Measurement Interval has been marked as suspect.

        The object is to be set to false at the start of a measurement
        interval. It is set to true when there is a discontinuity in the
        performance measurements during the Measurement Interval.  Conditions
        for a discontinuity include, but are not limited to the following:

        1 - The local time-of-day clock is adjusted by at least 10 seconds
        2 - The conducting of a performance measurement is halted before the
            current Measurement Interval is completed
        3 - A local test, failure, or reconfiguration that disrupts service
"
    REFERENCE
       "[MEF SOAM-PM] R39, R40, R41"
    ::= { soamPmDmStatsEntry 12 }

soamPmDmStatsReset15Min OBJECT-TYPE
    SYNTAX      INTEGER {
                    normal (1),
                    reset (2) }
    MAX-ACCESS  read-write
    STATUS      current
    DESCRIPTION
        "Reset the 15 minute counters for the
        DM session.

        After a successful reset the default value
        (normal) is restored in this action attribute.

"
    DEFVAL { normal }
    ::= { soamPmDmStatsEntry 13 }

soamPmDmStatsReset24H OBJECT-TYPE
    SYNTAX      INTEGER {
                    normal (1),
                    reset (2) }
    MAX-ACCESS  read-write
    STATUS      current
    DESCRIPTION
        "Reset the 24 hour counters for the DM session.

        After a successful reset the default value
        (normal) is restored in this action attribute.

"
    DEFVAL { normal }
    ::= { soamPmDmStatsEntry 14 }

soamPmDmStatsStartTime15Min OBJECT-TYPE
    SYNTAX      DateAndTime
    MAX-ACCESS  read-only
    STATUS      current
    DESCRIPTION
       "The time that the current Measurement Interval started.
"
    REFERENCE
       "[MEF SOAM-PM] R22, R66, R100"
    ::= { soamPmDmStatsEntry 15 }

soamPmDmStatsElapsedTime15Min OBJECT-TYPE
    SYNTAX      TimeInterval
    MAX-ACCESS  read-only
    STATUS      current
    DESCRIPTION
       "The time that the current Measurement Interval has been running, in seconds.
"
    REFERENCE
       "[MEF SOAM-PM] R24, R66, R100"
    ::= { soamPmDmStatsEntry 16 }

soamPmDmStatsFrameDelayTwoWayMin15Min OBJECT-TYPE
    SYNTAX      Unsigned32WithNA (0..100000 | 4294967294)
    MAX-ACCESS  read-only
    STATUS      current
    DESCRIPTION
       "This object contains the minimum two-way frame delay
        calculated by this MEP for this Measurement Interval.
        This object is undefined is soamPmDmCfgType is dm1DmTx or dm1DmRx.
        Unit is micro-seconds.
"
    REFERENCE
       "[MEF SOAM-PM] R66"
    DEFVAL { 4294967294 }
    ::= { soamPmDmStatsEntry 17 }

soamPmDmStatsFrameDelayTwoWayMax15Min OBJECT-TYPE
    SYNTAX      Unsigned32
    MAX-ACCESS  read-only
    STATUS      current
    DESCRIPTION
       "This object contains the maximum two-way frame delay
        calculated by this MEP for this Measurement Interval.

        This object is undefined is soamPmDmCfgType is dm1DmTx or dm1DmRx.
        Unit is micro-seconds.
"
    REFERENCE
       "[MEF SOAM-PM] R66"
    ::= { soamPmDmStatsEntry 18 }

soamPmDmStatsFrameDelayTwoWayAvg15Min OBJECT-TYPE
    SYNTAX      Unsigned32
    MAX-ACCESS  read-only
    STATUS      current
    DESCRIPTION
       "This object contains the average two-way frame delay
        calculated by this MEP for this Measurement Interval.

        This object is undefined is soamPmDmCfgType is dm1DmTx or dm1DmRx.
        Unit is micro-seconds.
"
    REFERENCE
       "[MEF SOAM-PM] R66"
    ::= { soamPmDmStatsEntry 19 }


soamPmDmStatsIfdvTwoWayMin15Min OBJECT-TYPE
    SYNTAX      Unsigned32WithNA
    MAX-ACCESS  read-only
    STATUS      current
    DESCRIPTION
       "This object contains the minimum two-way inter-frame delay
        interval calculated by this MEP for this
        Measurement Interval.

        The value of this object is undefined when soamPmDmCfgType
        is dm1DmTx or dm1DmRx.
        Unit is micro-seconds.
"
    DEFVAL { 4294967294 }
    ::= { soamPmDmStatsEntry 20 }

soamPmDmStatsIfdvTwoWayMax15Min OBJECT-TYPE
    SYNTAX      Unsigned32
    MAX-ACCESS  read-only
    STATUS      current
    DESCRIPTION
       "This object contains the maximum two-way inter-frame delay
        interval calculated by this MEP for this
        Measurement Interval.

        The value of this object is undefined when soamPmDmCfgType
        is dm1DmTx or dm1DmRx.
        Unit is micro-seconds.
"
    ::= { soamPmDmStatsEntry 21 }

soamPmDmStatsIfdvTwoWayAvg15Min OBJECT-TYPE
    SYNTAX      Unsigned32
    MAX-ACCESS  read-only
    STATUS      current
    DESCRIPTION
       "This object contains the average two-way inter-frame delay
        interval calculated by this MEP for this
        Measurement Interval.

        The value of this object is undefined when soamPmDmCfgType
        is dm1DmTx or dm1DmRx.
        Unit is micro-seconds.
"
    ::= { soamPmDmStatsEntry 22 }


soamPmDmStatsStartTimePrevious15Min OBJECT-TYPE
    SYNTAX      DateAndTime
    MAX-ACCESS  read-only
    STATUS      current
    DESCRIPTION
       "The time that the current Measurement Interval started.
"
    REFERENCE
       "[MEF SOAM-PM] R22, R66, R100"
    ::= { soamPmDmStatsEntry 23 }

soamPmDmStatsElapsedTimePrevious15Min OBJECT-TYPE
    SYNTAX      TimeInterval
    MAX-ACCESS  read-only
    STATUS      current
    DESCRIPTION
       "The time that the current Measurement Interval has been running, in seconds.
"
    REFERENCE
       "[MEF SOAM-PM] R24, R66, R100"
    ::= { soamPmDmStatsEntry 24 }

soamPmDmStatsFrameDelayTwoWayMinPrevious15Min OBJECT-TYPE
    SYNTAX      Unsigned32WithNA
    MAX-ACCESS  read-only
    STATUS      current
    DESCRIPTION
       "This object contains the minimum two-way frame delay
        calculated by this MEP for this Measurement Interval.
        This object is undefined is soamPmDmCfgType is dm1DmTx or dm1DmRx.
        Unit is micro-seconds.
"
    REFERENCE
       "[MEF SOAM-PM] R66"
    DEFVAL { 4294967294 }
    ::= { soamPmDmStatsEntry 25 }

soamPmDmStatsFrameDelayTwoWayMaxPrevious15Min OBJECT-TYPE
    SYNTAX      Unsigned32
    MAX-ACCESS  read-only
    STATUS      current
    DESCRIPTION
       "This object contains the maximum two-way frame delay
        calculated by this MEP for this Measurement Interval.

        This object is undefined is soamPmDmCfgType is dm1DmTx or dm1DmRx.
        Unit is micro-seconds.
"
    REFERENCE
       "[MEF SOAM-PM] R66"
    ::= { soamPmDmStatsEntry 26 }

soamPmDmStatsFrameDelayTwoWayAvgPrevious15Min OBJECT-TYPE
    SYNTAX      Unsigned32
    MAX-ACCESS  read-only
    STATUS      current
    DESCRIPTION
       "This object contains the average two-way frame delay
        calculated by this MEP for this Measurement Interval.

        This object is undefined is soamPmDmCfgType is dm1DmTx or dm1DmRx.
        Unit is micro-seconds.
"
    REFERENCE
       "[MEF SOAM-PM] R66"
    ::= { soamPmDmStatsEntry 27 }


soamPmDmStatsIfdvTwoWayMinPrevious15Min OBJECT-TYPE
    SYNTAX      Unsigned32WithNA
    MAX-ACCESS  read-only
    STATUS      current
    DESCRIPTION
       "This object contains the minimum two-way inter-frame delay
        interval calculated by this MEP for this
        Measurement Interval.

        The value of this object is undefined when soamPmDmCfgType
        is dm1DmTx or dm1DmRx.
        Unit is micro-seconds.
"
    DEFVAL { 4294967294 }
    ::= { soamPmDmStatsEntry 28 }

soamPmDmStatsIfdvTwoWayMaxPrevious15Min OBJECT-TYPE
    SYNTAX      Unsigned32
    MAX-ACCESS  read-only
    STATUS      current
    DESCRIPTION
       "This object contains the maximum two-way inter-frame delay
        interval calculated by this MEP for this
        Measurement Interval.

        The value of this object is undefined when soamPmDmCfgType
        is dm1DmTx or dm1DmRx.
        Unit is micro-seconds.
"
    ::= { soamPmDmStatsEntry 29 }

soamPmDmStatsIfdvTwoWayAvgPrevious15Min OBJECT-TYPE
    SYNTAX      Unsigned32
    MAX-ACCESS  read-only
    STATUS      current
    DESCRIPTION
       "This object contains the average two-way inter-frame delay
        interval calculated by this MEP for this
        Measurement Interval.

        The value of this object is undefined when soamPmDmCfgType
        is dm1DmTx or dm1DmRx.
        Unit is micro-seconds.
"
    ::= { soamPmDmStatsEntry 30 }

soamPmDmStatsStartTime24H OBJECT-TYPE
    SYNTAX      DateAndTime
    MAX-ACCESS  read-only
    STATUS      current
    DESCRIPTION
       "The time that the current Measurement Interval started.
"
    REFERENCE
       "[MEF SOAM-PM] R22, R66, R100"
    ::= { soamPmDmStatsEntry 31 }

soamPmDmStatsElapsedTime24H OBJECT-TYPE
    SYNTAX      TimeInterval
    MAX-ACCESS  read-only
    STATUS      current
    DESCRIPTION
       "The time that the current Measurement Interval has been running, in seconds.
"
    REFERENCE
       "[MEF SOAM-PM] R24, R66, R100"
    ::= { soamPmDmStatsEntry 32 }

soamPmDmStatsFrameDelayTwoWayMin24H OBJECT-TYPE
    SYNTAX      Unsigned32WithNA
    MAX-ACCESS  read-only
    STATUS      current
    DESCRIPTION
       "This object contains the minimum two-way frame delay
        calculated by this MEP for this Measurement Interval.
        This object is undefined is soamPmDmCfgType is dm1DmTx or dm1DmRx.
        Unit is micro-seconds.
"
    REFERENCE
       "[MEF SOAM-PM] R66"
    DEFVAL { 4294967294 }
    ::= { soamPmDmStatsEntry 33 }

soamPmDmStatsFrameDelayTwoWayMax24H OBJECT-TYPE
    SYNTAX      Unsigned32
    MAX-ACCESS  read-only
    STATUS      current
    DESCRIPTION
       "This object contains the maximum two-way frame delay
        calculated by this MEP for this Measurement Interval.

        This object is undefined is soamPmDmCfgType is dm1DmTx or dm1DmRx.
        Unit is micro-seconds.
"
    REFERENCE
       "[MEF SOAM-PM] R66"
    ::= { soamPmDmStatsEntry 34 }

soamPmDmStatsFrameDelayTwoWayAvg24H OBJECT-TYPE
    SYNTAX      Unsigned32
    MAX-ACCESS  read-only
    STATUS      current
    DESCRIPTION
       "This object contains the average two-way frame delay
        calculated by this MEP for this Measurement Interval.

        This object is undefined is soamPmDmCfgType is dm1DmTx or dm1DmRx.
        Unit is micro-seconds.
"
    REFERENCE
       "[MEF SOAM-PM] R66"
    ::= { soamPmDmStatsEntry 35 }


soamPmDmStatsIfdvTwoWayMin24H OBJECT-TYPE
    SYNTAX      Unsigned32WithNA
    MAX-ACCESS  read-only
    STATUS      current
    DESCRIPTION
       "This object contains the minimum two-way inter-frame delay
        interval calculated by this MEP for this
        Measurement Interval.

        The value of this object is undefined when soamPmDmCfgType
        is dm1DmTx or dm1DmRx.
        Unit is micro-seconds.
"
    DEFVAL { 4294967294 }
    ::= { soamPmDmStatsEntry 36 }

soamPmDmStatsIfdvTwoWayMax24H OBJECT-TYPE
    SYNTAX      Unsigned32
    MAX-ACCESS  read-only
    STATUS      current
    DESCRIPTION
       "This object contains the maximum two-way inter-frame delay
        interval calculated by this MEP for this
        Measurement Interval.

        The value of this object is undefined when soamPmDmCfgType
        is dm1DmTx or dm1DmRx.
        Unit is micro-seconds.
"
    ::= { soamPmDmStatsEntry 37 }

soamPmDmStatsIfdvTwoWayAvg24H OBJECT-TYPE
    SYNTAX      Unsigned32
    MAX-ACCESS  read-only
    STATUS      current
    DESCRIPTION
       "This object contains the average two-way inter-frame delay
        interval calculated by this MEP for this
        Measurement Interval.

        The value of this object is undefined when soamPmDmCfgType
        is dm1DmTx or dm1DmRx.
        Unit is micro-seconds.
"
    ::= { soamPmDmStatsEntry 38 }

soamPmDmStatsPriority OBJECT-TYPE
    SYNTAX      IEEE8021PriorityValue
    MAX-ACCESS  read-only
    STATUS      current
    DESCRIPTION
       "This object specifies the priority of frames with
        Delay Measurement OAM message information.

        The default value is to be the value which yields the lowest frame
        loss.

        This object can only be written at creation time and cannot be
        modified once it has been created.
"
    REFERENCE
       "[MEF SOAM-PM] R1, R2, R56, D21, R57, R58, R90-R94, D28;
        [MEF 10.2.1] Section 6.8"
    DEFVAL { 0 }
    ::= { soamPmDmStatsEntry 39 }



 -- ******************************************************************
 -- SOAM-PM MIB Units of conformance
 -- ******************************************************************
soamPmGeneralGroupV1 OBJECT-GROUP
    OBJECTS {
        soamPmGeneralLastChangeTime,
        soamPmGeneralLmStateLastChangeTime,
        soamPmGeneralLmObjectsTableSize,
        soamPmGeneralDmObjectsTableSize }
    STATUS  current
    DESCRIPTION
        "General objects for the MEF service OAM group (R22.0)."
    ::= { lumSoamPmGroups 1 }

soamPmLmCfgGroupV1 OBJECT-GROUP
    OBJECTS {
        soamPmLmCfgIndex,
        soamPmLmCfgName,
        soamPmLmCfgDescr,
        soamPmLmCfgSubrack,
        soamPmLmCfgSlot,
        soamPmLmCfgInternalReference,
        soamPmLmCfgLocalDeviceType,
        soamPmLmCfgType,
        soamPmLmCfgEnabled,
        soamPmLmCfgMessagePeriod,
        soamPmLmCfgPriority,
        soamPmLmCfgDestMacAddress,
        soamPmLmCfgMepName,
        soamPmLmCfgMaidIdentifier,
        soamPmLmCfgDestMepId,
        soamPmLmCfgDestIsMepId,
        soamPmLmCfgAvailabilityFlrThreshold,
        soamPmLmCfgAvailabilityUasAlarmThreshold,
        soamPmLmCfgSessionType,
        soamPmLmCfgSessionStatus }
    STATUS      current
    DESCRIPTION
       "Objects for the MEF Service OAM LM Configuration group (R22.0)."
    ::= { lumSoamPmGroups 2 }

soamPmLmStatsGroupV1 OBJECT-GROUP
    OBJECTS {
        soamPmLmStatsIndex,
        soamPmLmStatsLocalDeviceType,
        soamPmLmStatsName,
        soamPmLmStatsSubrack,
        soamPmLmStatsSlot,
        soamPmLmStatsDestMepId,
        soamPmLmStatsMaidIdentifier,
        soamPmLmStatsInternalReference,
        soamPmLmStatsMepName,

        soamPmLmStatsSuspect15Min,
        soamPmLmStatsSuspectPrevious15Min,
        soamPmLmStatsSuspect24H,

        soamPmLmStatsReset15Min,
        soamPmLmStatsReset24H,

        soamPmLmStatsStartTime15Min,
        soamPmLmStatsElapsedTime15Min,
        soamPmLmStatsForwardTransmittedFrames15Min,
        soamPmLmStatsForwardReceivedFrames15Min,
        soamPmLmStatsForwardMinFlr15Min,
        soamPmLmStatsForwardMaxFlr15Min,
        soamPmLmStatsForwardAvgFlr15Min,
        soamPmLmStatsForwardHighLoss15Min,
        soamPmLmStatsBackwardTransmittedFrames15Min,
        soamPmLmStatsBackwardReceivedFrames15Min,
        soamPmLmStatsBackwardMinFlr15Min,
        soamPmLmStatsBackwardMaxFlr15Min,
        soamPmLmStatsBackwardAvgFlr15Min,
        soamPmLmStatsBackwardHighLoss15Min,
        soamPmLmStatsUnavailableSeconds15Min,

        soamPmLmStatsStartTimePrevious15Min,
        soamPmLmStatsElapsedTimePrevious15Min,
        soamPmLmStatsForwardTransmittedFramesPrevious15Min,
        soamPmLmStatsForwardReceivedFramesPrevious15Min,
        soamPmLmStatsForwardMinFlrPrevious15Min,
        soamPmLmStatsForwardMaxFlrPrevious15Min,
        soamPmLmStatsForwardAvgFlrPrevious15Min,
        soamPmLmStatsForwardHighLossPrevious15Min,
        soamPmLmStatsBackwardTransmittedFramesPrevious15Min,
        soamPmLmStatsBackwardReceivedFramesPrevious15Min,
        soamPmLmStatsBackwardMinFlrPrevious15Min,
        soamPmLmStatsBackwardMaxFlrPrevious15Min,
        soamPmLmStatsBackwardAvgFlrPrevious15Min,
        soamPmLmStatsBackwardHighLossPrevious15Min,

        soamPmLmStatsStartTime24H,
        soamPmLmStatsElapsedTime24H,
        soamPmLmStatsForwardTransmittedFrames24H,
        soamPmLmStatsForwardReceivedFrames24H,
        soamPmLmStatsForwardMinFlr24H,
        soamPmLmStatsForwardMaxFlr24H,
        soamPmLmStatsForwardAvgFlr24H,
        soamPmLmStatsForwardHighLoss24H,
        soamPmLmStatsBackwardTransmittedFrames24H,
        soamPmLmStatsBackwardReceivedFrames24H,
        soamPmLmStatsBackwardMinFlr24H,
        soamPmLmStatsBackwardMaxFlr24H,
        soamPmLmStatsBackwardAvgFlr24H,
        soamPmLmStatsBackwardHighLoss24H,
        soamPmLmStatsUas }

    STATUS      current
    DESCRIPTION
       "Objects for the MEF Service OAM LM current statistics group (R22.0)."
    ::= { lumSoamPmGroups 3 }

soamPmDmCfgGroupV1 OBJECT-GROUP
    OBJECTS {
        soamPmDmCfgIndex,
        soamPmDmCfgName,
        soamPmDmCfgDescr,
        soamPmDmCfgSubrack,
        soamPmDmCfgSlot,
        soamPmDmCfgInternalReference,
        soamPmDmCfgLocalDeviceType,
        soamPmDmCfgDropEligible,
        soamPmDmCfgType,
        soamPmDmCfgEnabled,
        soamPmDmCfgMessagePeriod,
        soamPmDmCfgPriority,
        soamPmDmCfgDestMacAddress,
        soamPmDmCfgMepName,
        soamPmDmCfgMaidIdentifier,
        soamPmDmCfgDestMepId,
        soamPmDmCfgDestIsMepId,
        soamPmDmCfgSessionType,
        soamPmDmCfgSessionStatus }
    STATUS      current
    DESCRIPTION
       "Objects for the Service OAM DM configuration group (R22.0)."
    ::= { lumSoamPmGroups 4 }

soamPmDmStatsGroupV1 OBJECT-GROUP
    OBJECTS {
        soamPmDmStatsIndex,
        soamPmDmStatsLocalDeviceType,
        soamPmDmStatsName,
        soamPmDmStatsSubrack,
        soamPmDmStatsSlot,
        soamPmDmStatsDestMepId,
        soamPmDmStatsMaidIdentifier,
        soamPmDmStatsInternalReference,
        soamPmDmStatsMepName,

        soamPmDmStatsSuspect15Min,
        soamPmDmStatsSuspectPrevious15Min,
        soamPmDmStatsSuspect24H,

        soamPmDmStatsReset15Min,
        soamPmDmStatsReset24H,

        soamPmDmStatsStartTime15Min,
        soamPmDmStatsElapsedTime15Min,
        soamPmDmStatsFrameDelayTwoWayMin15Min,
        soamPmDmStatsFrameDelayTwoWayMax15Min,
        soamPmDmStatsFrameDelayTwoWayAvg15Min,

        soamPmDmStatsIfdvTwoWayMin15Min,
        soamPmDmStatsIfdvTwoWayMax15Min,
        soamPmDmStatsIfdvTwoWayAvg15Min,

        soamPmDmStatsStartTimePrevious15Min,
        soamPmDmStatsElapsedTimePrevious15Min,
        soamPmDmStatsFrameDelayTwoWayMinPrevious15Min,
        soamPmDmStatsFrameDelayTwoWayMaxPrevious15Min,
        soamPmDmStatsFrameDelayTwoWayAvgPrevious15Min,
        soamPmDmStatsIfdvTwoWayMinPrevious15Min,
        soamPmDmStatsIfdvTwoWayMaxPrevious15Min,
        soamPmDmStatsIfdvTwoWayAvgPrevious15Min,

        soamPmDmStatsStartTime24H,
        soamPmDmStatsElapsedTime24H,
        soamPmDmStatsFrameDelayTwoWayMin24H,
        soamPmDmStatsFrameDelayTwoWayMax24H,
        soamPmDmStatsFrameDelayTwoWayAvg24H,
        soamPmDmStatsIfdvTwoWayMin24H,
        soamPmDmStatsIfdvTwoWayMax24H,
        soamPmDmStatsIfdvTwoWayAvg24H }

    STATUS      current
    DESCRIPTION
       "Objects for the Service OAM DM current statistics group (R22.0)."
    ::= { lumSoamPmGroups 5 }


soamPmLmCfgGroupV2 OBJECT-GROUP
    OBJECTS {
        soamPmLmCfgIndex,
        soamPmLmCfgName,
        soamPmLmCfgDescr,
        soamPmLmCfgSubrack,
        soamPmLmCfgSlot,
        soamPmLmCfgInternalReference,
        soamPmLmCfgLocalDeviceType,
        soamPmLmCfgType,
        soamPmLmCfgEnabled,
        soamPmLmCfgMessagePeriod,
        soamPmLmCfgPriority,
        soamPmLmCfgDestMacAddress,
        soamPmLmCfgMepName,
        soamPmLmCfgMaidIdentifier,
        soamPmLmCfgDestMepId,
        soamPmLmCfgDestIsMepId,
        soamPmLmCfgAvailabilityFlrThreshold,
        soamPmLmCfgAvailabilityUasAlarmThreshold,
        soamPmLmCfgSessionType,
        soamPmLmCfgSessionStatus,
        soamPmLmCfgCosAwareness,
        soamPmLmCfgRowStatus,
        soamPmLmCfgAdminStatus,
        soamPmLmCfgOperStatus }
    STATUS      current
    DESCRIPTION
       "Objects for the MEF Service OAM LM Configuration group (R23.0)."
    ::= { lumSoamPmGroups 6 }

soamPmDmCfgGroupV2 OBJECT-GROUP
    OBJECTS {
        soamPmDmCfgIndex,
        soamPmDmCfgName,
        soamPmDmCfgDescr,
        soamPmDmCfgSubrack,
        soamPmDmCfgSlot,
        soamPmDmCfgInternalReference,
        soamPmDmCfgLocalDeviceType,
        soamPmDmCfgDropEligible,
        soamPmDmCfgType,
        soamPmDmCfgEnabled,
        soamPmDmCfgMessagePeriod,
        soamPmDmCfgPriority,
        soamPmDmCfgDestMacAddress,
        soamPmDmCfgMepName,
        soamPmDmCfgMaidIdentifier,
        soamPmDmCfgDestMepId,
        soamPmDmCfgDestIsMepId,
        soamPmDmCfgSessionType,
        soamPmDmCfgSessionStatus,
        soamPmDmCfgRowStatus,
        soamPmDmCfgAdminStatus,
        soamPmDmCfgOperStatus }
    STATUS      current
    DESCRIPTION
       "Objects for the Service OAM DM configuration group (R23.0)."
    ::= { lumSoamPmGroups 7 }

soamPmLmStatsGroupV2 OBJECT-GROUP
    OBJECTS {
        soamPmLmStatsIndex,
        soamPmLmStatsLocalDeviceType,
        soamPmLmStatsName,
        soamPmLmStatsSubrack,
        soamPmLmStatsSlot,
        soamPmLmStatsDestMepId,
        soamPmLmStatsMaidIdentifier,
        soamPmLmStatsInternalReference,
        soamPmLmStatsMepName,

        soamPmLmStatsSuspect15Min,
        soamPmLmStatsSuspectPrevious15Min,
        soamPmLmStatsSuspect24H,

        soamPmLmStatsReset15Min,
        soamPmLmStatsReset24H,

        soamPmLmStatsStartTime15Min,
        soamPmLmStatsElapsedTime15Min,
        soamPmLmStatsForwardTransmittedFrames15Min,
        soamPmLmStatsForwardReceivedFrames15Min,
        soamPmLmStatsForwardMinFlr15Min,
        soamPmLmStatsForwardMaxFlr15Min,
        soamPmLmStatsForwardAvgFlr15Min,
        soamPmLmStatsForwardHighLoss15Min,
        soamPmLmStatsBackwardTransmittedFrames15Min,
        soamPmLmStatsBackwardReceivedFrames15Min,
        soamPmLmStatsBackwardMinFlr15Min,
        soamPmLmStatsBackwardMaxFlr15Min,
        soamPmLmStatsBackwardAvgFlr15Min,
        soamPmLmStatsBackwardHighLoss15Min,
        soamPmLmStatsUnavailableSeconds15Min,

        soamPmLmStatsStartTimePrevious15Min,
        soamPmLmStatsElapsedTimePrevious15Min,
        soamPmLmStatsForwardTransmittedFramesPrevious15Min,
        soamPmLmStatsForwardReceivedFramesPrevious15Min,
        soamPmLmStatsForwardMinFlrPrevious15Min,
        soamPmLmStatsForwardMaxFlrPrevious15Min,
        soamPmLmStatsForwardAvgFlrPrevious15Min,
        soamPmLmStatsForwardHighLossPrevious15Min,
        soamPmLmStatsBackwardTransmittedFramesPrevious15Min,
        soamPmLmStatsBackwardReceivedFramesPrevious15Min,
        soamPmLmStatsBackwardMinFlrPrevious15Min,
        soamPmLmStatsBackwardMaxFlrPrevious15Min,
        soamPmLmStatsBackwardAvgFlrPrevious15Min,
        soamPmLmStatsBackwardHighLossPrevious15Min,

        soamPmLmStatsStartTime24H,
        soamPmLmStatsElapsedTime24H,
        soamPmLmStatsForwardTransmittedFrames24H,
        soamPmLmStatsForwardReceivedFrames24H,
        soamPmLmStatsForwardMinFlr24H,
        soamPmLmStatsForwardMaxFlr24H,
        soamPmLmStatsForwardAvgFlr24H,
        soamPmLmStatsForwardHighLoss24H,
        soamPmLmStatsBackwardTransmittedFrames24H,
        soamPmLmStatsBackwardReceivedFrames24H,
        soamPmLmStatsBackwardMinFlr24H,
        soamPmLmStatsBackwardMaxFlr24H,
        soamPmLmStatsBackwardAvgFlr24H,
        soamPmLmStatsBackwardHighLoss24H,
        soamPmLmStatsUas,
        soamPmLmStatsPriority }

    STATUS      current
    DESCRIPTION
       "Objects for the MEF Service OAM LM current statistics group (R23.0)."
    ::= { lumSoamPmGroups 8 }

soamPmDmStatsGroupV2 OBJECT-GROUP
    OBJECTS {
        soamPmDmStatsIndex,
        soamPmDmStatsLocalDeviceType,
        soamPmDmStatsName,
        soamPmDmStatsSubrack,
        soamPmDmStatsSlot,
        soamPmDmStatsDestMepId,
        soamPmDmStatsMaidIdentifier,
        soamPmDmStatsInternalReference,
        soamPmDmStatsMepName,

        soamPmDmStatsSuspect15Min,
        soamPmDmStatsSuspectPrevious15Min,
        soamPmDmStatsSuspect24H,

        soamPmDmStatsReset15Min,
        soamPmDmStatsReset24H,

        soamPmDmStatsStartTime15Min,
        soamPmDmStatsElapsedTime15Min,
        soamPmDmStatsFrameDelayTwoWayMin15Min,
        soamPmDmStatsFrameDelayTwoWayMax15Min,
        soamPmDmStatsFrameDelayTwoWayAvg15Min,

        soamPmDmStatsIfdvTwoWayMin15Min,
        soamPmDmStatsIfdvTwoWayMax15Min,
        soamPmDmStatsIfdvTwoWayAvg15Min,

        soamPmDmStatsStartTimePrevious15Min,
        soamPmDmStatsElapsedTimePrevious15Min,
        soamPmDmStatsFrameDelayTwoWayMinPrevious15Min,
        soamPmDmStatsFrameDelayTwoWayMaxPrevious15Min,
        soamPmDmStatsFrameDelayTwoWayAvgPrevious15Min,
        soamPmDmStatsIfdvTwoWayMinPrevious15Min,
        soamPmDmStatsIfdvTwoWayMaxPrevious15Min,
        soamPmDmStatsIfdvTwoWayAvgPrevious15Min,

        soamPmDmStatsStartTime24H,
        soamPmDmStatsElapsedTime24H,
        soamPmDmStatsFrameDelayTwoWayMin24H,
        soamPmDmStatsFrameDelayTwoWayMax24H,
        soamPmDmStatsFrameDelayTwoWayAvg24H,
        soamPmDmStatsIfdvTwoWayMin24H,
        soamPmDmStatsIfdvTwoWayMax24H,
        soamPmDmStatsIfdvTwoWayAvg24H,
        soamPmDmStatsPriority }

    STATUS      current
    DESCRIPTION
       "Objects for the Service OAM DM current statistics group (R23.0)."
    ::= { lumSoamPmGroups 9 }

soamPmLmCfgGroupV3 OBJECT-GROUP
    OBJECTS {
        soamPmLmCfgIndex,
        soamPmLmCfgName,
        soamPmLmCfgDescr,
        soamPmLmCfgSubrack,
        soamPmLmCfgSlot,
        soamPmLmCfgInternalReference,
        soamPmLmCfgLocalDeviceType,
        soamPmLmCfgType,
        soamPmLmCfgEnabled,
        soamPmLmCfgMessagePeriod,
        soamPmLmCfgPriority,
        soamPmLmCfgDestMacAddress,
        soamPmLmCfgMepName,
        soamPmLmCfgMaidIdentifier,
        soamPmLmCfgDestMepId,
        soamPmLmCfgDestIsMepId,
        soamPmLmCfgAvailabilityFlrThreshold,
        soamPmLmCfgAvailabilityUasAlarmThreshold,
        soamPmLmCfgSessionType,
        soamPmLmCfgSessionStatus,
        soamPmLmCfgCosAwareness,
        soamPmLmCfgRowStatus,
        soamPmLmCfgAdminStatus,
        soamPmLmCfgOperStatus,
        soamPmLmCfgStats}
    STATUS      current
    DESCRIPTION
       "Objects for the MEF Service OAM LM Configuration group (R25.0)."
    ::= { lumSoamPmGroups 10 }

soamPmDmCfgGroupV3 OBJECT-GROUP
    OBJECTS {
        soamPmDmCfgIndex,
        soamPmDmCfgName,
        soamPmDmCfgDescr,
        soamPmDmCfgSubrack,
        soamPmDmCfgSlot,
        soamPmDmCfgInternalReference,
        soamPmDmCfgLocalDeviceType,
        soamPmDmCfgDropEligible,
        soamPmDmCfgType,
        soamPmDmCfgEnabled,
        soamPmDmCfgMessagePeriod,
        soamPmDmCfgPriority,
        soamPmDmCfgDestMacAddress,
        soamPmDmCfgMepName,
        soamPmDmCfgMaidIdentifier,
        soamPmDmCfgDestMepId,
        soamPmDmCfgDestIsMepId,
        soamPmDmCfgSessionType,
        soamPmDmCfgSessionStatus,
        soamPmDmCfgRowStatus,
        soamPmDmCfgAdminStatus,
        soamPmDmCfgOperStatus,
        soamPmDmCfgStats }
    STATUS      current
    DESCRIPTION
       "Objects for the Service OAM DM configuration group (R25.0)."
    ::= { lumSoamPmGroups 11 }

 -- ******************************************************************
 -- SOAM-PM MIB Module Compliance statements
 -- ******************************************************************

soamPmBasicComplV1 MODULE-COMPLIANCE
    STATUS       current
    DESCRIPTION
        "The compliance statement for the MEF Service OAM PM MIB. (R22.0)"
    MODULE
        MANDATORY-GROUPS {
            soamPmGeneralGroupV1,
            soamPmLmCfgGroupV1,
            soamPmLmStatsGroupV1,
            soamPmDmCfgGroupV1,
            soamPmDmStatsGroupV1 }
    ::= { lumSoamPmCompliances 1 }


soamPmBasicComplV2 MODULE-COMPLIANCE
    STATUS       current
    DESCRIPTION
        "The compliance statement for the MEF Service OAM PM MIB. (R23.0)"
    MODULE
        MANDATORY-GROUPS {
            soamPmGeneralGroupV1,
            soamPmLmCfgGroupV2,
            soamPmLmStatsGroupV2,
            soamPmDmCfgGroupV2,
            soamPmDmStatsGroupV2 }
    ::= { lumSoamPmCompliances 2 }

soamPmBasicComplV3 MODULE-COMPLIANCE
    STATUS       current
    DESCRIPTION
        "The compliance statement for the MEF Service OAM PM MIB. (R25.0)"
    MODULE
        MANDATORY-GROUPS {
            soamPmGeneralGroupV1,
            soamPmLmCfgGroupV3,
            soamPmLmStatsGroupV2,
            soamPmDmCfgGroupV3,
            soamPmDmStatsGroupV2 }
    ::= { lumSoamPmCompliances 3 }

END
