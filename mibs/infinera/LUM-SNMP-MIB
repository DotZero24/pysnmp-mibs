LUM-SNMP-MIB DEFINITIONS ::= BEGIN

IMPORTS
    MODULE-IDENTITY, OBJECT-TYPE, Unsigned32, IpAddress
        FROM SNMPv2-SMI
    OBJECT-GROUP, MODULE-COMPLIANCE
        FROM SNMPv2-CONF
    SnmpEngineID
        FROM SNMP-FRAMEWORK-MIB
    RowStatus, DisplayString, DateAndTime, StorageType
        FROM SNMPv2-TC
    lumModules, lumSnmpMIB
        FROM LUM-REG
    CommandString
        FROM LUM-TC;

lumSnmpMIBModule MODULE-IDENTITY
    LAST-UPDATED
        "201804130000Z" -- April 13th 2018
    ORGANIZATION
        "Infinera Corporation"
    CONTACT-INFO
        "techsupport@infinera.com"
    DESCRIPTION
        "The SNMP MIB.

        - General

        - Inform sink list (trap receivers)

        - USM user definitions

"
    REVISION
        "201804130000Z" -- April 13th 2018
    DESCRIPTION
        "Changes made for release r30.1:
         - Added privacy settings."
    REVISION
        "201706150000Z" -- June 15th 2017
    DESCRIPTION
        "Changes made for release r29.0:
         - Changed ORGANIZATION and CONTACT-INFO"
    REVISION
        "201412090000Z" -- June 5th 2008
    DESCRIPTION
        "MIB II added"
    REVISION
        "200806050000Z" -- June 5th 2008
    DESCRIPTION
        "Traps off by default."
    REVISION
        "200410010000Z" -- October 1st 2004
    DESCRIPTION
        "Added table size variables."
    REVISION
        "200406230000Z" -- July 23d 2004
    DESCRIPTION
        "Added possibility to set storagetype on informSink rows
        and added trap filtering for informSinks."
    REVISION
        "200309300000Z" -- September 30th 2003
    DESCRIPTION
        "Updated compliance to indicate new functionality;
        it is now possible to create informSink rows."
    REVISION
        "200205300000Z" -- May 30th 2002
    DESCRIPTION
        "The initial revision of this module."
    ::= { lumModules 18 }


-- ----------------------------------------------------
-- Conformance area, containing groups and complicance
-- specifications.
-- ----------------------------------------------------

lumSnmpConfs OBJECT IDENTIFIER ::= { lumSnmpMIB 1 }
lumSnmpGroups OBJECT IDENTIFIER ::= { lumSnmpConfs 1 }
lumSnmpCompl OBJECT IDENTIFIER ::= { lumSnmpConfs 2 }


-- ----------------------------------------------------
-- Root for objects in the snmp MIB
-- ----------------------------------------------------

lumSnmpMIBObjects OBJECT IDENTIFIER ::= { lumSnmpMIB 2 }


-- ----------------------------------------------------
-- This MIB contains the following groups:
-- ----------------------------------------------------

snmpInformSinkList OBJECT IDENTIFIER ::= { lumSnmpMIBObjects 1 }
snmpGeneral OBJECT IDENTIFIER ::= { lumSnmpMIBObjects 2 }
snmpUserList OBJECT IDENTIFIER ::= { lumSnmpMIBObjects 3 }


-- ----------------------------------------------------
-- Textual Conventions
-- ----------------------------------------------------

-- n/a


-- ----------------------------------------------------
-- Informsink group
-- ----------------------------------------------------

snmpInformSinkTable  OBJECT-TYPE
    SYNTAX      SEQUENCE OF SnmpInformSinkEntry
    MAX-ACCESS  not-accessible
    STATUS      current
    DESCRIPTION
        "The notification (trap) receiver configuration
        directives list."
    ::= { snmpInformSinkList 1 }

snmpInformSinkEntry OBJECT-TYPE
    SYNTAX      SnmpInformSinkEntry
    MAX-ACCESS  not-accessible
    STATUS      current
    DESCRIPTION
        "An entry in the notification (trap) receiver
        list. Typically there should be one row
        for each management system.

        Only SNMPv2c trap receivers are supported.

        Create:

        <address>[:<port>[:storage[:<community>[:<alarms>:<pm>:<other>]]]]

        Default values: port is set to 162, community
        to 'public', storage to other(1) (meaning
        configuration file), alarms, pm and other
        to 'on'.

        Storagetype can also be set to volatile(2).
        Such entries will not be saved.

"
    INDEX { snmpInformSinkIndex }
    ::= { snmpInformSinkTable 1 }

SnmpInformSinkEntry ::=
    SEQUENCE {
        snmpInformSinkIndex                     Unsigned32,
        snmpInformSinkName                      DisplayString,
        snmpInformSinkAddr                      IpAddress,
        snmpInformSinkPort                      Unsigned32,
        snmpInformSinkCommunity                 DisplayString,
        snmpInformSinkRowStatus                 RowStatus,
        snmpInformSinkStorageType               StorageType,
        snmpInformSinkAlarmNotifications        INTEGER,
        snmpInformSinkPerformanceNotifications  INTEGER,
        snmpInformSinkOtherNotifications        INTEGER,
        snmpInformSinkMib2Notifications         INTEGER
    }

snmpInformSinkIndex OBJECT-TYPE
    SYNTAX      Unsigned32 (1..2147483647)
    MAX-ACCESS  read-only
    STATUS      current
    DESCRIPTION
        "An arbitrary index assigned to each entry.

"
    ::= { snmpInformSinkEntry 1 }

snmpInformSinkName OBJECT-TYPE
    SYNTAX      DisplayString (SIZE (0..255))
    MAX-ACCESS  read-only
    STATUS      current
    DESCRIPTION
        "Name assigned to each entry.

"
    ::= { snmpInformSinkEntry 2 }

snmpInformSinkAddr OBJECT-TYPE
    SYNTAX      IpAddress
    MAX-ACCESS  read-create
    STATUS      current
    DESCRIPTION
        "The IP address for the notification (trap)
        recevier.

        This attribute can be written via SNMP.
"
    ::= { snmpInformSinkEntry 3 }

snmpInformSinkPort OBJECT-TYPE
    SYNTAX      Unsigned32 (0..65535)
    MAX-ACCESS  read-create
    STATUS      current
    DESCRIPTION
        "The port number for the notification (trap)
        receiver.

        This attribute can be written via SNMP.
"
    DEFVAL { 162 }
    ::= { snmpInformSinkEntry 4 }

snmpInformSinkCommunity OBJECT-TYPE
    SYNTAX      DisplayString (SIZE (0..255))
    MAX-ACCESS  read-write
    STATUS      current
    DESCRIPTION
        "The community string included in the
        notification (trap).
        Only SNMPv2c notifications (traps) are supported.

        This attribute can be written via SNMP.
"
    DEFVAL { "public" }
    ::= { snmpInformSinkEntry 5 }

snmpInformSinkRowStatus OBJECT-TYPE
    SYNTAX      RowStatus
    MAX-ACCESS  read-create
    STATUS      current
    DESCRIPTION
        "Manages creation and deletion of conceptual rows.
        See also SNMPv2-TC.

        This attribute can be written via SNMP.

        Note: The newly created object will not necessarily
        receive the same index as used in the create
        procedure.
"
    ::= { snmpInformSinkEntry 6 }

snmpInformSinkStorageType OBJECT-TYPE
    SYNTAX      StorageType
    MAX-ACCESS  read-create
    STATUS      current
    DESCRIPTION
        "Sets the storage type for the row.
        See also SNMPv2-TC.

        other(1) - Saved in configuration file.

        volatile(2) - Not saved.

        nonVolatile(3) - Not used

        permanent(4) - Not used.

        readOnly(5) - Not used.

        This attribute can be written via SNMP.

        Note: The newly created object will not necessarily
        receive the same index as used in the create
        procedure.
"
    ::= { snmpInformSinkEntry 7 }

snmpInformSinkAlarmNotifications OBJECT-TYPE
    SYNTAX      INTEGER {
                    off (1),
                    on (2) }
    MAX-ACCESS  read-write
    STATUS      current
    DESCRIPTION
        "The mode for alarm notifications
        (traps) for the receiver.

        off - Alarms traps are inactive.

        on - Alarm traps are activated.

"
    DEFVAL { on }
    ::= { snmpInformSinkEntry  8 }

snmpInformSinkPerformanceNotifications OBJECT-TYPE
    SYNTAX      INTEGER {
                    off (1),
                    on (2) }
    MAX-ACCESS  read-write
    STATUS      current
    DESCRIPTION
        "The mode for performance measurement
        notifications (traps) for the receiver.

        off - PM traps are inactive.

        on - PM traps are activated.

"
    DEFVAL { off }
    ::= { snmpInformSinkEntry  9 }

snmpInformSinkOtherNotifications OBJECT-TYPE
    SYNTAX      INTEGER {
                    off (1),
                    on (2) }
    MAX-ACCESS  read-write
    STATUS      current
    DESCRIPTION
        "The mode for other notifications (traps)
        (not alarm or performance measurement related)
        for the receiver.

        off - Other traps are inactive.

        on - Other traps are activated.

"
    DEFVAL { off }
    ::= { snmpInformSinkEntry 10 }


snmpInformSinkMib2Notifications OBJECT-TYPE
    SYNTAX      INTEGER {
                    off (1),
                    on (2) }
    MAX-ACCESS  read-write
    STATUS      current
    DESCRIPTION
        "The mode to receive MIB II notifications

        off - MIB II traps are inactive.

        on - MIB II traps are activated.

"
    DEFVAL { off }
    ::= { snmpInformSinkEntry 11 }


-- ----------------------------------------------------
-- General group
-- ----------------------------------------------------

snmpGeneralLastChangeTime OBJECT-TYPE
    SYNTAX      DateAndTime
    MAX-ACCESS  read-only
    STATUS      current
    DESCRIPTION
        "The time when the state of the MIB was last
        changed.
"
    ::= { snmpGeneral 1 }

snmpGeneralConfigLastChangeTime OBJECT-TYPE
    SYNTAX      DateAndTime
    MAX-ACCESS  read-only
    STATUS      current
    DESCRIPTION
        "The time when the configuration of the MIB was
        last changed.

"
    ::= { snmpGeneral 2 }

snmpGeneralEngineID OBJECT-TYPE
    SYNTAX SnmpEngineID
    MAX-ACCESS  read-only
    STATUS      current
    DESCRIPTION
        "The engine id for the SNMP agent.

"
    ::= { snmpGeneral 3 }

snmpGeneralCommunity OBJECT-TYPE
    SYNTAX DisplayString (SIZE (0..33))
    MAX-ACCESS  read-write
    STATUS      current
    DESCRIPTION
        "The community string for the SNMP agent. SNMP
        v1/v2c must have a matching community string
        for the SNMP agent and Manager.

        To disable SNMP v1/v2c access the community
        string should be empty.

        SNMP v1 and v2c access are GET (read-only) for
        security reasons. To be able to change settings
        a SNMPv3 user must be defined. The node only
        supports one community string.

        All printable ASCII characters except '&' are
        allowed in the community string. Note that the
        community string is case sensitive.

"
    DEFVAL { "public" }
    ::= { snmpGeneral 4 }

snmpGeneralInformSinkTableSize  OBJECT-TYPE
    SYNTAX      Unsigned32
    MAX-ACCESS  read-only
    STATUS      current
    DESCRIPTION
        "Number of rows available in the
        inform sink table.

"
    ::= { snmpGeneral 5 }

snmpGeneralUserTableSize OBJECT-TYPE
    SYNTAX      Unsigned32
    MAX-ACCESS  read-only
    STATUS      current
    DESCRIPTION
        "Number of rows available in the
        SNMP user table.

"
    ::= { snmpGeneral 6 }


snmpGeneralResetEngineIDCommand OBJECT-TYPE
    SYNTAX      CommandString
    MAX-ACCESS  read-only
    STATUS      current
    DESCRIPTION
        "Reset the SNMP engine ID and recreate the users.

"
    ::= { snmpGeneral 7 }

snmpGeneralSecurityPolicy OBJECT-TYPE
    SYNTAX      INTEGER {
                    basic (1),
                    authentication (2),
                    authAndPrivacy (3) }
    MAX-ACCESS  read-only
    STATUS      current
    DESCRIPTION
        "SNMP Security level policy for authentication and privacy at node level.

         basic - Legacy mode, users can use all SNMP versions: v1, v2c and v3.
                 - v1/v2c with community string (read only)
                 - v3 MD5 Auth (read and write)
                 - v3 MD5 Auth + AES128 privacy (read and write)
         authentication - Users must use authentication key. Only SNMP v3 modes with or
                 without encryption are allowed.
                 - v3 MD5 Auth (read and write)
                 - v3 MD5 Auth + AES128 privacy (read and write)
         authAndPrivacy - Strict SNMP v3 with encryption. Users must use authentication and
                 privacy keys.
                 - v3 MD5 Auth + AES128 privacy (read and write)
                   Note: To be able to set the mode authAndPrivacy on a node, all
                   snmp users must have an authentication and privacy password
                   stored. Otherwise, changing to the highest security level will not be
                   allowed.

"
    DEFVAL { basic }
    ::= { snmpGeneral 8 }



-- ----------------------------------------------------
-- User group
-- ----------------------------------------------------

snmpUserTable  OBJECT-TYPE
    SYNTAX      SEQUENCE OF SnmpUserEntry
    MAX-ACCESS  not-accessible
    STATUS      current
    DESCRIPTION
        "The USM user list."
    ::= { snmpUserList 1 }

snmpUserEntry OBJECT-TYPE
    SYNTAX      SnmpUserEntry
    MAX-ACCESS  not-accessible
    STATUS      current
    DESCRIPTION
        "An entry in the USM user table.

        Create:

        <user>[:<password>]

        Default values: Password is set to the
        default password.

"
    INDEX { snmpUserIndex }
    ::= { snmpUserTable 1 }

SnmpUserEntry ::=
    SEQUENCE {
        snmpUserIndex                   Unsigned32,
        snmpUserName                    DisplayString,
        snmpUserChangePassword          CommandString,
        snmpUserEngineId                SnmpEngineID,
        snmpUserAuthKey                 OCTET STRING,
        snmpUserPrivKey                 OCTET STRING,
        snmpUserChangePrivPassword      CommandString,
        snmpUserPrivProtocol            INTEGER }

snmpUserIndex OBJECT-TYPE
    SYNTAX      Unsigned32 (1..2147483647)
    MAX-ACCESS  read-only
    STATUS      current
    DESCRIPTION
        "An arbitrary index assigned to each entry.

"
    ::= { snmpUserEntry 1 }

snmpUserName OBJECT-TYPE
    SYNTAX      DisplayString (SIZE (0..255))
    MAX-ACCESS  read-create
    STATUS      current
    DESCRIPTION
        "Name assigned to each entry.
        Used for SNMPv3 Auth-MD5 read and write mode.

        In application SNMPc
        V3 Auth/Priv Security Name

"
    DEFVAL { "oper" }
    ::= { snmpUserEntry 2 }

snmpUserChangePassword OBJECT-TYPE
    SYNTAX      CommandString
    MAX-ACCESS  read-write
    STATUS      current
    DESCRIPTION
        "Change user password.

        The password must be at least 8
        characters long.

        Default password is set to '1234567890'.

"
    DEFVAL { "1234567890" }
    ::= { snmpUserEntry 3 }

snmpUserEngineId OBJECT-TYPE
    SYNTAX SnmpEngineID
    MAX-ACCESS  read-write
    STATUS      current
    DESCRIPTION
        "The engine id used when the authority key was
        generated.

"
    ::= { snmpUserEntry 4 }

snmpUserAuthKey OBJECT-TYPE
    SYNTAX OCTET STRING
    MAX-ACCESS  read-write
    STATUS      current
    DESCRIPTION
        "The authority key for the user.

"
    ::= { snmpUserEntry 5 }

snmpUserPrivKey OBJECT-TYPE
    SYNTAX OCTET STRING
    MAX-ACCESS  read-write
    STATUS      current
    DESCRIPTION
        "The privacy key for the user.

"
    ::= { snmpUserEntry 6 }

snmpUserChangePrivPassword OBJECT-TYPE
    SYNTAX      CommandString
    MAX-ACCESS  read-write
    STATUS      current
    DESCRIPTION
        "Change user privacy password.

        The password must be at least 8 characters long,
        or empty to not use encryption.

        Default privacy password is empty.

"
    DEFVAL { "" }
    ::= { snmpUserEntry 7 }


-- tbd AuthProtocol
-- tbd PrivProtocol

snmpUserPrivProtocol OBJECT-TYPE
    SYNTAX      INTEGER {
                    none (1),
                    aes128 (2) }
    MAX-ACCESS  read-only
    STATUS      current
    DESCRIPTION
        "Privacy protocol, used for encryption of SNMP data.

         none - Encryption disabled. No privacy password exist.
         aes128 - AES 128 is used for encryption. Privacy password exist.

"
    DEFVAL { none }
    ::= { snmpUserEntry 8 }



-- ----------------------------------------------------
-- Notifications
-- ----------------------------------------------------

-- n/a


-- ----------------------------------------------------
-- Object and event groups
-- ----------------------------------------------------

snmpInformSinkGroup OBJECT-GROUP
    OBJECTS {
        snmpInformSinkIndex,
        snmpInformSinkName,
        snmpInformSinkAddr,
        snmpInformSinkPort,
        snmpInformSinkCommunity,
        snmpInformSinkRowStatus }
    STATUS      deprecated
    DESCRIPTION
        "The informsink objects."
    ::= { lumSnmpGroups 1 }

snmpGeneralGroup OBJECT-GROUP
    OBJECTS {
        snmpGeneralLastChangeTime,
        snmpGeneralConfigLastChangeTime }
    STATUS      deprecated
    DESCRIPTION
        "The general objects."
    ::= { lumSnmpGroups 2 }

snmpGeneralGroupV2 OBJECT-GROUP
    OBJECTS {
        snmpGeneralLastChangeTime,
        snmpGeneralConfigLastChangeTime,
        snmpGeneralEngineID }
    STATUS      deprecated
    DESCRIPTION
        "The general objects v2."
    ::= { lumSnmpGroups 3 }

snmpUserGroup OBJECT-GROUP
    OBJECTS {
        snmpUserIndex,
        snmpUserName,
        snmpUserChangePassword,
        snmpUserEngineId,
        snmpUserAuthKey }
    STATUS      deprecated
    DESCRIPTION
        "The user objects."
    ::= { lumSnmpGroups 4 }

snmpGeneralGroupV3 OBJECT-GROUP
    OBJECTS {
        snmpGeneralLastChangeTime,
        snmpGeneralConfigLastChangeTime,
        snmpGeneralEngineID,
        snmpGeneralCommunity }
    STATUS      deprecated
    DESCRIPTION
        "The general objects v3."
    ::= { lumSnmpGroups 5 }

snmpInformSinkGroupV2 OBJECT-GROUP
    OBJECTS {
        snmpInformSinkIndex,
        snmpInformSinkName,
        snmpInformSinkAddr,
        snmpInformSinkPort,
        snmpInformSinkCommunity,
        snmpInformSinkRowStatus,
        snmpInformSinkStorageType,
        snmpInformSinkAlarmNotifications,
        snmpInformSinkPerformanceNotifications,
        snmpInformSinkOtherNotifications }
    STATUS      deprecated
    DESCRIPTION
        "The informsink objects v2."
    ::= { lumSnmpGroups 6 }

snmpGeneralGroupV4 OBJECT-GROUP
    OBJECTS {
        snmpGeneralLastChangeTime,
        snmpGeneralConfigLastChangeTime,
        snmpGeneralEngineID,
        snmpGeneralCommunity,
        snmpGeneralInformSinkTableSize,
        snmpGeneralUserTableSize }
    STATUS      deprecated
    DESCRIPTION
        "The general objects v4."
    ::= { lumSnmpGroups 7 }

snmpInformSinkGroupV3 OBJECT-GROUP
    OBJECTS {
        snmpInformSinkIndex,
        snmpInformSinkName,
        snmpInformSinkAddr,
        snmpInformSinkPort,
        snmpInformSinkCommunity,
        snmpInformSinkRowStatus,
        snmpInformSinkStorageType,
        snmpInformSinkAlarmNotifications,
        snmpInformSinkPerformanceNotifications,
        snmpInformSinkOtherNotifications,
        snmpInformSinkMib2Notifications }
    STATUS      current
    DESCRIPTION
        "The informsink objects v3."
    ::= { lumSnmpGroups 8 }


snmpGeneralGroupV5 OBJECT-GROUP
    OBJECTS {
        snmpGeneralLastChangeTime,
        snmpGeneralConfigLastChangeTime,
        snmpGeneralEngineID,
        snmpGeneralCommunity,
        snmpGeneralInformSinkTableSize,
        snmpGeneralUserTableSize,
        snmpGeneralResetEngineIDCommand }
    STATUS      deprecated
    DESCRIPTION
        "The general objects v5."
    ::= { lumSnmpGroups 9 }

snmpGeneralGroupV6 OBJECT-GROUP
    OBJECTS {
        snmpGeneralLastChangeTime,
        snmpGeneralConfigLastChangeTime,
        snmpGeneralEngineID,
        snmpGeneralCommunity,
        snmpGeneralInformSinkTableSize,
        snmpGeneralUserTableSize,
        snmpGeneralResetEngineIDCommand,
	snmpGeneralSecurityPolicy }
    STATUS      current
    DESCRIPTION
        "The general objects v6."
    ::= { lumSnmpGroups 10 }

snmpUserGroupV2 OBJECT-GROUP
    OBJECTS {
        snmpUserIndex,
        snmpUserName,
        snmpUserChangePassword,
        snmpUserEngineId,
        snmpUserAuthKey,
        snmpUserPrivKey,
        snmpUserChangePrivPassword,
        snmpUserPrivProtocol }
    STATUS      current
    DESCRIPTION
        "The user objects V2."
    ::= { lumSnmpGroups 11 }

-- ----------------------------------------------------
-- Compliance
-- ----------------------------------------------------

lumSnmpBasicComplV1 MODULE-COMPLIANCE
    STATUS      deprecated
    DESCRIPTION
        "Basic implementation requirements for the SNMP MIB V1."
    MODULE
        MANDATORY-GROUPS {
            snmpInformSinkGroup,
            snmpGeneralGroup }
    ::= { lumSnmpCompl 1 }

lumSnmpBasicComplV2 MODULE-COMPLIANCE
    STATUS      deprecated
    DESCRIPTION
        "Basic implementation requirements for the SNMP MIB V2."
    MODULE
        MANDATORY-GROUPS {
            snmpInformSinkGroup,
            snmpGeneralGroupV2,
            snmpUserGroup }
    ::= { lumSnmpCompl 2 }

lumSnmpBasicComplV3 MODULE-COMPLIANCE
    STATUS      deprecated
    DESCRIPTION
        "Basic implementation requirements for the SNMP MIB V3."
    MODULE
        MANDATORY-GROUPS {
            snmpInformSinkGroup,
            snmpGeneralGroupV2,
            snmpUserGroup }
    ::= { lumSnmpCompl 3 }

lumSnmpBasicComplV4 MODULE-COMPLIANCE
    STATUS      deprecated
    DESCRIPTION
        "Basic implementation requirements for the SNMP MIB V4."
    MODULE
        MANDATORY-GROUPS {
            snmpInformSinkGroup,
            snmpGeneralGroupV3,
            snmpUserGroup }
    ::= { lumSnmpCompl 4 }

lumSnmpBasicComplV5 MODULE-COMPLIANCE
    STATUS      deprecated
    DESCRIPTION
        "Basic implementation requirements for the SNMP MIB V5."
    MODULE
        MANDATORY-GROUPS {
            snmpInformSinkGroupV2,
            snmpGeneralGroupV3,
            snmpUserGroup }
    ::= { lumSnmpCompl 5 }

lumSnmpBasicComplV6 MODULE-COMPLIANCE
    STATUS      deprecated
    DESCRIPTION
        "Basic implementation requirements for the SNMP MIB V6."
    MODULE
        MANDATORY-GROUPS {
            snmpInformSinkGroupV2,
            snmpGeneralGroupV4,
            snmpUserGroup }
    ::= { lumSnmpCompl 6 }

lumSnmpBasicComplV7 MODULE-COMPLIANCE
    STATUS      deprecated
    DESCRIPTION
        "Basic implementation requirements for the SNMP MIB V7."
    MODULE
        MANDATORY-GROUPS {
            snmpInformSinkGroupV3,
            snmpGeneralGroupV4,
            snmpUserGroup }
    ::= { lumSnmpCompl 7 }

lumSnmpBasicComplV8 MODULE-COMPLIANCE
    STATUS      deprecated
    DESCRIPTION
        "Basic implementation requirements for the SNMP MIB V8."
    MODULE
        MANDATORY-GROUPS {
            snmpInformSinkGroupV3,
            snmpGeneralGroupV5,
            snmpUserGroup }
    ::= { lumSnmpCompl 8 }

lumSnmpBasicComplV9 MODULE-COMPLIANCE
    STATUS      deprecated
    DESCRIPTION
        "Basic implementation requirements for the SNMP MIB V9."
    MODULE
        MANDATORY-GROUPS {
            snmpInformSinkGroupV3,
            snmpGeneralGroupV5,
            snmpUserGroup }
    ::= { lumSnmpCompl 9 }

lumSnmpBasicComplV10 MODULE-COMPLIANCE
    STATUS      current
    DESCRIPTION
        "Basic implementation requirements for the SNMP MIB V10 (30.1)."
    MODULE
        MANDATORY-GROUPS {
            snmpInformSinkGroupV3,
            snmpGeneralGroupV6,
            snmpUserGroupV2 }
    ::= { lumSnmpCompl 10 }

END
