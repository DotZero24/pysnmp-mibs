-- *****************************************************************
-- INFINERA-TP-DSEPTP-MIB
--
-- October 2008, Sharfuddin Syed / Narendra Gupta
--
--
-- Copyright (c) 2008-2012 by Infinera Inc.
-- All rights reserved.
-- ****************************************************************

INFINERA-TP-DSEPTP-MIB DEFINITIONS ::= BEGIN

IMPORTS
    MODULE-IDENTITY, OBJECT-TYPE,
    Integer32                                   FROM SNMPv2-SMI
    MODULE-COMPLIANCE, OBJECT-GROUP             FROM SNMPv2-CONF
    DisplayString, TruthValue                   FROM SNMPv2-TC
    ifIndex                                     FROM IF-MIB
    FloatTenths, InfnServiceType                FROM INFINERA-TC-MIB
    terminationPoint                            FROM INFINERA-REG-MIB;

dsePtpMIB MODULE-IDENTITY
    LAST-UPDATED  "200810200000Z"
    ORGANIZATION
        "Infinera"
    CONTACT-INFO
        "Infinera
                1322 Bordeaux Drive
                Sunnyvale, CA - 94089

                Contact : Technical Support
                Email   : support@infinera.com
                Phone   : 1-877-INF-5288"
    DESCRIPTION
        " "

    REVISION  "200810200000Z"
    DESCRIPTION
        "First Version"
::= { terminationPoint 22 }


-- Conformance Statements

dsePtpConformance  OBJECT IDENTIFIER ::= { dsePtpMIB 3 }
dsePtpCompliances  OBJECT IDENTIFIER ::= { dsePtpConformance 1 }
dsePtpGroups  OBJECT IDENTIFIER ::= { dsePtpConformance 2 }

dsePtpTable  OBJECT-TYPE
    SYNTAX SEQUENCE OF DsePtpEntry
    MAX-ACCESS not-accessible
    STATUS     current
    DESCRIPTION
        "A list of dsePtp entries. Each entry is uniquely identified by the value of ifIndex."
    ::= { dsePtpMIB 1 }

dsePtpEntry  OBJECT-TYPE
    SYNTAX     DsePtpEntry
    MAX-ACCESS not-accessible
    STATUS     current
    DESCRIPTION
        "A dsePtp entry containing information pertaining to Infinera dsePtp interfaces.
                This table is a subclass of IfCommon. Entries will exist in this table only for interfaces of
                type dsePtp."
    INDEX { ifIndex }
    ::= { dsePtpTable 1 }

DsePtpEntry  ::= SEQUENCE {
    dsePtpProvisionedRemoteTP    DisplayString,
    dsePtpPmHistStatsEnable  INTEGER

}

dsePtpProvisionedRemoteTP  OBJECT-TYPE
    SYNTAX     DisplayString
    MAX-ACCESS read-only
    STATUS     current
    DESCRIPTION
        ""
    ::= { dsePtpEntry 1 }

dsePtpPmHistStatsEnable OBJECT-TYPE
    SYNTAX  INTEGER {
        enabled(1),
        disabled(2)
    }
    MAX-ACCESS  read-write
    STATUS      current
    DESCRIPTION "This objects control the collection of historical PM."
    DEFVAL      { enabled }
    ::= { dsePtpEntry  2 }


dsePtpCompliance  MODULE-COMPLIANCE
    STATUS     current
    DESCRIPTION
        "Describes the requirements for conformance to the DSEPTP-MIB"
    MODULE
        MANDATORY-GROUPS { dsePtpGroup }
    ::= { dsePtpCompliances 1 }

dsePtpGroup  OBJECT-GROUP
    OBJECTS {
        dsePtpProvisionedRemoteTP,
        dsePtpPmHistStatsEnable
        }
    STATUS     current
    DESCRIPTION
        " A collection of objects for managing the dsePtp"
    ::= { dsePtpGroups 1 }
END
