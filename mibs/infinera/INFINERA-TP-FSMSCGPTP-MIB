-- *****************************************************************
-- INFINERA-TP-FSMSCGPTP-MIB
-- Copyright (c) 2008-2012 by Infinera Inc
-- All rights reserved.
-- ****************************************************************

INFINERA-TP-FSMSCGPTP-MIB DEFINITIONS ::= BEGIN

IMPORTS
    MODULE-IDENTITY, OBJECT-TYPE                FROM SNMPv2-SMI
    MODULE-COMPLIANCE, OBJECT-GROUP             FROM SNMPv2-CONF
    DisplayString                               FROM SNMPv2-TC
    ifIndex                                     FROM IF-MIB
    FloatHundredths,InfnEnableDisable,
    InfnEqptType                                FROM INFINERA-TC-MIB
    terminationPoint                            FROM INFINERA-REG-MIB;

fsmScgPtpMIB MODULE-IDENTITY
    LAST-UPDATED  "201310200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "201310200000Z"
    DESCRIPTION
        "First Version"
    ::= { terminationPoint 44 }

fsmScgPtpTable OBJECT-TYPE
    SYNTAX      SEQUENCE OF FsmScgPtpEntry
    MAX-ACCESS  not-accessible
    STATUS      current
    DESCRIPTION
        "A list of FsmScgPtp entries. Each entry is uniquely identified by the value of ifIndex."
    ::= { fsmScgPtpMIB 1 }

fsmScgPtpEntry  OBJECT-TYPE
    SYNTAX      FsmScgPtpEntry
    MAX-ACCESS  not-accessible
    STATUS      current
    DESCRIPTION
        "A FsmScgPtp entry containing information pertaining to Infinera FsmScgPtp Interfaces.
        This table is a subclass of IfCommon. Entries will exist in this table only for
        interfaces of type DLM OCG PTP."
    INDEX { ifIndex }
    ::= { fsmScgPtpTable 1 }


FsmScgPtpEntry  ::= SEQUENCE {
    fsmScgPtpPowerControlLoop               InfnEnableDisable,
    fsmScgPtpAvailableFreqSlotList          DisplayString,
    fsmScgPtpUsedFreqSlotList               DisplayString,
    fsmScgPtpPathLossCheckControlStatus     INTEGER,
    fsmScgPtpLastSuccessfullPathLossCheckTS Integer32,
    fsmScgPtpPathLoss                       FloatHundredths,
    fsmScgPtpPathLossCheckDetectPort        DisplayString,
    fsmScgPtpLastPathLossCheckAttemptTS     Integer32,
    fsmScgPtpLastPathLossCheckAttemptStatus INTEGER,
    fsmScgPtpLastPathLossCheckFailedReason  INTEGER,
    fsmScgPtpTxEdfaPowerOffset              FloatHundredths,
    fsmScgPtpRxEdfaPowerOffset              FloatHundredths,
    fsmScgPtpTrafficMode                    INTEGER,
    fsmScgPtpScgNumber                      Integer32,
    fsmScgPtpScgSupEqptType                 InfnEqptType,
    fsmScgPtpMPOAID                         DisplayString,
    fsmScgPtpProvisionedFPMPO               DisplayString,
    fsmScgPtpAutoDiscoveryState             INTEGER,
    fsmScgPtpDiscoveredNeighborTP           DisplayString,
    fsmScgPtpInterfaceType                  INTEGER,
    fsmScgPtpProvisionedNeighborTP          DisplayString,
    fsmScgPtpProvisionedOpenWaveRemotePtp   DisplayString,
    fsmScgPtpPmHistStatsEnable              INTEGER,
    fsmScgPtpPathLossHigh                   INTEGER

}

fsmScgPtpPowerControlLoop OBJECT-TYPE
    SYNTAX      InfnEnableDisable
    MAX-ACCESS  read-write
    STATUS      current
    DESCRIPTION ""
    ::= { fsmScgPtpEntry  1 }

fsmScgPtpAvailableFreqSlotList  OBJECT-TYPE
    SYNTAX      DisplayString
    MAX-ACCESS  read-only
    STATUS      current
    DESCRIPTION ""
    ::= { fsmScgPtpEntry  2 }

fsmScgPtpUsedFreqSlotList   OBJECT-TYPE
    SYNTAX      DisplayString
    MAX-ACCESS  read-only
    STATUS      current
    DESCRIPTION ""
    ::= { fsmScgPtpEntry  3 }

fsmScgPtpPathLossCheckControlStatus OBJECT-TYPE
    SYNTAX      INTEGER {
        inProgress(1),
        idle(2)
    }
    MAX-ACCESS  read-only
    STATUS      current
    DESCRIPTION ""
    ::= { fsmScgPtpEntry  4 }

fsmScgPtpLastSuccessfullPathLossCheckTS OBJECT-TYPE
    SYNTAX      Integer32
    MAX-ACCESS  read-only
    STATUS      current
    DESCRIPTION ""
    ::= { fsmScgPtpEntry  5 }

fsmScgPtpPathLoss   OBJECT-TYPE
    SYNTAX      FloatHundredths
    MAX-ACCESS  read-only
    STATUS      current
    DESCRIPTION ""
    ::= { fsmScgPtpEntry  6 }

fsmScgPtpPathLossCheckDetectPort    OBJECT-TYPE
    SYNTAX      DisplayString
    MAX-ACCESS  read-only
    STATUS      current
    DESCRIPTION ""
    ::= { fsmScgPtpEntry  7 }

fsmScgPtpLastPathLossCheckAttemptTS OBJECT-TYPE
    SYNTAX      Integer32
    MAX-ACCESS  read-only
    STATUS      current
    DESCRIPTION ""
    ::= { fsmScgPtpEntry  8 }

fsmScgPtpLastPathLossCheckAttemptStatus OBJECT-TYPE
    SYNTAX      INTEGER {
        successfull(1),
        unsuccessfull(2),
        notAttempted(3)
    }
    MAX-ACCESS  read-only
    STATUS      current
    DESCRIPTION ""
    ::= { fsmScgPtpEntry  9 }

fsmScgPtpLastPathLossCheckFailedReason  OBJECT-TYPE
    SYNTAX      INTEGER {
        notAvailable(1),
        timedOut(2),
        interruptedByAD(3),
        interruptedByReset(4),
        portInService(5)
    }
    MAX-ACCESS  read-only
    STATUS      current
    DESCRIPTION ""
    ::= { fsmScgPtpEntry  10 }

fsmScgPtpTxEdfaPowerOffset  OBJECT-TYPE
    SYNTAX      FloatHundredths
    MAX-ACCESS  read-write
    STATUS      current
    DESCRIPTION ""
    ::= { fsmScgPtpEntry 11 }

fsmScgPtpRxEdfaPowerOffset  OBJECT-TYPE
    SYNTAX      FloatHundredths
    MAX-ACCESS  read-write
    STATUS      current
    DESCRIPTION ""
    ::= { fsmScgPtpEntry 12 }

fsmScgPtpTrafficMode    OBJECT-TYPE
    SYNTAX      INTEGER {
        none (1),
        addDrop(2),
        pathLossCheckSource (3)
    }
    MAX-ACCESS  read-write
    STATUS      current
    DESCRIPTION ""
    ::= { fsmScgPtpEntry 13 }

fsmScgPtpScgNumber OBJECT-TYPE
    SYNTAX      Integer32
    MAX-ACCESS  read-only
    STATUS      current
    DESCRIPTION ""
    ::= { fsmScgPtpEntry 14 }


fsmScgPtpScgSupEqptType OBJECT-TYPE
    SYNTAX      InfnEqptType
    MAX-ACCESS  read-write
    STATUS      current
    DESCRIPTION ""
    ::= { fsmScgPtpEntry 15 }

fsmScgPtpMPOAID OBJECT-TYPE
    SYNTAX      DisplayString
    MAX-ACCESS  read-write
    STATUS      current
    DESCRIPTION ""
    ::= { fsmScgPtpEntry 16 }

fsmScgPtpProvisionedFPMPO  OBJECT-TYPE
    SYNTAX      DisplayString
    MAX-ACCESS  read-write
    STATUS      current
    DESCRIPTION ""
    ::= { fsmScgPtpEntry 17 }


fsmScgPtpAutoDiscoveryState OBJECT-TYPE
    SYNTAX      INTEGER {
        inProgress (1),
        completed (2),
        unknown(3),
        notValid (4),
        failed(5),
        waitToStart(6),
        associated(7)
    }

    MAX-ACCESS  read-only
    STATUS      current
    DESCRIPTION ""
    ::= { fsmScgPtpEntry 18 }

fsmScgPtpDiscoveredNeighborTP OBJECT-TYPE
    SYNTAX      DisplayString
    MAX-ACCESS  read-only
    STATUS      current
    DESCRIPTION ""
    ::= { fsmScgPtpEntry 19 }

fsmScgPtpInterfaceType OBJECT-TYPE
    SYNTAX      INTEGER {
        optical(1),
        electrical(2)
    }
    MAX-ACCESS  read-write
    STATUS      current
    DESCRIPTION ""
    ::= { fsmScgPtpEntry 20 }

fsmScgPtpProvisionedOpenWaveRemotePtp OBJECT-TYPE
    SYNTAX          DisplayString
    MAX-ACCESS      read-write
    STATUS          current
    DESCRIPTION     ""
    ::= { fsmScgPtpEntry 21 }

fsmScgPtpPmHistStatsEnable OBJECT-TYPE
    SYNTAX          INTEGER {
        enabled(1),
        disabled(2)
    }
    MAX-ACCESS      read-only
    STATUS          current
    DESCRIPTION     ""
    ::= { fsmScgPtpEntry 22 }

fsmScgPtpProvisionedNeighborTP OBJECT-TYPE
    SYNTAX      DisplayString
    MAX-ACCESS  read-only
    STATUS      current
    DESCRIPTION ""
    ::= { fsmScgPtpEntry 23 }

fsmScgPtpPathLossHigh OBJECT-TYPE
    SYNTAX      INTEGER {
        true(1),
        false(2)
    }
    MAX-ACCESS  read-only
    STATUS      current
    DESCRIPTION ""
    ::= { fsmScgPtpEntry 24 }



-- Conformance Statements
fsmScgPtpConformance    OBJECT IDENTIFIER ::= { fsmScgPtpMIB 3 }
fsmScgPtpCompliances    OBJECT IDENTIFIER ::= { fsmScgPtpConformance 1 }
fsmScgPtpGroups         OBJECT IDENTIFIER ::= { fsmScgPtpConformance 2 }

fsmScgPtpCompliance MODULE-COMPLIANCE
    STATUS current
    DESCRIPTION
    "Describes the requirements for conformance to the FSMSCGPTP-MIB"
    MODULE
        MANDATORY-GROUPS { fsmScgPtpGroup }
    ::= { fsmScgPtpCompliances 1 }

fsmScgPtpGroup OBJECT-GROUP
    OBJECTS {
        fsmScgPtpPowerControlLoop,
        fsmScgPtpAvailableFreqSlotList,
        fsmScgPtpUsedFreqSlotList,
        fsmScgPtpPathLossCheckControlStatus,
        fsmScgPtpLastSuccessfullPathLossCheckTS,
        fsmScgPtpPathLoss,
        fsmScgPtpPathLossCheckDetectPort,
        fsmScgPtpLastPathLossCheckAttemptTS,
        fsmScgPtpLastPathLossCheckAttemptStatus,
        fsmScgPtpLastPathLossCheckFailedReason,
        fsmScgPtpTxEdfaPowerOffset,
        fsmScgPtpRxEdfaPowerOffset,
        fsmScgPtpTrafficMode,
        fsmScgPtpScgNumber                     ,
        fsmScgPtpScgSupEqptType                ,
        fsmScgPtpMPOAID                        ,
        fsmScgPtpProvisionedFPMPO              ,
        fsmScgPtpAutoDiscoveryState            ,
        fsmScgPtpDiscoveredNeighborTP          ,
        fsmScgPtpInterfaceType                 ,
        fsmScgPtpProvisionedNeighborTP         ,
        fsmScgPtpProvisionedOpenWaveRemotePtp  ,
        fsmScgPtpPmHistStatsEnable             ,
        fsmScgPtpPathLossHigh

}
    STATUS current
    DESCRIPTION
        " A collection of objects for managing the fsmScgPtp"
    ::= { fsmScgPtpGroups 1 }
END
