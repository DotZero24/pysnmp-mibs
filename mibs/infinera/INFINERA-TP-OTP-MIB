-- *****************************************************************
-- INFINERA-TP-OTP-MIB
-- Copyright (c) 2008-2012 by Infinera Inc
-- All rights reserved.
-- ****************************************************************

INFINERA-TP-OTP-MIB DEFINITIONS ::= BEGIN

IMPORTS
    MODULE-IDENTITY, OBJECT-TYPE                FROM SNMPv2-SMI
    MODULE-COMPLIANCE, OBJECT-GROUP             FROM SNMPv2-CONF
    DisplayString                               FROM SNMPv2-TC
    ifIndex                                     FROM IF-MIB
    FloatHundredths,InfnEnableDisable           FROM INFINERA-TC-MIB
    terminationPoint                            FROM INFINERA-REG-MIB;

optPtpMIB MODULE-IDENTITY
    LAST-UPDATED  "201310200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "201310200000Z"
    DESCRIPTION
        "First Version"
    ::= { terminationPoint 39 }

optPtpTable OBJECT-TYPE
    SYNTAX      SEQUENCE OF OptPtpEntry
    MAX-ACCESS  not-accessible
    STATUS      current
    DESCRIPTION
        "A list of OptPtp entries. Each entry is uniquely identified by the value of ifIndex."
    ::= { optPtpMIB 1 }

optPtpEntry  OBJECT-TYPE
    SYNTAX      OptPtpEntry
    MAX-ACCESS  not-accessible
    STATUS      current
    DESCRIPTION
        "A OptPtp entry containing information pertaining to Infinera OptPtp Interfaces.
        This table is a subclass of IfCommon. Entries will exist in this table only for
        interfaces of type DLM OCG PTP."
    INDEX { ifIndex }
    ::= { optPtpTable 1 }


OptPtpEntry  ::= SEQUENCE {
    optPtpProvNbrTP           DisplayString
}

optPtpProvNbrTP   OBJECT-TYPE
    SYNTAX      DisplayString
    MAX-ACCESS  read-write
    STATUS      current
    DESCRIPTION ""
    ::= { optPtpEntry 1 }

-- Conformance Statements
optPtpConformance    OBJECT IDENTIFIER ::= { optPtpMIB 3 }
optPtpCompliances    OBJECT IDENTIFIER ::= { optPtpConformance 1 }
optPtpGroups         OBJECT IDENTIFIER ::= { optPtpConformance 2 }

optPtpCompliance MODULE-COMPLIANCE
    STATUS current
    DESCRIPTION
    "Describes the requirements for conformance to the OTP-MIB"
    MODULE
        MANDATORY-GROUPS { optPtpGroup }
    ::= { optPtpCompliances 1 }

optPtpGroup OBJECT-GROUP
    OBJECTS {
        optPtpProvNbrTP
}
    STATUS current
    DESCRIPTION
        " A collection of objects for managing the optPtp"
    ::= { optPtpGroups 1 }
END
