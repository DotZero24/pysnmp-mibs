-- *****************************************************************
-- INFINERA-TP-BANDPTP-MIB
-- October 2008, Sharfuddin Syed / Narendra Gupta
-- Copyright (c) 2008-2012 by Infinera Inc.
-- All rights reserved.
-- ****************************************************************

INFINERA-TP-BANDPTP-MIB DEFINITIONS ::= BEGIN

IMPORTS
    MODULE-IDENTITY, OBJECT-TYPE,
    Integer32                                   FROM SNMPv2-SMI
    MODULE-COMPLIANCE, OBJECT-GROUP             FROM SNMPv2-CONF
    DisplayString, TruthValue                   FROM SNMPv2-TC
    ifIndex                                     FROM IF-MIB
    FloatTenths, InfnServiceType,
    InfnCircuitPackType, InfnEqptType,
	InfnEnableDisable,InfnPmHistStatsControl    FROM INFINERA-TC-MIB
    terminationPoint                            FROM INFINERA-REG-MIB;

bandPtpMIB MODULE-IDENTITY
    LAST-UPDATED  "200810200000Z"
    ORGANIZATION
        "Infinera"
    CONTACT-INFO
        "Infinera
                1322 Bordeaux Drive
                Sunnyvale, CA - 94089
                Contact : Technical Support
                Email   : support@infinera.com
                Phone   : 1-877-INF-5288"
    DESCRIPTION
        " "

    REVISION  "200810200000Z"
    DESCRIPTION
        "First Version"
::= { terminationPoint 20 }


-- Conformance Statements

bandPtpConformance  OBJECT IDENTIFIER ::= { bandPtpMIB 3 }
bandPtpCompliances  OBJECT IDENTIFIER ::= { bandPtpConformance 1 }
bandPtpGroups  OBJECT IDENTIFIER ::= { bandPtpConformance 2 }

-- February 18, 2008

bandPtpTable  OBJECT-TYPE
    SYNTAX SEQUENCE OF BandPtpEntry
    MAX-ACCESS not-accessible
    STATUS     current
    DESCRIPTION
        "A list of bandPtp entries. Each entry is uniquely identified by the value of ifIndex."
    ::= { bandPtpMIB 1 }

bandPtpEntry  OBJECT-TYPE
    SYNTAX     BandPtpEntry
    MAX-ACCESS not-accessible
    STATUS     current
    DESCRIPTION
        "A bandPtp entry containing information pertaining to Infinera bandPtp interfaces.
                This table is a subclass of IfCommon. Entries will exist in this table only for interfaces of
                type bandPtp."
    INDEX { ifIndex }
    ::= { bandPtpTable 1 }

BandPtpEntry  ::= SEQUENCE {
    bandPtpProvisionedNeighborTP        DisplayString,
    bandPtpProvAseTP                    DisplayString,
    bandPtpPmHistStatsEnable            InfnPmHistStatsControl,
    bandPtpBringupLoopbackMode          InfnEnableDisable,
	bandPtpTxProvNbrTP                  DisplayString,
	bandPtpRxProvNbrTP                  DisplayString,
	bandPtpTxProvEqptType               InfnEqptType,
	bandPtpRxProvEqptType               InfnEqptType,
    bandPtpAssociatedEqptType           InfnEqptType,
    bandPtpMuxFreqSlotAttenProfile      DisplayString,
    bandPtpDemuxFreqSlotAttenProfile    DisplayString,
    bandPtpProvisionedOpenWaveRemotePtp DisplayString
}

bandPtpProvisionedNeighborTP  OBJECT-TYPE
    SYNTAX     DisplayString
    MAX-ACCESS read-create
    STATUS     current
    DESCRIPTION
        "This objects refers to the peer BandPtp where fiber is connected"
    ::= { bandPtpEntry 1 }


bandPtpProvAseTP  OBJECT-TYPE
    SYNTAX     DisplayString
    MAX-ACCESS read-only
    STATUS     current
    DESCRIPTION
        "This object associates BANDPTP to GAM "
    ::= { bandPtpEntry 2 }

bandPtpPmHistStatsEnable    OBJECT-TYPE
    SYNTAX      InfnPmHistStatsControl
    MAX-ACCESS  read-write
    STATUS      current
    DESCRIPTION ""
    ::= { bandPtpEntry 3 }

bandPtpBringupLoopbackMode   OBJECT-TYPE
    SYNTAX      InfnEnableDisable
    MAX-ACCESS  read-write
    STATUS      current
    DESCRIPTION ""
    ::= { bandPtpEntry 4 }

bandPtpTxProvNbrTP    OBJECT-TYPE
    SYNTAX      DisplayString
    MAX-ACCESS  read-write
    STATUS      current
    DESCRIPTION ""
    ::= { bandPtpEntry 5 }

bandPtpRxProvNbrTP    OBJECT-TYPE
    SYNTAX      DisplayString
    MAX-ACCESS  read-write
    STATUS      current
    DESCRIPTION ""
    ::= { bandPtpEntry  6 }

bandPtpTxProvEqptType OBJECT-TYPE
    SYNTAX      InfnEqptType
    MAX-ACCESS  read-only
    STATUS      current
    DESCRIPTION ""
    ::= { bandPtpEntry 7 }

bandPtpRxProvEqptType OBJECT-TYPE
    SYNTAX      InfnEqptType
    MAX-ACCESS  read-only
    STATUS      current
    DESCRIPTION ""
    ::= { bandPtpEntry 8 }

bandPtpAssociatedEqptType   OBJECT-TYPE
    SYNTAX      InfnEqptType
    MAX-ACCESS  read-only
    STATUS      current
    DESCRIPTION ""
    ::= { bandPtpEntry 9 }

bandPtpMuxFreqSlotAttenProfile  OBJECT-TYPE
    SYNTAX      DisplayString
   MAX-ACCESS  read-write
    STATUS      current
    DESCRIPTION ""
   ::= { bandPtpEntry 10 }

bandPtpDemuxFreqSlotAttenProfile    OBJECT-TYPE
    SYNTAX      DisplayString
    MAX-ACCESS  read-write
    STATUS      current
    DESCRIPTION ""
    ::= { bandPtpEntry 11 }

bandPtpProvisionedOpenWaveRemotePtp OBJECT-TYPE
    SYNTAX      DisplayString
    MAX-ACCESS  read-write
    STATUS      current
    DESCRIPTION ""
    ::= { bandPtpEntry 12 }

bandPtpCompliance  MODULE-COMPLIANCE
    STATUS     current
    DESCRIPTION
        "Describes the requirements for conformance to the BANDPTP-MIB"
    MODULE
        MANDATORY-GROUPS { bandPtpGroup }
    ::= { bandPtpCompliances 1 }

bandPtpGroup  OBJECT-GROUP
    OBJECTS {
        bandPtpProvisionedNeighborTP,
        bandPtpProvAseTP,
        bandPtpPmHistStatsEnable,
		bandPtpBringupLoopbackMode,
		bandPtpTxProvNbrTP,
		bandPtpRxProvNbrTP,
		bandPtpTxProvEqptType,
		bandPtpRxProvEqptType,
        bandPtpAssociatedEqptType,
        bandPtpMuxFreqSlotAttenProfile,
        bandPtpDemuxFreqSlotAttenProfile,
        bandPtpProvisionedOpenWaveRemotePtp
    }
    STATUS     current
    DESCRIPTION
        " A collection of objects for managing the bandPtp"
    ::= { bandPtpGroups 1 }
END
