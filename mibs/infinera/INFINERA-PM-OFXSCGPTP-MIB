-- *****************************************************************
-- INFINERA-PM-OFXSCGPTP-MIB
--
-- October 2013, Rishab Joshi
--
--
-- Copyright (c) 2008-2013 by Infinera Inc.
-- All rights reserved.
-- ****************************************************************

INFINERA-PM-OFXSCGPTP-MIB DEFINITIONS ::= BEGIN

IMPORTS
    MODULE-IDENTITY, OBJECT-TYPE,
    Integer32                                   FROM SNMPv2-SMI
    MODULE-COMPLIANCE, OBJECT-GROUP             FROM SNMPv2-CONF
    TruthValue                                  FROM SNMPv2-TC
    ifIndex                                     FROM IF-MIB
    FloatHundredths                             FROM INFINERA-TC-MIB
    perfMon                                     FROM INFINERA-REG-MIB;


ofxScgPtpPmMIB MODULE-IDENTITY
    LAST-UPDATED  "201310080000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION      "201310080000Z"
    DESCRIPTION
        "First Version"
    ::= { perfMon 39 }


ofxScgPtpPmTable OBJECT-TYPE
    SYNTAX      SEQUENCE OF OfxScgPtpPmEntry
    MAX-ACCESS  not-accessible
    STATUS      current
    DESCRIPTION
        "A list of OfxScgPtpPm entries. Each entry is uniquely identified by the value of ifIndex."
    ::= { ofxScgPtpPmMIB 2 }

ofxScgPtpPmEntry  OBJECT-TYPE
    SYNTAX      OfxScgPtpPmEntry
    MAX-ACCESS  not-accessible
    STATUS      current
    DESCRIPTION
        "A OfxScgPtp entry containing historical performance information pertaining to Infinera OFXSCGPTP.
        This table is a subclass of IfCommon. Entries will exist in this table only for interfaces
        of type OFXSCGPTP."
    INDEX { ifIndex}
    ::= { ofxScgPtpPmTable 1 }


OfxScgPtpPmEntry  ::= SEQUENCE {
   ofxScgPtpPmTimestamp        Integer32,
   ofxScgPtpPmSampleDuration   INTEGER,
   ofxScgPtpPmValidity         TruthValue,
   ofxScgPtpPmTxEdfaOprMin     FloatHundredths,
   ofxScgPtpPmTxEdfaOprMax     FloatHundredths,
   ofxScgPtpPmTxEdfaOprAve     FloatHundredths,
   ofxScgPtpPmTxEdfaOptMin     FloatHundredths,
   ofxScgPtpPmTxEdfaOptMax     FloatHundredths,
   ofxScgPtpPmTxEdfaOptAve     FloatHundredths,
   ofxScgPtpPmTxEdfaLbcMin     FloatHundredths,
   ofxScgPtpPmTxEdfaLbcMax     FloatHundredths,
   ofxScgPtpPmTxEdfaLbcAve     FloatHundredths,
   ofxScgPtpPmRxEdfaOprMin     FloatHundredths,
   ofxScgPtpPmRxEdfaOprMax     FloatHundredths,
   ofxScgPtpPmRxEdfaOprAve     FloatHundredths,
   ofxScgPtpPmRxEdfaOptMin     FloatHundredths,
   ofxScgPtpPmRxEdfaOptMax     FloatHundredths,
   ofxScgPtpPmRxEdfaOptAve     FloatHundredths,
   ofxScgPtpPmRxEdfaLbcMin     FloatHundredths,
   ofxScgPtpPmRxEdfaLbcMax     FloatHundredths,
   ofxScgPtpPmRxEdfaLbcAve     FloatHundredths,
   ofxScgPtpPmQPreFecMin	   FloatHundredths,
   ofxScgPtpPmQPreFecMax	   FloatHundredths,
   ofxScgPtpPmQPreFecAve	   FloatHundredths,
   ofxScgPtpPmBerPreFecMin	   FloatHundredths,
   ofxScgPtpPmBerPreFecMax	   FloatHundredths,
   ofxScgPtpPmBerPreFecAve	   FloatHundredths
}

ofxScgPtpPmTimestamp OBJECT-TYPE
    SYNTAX      Integer32 (0..2147483647)
    MAX-ACCESS  not-accessible
    STATUS      current
    DESCRIPTION
        "End Time stamp for this interval. If this time is later than the current time,then the data for this bucket is currently being collected."
    ::= { ofxScgPtpPmEntry 1 }


ofxScgPtpPmSampleDuration OBJECT-TYPE
    SYNTAX      INTEGER {
        fifteenMinutes(1),
        day(2)
    }
    MAX-ACCESS  not-accessible
    STATUS      current
    DESCRIPTION
        "The duration of this sample."
    ::= { ofxScgPtpPmEntry 2 }

ofxScgPtpPmValidity OBJECT-TYPE
    SYNTAX      TruthValue
    MAX-ACCESS  read-only
    STATUS      current
    DESCRIPTION "Flag indicating if data was valid for the entire interval"
    ::= { ofxScgPtpPmEntry  3 }

ofxScgPtpPmTxEdfaOprMin OBJECT-TYPE
    SYNTAX      FloatHundredths
    MAX-ACCESS  read-only
    STATUS      current
    DESCRIPTION "Minimum OfxScg optical power receive."
    ::= { ofxScgPtpPmEntry  4}

ofxScgPtpPmTxEdfaOprMax OBJECT-TYPE
    SYNTAX      FloatHundredths
    MAX-ACCESS  read-only
    STATUS      current
    DESCRIPTION "Maximum OfxScg optical power receive."
    ::= { ofxScgPtpPmEntry  5}

ofxScgPtpPmTxEdfaOprAve OBJECT-TYPE
    SYNTAX      FloatHundredths
    MAX-ACCESS  read-only
    STATUS      current
    DESCRIPTION "Average OfxScg optical power receive."
    ::= { ofxScgPtpPmEntry  6}


ofxScgPtpPmTxEdfaOptMin OBJECT-TYPE
    SYNTAX      FloatHundredths
    MAX-ACCESS  read-only
    STATUS      current
    DESCRIPTION "Minimum OfxScg optical power transmit."
    ::= { ofxScgPtpPmEntry  7 }


ofxScgPtpPmTxEdfaOptMax OBJECT-TYPE
    SYNTAX      FloatHundredths
    MAX-ACCESS  read-only
    STATUS      current
    DESCRIPTION "Maximum OfxScg optical power transmit."
    ::= { ofxScgPtpPmEntry  8 }


ofxScgPtpPmTxEdfaOptAve OBJECT-TYPE
    SYNTAX      FloatHundredths
    MAX-ACCESS  read-only
    STATUS      current
    DESCRIPTION "Average OfxScg optical power transmit."
    ::= { ofxScgPtpPmEntry  9 }


ofxScgPtpPmTxEdfaLbcMin OBJECT-TYPE
    SYNTAX      FloatHundredths
    MAX-ACCESS  read-only
    STATUS      current
    DESCRIPTION "Minimum EDFA LBC transmit."
    ::= { ofxScgPtpPmEntry  10 }


ofxScgPtpPmTxEdfaLbcMax OBJECT-TYPE
    SYNTAX      FloatHundredths
    MAX-ACCESS  read-only
    STATUS      current
    DESCRIPTION "Maxmimum EDFA LBC transmit."
    ::= { ofxScgPtpPmEntry  11 }


ofxScgPtpPmTxEdfaLbcAve OBJECT-TYPE
    SYNTAX      FloatHundredths
    MAX-ACCESS  read-only
    STATUS      current
    DESCRIPTION "Average EDFA LBC transmit."
    ::= { ofxScgPtpPmEntry  12 }

ofxScgPtpPmRxEdfaOprMin OBJECT-TYPE
    SYNTAX      FloatHundredths
    MAX-ACCESS  read-only
    STATUS      current
    DESCRIPTION "Minimum EDFA power receive."
    ::= { ofxScgPtpPmEntry  13 }

ofxScgPtpPmRxEdfaOprMax OBJECT-TYPE
    SYNTAX      FloatHundredths
    MAX-ACCESS  read-only
    STATUS      current
    DESCRIPTION "Maximum EDFA power receive."
    ::= { ofxScgPtpPmEntry  14 }

ofxScgPtpPmRxEdfaOprAve OBJECT-TYPE
    SYNTAX      FloatHundredths
    MAX-ACCESS  read-only
    STATUS      current
    DESCRIPTION "Average EDFA power receive."
    ::= { ofxScgPtpPmEntry  15 }

ofxScgPtpPmRxEdfaOptMin OBJECT-TYPE
    SYNTAX      FloatHundredths
    MAX-ACCESS  read-only
    STATUS      current
    DESCRIPTION "Minimum EDFA power trasmit."
    ::= { ofxScgPtpPmEntry  16 }

ofxScgPtpPmRxEdfaOptMax OBJECT-TYPE
    SYNTAX      FloatHundredths
    MAX-ACCESS  read-only
    STATUS      current
    DESCRIPTION "Maximum EDFA power trasmit."
    ::= { ofxScgPtpPmEntry  17 }

ofxScgPtpPmRxEdfaOptAve OBJECT-TYPE
    SYNTAX      FloatHundredths
    MAX-ACCESS  read-only
    STATUS      current
    DESCRIPTION "Average EDFA power transmit."
    ::= { ofxScgPtpPmEntry  18 }

ofxScgPtpPmRxEdfaLbcMin OBJECT-TYPE
    SYNTAX      FloatHundredths
    MAX-ACCESS  read-only
    STATUS      current
    DESCRIPTION "Minimum EDFA LBC receive."
    ::= { ofxScgPtpPmEntry  19 }


ofxScgPtpPmRxEdfaLbcMax OBJECT-TYPE
    SYNTAX      FloatHundredths
    MAX-ACCESS  read-only
    STATUS      current
    DESCRIPTION "Maxmimum EDFA LBC receive."
    ::= { ofxScgPtpPmEntry  20 }


ofxScgPtpPmRxEdfaLbcAve OBJECT-TYPE
    SYNTAX      FloatHundredths
    MAX-ACCESS  read-only
    STATUS      current
    DESCRIPTION "Average EDFA LBC receive."
    ::= { ofxScgPtpPmEntry  21 }

ofxScgPtpPmQPreFecMin	OBJECT-TYPE
    SYNTAX      FloatHundredths
    MAX-ACCESS  read-only
    STATUS      current
    DESCRIPTION ""
    ::= { ofxScgPtpPmEntry 22  }

ofxScgPtpPmQPreFecMax	OBJECT-TYPE
    SYNTAX      FloatHundredths
    MAX-ACCESS  read-only
    STATUS      current
    DESCRIPTION ""
    ::= { ofxScgPtpPmEntry 23   }

ofxScgPtpPmQPreFecAve	OBJECT-TYPE
    SYNTAX      FloatHundredths
    MAX-ACCESS  read-only
    STATUS      current
    DESCRIPTION ""
    ::= { ofxScgPtpPmEntry 24  }

ofxScgPtpPmBerPreFecMin	OBJECT-TYPE
    SYNTAX      FloatHundredths
    MAX-ACCESS  read-only
    STATUS      current
    DESCRIPTION ""
    ::= { ofxScgPtpPmEntry 25  }

ofxScgPtpPmBerPreFecMax	OBJECT-TYPE
    SYNTAX      FloatHundredths
    MAX-ACCESS  read-only
    STATUS      current
    DESCRIPTION ""
    ::= { ofxScgPtpPmEntry 26  }

ofxScgPtpPmBerPreFecAve	OBJECT-TYPE
    SYNTAX      FloatHundredths
    MAX-ACCESS  read-only
    STATUS      current
    DESCRIPTION ""
    ::= { ofxScgPtpPmEntry 27  }

ofxScgPtpPmRealTable OBJECT-TYPE
    SYNTAX      SEQUENCE OF OfxScgPtpPmRealEntry
    MAX-ACCESS  not-accessible
    STATUS      current
    DESCRIPTION
        "A list of OfxScgPtpPmReal entries. Each entry is uniquely identified by the value of ifIndex."
    ::= { ofxScgPtpPmMIB 1 }

ofxScgPtpPmRealEntry  OBJECT-TYPE
    SYNTAX      OfxScgPtpPmRealEntry
    MAX-ACCESS  not-accessible
    STATUS      current
    DESCRIPTION
        "A  ofxScgPtp entry containing real-time performance information pertaining to Infinera
         ofxScgPtp interfaces. This table is a subclass of IfCommon."
    INDEX { ifIndex }
    ::= { ofxScgPtpPmRealTable 1 }


OfxScgPtpPmRealEntry  ::= SEQUENCE {
    ofxScgPtpPmRealChanScgOpt       FloatHundredths,
    ofxScgPtpPmRealChanScgOpr       FloatHundredths,
    ofxScgPtpPmRealTxEdfaOpr        FloatHundredths,
    ofxScgPtpPmRealTxEdfaOpt        FloatHundredths,
    ofxScgPtpPmRealTxEdfaLbc        FloatHundredths,
    ofxScgPtpPmRealRxEdfaOpr        FloatHundredths,
    ofxScgPtpPmRealRxEdfaOpt        FloatHundredths,
    ofxScgPtpPmRealRxEdfaLbc        FloatHundredths,
	ofxScgPtpPmRealQPreFec          FloatHundredths,
    ofxScgPtpPmRealBerPreFec		FloatHundredths

}

ofxScgPtpPmRealChanScgOpt OBJECT-TYPE
    SYNTAX      FloatHundredths
    MAX-ACCESS  read-only
    STATUS      current
    DESCRIPTION "Total OfxScg optical power trasmit."
    ::= { ofxScgPtpPmRealEntry  1 }

ofxScgPtpPmRealChanScgOpr OBJECT-TYPE
    SYNTAX      FloatHundredths
    MAX-ACCESS  read-only
    STATUS      current
    DESCRIPTION "Total OfxScg optical power receive."
    ::= { ofxScgPtpPmRealEntry  2 }

ofxScgPtpPmRealTxEdfaOpr OBJECT-TYPE
    SYNTAX      FloatHundredths
    MAX-ACCESS  read-only
    STATUS      current
    DESCRIPTION "Total Edfa power transmit."
    ::= { ofxScgPtpPmRealEntry  3 }

ofxScgPtpPmRealTxEdfaOpt OBJECT-TYPE
    SYNTAX      FloatHundredths
    MAX-ACCESS  read-only
    STATUS      current
    DESCRIPTION "Total Edfa power receive."
    ::= { ofxScgPtpPmRealEntry  4 }

ofxScgPtpPmRealTxEdfaLbc OBJECT-TYPE
    SYNTAX      FloatHundredths
    MAX-ACCESS  read-only
    STATUS      current
    DESCRIPTION "EdfaLbc."
    ::= { ofxScgPtpPmRealEntry  5 }

ofxScgPtpPmRealRxEdfaOpr OBJECT-TYPE
    SYNTAX      FloatHundredths
    MAX-ACCESS  read-only
    STATUS      current
    DESCRIPTION "EdfaOpr."
    ::= { ofxScgPtpPmRealEntry  6 }

ofxScgPtpPmRealRxEdfaOpt OBJECT-TYPE
    SYNTAX      FloatHundredths
    MAX-ACCESS  read-only
    STATUS      current
    DESCRIPTION "Total Edfa power trasmit."
    ::= { ofxScgPtpPmRealEntry  7 }

ofxScgPtpPmRealRxEdfaLbc OBJECT-TYPE
    SYNTAX      FloatHundredths
    MAX-ACCESS  read-only
    STATUS      current
    DESCRIPTION "Total EdfaLBC."
    ::= { ofxScgPtpPmRealEntry  8 }

ofxScgPtpPmRealQPreFec	OBJECT-TYPE
    SYNTAX      FloatHundredths
    MAX-ACCESS  read-only
    STATUS      current
    DESCRIPTION ""
    ::= { ofxScgPtpPmRealEntry  9 }

ofxScgPtpPmRealBerPreFec OBJECT-TYPE
    SYNTAX      FloatHundredths
    MAX-ACCESS  read-only
    STATUS      current
    DESCRIPTION ""
    ::= { ofxScgPtpPmRealEntry  10 }

-- Conformance Statements
ofxScgPtpPmConformance    OBJECT IDENTIFIER ::= { ofxScgPtpPmMIB 3 }
ofxScgPtpPmCompliances    OBJECT IDENTIFIER ::= { ofxScgPtpPmConformance 1 }
ofxScgPtpPmGroups         OBJECT IDENTIFIER ::= { ofxScgPtpPmConformance 2 }

ofxScgPtpPmCompliance MODULE-COMPLIANCE
    STATUS current
    DESCRIPTION
    "Describes the requirements for conformance to the  ofxScgPtp-MIB"
    MODULE
        MANDATORY-GROUPS { ofxScgPtpPmGroup }
    ::= { ofxScgPtpPmCompliances 1 }

ofxScgPtpPmRealCompliance MODULE-COMPLIANCE
    STATUS current
    DESCRIPTION
    "Describes the requirements for conformance to the OfxScgPtpPmReal-MIB"
    MODULE
        MANDATORY-GROUPS { ofxScgPtpPmRealGroup }
    ::= { ofxScgPtpPmCompliances 2 }

ofxScgPtpPmGroup OBJECT-GROUP
    OBJECTS {
		ofxScgPtpPmTimestamp,
		ofxScgPtpPmSampleDuration,
        ofxScgPtpPmValidity,
        ofxScgPtpPmTxEdfaOprMin,
        ofxScgPtpPmTxEdfaOprMax,
        ofxScgPtpPmTxEdfaOprAve,
        ofxScgPtpPmTxEdfaOptMin,
        ofxScgPtpPmTxEdfaOptMax,
        ofxScgPtpPmTxEdfaOptAve,
        ofxScgPtpPmTxEdfaLbcMin,
        ofxScgPtpPmTxEdfaLbcMax,
        ofxScgPtpPmTxEdfaLbcAve,
        ofxScgPtpPmRxEdfaOprMin,
        ofxScgPtpPmRxEdfaOprMax,
        ofxScgPtpPmRxEdfaOprAve,
        ofxScgPtpPmRxEdfaOptMin,
        ofxScgPtpPmRxEdfaOptMax,
        ofxScgPtpPmRxEdfaOptAve,
        ofxScgPtpPmRxEdfaLbcMin,
        ofxScgPtpPmRxEdfaLbcMax,
        ofxScgPtpPmRxEdfaLbcAve,
		ofxScgPtpPmQPreFecMin,
		ofxScgPtpPmQPreFecMax,
		ofxScgPtpPmQPreFecAve,
		ofxScgPtpPmBerPreFecMin,
		ofxScgPtpPmBerPreFecMax,
		ofxScgPtpPmBerPreFecAve

    }
    STATUS current
    DESCRIPTION
        " A collection of objects for reading the historical performance of the  ofxScgPtp."
    ::= { ofxScgPtpPmGroups 1 }

ofxScgPtpPmRealGroup OBJECT-GROUP
    OBJECTS {
        ofxScgPtpPmRealChanScgOpt,
        ofxScgPtpPmRealChanScgOpr,
        ofxScgPtpPmRealTxEdfaOpr,
        ofxScgPtpPmRealTxEdfaOpt,
        ofxScgPtpPmRealTxEdfaLbc,
        ofxScgPtpPmRealRxEdfaOpr,
        ofxScgPtpPmRealRxEdfaOpt,
        ofxScgPtpPmRealRxEdfaLbc,
		ofxScgPtpPmRealQPreFec,
		ofxScgPtpPmRealBerPreFec
    }
    STATUS current
    DESCRIPTION
        " A collection of objects for reading the real-time performance of the  ofxScgPtp."
    ::= { ofxScgPtpPmGroups 2 }

END
