-- ***************************************************************
-- INFINERA-ENTITY-TOM-MIB
--
-- October 2008, Sharfuddin Syed / Narendra Gupta
--
--
-- Copyright (c) 2008-2012 by Infinera Inc.
-- All rights reserved.
-- ****************************************************************

INFINERA-ENTITY-TOM-MIB DEFINITIONS ::= BEGIN

IMPORTS
    Integer32,
    OBJECT-TYPE, MODULE-IDENTITY, Unsigned32       FROM SNMPv2-SMI
    OBJECT-GROUP, MODULE-COMPLIANCE                FROM SNMPv2-CONF
    RowStatus, DisplayString, TruthValue           FROM SNMPv2-TC
    entLPPhysicalIndex                             FROM ENTITY-MIB
    equipment                                      FROM INFINERA-REG-MIB
    InfnEqptType, InfnPhyMode                      FROM INFINERA-TC-MIB;

tomMIB MODULE-IDENTITY
    LAST-UPDATED  "200810200000Z"
    ORGANIZATION
        "INFINERA"
    CONTACT-INFO
        "Infinera
        169 Java Drive
        Sunnyvale, CA - 94089

        Contact : Technical Support
        Email   : support@infinera.com
        Phone   : 1-877-INF-5288"
    DESCRIPTION
        "This MIB is modeling for TOM equipment table."

::= { equipment 9 }

tomConformance       OBJECT IDENTIFIER ::= { tomMIB 3 }
tomCompliances       OBJECT IDENTIFIER ::= { tomConformance 1 }
tomGroups            OBJECT IDENTIFIER ::= { tomConformance 2 }

tomTable  OBJECT-TYPE
    SYNTAX SEQUENCE OF TomEntry
    MAX-ACCESS not-accessible
    STATUS     current
    DESCRIPTION
        "This table contains all TOM modules that are currently present in a network element.
        "
    ::= { tomMIB 1 }

tomEntry  OBJECT-TYPE
    SYNTAX     TomEntry
    MAX-ACCESS not-accessible
    STATUS     current
    DESCRIPTION
        "A row in the TOM table. Each row in the table is identified with a unique entPhysicalIndexID.
        "
    INDEX { entLPPhysicalIndex }
    ::= { tomTable 1 }

TomEntry ::= SEQUENCE {
    tomMoId                   DisplayString,
    tomProvEqptType           InfnEqptType,
    tomSFPState               INTEGER,
    tomTxPowerThresholdPcentge Unsigned32,
    tomRxPowerThresholdPcentge  Unsigned32,
    tomProvisionedFrequency   Unsigned32,
    tomInstalledFrequency     Unsigned32,
    tomProvisionedWavelength  Unsigned32,
    tomInstalledWavelength    Unsigned32,
    tomPhyMode                  InfnPhyMode,
    tomSerdesOverride           TruthValue,
    tomTxAmplitude              Integer32,
    tomTxVod                    Integer32,
    tomTxPost1                  Integer32,
    tomTxPost2                  Integer32,
    tomTxPre                    Integer32,
    tomTxIDrv                   Integer32,
    tomTxIPreDrv                Integer32,
    tomTxPoshUp                 Integer32,
    tomTxPoshDn                 Integer32,
    tomTxPost3                  Integer32,
    tomTxEq                     Integer32,
    tomTx12Eq                   Integer32,
    tomTx34Eq                   Integer32,
    tomRx12Emphasis             Integer32,
    tomRx34Emphasis             Integer32,
    tomRx12Amplitude            Integer32,
    tomRx34Amplitude            Integer32,
    tomHighPowerEnable          TruthValue,
    tomRxCtleOverride           TruthValue,
    tomRxCtleEqValue            Integer32,
    tomIs3rdPartyTom            TruthValue
}

tomMoId  OBJECT-TYPE
    SYNTAX     DisplayString
    MAX-ACCESS read-create
    STATUS     current
    DESCRIPTION
        "This is the primary Key of the objects e.g 1-A-3-1-1"
    ::= { tomEntry 1 }

tomProvEqptType  OBJECT-TYPE
    SYNTAX     InfnEqptType
    MAX-ACCESS read-write
    STATUS     current
    DESCRIPTION
        "The configured TOM type."
    ::= { tomEntry 2 }

tomSFPState     OBJECT-TYPE
    SYNTAX      INTEGER {
        locked(1),
        maintenance(2),
        unlocked (3)
    }
    MAX-ACCESS read-only
    STATUS      current
    DESCRIPTION ""
    ::= { tomEntry 3 }

tomTxPowerThresholdPcentge  OBJECT-TYPE
    SYNTAX      Unsigned32
    MAX-ACCESS  read-write
    STATUS      current
    DESCRIPTION ""
    ::= { tomEntry 4 }

tomRxPowerThresholdPcentge  OBJECT-TYPE
    SYNTAX      Unsigned32
    MAX-ACCESS  read-write
    STATUS      current
    DESCRIPTION ""
    ::= { tomEntry 5 }

tomProvisionedFrequency  OBJECT-TYPE
    SYNTAX     Unsigned32
    MAX-ACCESS read-write
    STATUS     current
    DESCRIPTION
        "This parameter is valid only for the DWDM-LR2,DWA-LR2 & MR_DWDM-LR2 TOMs. This attribute is
         used to provision the 10G DWDM TOM with the frequency value."
    ::= { tomEntry 6 }

tomInstalledFrequency  OBJECT-TYPE
    SYNTAX     Unsigned32
    MAX-ACCESS read-only
    STATUS     current
    DESCRIPTION
        "This parameter is valid only for the DWDM-LR2,DWA-LR2 & MR_DWDM-LR2 TOMs. This attribute
        is used to report the value of the frequency that is currently supported by the installed TOM."
    ::= { tomEntry 7 }

tomProvisionedWavelength  OBJECT-TYPE
    SYNTAX     Unsigned32
    MAX-ACCESS read-only
    STATUS     current
    DESCRIPTION
        "This parameter is valid only for the CWDM-LR2 TOMs. This attribute
        is used to report the value of the Wavelength that is currently supported by the installed TOM."
    ::= { tomEntry 8 }

tomInstalledWavelength OBJECT-TYPE
    SYNTAX     Unsigned32
    MAX-ACCESS read-only
    STATUS     current
    DESCRIPTION
        "This parameter is valid only for the CWDM-LR2 TOMs. This attribute
        is used to report the value of the Wavelength that is currently supported by the installed TOM."
    ::= { tomEntry 9 }

tomPhyMode  OBJECT-TYPE
    SYNTAX     InfnPhyMode
    MAX-ACCESS read-write
    STATUS     current
    DESCRIPTION
        ""
    ::= { tomEntry 10 }

tomSerdesOverride  OBJECT-TYPE
    SYNTAX     TruthValue
    MAX-ACCESS read-write
    STATUS     current
    DESCRIPTION
        ""
    ::= { tomEntry 11 }

tomTxAmplitude  OBJECT-TYPE
    SYNTAX     Integer32
    MAX-ACCESS read-write
    STATUS     current
    DESCRIPTION
        ""
    ::= { tomEntry 12 }

tomTxVod  OBJECT-TYPE
    SYNTAX     Integer32
    MAX-ACCESS read-write
    STATUS     current
    DESCRIPTION
        ""
    ::= { tomEntry 13 }

tomTxPost1  OBJECT-TYPE
    SYNTAX     Integer32
    MAX-ACCESS read-write
    STATUS     current
    DESCRIPTION
        ""
    ::= { tomEntry 14 }

tomTxPost2  OBJECT-TYPE
    SYNTAX     Integer32
    MAX-ACCESS read-write
    STATUS     current
    DESCRIPTION
        ""
    ::= { tomEntry 15 }

tomTxPre  OBJECT-TYPE
    SYNTAX     Integer32
    MAX-ACCESS read-write
    STATUS     current
    DESCRIPTION
        ""
    ::= { tomEntry 16 }

tomTxIDrv  OBJECT-TYPE
    SYNTAX     Integer32
    MAX-ACCESS read-write
    STATUS     current
    DESCRIPTION
        ""
    ::= { tomEntry 17 }

tomTxIPreDrv  OBJECT-TYPE
    SYNTAX     Integer32
    MAX-ACCESS read-write
    STATUS     current
    DESCRIPTION
        ""
    ::= { tomEntry 18 }

tomTxPoshUp  OBJECT-TYPE
    SYNTAX     Integer32
    MAX-ACCESS read-write
    STATUS     current
    DESCRIPTION
        ""
    ::= { tomEntry 19 }

tomTxPoshDn  OBJECT-TYPE
    SYNTAX     Integer32
    MAX-ACCESS read-write
    STATUS     current
    DESCRIPTION
        ""
    ::= { tomEntry 20 }

tomTxPost3  OBJECT-TYPE
    SYNTAX     Integer32
    MAX-ACCESS read-write
    STATUS     current
    DESCRIPTION
        ""
    ::= { tomEntry 21 }

tomTxEq  OBJECT-TYPE
    SYNTAX     Integer32
    MAX-ACCESS read-write
    STATUS     current
    DESCRIPTION
        ""
    ::= { tomEntry 22 }

tomTx12Eq  OBJECT-TYPE
    SYNTAX     Integer32
    MAX-ACCESS read-write
    STATUS     current
    DESCRIPTION
        ""
    ::= { tomEntry 23 }

tomTx34Eq  OBJECT-TYPE
    SYNTAX     Integer32
    MAX-ACCESS read-write
    STATUS     current
    DESCRIPTION
        ""
    ::= { tomEntry 24 }

tomRx12Emphasis  OBJECT-TYPE
    SYNTAX     Integer32
    MAX-ACCESS read-write
    STATUS     current
    DESCRIPTION
        ""
    ::= { tomEntry 25 }

tomRx34Emphasis  OBJECT-TYPE
    SYNTAX     Integer32
    MAX-ACCESS read-write
    STATUS     current
    DESCRIPTION
        ""
    ::= { tomEntry 26 }

tomRx12Amplitude  OBJECT-TYPE
    SYNTAX     Integer32
    MAX-ACCESS read-write
    STATUS     current
    DESCRIPTION
        ""
    ::= { tomEntry 27 }

tomRx34Amplitude  OBJECT-TYPE
    SYNTAX     Integer32
    MAX-ACCESS read-write
    STATUS     current
    DESCRIPTION
        ""
    ::= { tomEntry 28 }

tomHighPowerEnable OBJECT-TYPE
    SYNTAX     TruthValue
    MAX-ACCESS read-write
    STATUS     current
    DESCRIPTION
        ""
    ::= { tomEntry 29 }

tomRxCtleOverride OBJECT-TYPE
    SYNTAX     TruthValue
    MAX-ACCESS read-write
    STATUS     current
    DESCRIPTION
        ""
    ::= { tomEntry 30 }

tomRxCtleEqValue OBJECT-TYPE
    SYNTAX     Integer32
    MAX-ACCESS read-write
    STATUS     current
    DESCRIPTION
        ""
    ::= { tomEntry 31 }

tomIs3rdPartyTom OBJECT-TYPE
    SYNTAX     TruthValue
    MAX-ACCESS read-only
    STATUS     current
    DESCRIPTION
        ""
    ::= { tomEntry 32 }

tomCompliance  MODULE-COMPLIANCE
    STATUS     current
    DESCRIPTION
        ""
    MODULE
        MANDATORY-GROUPS { tomGroup }
    ::= { tomCompliances 1 }

tomGroup  OBJECT-GROUP
    OBJECTS { tomInstalledFrequency,
        tomMoId,
        tomProvEqptType,
        tomSFPState,
        tomTxPowerThresholdPcentge,
        tomRxPowerThresholdPcentge,
        tomProvisionedFrequency,
        tomProvisionedWavelength,
        tomInstalledWavelength,
        tomPhyMode,
        tomSerdesOverride,
        tomTxAmplitude,
        tomTxVod,
        tomTxPost1,
        tomTxPost2,
        tomTxPre,
        tomTxIDrv,
        tomTxIPreDrv,
        tomTxPoshUp,
        tomTxPoshDn,
        tomTxPost3,
        tomTxEq,
        tomTx12Eq,
        tomTx34Eq,
        tomRx12Emphasis,
        tomRx34Emphasis,
        tomRx12Amplitude,
        tomRx34Amplitude,
        tomHighPowerEnable,
        tomRxCtleOverride,
        tomRxCtleEqValue,
        tomIs3rdPartyTom
    }
    STATUS     current
    DESCRIPTION
        ""
    ::= { tomGroups 1 }
END
