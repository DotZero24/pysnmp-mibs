-- ***************************************************************
-- INFINERA-ENTITY-OFIX-MIB
--
--
-- Copyright (c) 2011-2015 by Infinera Inc.
-- All rights reserved.
-- ****************************************************************

INFINERA-ENTITY-OFIX-MIB DEFINITIONS ::= BEGIN

IMPORTS
    OBJECT-TYPE, MODULE-IDENTITY        	FROM SNMPv2-SMI
    OBJECT-GROUP, MODULE-COMPLIANCE     	FROM SNMPv2-CONF
    DisplayString            	            FROM SNMPv2-TC
    entLPPhysicalIndex                  	FROM ENTITY-MIB
    equipment                           	FROM INFINERA-REG-MIB
    InfnEqptType, InfnOtnOtuType,
	InfnEnforcementMode,
	FloatTenths           					FROM INFINERA-TC-MIB;

ofixMIB MODULE-IDENTITY
    LAST-UPDATED  "201505270000Z"
    ORGANIZATION "INFINERA"
    CONTACT-INFO
        "Infinera
        169 Java Drive
        Sunnyvale, CA - 94089

        Contact : Technical Support
        Email   : support@infinera.com
        Phone   : 1-877-INF-5288 "
        DESCRIPTION
        "This MIB is modeling for OFIX equipment table"

::= { equipment 45 }

ofixConformance       OBJECT IDENTIFIER ::= { ofixMIB 3 }
ofixCompliances       OBJECT IDENTIFIER ::= { ofixConformance 1 }
ofixGroups            OBJECT IDENTIFIER ::= { ofixConformance 2 }

ofixTable  OBJECT-TYPE
    SYNTAX SEQUENCE OF OfixEntry
    MAX-ACCESS not-accessible
    STATUS     current
    DESCRIPTION
        "This table contains all OFIX modules that are currently present in a network element.
        "
    ::= { ofixMIB 1 }

ofixEntry  OBJECT-TYPE
    SYNTAX     OfixEntry
    MAX-ACCESS not-accessible
    STATUS     current
    DESCRIPTION
        "A row in the OFIX table. Each row in the table is identified with a unique entPhysicalIndexID."
    INDEX { entLPPhysicalIndex }
    ::= { ofixTable 1 }

OfixEntry ::= SEQUENCE {
   ofixMoId                                  DisplayString,
   ofixProvEqptType                          InfnEqptType,
   ofixOTNContainerRepresentation            InfnOtnOtuType,
   ofixPicDspVer                             DisplayString,
   ofixMaxFruGain                            FloatTenths,
   ofixRxEdfaOutputPowerTarget               FloatTenths,
   ofixRxEdfaGain                            FloatTenths,
   ofixRecommendedGain                       FloatTenths,
   ofixBwQmax                                FloatTenths,
   ofixBwQused                               FloatTenths,
   ofixBwBmax                                FloatTenths,
   ofixBwBused                               FloatTenths,
   ofixBwUsgWaterMarkGranularity             FloatTenths,
   ofixAvailableTunableSuperChNumbers        DisplayString
}

ofixMoId     OBJECT-TYPE
    SYNTAX      DisplayString
    MAX-ACCESS  read-write
    STATUS      current
    DESCRIPTION ""
    ::= { ofixEntry 1 }

ofixProvEqptType     OBJECT-TYPE
    SYNTAX      InfnEqptType
    MAX-ACCESS  read-write
    STATUS      current
    DESCRIPTION ""
    ::= { ofixEntry 2 }

ofixOTNContainerRepresentation OBJECT-TYPE
    SYNTAX      InfnOtnOtuType
    MAX-ACCESS  read-write
    STATUS      current
    DESCRIPTION ""
    ::= { ofixEntry  3 }

ofixPicDspVer    OBJECT-TYPE
    SYNTAX      DisplayString
    MAX-ACCESS  read-only
    STATUS      current
    DESCRIPTION ""
    ::= { ofixEntry  4 }

ofixMaxFruGain   OBJECT-TYPE
    SYNTAX      FloatTenths
    MAX-ACCESS  read-only
    STATUS      current
    DESCRIPTION ""
    ::= { ofixEntry  5 }

ofixRecommendedGain OBJECT-TYPE
    SYNTAX          FloatTenths
    MAX-ACCESS      read-only
    STATUS          current
    DESCRIPTION     ""
    ::= { ofixEntry 6 }

ofixRxEdfaOutputPowerTarget  OBJECT-TYPE
    SYNTAX      FloatTenths
    MAX-ACCESS  read-only
    STATUS      current
    DESCRIPTION ""
    ::= { ofixEntry  7 }

ofixRxEdfaGain   OBJECT-TYPE
    SYNTAX      FloatTenths
    MAX-ACCESS  read-write
    STATUS      current
    DESCRIPTION ""
    ::= { ofixEntry  8 }

ofixBwQmax   OBJECT-TYPE
    SYNTAX      FloatTenths
    MAX-ACCESS  read-write
    STATUS      current
    DESCRIPTION ""
    ::= { ofixEntry 9 }

ofixBwQused      OBJECT-TYPE
    SYNTAX      FloatTenths
    MAX-ACCESS  read-write
    STATUS      current
    DESCRIPTION ""
    ::= { ofixEntry 10 }

ofixBwBmax       OBJECT-TYPE
    SYNTAX      FloatTenths
    MAX-ACCESS  read-write
    STATUS      current
    DESCRIPTION ""
    ::= { ofixEntry 11 }

ofixBwBused      OBJECT-TYPE
    SYNTAX      FloatTenths
    MAX-ACCESS  read-write
    STATUS      current
    DESCRIPTION ""
    ::= { ofixEntry 12 }

ofixBwUsgWaterMarkGranularity    OBJECT-TYPE
    SYNTAX      FloatTenths
    MAX-ACCESS  read-write
    STATUS      current
    DESCRIPTION ""
    ::= { ofixEntry 13 }

ofixAvailableTunableSuperChNumbers OBJECT-TYPE
    SYNTAX      DisplayString
    MAX-ACCESS  read-only
    STATUS      current
    DESCRIPTION ""
    ::= { ofixEntry  14 }

ofixCompliance  MODULE-COMPLIANCE
    STATUS      current
    DESCRIPTION ""
    MODULE
        MANDATORY-GROUPS { ofixGroup }
    ::= { ofixCompliances 1 }

ofixGroup  OBJECT-GROUP
    OBJECTS {
        ofixMoId,
        ofixProvEqptType,
        ofixPicDspVer,
        ofixMaxFruGain,
        ofixRxEdfaOutputPowerTarget,
        ofixRxEdfaGain,
        ofixOTNContainerRepresentation,
        ofixRecommendedGain,
        ofixBwQmax,
        ofixBwQused,
        ofixBwBmax,
        ofixBwBused,
        ofixBwUsgWaterMarkGranularity,
        ofixAvailableTunableSuperChNumbers
    }
    STATUS     current
    DESCRIPTION
        ""
    ::= { ofixGroups 1 }
END
