-- *****************************************************************
-- INFINERA-PM-FMMFSCGPTP-MIB
--
-- April 2015, Mithun Murthy
--
--
-- Copyright (c) 2008-2013 by Infinera Inc.
-- All rights reserved.
-- ****************************************************************

INFINERA-PM-FMMFSCGPTP-MIB DEFINITIONS ::= BEGIN

IMPORTS
    MODULE-IDENTITY, OBJECT-TYPE,
    Integer32                                   FROM SNMPv2-SMI
    MODULE-COMPLIANCE, OBJECT-GROUP             FROM SNMPv2-CONF
    TruthValue                                  FROM SNMPv2-TC
    ifIndex                                     FROM IF-MIB
    FloatHundredths, InfnSampleDuration         FROM INFINERA-TC-MIB
    perfMon                                     FROM INFINERA-REG-MIB;


fmmfScgPtpPmMIB MODULE-IDENTITY
    LAST-UPDATED  "201504180000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION      "201504180000Z"
    DESCRIPTION
        "First Version"
    ::= { perfMon 49 }


fmmfScgPtpPmTable OBJECT-TYPE
    SYNTAX      SEQUENCE OF FmmfScgPtpPmEntry
    MAX-ACCESS  not-accessible
    STATUS      current
    DESCRIPTION
        "A list of FmmfScgPtpPm entries. Each entry is uniquely identified by the value of ifIndex."
    ::= { fmmfScgPtpPmMIB 2 }

fmmfScgPtpPmEntry  OBJECT-TYPE
    SYNTAX      FmmfScgPtpPmEntry
    MAX-ACCESS  not-accessible
    STATUS      current
    DESCRIPTION
        "A FmmfScgPtp entry containing historical performance information pertaining to Infinera FMMFSCGPTP.
        This table is a subclass of IfCommon. Entries will exist in this table only for interfaces
        of type FMMFSCGPTP."
    INDEX { ifIndex, fmmfScgPtpPmSampleDuration, fmmfScgPtpPmTimestamp}
    ::= { fmmfScgPtpPmTable 1 }


FmmfScgPtpPmEntry  ::= SEQUENCE {
   fmmfScgPtpPmTimestamp            Integer32,
   fmmfScgPtpPmSampleDuration       INTEGER,
   fmmfScgPtpPmValidity             TruthValue,
   fmmfScgPtpPmCmnScgOptMin         FloatHundredths,
   fmmfScgPtpPmCmnScgOptMax         FloatHundredths,
   fmmfScgPtpPmCmnScgOptAve         FloatHundredths,
   fmmfScgPtpPmCmnScgOprMin         FloatHundredths,
   fmmfScgPtpPmCmnScgOprMax         FloatHundredths,
   fmmfScgPtpPmCmnScgOprAve         FloatHundredths,
   fmmfScgPtpPmOptOsaTapRatioMin    FloatHundredths,
   fmmfScgPtpPmOptOsaTapRatioMax    FloatHundredths,
   fmmfScgPtpPmOptOsaTapRatioAve    FloatHundredths
}


fmmfScgPtpPmTimestamp OBJECT-TYPE
    SYNTAX      Integer32 (0..2147483647)
    MAX-ACCESS  not-accessible
    STATUS      current
    DESCRIPTION
        "End Time stamp for this interval. If this time is later than the current time,then the data for this bucket is currently being collected."
    ::= { fmmfScgPtpPmEntry  1 }


fmmfScgPtpPmSampleDuration OBJECT-TYPE
    SYNTAX      INTEGER {
        fifteenMinutes(1),
        day(2)
    }
    MAX-ACCESS  not-accessible
    STATUS      current
    DESCRIPTION
        "The duration of this sample."
    ::= { fmmfScgPtpPmEntry  2 }

fmmfScgPtpPmValidity OBJECT-TYPE
    SYNTAX      TruthValue
    MAX-ACCESS  read-only
    STATUS      current
    DESCRIPTION "Flag indicating if data was valid for the entire interval"
    ::= { fmmfScgPtpPmEntry  3 }


fmmfScgPtpPmCmnScgOptMin OBJECT-TYPE
    SYNTAX      FloatHundredths
    MAX-ACCESS  read-only
    STATUS      current
    DESCRIPTION "Minimum FmmfScg optical power min."
    ::= { fmmfScgPtpPmEntry  4 }


fmmfScgPtpPmCmnScgOptMax OBJECT-TYPE
    SYNTAX      FloatHundredths
    MAX-ACCESS  read-only
    STATUS      current
    DESCRIPTION "Maximum FmmfScg optical power max."
    ::= { fmmfScgPtpPmEntry  5 }


fmmfScgPtpPmCmnScgOptAve OBJECT-TYPE
    SYNTAX      FloatHundredths
    MAX-ACCESS  read-only
    STATUS      current
    DESCRIPTION "Average FmmfScg optical power ave."
    ::= { fmmfScgPtpPmEntry  6 }


fmmfScgPtpPmCmnScgOprMin OBJECT-TYPE
    SYNTAX      FloatHundredths
    MAX-ACCESS  read-only
    STATUS      current
    DESCRIPTION "Minimum FmmfScg optical power min."
    ::= { fmmfScgPtpPmEntry  7}


fmmfScgPtpPmCmnScgOprMax OBJECT-TYPE
    SYNTAX      FloatHundredths
    MAX-ACCESS  read-only
    STATUS      current
    DESCRIPTION "Maximum FmmfScg optical power max."
    ::= { fmmfScgPtpPmEntry  8}


fmmfScgPtpPmCmnScgOprAve OBJECT-TYPE
    SYNTAX      FloatHundredths
    MAX-ACCESS  read-only
    STATUS      current
    DESCRIPTION "Average FmmfScg optical power ave."
    ::= { fmmfScgPtpPmEntry  9}


fmmfScgPtpPmOptOsaTapRatioMin OBJECT-TYPE
    SYNTAX      FloatHundredths
    MAX-ACCESS  read-only
    STATUS      current
    DESCRIPTION "Minimum FmmfScg optical power min."
    ::= { fmmfScgPtpPmEntry  10}


fmmfScgPtpPmOptOsaTapRatioMax OBJECT-TYPE
    SYNTAX      FloatHundredths
    MAX-ACCESS  read-only
    STATUS      current
    DESCRIPTION "Maximum FmmfScg optical power max."
    ::= { fmmfScgPtpPmEntry  11}


fmmfScgPtpPmOptOsaTapRatioAve  OBJECT-TYPE
    SYNTAX      FloatHundredths
    MAX-ACCESS  read-only
    STATUS      current
    DESCRIPTION "Average FmmfScg optical power ave."
    ::= { fmmfScgPtpPmEntry  12 }



fmmfScgPtpPmRealTable OBJECT-TYPE
    SYNTAX      SEQUENCE OF FmmfScgPtpPmRealEntry
    MAX-ACCESS  not-accessible
    STATUS      current
    DESCRIPTION
        "A list of FmmfScgPtpPmReal entries. Each entry is uniquely identified by the value of ifIndex."
    ::= { fmmfScgPtpPmMIB 1 }

fmmfScgPtpPmRealEntry  OBJECT-TYPE
    SYNTAX      FmmfScgPtpPmRealEntry
    MAX-ACCESS  not-accessible
    STATUS      current
    DESCRIPTION
        "A  fmmfScgPtp entry containing real-time performance information pertaining to Infinera
         fmmfScgPtp interfaces. This table is a subclass of IfCommon."
    INDEX { ifIndex }
    ::= { fmmfScgPtpPmRealTable 1 }


FmmfScgPtpPmRealEntry  ::= SEQUENCE {
    fmmfScgPtpPmRealCmnScgOpt       FloatHundredths,
    fmmfScgPtpPmRealCmnScgOpr       FloatHundredths,
    fmmfScgPtpPmRealOptOsaTapRatio  FloatHundredths
}

fmmfScgPtpPmRealCmnScgOpt OBJECT-TYPE
    SYNTAX      FloatHundredths
    MAX-ACCESS  read-only
    STATUS      current
    DESCRIPTION "Total FmmfScg optical power trasmit."
    ::= { fmmfScgPtpPmRealEntry  1 }


fmmfScgPtpPmRealCmnScgOpr OBJECT-TYPE
    SYNTAX      FloatHundredths
    MAX-ACCESS  read-only
    STATUS      current
    DESCRIPTION "Total FmmfScg optical power receive."
    ::= { fmmfScgPtpPmRealEntry  2 }


fmmfScgPtpPmRealOptOsaTapRatio OBJECT-TYPE
    SYNTAX      FloatHundredths
    MAX-ACCESS  read-only
    STATUS      current
    DESCRIPTION "Total FmmfScg optical power receive."
    ::= { fmmfScgPtpPmRealEntry  3 }

-- Conformance Statements
fmmfScgPtpPmConformance    OBJECT IDENTIFIER ::= { fmmfScgPtpPmMIB 3 }
fmmfScgPtpPmCompliances    OBJECT IDENTIFIER ::= { fmmfScgPtpPmConformance 1 }
fmmfScgPtpPmGroups         OBJECT IDENTIFIER ::= { fmmfScgPtpPmConformance 2 }

fmmfScgPtpPmCompliance MODULE-COMPLIANCE
    STATUS current
    DESCRIPTION
    "Describes the requirements for conformance to the  fmmfScgPtp-MIB"
    MODULE
        MANDATORY-GROUPS { fmmfScgPtpPmGroup }
    ::= { fmmfScgPtpPmCompliances 1 }

fmmfScgPtpPmRealCompliance MODULE-COMPLIANCE
    STATUS current
    DESCRIPTION
    "Describes the requirements for conformance to the FmmfScgPtpPmReal-MIB"
    MODULE
        MANDATORY-GROUPS { fmmfScgPtpPmRealGroup }
    ::= { fmmfScgPtpPmCompliances 2 }

fmmfScgPtpPmGroup OBJECT-GROUP
    OBJECTS {
        fmmfScgPtpPmTimestamp,
        fmmfScgPtpPmSampleDuration,
        fmmfScgPtpPmValidity,
        fmmfScgPtpPmCmnScgOptMin,
        fmmfScgPtpPmCmnScgOptMax,
        fmmfScgPtpPmCmnScgOptAve,
        fmmfScgPtpPmCmnScgOprMin,
        fmmfScgPtpPmCmnScgOprMax,
        fmmfScgPtpPmCmnScgOprAve,
        fmmfScgPtpPmOptOsaTapRatioMin,
        fmmfScgPtpPmOptOsaTapRatioMax,
        fmmfScgPtpPmOptOsaTapRatioAve
    }
    STATUS current
    DESCRIPTION
        " A collection of objects for reading the historical performance of the  fmmfScgPtp."
    ::= { fmmfScgPtpPmGroups 1 }

fmmfScgPtpPmRealGroup OBJECT-GROUP
    OBJECTS {
        fmmfScgPtpPmRealCmnScgOpt,
        fmmfScgPtpPmRealCmnScgOpr,
        fmmfScgPtpPmRealOptOsaTapRatio
    }
    STATUS current
    DESCRIPTION
        " A collection of objects for reading the real-time performance of the  fmmfScgPtp."
    ::= { fmmfScgPtpPmGroups 2 }

END
