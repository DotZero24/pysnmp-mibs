-- *****************************************************************
-- INFINERA-TP-FCCLIENTCTP-MIB
-- October 2008, Sharfuddin Syed / Narendra Gupta
-- Copyright (c) 2009-2012 by Infinera Inc.
-- All rights reserved.
-- ****************************************************************

INFINERA-TP-FCCLIENTCTP-MIB DEFINITIONS ::= BEGIN

IMPORTS
    MODULE-IDENTITY, OBJECT-TYPE,
    Integer32, Counter64                        FROM SNMPv2-SMI
    MODULE-COMPLIANCE, OBJECT-GROUP             FROM SNMPv2-CONF
    DisplayString, TruthValue                   FROM SNMPv2-TC
    ifIndex                                     FROM IF-MIB
    InfnServiceType,InfnEqptType,InfnArc,
    InfnTestPattern,InfnEnableDisable,
    InfnLoopbackType,InfnServiceMode,
    InfnSMQ										FROM INFINERA-TC-MIB
    terminationPoint                            FROM INFINERA-REG-MIB;


fcClientCtpMIB MODULE-IDENTITY
    LAST-UPDATED  "200904200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "200904200000Z"
    DESCRIPTION
        "First Version"
    ::= { terminationPoint 26 }



fcClientCtpTable OBJECT-TYPE
    SYNTAX      SEQUENCE OF FcClientCtpEntry
    MAX-ACCESS  not-accessible
    STATUS      current
    DESCRIPTION
        "A list of Fiber channel Client CTP entries. Each entry is uniquely identified by the value of ifIndex."
    ::= { fcClientCtpMIB 1 }

fcClientCtpEntry  OBJECT-TYPE
    SYNTAX      FcClientCtpEntry
    MAX-ACCESS  not-accessible
    STATUS      current
    DESCRIPTION
        "A Fiber channel ClientCtp entry containing information pertaining to Infinera FcClientCtp interfaces. Entries will exist in this table for interfaces of type fcclientCtp."
    INDEX { ifIndex }
    ::= { fcClientCtpTable 1 }


FcClientCtpEntry  ::= SEQUENCE {
    fcClientCtpScrambling                  InfnEnableDisable,
    fcClientCtpDeScrambling                InfnEnableDisable,
    fcClientCtpTribTestSigGenMode          InfnEnableDisable,
    fcClientCtpTribTestSigMonMode          InfnEnableDisable,
    fcClientCtpLineSigGenMode              InfnEnableDisable,
    fcClientCtpLineSigMonMode              InfnEnableDisable,
    fcClientCtpPmHistStatsEnable           INTEGER,
    fcClientCtpAlarmReportControl          InfnArc,
    fcClientCtpSupportingCircuitIdList     DisplayString,
    fcClientCtpTamType                     InfnEqptType,
    fcClientCtpLoopback                    InfnLoopbackType,
    fcClientCtpConfiguredServiceType       InfnServiceType,

    fcClientCtpRxRpi15MinutesTce       Counter64,
    fcClientCtpRxRpiDayTce             Counter64,
    fcClientCtpTxTpi15MinutesTce       Counter64,
    fcClientCtpTxTpiDayTce             Counter64,

    fcClientCtpRxRpss15MinutesTce      Integer32,
    fcClientCtpRxRpssDayTce            Integer32,
    fcClientCtpTxTpss15MinutesTce      Integer32,
    fcClientCtpTxTpssDayTce            Integer32,

    fcClientCtpRxRpss15MinutesTce      Integer32,
    fcClientCtpRxRpssDayTce            Integer32,
    fcClientCtpTxTpss15MinutesTce      Integer32,
    fcClientCtpTxTpssDayTce            Integer32,

    fcClientCtpRxRps15MinutesTce      Integer32,
    fcClientCtpRxRpsDayTce            Integer32,
    fcClientCtpTxTps15MinutesTce      Integer32,
    fcClientCtpTxTpsDayTce            Integer32,

    fcClientCtpRxRpe15MinutesTce      Integer32,
    fcClientCtpRxRpeDayTce            Integer32,
    fcClientCtpTxTpe15MinutesTce      Integer32,
    fcClientCtpTxTpeDayTce            Integer32,

    fcClientCtpRxRf15MinutesTce       Counter64,
    fcClientCtpRxRfDayTce             Counter64,


    fcClientCtpTxTf15MinutesTce       Counter64,
    fcClientCtpTxTfDayTce             Counter64,

    fcClientCtpRxRef15MinutesTce      Counter64,
    fcClientCtpRxRefDayTce            Counter64,

    fcClientCtpTxTef15MinutesTce      Counter64,
    fcClientCtpTxTefDayTce            Counter64,


    fcClientCtpRxRo15MinutesTce       Counter64,
    fcClientCtpRxRoDayTce             Counter64,

    fcClientCtpTxTo15MinutesTce       Counter64,
    fcClientCtpTxToDayTce             Counter64,

    fcClientCtpRxREo15MinutesTce      Counter64,
    fcClientCtpRxREoDayTce            Counter64,

    fcClientCtpTxTEo15MinutesTce      Counter64,
    fcClientCtpTxTEoDayTce            Counter64,

    fcClientCtpRxRFs15MinutesTce      Integer32,
    fcClientCtpRxRFsDayTce            Integer32,
    fcClientCtpTxTFs15MinutesTce      Integer32,
    fcClientCtpTxTFsDayTce            Integer32,


    fcClientCtpRxRpi15MinutesTceReporting          TruthValue,
    fcClientCtpRxRpiDayTceReporting                TruthValue,
    fcClientCtpTxTpi15MinutesTceReporting          TruthValue,
    fcClientCtpTxTpiDayTceReporting                TruthValue,
    fcClientCtpRxRpss15MinutesTceReporting         TruthValue,
    fcClientCtpRxRpssDayTceReporting               TruthValue,
    fcClientCtpTxTpss15MinutesTceReporting         TruthValue,
    fcClientCtpTxTpssDayTceReporting               TruthValue,
    fcClientCtpRxRps15MinutesTceReporting          TruthValue,
    fcClientCtpRxRpsDayTceReporting                TruthValue,
    fcClientCtpTxTps15MinutesTceReporting          TruthValue,
    fcClientCtpTxTpsDayTceReporting                TruthValue,
    fcClientCtpRxRpe15MinutesTceReporting          TruthValue,
    fcClientCtpRxRpeDayTceReporting                TruthValue,
    fcClientCtpTxTpe15MinutesTceReporting          TruthValue,
    fcClientCtpTxTpeDayTceReporting                TruthValue,
    fcClientCtpRxRf15MinutesTceReporting           TruthValue,
    fcClientCtpRxRfDayTceReporting                 TruthValue,
    fcClientCtpTxTf15MinutesTceReporting           TruthValue,
    fcClientCtpTxTfDayTceReporting                 TruthValue,
    fcClientCtpRxRef15MinutesTceReporting          TruthValue,
    fcClientCtpRxRefDayTceReporting                TruthValue,
    fcClientCtpTxTef15MinutesTceReporting          TruthValue,
    fcClientCtpTxTefDayTceReporting                TruthValue,
    fcClientCtpRxRo15MinutesTceReporting           TruthValue,
    fcClientCtpRxRoDayTceReporting                 TruthValue,
    fcClientCtpTxTo15MinutesTceReporting           TruthValue,
    fcClientCtpTxToDayTceReporting                 TruthValue,
    fcClientCtpRxREo15MinutesTceReporting          TruthValue,
    fcClientCtpRxREoDayTceReporting                TruthValue,
    fcClientCtpTxTEo15MinutesTceReporting          TruthValue,
    fcClientCtpTxTEoDayTceReporting                TruthValue,
    fcClientCtpRxRFs15MinutesTceReporting          TruthValue,
    fcClientCtpRxRFsDayTceReporting                TruthValue,
    fcClientCtpTxTFs15MinutesTceReporting          TruthValue,
    fcClientCtpTxTFsDayTceReporting                TruthValue,
    fcClientCtpServiceMode                     	   InfnServiceMode,
    fcClientCtpServiceModeQualifier            	   InfnSMQ

}

 fcClientCtpScrambling OBJECT-TYPE
    SYNTAX  InfnEnableDisable
    MAX-ACCESS  read-write
    STATUS      current
    DESCRIPTION " Flag to enable or disable the scrambling of data on the egress data path.
        Applicable to: 8GFC and 10GFC."
    DEFVAL      {enabled }
    ::= { fcClientCtpEntry  1 }



 fcClientCtpDeScrambling OBJECT-TYPE
    SYNTAX  InfnEnableDisable
    MAX-ACCESS  read-write
    STATUS      current
    DESCRIPTION " Flag to enable or disable the De-scrambling of data on the ingress data path.
        Applicable to: 8GFC and 10GFC  ."
    DEFVAL      { enabled }
    ::= { fcClientCtpEntry  2 }


fcClientCtpTribTestSigGenMode  OBJECT-TYPE
    SYNTAX  InfnTestPattern
    MAX-ACCESS  read-write
    STATUS      current
    DESCRIPTION " The type of test pattern that is configured to be injected towards the client from
        the Infinera network.
        The following are the values that shall be applicable to each FC Client type:
        1GFC, 2GFC, 4GFC: CRPAT, CJTPAT
        8GFC: JSPAT, JTSPAT
        10GFC: PRTS1, PRTS2, SQWAVE, PRBS31 ."
    DEFVAL      { disabled }
    ::= { fcClientCtpEntry  3 }


fcClientCtpTribTestSigMonMode  OBJECT-TYPE
    SYNTAX InfnTestPattern
    MAX-ACCESS  read-write
    STATUS      obsolete
    DESCRIPTION " The type of test pattern that is configured to be monitored coming from the client to
        the Infinera network."
    DEFVAL      { disabled }
    ::= { fcClientCtpEntry  4 }


fcClientCtpLineSigGenMode OBJECT-TYPE
    SYNTAX  InfnTestPattern
    MAX-ACCESS  read-write
    STATUS      current
    DESCRIPTION "  The type of test pattern that is configured to be injected towards the
        Infinera network. The following are the values that shall be applicable to each FC Client type:
        1GFC, 2GFC, 4GFC: CRPAT,CJTPAT
        8GFC: JSPAT, JTSPAT
        10GFC: PRTS1, PRTS2, SQWAVE, PRBS31."
    DEFVAL      { disabled }
    ::= { fcClientCtpEntry  5 }

fcClientCtpLineSigMonMode OBJECT-TYPE
    SYNTAX  InfnTestPattern
    MAX-ACCESS  read-write
    STATUS      obsolete
    DESCRIPTION " The type of test pattern that is configured to be monitored coming
        from inside the Infinera network ."
    DEFVAL      { disabled }
    ::= { fcClientCtpEntry  6 }


fcClientCtpPmHistStatsEnable OBJECT-TYPE
    SYNTAX  INTEGER {
        enabled(1),
        disabled(2)
        }
    MAX-ACCESS  read-write
    STATUS      current
    DESCRIPTION " Flag to enable or disable the collection of PMs on Fiber Channel Clients."
    DEFVAL      { enabled }
    ::= { fcClientCtpEntry  7 }

fcClientCtpAlarmReportControl  OBJECT-TYPE
    SYNTAX InfnArc
    MAX-ACCESS  read-write
    STATUS      current
    DESCRIPTION "The Alarm Reporting Control Flag for the Fiber Channel Clients."
    DEFVAL      { allowed }
    ::= { fcClientCtpEntry  8 }


fcClientCtpSupportingCircuitIdList OBJECT-TYPE
    SYNTAX      DisplayString
    MAX-ACCESS  read-only
    STATUS      current
    DESCRIPTION "The Supporting Circuit ID List that is this client is using. "
    ::= { fcClientCtpEntry   9 }

fcClientCtpTamType  OBJECT-TYPE
    SYNTAX     InfnEqptType
    MAX-ACCESS read-only
    STATUS     obsolete
    DESCRIPTION "The equipment type where this Fiber Channel is residing."
    ::= { fcClientCtpEntry  10 }


fcClientCtpLoopback OBJECT-TYPE
    SYNTAX  InfnLoopbackType
    MAX-ACCESS  read-write
    STATUS      current
    DESCRIPTION "The Type of Loopback that is provisioned on this Fiber Channel Client interface."
    DEFVAL      { none }
    ::= { fcClientCtpEntry  11 }

fcClientCtpConfiguredServiceType  OBJECT-TYPE
    SYNTAX InfnServiceType
    MAX-ACCESS  read-only
    STATUS      current
    DESCRIPTION "The Fiber Channel Service type that is configured on this generic Fiber Channel Client CTP managed object."
      ::= { fcClientCtpEntry 12 }

fcClientCtpRxRpi15MinutesTce  OBJECT-TYPE
    SYNTAX      Counter64
    MAX-ACCESS  read-write
    STATUS      current
    DESCRIPTION "Number of  Invalid Code Groups in received direction during 15 minutes interval."
    ::= { fcClientCtpEntry  13 }

fcClientCtpRxRpiDayTce  OBJECT-TYPE
    SYNTAX      Counter64
    MAX-ACCESS  read-write
    STATUS      current
    DESCRIPTION "Number of  Invalid Code Groups in received direction during 24 hours interval."
    ::= { fcClientCtpEntry  14 }

fcClientCtpTxTpi15MinutesTce  OBJECT-TYPE
    SYNTAX      Counter64
    MAX-ACCESS  read-write
    STATUS      current
    DESCRIPTION "Number of  Invalid Code Groups in transmit direction during 15 minutes interval."
    ::= { fcClientCtpEntry  15 }

fcClientCtpTxTpiDayTce  OBJECT-TYPE
    SYNTAX      Counter64
    MAX-ACCESS  read-write
    STATUS      current
    DESCRIPTION "Number of Invalid Code Groups  in transmit direction during 24 hour interval."
    ::= { fcClientCtpEntry  16 }

fcClientCtpRxRpss15MinutesTce  OBJECT-TYPE
    SYNTAX      Integer32
    MAX-ACCESS  read-write
    STATUS      current
    DESCRIPTION "Number of Severely Errored Sync Seconds in received direction during 15 minutes interval."
    DEFVAL      { 1500 }
    ::= { fcClientCtpEntry  17 }

fcClientCtpRxRpssDayTce  OBJECT-TYPE
    SYNTAX      Integer32
    MAX-ACCESS  read-write
    STATUS      current
    DESCRIPTION "Number of  Severely Errored Sync Seconds in transmitted direction during 24 hours interval."
    DEFVAL      { 1500 }
    ::= { fcClientCtpEntry  18 }

fcClientCtpTxTpss15MinutesTce  OBJECT-TYPE
    SYNTAX      Integer32
    MAX-ACCESS  read-write
    STATUS      current
    DESCRIPTION "Number of Severely Errored Sync Seconds in transmitted direction during 15 minutes interval."
    DEFVAL      { 1500 }
    ::= { fcClientCtpEntry  19 }

fcClientCtpTxTpssDayTce   OBJECT-TYPE
    SYNTAX      Integer32
    MAX-ACCESS  read-write
    STATUS      current
    DESCRIPTION "Number of  Severely Errored Sync Seconds in transmitted direction during 24 Hour interval."
    DEFVAL      { 1500 }
    ::= { fcClientCtpEntry  20 }

fcClientCtpRxRps15MinutesTce  OBJECT-TYPE
    SYNTAX      Integer32
    MAX-ACCESS  read-write
    STATUS      current
    DESCRIPTION "Number of  Severely Errored Seconds in received direction during 15 minutes interval."
    DEFVAL      { 1500 }
    ::= { fcClientCtpEntry  21 }

fcClientCtpRxRpsDayTce  OBJECT-TYPE
    SYNTAX      Integer32
    MAX-ACCESS  read-write
    STATUS      current
    DESCRIPTION "Number of Severely Errored Seconds in received direction during 24 hour interval."
    DEFVAL      { 1500 }
    ::= { fcClientCtpEntry  22 }

fcClientCtpTxTps15MinutesTce  OBJECT-TYPE
    SYNTAX      Integer32
    MAX-ACCESS  read-write
    STATUS      current
    DESCRIPTION "Number of  Severely Errored Seconds in transmitted direction during 15 minutes interval."
    DEFVAL      { 1500 }
    ::= { fcClientCtpEntry  23 }

fcClientCtpTxTpsDayTce  OBJECT-TYPE
    SYNTAX      Integer32
    MAX-ACCESS  read-write
    STATUS      current
    DESCRIPTION "Number of  Severely Errored Seconds in transmitted direction during 24 hour interval."
    DEFVAL      { 1500 }
    ::= { fcClientCtpEntry  24 }

 fcClientCtpRxRpe15MinutesTce OBJECT-TYPE
    SYNTAX      Integer32
    MAX-ACCESS  read-write
    STATUS      current
    DESCRIPTION "Number of Errored Seconds  in received direction during 15 minutes interval."
    DEFVAL      { 1500 }
    ::= { fcClientCtpEntry  25 }

fcClientCtpRxRpeDayTce  OBJECT-TYPE
    SYNTAX      Integer32
    MAX-ACCESS  read-write
    STATUS      current
    DESCRIPTION "Number of  Errored Seconds in received direction during 24 hour interval."
    DEFVAL      { 1500 }
    ::= { fcClientCtpEntry  26 }

fcClientCtpTxTpe15MinutesTce  OBJECT-TYPE
    SYNTAX      Integer32
    MAX-ACCESS  read-write
    STATUS      current
    DESCRIPTION "Number of  Errored Seconds in transmitted direction during 15 minutes interval."
    DEFVAL      { 1500 }
    ::= { fcClientCtpEntry  27 }

fcClientCtpTxTpeDayTce  OBJECT-TYPE
    SYNTAX      Integer32
    MAX-ACCESS  read-write
    STATUS      current
    DESCRIPTION "Number of Errored Seconds in transmitted direction during 24 hour interval."
    DEFVAL      { 1500 }
    ::= { fcClientCtpEntry  28 }

fcClientCtpRxRf15MinutesTce  OBJECT-TYPE
    SYNTAX      Counter64
    MAX-ACCESS  read-write
    STATUS      current
    DESCRIPTION "Number of FC Frames in received direction during 15 minutes interval."
    ::= { fcClientCtpEntry  29 }

fcClientCtpRxRfDayTce  OBJECT-TYPE
    SYNTAX      Counter64
    MAX-ACCESS  read-write
    STATUS      current
    DESCRIPTION "Number of FC Frames in received direction during 24 hour interval."
    ::= { fcClientCtpEntry  30 }

 fcClientCtpTxTf15MinutesTce OBJECT-TYPE
    SYNTAX      Counter64
    MAX-ACCESS  read-write
    STATUS      current
    DESCRIPTION "Number of FC Frames in transmitted direction during 15 minutes interval."
    ::= { fcClientCtpEntry  31 }

fcClientCtpTxTfDayTce  OBJECT-TYPE
    SYNTAX      Counter64
    MAX-ACCESS  read-write
    STATUS      current
    DESCRIPTION "Number of  FC Frames in transmitted direction during 24 hour interval."
    ::= { fcClientCtpEntry  32 }

fcClientCtpRxRef15MinutesTce  OBJECT-TYPE
    SYNTAX      Counter64
    MAX-ACCESS  read-write
    STATUS      current
    DESCRIPTION "Number of  Errored Frames in received direction during 15 minutes interval."
    ::= { fcClientCtpEntry  33 }

fcClientCtpRxRefDayTce  OBJECT-TYPE
    SYNTAX      Counter64
    MAX-ACCESS  read-write
    STATUS      current
    DESCRIPTION "Number of  Errored Frames in received direction during 24 hour interval."
    ::= { fcClientCtpEntry  34 }

fcClientCtpTxTef15MinutesTce  OBJECT-TYPE
    SYNTAX      Counter64
    MAX-ACCESS  read-write
    STATUS      current
    DESCRIPTION "Number of Errored Frames in transmitted direction during 15 minutes interval."
    ::= { fcClientCtpEntry  35 }

fcClientCtpTxTefDayTce  OBJECT-TYPE
    SYNTAX      Counter64
    MAX-ACCESS  read-write
    STATUS      current
    DESCRIPTION "Number of  Errored Frames in transmitted direction during 24 hour interval."
    ::= { fcClientCtpEntry  36 }

fcClientCtpRxRo15MinutesTce  OBJECT-TYPE
    SYNTAX      Counter64
    MAX-ACCESS  read-write
    STATUS      current
    DESCRIPTION "Number of Octets in received direction during 15 minutes interval."
    ::= { fcClientCtpEntry  37 }

fcClientCtpRxRoDayTce  OBJECT-TYPE
    SYNTAX      Counter64
    MAX-ACCESS  read-write
    STATUS      current
    DESCRIPTION "Number of Octets in received direction during 24 hour interval."
    ::= { fcClientCtpEntry  38 }

fcClientCtpTxTo15MinutesTce  OBJECT-TYPE
    SYNTAX      Counter64
    MAX-ACCESS  read-write
    STATUS      current
    DESCRIPTION "Number of Octets  in transmitted direction during 15 minutes interval."
    ::= { fcClientCtpEntry  39 }

fcClientCtpTxToDayTce  OBJECT-TYPE
    SYNTAX      Counter64
    MAX-ACCESS  read-write
    STATUS      current
    DESCRIPTION "Number of  Octets in transmitted direction during 24 hour interval."
    ::= { fcClientCtpEntry  40 }

fcClientCtpRxREo15MinutesTce  OBJECT-TYPE
    SYNTAX      Counter64
    MAX-ACCESS  read-write
    STATUS      current
    DESCRIPTION "Number of  Errored Octets in received direction during 15 minutes interval."
    ::= { fcClientCtpEntry  41 }

fcClientCtpRxREoDayTce  OBJECT-TYPE
    SYNTAX      Counter64
    MAX-ACCESS  read-write
    STATUS      current
    DESCRIPTION "Number of Errored Octets in received direction during 24 hour interval."
    ::= { fcClientCtpEntry  42 }

fcClientCtpTxTEo15MinutesTce  OBJECT-TYPE
    SYNTAX      Counter64
    MAX-ACCESS  read-write
    STATUS      current
    DESCRIPTION "Number of  Errored Octets in transmitted direction during 15 minutes interval."
    ::= { fcClientCtpEntry  43 }

fcClientCtpTxTEoDayTce  OBJECT-TYPE
    SYNTAX      Counter64
    MAX-ACCESS  read-write
    STATUS      current
    DESCRIPTION "Number of  Errored Octets in transmitted direction during 24 hour interval."
    ::= { fcClientCtpEntry  44 }

fcClientCtpRxRFs15MinutesTce  OBJECT-TYPE
    SYNTAX      Integer32
    MAX-ACCESS  read-write
    STATUS      current
    DESCRIPTION "Number of  Frames  in received direction during 15 minutes interval."
    DEFVAL      { 1500 }
    ::= { fcClientCtpEntry  45 }

fcClientCtpRxRFsDayTce  OBJECT-TYPE
    SYNTAX      Integer32
    MAX-ACCESS  read-write
    STATUS      current
    DESCRIPTION "Number of  Frames  in received direction during 24 hour interval."
    DEFVAL      { 1500 }
    ::= { fcClientCtpEntry  46 }

fcClientCtpTxTFs15MinutesTce  OBJECT-TYPE
    SYNTAX      Integer32
    MAX-ACCESS  read-write
    STATUS      current
    DESCRIPTION "Number of Frames   in transmitted direction during 15 minutes interval."
    DEFVAL      { 1500 }
    ::= { fcClientCtpEntry  47 }


fcClientCtpTxTFsDayTce  OBJECT-TYPE
    SYNTAX      Integer32
    MAX-ACCESS  read-write
    STATUS      current
    DESCRIPTION "Number of  Frames in transmitted direction during 24 hour interval."
    DEFVAL      { 1500 }
    ::= { fcClientCtpEntry  48 }

fcClientCtpRxRpi15MinutesTceReporting OBJECT-TYPE
    SYNTAX      TruthValue
    MAX-ACCESS  read-write
    STATUS      current
    DESCRIPTION " Flag that enables/disables the reporting of threshold crossing."
    DEFVAL      { false }
    ::= { fcClientCtpEntry  49 }

fcClientCtpRxRpiDayTceReporting OBJECT-TYPE
    SYNTAX      TruthValue
    MAX-ACCESS  read-write
    STATUS      current
    DESCRIPTION " Flag that enables/disables the reporting of  threshold crossing."
    DEFVAL      { false }
    ::= { fcClientCtpEntry  50 }

fcClientCtpTxTpi15MinutesTceReporting OBJECT-TYPE
    SYNTAX      TruthValue
    MAX-ACCESS  read-write
    STATUS      current
    DESCRIPTION " Flag that enables/disables the reporting of  threshold crossing."
    DEFVAL      { false }
    ::= { fcClientCtpEntry  51 }

fcClientCtpTxTpiDayTceReporting   OBJECT-TYPE
    SYNTAX      TruthValue
    MAX-ACCESS  read-write
    STATUS      current
    DESCRIPTION " Flag that enables/disables the reporting of  threshold crossing."
    DEFVAL      { false }
    ::= { fcClientCtpEntry  52 }

fcClientCtpRxRpss15MinutesTceReporting     OBJECT-TYPE
    SYNTAX      TruthValue
    MAX-ACCESS  read-write
    STATUS      current
    DESCRIPTION " Flag that enables/disables the reporting of  threshold crossing."
    DEFVAL      { false }
    ::= { fcClientCtpEntry  53 }

fcClientCtpRxRpssDayTceReporting           OBJECT-TYPE
    SYNTAX      TruthValue
    MAX-ACCESS  read-write
    STATUS      current
    DESCRIPTION " Flag that enables/disables the reporting of  threshold crossing."
    DEFVAL      { false }
    ::= { fcClientCtpEntry  54 }

fcClientCtpTxTpss15MinutesTceReporting     OBJECT-TYPE
    SYNTAX      TruthValue
    MAX-ACCESS  read-write
    STATUS      current
    DESCRIPTION " Flag that enables/disables the reporting of  threshold crossing."
    DEFVAL      { false }
    ::= { fcClientCtpEntry  55 }

fcClientCtpTxTpssDayTceReporting           OBJECT-TYPE
    SYNTAX      TruthValue
    MAX-ACCESS  read-write
    STATUS      current
    DESCRIPTION " Flag that enables/disables the reporting of  threshold crossing."
    DEFVAL      { false }
    ::= { fcClientCtpEntry  56 }

fcClientCtpRxRps15MinutesTceReporting      OBJECT-TYPE
    SYNTAX      TruthValue
    MAX-ACCESS  read-write
    STATUS      current
    DESCRIPTION " Flag that enables/disables the reporting of   threshold crossing."
    DEFVAL      { false }
    ::= { fcClientCtpEntry  57 }

fcClientCtpRxRpsDayTceReporting            OBJECT-TYPE
    SYNTAX      TruthValue
    MAX-ACCESS  read-write
    STATUS      current
    DESCRIPTION " Flag that enables/disables the reporting of   threshold crossing."
    DEFVAL      { false }
    ::= { fcClientCtpEntry  58 }

fcClientCtpTxTps15MinutesTceReporting      OBJECT-TYPE
    SYNTAX      TruthValue
    MAX-ACCESS  read-write
    STATUS      current
    DESCRIPTION " Flag that enables/disables the reporting of   threshold crossing."
    DEFVAL      { false }
    ::= { fcClientCtpEntry  59 }

fcClientCtpTxTpsDayTceReporting            OBJECT-TYPE
    SYNTAX      TruthValue
    MAX-ACCESS  read-write
    STATUS      current
    DESCRIPTION " Flag that enables/disables the reporting of   threshold crossing."
    DEFVAL      { false }
    ::= { fcClientCtpEntry  60 }

fcClientCtpRxRpe15MinutesTceReporting      OBJECT-TYPE
    SYNTAX      TruthValue
    MAX-ACCESS  read-write
    STATUS      current
    DESCRIPTION " Flag that enables/disables the reporting of   threshold crossing."
    DEFVAL      { false }
    ::= { fcClientCtpEntry  61 }

fcClientCtpRxRpeDayTceReporting            OBJECT-TYPE
    SYNTAX      TruthValue
    MAX-ACCESS  read-write
    STATUS      current
    DESCRIPTION " Flag that enables/disables the reporting of   threshold crossing."
    DEFVAL      { false }
    ::= { fcClientCtpEntry  62 }

fcClientCtpTxTpe15MinutesTceReporting      OBJECT-TYPE
    SYNTAX      TruthValue
    MAX-ACCESS  read-write
    STATUS      current
    DESCRIPTION " Flag that enables/disables the reporting of   threshold crossing."
    DEFVAL      { false }
    ::= { fcClientCtpEntry  63 }

fcClientCtpTxTpeDayTceReporting            OBJECT-TYPE
    SYNTAX      TruthValue
    MAX-ACCESS  read-write
    STATUS      current
    DESCRIPTION " Flag that enables/disables the reporting of   threshold crossing."
    DEFVAL      { false }
    ::= { fcClientCtpEntry  64 }

fcClientCtpRxRf15MinutesTceReporting           OBJECT-TYPE
    SYNTAX      TruthValue
    MAX-ACCESS  read-write
    STATUS      current
    DESCRIPTION " Flag that enables/disables the reporting of   threshold crossing."
    DEFVAL      { false }
    ::= { fcClientCtpEntry  65 }

fcClientCtpRxRfDayTceReporting                 OBJECT-TYPE
    SYNTAX      TruthValue
    MAX-ACCESS  read-write
    STATUS      current
    DESCRIPTION " Flag that enables/disables the reporting of   threshold crossing."
    DEFVAL      { false }
    ::= { fcClientCtpEntry  66 }

fcClientCtpTxTf15MinutesTceReporting           OBJECT-TYPE
    SYNTAX      TruthValue
    MAX-ACCESS  read-write
    STATUS      current
    DESCRIPTION " Flag that enables/disables the reporting of   threshold crossing."
    DEFVAL      { false }
    ::= { fcClientCtpEntry  67 }

fcClientCtpTxTfDayTceReporting                 OBJECT-TYPE
    SYNTAX      TruthValue
    MAX-ACCESS  read-write
    STATUS      current
    DESCRIPTION " Flag that enables/disables the reporting of   threshold crossing."
    DEFVAL      { false }
    ::= { fcClientCtpEntry  68 }

fcClientCtpRxRef15MinutesTceReporting          OBJECT-TYPE
    SYNTAX      TruthValue
    MAX-ACCESS  read-write
    STATUS      current
    DESCRIPTION " Flag that enables/disables the reporting of   threshold crossing."
    DEFVAL      { false }
    ::= { fcClientCtpEntry  69 }

fcClientCtpRxRefDayTceReporting                OBJECT-TYPE
    SYNTAX      TruthValue
    MAX-ACCESS  read-write
    STATUS      current
    DESCRIPTION " Flag that enables/disables the reporting of   threshold crossing."
    DEFVAL      { false }
    ::= { fcClientCtpEntry  70 }

fcClientCtpTxTef15MinutesTceReporting          OBJECT-TYPE
    SYNTAX      TruthValue
    MAX-ACCESS  read-write
    STATUS      current
    DESCRIPTION " Flag that enables/disables the reporting of   threshold crossing."
    DEFVAL      { false }
    ::= { fcClientCtpEntry  71 }

fcClientCtpTxTefDayTceReporting                OBJECT-TYPE
    SYNTAX      TruthValue
    MAX-ACCESS  read-write
    STATUS      current
    DESCRIPTION " Flag that enables/disables the reporting of   threshold crossing."
    DEFVAL      { false }
    ::= { fcClientCtpEntry  72 }

fcClientCtpRxRo15MinutesTceReporting           OBJECT-TYPE
    SYNTAX      TruthValue
    MAX-ACCESS  read-write
    STATUS      current
    DESCRIPTION " Flag that enables/disables the reporting of   threshold crossing."
    DEFVAL      { false }
    ::= { fcClientCtpEntry  73 }

fcClientCtpRxRoDayTceReporting                 OBJECT-TYPE
    SYNTAX      TruthValue
    MAX-ACCESS  read-write
    STATUS      current
    DESCRIPTION " Flag that enables/disables the reporting of   threshold crossing."
    DEFVAL      { false }
    ::= { fcClientCtpEntry  74 }

fcClientCtpTxTo15MinutesTceReporting           OBJECT-TYPE
    SYNTAX      TruthValue
    MAX-ACCESS  read-write
    STATUS      current
    DESCRIPTION " Flag that enables/disables the reporting of   threshold crossing."
    DEFVAL      { false }
    ::= { fcClientCtpEntry  75 }

fcClientCtpTxToDayTceReporting                 OBJECT-TYPE
    SYNTAX      TruthValue
    MAX-ACCESS  read-write
    STATUS      current
    DESCRIPTION " Flag that enables/disables the reporting of   threshold crossing."
    DEFVAL      { false }
    ::= { fcClientCtpEntry  76 }

fcClientCtpRxREo15MinutesTceReporting          OBJECT-TYPE
    SYNTAX      TruthValue
    MAX-ACCESS  read-write
    STATUS      current
    DESCRIPTION " Flag that enables/disables the reporting of   threshold crossing."
    DEFVAL      { false }
    ::= { fcClientCtpEntry  77 }

fcClientCtpRxREoDayTceReporting                OBJECT-TYPE
    SYNTAX      TruthValue
    MAX-ACCESS  read-write
    STATUS      current
    DESCRIPTION " Flag that enables/disables the reporting of   threshold crossing."
    DEFVAL      { false }
    ::= { fcClientCtpEntry  78 }

fcClientCtpTxTEo15MinutesTceReporting          OBJECT-TYPE
    SYNTAX      TruthValue
    MAX-ACCESS  read-write
    STATUS      current
    DESCRIPTION " Flag that enables/disables the reporting of   threshold crossing."
    DEFVAL      { false }
    ::= { fcClientCtpEntry  79 }

fcClientCtpTxTEoDayTceReporting                OBJECT-TYPE
    SYNTAX      TruthValue
    MAX-ACCESS  read-write
    STATUS      current
    DESCRIPTION " Flag that enables/disables the reporting of   threshold crossing."
    DEFVAL      { false }
    ::= { fcClientCtpEntry  80 }

fcClientCtpRxRFs15MinutesTceReporting          OBJECT-TYPE
    SYNTAX      TruthValue
    MAX-ACCESS  read-write
    STATUS      current
    DESCRIPTION " Flag that enables/disables the reporting of   threshold crossing."
    DEFVAL      { false }
    ::= { fcClientCtpEntry  81 }

fcClientCtpRxRFsDayTceReporting                OBJECT-TYPE
    SYNTAX      TruthValue
    MAX-ACCESS  read-write
    STATUS      current
    DESCRIPTION " Flag that enables/disables the reporting of   threshold crossing."
    DEFVAL      { false }
    ::= { fcClientCtpEntry  82 }

fcClientCtpTxTFs15MinutesTceReporting          OBJECT-TYPE
    SYNTAX      TruthValue
    MAX-ACCESS  read-write
    STATUS      current
    DESCRIPTION " Flag that enables/disables the reporting of   threshold crossing."
        DEFVAL      { false }
        ::= { fcClientCtpEntry  83 }

fcClientCtpTxTFsDayTceReporting                OBJECT-TYPE
    SYNTAX      TruthValue
    MAX-ACCESS  read-write
    STATUS      current
    DESCRIPTION " Flag that enables/disables the reporting of   threshold crossing."
    DEFVAL      { false }
    ::= { fcClientCtpEntry  84 }

fcClientCtpServiceMode OBJECT-TYPE
    SYNTAX  InfnServiceMode
    MAX-ACCESS  read-only
    STATUS      current
    DESCRIPTION "ServiceMode of FC client CTP."
    DEFVAL      { none }
    ::= { fcClientCtpEntry  85 }

fcClientCtpServiceModeQualifier  OBJECT-TYPE
    SYNTAX      InfnSMQ
    MAX-ACCESS  read-only
    STATUS      current
    DESCRIPTION "The Service Mode Qualifier (SMQ) of the FCclient CTP (i.e., the mode/type of service in which
        this ODU client CTP is being used,). None’ is the default value indicated for the FC client CTP when it is initially created."
    DEFVAL      { none }
    ::= { fcClientCtpEntry  86 }


-- Conformance Statements
fcClientCtpConformance    OBJECT IDENTIFIER ::= { fcClientCtpMIB 3 }
fcClientCtpCompliances    OBJECT IDENTIFIER ::= { fcClientCtpConformance 1 }
fcClientCtpGroups         OBJECT IDENTIFIER ::= { fcClientCtpConformance 2 }

fcClientCtpCompliance MODULE-COMPLIANCE
    STATUS current
    DESCRIPTION
    "Describes the requirements for conformance to the FCCLIENTCTP-MIB"
    MODULE
        MANDATORY-GROUPS { fcClientCtpGroup }
    ::= { fcClientCtpCompliances 1 }

fcClientCtpGroup OBJECT-GROUP
    OBJECTS {
    fcClientCtpScrambling,
    fcClientCtpDeScrambling,
    fcClientCtpTribTestSigGenMode,
    fcClientCtpTribTestSigMonMode,
    fcClientCtpLineSigGenMode,
    fcClientCtpLineSigMonMode,
    fcClientCtpPmHistStatsEnable,
    fcClientCtpAlarmReportControl,
    fcClientCtpSupportingCircuitIdList,
    fcClientCtpTamType,
    fcClientCtpLoopback,
    fcClientCtpConfiguredServiceType,
    fcClientCtpRxRpi15MinutesTce     ,
    fcClientCtpRxRpiDayTce           ,
    fcClientCtpTxTpi15MinutesTce     ,
    fcClientCtpTxTpiDayTce           ,

    fcClientCtpRxRpss15MinutesTce      ,
    fcClientCtpRxRpssDayTce            ,
    fcClientCtpTxTpss15MinutesTce      ,
    fcClientCtpTxTpssDayTce            ,

    fcClientCtpRxRpss15MinutesTce      ,
    fcClientCtpRxRpssDayTce            ,
    fcClientCtpTxTpss15MinutesTce     ,
    fcClientCtpTxTpssDayTce           ,

    fcClientCtpRxRps15MinutesTce      ,
    fcClientCtpRxRpsDayTce            ,
    fcClientCtpTxTps15MinutesTce      ,
    fcClientCtpTxTpsDayTce            ,

    fcClientCtpRxRpe15MinutesTce      ,
    fcClientCtpRxRpeDayTce            ,
    fcClientCtpTxTpe15MinutesTce      ,
    fcClientCtpTxTpeDayTce            ,

    fcClientCtpRxRf15MinutesTce       ,
    fcClientCtpRxRfDayTce             ,


    fcClientCtpTxTf15MinutesTce       ,
    fcClientCtpTxTfDayTce             ,

    fcClientCtpRxRef15MinutesTce      ,
    fcClientCtpRxRefDayTce            ,

    fcClientCtpTxTef15MinutesTce      ,
    fcClientCtpTxTefDayTce            ,


    fcClientCtpRxRo15MinutesTce       ,
    fcClientCtpRxRoDayTce             ,

    fcClientCtpTxTo15MinutesTce       ,
    fcClientCtpTxToDayTce             ,

    fcClientCtpRxREo15MinutesTce      ,
    fcClientCtpRxREoDayTce            ,

    fcClientCtpTxTEo15MinutesTce      ,
    fcClientCtpTxTEoDayTce            ,

    fcClientCtpRxRFs15MinutesTce      ,
    fcClientCtpRxRFsDayTce            ,
    fcClientCtpTxTFs15MinutesTce      ,
    fcClientCtpTxTFsDayTce            ,


    fcClientCtpRxRpi15MinutesTceReporting,
    fcClientCtpRxRpiDayTceReporting      ,
    fcClientCtpTxTpi15MinutesTceReporting,
    fcClientCtpTxTpiDayTceReporting      ,
    fcClientCtpRxRpss15MinutesTceReporting,
    fcClientCtpRxRpssDayTceReporting      ,
    fcClientCtpTxTpss15MinutesTceReporting,
    fcClientCtpTxTpssDayTceReporting      ,
    fcClientCtpRxRps15MinutesTceReporting ,
    fcClientCtpRxRpsDayTceReporting       ,
    fcClientCtpTxTps15MinutesTceReporting ,
    fcClientCtpTxTpsDayTceReporting       ,
    fcClientCtpRxRpe15MinutesTceReporting ,
    fcClientCtpRxRpeDayTceReporting       ,
    fcClientCtpTxTpe15MinutesTceReporting ,
    fcClientCtpTxTpeDayTceReporting       ,
    fcClientCtpRxRf15MinutesTceReporting  ,
    fcClientCtpRxRfDayTceReporting        ,
    fcClientCtpTxTf15MinutesTceReporting  ,
    fcClientCtpTxTfDayTceReporting        ,
    fcClientCtpRxRef15MinutesTceReporting ,
    fcClientCtpRxRefDayTceReporting       ,
    fcClientCtpTxTef15MinutesTceReporting ,
    fcClientCtpTxTefDayTceReporting       ,
    fcClientCtpRxRo15MinutesTceReporting  ,
    fcClientCtpRxRoDayTceReporting        ,
    fcClientCtpTxTo15MinutesTceReporting  ,
    fcClientCtpTxToDayTceReporting        ,
    fcClientCtpRxREo15MinutesTceReporting ,
    fcClientCtpRxREoDayTceReporting       ,
    fcClientCtpTxTEo15MinutesTceReporting ,
    fcClientCtpTxTEoDayTceReporting       ,
    fcClientCtpRxRFs15MinutesTceReporting ,
    fcClientCtpRxRFsDayTceReporting       ,
    fcClientCtpTxTFs15MinutesTceReporting ,
    fcClientCtpTxTFsDayTceReporting    	,
    fcClientCtpServiceMode		,
    fcClientCtpServiceModeQualifier
    }
    STATUS current
    DESCRIPTION
        "A collection of objects for managing the Fiber channel Client CTP"
    ::= { fcClientCtpGroups 1 }


END
