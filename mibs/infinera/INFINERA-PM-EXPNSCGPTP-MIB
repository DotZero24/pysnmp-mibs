-- *****************************************************************
-- INFINERA-PM-EXPNSCGPTP-MIB
--
-- October 2013, Rishab Joshi
--
--
-- Copyright (c) 2008-2013 by Infinera Inc.
-- All rights reserved.
-- ****************************************************************

INFINERA-PM-EXPNSCGPTP-MIB DEFINITIONS ::= BEGIN

IMPORTS
    MODULE-IDENTITY, OBJECT-TYPE,
    Integer32                                   FROM SNMPv2-SMI
    MODULE-COMPLIANCE, OBJECT-GROUP             FROM SNMPv2-CONF
    TruthValue                                  FROM SNMPv2-TC
    ifIndex                                     FROM IF-MIB
    FloatHundredths                             FROM INFINERA-TC-MIB
    perfMon                                     FROM INFINERA-REG-MIB;


expnScgPtpPmMIB MODULE-IDENTITY
    LAST-UPDATED  "201310080000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION      "201310080000Z"
    DESCRIPTION
        "First Version"
    ::= { perfMon 48 }


expnScgPtpPmTable OBJECT-TYPE
    SYNTAX      SEQUENCE OF ExpnScgPtpPmEntry
    MAX-ACCESS  not-accessible
    STATUS      current
    DESCRIPTION
        "A list of ExpnScgPtpP entries. Each entry is uniquely identified by the value of ifIndex."
    ::= { expnScgPtpPmMIB 2 }

expnScgPtpPmEntry  OBJECT-TYPE
    SYNTAX      ExpnScgPtpPmEntry
    MAX-ACCESS  not-accessible
    STATUS      current
    DESCRIPTION
        "A ExpnScgPtpPm entry containing historical performance information pertaining to Infinera ExpnScgPtp.
        This table is a subclass of IfCommon. Entries will exist in this table only for interfaces
        of type ExpnScgPtp."
    INDEX { ifIndex}
    ::= { expnScgPtpPmTable 1 }


ExpnScgPtpPmEntry  ::= SEQUENCE {
   expnScgPtpPmValidity         TruthValue,
   expnScgPtpPmCmnScgOptMin     FloatHundredths,
   expnScgPtpPmCmnScgOptMax     FloatHundredths,
   expnScgPtpPmCmnScgOptAve     FloatHundredths,
   expnScgPtpPmCmnScgOprMin     FloatHundredths,
   expnScgPtpPmCmnScgOprMax     FloatHundredths,
   expnScgPtpPmCmnScgOprAve     FloatHundredths
}

expnScgPtpPmValidity OBJECT-TYPE
    SYNTAX      TruthValue
    MAX-ACCESS  read-only
    STATUS      current
    DESCRIPTION "Flag indicating if data was valid for the entire interval"
    ::= { expnScgPtpPmEntry  3 }


expnScgPtpPmCmnScgOptMin OBJECT-TYPE
    SYNTAX      FloatHundredths
    MAX-ACCESS  read-only
    STATUS      current
    DESCRIPTION "Minimum FsmScg optical power min."
    ::= { expnScgPtpPmEntry  4 }


expnScgPtpPmCmnScgOptMax OBJECT-TYPE
    SYNTAX      FloatHundredths
    MAX-ACCESS  read-only
    STATUS      current
    DESCRIPTION "Maximum FsmScg optical power max."
    ::= { expnScgPtpPmEntry  5 }


expnScgPtpPmCmnScgOptAve OBJECT-TYPE
    SYNTAX      FloatHundredths
    MAX-ACCESS  read-only
    STATUS      current
    DESCRIPTION "Average FsmScg optical power ave."
    ::= { expnScgPtpPmEntry  6 }


expnScgPtpPmCmnScgOprMin OBJECT-TYPE
    SYNTAX      FloatHundredths
    MAX-ACCESS  read-only
    STATUS      current
    DESCRIPTION "Minimum FsmScg optical power min."
    ::= { expnScgPtpPmEntry  7}


expnScgPtpPmCmnScgOprMax OBJECT-TYPE
    SYNTAX      FloatHundredths
    MAX-ACCESS  read-only
    STATUS      current
    DESCRIPTION "Maximum FsmScg optical power max."
    ::= { expnScgPtpPmEntry  8}


expnScgPtpPmCmnScgOprAve OBJECT-TYPE
    SYNTAX      FloatHundredths
    MAX-ACCESS  read-only
    STATUS      current
    DESCRIPTION "Average FsmScg optical power ave."
    ::= { expnScgPtpPmEntry  9}




expnScgPtpPmRealTable OBJECT-TYPE
    SYNTAX      SEQUENCE OF ExpnScgPtpPmRealEntry
    MAX-ACCESS  not-accessible
    STATUS      current
    DESCRIPTION
        "A list of FsmScgPtpPmReal entries. Each entry is uniquely identified by the value of ifIndex."
    ::= { expnScgPtpPmMIB 1 }

expnScgPtpPmRealEntry  OBJECT-TYPE
    SYNTAX      ExpnScgPtpPmRealEntry
    MAX-ACCESS  not-accessible
    STATUS      current
    DESCRIPTION
        "A  expnScgPtp entry containing real-time performance information pertaining to Infinera
         expnScgPtp interfaces. This table is a subclass of IfCommon."
    INDEX { ifIndex }
    ::= { expnScgPtpPmRealTable 1 }


ExpnScgPtpPmRealEntry  ::= SEQUENCE {
    expnScgPtpPmRealCmnScgOpt       FloatHundredths,
    expnScgPtpPmRealCmnScgOpr       FloatHundredths
}

expnScgPtpPmRealCmnScgOpt OBJECT-TYPE
    SYNTAX      FloatHundredths
    MAX-ACCESS  read-only
    STATUS      current
    DESCRIPTION "Total FsmScg optical power trasmit."
    ::= { expnScgPtpPmRealEntry  1 }


expnScgPtpPmRealCmnScgOpr OBJECT-TYPE
    SYNTAX      FloatHundredths
    MAX-ACCESS  read-only
    STATUS      current
    DESCRIPTION "Total FsmScg optical power receive."
    ::= { expnScgPtpPmRealEntry  2 }



-- Conformance Statements
expnScgPtpPmConformance    OBJECT IDENTIFIER ::= { expnScgPtpPmMIB 3 }
expnScgPtpPmCompliances    OBJECT IDENTIFIER ::= { expnScgPtpPmConformance 1 }
expnScgPtpPmGroups         OBJECT IDENTIFIER ::= { expnScgPtpPmConformance 2 }

expnScgPtpPmCompliance MODULE-COMPLIANCE
    STATUS current
    DESCRIPTION
    "Describes the requirements for conformance to the  expnScgPtp-MIB"
    MODULE
        MANDATORY-GROUPS { expnScgPtpPmGroup }
    ::= { expnScgPtpPmCompliances 1 }

expnScgPtpPmRealCompliance MODULE-COMPLIANCE
    STATUS current
    DESCRIPTION
    "Describes the requirements for conformance to the FsmScgPtpPmReal-MIB"
    MODULE
        MANDATORY-GROUPS { expnScgPtpPmRealGroup }
    ::= { expnScgPtpPmCompliances 2 }

expnScgPtpPmGroup OBJECT-GROUP
    OBJECTS {
        expnScgPtpPmValidity,
        expnScgPtpPmCmnScgOptMin,
        expnScgPtpPmCmnScgOptMax,
        expnScgPtpPmCmnScgOptAve,
        expnScgPtpPmCmnScgOprMin,
        expnScgPtpPmCmnScgOprMax,
        expnScgPtpPmCmnScgOprAve
    }
    STATUS current
    DESCRIPTION
        " A collection of objects for reading the historical performance of the  expnScgPtp."
    ::= { expnScgPtpPmGroups 1 }

expnScgPtpPmRealGroup OBJECT-GROUP
    OBJECTS {
        expnScgPtpPmRealCmnScgOpt,
        expnScgPtpPmRealCmnScgOpr
    }
    STATUS current
    DESCRIPTION
        " A collection of objects for reading the real-time performance of the  expnScgPtp."
    ::= { expnScgPtpPmGroups 2 }

END
