-- *****************************************************************
-- INFINERA-TP-GFPTP-MIB
-- Copyright (c) 2014 by Infinera Inc.
-- All rights reserved.
-- ****************************************************************

INFINERA-TP-GFPTP-MIB DEFINITIONS ::= BEGIN

IMPORTS
    MODULE-IDENTITY, OBJECT-TYPE,
    Unsigned32                             			FROM SNMPv2-SMI
    ifIndex                                         FROM IF-MIB
    MODULE-COMPLIANCE, OBJECT-GROUP            	 	FROM SNMPv2-CONF
    InfnSMQ, InfnServiceMode, InfnNetworkMapping,
    InfnGFPState, InfnPmHistStatsControl,
    InfnGFPPayloadFCS, InfnGfpExtHdrTyp 		    FROM INFINERA-TC-MIB
    terminationPoint                        		FROM INFINERA-REG-MIB;


gfpTpMIB MODULE-IDENTITY
    LAST-UPDATED  "201104200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "201104200000Z"
    DESCRIPTION
        "First Version"
    ::= { terminationPoint 80 }



gfpTpTable OBJECT-TYPE
    SYNTAX      SEQUENCE OF GfpTpEntry
    MAX-ACCESS  not-accessible
    STATUS      current
    DESCRIPTION
        "A list of GfpTp  entries. Each entry is uniquely identified by the value of ifIndex."
    ::= { gfpTpMIB 1 }

gfpTpEntry  OBJECT-TYPE
    SYNTAX      GfpTpEntry
    MAX-ACCESS  not-accessible
    STATUS      current
    DESCRIPTION
        "A GfpTp entry containing information pertaining to Infinera GfpTp interfaces.
        Entries will exist in this table for interfaces of type otuclientCtp."
    INDEX { ifIndex }
    ::= { gfpTpTable 1 }


GfpTpEntry  ::= SEQUENCE {

    gfpTpPayloadFCS     InfnGFPPayloadFCS,
    gfpTpExtHeaderType	InfnGfpExtHdrTyp,
    gfpTpChannelId		Unsigned32,
    gfpTpServiceMode    InfnServiceMode,
    gfpTpServiceModeQualifier       InfnSMQ,
    gfpTpNetworkMap                 InfnNetworkMapping,
    gfpTpGFPState                   InfnGFPState,
    gfpTpHistStatsEnable            InfnPmHistStatsControl

}

gfpTpPayloadFCS  OBJECT-TYPE
    SYNTAX      InfnGFPPayloadFCS
    MAX-ACCESS  read-write
    STATUS      current

    DESCRIPTION "	whether or not Payload FCS is
	included in the generated (sourced) GFP client
	frames."
    DEFVAL      { disable }
    ::= { gfpTpEntry  1 }


gfpTpExtHeaderType  OBJECT-TYPE
    SYNTAX      InfnGfpExtHdrTyp
    MAX-ACCESS  read-write
    STATUS      current
    DESCRIPTION ""
    DEFVAL      { null }
    ::= { gfpTpEntry  2 }

gfpTpChannelId  OBJECT-TYPE
    SYNTAX     	Unsigned32
    MAX-ACCESS  read-write
    STATUS      current
    DESCRIPTION ""
    DEFVAL      { 0 }
    ::= { gfpTpEntry  3 }

gfpTpServiceMode OBJECT-TYPE
    SYNTAX  InfnServiceMode
    MAX-ACCESS  read-only
    STATUS      current
    DESCRIPTION "Service Mode"
    DEFVAL      { none }
    ::= { gfpTpEntry  4 }

gfpTpServiceModeQualifier  OBJECT-TYPE
    SYNTAX      InfnSMQ
    MAX-ACCESS  read-only
    STATUS      current
    DESCRIPTION "Service Mode Qualifier"
    DEFVAL      { none }
    ::= { gfpTpEntry  5 }

gfpTpNetworkMap  OBJECT-TYPE
    SYNTAX      InfnNetworkMapping
    MAX-ACCESS  read-only
    STATUS      current
    DESCRIPTION "Network Mapping"
    ::= { gfpTpEntry  6 }

gfpTpGFPState  OBJECT-TYPE
    SYNTAX      InfnGFPState
    MAX-ACCESS  read-only
    STATUS      current
    DESCRIPTION "GFP state"
    ::= { gfpTpEntry  7 }

gfpTpHistStatsEnable  OBJECT-TYPE
    SYNTAX     InfnPmHistStatsControl
    MAX-ACCESS read-write
    STATUS     current
    DESCRIPTION
        "Flag to enable or disable PM collection."
    ::= { gfpTpEntry 8 }



-- Conformance Statements
gfpTpConformance    OBJECT IDENTIFIER ::= { gfpTpMIB 3 }
gfpTpCompliances    OBJECT IDENTIFIER ::= { gfpTpConformance 1 }
gfpTpGroups         OBJECT IDENTIFIER ::= { gfpTpConformance 2 }

gfpTpCompliance MODULE-COMPLIANCE
    STATUS current
    DESCRIPTION
    "Describes the requirements for conformance to the OTUCLIENTCTP-MIB"
    MODULE
        MANDATORY-GROUPS { gfpTpGroup }
    ::= { gfpTpCompliances 1 }

gfpTpGroup OBJECT-GROUP
    OBJECTS {

    gfpTpPayloadFCS ,
    gfpTpExtHeaderType,
    gfpTpChannelId,
    gfpTpServiceMode,
    gfpTpServiceModeQualifier,
    gfpTpNetworkMap,
    gfpTpGFPState,
    gfpTpHistStatsEnable
    }
    STATUS current
    DESCRIPTION
        " A collection of objects for managing the gfpTp"
    ::= { gfpTpGroups 1 }


END
