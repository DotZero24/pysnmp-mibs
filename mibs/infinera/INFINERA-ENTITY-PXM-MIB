-- ***************************************************************
-- INFINERA-ENTITY-PXM-MIB
--
-- October 2014, Anusree Bhattacharjee
--
--
-- Copyright (c) 2008-2012 by Infinera Inc.
-- All rights reserved.
-- ****************************************************************
INFINERA-ENTITY-PXM-MIB DEFINITIONS ::= BEGIN

IMPORTS
    OBJECT-TYPE, MODULE-IDENTITY, Unsigned32    FROM SNMPv2-SMI
    OBJECT-GROUP, MODULE-COMPLIANCE             FROM SNMPv2-CONF
    DisplayString                               FROM SNMPv2-TC
    entLPPhysicalIndex                          FROM ENTITY-MIB
    equipment                                   FROM INFINERA-REG-MIB
    InfnEqptType,FloatTenths,InfnMeterActionRed,
    InfnSchedulerType, InfnNetworkMappingMode,
    InfnMacFlapAction, InfnFlushFdbType,
	FloatHundredths							    FROM INFINERA-TC-MIB;

pxmMIB MODULE-IDENTITY
    LAST-UPDATED  "201410200000Z"
    ORGANIZATION
        "INFINERA"
    CONTACT-INFO
        "Infinera
        169 Java Drive
        Sunnyvale, CA - 94089

        Contact : Technical Support
        Email   : support@infinera.com
        Phone   : 1-877-INF-5288"
    DESCRIPTION
        "This MIB is modeling for PXM equipment table."
::= { equipment 30 }

pxmConformance       OBJECT IDENTIFIER ::= { pxmMIB 3 }
pxmCompliances       OBJECT IDENTIFIER ::= { pxmConformance 1 }
pxmGroups            OBJECT IDENTIFIER ::= { pxmConformance 2 }

pxmTable  OBJECT-TYPE
    SYNTAX SEQUENCE OF PxmEntry
    MAX-ACCESS not-accessible
    STATUS     current
    DESCRIPTION
        "This table contains all PXM  modules that are currently present in a network element.
        "
    ::= { pxmMIB 1 }

pxmEntry  OBJECT-TYPE
    SYNTAX     PxmEntry
    MAX-ACCESS not-accessible
    STATUS     current
    DESCRIPTION
        "A row in the PXM table. Each row in the table is identified with a unique entPhysicalIndexID."
    INDEX { entLPPhysicalIndex }
    ::= { pxmTable 1 }

PxmEntry ::= SEQUENCE {
    pxmMoId                     DisplayString,
    pxmSchedulerType            InfnSchedulerType,
    pxmNetworkMappingMode       InfnNetworkMappingMode,
    pxmTotalBandwidth           Unsigned32,
    pxmTotalAvailableBW         Unsigned32,
    pxmMeterActionRed           InfnMeterActionRed,
    pxmMaxSwitchingCapacityFactor   FloatTenths,
    pxmAvailableSwitchingCapacity   FloatTenths,
    pxmMaxSwitchingCapacity         FloatTenths,
	pxmProvEqptType           	InfnEqptType,
	pxmInstalledEqptType      	InfnEqptType,
	pxmEqptMaxPowerDraw         FloatHundredths,
    pxmMacAgingTime             Integer32,
    pxmMacFlapCountThreshold    Integer32,
    pxmMacFlapTimeInterval      Integer32,
    pxmMacFlapAction            InfnMacFlapAction,
    pxmFlushFdbType             InfnFlushFdbType,
    pxmVsiOrInterface           DisplayString,
    pxmGlobalId                 Integer32,
    pxmMPLSTPNodeID             Integer32
}

pxmMoId  OBJECT-TYPE
    SYNTAX     DisplayString
    MAX-ACCESS read-only
    STATUS     current
    DESCRIPTION
        "This is the primary Key of the objects e.g 1-IOSHELF-PXMA, 1-IOSHELF-PXMB etc."
    ::= { pxmEntry 1 }


pxmSchedulerType OBJECT-TYPE
    SYNTAX      InfnSchedulerType
    MAX-ACCESS  read-write
    STATUS      current
    DESCRIPTION ""
    ::= { pxmEntry 2 }

pxmNetworkMappingMode OBJECT-TYPE
    SYNTAX      InfnNetworkMappingMode
    MAX-ACCESS  read-write
    STATUS      current
    DESCRIPTION ""
    ::= { pxmEntry 3 }

pxmTotalBandwidth OBJECT-TYPE
    SYNTAX      Unsigned32
    MAX-ACCESS  read-only
    STATUS      current
    DESCRIPTION ""
    ::= { pxmEntry 4 }

pxmTotalAvailableBW OBJECT-TYPE
    SYNTAX      Unsigned32
    MAX-ACCESS  read-only
    STATUS      current
    DESCRIPTION ""
    ::= { pxmEntry 5 }

pxmMeterActionRed OBJECT-TYPE
    SYNTAX      InfnMeterActionRed
    MAX-ACCESS  read-write
    STATUS      current
    DESCRIPTION ""
    ::= { pxmEntry 6 }

pxmMaxSwitchingCapacityFactor   OBJECT-TYPE
    SYNTAX     FloatTenths
    MAX-ACCESS read-write
    STATUS     current
    DESCRIPTION
        ""
    ::= { pxmEntry 7 }

pxmAvailableSwitchingCapacity   OBJECT-TYPE
    SYNTAX     FloatTenths
    MAX-ACCESS read-only
    STATUS     current
    DESCRIPTION
        ""
    ::= { pxmEntry 8 }

pxmMaxSwitchingCapacity OBJECT-TYPE
    SYNTAX     FloatTenths
    MAX-ACCESS read-only
    STATUS     current
    DESCRIPTION
        ""
    ::= { pxmEntry 9 }

pxmProvEqptType  OBJECT-TYPE
     SYNTAX     InfnEqptType
     MAX-ACCESS read-only
     STATUS     current
     DESCRIPTION
         "The configured equipment type."
     ::= { pxmEntry	10 }

pxmInstalledEqptType  OBJECT-TYPE
     SYNTAX     InfnEqptType
     MAX-ACCESS read-only
     STATUS     current
     DESCRIPTION
         "The equipment type installed in the slot."
     ::= { pxmEntry 11 }

pxmEqptMaxPowerDraw  OBJECT-TYPE
	SYNTAX     FloatHundredths
	MAX-ACCESS read-only
	STATUS     current
	DESCRIPTION
    	"Parameter denoting the estimated power drawn by the FRU. This varies
     	depending on the type of the FRU."
	::= { pxmEntry 12 }


pxmMacAgingTime  OBJECT-TYPE
    SYNTAX     Integer32
    MAX-ACCESS read-write
    STATUS     current
    DESCRIPTION
        "Parameter indicating the MAC Aging Time"
    ::= { pxmEntry 13 }

pxmMacFlapCountThreshold  OBJECT-TYPE
    SYNTAX     Integer32
    MAX-ACCESS read-write
    STATUS     current
    DESCRIPTION
        "Parameter indicating MAC Flap Count threshold"
    ::= { pxmEntry 14 }

pxmMacFlapTimeInterval  OBJECT-TYPE
    SYNTAX     Integer32
    MAX-ACCESS read-write
    STATUS     current
    DESCRIPTION
        "Parameter indicating MAC Flap Time Interval"
    ::= { pxmEntry 15 }

pxmMacFlapAction  OBJECT-TYPE
    SYNTAX     InfnMacFlapAction
    MAX-ACCESS read-write
    STATUS     current
    DESCRIPTION
        "Parameter indicating MAC Flap Action"
    ::= { pxmEntry 16 }

pxmFlushFdbType  OBJECT-TYPE
    SYNTAX     InfnFlushFdbType
    MAX-ACCESS read-write
    STATUS     current
    DESCRIPTION
        "Parameter indicating MAC Flush Fdb Type"
    ::= { pxmEntry 17 }

pxmVsiOrInterface  OBJECT-TYPE
    SYNTAX     DisplayString
    MAX-ACCESS read-write
    STATUS     current
    DESCRIPTION
        "Indicates if VSI flush operation is on VSI or AC/PW Interface"
    ::= { pxmEntry 18 }

pxmGlobalId  OBJECT-TYPE
    SYNTAX     Integer32
    MAX-ACCESS read-write
    STATUS     current
    DESCRIPTION
        ""
    ::= { pxmEntry 19 }

pxmMPLSTPNodeID  OBJECT-TYPE
    SYNTAX     Integer32
    MAX-ACCESS read-write
    STATUS     current
    DESCRIPTION
        ""
    ::= { pxmEntry 20 }

pxmCompliance  MODULE-COMPLIANCE
    STATUS     current
    DESCRIPTION ""
    MODULE
        MANDATORY-GROUPS { pxmGroup }
    ::= { pxmCompliances 1 }

pxmGroup  OBJECT-GROUP
    OBJECTS {
    pxmMoId,
    pxmSchedulerType,
    pxmNetworkMappingMode,
    pxmTotalBandwidth,
    pxmTotalAvailableBW,
    pxmMeterActionRed,
    pxmMaxSwitchingCapacityFactor,
    pxmAvailableSwitchingCapacity,
    pxmMaxSwitchingCapacity,
   	pxmProvEqptType,
	pxmInstalledEqptType,
	pxmEqptMaxPowerDraw,
    pxmMacAgingTime,
    pxmMacFlapCountThreshold,
    pxmMacFlapTimeInterval,
    pxmMacFlapAction,
    pxmFlushFdbType,
    pxmVsiOrInterface,
    pxmGlobalId,
    pxmMPLSTPNodeID
}
    STATUS     current
    DESCRIPTION ""
    ::= { pxmGroups 1 }
END
