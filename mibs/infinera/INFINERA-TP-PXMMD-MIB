-- ***************************************************************
-- INFINERA-TP-PXMMD-MIB
--
-- May 2016, Kavitha Manjunatha / Divyank Rastogi
--
--
-- Copyright (c) 2008-2012 by Infinera Inc.
-- All rights reserved.
-- ****************************************************************
INFINERA-TP-PXMMD-MIB DEFINITIONS ::= BEGIN

IMPORTS
    OBJECT-TYPE, MODULE-IDENTITY, Unsigned32    FROM SNMPv2-SMI
    OBJECT-GROUP, MODULE-COMPLIANCE             FROM SNMPv2-CONF
    DisplayString                               FROM SNMPv2-TC
    ifIndex                                     FROM IF-MIB
    terminationPoint                            FROM INFINERA-REG-MIB
    InfnMDNameFormat, InfnMHFCreationCriteria,
    InfnSenderIDTLV                             FROM INFINERA-TC-MIB;

mdMIB MODULE-IDENTITY
    LAST-UPDATED  "201605200000Z"
    ORGANIZATION
        "INFINERA"
    CONTACT-INFO
        "Infinera
        169 Java Drive
        Sunnyvale, CA - 94089

        Contact : Technical Support
        Email   : support@infinera.com
        Phone   : 1-877-INF-5288"
    DESCRIPTION
        "This MIB is modeling for MD interface table."
::= { terminationPoint 78 }

mdTable  OBJECT-TYPE
    SYNTAX SEQUENCE OF MdEntry
    MAX-ACCESS not-accessible
    STATUS     current
    DESCRIPTION
        "This table contains all MD modules that are currently present in a network element.
        "
    ::= { mdMIB 1 }

mdEntry  OBJECT-TYPE
    SYNTAX     MdEntry
    MAX-ACCESS not-accessible
    STATUS     current
    DESCRIPTION
        "A row in the MD table. Each row in the table is identified with a unique ifIndex."
    INDEX { ifIndex }
    ::= { mdTable 1 }

MdEntry ::= SEQUENCE {
    mdName                      DisplayString,
    mdLevel                     Integer32,
    mdMDNameFormat              InfnMDNameFormat,
    mdMHFCreationCriteria       InfnMHFCreationCriteria,
    mdSenderIDTLV               InfnSenderIDTLV
}

mdName  OBJECT-TYPE
    SYNTAX     DisplayString
    MAX-ACCESS read-write
    STATUS     current
    DESCRIPTION
        "MD Name"
    ::= { mdEntry 1 }

mdLevel  OBJECT-TYPE
    SYNTAX     Integer32
    MAX-ACCESS read-write
    STATUS     current
    DESCRIPTION
        "MD Level"
    ::= { mdEntry 2 }

mdMDNameFormat  OBJECT-TYPE
    SYNTAX     InfnMDNameFormat
    MAX-ACCESS read-write
    STATUS     current
    DESCRIPTION
        "MD Name Format"
    ::= { mdEntry 3 }

mdMHFCreationCriteria  OBJECT-TYPE
    SYNTAX     InfnMHFCreationCriteria
    MAX-ACCESS read-write
    STATUS     current
    DESCRIPTION
        "MHF Creation Criteria"
    ::= { mdEntry 4 }

mdSenderIDTLV  OBJECT-TYPE
    SYNTAX     InfnSenderIDTLV
    MAX-ACCESS read-write
    STATUS     current
    DESCRIPTION
        "Sender ID TLV"
    ::= { mdEntry 5 }

mdConformance       OBJECT IDENTIFIER ::= { mdMIB 3 }
mdCompliances       OBJECT IDENTIFIER ::= { mdConformance 1 }
mdGroups            OBJECT IDENTIFIER ::= { mdConformance 2 }

mdCompliance  MODULE-COMPLIANCE
    STATUS     current
    DESCRIPTION ""
    MODULE
        MANDATORY-GROUPS { mdGroup }
    ::= { mdCompliances 1 }

mdGroup  OBJECT-GROUP
    OBJECTS {
        mdName,
        mdLevel,
        mdMDNameFormat,
        mdMHFCreationCriteria,
        mdSenderIDTLV
    }
    STATUS     current
    DESCRIPTION ""
    ::= { mdGroups 1 }
END
