-- *****************************************************************
-- INFINERA-TP-OTUKICLIENTCTP-MIB
-- Copyright (c) 2011-2012 by Infinera Inc.
-- All rights reserved.
-- ****************************************************************

INFINERA-TP-OTUKICTP-MIB DEFINITIONS ::= BEGIN

IMPORTS
    MODULE-IDENTITY, OBJECT-TYPE,
    Integer32, Counter64                        	FROM SNMPv2-SMI
    MODULE-COMPLIANCE, OBJECT-GROUP             	FROM SNMPv2-CONF
    DisplayString, TruthValue                   	FROM SNMPv2-TC
    ifIndex                                     	FROM IF-MIB
    InfnServiceType,InfnEqptType,InfnArc,
    InfnEnableDisable,InfnMonitoringMode,
    InfnSMQ,InfnServiceMode,
    FloatTenths,InfnOtuBitRateK                     FROM INFINERA-TC-MIB
    terminationPoint                            	FROM INFINERA-REG-MIB;


otukiCtpMIB MODULE-IDENTITY
    LAST-UPDATED  "200904200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "200904200000Z"
    DESCRIPTION
        "First Version"
    ::= { terminationPoint 31 }



otukiCtpTable OBJECT-TYPE
    SYNTAX      SEQUENCE OF OtuKiCtpEntry
    MAX-ACCESS  not-accessible
    STATUS      current
    DESCRIPTION
        "A list of OtuKiClientCtp entries. Each entry is uniquely identified by the value of ifIndex."
    ::= { otukiCtpMIB 1 }

otukiCtpEntry  OBJECT-TYPE
    SYNTAX      OtuKiCtpEntry
    MAX-ACCESS  not-accessible
    STATUS      current
    DESCRIPTION
        "A OtuKiClientCtp entry containing information pertaining to Infinera OtuKiClientCtp interfaces.
        Entries will exist in this table for interfaces of type otuKiclientCtp."
    INDEX { ifIndex }
    ::= { otukiCtpTable 1 }


OtuKiCtpEntry  ::= SEQUENCE {


    otukiCtpServiceMode                     InfnServiceMode,
    otukiCtpServiceModeQualifier            InfnSMQ,
    otukiCtpFecCorrection                   InfnEnableDisable,
    otukiCtpFecEnabled                      InfnEnableDisable,
    otukiFecDecoderIterationCount	    Integer32,
    otukpropagationDelay	 	    FloatTenths,
    otukiBitRateK		            InfnOtuBitRateK,
    otukiCtpFacTxTTI                        DisplayString,
    otukiCtpFacExpectedSAPI                 DisplayString,
    otukiCtpFacExpectedDAPI                 DisplayString,
    otukiCtpFacRxTTI		 	    DisplayString,
    otukiCtpFacPmHistStatsEnable            InfnEnableDisable,
    otukiCtpFacMonitoringMode               InfnMonitoringMode,
    otukiCtpFacDSThreshold                  Integer32,
    otukiCtpFacSDThreshold                  Integer32 ,
    otukiCtpFacTimDetMode                   INTEGER,

    otukiCtpSupportingOchList         	    DisplayString,
    otukiCtpRxEb15MinutesTce                Integer32,
    otukiCtpRxEbDayTce                      Integer32,
    otukiCtpRxDs15MinutesTce                Integer32,
    otukiCtpRxDsDayTce                      Integer32,
    otukiCtpRxEbDayTceReporting             TruthValue,
    otukiCtpRxEb15MinutesTceReporting       TruthValue,
    otukiCtpRxDsDayTceReporting             TruthValue,
    otukiCtpRxDs15MinutesTceReporting       TruthValue,
    otukiCtpAlarmReportControl              InfnArc,
    otukiCtpConfiguredServiceType       InfnServiceType

}



otukiCtpServiceMode OBJECT-TYPE
    SYNTAX  	InfnServiceMode
    MAX-ACCESS  read-only
    STATUS      current
    DESCRIPTION "'None’ is the default value indicated for the OTU client CTP when it is initially created.
     OTUk alarms, loopbacks/diagnostics, PMs, etc. are intended to be supported in alignment with pre-R6 support for
     similar SONET/SDH CTPs. See also Fac/TermMonitoringMode"
    DEFVAL      { none }
    ::= { otukiCtpEntry  1 }

otukiCtpServiceModeQualifier  OBJECT-TYPE
    SYNTAX      InfnSMQ
    MAX-ACCESS  read-only
    STATUS      current
    DESCRIPTION "The Service Mode Qualifier (SMQ) of the ODU client CTP (i.e., the mode/type of service in which
        this ODU client CTP is being used,). None’ is the default value indicated for the OTU client CTP when it is initially created.
        Value is set as a result of service provisioning (see Xcon and SNC provisioning). Allowed value is dependent on the Configured Service Type and
        the Service Mode (which are also the result of service provisioning)"
    DEFVAL      { none }
    ::= { otukiCtpEntry  2 }


otukiCtpFecCorrection OBJECT-TYPE
    SYNTAX  InfnEnableDisable
    MAX-ACCESS  read-write
    STATUS      current
    DESCRIPTION "This atTermute is used to enable or disable the FEC correction at the ingress of the OTU client facility.
    When Disabled, the FEC statistics are still provided. Applicable to:All OtuKiClientCtp."
    DEFVAL      { enabled }
    ::= { otukiCtpEntry  3 }

otukiCtpFecEnabled OBJECT-TYPE
    SYNTAX  InfnEnableDisable
    MAX-ACCESS  read-write
    STATUS      current
    DESCRIPTION "This atTermute is used to enable or disable the G.709 Fec Generation
        and handling on the OTU Term interface. If the FECEnabled is FALSE, all zeroes are inserted on the FEC overhead signal.
        Similarly, a OTU Term interfaces receiving the Zero FEC signal, will not be able to detect or correct errors"
    DEFVAL      { enabled }
    ::= { otukiCtpEntry  4 }


otukiFecDecoderIterationCount OBJECT-TYPE
    SYNTAX      Integer32
    MAX-ACCESS  read-write
    STATUS      current
    DESCRIPTION ""
    DEFVAL      { 3 }
    ::= { otukiCtpEntry  5 }

otukpropagationDelay OBJECT-TYPE
    SYNTAX      FloatTenths
    MAX-ACCESS  read-write
    STATUS      current
    DESCRIPTION
        ""
    ::= { otukiCtpEntry  6  }



otukiBitRateK OBJECT-TYPE
    SYNTAX      InfnOtuBitRateK
    MAX-ACCESS  read-only
    STATUS      current
    DESCRIPTION
        ""
    ::= { otukiCtpEntry  7  }

otukiCtpFacTxTTI OBJECT-TYPE
    SYNTAX      DisplayString (SIZE(1..64))
    MAX-ACCESS  read-write
    STATUS      current
    DESCRIPTION "The TTI message that needs to be transmitted in the Facility direction (e.g., from Line to Trib direction)."
    ::= { otukiCtpEntry  8 }

otukiCtpFacExpectedSAPI OBJECT-TYPE
    SYNTAX      DisplayString (SIZE(1..16))
    MAX-ACCESS  read-write
    STATUS      current
    DESCRIPTION "The Source Access Point Identifier that is expected from the Facility side (e.g., Trib to Line direction). "
    ::= { otukiCtpEntry  9 }

otukiCtpFacExpectedDAPI OBJECT-TYPE
    SYNTAX      DisplayString (SIZE(1..16))
    MAX-ACCESS  read-write
    STATUS      current
    DESCRIPTION "The Destination Access Point Identifier that is expected from the Facility side (e.g., Trib to Line direction) "
    ::= { otukiCtpEntry  10 }

otukiCtpFacRxTTI OBJECT-TYPE
    SYNTAX      DisplayString (SIZE(1..64))
    MAX-ACCESS  read-only
    STATUS      current
    DESCRIPTION "The TTI message that needs to be transmitted in the Facility direction (e.g., from Line to Trib direction)."
    ::= { otukiCtpEntry  11 }

otukiCtpFacPmHistStatsEnable OBJECT-TYPE
    SYNTAX  InfnEnableDisable
    MAX-ACCESS  read-write
    STATUS      current
    DESCRIPTION "  Flag to enable or disable the collection of PMs on the Terminal side of OTU Clients."
    DEFVAL      { enabled }
    ::= { otukiCtpEntry  12 }


otukiCtpFacMonitoringMode OBJECT-TYPE
    SYNTAX  InfnMonitoringMode
    MAX-ACCESS  read-only
    STATUS      current
    DESCRIPTION "Allowed Section Monitoring / Path  Monitoring / TCM Attribute Value(s)
        (For side corresponding to MonitoringMode) (Fac-Side/Term-Side)."
    ::= { otukiCtpEntry 13 }

otukiCtpFacDSThreshold OBJECT-TYPE
    SYNTAX      Integer32 (1..100)
    MAX-ACCESS  read-write
    STATUS      current
    DESCRIPTION "This attribute indicates the Facility-side (e.g., Trib-side) threshold level for declaring a
    performance monitoring (PM) Second to be bad. A PM Second is declared bad if the percentage of detected errored blocks
    in that second is greater than or equal to the specified threshold level.
    This attribute maps to the DEGThr MIB of RFC-3591"
    DEFVAL      { 30 }
    ::= { otukiCtpEntry  14 }

otukiCtpFacSDThreshold  OBJECT-TYPE
    SYNTAX      Integer32 (2..10)
    MAX-ACCESS  read-write
    STATUS      current
    DESCRIPTION "This attribute indicates the Facility-side (e.g.,Trib-side) threshold level for declaring a
    Degraded Signal defect. A Degraded Signal defect shall be declared if SDThreshold consecutive bad PM Seconds are
    detected. This attribute maps to the DEGM MIB of RFC-3591"
    DEFVAL      { 7 }
    ::= { otukiCtpEntry  15 }

otukiCtpFacTimDetMode  OBJECT-TYPE
    SYNTAX  INTEGER {
    off(1),
    sapi(2),
    dapi(3),
    sapidapi(4)
    }
    MAX-ACCESS  read-write
    STATUS      current
    DESCRIPTION "This atTermute is used to configure if the TIM-S alarm shall be reported on mismatch of Expected
        and Received TTI message. The following are the values and their meaning:
        OFF: TIM-S is not reported.
        DAPI: TIM-S is reported only if the DAPI message mismatch occurs.
        SAPI: TIM-S is reported only if the SAPI message mismatch occurs.
        DAPI_SAPI: Either the DAPI or the SAPI messages are in a mismatch       state. "
    DEFVAL      { off }
    ::= { otukiCtpEntry 16 }



otukiCtpSupportingOchList  OBJECT-TYPE
    SYNTAX      DisplayString
    MAX-ACCESS  read-only
    STATUS      current
    DESCRIPTION "The Supporting OCH List that is this client is using. "
    ::= { otukiCtpEntry   17 }

otukiCtpRxEb15MinutesTce  OBJECT-TYPE
    SYNTAX      Integer32
    MAX-ACCESS  read-write
    STATUS      current
    DESCRIPTION "Number of ErrorBlock in receive direction during 15 minutes interval."
    DEFVAL      { 1500 }
    ::= { otukiCtpEntry  18 }


otukiCtpRxEbDayTce OBJECT-TYPE
    SYNTAX      Integer32
    MAX-ACCESS  read-write
    STATUS      current
    DESCRIPTION "Number of ErrorBlock in receive direction during 24 hours interval."
    DEFVAL      { 15000 }
    ::= { otukiCtpEntry  19}


otukiCtpRxDs15MinutesTce  OBJECT-TYPE
    SYNTAX      Integer32
    MAX-ACCESS  read-write
    STATUS      current
    DESCRIPTION "Number of Defect Seconds in receive direction during 15 minutes interval."
    DEFVAL      { 120 }
    ::= { otukiCtpEntry  20 }


otukiCtpRxDsDayTce OBJECT-TYPE
    SYNTAX      Integer32
    MAX-ACCESS  read-write
    STATUS      current
    DESCRIPTION "Number of Defect Seconds in receive direction during 24 hours interval."
    DEFVAL      { 1200 }
    ::= { otukiCtpEntry  21 }


otukiCtpRxEbDayTceReporting OBJECT-TYPE
    SYNTAX      TruthValue
    MAX-ACCESS  read-write
    STATUS      current
    DESCRIPTION " Flag that enables/disables the reporting of RxEbDayTce threshold crossing."
    DEFVAL      { false }
    ::= { otukiCtpEntry  22 }

otukiCtpRxEb15MinutesTceReporting OBJECT-TYPE
    SYNTAX      TruthValue
    MAX-ACCESS  read-write
    STATUS      current
    DESCRIPTION "  Flag that enables/disables the reporting of RxEb15MinutesTce threshold crossing."
    DEFVAL      { false }
    ::= { otukiCtpEntry  23 }


otukiCtpRxDsDayTceReporting OBJECT-TYPE
    SYNTAX      TruthValue
    MAX-ACCESS  read-write
    STATUS      current
    DESCRIPTION " Flag that enables/disables the reporting of RxDsDayTce threshold crossing."
    DEFVAL      { false }
    ::= { otukiCtpEntry  24 }

otukiCtpRxDs15MinutesTceReporting OBJECT-TYPE
    SYNTAX      TruthValue
    MAX-ACCESS  read-write
    STATUS      current
    DESCRIPTION " Flag that enables/disables the reporting of RxDs15MinutesTce threshold crossing."
    DEFVAL      { false }
    ::= { otukiCtpEntry  25 }


otukiCtpAlarmReportControl OBJECT-TYPE
    SYNTAX InfnArc
    MAX-ACCESS  read-write
    STATUS      current
    DESCRIPTION " The Alarm Reporting Control Flag for the OTU Clients. ."
    DEFVAL      { allowed }
    ::= { otukiCtpEntry  26 }

otukiCtpConfiguredServiceType OBJECT-TYPE
    SYNTAX InfnServiceType
    MAX-ACCESS  read-only
    STATUS      current
    DESCRIPTION " "
    ::= { otukiCtpEntry  27 }


-- Conformance Statements
otukiCtpConformance    OBJECT IDENTIFIER ::= { otukiCtpMIB 3 }
otukiCtpCompliances    OBJECT IDENTIFIER ::= { otukiCtpConformance 1 }
otukiCtpGroups         OBJECT IDENTIFIER ::= { otukiCtpConformance 2 }

otukiCtpCompliance MODULE-COMPLIANCE
    STATUS current
    DESCRIPTION
    "Describes the requirements for conformance to the OTUKICLIENTCTP-MIB"
    MODULE
        MANDATORY-GROUPS { otukiCtpGroup }
    ::= { otukiCtpCompliances 1 }

otukiCtpGroup OBJECT-GROUP
    OBJECTS {

    otukiCtpServiceMode,
    otukiCtpServiceModeQualifier,
    otukiCtpFecCorrection,
    otukiCtpFecEnabled ,
    otukiFecDecoderIterationCount,
    otukpropagationDelay,
    otukiBitRateK,
    otukiCtpFacTxTTI,
    otukiCtpFacExpectedSAPI,
    otukiCtpFacExpectedDAPI ,
    otukiCtpFacRxTTI,
    otukiCtpFacPmHistStatsEnable,
    otukiCtpFacMonitoringMode ,
    otukiCtpFacDSThreshold,
    otukiCtpFacSDThreshold ,
    otukiCtpFacTimDetMode,
    otukiCtpSupportingOchList,
    otukiCtpRxEb15MinutesTce ,
    otukiCtpRxEbDayTce ,
    otukiCtpRxDs15MinutesTce,
    otukiCtpRxDsDayTce ,
    otukiCtpRxEbDayTceReporting,
    otukiCtpRxEb15MinutesTceReporting ,
    otukiCtpRxDsDayTceReporting,
    otukiCtpRxDs15MinutesTceReporting,
    otukiCtpAlarmReportControl,
    otukiCtpConfiguredServiceType
    }
    STATUS current
    DESCRIPTION
        " A collection of objects for managing the otukiCtp"
    ::= { otukiCtpGroups 1 }


END
