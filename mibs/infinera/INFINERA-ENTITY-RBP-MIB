-- ***************************************************************
-- INFINERA-ENTITY-RBP-MIB
--
-- Jan 2015, Kavitha Manjunatha
--
--
-- Copyright (c) 2010-2012 by Infinera Inc.
-- All rights reserved.
-- ****************************************************************

INFINERA-ENTITY-RBP-MIB DEFINITIONS ::= BEGIN

IMPORTS
    OBJECT-TYPE, MODULE-IDENTITY        FROM SNMPv2-SMI
    OBJECT-GROUP, MODULE-COMPLIANCE     FROM SNMPv2-CONF
    RowStatus, DisplayString            FROM SNMPv2-TC
    entLPPhysicalIndex                  FROM ENTITY-MIB
    equipment                           FROM INFINERA-REG-MIB
    InfnEqptType                        FROM INFINERA-TC-MIB;

rbpMIB MODULE-IDENTITY
    LAST-UPDATED  "201501080000Z"
    ORGANIZATION
        "INFINERA"
    CONTACT-INFO
        "Infinera
        169 Java Drive
        Sunnyvale, CA - 94089

        Contact : Technical Support
        Email   : support@infinera.com
        Phone   : 1-877-INF-5288"
    DESCRIPTION
        "This MIB is modeling for RBP equipment table."

::= { equipment 49 }

rbpConformance       OBJECT IDENTIFIER ::= { rbpMIB 3 }
rbpCompliances       OBJECT IDENTIFIER ::= { rbpConformance 1 }
rbpGroups            OBJECT IDENTIFIER ::= { rbpConformance 2 }

rbpTable  OBJECT-TYPE
    SYNTAX SEQUENCE OF RbpEntry
    MAX-ACCESS not-accessible
    STATUS     current
    DESCRIPTION
        "This table contains all SCM modules that are currently present in a network element.
        "
    ::= { rbpMIB 1 }

rbpEntry  OBJECT-TYPE
    SYNTAX     RbpEntry
    MAX-ACCESS not-accessible
    STATUS     current
    DESCRIPTION
        "A row in the SCM table. Each row in the table is identified with a unique entPhysicalIndexID.
        "
    INDEX { entLPPhysicalIndex }
    ::= { rbpTable 1 }


RbpEntry ::= SEQUENCE {
    rbpMoId             DisplayString,
    rbpProvEqptType     InfnEqptType,
    rbpProvSerialNumber DisplayString
}

rbpMoId  OBJECT-TYPE
    SYNTAX     DisplayString
    MAX-ACCESS read-create
    STATUS     current
    DESCRIPTION
        "This is the primary Key of the objects e.g 1-A-1"
    ::= { rbpEntry 1 }

rbpProvEqptType  OBJECT-TYPE
    SYNTAX     InfnEqptType
    MAX-ACCESS read-create
    STATUS     current
    DESCRIPTION
        "User provisioned SCM type."
    ::= { rbpEntry 2 }

rbpProvSerialNumber OBJECT-TYPE
    SYNTAX      DisplayString
    MAX-ACCESS  read-write
    STATUS      current
    DESCRIPTION ""
    ::= { rbpEntry 3 }


rbpCompliance  MODULE-COMPLIANCE
    STATUS     current
    DESCRIPTION
        "Describes the requirements for conformance to the RBP-MIB"
    MODULE
        MANDATORY-GROUPS { rbpGroup }
    ::= { rbpCompliances 1 }

rbpGroup  OBJECT-GROUP
    OBJECTS {
        rbpMoId,
        rbpProvEqptType,
        rbpProvSerialNumber
    }
    STATUS     current
    DESCRIPTION
        " A collection of objects for managing a RBP module"
    ::= { rbpGroups 1 }
END
