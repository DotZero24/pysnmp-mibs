-- *****************************************************************
-- INFINERA-TP-SONETCLIENTCTP-MIB
--
-- October 2008, Sharfuddin Syed / Narendra Gupta
--
--
-- Copyright (c) 2008-2012 by Infinera Inc.
-- All rights reserved.
-- ****************************************************************

INFINERA-TP-SONETCLIENTCTP-MIB DEFINITIONS ::= BEGIN

IMPORTS
    MODULE-IDENTITY, OBJECT-TYPE,
    Integer32, Counter64                        FROM SNMPv2-SMI
    MODULE-COMPLIANCE, OBJECT-GROUP             FROM SNMPv2-CONF
    DisplayString, TruthValue                   FROM SNMPv2-TC
    ifIndex                                     FROM IF-MIB
    InfnServiceType,InfnSMQ,
	InfnServiceMode, InfnClientAction, InfnEnableDisable,
    InfnLoopbackType, InfnJ0TraceMode, InfnJ0MessageCompliance,
    InfnPmHistStatsControl                      FROM INFINERA-TC-MIB
    terminationPoint                            FROM INFINERA-REG-MIB;


sonetClientCtpMIB MODULE-IDENTITY
    LAST-UPDATED  "200810200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "200810200000Z"
    DESCRIPTION
        "First Version"
    ::= { terminationPoint 16 }



sonetClientCtpTable OBJECT-TYPE
    SYNTAX      SEQUENCE OF SonetClientCtpEntry
    MAX-ACCESS  not-accessible
    STATUS      current
    DESCRIPTION
        "A list of SonetClientCtp entries. Each entry is uniquely identified by the value of ifIndex."
    ::= { sonetClientCtpMIB 1 }

sonetClientCtpEntry  OBJECT-TYPE
    SYNTAX      SonetClientCtpEntry
    MAX-ACCESS  not-accessible
    STATUS      current
    DESCRIPTION
        "A SonetClientCtp entry containing information pertaining to
        Infinera SonetClientCtp interfaces. Entries will exist in this table for
        interfaces of type sonetClientCtp."
    INDEX { ifIndex }
    ::= { sonetClientCtpTable 1 }


SonetClientCtpEntry  ::= SEQUENCE {
    sonetClientCtpTribPrbsGenMode                InfnEnableDisable,
    sonetClientCtpTribPrbsMonMode                InfnEnableDisable,
    sonetClientCtpSupportingCircuitIdList        DisplayString,
    sonetClientCtpLoopback                       InfnLoopbackType,
    sonetClientCtpPmHistStatsEnable              InfnPmHistStatsControl,
    sonetClientCtpConfiguredServiceType          InfnServiceType,
    sonetClientCtpRxJ0                           DisplayString,
    sonetClientCtpExpectedRxJ0                   DisplayString,
    sonetClientCtpTransmittedJ0                  DisplayString,
    sonetClientCtpRxJ0MessageLength              Integer32,
    sonetClientCtpRxJ0MismatchReporting          InfnEnableDisable,
    sonetClientCtpRxJ0TraceMode                  InfnJ0TraceMode,
    sonetClientCtpRxJ0MessageCompliance          InfnJ0MessageCompliance,
    sonetClientCtpRxCv15MinutesTce               Counter64,
    sonetClientCtpRxSefs15MinutesTce             Integer32,
    sonetClientCtpRxEs15MinutesTce               Integer32,
    sonetClientCtpRxSes15MinutesTce              Integer32,
    sonetClientCtpRxCvDayTce                     Counter64,
    sonetClientCtpRxSefsDayTce                   Integer32,
    sonetClientCtpRxEsDayTce                     Integer32,
    sonetClientCtpRxSesDayTce                    Integer32,
    sonetClientCtpTxCv15MinutesTce               Counter64,
    sonetClientCtpTxSefs15MinutesTce             Integer32,
    sonetClientCtpTxEs15MinutesTce               Integer32,
    sonetClientCtpTxSes15MinutesTce              Integer32,
    sonetClientCtpTxCvDayTce                     Counter64,
    sonetClientCtpTxSefsDayTce                   Integer32,
    sonetClientCtpTxEsDayTce                     Integer32,
    sonetClientCtpTxSesDayTce                    Integer32,
    sonetClientCtpRxCv15MinutesTceReporting      TruthValue,
    sonetClientCtpRxSefs15MinutesTceReporting    TruthValue,
    sonetClientCtpRxEs15MinutesTceReporting      TruthValue,
    sonetClientCtpRxSes15MinutesTceReporting     TruthValue,
    sonetClientCtpRxCvDayTceReporting            TruthValue,
    sonetClientCtpRxSefsDayTceReporting          TruthValue,
    sonetClientCtpRxEsDayTceReporting            TruthValue,
    sonetClientCtpRxSesDayTceReporting           TruthValue,
    sonetClientCtpTxCv15MinutesTceReporting      TruthValue,
    sonetClientCtpTxSefs15MinutesTceReporting    TruthValue,
    sonetClientCtpTxEs15MinutesTceReporting      TruthValue,
    sonetClientCtpTxSes15MinutesTceReporting     TruthValue,
    sonetClientCtpTxCvDayTceReporting            TruthValue,
    sonetClientCtpTxSefsDayTceReporting          TruthValue,
    sonetClientCtpTxEsDayTceReporting            TruthValue,
    sonetClientCtpTxSesDayTceReporting           TruthValue,
    sonetClientCtpLinePrbsGenMode                InfnEnableDisable,
    sonetClientCtpLinePrbsMonMode                InfnEnableDisable,
    sonetClientCtpServiceMode			         InfnServiceMode,
    sonetClientCtpServiceModeQualifier		     InfnSMQ,
    sonetClientCtpEncapClientDisableAction       InfnClientAction

}

sonetClientCtpTribPrbsGenMode OBJECT-TYPE
    SYNTAX   InfnEnableDisable
    MAX-ACCESS  read-write
    STATUS      current
    DESCRIPTION "Flag which enables the generation of PRBS data on the transmit side."
    DEFVAL      { disabled }
    ::= { sonetClientCtpEntry  1 }


sonetClientCtpTribPrbsMonMode OBJECT-TYPE
    SYNTAX  InfnEnableDisable
    MAX-ACCESS  read-write
    STATUS      current
    DESCRIPTION "Flag which enables the monitoring of bit errors."
    DEFVAL      { disabled }
    ::= { sonetClientCtpEntry  2 }


sonetClientCtpSupportingCircuitIdList OBJECT-TYPE
    SYNTAX      DisplayString
    MAX-ACCESS  read-only
    STATUS      current
    DESCRIPTION
        "An unordered list of the circuitIDs supporting this Managed Object.
        This string contains the string representation of each supporting
        circuitID, separated by a ',' (comma) if there is more than one
        supporting circuitID."
    ::= { sonetClientCtpEntry  3 }


sonetClientCtpLoopback OBJECT-TYPE
    SYNTAX  InfnLoopbackType
    MAX-ACCESS  read-write
    STATUS      current
    DESCRIPTION "Flag to enable the loopback."
    DEFVAL      { none }
    ::= { sonetClientCtpEntry  4 }


sonetClientCtpPmHistStatsEnable OBJECT-TYPE
    SYNTAX  InfnPmHistStatsControl
    MAX-ACCESS  read-write
    STATUS      current
    DESCRIPTION "Flag to enable or disable PM collection."
    DEFVAL      { enabled }
    ::= { sonetClientCtpEntry  5 }


sonetClientCtpConfiguredServiceType OBJECT-TYPE
    SYNTAX  InfnServiceType
    MAX-ACCESS  read-only
    STATUS      current
    DESCRIPTION "The configured payload type."
    ::= { sonetClientCtpEntry  6 }


sonetClientCtpRxJ0 OBJECT-TYPE
    SYNTAX      DisplayString
    MAX-ACCESS  read-only
    STATUS      current
    DESCRIPTION
        "The trace that we are receiving currently. (COs update the MOs only when there is a change in the
        filtered received trace). For SONET, CRLF should be removed from the end. Whatever is remaining is
        converted to ascii representation of hex string and reported to users. For example, Infinera
        followed by 0x1 character will result in string 'Infinera\01h'. With this approach the length
        could be as large as 256 characters."
    ::= { sonetClientCtpEntry  7 }


sonetClientCtpExpectedRxJ0 OBJECT-TYPE
    SYNTAX      DisplayString
    MAX-ACCESS  read-write
    STATUS      current
    DESCRIPTION
        "The J0 trace that is to be expected from the receive side from the customer equipment. If not
        zero-length and different from J0ReceivedTrace, a J0 mismatch alarm will be raised. Message is
        always ASCII characters."
    ::= { sonetClientCtpEntry  8 }


sonetClientCtpTransmittedJ0 OBJECT-TYPE
    SYNTAX      DisplayString
    MAX-ACCESS  read-write
    STATUS      current
    DESCRIPTION "Transmitted J0 message."
    ::= { sonetClientCtpEntry  9 }


sonetClientCtpRxJ0MessageLength OBJECT-TYPE
    SYNTAX      Integer32
    MAX-ACCESS  read-write
    STATUS      current
    DESCRIPTION "The length of J0 byte."
    DEFVAL      { 16 }
    ::= { sonetClientCtpEntry  10 }


sonetClientCtpRxJ0MismatchReporting OBJECT-TYPE
    SYNTAX  InfnEnableDisable
    MAX-ACCESS  read-write
    STATUS      current
    DESCRIPTION "The flag for enabling or disabling the reporting of J0 trace mismatch condition."
    DEFVAL      { disabled }
    ::= { sonetClientCtpEntry  11 }


sonetClientCtpRxJ0TraceMode OBJECT-TYPE
    SYNTAX   InfnJ0TraceMode
    MAX-ACCESS  read-write
    STATUS      current
    DESCRIPTION "Transparent mode ignores the configured Transmit and
    transparently forward the Receive towards the client equipment. This is
    the default value for Trace Mode. Overwrite mode forwards the configured
    Transmit towards the client equipment."
    DEFVAL      { transparent }
    ::= { sonetClientCtpEntry  12 }


sonetClientCtpRxJ0MessageCompliance OBJECT-TYPE
    SYNTAX  InfnJ0MessageCompliance
    MAX-ACCESS  read-write
    STATUS      current
    DESCRIPTION "Section Trace standard compliance."
    DEFVAL      { ansiItu }
    ::= { sonetClientCtpEntry  13 }


sonetClientCtpRxCv15MinutesTce OBJECT-TYPE
    SYNTAX      Counter64
    MAX-ACCESS  read-write
    STATUS      current
    DESCRIPTION "Count of received code violations in 15 minutes."
    ::= { sonetClientCtpEntry  14 }


sonetClientCtpRxSefs15MinutesTce OBJECT-TYPE
    SYNTAX      Integer32
    MAX-ACCESS  read-write
    STATUS      current
    DESCRIPTION "Count of seconds during which an LOF defect is present."
    DEFVAL      { 3 }
    ::= { sonetClientCtpEntry  15 }


sonetClientCtpRxEs15MinutesTce OBJECT-TYPE
    SYNTAX      Integer32
    MAX-ACCESS  read-write
    STATUS      current
    DESCRIPTION "Count of BIP errors detected at the Section layer in 15 minute
    (in the incoming clients SONET signal). Up to eight Section BIP errors can
    be detected per STS-N frame, with each error incrementing the Sonet-Rx-CV-S
    current second register."
    DEFVAL      { 120 }
    ::= { sonetClientCtpEntry  16 }


sonetClientCtpRxSes15MinutesTce OBJECT-TYPE
    SYNTAX      Integer32
    MAX-ACCESS  read-write
    STATUS      current
    DESCRIPTION "Count of the seconds during which30% or more RS block errors
    were detected or an LOS or SEF defect was present in 15 minutes."
    DEFVAL      { 3 }
    ::= { sonetClientCtpEntry  17 }


sonetClientCtpRxCvDayTce OBJECT-TYPE
    SYNTAX      Counter64
    MAX-ACCESS  read-write
    STATUS      current
    DESCRIPTION "Count of code violations in 24 hours."
    ::= { sonetClientCtpEntry  18 }


sonetClientCtpRxSefsDayTce OBJECT-TYPE
    SYNTAX      Integer32
    MAX-ACCESS  read-write
    STATUS      current
    DESCRIPTION "Count of seconds during which an LOF defect is present."
    DEFVAL      { 7 }
    ::= { sonetClientCtpEntry  19 }


sonetClientCtpRxEsDayTce OBJECT-TYPE
    SYNTAX      Integer32
    MAX-ACCESS  read-write
    STATUS      current
    DESCRIPTION "Count of BIP errors detected at the Section layer in 24 hours
    (in the incoming clients SONET signal). Up to eight Section BIP errors can
    be detected per STS-N frame, with each error incrementing the Sonet-Rx-CV-S
    current second register."
    DEFVAL      { 1200 }
    ::= { sonetClientCtpEntry  20 }


sonetClientCtpRxSesDayTce OBJECT-TYPE
    SYNTAX      Integer32
    MAX-ACCESS  read-write
    STATUS      current
    DESCRIPTION "Count of the seconds during which30% or more RS block errors
    were detected or an LOS or SEF defect was present in 24 hours."
    DEFVAL      { 7 }
    ::= { sonetClientCtpEntry  21 }


sonetClientCtpTxCv15MinutesTce OBJECT-TYPE
    SYNTAX      Counter64
    MAX-ACCESS  read-write
    STATUS      current
    DESCRIPTION "Count of BIP errors detected at the Section layer in the SONET
    signal received from the line/system side and to be transmitted to the
    receiving client. Up to eight Section BIP errors can be detected per STS-N
    frame, with each error incrementing the Sonet-Rx-CV-S current second
    register in 15 minutes."
    ::= { sonetClientCtpEntry  22 }


sonetClientCtpTxSefs15MinutesTce OBJECT-TYPE
    SYNTAX      Integer32
    MAX-ACCESS  read-write
    STATUS      current
    DESCRIPTION "Count of the seconds during which (at any point during the
    second) an SEF defect was present in 15 minutes."
    DEFVAL      { 3 }
    ::= { sonetClientCtpEntry  23 }


sonetClientCtpTxEs15MinutesTce OBJECT-TYPE
    SYNTAX      Integer32
    MAX-ACCESS  read-write
    STATUS      current
    DESCRIPTION "Count of the number of seconds during which (at any point during the
     second) at least one Tx RS block error was detected or an LOS or SEF defect was present in 15 minutes."
    DEFVAL      { 120 }
    ::= { sonetClientCtpEntry  24 }


sonetClientCtpTxSes15MinutesTce OBJECT-TYPE
    SYNTAX      Integer32
    MAX-ACCESS  read-write
    STATUS      current
    DESCRIPTION "Count of the seconds during which K (=10000) or more SONET
    TX BIP errors were detected or an LOS or SEF defect was present in 15 minutes."
    DEFVAL      { 3 }
    ::= { sonetClientCtpEntry  25 }


sonetClientCtpTxCvDayTce OBJECT-TYPE
    SYNTAX      Counter64
    MAX-ACCESS  read-write
    STATUS      current
    DESCRIPTION "Count of BIP errors detected at the Section layer in the SONET
     signal received from the line/system side and to be transmitted to the
     receiving client. Up to eight Section BIP errors can be detected per STS-N
     frame, with each error incrementing the Sonet-Rx-CV-S current second register in 24 hours."
    ::= { sonetClientCtpEntry  26 }


sonetClientCtpTxSefsDayTce OBJECT-TYPE
    SYNTAX      Integer32
    MAX-ACCESS  read-write
    STATUS      current
    DESCRIPTION "Count of the seconds during which (at any point during the
    second) an SEF defect was present in 24 hours."
    DEFVAL      { 7 }
    ::= { sonetClientCtpEntry  27 }


sonetClientCtpTxEsDayTce OBJECT-TYPE
    SYNTAX      Integer32
    MAX-ACCESS  read-write
    STATUS      current
    DESCRIPTION "Count of the number of seconds during which (at any point
    during the second) at least one Tx RS block error was detected or an LOS
    or SEF defect was present in 24 hours."
    DEFVAL      { 1200 }
    ::= { sonetClientCtpEntry  28 }


sonetClientCtpTxSesDayTce OBJECT-TYPE
    SYNTAX      Integer32
    MAX-ACCESS  read-write
    STATUS      current
    DESCRIPTION "Count of the seconds during which K (=10000) or more SONET
    TX BIP errors were detected or an LOS or SEF defect was present in 24 hours."
    DEFVAL      { 7 }
    ::= { sonetClientCtpEntry  29 }


sonetClientCtpRxCv15MinutesTceReporting OBJECT-TYPE
    SYNTAX      TruthValue
    MAX-ACCESS  read-write
    STATUS      current
    DESCRIPTION "Flag that enables the reporting of RxCv15MinutesTce threshold crossing."
    DEFVAL      { false }
    ::= { sonetClientCtpEntry  30 }


sonetClientCtpRxSefs15MinutesTceReporting OBJECT-TYPE
    SYNTAX      TruthValue
    MAX-ACCESS  read-write
    STATUS      current
    DESCRIPTION "Flag that enables the reporting of RxSefs15MinutesTce threshold crossing."
    DEFVAL      { false }
    ::= { sonetClientCtpEntry  31 }


sonetClientCtpRxEs15MinutesTceReporting OBJECT-TYPE
    SYNTAX      TruthValue
    MAX-ACCESS  read-write
    STATUS      current
    DESCRIPTION "Flag that enables the reporting of RxEs15Minutes threshold crossing."
    DEFVAL      { false }
    ::= { sonetClientCtpEntry  32 }


sonetClientCtpRxSes15MinutesTceReporting OBJECT-TYPE
    SYNTAX      TruthValue
    MAX-ACCESS  read-write
    STATUS      current
    DESCRIPTION "Flag that enables the reporting of RxSes15MinutesTce threshold crossing."
    DEFVAL      { false }
    ::= { sonetClientCtpEntry  33 }


sonetClientCtpRxCvDayTceReporting OBJECT-TYPE
    SYNTAX      TruthValue
    MAX-ACCESS  read-write
    STATUS      current
    DESCRIPTION "Flag that enables the reporting of RxCvDayTce threshold crossing."
    DEFVAL      { false }
    ::= { sonetClientCtpEntry  34 }


sonetClientCtpRxSefsDayTceReporting OBJECT-TYPE
    SYNTAX      TruthValue
    MAX-ACCESS  read-write
    STATUS      current
    DESCRIPTION "Flag that enables the reporting of RxSefs15MinutesTce threshold crossing."
    DEFVAL      { false }
    ::= { sonetClientCtpEntry  35 }


sonetClientCtpRxEsDayTceReporting OBJECT-TYPE
    SYNTAX      TruthValue
    MAX-ACCESS  read-write
    STATUS      current
    DESCRIPTION "Flag that enables the reporting of RxEsDayTce threshold crossing."
    DEFVAL      { false }
    ::= { sonetClientCtpEntry  36 }


sonetClientCtpRxSesDayTceReporting OBJECT-TYPE
    SYNTAX      TruthValue
    MAX-ACCESS  read-write
    STATUS      current
    DESCRIPTION "Flag that enables the reporting of RxSesDayTce threshold crossing."
    DEFVAL      { false }
    ::= { sonetClientCtpEntry  37 }


sonetClientCtpTxCv15MinutesTceReporting OBJECT-TYPE
    SYNTAX      TruthValue
    MAX-ACCESS  read-write
    STATUS      current
    DESCRIPTION "Flag that enables the reporting of TxCv15MinutesTce threshold crossing."
    DEFVAL      { false }
    ::= { sonetClientCtpEntry  38 }


sonetClientCtpTxSefs15MinutesTceReporting OBJECT-TYPE
    SYNTAX      TruthValue
    MAX-ACCESS  read-write
    STATUS      current
    DESCRIPTION "Flag that enables the reporting of TxSefs15MinutesTce crossing."
    DEFVAL      { false }
    ::= { sonetClientCtpEntry  39 }


sonetClientCtpTxEs15MinutesTceReporting OBJECT-TYPE
    SYNTAX      TruthValue
    MAX-ACCESS  read-write
    STATUS      current
    DESCRIPTION "Flag that enables the reporting of TxEs15MinutesTce crossing."
    DEFVAL      { false }
    ::= { sonetClientCtpEntry  40 }


sonetClientCtpTxSes15MinutesTceReporting OBJECT-TYPE
    SYNTAX      TruthValue
    MAX-ACCESS  read-write
    STATUS      current
    DESCRIPTION "Flag that enables the reporting of TxSes15MinutesTce crossing."
    DEFVAL      { false }
    ::= { sonetClientCtpEntry  41 }


sonetClientCtpTxCvDayTceReporting OBJECT-TYPE
    SYNTAX      TruthValue
    MAX-ACCESS  read-write
    STATUS      current
    DESCRIPTION "Flag that enables the reporting of TxCvDayTcethreshold crossing."
    DEFVAL      { false }
    ::= { sonetClientCtpEntry  42 }


sonetClientCtpTxSefsDayTceReporting OBJECT-TYPE
    SYNTAX      TruthValue
    MAX-ACCESS  read-write
    STATUS      current
    DESCRIPTION "Flag that enables the reporting of TxSefsDayTce crossing."
    DEFVAL      { false }
    ::= { sonetClientCtpEntry  43 }


sonetClientCtpTxEsDayTceReporting OBJECT-TYPE
    SYNTAX      TruthValue
    MAX-ACCESS  read-write
    STATUS      current
    DESCRIPTION "Flag that enables the reporting of TxEsDayTce crossing."
    DEFVAL      { false }
    ::= { sonetClientCtpEntry  44 }


sonetClientCtpTxSesDayTceReporting OBJECT-TYPE
    SYNTAX      TruthValue
    MAX-ACCESS  read-write
    STATUS      current
    DESCRIPTION "Flag that enables the reporting of TxSefsDayTce crossing."
    DEFVAL      { false }
    ::= { sonetClientCtpEntry  45 }

sonetClientCtpLinePrbsGenMode OBJECT-TYPE
    SYNTAX   InfnEnableDisable
    MAX-ACCESS  read-write
    STATUS      current
    DESCRIPTION "Flag which enables the generation of PRBS data on the Line side."
    DEFVAL      { disabled }
    ::= { sonetClientCtpEntry  46 }


sonetClientCtpLinePrbsMonMode OBJECT-TYPE
    SYNTAX  InfnEnableDisable
    MAX-ACCESS  read-write
    STATUS      current
    DESCRIPTION "Flag which enables the monitoring of bit errors."
    DEFVAL      { disabled }
    ::= { sonetClientCtpEntry  47 }

sonetClientCtpServiceMode 	OBJECT-TYPE
    SYNTAX     InfnServiceMode
    MAX-ACCESS read-only
    STATUS     current
    DESCRIPTION
        "The Service Mode (SM) of the client CTP (i.e., the mode/type of service in which
        this sonet client CTP is being used."
    ::= { sonetClientCtpEntry 48 }

sonetClientCtpServiceModeQualifier 	OBJECT-TYPE
    SYNTAX     InfnSMQ
    MAX-ACCESS read-only
    STATUS     current
    DESCRIPTION
        "The Service Mode Qualifier (SMQ) of the sonet client CTP
    (i.e., the mode/type of service in which this sonet client CTP is being used."
    ::= { sonetClientCtpEntry 49 }

sonetClientCtpEncapClientDisableAction OBJECT-TYPE
    SYNTAX   InfnClientAction
    MAX-ACCESS  read-write
    STATUS      current
    DESCRIPTION ""
    ::= { sonetClientCtpEntry 50 }

-- Conformance Statements
sonetClientCtpConformance    OBJECT IDENTIFIER ::= { sonetClientCtpMIB 3 }
sonetClientCtpCompliances    OBJECT IDENTIFIER ::= { sonetClientCtpConformance 1 }
sonetClientCtpGroups         OBJECT IDENTIFIER ::= { sonetClientCtpConformance 2 }

sonetClientCtpCompliance MODULE-COMPLIANCE
    STATUS current
    DESCRIPTION
    "Describes the requirements for conformance to the SONETCLIENTCTP-MIB"
    MODULE
        MANDATORY-GROUPS { sonetClientCtpGroup }
    ::= { sonetClientCtpCompliances 1 }

sonetClientCtpGroup OBJECT-GROUP
    OBJECTS {
        sonetClientCtpTribPrbsGenMode,
        sonetClientCtpTribPrbsMonMode,
        sonetClientCtpSupportingCircuitIdList,
        sonetClientCtpLoopback,
        sonetClientCtpPmHistStatsEnable,
        sonetClientCtpConfiguredServiceType,
        sonetClientCtpRxJ0,
        sonetClientCtpExpectedRxJ0,
        sonetClientCtpTransmittedJ0,
        sonetClientCtpRxJ0MessageLength,
        sonetClientCtpRxJ0MismatchReporting,
        sonetClientCtpRxJ0TraceMode,
        sonetClientCtpRxJ0MessageCompliance,
        sonetClientCtpRxCv15MinutesTce,
        sonetClientCtpRxSefs15MinutesTce,
        sonetClientCtpRxEs15MinutesTce,
        sonetClientCtpRxSes15MinutesTce,
        sonetClientCtpRxCvDayTce,
        sonetClientCtpRxSefsDayTce,
        sonetClientCtpRxEsDayTce,
        sonetClientCtpRxSesDayTce,
        sonetClientCtpTxCv15MinutesTce,
        sonetClientCtpTxSefs15MinutesTce,
        sonetClientCtpTxEs15MinutesTce,
        sonetClientCtpTxSes15MinutesTce,
        sonetClientCtpTxCvDayTce,
        sonetClientCtpTxSefsDayTce,
        sonetClientCtpTxEsDayTce,
        sonetClientCtpTxSesDayTce,
        sonetClientCtpRxCv15MinutesTceReporting,
        sonetClientCtpRxSefs15MinutesTceReporting,
        sonetClientCtpRxEs15MinutesTceReporting,
        sonetClientCtpRxSes15MinutesTceReporting,
        sonetClientCtpRxCvDayTceReporting,
        sonetClientCtpRxSefsDayTceReporting,
        sonetClientCtpRxEsDayTceReporting,
        sonetClientCtpRxSesDayTceReporting,
        sonetClientCtpTxCv15MinutesTceReporting,
        sonetClientCtpTxSefs15MinutesTceReporting,
        sonetClientCtpTxEs15MinutesTceReporting,
        sonetClientCtpTxSes15MinutesTceReporting,
        sonetClientCtpTxCvDayTceReporting,
        sonetClientCtpTxSefsDayTceReporting,
        sonetClientCtpTxEsDayTceReporting,
        sonetClientCtpTxSesDayTceReporting,
        sonetClientCtpLinePrbsGenMode,
        sonetClientCtpLinePrbsMonMode,
    	sonetClientCtpServiceMode,
	    sonetClientCtpServiceModeQualifier        ,
        sonetClientCtpEncapClientDisableAction
    }
    STATUS current
    DESCRIPTION
        " A collection of objects for managing the sonetClientCtp"
    ::= { sonetClientCtpGroups 1 }


END
