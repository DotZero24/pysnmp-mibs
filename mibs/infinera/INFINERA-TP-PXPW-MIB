-- *****************************************************************
-- INFINERA-TP-PXPW-MIB
--
-- Mithun Murthy/ Divyank Rastogi
--
--
-- Copyright (c) 2008-2012 by Infinera Inc.
-- All rights reserved.
-- ****************************************************************

INFINERA-TP-PXPW-MIB DEFINITIONS ::= BEGIN

IMPORTS
    MODULE-IDENTITY, OBJECT-TYPE, Integer32     FROM SNMPv2-SMI
    MODULE-COMPLIANCE, OBJECT-GROUP             FROM SNMPv2-CONF
    DisplayString                               FROM SNMPv2-TC
    ifIndex                                     FROM IF-MIB
	FloatTenths, FloatHundredths,
	InfnPmHistStatsControl,InfnFlapActionClear,
	InfnCreationType, InfnPWSetupMode			FROM INFINERA-TC-MIB
    terminationPoint                            FROM INFINERA-REG-MIB;

pxmPwMIB MODULE-IDENTITY
    LAST-UPDATED  "201605200000Z"
    ORGANIZATION
        "Infinera"
    CONTACT-INFO
        "Infinera
                1322 Bordeaux Drive
                Sunnyvale, CA - 94089

                Contact : Technical Support
                Email   : support@infinera.com
                Phone   : 1-877-INF-5288"
    DESCRIPTION
        " "

    REVISION  "201605200000Z"
    DESCRIPTION
        " "
::= { terminationPoint 75 }


pxmPwConformance   OBJECT IDENTIFIER ::= { pxmPwMIB 3 }
pxmPwCompliances   OBJECT IDENTIFIER ::= { pxmPwConformance 1 }
pxmPwGroups        OBJECT IDENTIFIER ::= { pxmPwConformance 2 }

pxmPwTable  OBJECT-TYPE
    SYNTAX SEQUENCE OF PxmPwEntry
    MAX-ACCESS not-accessible
    STATUS     current
    DESCRIPTION
        "A list of PxmPw entries. Each entry is uniquely identified by
                the value of ifIndex."
    ::= { pxmPwMIB 1 }

pxmPwEntry  OBJECT-TYPE
    SYNTAX     PxmPwEntry
    MAX-ACCESS not-accessible
    STATUS     current
    DESCRIPTION
        "A PxmPw entry containing information pertaining to
                Infinera PxmPw interfaces. This table is a subclass of IfCommon.
                Entries will exist in this table only for interfaces of type PxmPw."
    INDEX { ifIndex }
    ::= { pxmPwTable 1 }

PxmPwEntry  ::= SEQUENCE {
	pxmPwMTUSize			Integer32,
	pxmPwSetupMode			InfnPWSetupMode,
	pxmPwIncomingLabel		Integer32,
	pxmPwOutgoingLabel		Integer32,
	pxmPwCreationType		InfnCreationType,
	pxmPwPmHistStatsEnable	InfnPmHistStatsControl,
	pxmPwSplitHorizonGroupID Integer32,
	pxmPwFlapActionClear	InfnFlapActionClear,
        pxmPwAssociatedMPLSTunnel DisplayString
}

pxmPwMTUSize	OBJECT-TYPE
    SYNTAX     	Integer32
    MAX-ACCESS	read-only
    STATUS     	current
    DESCRIPTION
        ""
    ::= { pxmPwEntry 1 }

pxmPwSetupMode	OBJECT-TYPE
    SYNTAX     InfnPWSetupMode
    MAX-ACCESS read-write
    STATUS     current
    DESCRIPTION
        ""
    ::= { pxmPwEntry 2 }

pxmPwIncomingLabel	OBJECT-TYPE
    SYNTAX     Integer32
    MAX-ACCESS read-only
    STATUS     current
    DESCRIPTION
        ""
    ::= { pxmPwEntry 3 }

pxmPwOutgoingLabel	OBJECT-TYPE
    SYNTAX   	Integer32
    MAX-ACCESS read-only
    STATUS     current
    DESCRIPTION
        ""
    ::= { pxmPwEntry 4 }

pxmPwCreationType		OBJECT-TYPE
    SYNTAX     InfnCreationType
    MAX-ACCESS read-only
    STATUS     current
    DESCRIPTION
        ""
    ::= { pxmPwEntry 5 }

pxmPwPmHistStatsEnable	OBJECT-TYPE
    SYNTAX     InfnPmHistStatsControl
    MAX-ACCESS read-write
    STATUS     current
    DESCRIPTION
        ""
    ::= { pxmPwEntry 6 }

pxmPwSplitHorizonGroupID	OBJECT-TYPE
    SYNTAX    Integer32
    MAX-ACCESS read-only
    STATUS     current
    DESCRIPTION
        ""
    ::= { pxmPwEntry  7 }

pxmPwFlapActionClear	OBJECT-TYPE
    SYNTAX     InfnFlapActionClear
    MAX-ACCESS read-write
    STATUS     current
    DESCRIPTION
        ""
    ::= { pxmPwEntry  8 }

pxmPwAssociatedMPLSTunnel    OBJECT-TYPE
    SYNTAX     DisplayString
    MAX-ACCESS read-write
    STATUS     current
    DESCRIPTION
        ""
    ::= { pxmPwEntry  9 }

pxmPwCompliance  MODULE-COMPLIANCE
    STATUS     current
    DESCRIPTION
        "Describes the requirements for conformance to the TRIBPTP-MIB"
    MODULE
        MANDATORY-GROUPS { pxmPwGroup }
    ::= { pxmPwCompliances 1 }

pxmPwGroup  OBJECT-GROUP
    OBJECTS {
		pxmPwMTUSize,
		pxmPwSetupMode,
		pxmPwIncomingLabel,
		pxmPwOutgoingLabel,
		pxmPwCreationType,
		pxmPwPmHistStatsEnable,
		pxmPwSplitHorizonGroupID,
 		pxmPwFlapActionClear,
                pxmPwAssociatedMPLSTunnel
	}
    STATUS     current
    DESCRIPTION
        " A collection of objects for managing pxmPw interfaces."
    ::= { pxmPwGroups 1 }
END
