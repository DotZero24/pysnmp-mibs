-- ***************************************************************
-- INFINERA-PM-OTDRTESTRESULT-MIB
--
--
-- Copyright (c) 2011-2012 by Infinera Inc.
-- All rights reserved.
-- ****************************************************************

INFINERA-TP-OTDRTESTRESULT-MIB DEFINITIONS ::= BEGIN

IMPORTS
    OBJECT-TYPE, MODULE-IDENTITY            FROM SNMPv2-SMI
    OBJECT-GROUP, MODULE-COMPLIANCE         FROM SNMPv2-CONF
    DisplayString                           FROM SNMPv2-TC
    --entLPPhysicalIndex                      FROM ENTITY-MIB
	ifIndex								   FROM IF-MIB
    FloatHundredths,InfnOtdrTestExecutionType,
    InfnOtdrTestAcquisitionMode, InfnFiberType,
	InfnOtdrPtpConnState, InfnOtdrTestPulseWidth,
	InfnOtdrFileUploadStatus 	            FROM INFINERA-TC-MIB
    terminationPoint						FROM INFINERA-REG-MIB;

otdrTestResultMIB MODULE-IDENTITY
    LAST-UPDATED  "201310200000Z"
    ORGANIZATION "INFINERA"
    CONTACT-INFO
        "Infinera
        169 Java Drive
        Sunnyvale, CA - 94089

        Contact : Technical Support
        Email   : support@infinera.com
        Phone   : 1-877-INF-5288 "
        DESCRIPTION
        "This MIB is modeling for OTDRTESTRESULT equipment table"

::= { terminationPoint 62 }

otdrTestResultConformance       OBJECT IDENTIFIER ::= { otdrTestResultMIB 3 }
otdrTestResultCompliances       OBJECT IDENTIFIER ::= { otdrTestResultConformance 1 }
otdrTestResultGroups            OBJECT IDENTIFIER ::= { otdrTestResultConformance 2 }

otdrTestResultTable  OBJECT-TYPE
    SYNTAX SEQUENCE OF OtdrTestResultEntry
    MAX-ACCESS not-accessible
    STATUS     current
    DESCRIPTION
        "This table contains all OTDRTESTRESULT modules that are currently present in a network element.
        "
    ::= { otdrTestResultMIB 1 }

otdrTestResultEntry  OBJECT-TYPE
    SYNTAX     OtdrTestResultEntry
    MAX-ACCESS not-accessible
    STATUS     current
    DESCRIPTION
        "A row in the OTDRTESTRESULT table. Each row in the table is identified with a unique entPhysicalIndexID."
    --INDEX { entLPPhysicalIndex }
	INDEX { ifIndex }
    ::= { otdrTestResultTable 1 }

OtdrTestResultEntry ::= SEQUENCE {
    otdrTestResultTimeStamp                 Integer32,
    otdrTestResultOtdmSerialNumber          DisplayString,
    otdrTestResultOtdmPortId                DisplayString,
    otdrTestResultTestExecutionType         InfnOtdrTestExecutionType,
    otdrTestResultAcquisitionMode           InfnOtdrTestAcquisitionMode,
    otdrTestResultProvisionedNeighborPtp    DisplayString,
    otdrTestResultConnectivityState         InfnOtdrPtpConnState,
    otdrTestResultTestCableID               DisplayString,
    otdrTestResultTestFiberID               DisplayString,
    otdrTestResultTestFiberType             InfnFiberType,
    otdrTestResultDataPointsCount           Integer32,
    otdrTestResultKeyEventsCount            Integer32,
    otdrTestResultEndToEndLoss              FloatHundredths,
    otdrTestResultOpticalReturnLoss         FloatHundredths,
    otdrTestResultUnitsOfDistance           DisplayString,
    otdrTestResultPulseWidth                InfnOtdrTestPulseWidth,
    otdrTestResultDataSpacing               FloatHundredths,
    otdrTestResultBackScatterCoefficient    Integer32,
    otdrTestResultTestAcquisitionTime       Integer32,
    otdrTestResultAcquisitionRange          Integer32,
    otdrTestResultAcquisitionRangeDistance  Integer32,
    otdrTestResultEventLossThreshold        FloatHundredths,
    otdrTestResultReflectanceThreshold      Integer32,
    otdrTestResultEndOfFiberThreshold       Integer32,
    otdrTestResultUploadStatus             	InfnOtdrFileUploadStatus
    }

otdrTestResultTimeStamp     OBJECT-TYPE
    SYNTAX      Integer32
    MAX-ACCESS  read-only
    STATUS      current
    DESCRIPTION ""
    ::= { otdrTestResultEntry 1 }

otdrTestResultOtdmSerialNumber  OBJECT-TYPE
    SYNTAX      DisplayString
    MAX-ACCESS  read-only
    STATUS      current
    DESCRIPTION ""
    ::= { otdrTestResultEntry 2 }

otdrTestResultOtdmPortId    OBJECT-TYPE
    SYNTAX      DisplayString
    MAX-ACCESS  read-only
    STATUS      current
    DESCRIPTION ""
    ::= { otdrTestResultEntry 3 }


otdrTestResultTestExecutionType     OBJECT-TYPE
    SYNTAX      InfnOtdrTestExecutionType
    MAX-ACCESS  read-only
    STATUS      current
    DESCRIPTION ""
    ::= { otdrTestResultEntry 4 }

otdrTestResultAcquisitionMode   OBJECT-TYPE
    SYNTAX      InfnOtdrTestAcquisitionMode
    MAX-ACCESS  read-only
    STATUS      current
    DESCRIPTION ""
    ::= { otdrTestResultEntry 5 }

otdrTestResultProvisionedNeighborPtp   OBJECT-TYPE
    SYNTAX      DisplayString
    MAX-ACCESS  read-only
    STATUS      current
    DESCRIPTION ""
    ::= {  otdrTestResultEntry 6 }

otdrTestResultConnectivityState    OBJECT-TYPE
    SYNTAX      InfnOtdrPtpConnState
    MAX-ACCESS  read-only
    STATUS      current
    DESCRIPTION ""
    ::= {  otdrTestResultEntry 7 }

otdrTestResultTestCableID OBJECT-TYPE
    SYNTAX      DisplayString
    MAX-ACCESS  read-only
    STATUS      current
    DESCRIPTION ""
    ::= { otdrTestResultEntry 8 }

otdrTestResultTestFiberID   OBJECT-TYPE
    SYNTAX      DisplayString
    MAX-ACCESS  read-only
    STATUS      current
    DESCRIPTION ""
    ::= { otdrTestResultEntry 9 }

otdrTestResultTestFiberType OBJECT-TYPE
    SYNTAX      InfnFiberType
    MAX-ACCESS  read-only
    STATUS      current
    DESCRIPTION ""
    ::= { otdrTestResultEntry 10 }

otdrTestResultDataPointsCount OBJECT-TYPE
    SYNTAX      Integer32
    MAX-ACCESS  read-only
    STATUS      current
    DESCRIPTION ""
    ::= { otdrTestResultEntry 11 }

otdrTestResultKeyEventsCount OBJECT-TYPE
    SYNTAX      Integer32
    MAX-ACCESS  read-only
    STATUS      current
    DESCRIPTION ""
    ::= { otdrTestResultEntry 12 }

otdrTestResultEndToEndLoss  OBJECT-TYPE
    SYNTAX      FloatHundredths
    MAX-ACCESS  read-only
    STATUS      current
    DESCRIPTION ""
    ::= { otdrTestResultEntry 13 }

otdrTestResultOpticalReturnLoss OBJECT-TYPE
    SYNTAX      FloatHundredths
    MAX-ACCESS  read-only
    STATUS      current
    DESCRIPTION ""
    ::= { otdrTestResultEntry 14 }

otdrTestResultUnitsOfDistance   OBJECT-TYPE
    SYNTAX      DisplayString
    MAX-ACCESS  read-only
    STATUS      current
    DESCRIPTION ""
    ::= { otdrTestResultEntry 15 }

otdrTestResultPulseWidth OBJECT-TYPE
    SYNTAX     	InfnOtdrTestPulseWidth
    MAX-ACCESS  read-only
    STATUS      current
    DESCRIPTION  ""
    ::= { otdrTestResultEntry 16 }

otdrTestResultDataSpacing   OBJECT-TYPE
    SYNTAX      FloatHundredths
    MAX-ACCESS  read-only
    STATUS      current
    DESCRIPTION ""
    ::= { otdrTestResultEntry 17 }

otdrTestResultBackScatterCoefficient    OBJECT-TYPE
    SYNTAX      Integer32
    MAX-ACCESS  read-only
    STATUS      current
    DESCRIPTION ""
    ::= { otdrTestResultEntry 18 }

otdrTestResultTestAcquisitionTime   OBJECT-TYPE
    SYNTAX      Integer32
    MAX-ACCESS  read-only
    STATUS      current
    DESCRIPTION ""
    ::= { otdrTestResultEntry 19 }

otdrTestResultAcquisitionRange  OBJECT-TYPE
    SYNTAX      Integer32
    MAX-ACCESS  read-only
    STATUS      current
    DESCRIPTION ""
    ::= { otdrTestResultEntry 20 }

otdrTestResultAcquisitionRangeDistance  OBJECT-TYPE
    SYNTAX      Integer32
    MAX-ACCESS  read-only
    STATUS      current
    DESCRIPTION ""
    ::= { otdrTestResultEntry 21 }

otdrTestResultEventLossThreshold    OBJECT-TYPE
    SYNTAX      FloatHundredths
    MAX-ACCESS  read-only
    STATUS      current
    DESCRIPTION ""
    ::= { otdrTestResultEntry 22 }

otdrTestResultReflectanceThreshold  OBJECT-TYPE
    SYNTAX      Integer32
    MAX-ACCESS  read-only
    STATUS      current
    DESCRIPTION ""
    ::= { otdrTestResultEntry 23 }

otdrTestResultEndOfFiberThreshold   OBJECT-TYPE
    SYNTAX      Integer32
    MAX-ACCESS  read-only
    STATUS      current
    DESCRIPTION ""
    ::= { otdrTestResultEntry 24 }

otdrTestResultUploadStatus OBJECT-TYPE
    SYNTAX      InfnOtdrFileUploadStatus
    MAX-ACCESS  read-only
    STATUS      current
    DESCRIPTION ""
    ::= { otdrTestResultEntry 25 }


otdrTestResultCompliance  MODULE-COMPLIANCE
    STATUS      current
    DESCRIPTION ""
    MODULE
        MANDATORY-GROUPS { otdrTestResultGroup }
    ::= { otdrTestResultCompliances 1 }

otdrTestResultGroup  OBJECT-GROUP
    OBJECTS {
    otdrTestResultTimeStamp                 ,
    otdrTestResultOtdmSerialNumber          ,
    otdrTestResultOtdmPortId                ,
    otdrTestResultTestExecutionType         ,
    otdrTestResultAcquisitionMode           ,
    otdrTestResultProvisionedNeighborPtp    ,
    otdrTestResultConnectivityState         ,
    otdrTestResultTestCableID               ,
    otdrTestResultTestFiberID               ,
    otdrTestResultTestFiberType             ,
    otdrTestResultDataPointsCount           ,
    otdrTestResultKeyEventsCount            ,
    otdrTestResultEndToEndLoss              ,
    otdrTestResultOpticalReturnLoss         ,
    otdrTestResultUnitsOfDistance           ,
    otdrTestResultPulseWidth                ,
    otdrTestResultDataSpacing               ,
    otdrTestResultBackScatterCoefficient    ,
    otdrTestResultTestAcquisitionTime      ,
    otdrTestResultAcquisitionRange          ,
    otdrTestResultAcquisitionRangeDistance  ,
    otdrTestResultEventLossThreshold        ,
    otdrTestResultReflectanceThreshold      ,
    otdrTestResultEndOfFiberThreshold       ,
    otdrTestResultUploadStatus

    }
    STATUS          current
    DESCRIPTION     ""
    ::= { otdrTestResultGroups 1 }
END
