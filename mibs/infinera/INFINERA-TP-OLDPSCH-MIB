-- *****************************************************************
-- INFINERA-TP-OLDPSCH-MIB
-- Copyright (c) 2013-2014 by Infinera Inc.
-- All rights reserved.
-- ****************************************************************

INFINERA-TP-OLDPSCH-MIB DEFINITIONS ::= BEGIN

IMPORTS
    MODULE-IDENTITY, OBJECT-TYPE                FROM SNMPv2-SMI
    MODULE-COMPLIANCE, OBJECT-GROUP             FROM SNMPv2-CONF
    DisplayString                               FROM SNMPv2-TC
    ifIndex                                     FROM IF-MIB
    InfnTimReptMode, InfnMonitoringMode		    FROM INFINERA-TC-MIB
    terminationPoint                            FROM INFINERA-REG-MIB;

oldpSchMIB MODULE-IDENTITY
    LAST-UPDATED  "201608290000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "201608290000Z"
    DESCRIPTION
        "First Version"
    ::= { terminationPoint 58 }

oldpSchTable OBJECT-TYPE
    SYNTAX      SEQUENCE OF OldpSchEntry
    MAX-ACCESS  not-accessible
    STATUS      current
    DESCRIPTION
        "A list of OldpSch entries. Each entry is uniquely identified by the value of ifIndex."
    ::= { oldpSchMIB 1 }

oldpSchEntry  OBJECT-TYPE
    SYNTAX      OldpSchEntry
    MAX-ACCESS  not-accessible
    STATUS      current
    DESCRIPTION
        "A OldpSch entry containing information pertaining to Infinera OldpSch Interfaces.
        This table is a subclass of IfCommon. Entries will exist in this table only for
        interfaces of type SCH CTP."
    INDEX { ifIndex }
    ::= { oldpSchTable 1 }


OldpSchEntry  ::= SEQUENCE {
     transmitTTI                   DisplayString,
     recievedTTI                   DisplayString,
     expectedSAPI                  DisplayString,
     expectedDAPI                  DisplayString,
     timDetMode                    InfnTimReptMode,
     monitoringMode                InfnMonitoringMode
    }

transmitTTI   OBJECT-TYPE
     SYNTAX      DisplayString
     MAX-ACCESS  read-write
     STATUS      current
     DESCRIPTION ""
     ::= { oldpSchEntry 1 }

recievedTTI   OBJECT-TYPE
     SYNTAX      DisplayString
     MAX-ACCESS  read-only
     STATUS      current
     DESCRIPTION ""
     ::= { oldpSchEntry 2 }

expectedSAPI  OBJECT-TYPE
     SYNTAX      DisplayString
     MAX-ACCESS  read-write
     STATUS      current
     DESCRIPTION ""
     ::= { oldpSchEntry 3 }

expectedDAPI      OBJECT-TYPE
     SYNTAX      DisplayString
     MAX-ACCESS  read-write
     STATUS      current
     DESCRIPTION ""
     ::= { oldpSchEntry 4 }

timDetMode        OBJECT-TYPE
     SYNTAX      InfnTimReptMode
     MAX-ACCESS  read-write
     STATUS      current
     DESCRIPTION ""
    ::= { oldpSchEntry 5 }

monitoringMode    OBJECT-TYPE
     SYNTAX      InfnMonitoringMode
     MAX-ACCESS  read-write
     STATUS      current
     DESCRIPTION ""
     ::= { oldpSchEntry 6 }

--  Conformance Statements
oldpSchConformance    OBJECT IDENTIFIER ::= { oldpSchMIB 3 }
oldpSchCompliances    OBJECT IDENTIFIER ::= { oldpSchConformance 1 }
oldpSchGroups         OBJECT IDENTIFIER ::= { oldpSchConformance 2 }

oldpSchCompliance MODULE-COMPLIANCE
    STATUS current
    DESCRIPTION
    "Describes the requirements for conformance to the OLDPSCH-MIB"
    MODULE
        MANDATORY-GROUPS { oldpSchGroup }
    ::= { oldpSchCompliances 1 }

oldpSchGroup OBJECT-GROUP
    OBJECTS {
     transmitTTI,
	 recievedTTI,
     expectedSAPI,
     expectedDAPI,
     timDetMode,
     monitoringMode
    }
    STATUS current
    DESCRIPTION
        " A collection of objects for managing the OldpSch"
    ::= { oldpSchGroups 1 }

END
