-- ***************************************************************
-- INFINERA-ENTITY-OTP-MIB
--
-- Jan 2015, Kavitha Manjunatha
--
--
-- Copyright (c) 2010-2012 by Infinera Inc.
-- All rights reserved.
-- ****************************************************************

INFINERA-ENTITY-OTP-MIB DEFINITIONS ::= BEGIN

IMPORTS
    OBJECT-TYPE, MODULE-IDENTITY        FROM SNMPv2-SMI
    OBJECT-GROUP, MODULE-COMPLIANCE     FROM SNMPv2-CONF
    RowStatus, DisplayString            FROM SNMPv2-TC
    entLPPhysicalIndex                  FROM ENTITY-MIB
    equipment                           FROM INFINERA-REG-MIB
    InfnEqptType                        FROM INFINERA-TC-MIB;

otpMIB MODULE-IDENTITY
    LAST-UPDATED  "201501080000Z"
    ORGANIZATION
        "INFINERA"
    CONTACT-INFO
        "Infinera
        169 Java Drive
        Sunnyvale, CA - 94089

        Contact : Technical Support
        Email   : support@infinera.com
        Phone   : 1-877-INF-5288"
    DESCRIPTION
        "This MIB is modeling for OTP equipment table."

::= { equipment 39 }

otpConformance       OBJECT IDENTIFIER ::= { otpMIB 3 }
otpCompliances       OBJECT IDENTIFIER ::= { otpConformance 1 }
otpGroups            OBJECT IDENTIFIER ::= { otpConformance 2 }

otpTable  OBJECT-TYPE
    SYNTAX SEQUENCE OF OtpEntry
    MAX-ACCESS not-accessible
    STATUS     current
    DESCRIPTION
        "This table contains all SCM modules that are currently present in a network element.
        "
    ::= { otpMIB 1 }

otpEntry  OBJECT-TYPE
    SYNTAX     OtpEntry
    MAX-ACCESS not-accessible
    STATUS     current
    DESCRIPTION
        "A row in the SCM table. Each row in the table is identified with a unique entPhysicalIndexID.
        "
    INDEX { entLPPhysicalIndex }
    ::= { otpTable 1 }


OtpEntry ::= SEQUENCE {
    otpMoId             DisplayString,
    otpProvEqptType     InfnEqptType,
    otpProvSerialNumber DisplayString
}

otpMoId  OBJECT-TYPE
    SYNTAX     DisplayString
    MAX-ACCESS read-create
    STATUS     current
    DESCRIPTION
        "This is the primary Key of the objects e.g 1-A-1"
    ::= { otpEntry 1 }

otpProvEqptType  OBJECT-TYPE
    SYNTAX     InfnEqptType
    MAX-ACCESS read-create
    STATUS     current
    DESCRIPTION
        "User provisioned SCM type."
    ::= { otpEntry 2 }

otpProvSerialNumber OBJECT-TYPE
    SYNTAX      DisplayString
    MAX-ACCESS  read-write
    STATUS      current
    DESCRIPTION ""
    ::= { otpEntry 3 }

otpCompliance  MODULE-COMPLIANCE
    STATUS     current
    DESCRIPTION
        "Describes the requirements for conformance to the OTP-MIB"
    MODULE
        MANDATORY-GROUPS { otpGroup }
    ::= { otpCompliances 1 }

otpGroup  OBJECT-GROUP
    OBJECTS {
        otpMoId,
        otpProvEqptType,
        otpProvSerialNumber
    }
    STATUS     current
    DESCRIPTION
        " A collection of objects for managing a BMM module"
    ::= { otpGroups 1 }
END
