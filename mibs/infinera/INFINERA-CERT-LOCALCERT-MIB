-- *****************************************************************
-- INFINERA-CERT-LOCALCERT
--
-- October 2016, Kavitha Manjunatha
--
--
-- Copyright (c) 2008-2012 by Infinera Inc.
-- All rights reserved.
-- ****************************************************************

INFINERA-CERT-LOCALCERT-MIB DEFINITIONS ::= BEGIN

IMPORTS
    MODULE-IDENTITY, OBJECT-TYPE                FROM SNMPv2-SMI
    MODULE-COMPLIANCE, OBJECT-GROUP             FROM SNMPv2-CONF
    cert                                        FROM INFINERA-REG-MIB
    ifIndex                                     FROM IF-MIB
    DisplayString                               FROM SNMPv2-TC
    InfnX509Version, InfnX509Encoding,
    InfnX509Status                              FROM INFINERA-TC-MIB
    ;

localCertMIB MODULE-IDENTITY
    LAST-UPDATED  "201610100000Z"
    ORGANIZATION
        "Infinera"
    CONTACT-INFO
        "Infinera
                1322 Bordeaux Drive
                Sunnyvale, CA - 94089

                Contact : Technical Support
                Email   : support@infinera.com
                Phone   : 1-877-INF-5288"
    DESCRIPTION
        " "

    REVISION  "201601010000Z"
    DESCRIPTION
        " "
::= { cert 1 }

localCertTable  OBJECT-TYPE
    SYNTAX SEQUENCE OF LocalCertEntry
    MAX-ACCESS not-accessible
    STATUS     current
    DESCRIPTION
        "A list of LocalCert entries. Each entry is uniquely identified by
                the value of ifIndex."
    ::= { localCertMIB 1 }

localCertEntry  OBJECT-TYPE
    SYNTAX     LocalCertEntry
    MAX-ACCESS not-accessible
    STATUS     current
    DESCRIPTION
        "A localCert entry containing information pertaining to Infinera localCerts"
    INDEX { ifIndex }
    ::= { localCertTable 1 }

LocalCertEntry  ::= SEQUENCE {
    localCertMoId                    DisplayString,
    localCertSerialNumber            DisplayString,
    localCertVersion                 InfnX509Version,
    localCertIssuer                  DisplayString,
    localCertSubject                 DisplayString,
    localCertValidFrom               DisplayString,
    localCertValidTo                 DisplayString,
    localCertEncoding                InfnX509Encoding,
    localCertStatus                  InfnX509Status,
    localCertPublicKeyAlgorithm      DisplayString,
    localCertPublicKeyLength         Integer32,
    localCertSignatureAlgorithm      DisplayString
}

localCertMoId   OBJECT-TYPE
    SYNTAX      DisplayString
    MAX-ACCESS  read-only
    STATUS      current
    DESCRIPTION ""
    ::= { localCertEntry 1 }

localCertSerialNumber   OBJECT-TYPE
    SYNTAX      DisplayString
    MAX-ACCESS  read-only
    STATUS      current
    DESCRIPTION ""
    ::= { localCertEntry 2 }

localCertVersion   OBJECT-TYPE
    SYNTAX      InfnX509Version
    MAX-ACCESS  read-only
    STATUS      current
    DESCRIPTION ""
    ::= { localCertEntry 3 }

localCertIssuer   OBJECT-TYPE
    SYNTAX      DisplayString
    MAX-ACCESS  read-only
    STATUS      current
    DESCRIPTION ""
    ::= { localCertEntry 4 }

localCertSubject   OBJECT-TYPE
    SYNTAX      DisplayString
    MAX-ACCESS  read-only
    STATUS      current
    DESCRIPTION ""
    ::= { localCertEntry 5 }

localCertValidFrom   OBJECT-TYPE
    SYNTAX      DisplayString
    MAX-ACCESS  read-only
    STATUS      current
    DESCRIPTION ""
    ::= { localCertEntry 6 }

localCertValidTo   OBJECT-TYPE
    SYNTAX      DisplayString
    MAX-ACCESS  read-only
    STATUS      current
    DESCRIPTION ""
    ::= { localCertEntry 7 }

localCertEncoding   OBJECT-TYPE
    SYNTAX      InfnX509Encoding
    MAX-ACCESS  read-write
    STATUS      current
    DESCRIPTION ""
    ::= { localCertEntry 8 }

localCertStatus   OBJECT-TYPE
    SYNTAX      InfnX509Status
    MAX-ACCESS  read-only
    STATUS      current
    DESCRIPTION ""
    ::= { localCertEntry 9 }

localCertPublicKeyAlgorithm   OBJECT-TYPE
    SYNTAX      DisplayString
    MAX-ACCESS  read-only
    STATUS      current
    DESCRIPTION ""
    ::= { localCertEntry 10 }

localCertPublicKeyLength   OBJECT-TYPE
    SYNTAX      Integer32
    MAX-ACCESS  read-only
    STATUS      current
    DESCRIPTION ""
    ::= { localCertEntry 11 }

localCertSignatureAlgorithm   OBJECT-TYPE
    SYNTAX      DisplayString
    MAX-ACCESS  read-only
    STATUS      current
    DESCRIPTION ""
    ::= { localCertEntry 12 }

localCertConformance   OBJECT IDENTIFIER ::= { localCertMIB 2 }
localCertCompliances   OBJECT IDENTIFIER ::= { localCertConformance 1 }
localCertGroups        OBJECT IDENTIFIER ::= { localCertConformance 2 }

localCertCompliance MODULE-COMPLIANCE
    STATUS current
    DESCRIPTION
    "Describes the requirements for conformance to the BPP-MIB"
    MODULE
        MANDATORY-GROUPS { localCertGroup }
    ::= { localCertCompliances 1 }

localCertGroup OBJECT-GROUP
    OBJECTS {
        localCertMoId,
        localCertSerialNumber,
        localCertVersion,
        localCertIssuer,
        localCertSubject,
        localCertValidFrom,
        localCertValidTo,
        localCertEncoding,
        localCertStatus,
        localCertPublicKeyAlgorithm,
        localCertPublicKeyLength,
        localCertSignatureAlgorithm
}
    STATUS current
    DESCRIPTION
        " A collection of objects for managing the localCerts"
    ::= { localCertGroups 1 }

END
