LUM-PORTDEVICEIF-MIB DEFINITIONS ::= BEGIN

IMPORTS
    MODULE-IDENTITY, OBJECT-TYPE, Unsigned32, Integer32
        FROM SNMPv2-SMI
    TEXTUAL-CONVENTION, DisplayString, DateAndTime
        FROM SNMPv2-TC
    OBJECT-GROUP, MODULE-COMPLIANCE
        FROM SNMPv2-CONF
    InterfaceIndex
        FROM IF-MIB
    lumModules, lumPortdeviceIfMIB
        FROM LUM-REG
    MgmtNameString, SubrackNumber, SlotNumber, BoardOrInterfaceOperStatus,
    FaultStatus, AdminStatus, TrxMedia, LambdaFrequency, OnOff
        FROM LUM-TC
    ;

lumPortdeviceIfMIBModule MODULE-IDENTITY
    LAST-UPDATED
        "201706150000Z" -- June 15th 2017
    ORGANIZATION
        "Infinera Corporation"
    CONTACT-INFO
        "techsupport@infinera.com"
    DESCRIPTION
        "The equipment configuration MIB module for port device interface.

        Then tables contained in this MIB are:

        (1) The Interface groups contains information and configurations for
            each port device interface.

        - L1 Configuration
        - L2 Configuration

"
    REVISION
        "201706150000Z" -- June 15th 2017
    DESCRIPTION
        "Changes made for release r29.0:
         - Changed ORGANIZATION and CONTACT-INFO"
    REVISION
        "201305310000Z" -- May 31st 2013
    DESCRIPTION
        "Initial revision."
    ::= { lumModules 58 }


-- ----------------------------------------------------
-- Compliance area, containing groups and compliance
-- specifications.
-- ----------------------------------------------------

lumPortdeviceIfConfs OBJECT IDENTIFIER ::= { lumPortdeviceIfMIB 1 }
lumPortdeviceIfGroups OBJECT IDENTIFIER ::= { lumPortdeviceIfConfs 1 }
lumPortdeviceIfCompl OBJECT IDENTIFIER ::= { lumPortdeviceIfConfs 2 }


-- ----------------------------------------------------
-- Root for objects in the PORTDEVICE IF MIB
-- ----------------------------------------------------

lumPortdeviceIfMIBObjects  OBJECT IDENTIFIER ::= { lumPortdeviceIfMIB 2 }


-- ----------------------------------------------------
-- This MIB contains the following groups:
-- ----------------------------------------------------

portDevIfGeneral OBJECT IDENTIFIER ::= { lumPortdeviceIfMIBObjects 1 }
portDevIfL1List OBJECT IDENTIFIER ::= { lumPortdeviceIfMIBObjects 2 }
portDevIfL2List OBJECT IDENTIFIER ::= { lumPortdeviceIfMIBObjects 3 }

-- =============================================================
-- Textual Conventions
-- =============================================================

LumPortDeviceDuplexMode ::= TEXTUAL-CONVENTION
    STATUS current
    DESCRIPTION
        "Represents a duplex mode of an interface of an SD."
    SYNTAX INTEGER {
           halfDuplex(0),
           fullDuplex(1),
           autoDuplex(2),
           incomplete(3),
           duplexNotAvailable(254),
           duplexNotApplicable(255)
           }

LumPortDeviceInterfaceSpeed ::= TEXTUAL-CONVENTION
    STATUS current
    DESCRIPTION
        "The speed of an interface of an SD."
    SYNTAX INTEGER {
           fastEthernet(0),
           gbE(1)
           }

LumPortDeviceMasterSlaveRole ::= TEXTUAL-CONVENTION
    STATUS current
    DESCRIPTION
        "Represents a master-slave role of an interface of an SD."
    SYNTAX INTEGER {
           msMaster(0),
           msSlave(1),
           msAuto(2),
           msNotAvailable(254),
           msNotApplicable(255)
           }

LumPortDeviceMdixMode ::= TEXTUAL-CONVENTION
    STATUS current
    DESCRIPTION
        "Represents the MDI/MDIX mode of an SD."
    SYNTAX INTEGER {
           mdi(0),
           mdix(1),
           mdiNotAvailable(254),
           mdiNotApplicable(255)
           }

LumPortDevicePauseMode ::= TEXTUAL-CONVENTION
    STATUS current
    DESCRIPTION
        "Represents a pause mode of an interface of an SD."
    SYNTAX INTEGER {
           pauseDisabled(0),
           pauseEnabled(1),
           pauseTxEnabledRxDisabled(2),
           pauseTxDisabledRxEnabled(3),
           pauseAuto(4),
           pauseNotAvailable(254),
           pauseNotApplicable(255)
           }

LumPortDeviceInterface ::= TEXTUAL-CONVENTION
    STATUS current
    DESCRIPTION
        "Nid Interface Type."
    SYNTAX INTEGER {
           interfaceNone(0),
           ifNif(1),
           ifCifA(2),
           ifCifB(3)
           }

-- ----------------------------------------------------
-- General group
-- ----------------------------------------------------
--

portDevIfGeneralLastChangeTime OBJECT-TYPE
    SYNTAX      DateAndTime
    MAX-ACCESS  read-only
    STATUS      current
    DESCRIPTION
        "The time when the configuration of the MIB was
        last changed.

"
    ::= { portDevIfGeneral 1 }

portDevIfGeneralStateLastChangeTime OBJECT-TYPE
    SYNTAX      DateAndTime
    MAX-ACCESS  read-only
    STATUS      current
    DESCRIPTION
        "The time when the state and/or configuration of the
        MIB was last changed.

"
    ::= { portDevIfGeneral 2 }

portDevIfL1TableSize OBJECT-TYPE
     SYNTAX      Unsigned32
     MAX-ACCESS  read-only
     STATUS      current
     DESCRIPTION
         "Size of portDevIfL1 table.

"
     ::= { portDevIfGeneral 3 }

portDevIfL2TableSize OBJECT-TYPE
     SYNTAX      Unsigned32
     MAX-ACCESS  read-only
     STATUS      current
     DESCRIPTION
         "Size of portDevIfL2 table.

"
     ::= { portDevIfGeneral 4 }

-- =============================================================
-- portDevIfTable
-- =============================================================

portDevIfL1Table OBJECT-TYPE
    SYNTAX      SEQUENCE OF LumPortdeviceIfL1Entry
    MAX-ACCESS  not-accessible
    STATUS      current
    DESCRIPTION
        "A table containing the parameters of the interfaces of all SDs."
    ::= { portDevIfL1List 1 }

portDevIfL1Entry OBJECT-TYPE
    SYNTAX      LumPortdeviceIfL1Entry
    MAX-ACCESS  not-accessible
    STATUS      current
    DESCRIPTION
        "A list of objects containing the parameters of an interface of
         an SD.

"

    INDEX  { portDevIfIndex }
    ::= { portDevIfL1Table 1 }


LumPortdeviceIfL1Entry ::=
    SEQUENCE {
        portDevIfIndex                    InterfaceIndex,
        portDevIfL1Name                   MgmtNameString,
        portDevIfL1Descr                  DisplayString,
        portDevIfL1AdminStatus            AdminStatus,
        portDevIfL1OperStatus             BoardOrInterfaceOperStatus,
        portDevIfL1PortDevId              Unsigned32,
        portDevIfL1Subrack                SubrackNumber,
        portDevIfL1Slot                   SlotNumber,
        portDevIfL1LocalPort              Unsigned32,
        portDevIfL1VlanId                 Unsigned32,
        portDevIfL1NidPort                LumPortDeviceInterface,
        portDevIfL1InternalReference      Unsigned32,
        portDevIfL1LaserStatus            INTEGER,
        portDevIfL1LaserBias              Unsigned32,
        portDevIfL1LaserTempActual        Integer32,
        portDevIfL1TxFrequency            LambdaFrequency,
        portDevIfL1ExpectedTxFrequency    LambdaFrequency,
        portDevIfL1SignalFormat           LumPortDeviceInterfaceSpeed,
        portDevIfL1TrxMedia               TrxMedia,
        portDevIfL1ReceiverSensitivity    Integer32,
        portDevIfL1PowerLevel             Integer32,
        portDevIfL1PowerLevelLowRelativeThreshold    Integer32,
        portDevIfL1TxPowerLevel           Integer32,
        portDevIfL1RxHighPower            Integer32,
        portDevIfL1TrxClass               DisplayString,
        portDevIfL1LossOfSignal           FaultStatus,
        portDevIfL1TrxMissing             FaultStatus,
        portDevIfL1ReceivedPowerLow       FaultStatus,
        portDevIfL1ReceivedPowerHigh      FaultStatus
    }

portDevIfIndex OBJECT-TYPE
    SYNTAX      InterfaceIndex
    MAX-ACCESS  read-only
    STATUS      current
    DESCRIPTION
        "Unique number identifying the portdev interface.
"
    ::= { portDevIfL1Entry 1 }

portDevIfL1Name OBJECT-TYPE
    SYNTAX      MgmtNameString
    MAX-ACCESS  read-only
    STATUS      current
    DESCRIPTION
        "The management name of the nid customer interface, for example
        'nid:1', where the first number indicates customer interface
"
    ::= { portDevIfL1Entry 2 }

portDevIfL1Descr OBJECT-TYPE
    SYNTAX      DisplayString
    MAX-ACCESS  read-write
    STATUS      current
    DESCRIPTION
        "User configurable label for the port device interface L2 Description .
"
    DEFVAL { "" }
    ::= {  portDevIfL1Entry  3 }

portDevIfL1AdminStatus OBJECT-TYPE
    SYNTAX      AdminStatus
    MAX-ACCESS  read-write
    STATUS      current
    DESCRIPTION
        "The administrative alarm status of the port device interface.
		Note that the portdevice interface is still active when set to down.
		To shut down traffic, use the Administrative status from the NID General tab.

        down - Alarms are suppressed.
        up - Alarms are not suppressed.

"
    DEFVAL { up }
    ::= { portDevIfL1Entry 4 }

portDevIfL1OperStatus OBJECT-TYPE
    SYNTAX      BoardOrInterfaceOperStatus
    MAX-ACCESS  read-only
    STATUS      current
    DESCRIPTION
        "The operational state of the port device interface.

        notPresent - The physical resources are not
        available.

        down - The interface is de-activated or the are
        faults preventing it from going to the 'up'-state.

        up - The interface is operational.
"
    DEFVAL { up }
    ::= { portDevIfL1Entry 5 }

portDevIfL1PortDevId OBJECT-TYPE
    SYNTAX      Unsigned32 (1..2147483647)
    MAX-ACCESS  read-create
    STATUS      current
    DESCRIPTION
        "An arbitrary index assigned to each
        port device entry aka sdId.
"
    ::= { portDevIfL1Entry 6 }

portDevIfL1Subrack OBJECT-TYPE
    SYNTAX      SubrackNumber
    MAX-ACCESS  read-create
    STATUS      current
    DESCRIPTION
        "The number of the subrack where the port device is
        located.
"
    ::= { portDevIfL1Entry 7 }

portDevIfL1Slot OBJECT-TYPE
    SYNTAX      SlotNumber
    MAX-ACCESS  read-create
    STATUS      current
    DESCRIPTION
        "The slot where the port device is located.
"
    ::= { portDevIfL1Entry 8 }

portDevIfL1LocalPort OBJECT-TYPE
    SYNTAX      Unsigned32 (0..2147483647)
    MAX-ACCESS  read-create
    STATUS      current
    DESCRIPTION
        "The index of the local port that this device is connected to.
"
    ::= { portDevIfL1Entry 9 }

portDevIfL1VlanId OBJECT-TYPE
    SYNTAX      Unsigned32(1..4094)
    MAX-ACCESS  read-create
    STATUS      current
    DESCRIPTION
        "User specified VLAN ID, which is last number in the
        port device ID.
        If no VLAN ID is specified then VLAN ID 0 is assumed.
"
    ::= { portDevIfL1Entry 10 }

portDevIfL1NidPort OBJECT-TYPE
    SYNTAX      LumPortDeviceInterface
    MAX-ACCESS  read-create
    STATUS      current
    DESCRIPTION
    "Describes which port of Nid is used, Nif, CifA or CifB
"
    ::= { portDevIfL1Entry 11 }

portDevIfL1InternalReference OBJECT-TYPE
    SYNTAX      Unsigned32 (0..2147483647)
    MAX-ACCESS  read-create
    STATUS      current
    DESCRIPTION
        "For internal use only.
"
    DEFVAL { 0 }
    ::= { portDevIfL1Entry 12 }

portDevIfL1LaserStatus OBJECT-TYPE
    SYNTAX      INTEGER {
                    off (1),
                    on (2) }
    MAX-ACCESS  read-only
    STATUS      current
    DESCRIPTION
        "The operational state of the laser.

        off - The laser is turned off.
        on - The laser is turned on.

"
    DEFVAL { on }
    ::= { portDevIfL1Entry 13 }

portDevIfL1LaserBias OBJECT-TYPE
    SYNTAX      Unsigned32
    MAX-ACCESS  read-only
    STATUS      current
    DESCRIPTION
        "Measures laser bias current value in tenths of
        mA (0.1 mA).

"
    ::= { portDevIfL1Entry 14 }

portDevIfL1LaserTempActual OBJECT-TYPE
    SYNTAX      Integer32
    MAX-ACCESS  read-only
    STATUS      current
    DESCRIPTION
        "The actual laser temperature in units of
        0.1 degrees centigrade.

"
    ::= { portDevIfL1Entry 15 }

portDevIfL1TxFrequency OBJECT-TYPE
    SYNTAX      LambdaFrequency
    MAX-ACCESS  read-only
    STATUS      current
    DESCRIPTION
        "The transmitted frequency given in hundreds of
        GHz (0.01 GHz).
"
    ::= { portDevIfL1Entry 16 }

portDevIfL1ExpectedTxFrequency OBJECT-TYPE
    SYNTAX      LambdaFrequency
    MAX-ACCESS  read-write
    STATUS      current
    DESCRIPTION
        "The expected frequency given in hundreds of GHz
        (0.01 GHz).

"
    DEFVAL { 0 }
    ::= { portDevIfL1Entry 17 }

portDevIfL1SignalFormat OBJECT-TYPE
    SYNTAX      LumPortDeviceInterfaceSpeed

    MAX-ACCESS  read-write
    STATUS      current
    DESCRIPTION
        "The expected signal format.
         This value is only used for electrical interfaces.
"
    DEFVAL { gbE }
    ::= { portDevIfL1Entry  18 }

portDevIfL1TrxMedia OBJECT-TYPE
    SYNTAX      TrxMedia
    MAX-ACCESS  read-create
    STATUS      current
    DESCRIPTION
        "Defines the media and capability of the TRX.

"
     DEFVAL { optical }
    ::= { portDevIfL1Entry 19 }

portDevIfL1ReceiverSensitivity OBJECT-TYPE
    SYNTAX      Integer32
    MAX-ACCESS  read-only
    STATUS      current
    DESCRIPTION
        "The lowest power that the receiver is guaranteed
        to handle, in units of 0.1 dBm.

"
    ::= { portDevIfL1Entry 20 }

portDevIfL1PowerLevel OBJECT-TYPE
    SYNTAX      Integer32
    MAX-ACCESS  read-only
    STATUS      current
    DESCRIPTION
        "The received power level in units of 0.1 dBm.

"
    ::= { portDevIfL1Entry 21 }

portDevIfL1PowerLevelLowRelativeThreshold OBJECT-TYPE
    SYNTAX      Integer32 (-50..100)
    MAX-ACCESS  read-write
    STATUS      current
    DESCRIPTION
        "The lower threshold for received power level in
        units of 0.1 dB, relative to the receiver
        sensitivity.
"
    DEFVAL { 30 }
    ::= { portDevIfL1Entry 22 }

portDevIfL1TxPowerLevel OBJECT-TYPE
    SYNTAX      Integer32
    MAX-ACCESS  read-only
    STATUS      current
    DESCRIPTION
        "The transmitted power level in units of 0.1 dBm.

"
    ::= { portDevIfL1Entry 23 }

portDevIfL1RxHighPower OBJECT-TYPE
    SYNTAX      Integer32
    MAX-ACCESS  read-only
    STATUS      current
    DESCRIPTION
        "The highest power that the receiver is guaranteed
        to handle, in units of 0.1 dBm.

"
    ::= { portDevIfL1Entry 24 }

portDevIfL1TrxClass OBJECT-TYPE
    SYNTAX      DisplayString
    MAX-ACCESS  read-only
    STATUS      current
    DESCRIPTION
        "String that describes the transceiver class.
"
    DEFVAL { "" }
    ::= { portDevIfL1Entry 25 }


portDevIfL1LossOfSignal OBJECT-TYPE
    SYNTAX      FaultStatus
    MAX-ACCESS  read-only
    STATUS      current
    DESCRIPTION
        "Loss of signal on a portdevice interface

        A(ctivation): Signal is lost.

        D(e-activation): Signal is restored.

"
    ::= {portDevIfL1Entry 26 }

portDevIfL1TrxMissing OBJECT-TYPE
    SYNTAX      FaultStatus
    MAX-ACCESS  read-only
    STATUS      current
    DESCRIPTION
        "transceiver not inserted on a portdevice interface

        A(ctivation): An expected transceiver is missing.

        D(e-activation): The missing transceiver is inserted.

"
    ::= {portDevIfL1Entry 27 }

portDevIfL1ReceivedPowerLow OBJECT-TYPE
    SYNTAX      FaultStatus
    MAX-ACCESS  read-only
    STATUS      current
    DESCRIPTION
        "Received power level low threshold exceeded.
        Applicable for all signal formats.

        A(ctivation): The received power level is below the
        associated threshold.

        D(e-activation): The received power level is 0.5 dB above the
        threshold.

"
    ::= {portDevIfL1Entry 28 }

portDevIfL1ReceivedPowerHigh OBJECT-TYPE
    SYNTAX      FaultStatus
    MAX-ACCESS  read-only
    STATUS      current
    DESCRIPTION
        "Received power level too high for the transceiver

        Applicable for all signal formats.

"
    ::= {portDevIfL1Entry 29 }

-- =============================================================
-- portDevIfL2Table
-- =============================================================

portDevIfL2Table OBJECT-TYPE
    SYNTAX      SEQUENCE OF LumPortdeviceIfL2Entry
    MAX-ACCESS  not-accessible
    STATUS      current
    DESCRIPTION
        "A table containing the L2 parameters of all interfaces
         of all SDs."
    ::= { portDevIfL2List 1 }

portDevIfL2Entry OBJECT-TYPE
    SYNTAX      LumPortdeviceIfL2Entry
    MAX-ACCESS  not-accessible
    STATUS      current
    DESCRIPTION
        "A list of objects containing the L2 parameters of a portdevice interface.
"
    INDEX  { portDevIfL2Index }
    ::= { portDevIfL2Table 1 }

LumPortdeviceIfL2Entry ::=
    SEQUENCE {
        portDevIfL2Index        InterfaceIndex,
        portDevIfL2Name         MgmtNameString,
        portDevIfL2Descr        DisplayString,
        portDevIfL2PortDevId    Unsigned32,
        portDevIfL2Subrack      SubrackNumber,
        portDevIfL2Slot         SlotNumber,
        portDevIfL2LocalPort    Unsigned32,
        portDevIfL2VlanId       Unsigned32,
        portDevIfL2NidPort      LumPortDeviceInterface,
        portDevIfL2InternalReference Unsigned32,

-- Only CIF Ports.
        portDevIfL2AutoNegotiation        INTEGER,

-- Only CIF Ports.
        portDevIfL2AutoNegotiationStatus LumPortDeviceDuplexMode

    }

portDevIfL2Index OBJECT-TYPE
    SYNTAX      InterfaceIndex
    MAX-ACCESS  read-create
    STATUS      current
    DESCRIPTION
        "Unique number identifying the portdevice interface within the scope of the
         containing interface.
"
    ::= { portDevIfL2Entry 1 }

portDevIfL2Name OBJECT-TYPE
    SYNTAX      MgmtNameString
    MAX-ACCESS  read-only
    STATUS      current
    DESCRIPTION
        "The management name of the nid customer interface, for example
        'L2:1:1:1:1:CifA'.
"
    ::= { portDevIfL2Entry 2 }

portDevIfL2Descr OBJECT-TYPE
    SYNTAX      DisplayString
    MAX-ACCESS  read-write
    STATUS      current
    DESCRIPTION
        "User configurable label for the port device interface L2 Description .
"
    DEFVAL { "" }
    ::= { portDevIfL2Entry  3 }

portDevIfL2PortDevId OBJECT-TYPE
    SYNTAX      Unsigned32 (1..2147483647)
    MAX-ACCESS  read-create
    STATUS      current
    DESCRIPTION
        "An arbitrary index assigned to each
        port device entry aka sdId.
"
    ::= { portDevIfL2Entry 4 }

portDevIfL2Subrack OBJECT-TYPE
    SYNTAX      SubrackNumber
    MAX-ACCESS  read-create
    STATUS      current
    DESCRIPTION
        "The number of the subrack where the port device is
        located.
"
    ::= { portDevIfL2Entry 5 }

portDevIfL2Slot OBJECT-TYPE
    SYNTAX      SlotNumber
    MAX-ACCESS  read-create
    STATUS      current
    DESCRIPTION
        "The slot where the port device is located.
"
    ::= { portDevIfL2Entry 6 }

portDevIfL2LocalPort OBJECT-TYPE
    SYNTAX      Unsigned32 (0..2147483647)
    MAX-ACCESS  read-create
    STATUS      current
    DESCRIPTION
        "The index of the port that this device is connected to.
"
    ::= { portDevIfL2Entry 7 }

portDevIfL2VlanId OBJECT-TYPE
    SYNTAX      Unsigned32(1..4094)
    MAX-ACCESS  read-create
    STATUS      current
    DESCRIPTION
        "User specified VLAN ID, which is last number in the
        port device ID.
        If no VLAN ID is specified then VLAN ID 0 is assumed.
"
    ::= { portDevIfL2Entry 8 }

portDevIfL2NidPort OBJECT-TYPE
    SYNTAX      LumPortDeviceInterface
    MAX-ACCESS  read-create
    STATUS      current
    DESCRIPTION
    "Describes which port of Nid is used, Nif, CifA or CifB
"
    ::= { portDevIfL2Entry 9 }

portDevIfL2InternalReference OBJECT-TYPE
    SYNTAX      Unsigned32 (0..2147483647)
    MAX-ACCESS  read-create
    STATUS      current
    DESCRIPTION
        "For internal use only.
"
    DEFVAL { 0 }
    ::= {portDevIfL2Entry 10 }

portDevIfL2AutoNegotiation OBJECT-TYPE
    SYNTAX     OnOff
    MAX-ACCESS  read-write
    STATUS      current
    DESCRIPTION
        "Indicates whether auto-negotiation is enabled for the portdevice interfaces.
"
    DEFVAL { on }
    ::= { portDevIfL2Entry 11 }

portDevIfL2AutoNegotiationStatus OBJECT-TYPE
    SYNTAX      LumPortDeviceDuplexMode
    MAX-ACCESS  read-only
    STATUS      current
    DESCRIPTION
        "The current auto-negotiation status of the portdevice interfaces:
        halfDuplex
        fullDuplex
        autoDuplex
        incomplete
"
    DEFVAL { incomplete }
    ::= { portDevIfL2Entry 12 }

--
-- *----------------------------------------------------
-- Object and event groups
-- *----------------------------------------------------

portDevIfGeneralGroupV1 OBJECT-GROUP
    OBJECTS {
        portDevIfGeneralLastChangeTime,
        portDevIfGeneralStateLastChangeTime,
        portDevIfL1TableSize,
        portDevIfL2TableSize
        }
    STATUS      current
    DESCRIPTION
        "The general objects. "
    ::= { lumPortdeviceIfGroups 1 }

portDevIfL1GroupV1 OBJECT-GROUP
     OBJECTS {
        portDevIfIndex,
        portDevIfL1Name,
        portDevIfL1Descr,
        portDevIfL1AdminStatus,
        portDevIfL1OperStatus,
        portDevIfL1PortDevId,
        portDevIfL1Subrack,
        portDevIfL1Slot,
        portDevIfL1LocalPort,
        portDevIfL1VlanId,
        portDevIfL1NidPort,
        portDevIfL1InternalReference,
        portDevIfL1LaserStatus,
        portDevIfL1LaserBias,
        portDevIfL1LaserTempActual,
        portDevIfL1TxFrequency,
        portDevIfL1ExpectedTxFrequency,
        portDevIfL1SignalFormat,
        portDevIfL1TrxMedia,
        portDevIfL1ReceiverSensitivity,
        portDevIfL1PowerLevel,
        portDevIfL1PowerLevelLowRelativeThreshold,
        portDevIfL1TxPowerLevel,
        portDevIfL1RxHighPower,
        portDevIfL1TrxClass,
        portDevIfL1LossOfSignal,
        portDevIfL1TrxMissing,
        portDevIfL1ReceivedPowerLow,
        portDevIfL1ReceivedPowerHigh
      }
     STATUS      current
     DESCRIPTION
         "The L1 objects (R21.0).
         "
     ::= { lumPortdeviceIfGroups 2 }


portDevIfL2GroupV1 OBJECT-GROUP
     OBJECTS {
        portDevIfL2Index,
        portDevIfL2Name,
        portDevIfL2Descr,
        portDevIfL2PortDevId,
        portDevIfL2Subrack,
        portDevIfL2Slot,
        portDevIfL2LocalPort,
        portDevIfL2VlanId,
        portDevIfL2NidPort,
        portDevIfL2InternalReference,
        portDevIfL2AutoNegotiation,
        portDevIfL2AutoNegotiationStatus
      }
     STATUS      current
     DESCRIPTION
         "The L2 objects (R21.0)."
     ::= { lumPortdeviceIfGroups 3 }

-- ----------------------------------------------------
-- Compliance
-- ----------------------------------------------------

lumPortDeviceBasicComplV1 MODULE-COMPLIANCE
    STATUS      current
    DESCRIPTION
        "Basic implementation requirements for the port device interface MIB. (R21.0)."
    MODULE
    MANDATORY-GROUPS {
        portDevIfGeneralGroupV1,
        portDevIfL1GroupV1,
        portDevIfL2GroupV1 }
        ::= { lumPortdeviceIfCompl 1 }

END
