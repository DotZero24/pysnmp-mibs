-- *****************************************************************
-- INFINERA-SECURITY-SECYCTRL-MIB
--
-- October 2016, Kavitha Manjunatha
--
--
-- Copyright (c) 2008-2012 by Infinera Inc.
-- All rights reserved.
-- ****************************************************************

INFINERA-SECURITY-SECYCTRL-MIB DEFINITIONS ::= BEGIN

IMPORTS
    MODULE-IDENTITY, OBJECT-TYPE                FROM SNMPv2-SMI
    MODULE-COMPLIANCE, OBJECT-GROUP             FROM SNMPv2-CONF
    ike                                         FROM INFINERA-REG-MIB
    ifIndex                                     FROM IF-MIB
    DisplayString                               FROM SNMPv2-TC
    InfnFailPolicy, InfnCipherSuite,
    InfnICVLength, InfnEnableDisable            FROM INFINERA-TC-MIB
    ;

secyCtrlMIB MODULE-IDENTITY
    LAST-UPDATED  "201610100000Z"
    ORGANIZATION
        "Infinera"
    CONTACT-INFO
        "Infinera
                1322 Bordeaux Drive
                Sunnyvale, CA - 94089

                Contact : Technical Support
                Email   : support@infinera.com
                Phone   : 1-877-INF-5288"
    DESCRIPTION
        " "

    REVISION  "201610100000Z"
    DESCRIPTION
        " "
::= { ike 2 }

secyCtrlTable  OBJECT-TYPE
    SYNTAX SEQUENCE OF SecyCtrlEntry
    MAX-ACCESS not-accessible
    STATUS     current
    DESCRIPTION
        "A list of SecyCtrl entries. Each entry is uniquely identified by
                the value of ifIndex."
    ::= { secyCtrlMIB 1 }

secyCtrlEntry  OBJECT-TYPE
    SYNTAX     SecyCtrlEntry
    MAX-ACCESS not-accessible
    STATUS     current
    DESCRIPTION
        "A SecyCtrl entry containing information pertaining to Infinera SecyCtrls"
    INDEX { ifIndex }
    ::= { secyCtrlTable 1 }

SecyCtrlEntry  ::= SEQUENCE {
    secyCtrlMoId                        DisplayString,
    secyCtrlRekeyMACsecSAFrequency      Integer32,
    secyCtrlRekeyMACsecSAFailPolicy     InfnFailPolicy,
    secyCtrlTrafficKillOffset           Integer32,
    secyCtrlSelectedCipherSuite         InfnCipherSuite,
    secyCtrlIntegrity                   InfnEnableDisable,
    secyCtrlConfidentiality             InfnEnableDisable,
    secyCtrlICVLength                   InfnICVLength,
    secyCtrlReplayProtection            InfnEnableDisable,
    secyCtrlReplayWindow                Integer32,
    secyCtrlLowestPacketNumber          Integer32,
    secyCtrlAssociatedIKEPeer           DisplayString
}

secyCtrlMoId    OBJECT-TYPE
    SYNTAX      DisplayString
    MAX-ACCESS  read-only
    STATUS      current
    DESCRIPTION "Interface on which SecY is enabled"
    ::= { secyCtrlEntry 1 }

secyCtrlRekeyMACsecSAFrequency   OBJECT-TYPE
    SYNTAX      Integer32
    MAX-ACCESS  read-write
    STATUS      current
    DESCRIPTION "MACSEC Rekey SA frequency in seconds"
    ::= { secyCtrlEntry 2 }

secyCtrlRekeyMACsecSAFailPolicy   OBJECT-TYPE
    SYNTAX      InfnFailPolicy
    MAX-ACCESS  read-write
    STATUS      current
    DESCRIPTION "MACSEC Rekey SA Fail Policy"
    ::= { secyCtrlEntry 3 }

secyCtrlTrafficKillOffset   OBJECT-TYPE
    SYNTAX      Integer32
    MAX-ACCESS  read-write
    STATUS      current
    DESCRIPTION "Traffic kill offset"
    ::= { secyCtrlEntry 4 }

secyCtrlSelectedCipherSuite   OBJECT-TYPE
    SYNTAX      InfnCipherSuite
    MAX-ACCESS  read-only
    STATUS      current
    DESCRIPTION "Selected Cipher Suite"
    ::= { secyCtrlEntry 5 }

secyCtrlIntegrity   OBJECT-TYPE
    SYNTAX      InfnEnableDisable
    MAX-ACCESS  read-only
    STATUS      current
    DESCRIPTION ""
    ::= { secyCtrlEntry 6 }

secyCtrlConfidentiality   OBJECT-TYPE
    SYNTAX      InfnEnableDisable
    MAX-ACCESS  read-only
    STATUS      current
    DESCRIPTION ""
    ::= { secyCtrlEntry 7 }

secyCtrlICVLength   OBJECT-TYPE
    SYNTAX      InfnICVLength
    MAX-ACCESS  read-only
    STATUS      current
    DESCRIPTION "ICV Length"
    ::= { secyCtrlEntry 8 }

secyCtrlReplayProtection   OBJECT-TYPE
    SYNTAX      InfnEnableDisable
    MAX-ACCESS  read-only
    STATUS      current
    DESCRIPTION "Replay Protection"
    ::= { secyCtrlEntry 9 }

secyCtrlReplayWindow   OBJECT-TYPE
    SYNTAX      Integer32
    MAX-ACCESS  read-only
    STATUS      current
    DESCRIPTION "Replay Window"
    ::= { secyCtrlEntry 10 }

secyCtrlLowestPacketNumber   OBJECT-TYPE
    SYNTAX      Integer32
    MAX-ACCESS  read-only
    STATUS      current
    DESCRIPTION "Packet Number"
    ::= { secyCtrlEntry 11 }

secyCtrlAssociatedIKEPeer   OBJECT-TYPE
    SYNTAX      DisplayString
    MAX-ACCESS  read-write
    STATUS      current
    DESCRIPTION "Associated IKE Peer"
    ::= { secyCtrlEntry 12 }

secyCtrlConformance   OBJECT IDENTIFIER ::= { secyCtrlMIB 2 }
secyCtrlCompliances   OBJECT IDENTIFIER ::= { secyCtrlConformance 1 }
secyCtrlGroups        OBJECT IDENTIFIER ::= { secyCtrlConformance 2 }

secyCtrlCompliance MODULE-COMPLIANCE
    STATUS current
    DESCRIPTION
    "Describes the requirements for conformance to the BPP-MIB"
    MODULE
        MANDATORY-GROUPS { secyCtrlGroup }
    ::= { secyCtrlCompliances 1 }

secyCtrlGroup OBJECT-GROUP
    OBJECTS {
        secyCtrlMoId,
        secyCtrlRekeyMACsecSAFrequency,
        secyCtrlRekeyMACsecSAFailPolicy,
        secyCtrlTrafficKillOffset,
        secyCtrlSelectedCipherSuite,
        secyCtrlIntegrity,
        secyCtrlConfidentiality,
        secyCtrlICVLength,
        secyCtrlReplayProtection,
        secyCtrlReplayWindow,
        secyCtrlLowestPacketNumber,
        secyCtrlAssociatedIKEPeer
}
    STATUS current
    DESCRIPTION
        " A collection of objects for managing the SECYCTRL objects"
    ::= { secyCtrlGroups 1 }

END
