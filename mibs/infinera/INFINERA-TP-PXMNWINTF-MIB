-- *****************************************************************
-- INFINERA-TP-PXMNWINTF-MIB
--
-- Mithun Murthy/ Divyank Rastogi
--
--
-- Copyright (c) 2008-2012 by Infinera Inc.
-- All rights reserved.
-- ****************************************************************

INFINERA-TP-PXMNWINTF-MIB DEFINITIONS ::= BEGIN

IMPORTS
    MODULE-IDENTITY, OBJECT-TYPE, Integer32     FROM SNMPv2-SMI
    MODULE-COMPLIANCE, OBJECT-GROUP             FROM SNMPv2-CONF
    DisplayString                               FROM SNMPv2-TC
    ifIndex                                     FROM IF-MIB
	FloatTenths, FloatHundredths,
	InfnPmHistStatsControl						FROM INFINERA-TC-MIB
    terminationPoint                            FROM INFINERA-REG-MIB;

pxmNwIntfMIB MODULE-IDENTITY
    LAST-UPDATED  "201605200000Z"
    ORGANIZATION
        "Infinera"
    CONTACT-INFO
        "Infinera
                1322 Bordeaux Drive
                Sunnyvale, CA - 94089

                Contact : Technical Support
                Email   : support@infinera.com
                Phone   : 1-877-INF-5288"
    DESCRIPTION
        " "

    REVISION  "201605150000Z"
    DESCRIPTION
        " "
::= { terminationPoint 74 }


pxmNwIntfConformance   OBJECT IDENTIFIER ::= { pxmNwIntfMIB 3 }
pxmNwIntfCompliances   OBJECT IDENTIFIER ::= { pxmNwIntfConformance 1 }
pxmNwIntfGroups        OBJECT IDENTIFIER ::= { pxmNwIntfConformance 2 }

pxmNwIntfTable  OBJECT-TYPE
    SYNTAX SEQUENCE OF PxmNwIntfEntry
    MAX-ACCESS not-accessible
    STATUS     current
    DESCRIPTION
        "A list of PxmNwIntf entries. Each entry is uniquely identified by
                the value of ifIndex."
    ::= { pxmNwIntfMIB 1 }

pxmNwIntfEntry  OBJECT-TYPE
    SYNTAX     PxmNwIntfEntry
    MAX-ACCESS not-accessible
    STATUS     current
    DESCRIPTION
        "A PxmNwIntf entry containing information pertaining to
                Infinera PxmNwIntf interfaces. This table is a subclass of IfCommon.
                Entries will exist in this table only for interfaces of type PxmNwIntf."
    INDEX { ifIndex }
    ::= { pxmNwIntfTable 1 }

PxmNwIntfEntry  ::= SEQUENCE {
	pxmNwIntfAssociatedODUCtp	DisplayString,
	pxmNwIntfMTUSize			Integer32,
	pxmNwIntfInterfaceRate		Integer32,
	pxmNwIntfOverbookingFactor	FloatTenths,
	pxmNwIntfMaxReservableBW	FloatHundredths,
	pxmNwIntfAvailableBW		FloatHundredths,
	pxmNwIntfPmHistStatsEnable	InfnPmHistStatsControl,
	pxmNwIntfMacAddress			DisplayString
}

pxmNwIntfAssociatedODUCtp	OBJECT-TYPE
    SYNTAX     DisplayString
    MAX-ACCESS read-only
    STATUS     current
    DESCRIPTION
        ""
    ::= { pxmNwIntfEntry 1 }

pxmNwIntfMTUSize			OBJECT-TYPE
    SYNTAX     	Integer32
    MAX-ACCESS	read-only
    STATUS     	current
    DESCRIPTION
        ""
    ::= { pxmNwIntfEntry 2 }

pxmNwIntfInterfaceRate		OBJECT-TYPE
    SYNTAX     Integer32
    MAX-ACCESS read-only
    STATUS     current
    DESCRIPTION
        ""
    ::= { pxmNwIntfEntry 3 }

pxmNwIntfOverbookingFactor	OBJECT-TYPE
    SYNTAX     FloatTenths
    MAX-ACCESS read-write
    STATUS     current
    DESCRIPTION
        ""
    ::= { pxmNwIntfEntry 4 }

pxmNwIntfMaxReservableBW	OBJECT-TYPE
    SYNTAX   	FloatHundredths
    MAX-ACCESS read-only
    STATUS     current
    DESCRIPTION
        ""
    ::= { pxmNwIntfEntry 5 }

pxmNwIntfAvailableBW		OBJECT-TYPE
    SYNTAX     FloatHundredths
    MAX-ACCESS read-only
    STATUS     current
    DESCRIPTION
        ""
    ::= { pxmNwIntfEntry 6 }

pxmNwIntfPmHistStatsEnable	OBJECT-TYPE
    SYNTAX     InfnPmHistStatsControl
    MAX-ACCESS read-write
    STATUS     current
    DESCRIPTION
        ""
    ::= { pxmNwIntfEntry 7 }

pxmNwIntfMacAddress			OBJECT-TYPE
    SYNTAX     DisplayString
    MAX-ACCESS read-only
    STATUS     current
    DESCRIPTION
        ""
    ::= { pxmNwIntfEntry  8 }

pxmNwIntfCompliance  MODULE-COMPLIANCE
    STATUS     current
    DESCRIPTION
        "Describes the requirements for conformance to the TRIBPTP-MIB"
    MODULE
        MANDATORY-GROUPS { pxmNwIntfGroup }
    ::= { pxmNwIntfCompliances 1 }

pxmNwIntfGroup  OBJECT-GROUP
    OBJECTS {
  		pxmNwIntfAssociatedODUCtp,
		pxmNwIntfMTUSize,
		pxmNwIntfInterfaceRate,
		pxmNwIntfOverbookingFactor,
		pxmNwIntfMaxReservableBW,
		pxmNwIntfAvailableBW,
		pxmNwIntfPmHistStatsEnable,
		pxmNwIntfMacAddress

	}
    STATUS     current
    DESCRIPTION
        " A collection of objects for managing pxmNwIntf interfaces."
    ::= { pxmNwIntfGroups 1 }
END
