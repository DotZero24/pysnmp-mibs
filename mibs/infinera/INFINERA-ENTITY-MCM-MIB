-- ***************************************************************
-- INFINERA-ENTITY-MCM-MIB
--
-- October 2008, Sharfuddin Syed / Narendra Gupta
--
--
-- Copyright (c) 2008-2012 by Infinera Inc.
-- All rights reserved.
-- ****************************************************************

INFINERA-ENTITY-MCM-MIB DEFINITIONS ::= BEGIN

IMPORTS
    OBJECT-TYPE, MODULE-IDENTITY           FROM SNMPv2-SMI
    OBJECT-GROUP, MODULE-COMPLIANCE        FROM SNMPv2-CONF
    RowStatus, TruthValue, DisplayString   FROM SNMPv2-TC
    entLPPhysicalIndex                     FROM ENTITY-MIB
    equipment                              FROM INFINERA-REG-MIB
    InfnEqptType                           FROM INFINERA-TC-MIB;

mcmMIB MODULE-IDENTITY
    LAST-UPDATED  "200810200000Z"
    ORGANIZATION
        "INFINERA"
    CONTACT-INFO
        "Infinera
        169 Java Drive
        Sunnyvale, CA - 94089

        Contact : Technical Support
        Email   : support@infinera.com
        Phone   : 1-877-INF-5288"
    DESCRIPTION
        "This MIB is modeling for MCM equipment table."

::= { equipment 2 }

mcmConformance       OBJECT IDENTIFIER ::= { mcmMIB 3 }
mcmCompliances       OBJECT IDENTIFIER ::= { mcmConformance 1 }
mcmGroups            OBJECT IDENTIFIER ::= { mcmConformance 2 }

mcmTable  OBJECT-TYPE
    SYNTAX SEQUENCE OF McmEntry
    MAX-ACCESS not-accessible
    STATUS     current
    DESCRIPTION
        "This table contains all MCM modules that are currently present in a network element.
        "
    ::= { mcmMIB 1 }

mcmEntry  OBJECT-TYPE
    SYNTAX     McmEntry
    MAX-ACCESS not-accessible
    STATUS     current
    DESCRIPTION
        "A row in the MCM table. Each row in the table is identified with a unique entPhysicalIndexID.
        "
    INDEX { entLPPhysicalIndex }
    ::= { mcmTable 1 }

McmEntry ::= SEQUENCE {
    mcmMoId                DisplayString,
    mcmProvType            InfnEqptType,
    mcmRedundancyStatus    INTEGER,
    mcmBrandingFault       TruthValue,
    mcmRowStatus           RowStatus
}

mcmMoId  OBJECT-TYPE
    SYNTAX     DisplayString
    MAX-ACCESS read-create
    STATUS     current
    DESCRIPTION
        "The object identifier for MCM"
    ::= { mcmEntry 1 }

mcmProvType  OBJECT-TYPE
    SYNTAX     InfnEqptType
    MAX-ACCESS read-create
    STATUS     current
    DESCRIPTION
        "The configured MCM type."
    ::= { mcmEntry 2 }

mcmRedundancyStatus  OBJECT-TYPE
    SYNTAX     INTEGER {
        none (1),
        single (2),
        active (3),
        standby (4),
        makeStandbyInProgress (5),
        oos (6),
        lock (7)
    }
    MAX-ACCESS read-only
    STATUS     current
    DESCRIPTION
        "Indicates the status of the MCM. Valid values:active, standby and makeStandbyInProgress"
    ::= { mcmEntry 3 }

mcmBrandingFault  OBJECT-TYPE
    SYNTAX     TruthValue
    MAX-ACCESS read-only
    STATUS     current
    DESCRIPTION
        "This indiactes whether equpiment has branding faults."
    ::= { mcmEntry 4 }

mcmRowStatus  OBJECT-TYPE
    SYNTAX     RowStatus
    MAX-ACCESS read-create
    STATUS     current
    DESCRIPTION
        "The row status of this MCM entry.
                Because rows in this table are indexed by entPhysicalIndex, to create a new row one must
                choose a value of entPhysicalIndex that is not already in use.

                A side-effect of the creation of a row in this table is the creation of a corresponding
                row in the eqptTable and the entPhysicalTable.

                The status may not be set to active if the mcmMoId and mcmProvEqptType are not set to valid values.

                This row may only be deleted if it was a pre-provisioned row and the hardware is not present.

                If this row is deleted, the associated row in the Eqpt Table and entPhysicalTable will be
                deleted by the agent."
    ::= { mcmEntry 5 }

mcmCompliance  MODULE-COMPLIANCE
    STATUS     current
    DESCRIPTION
        ""
    MODULE
        MANDATORY-GROUPS { mcmGroup }
    ::= { mcmCompliances 1 }

mcmGroup  OBJECT-GROUP
    OBJECTS { mcmBrandingFault,
        mcmMoId,
        mcmProvType,
        mcmRedundancyStatus,
        mcmRowStatus }
    STATUS     current
    DESCRIPTION
        ""
    ::= { mcmGroups 1 }
END
