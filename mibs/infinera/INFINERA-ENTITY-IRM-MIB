-- ***************************************************************
-- INFINERA-ENTITY-IRM-MIB
-- Copyright (c) 2008-2012 by Infinera Inc.
-- All rights reserved.
-- ****************************************************************

INFINERA-ENTITY-IRM-MIB DEFINITIONS ::= BEGIN

IMPORTS
    OBJECT-TYPE, MODULE-IDENTITY        FROM SNMPv2-SMI
    OBJECT-GROUP, MODULE-COMPLIANCE     FROM SNMPv2-CONF
    TruthValue, DisplayString           FROM SNMPv2-TC
    entLPPhysicalIndex                  FROM ENTITY-MIB
    equipment                           FROM INFINERA-REG-MIB
    InfnEqptType, FloatHundredths,
    InfnFiberType, InfnEnableDisable,
    InfnOAOperatingMode,
    InfnOlosSoakTime, InfnDeploymentConfig,
    FloatArbitraryPrecision,
    InfnALSDetectionMode,
    InfnALSDisableMode                  FROM INFINERA-TC-MIB;

irmMIB MODULE-IDENTITY
    LAST-UPDATED  "201310200000Z"
    ORGANIZATION
        "INFINERA"
    CONTACT-INFO
        "Infinera
        169 Java Drive
        Sunnyvale, CA - 94089
        Contact : Technical Support
        Email   : support@infinera.com
        Phone   : 1-877-INF-5288"
    DESCRIPTION
        "This MIB is modeling for IRM equipment table."
    ::= { equipment 29 }

irmConformance       OBJECT IDENTIFIER ::= { irmMIB 3 }
irmCompliances       OBJECT IDENTIFIER ::= { irmConformance 1 }
irmGroups            OBJECT IDENTIFIER ::= { irmConformance 2 }

irmTable  OBJECT-TYPE
    SYNTAX SEQUENCE OF IrmEntry
    MAX-ACCESS not-accessible
    STATUS     current
    DESCRIPTION
        "This table contains all IRM modules that are currently present in a network element.
        "
    ::= { irmMIB 1 }

irmEntry  OBJECT-TYPE
    SYNTAX     IrmEntry
    MAX-ACCESS not-accessible
    STATUS     current
    DESCRIPTION
        "A row in the IRM table. Each row in the table is identified with a unique entPhysicalIndexID.
        "
    INDEX { entLPPhysicalIndex }
    ::= { irmTable 1 }

IrmEntry ::= SEQUENCE {
    irmMoId                             DisplayString,
    irmProvEqptType                     InfnEqptType,
    irmPointLossOffset                  FloatHundredths,
    irmLaunchPowerOffset                FloatHundredths,
    irmRxDampSeqNum                     Integer32,
    irmEnhPMRept                        InfnEnableDisable,
    irmAutomaticPLOAdjustmen            InfnEnableDisable,
    irmFiberType                        InfnFiberType,
    irmAsePowerBetaCoeffX               FloatHundredths,
    irmAsePowerBetaCoeffY               FloatHundredths,
    irmAsePowerBetaCoeffZ               FloatHundredths,
    irmPumpPowerBetaCoeffX              FloatHundredths,
    irmPumpPowerBetaCoeffY              FloatHundredths,
    irmPumpPowerBetaCoeffZ              FloatHundredths,
    irmPumpRatioPump1                   FloatHundredths,
    irmPumpRatioPump2                   FloatHundredths,
    irmPumpRatioPump3                   FloatHundredths,
    irmPumpRatioPump4                   FloatHundredths,
    irmStaticRamanGain                  FloatHundredths,
    irmStaticEdfaGain                   FloatHundredths,
    irmStaticPostEdfaVoaAttenuation     FloatHundredths,
    irmTxDampSeqNum                     Integer32,
    irmALSDetectionMode                 InfnALSDetectionMode,
    irmPilotLaserDisable                TruthValue,
    irmGainTiltOffset                   FloatHundredths,
    irmOlosSoakTime                     InfnOlosSoakTime,
    irmOperatingMode                    InfnOAOperatingMode,
    irmDeploymentConfig                 InfnDeploymentConfig,
    irmRamanGain                        FloatArbitraryPrecision,
    irmRamanTiltOffset                  FloatArbitraryPrecision,
    irmTxVOA                            FloatArbitraryPrecision,
    irmLimitPower                       InfnEnableDisable,
    irmSingleSlotMode                   InfnEnableDisable,
    irmALSDisableMode                   InfnALSDisableMode,
    irmRxEDFAGain                       FloatArbitraryPrecision
}

irmMoId     OBJECT-TYPE
    SYNTAX      DisplayString
    MAX-ACCESS  read-create
    STATUS      current
    DESCRIPTION ""
    ::= {   irmEntry 1 }

irmProvEqptType     OBJECT-TYPE
    SYNTAX      InfnEqptType
    MAX-ACCESS  read-create
    STATUS      current
    DESCRIPTION ""
    ::= {   irmEntry 2 }

irmPointLossOffset  OBJECT-TYPE
    SYNTAX      FloatHundredths
    MAX-ACCESS read-create
    STATUS     current
    DESCRIPTION ""
    ::= { irmEntry 3 }

irmLaunchPowerOffset  OBJECT-TYPE
    SYNTAX     FloatHundredths
    MAX-ACCESS read-create
    STATUS     current
    DESCRIPTION ""
    ::= { irmEntry 4 }

irmRxDampSeqNum  OBJECT-TYPE
    SYNTAX     Integer32
    MAX-ACCESS read-only
    STATUS     current
    DESCRIPTION ""
    ::= { irmEntry 5 }

irmTxDampSeqNum  OBJECT-TYPE
    SYNTAX     Integer32
    MAX-ACCESS read-only
    STATUS     current
    DESCRIPTION ""
    ::= { irmEntry 6 }

irmPilotLaserDisable    OBJECT-TYPE
    SYNTAX      TruthValue
    MAX-ACCESS  read-write
    STATUS      current
    DESCRIPTION ""
    ::= {   irmEntry 7 }

irmEnhPMRept OBJECT-TYPE
    SYNTAX     InfnEnableDisable
    MAX-ACCESS read-create
    STATUS     current
    DESCRIPTION ""
    ::= { irmEntry 8 }

irmALSDetectionMode     OBJECT-TYPE
    SYNTAX InfnALSDetectionMode
    MAX-ACCESS  read-write
    STATUS      current
    DESCRIPTION ""
    ::= { irmEntry 9 }

irmAutomaticPLOAdjustmen  OBJECT-TYPE
    SYNTAX     InfnEnableDisable
    MAX-ACCESS read-create
    STATUS     current
    DESCRIPTION ""
    ::= { irmEntry 10 }

irmAsePowerBetaCoeffX  OBJECT-TYPE
    SYNTAX     FloatHundredths
    MAX-ACCESS read-create
    STATUS     current
    DESCRIPTION ""
    ::= { irmEntry 11 }

irmAsePowerBetaCoeffY  OBJECT-TYPE
    SYNTAX     FloatHundredths
    MAX-ACCESS read-create
    STATUS     current
    DESCRIPTION ""
    ::= { irmEntry 12 }

irmAsePowerBetaCoeffZ  OBJECT-TYPE
    SYNTAX     FloatHundredths
    MAX-ACCESS read-create
    STATUS     current
    DESCRIPTION ""
    ::= { irmEntry 13 }

irmPumpPowerBetaCoeffX  OBJECT-TYPE
    SYNTAX     FloatHundredths
    MAX-ACCESS read-create
    STATUS     current
    DESCRIPTION ""
    ::= { irmEntry 14 }

irmPumpPowerBetaCoeffY  OBJECT-TYPE
    SYNTAX     FloatHundredths
    MAX-ACCESS read-create
    STATUS     current
    DESCRIPTION ""
    ::= { irmEntry 15 }

irmPumpPowerBetaCoeffZ  OBJECT-TYPE
    SYNTAX     FloatHundredths
    MAX-ACCESS read-create
    STATUS     current
    DESCRIPTION ""
    ::= { irmEntry 16 }

irmPumpRatioPump1  OBJECT-TYPE
    SYNTAX     FloatHundredths
    MAX-ACCESS read-create
    STATUS     current
    DESCRIPTION ""
    ::= { irmEntry 17 }

irmPumpRatioPump2  OBJECT-TYPE
    SYNTAX     FloatHundredths
    MAX-ACCESS read-create
    STATUS     current
    DESCRIPTION ""
    ::= { irmEntry 18 }

irmPumpRatioPump3  OBJECT-TYPE
    SYNTAX     FloatHundredths
    MAX-ACCESS read-create
    STATUS     current
    DESCRIPTION ""
    ::= { irmEntry 19 }

irmPumpRatioPump4  OBJECT-TYPE
    SYNTAX     FloatHundredths
    MAX-ACCESS read-create
    STATUS     current
    DESCRIPTION ""
    ::= { irmEntry 20 }

irmStaticRamanGain  OBJECT-TYPE
    SYNTAX     FloatHundredths
    MAX-ACCESS read-create
    STATUS     current
    DESCRIPTION ""
    ::= { irmEntry 21 }

irmStaticEdfaGain  OBJECT-TYPE
    SYNTAX     FloatHundredths
    MAX-ACCESS read-create
    STATUS     current
    DESCRIPTION ""
    ::= { irmEntry 22 }

irmStaticPostEdfaVoaAttenuation  OBJECT-TYPE
    SYNTAX     FloatHundredths
    MAX-ACCESS read-create
    STATUS     current
    DESCRIPTION ""
    ::= { irmEntry 23 }

irmFiberType  OBJECT-TYPE
    SYNTAX     InfnFiberType
    MAX-ACCESS read-create
    STATUS     current
    DESCRIPTION ""
    ::= { irmEntry 24 }


irmGainTiltOffset   OBJECT-TYPE
    SYNTAX      FloatHundredths
    MAX-ACCESS  read-create
    STATUS      current
    DESCRIPTION ""
    ::= { irmEntry 25 }

irmOlosSoakTime OBJECT-TYPE
    SYNTAX InfnOlosSoakTime
    MAX-ACCESS  read-write
    STATUS      current
    DESCRIPTION ""
    ::= { irmEntry 26 }

irmOperatingMode OBJECT-TYPE
    SYNTAX      InfnOAOperatingMode
    MAX-ACCESS  read-write
    STATUS      current
    DESCRIPTION ""
    ::= { irmEntry 27 }

irmDeploymentConfig OBJECT-TYPE
    SYNTAX      InfnDeploymentConfig
    MAX-ACCESS  read-write
    STATUS      current
    DESCRIPTION ""
    ::= { irmEntry 28 }


irmRamanGain OBJECT-TYPE
    SYNTAX      FloatArbitraryPrecision
    MAX-ACCESS  read-write
    STATUS      current
    DESCRIPTION ""
    ::= { irmEntry 29 }

irmRamanTiltOffset OBJECT-TYPE
    SYNTAX      FloatArbitraryPrecision
    MAX-ACCESS  read-write
    STATUS      current
    DESCRIPTION ""
    ::= { irmEntry 30 }

irmTxVOA OBJECT-TYPE
    SYNTAX      FloatArbitraryPrecision
    MAX-ACCESS  read-write
    STATUS      current
    DESCRIPTION ""
    ::= { irmEntry 31 }

irmLimitPower OBJECT-TYPE
    SYNTAX      InfnEnableDisable
    MAX-ACCESS  read-write
    STATUS      current
    DESCRIPTION ""
    ::= { irmEntry 32 }

irmSingleSlotMode OBJECT-TYPE
    SYNTAX      InfnEnableDisable
    MAX-ACCESS  read-write
    STATUS      current
    DESCRIPTION ""
    ::= { irmEntry 33 }

irmALSDisableMode OBJECT-TYPE
    SYNTAX      InfnALSDisableMode
    MAX-ACCESS  read-write
    STATUS      current
    DESCRIPTION ""
    ::= { irmEntry 34 }

irmRxEDFAGain OBJECT-TYPE
    SYNTAX      FloatArbitraryPrecision
    MAX-ACCESS  read-write
    STATUS      current
    DESCRIPTION ""
    ::= { irmEntry 35 }

irmCompliance  MODULE-COMPLIANCE
    STATUS      current
    DESCRIPTION ""
    MODULE
        MANDATORY-GROUPS { irmGroup }
    ::= { irmCompliances 1 }

irmGroup  OBJECT-GROUP
    OBJECTS {
        irmMoId,
        irmProvEqptType,
        irmPointLossOffset,
        irmLaunchPowerOffset,
        irmRxDampSeqNum,
        irmEnhPMRept,
        irmAutomaticPLOAdjustmen,
        irmFiberType,
        irmAsePowerBetaCoeffX,
        irmAsePowerBetaCoeffY,
        irmAsePowerBetaCoeffZ,
        irmPumpPowerBetaCoeffX,
        irmPumpPowerBetaCoeffY,
        irmPumpPowerBetaCoeffZ,
        irmPumpRatioPump1,
        irmPumpRatioPump2,
        irmPumpRatioPump3,
        irmPumpRatioPump4,
        irmStaticRamanGain,
        irmStaticEdfaGain,
        irmStaticPostEdfaVoaAttenuation,
        irmTxDampSeqNum,
        irmALSDetectionMode,
        irmPilotLaserDisable,
        irmGainTiltOffset,
        irmOlosSoakTime,
        irmOperatingMode,
        irmDeploymentConfig,
        irmRamanGain,
        irmRamanTiltOffset,
        irmTxVOA,
        irmLimitPower,
        irmSingleSlotMode,
        irmALSDisableMode,
        irmRxEDFAGain

    }
    STATUS      current
    DESCRIPTION ""
    ::= { irmGroups 1 }
END
