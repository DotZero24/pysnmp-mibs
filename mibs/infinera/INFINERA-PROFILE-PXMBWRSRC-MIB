-- ***************************************************************
-- INFINERA-PROFILE-PXMBWRSRC-MIB
--
-- May 2016, Kavitha Manjunatha / Divyank Rastogi
--
--
-- Copyright (c) 2008-2012 by Infinera Inc.
-- All rights reserved.
-- ****************************************************************
INFINERA-PROFILE-PXMBWRSRC-MIB DEFINITIONS ::= BEGIN

IMPORTS
    OBJECT-TYPE, MODULE-IDENTITY, Unsigned32    FROM SNMPv2-SMI
    OBJECT-GROUP, MODULE-COMPLIANCE             FROM SNMPv2-CONF
    DisplayString, TruthValue                   FROM SNMPv2-TC
    ifIndex                                     FROM IF-MIB
    commonProfile                               FROM INFINERA-REG-MIB
    InfnBwRateUnit                              FROM INFINERA-TC-MIB;

bwRsrcProfileMIB MODULE-IDENTITY
    LAST-UPDATED  "201605050000Z"
    ORGANIZATION
        "INFINERA"
    CONTACT-INFO
        "Infinera
        169 Java Drive
        Sunnyvale, CA - 94089

        Contact : Technical Support
        Email   : support@infinera.com
        Phone   : 1-877-INF-5288"
    DESCRIPTION
        "This MIB is modeling for PXMBWRSRC profile table."
::= { commonProfile 2 }

bwRsrcProfileConformance       OBJECT IDENTIFIER ::= { bwRsrcProfileMIB 3 }
bwRsrcProfileCompliances       OBJECT IDENTIFIER ::= { bwRsrcProfileConformance 1 }
bwRsrcProfileGroups            OBJECT IDENTIFIER ::= { bwRsrcProfileConformance 2 }

bwRsrcTable  OBJECT-TYPE
    SYNTAX SEQUENCE OF BwRsrcProfileEntry
    MAX-ACCESS not-accessible
    STATUS     current
    DESCRIPTION
        "This table contains all PXM BWRSRC profiles that are currently present in a network element.
        "
    ::= { bwRsrcProfileMIB 1 }

bwRsrcProfileEntry  OBJECT-TYPE
    SYNTAX     BwRsrcProfileEntry
    MAX-ACCESS not-accessible
    STATUS     current
    DESCRIPTION
        "A row in the PXM BWRSRC table. Each row in the table is identified with a unique ifIndex."
    INDEX { ifIndex }
    ::= { bwRsrcTable 1 }

BwRsrcProfileEntry ::= SEQUENCE {
    bwRsrcProfInUse                     TruthValue,
    bwRsrcProfCIR                       Integer32,
    bwRsrcProfCBS                       Integer32,
    bwRsrcProfEIR                       Integer32,
    bwRsrcProfEBS                       Integer32,
    bwRsrcProfRateUnit                  InfnBwRateUnit
}

bwRsrcProfInUse  OBJECT-TYPE
    SYNTAX     TruthValue
    MAX-ACCESS read-only
    STATUS     current
    DESCRIPTION
        "Profile In use"
    ::= { bwRsrcProfileEntry 1 }

bwRsrcProfCIR OBJECT-TYPE
    SYNTAX     Integer32
    MAX-ACCESS read-write
    STATUS     current
    DESCRIPTION
        ""
    ::= { bwRsrcProfileEntry 2 }

bwRsrcProfCBS  OBJECT-TYPE
    SYNTAX     Integer32
    MAX-ACCESS read-write
    STATUS     current
    DESCRIPTION
        ""
    ::= { bwRsrcProfileEntry 3 }

bwRsrcProfEIR  OBJECT-TYPE
    SYNTAX     Integer32
    MAX-ACCESS read-write
    STATUS     current
    DESCRIPTION
        ""
    ::= { bwRsrcProfileEntry 4 }

bwRsrcProfEBS  OBJECT-TYPE
    SYNTAX     Integer32
    MAX-ACCESS read-write
    STATUS     current
    DESCRIPTION
        ""
    ::= { bwRsrcProfileEntry 5 }

bwRsrcProfRateUnit  OBJECT-TYPE
    SYNTAX     InfnBwRateUnit
    MAX-ACCESS read-write
    STATUS     current
    DESCRIPTION
        ""
    ::= { bwRsrcProfileEntry 6 }

bwRsrcProfileCompliance  MODULE-COMPLIANCE
    STATUS     current
    DESCRIPTION ""
    MODULE
        MANDATORY-GROUPS { bwRsrcProfileGroup }
    ::= { bwRsrcProfileCompliances 1 }

bwRsrcProfileGroup  OBJECT-GROUP
    OBJECTS {
        bwRsrcProfInUse,
        bwRsrcProfCIR,
        bwRsrcProfCBS,
        bwRsrcProfEIR,
        bwRsrcProfEBS,
        bwRsrcProfRateUnit
    }
    STATUS     current
    DESCRIPTION ""
    ::= { bwRsrcProfileGroups 1 }
END
