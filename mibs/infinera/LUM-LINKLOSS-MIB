LUM-LINKLOSS-MIB DEFINITIONS ::= BEGIN

IMPORTS
    MODULE-IDENTITY, OBJECT-TYPE, Unsigned32
        FROM SNMPv2-SMI
    OBJECT-GROUP, MODULE-COMPLIANCE
        FROM SNMPv2-CONF
    DateAndTime
        FROM SNMPv2-TC
    lumModules, lumLinkLossMIB
        FROM LUM-REG
    FaultStatus
        FROM LUM-TC;

lumLinkLossMIBModule MODULE-IDENTITY
    LAST-UPDATED
        "201706150000Z" -- June 15th 2017
    ORGANIZATION
        "Infinera Corporation"
    CONTACT-INFO
        "techsupport@infinera.com"
    DESCRIPTION
        "The link loss MIB.

        - General

        - Link loss status

"

    REVISION
        "201706150000Z" -- June 15th 2017
    DESCRIPTION
        "Changes made for release r29.0:
         - Changed ORGANIZATION and CONTACT-INFO"
    REVISION
        "201203090000Z" -- Mars 9th 2012
    DESCRIPTION
        "The initial revision of this module."
    ::= { lumModules 45 }


-- ----------------------------------------------------
-- Conformance area, containing groups and complicance
-- specifications.
-- ----------------------------------------------------

lumLinkLossConfs OBJECT IDENTIFIER ::= { lumLinkLossMIB 1 }
lumLinkLossGroups OBJECT IDENTIFIER ::= { lumLinkLossConfs 1 }
lumLinkLossCompl OBJECT IDENTIFIER ::= { lumLinkLossConfs 2 }


-- ----------------------------------------------------
-- Root for objects in the Link Loss MIB
-- ----------------------------------------------------

lumLinkLossMIBObjects OBJECT IDENTIFIER ::= { lumLinkLossMIB 2 }

-- ----------------------------------------------------
-- This MIB contains the following groups:
-- ----------------------------------------------------

linkLossGeneral OBJECT IDENTIFIER ::= { lumLinkLossMIBObjects 1 }
linkLossStatusList OBJECT IDENTIFIER ::= { lumLinkLossMIBObjects 2 }

-- ----------------------------------------------------
-- Textual Conventions
-- ----------------------------------------------------

-- n/a

-------------------------------------------------------
-- General group
-- ----------------------------------------------------

linkLossGeneralConfigLastChangeTime OBJECT-TYPE
    SYNTAX      DateAndTime
    MAX-ACCESS  read-only
    STATUS      current
    DESCRIPTION
        "The time when the configuration of the MIB was
        last changed.

"
    ::= { linkLossGeneral 1 }

linkLossGeneralStateLastChangeTime OBJECT-TYPE
    SYNTAX      DateAndTime
    MAX-ACCESS  read-only
    STATUS      current
    DESCRIPTION
        "The time when the state of the MIB was last
        changed.

"
    ::= { linkLossGeneral 2 }

linkLossGeneralStatusTableSize OBJECT-TYPE
    SYNTAX      Unsigned32
    MAX-ACCESS  read-only
    STATUS      current
    DESCRIPTION
        "Size of table.

"
    ::= { linkLossGeneral 3 }

-------------------------------------------------------
-- Link Loss status table
-- ----------------------------------------------------

linkLossStatusTable  OBJECT-TYPE
    SYNTAX      SEQUENCE OF LinkLossStatusEntry
    MAX-ACCESS  not-accessible
    STATUS      current
    DESCRIPTION
        "The status list."
    ::= { linkLossStatusList 1 }

linkLossStatusEntry OBJECT-TYPE
    SYNTAX      LinkLossStatusEntry
    MAX-ACCESS  not-accessible
    STATUS      current
    DESCRIPTION
        "An entry in the status list.

"
    INDEX { linkLossStatusIndex }
    ::= { linkLossStatusTable 1 }

LinkLossStatusEntry ::=
    SEQUENCE {
        linkLossStatusIndex			Unsigned32,
        linkLossStatusThresholdExceeded		FaultStatus,
        linkLossStatusMeasurementFailed		FaultStatus,
	linkLossStatusMeasurementFailedOneDb	FaultStatus,
	linkLossStatusMeasurementFailedFiveSec	FaultStatus }

linkLossStatusIndex OBJECT-TYPE
    SYNTAX      Unsigned32 (1..2147483647)
    MAX-ACCESS  read-only
    STATUS      current
    DESCRIPTION
        "An arbitrary index assigned to each entry.

"
   ::= { linkLossStatusEntry 1 }

linkLossStatusThresholdExceeded  OBJECT-TYPE
    SYNTAX      FaultStatus
    MAX-ACCESS  read-only
    STATUS      current
    DESCRIPTION
        "tbd

"
   ::= { linkLossStatusEntry 2 }

linkLossStatusMeasurementFailed  OBJECT-TYPE
    SYNTAX      FaultStatus
    MAX-ACCESS  read-only
    STATUS      current
    DESCRIPTION
        "tbd

"
   ::= { linkLossStatusEntry 3 }

linkLossStatusMeasurementFailedOneDb  OBJECT-TYPE
    SYNTAX      FaultStatus
    MAX-ACCESS  read-only
    STATUS      current
    DESCRIPTION
        "tbd.

"
   ::= { linkLossStatusEntry 4 }

linkLossStatusMeasurementFailedFiveSec  OBJECT-TYPE
    SYNTAX      FaultStatus
    MAX-ACCESS  read-only
    STATUS      current
    DESCRIPTION
        "tbd.

"
   ::= { linkLossStatusEntry 5 }



-- ----------------------------------------------------
-- Object and event groups
-- ----------------------------------------------------

linkLossGeneralGroup OBJECT-GROUP
    OBJECTS {
        linkLossGeneralConfigLastChangeTime,
        linkLossGeneralStateLastChangeTime,
        linkLossGeneralStatusTableSize }
    STATUS      current
    DESCRIPTION
        "The general objects."
    ::= { lumLinkLossGroups 1 }

linkLossStatusGroup OBJECT-GROUP
    OBJECTS {
        linkLossStatusIndex,
        linkLossStatusThresholdExceeded,
        linkLossStatusMeasurementFailed,
        linkLossStatusMeasurementFailedOneDb,
	linkLossStatusMeasurementFailedFiveSec }
    STATUS      current
    DESCRIPTION
        "The general objects."
    ::= { lumLinkLossGroups 2 }


-- ----------------------------------------------------
-- Compliance
-- ----------------------------------------------------

lumLinkLossBasicComplV1 MODULE-COMPLIANCE
    STATUS      current
    DESCRIPTION
        "Basic implementation requirements for the Link Loss MIB V1."
    MODULE
        MANDATORY-GROUPS {
            linkLossGeneralGroup,
            linkLossStatusGroup }
    ::= { lumLinkLossCompl 1 }



END
