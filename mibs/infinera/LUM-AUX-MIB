LUM-AUX-MIB DEFINITIONS ::= BEGIN

IMPORTS
    MODULE-IDENTITY, OBJECT-TYPE, Unsigned32, IpAddress,
    Integer32
        FROM SNMPv2-SMI
    OBJECT-GROUP, MODULE-COMPLIANCE
        FROM SNMPv2-CONF
    TestAndIncr, DateAndTime, DisplayString
        FROM SNMPv2-TC
    lumModules, lumAuxMIB
        FROM LUM-REG
    MgmtNameString, FaultStatus, SubrackNumber, SlotNumber, PortNumber,
    BoardOrInterfaceAdminStatus, BoardOrInterfaceOperStatus, ObjectProperty,
    CommandString, AdminStatusWithNA, Signed32WithNA
        FROM LUM-TC;

lumAuxMIBModule MODULE-IDENTITY
    LAST-UPDATED
        "201706150000Z" -- June 15th 2017
    ORGANIZATION
        "Infinera Corporation"
    CONTACT-INFO
        "techsupport@infinera.com"
    DESCRIPTION
        "The auxiliary equipment MIB.

        - General

        - Parameters for SNMP managed equipment

        - Fiber protection interfaces

        - Node table for TM2000.

        - Equipment table for TM2000.

"
    REVISION
        "201706150000Z" -- June 15th 2017
    DESCRIPTION
        "Changes made for release r29.0:
         - Changed ORGANIZATION and CONTACT-INFO"
    REVISION
        "201704170000Z" -- April 17th 2017
    DESCRIPTION
        "Changes made for release r28.1:
        - Changed presentation of cabinet oper mode."
    REVISION
        "201604250000Z" -- Apr 25th 2016
    DESCRIPTION
	"Added attributes to cabinet table. Added Fan and FanGroup tables."
    REVISION
        "201601110000Z" -- Jan 11th 2016
    DESCRIPTION
	"Added default operStatus to notPresent."
    REVISION
        "201411030000Z" -- November 3:rd 2014
    DESCRIPTION
        "Added rx/txSignalStatus, to support MIB-II implementation."
    REVISION
        "201212200000Z" -- December 20th 2012
    DESCRIPTION
        "Host Unreachable and Configuration Mismatch alarms (TM2000) added."
    REVISION
        "201110120000Z" -- October 12th 2011
    DESCRIPTION
        "Node table (TM2000) added."
    REVISION
        "200908190000Z" -- August 19th 2009
    DESCRIPTION
        "Power extender added."
    REVISION
        "200410080000Z" -- October 8th 2004
    DESCRIPTION
        "The initial revision of this module."
    ::= { lumModules 29 }


-- ----------------------------------------------------
-- Conformance area, containing groups and complicance
-- specifications.
-- ----------------------------------------------------

lumAuxConfs OBJECT IDENTIFIER ::= { lumAuxMIB 1 }
lumAuxGroups OBJECT IDENTIFIER ::= { lumAuxConfs 1 }
lumAuxCompl OBJECT IDENTIFIER ::= { lumAuxConfs 2 }


-- ----------------------------------------------------
-- Root for objects in the aux MIB
-- ----------------------------------------------------

lumAuxMIBObjects OBJECT IDENTIFIER ::= { lumAuxMIB 2 }


-- ----------------------------------------------------
-- This MIB contains the following groups:
-- ----------------------------------------------------

auxGeneral OBJECT IDENTIFIER ::= { lumAuxMIBObjects 1 }
auxSnmpList OBJECT IDENTIFIER ::= { lumAuxMIBObjects 2 }
auxFxIfList OBJECT IDENTIFIER ::= { lumAuxMIBObjects 3 }
auxEquipmentList OBJECT IDENTIFIER ::= { lumAuxMIBObjects 4 }
auxRamanIfList OBJECT IDENTIFIER ::= { lumAuxMIBObjects 5 }
auxRamanSafetyList OBJECT IDENTIFIER ::= { lumAuxMIBObjects 6 }
auxPEIfList OBJECT IDENTIFIER ::= { lumAuxMIBObjects 7 }
auxNodeList OBJECT IDENTIFIER ::= { lumAuxMIBObjects 8 }
auxCabinetList OBJECT IDENTIFIER ::= { lumAuxMIBObjects 9 }
auxFanList OBJECT IDENTIFIER ::= { lumAuxMIBObjects 10 }
auxFanGroupList OBJECT IDENTIFIER ::= { lumAuxMIBObjects 11 }


-- ----------------------------------------------------
-- Textual Conventions
-- ----------------------------------------------------

-- n/a


-- ----------------------------------------------------
-- General group
-- ----------------------------------------------------

auxGeneralTestAndIncr OBJECT-TYPE
    SYNTAX      TestAndIncr
    MAX-ACCESS  read-write
    STATUS      current
    DESCRIPTION
        "Protection against simultaneous access from
        multiple managers. See SNMPv2-TC.

"
    ::= { auxGeneral 1 }

auxGeneralStateLastChangeTime OBJECT-TYPE
    SYNTAX      DateAndTime
    MAX-ACCESS  read-only
    STATUS      current
    DESCRIPTION
        "The time when the state of the MIB was last
        changed.

"
    ::= { auxGeneral 2 }

auxGeneralConfigLastChangeTime OBJECT-TYPE
    SYNTAX      DateAndTime
    MAX-ACCESS  read-only
    STATUS      current
    DESCRIPTION
        "The time when the configuration of the MIB
        was last changed.

"
    ::= { auxGeneral 3 }

auxGeneralSnmpTableSize OBJECT-TYPE
    SYNTAX      Unsigned32
    MAX-ACCESS  read-only
    STATUS      current
    DESCRIPTION
        "Number of rows available in the
        table for snmp managed equipment.

"
    ::= { auxGeneral 4 }

auxGeneralFxIfTableSize OBJECT-TYPE
    SYNTAX      Unsigned32
    MAX-ACCESS  read-only
    STATUS      current
    DESCRIPTION
        "Number of rows available in the
        fiber protections interface table.

"
    ::= { auxGeneral 5 }

auxGeneralAuxEquipmentTableSize OBJECT-TYPE
    SYNTAX      Unsigned32
    MAX-ACCESS  read-only
    STATUS      current
    DESCRIPTION
        "Number of rows available in the
        fiber protections interface table.

"
    ::= { auxGeneral 6 }

auxGeneralRamanIfTableSize OBJECT-TYPE
    SYNTAX      Unsigned32
    MAX-ACCESS  read-only
    STATUS      current
    DESCRIPTION
        "Number of rows available in the
        raman amplifier interface table.

"
    ::= { auxGeneral 7 }

auxGeneralRamanSafetyTableSize OBJECT-TYPE
    SYNTAX      Unsigned32
    MAX-ACCESS  read-only
    STATUS      current
    DESCRIPTION
        "Number of rows available in the
        raman amplifier safety table.

"
    ::= { auxGeneral 8 }

auxGeneralPEIfTableSize OBJECT-TYPE
    SYNTAX      Unsigned32
    MAX-ACCESS  read-only
    STATUS      current
    DESCRIPTION
        "Number of rows available in the
        raman amplifier interface table.

"
    ::= { auxGeneral 9 }

auxGeneralNodeTableSize OBJECT-TYPE
    SYNTAX      Unsigned32
    MAX-ACCESS  read-only
    STATUS      current
    DESCRIPTION
        "Number of rows available in the
        Node table.

"
    ::= { auxGeneral 10 }

auxGeneralCabinetTableSize OBJECT-TYPE
    SYNTAX      Unsigned32
    MAX-ACCESS  read-only
    STATUS      current
    DESCRIPTION
        "Number of rows available in the
        Cabinet table.

"
    ::= { auxGeneral 11 }

auxGeneralFanTableSize OBJECT-TYPE
    SYNTAX      Unsigned32
    MAX-ACCESS  read-only
    STATUS      current
    DESCRIPTION
        "Number of rows available in the
        Fan table.

"
    ::= { auxGeneral 12 }

auxGeneralFanGroupTableSize OBJECT-TYPE
    SYNTAX      Unsigned32
    MAX-ACCESS  read-only
    STATUS      current
    DESCRIPTION
        "Number of rows available in the
        FanGroup table.

"
    ::= { auxGeneral 13 }


-- ----------------------------------------------------
-- Aux SNMP managed equipment table
-- ----------------------------------------------------

auxSnmpTable  OBJECT-TYPE
    SYNTAX      SEQUENCE OF AuxSnmpEntry
    MAX-ACCESS  not-accessible
    STATUS      current
    DESCRIPTION
        "The list of SNMP managed equipment."
    ::= { auxSnmpList 1 }

auxSnmpEntry OBJECT-TYPE
    SYNTAX      AuxSnmpEntry
    MAX-ACCESS  not-accessible
    STATUS      current
    DESCRIPTION
        "An entry in the SNMP managed equipment list.

"
    INDEX { auxSnmpIndex }
    ::= { auxSnmpTable 1 }

AuxSnmpEntry ::=
    SEQUENCE {
        auxSnmpIndex            Unsigned32,
        auxSnmpName             MgmtNameString,
        auxSnmpDescr            DisplayString,
        auxSnmpAddress          IpAddress,
        auxSnmpPort             Unsigned32,
        auxSnmpVersion          INTEGER,
        auxSnmpReadCommunity    DisplayString,
        auxSnmpWriteCommunity   DisplayString,
        auxSnmpAdminStatus      BoardOrInterfaceAdminStatus,
        auxSnmpOperStatus       BoardOrInterfaceOperStatus,
        auxSnmpInvPhysIndexOrZero  Unsigned32,
        auxSnmpHostUnreachable  FaultStatus,
        auxSnmpSnmpError        FaultStatus,
        auxSnmpUnexpectedEquipmentType FaultStatus,
        auxSnmpInconsistentConfiguration FaultStatus,
        auxSnmpConfigurationProblem FaultStatus }

auxSnmpIndex OBJECT-TYPE
    SYNTAX      Unsigned32 (1..2147483647)
    MAX-ACCESS  read-only
    STATUS      current
    DESCRIPTION
        "An arbitrary index assigned to each
        equipment.

"
    ::= { auxSnmpEntry 1 }

auxSnmpName OBJECT-TYPE
    SYNTAX      MgmtNameString
    MAX-ACCESS  read-only
    STATUS      current
    DESCRIPTION
        "The name of the SNMP managed equipment.

"
    ::= { auxSnmpEntry 2 }

auxSnmpDescr OBJECT-TYPE
    SYNTAX      DisplayString
    MAX-ACCESS  read-write
    STATUS      current
    DESCRIPTION
        "User configurable label.

"
    ::= { auxSnmpEntry 3 }

auxSnmpAddress OBJECT-TYPE
    SYNTAX      IpAddress
    MAX-ACCESS  read-write
    STATUS      current
    DESCRIPTION
        "The IP address for the SNMP
        managed equipment.

"
    ::= { auxSnmpEntry 4 }

auxSnmpVersion OBJECT-TYPE
    SYNTAX      INTEGER {
                    v1 (1),
                    v2c (2) }
    MAX-ACCESS  read-write
    STATUS      current
    DESCRIPTION
        "SNMP protocol version.

"
    DEFVAL { v2c }
    ::= { auxSnmpEntry 5 }

auxSnmpPort OBJECT-TYPE
    SYNTAX      Unsigned32 (0..65535)
    MAX-ACCESS  read-write
    STATUS      current
    DESCRIPTION
        "The port number for the
        SNMP managed equipment.

"
    DEFVAL { 161 }
    ::= { auxSnmpEntry 6 }

auxSnmpReadCommunity OBJECT-TYPE
    SYNTAX      DisplayString (SIZE (0..255))
    MAX-ACCESS  read-write
    STATUS      current
    DESCRIPTION
        "The community string to use when
        reading information from the SNMP
        managed equipment.

"
    DEFVAL { "public" }
    ::= { auxSnmpEntry 7 }

auxSnmpWriteCommunity OBJECT-TYPE
    SYNTAX      DisplayString (SIZE (0..255))
    MAX-ACCESS  read-write
    STATUS      current
    DESCRIPTION
        "The community string to use when
        configuring the SNMP managed equipment.

"
    DEFVAL { "private" }
    ::= { auxSnmpEntry 8 }

auxSnmpAdminStatus OBJECT-TYPE
    SYNTAX      BoardOrInterfaceAdminStatus
    MAX-ACCESS  read-write
    STATUS      current
    DESCRIPTION
        "The administrative state for the interface.

        down - The interface should be inactive.

        service - The interface is activated but alarms
        are suppressed. Intended for use during service
        or re-configuration. When service is concluded
        adminStatus should be set to 'up' again.

        up - The interface should be activated when
        it becomes available. Alarms are not suppressed.

"
    DEFVAL { up }
    ::= { auxSnmpEntry 9 }

auxSnmpOperStatus OBJECT-TYPE
    SYNTAX      BoardOrInterfaceOperStatus
    MAX-ACCESS  read-only
    STATUS      current
    DESCRIPTION
        "The operational state for the object.

        notPresent - The HW related to the object
        is not available

        down - The object is de-activated or there are
        faults preventing it from going to the 'up'-state.

        up - The interface is active.

"
    DEFVAL { notPresent }
    ::= { auxSnmpEntry 10 }

auxSnmpInvPhysIndexOrZero OBJECT-TYPE
    SYNTAX      Unsigned32 (0..2147483647)
    MAX-ACCESS  read-only
    STATUS      current
    DESCRIPTION
        "The row in the invPhysTable for this interface.
        Set to 0 if not known.

"
    ::= { auxSnmpEntry 11 }

auxSnmpHostUnreachable OBJECT-TYPE
    SYNTAX      FaultStatus
    MAX-ACCESS  read-only
    STATUS      current
    DESCRIPTION
        "Can not contact the remote external equipment.
        Check address and community strings.

        A(ctivation): Contact lost

        D(e-activation): Contact stablished again

"
    ::= { auxSnmpEntry 12 }

auxSnmpSnmpError OBJECT-TYPE
    SYNTAX      FaultStatus
    MAX-ACCESS  read-only
    STATUS      current
    DESCRIPTION
        "Can not login to the remote external equipment

        A(ctivation): Contact lost

        D(e-activation): Contact stablished again

"
    ::= { auxSnmpEntry 13 }

auxSnmpUnexpectedEquipmentType OBJECT-TYPE
    SYNTAX      FaultStatus
    MAX-ACCESS  read-only
    STATUS      current
    DESCRIPTION
        "The remote external equipment is not of the
         expected type.

        A(ctivation): Wrong equipment detected

        D(e-activation): Expected equipment detected

"
    ::= { auxSnmpEntry 14 }

auxSnmpInconsistentConfiguration OBJECT-TYPE
    SYNTAX      FaultStatus
    MAX-ACCESS  read-only
    STATUS      current
    DESCRIPTION
        "Changes in the configuration of the remote
         equipment has been detected.

         This could happen if some other SNMP-manager
         is manipulating the configuration, or the
         configuration is changed via some local CLI.

        A(ctivation): Changes in the configuration detected

        D(e-activation): Configuration is consistent

"
    ::= { auxSnmpEntry 15 }

auxSnmpConfigurationProblem OBJECT-TYPE
    SYNTAX      FaultStatus
    MAX-ACCESS  read-only
    STATUS      current
    DESCRIPTION
        "The SNMP-manager can not configure the remote
         equipment.

         A possible cause could be that the writeCommunity
         does not match the remote equipment.

        A(ctivation): A number of consecutive write
                      operations failed.

        D(e-activation): Write operation succeded.

"
    ::= { auxSnmpEntry 16 }


-- ----------------------------------------------------
-- Aux i/f group
-- ----------------------------------------------------

auxFxIfTable  OBJECT-TYPE
    SYNTAX      SEQUENCE OF AuxFxIfEntry
    MAX-ACCESS  not-accessible
    STATUS      current
    DESCRIPTION
        "The list of OAS modules."
    ::= { auxFxIfList 1 }

auxFxIfEntry OBJECT-TYPE
    SYNTAX      AuxFxIfEntry
    MAX-ACCESS  not-accessible
    STATUS      current
    DESCRIPTION
        "An entry in the OAS module list.

"
    INDEX { auxFxIfIndex }
    ::= { auxFxIfTable 1 }

AuxFxIfEntry ::=
    SEQUENCE {
        auxFxIfIndex            Unsigned32,
        auxFxIfName             MgmtNameString,
        auxFxIfDescr            DisplayString,
        auxFxIfSubrack          SubrackNumber,
        auxFxIfSlot             SlotNumber,
        auxFxIfRxPort           PortNumber,
        auxFxIfTxPort           PortNumber,
        auxFxIfInvPhysIndexOrZero Unsigned32,
        auxFxIfAdminStatus      BoardOrInterfaceAdminStatus,
        auxFxIfOperStatus       BoardOrInterfaceOperStatus,
        auxFxIfRxPowerLevel     Integer32,
        auxFxIfLossOfSignalThreshold Integer32,
        auxFxIfLossOfSignal     FaultStatus,
        auxFxIfObjectProperty   ObjectProperty }

auxFxIfIndex OBJECT-TYPE
    SYNTAX      Unsigned32 (1..2147483647)
    MAX-ACCESS  read-only
    STATUS      current
    DESCRIPTION
        "An arbitrary index assigned to each
        configuration equipment.

"
    ::= { auxFxIfEntry 1 }

auxFxIfName OBJECT-TYPE
    SYNTAX      MgmtNameString
    MAX-ACCESS  read-only
    STATUS      current
    DESCRIPTION
        "The name of the FxIf.

"
    ::= { auxFxIfEntry 2 }

auxFxIfDescr OBJECT-TYPE
    SYNTAX      DisplayString
    MAX-ACCESS  read-write
    STATUS      current
    DESCRIPTION
        "User configurable label.

"
    DEFVAL { "" }
    ::= { auxFxIfEntry 3 }

auxFxIfSubrack OBJECT-TYPE
    SYNTAX      SubrackNumber
    MAX-ACCESS  read-only
    STATUS      current
    DESCRIPTION
        "The number of the subrack where the interface
        is located.

"
    ::= { auxFxIfEntry 4 }

auxFxIfSlot OBJECT-TYPE
    SYNTAX      SlotNumber
    MAX-ACCESS  read-only
    STATUS      current
    DESCRIPTION
        "The number of the slot where the interface is
        located.

"
    ::= { auxFxIfEntry 5 }

auxFxIfTxPort OBJECT-TYPE
    SYNTAX      PortNumber
    MAX-ACCESS  read-only
    STATUS      current
    DESCRIPTION
        "The number of the port where the interface is
        located.

"
    ::= { auxFxIfEntry 6 }

auxFxIfRxPort OBJECT-TYPE
    SYNTAX      PortNumber
    MAX-ACCESS  read-only
    STATUS      current
    DESCRIPTION
        "The number of the port where the interface is
        located.

"
    ::= { auxFxIfEntry 7 }

auxFxIfInvPhysIndexOrZero OBJECT-TYPE
    SYNTAX      Unsigned32 (0..2147483647)
    MAX-ACCESS  read-only
    STATUS      current
    DESCRIPTION
        "The row in the invPhysTable for this interface.
        Set to 0 if not known.

"
    ::= { auxFxIfEntry 8 }

auxFxIfAdminStatus OBJECT-TYPE
    SYNTAX      BoardOrInterfaceAdminStatus
    MAX-ACCESS  read-write
    STATUS      current
    DESCRIPTION
        "The administrative state for the interface.

        down - The interface should be inactive.

        service - The interface is activated but alarms
        are suppressed. Intended for use during service
        or re-configuration. When service is concluded
        adminStatus should be set to 'up' again.

        up - The interface should be activated when
        it becomes available. Alarms are not suppressed.

"
    DEFVAL { up }
    ::= { auxFxIfEntry 9 }

auxFxIfOperStatus OBJECT-TYPE
    SYNTAX      BoardOrInterfaceOperStatus
    MAX-ACCESS  read-only
    STATUS      current
    DESCRIPTION
        "The operational state for the interface.

        notPresent - The interface is not available.

        down - The interface is de-activated or there are
        faults preventing it from going to the 'up'-state.

        up - The interface is active.

"
    DEFVAL { notPresent }
    ::= { auxFxIfEntry 10 }

auxFxIfRxPowerLevel OBJECT-TYPE
    SYNTAX      Integer32
    MAX-ACCESS  read-only
    STATUS      current
    DESCRIPTION
        "The received power level in units of 0.1 dBm.

"
    ::= { auxFxIfEntry 11 }

auxFxIfLossOfSignalThreshold OBJECT-TYPE
    SYNTAX      Integer32 (-350..-60)
    MAX-ACCESS  read-write
    STATUS      current
    DESCRIPTION
        "The lower threshold for received power level in
        units of 0.1 dBm.

        Note: Depending on the type of board and interface
        the value range may vary.

"
    DEFVAL { -350 }
    ::= { auxFxIfEntry 12 }

auxFxIfLossOfSignal OBJECT-TYPE
    SYNTAX      FaultStatus
    MAX-ACCESS  read-only
    STATUS      current
    DESCRIPTION
        "Loss of signal.
        Applicable for all signal formats.

        A(ctivation): Active loss of signal HW indication.

        D(e-activation): Inactive loss of signal HW
        indication.

"
    ::= { auxFxIfEntry 13 }

auxFxIfObjectProperty OBJECT-TYPE
    SYNTAX      ObjectProperty
    MAX-ACCESS  read-only
    STATUS      current
    DESCRIPTION
        "Property mask.

"
    ::= { auxFxIfEntry 14 }

-- ----------------------------------------------------
-- Aux equipment group
-- ----------------------------------------------------

auxEquipmentTable  OBJECT-TYPE
    SYNTAX      SEQUENCE OF AuxEquipmentEntry
    MAX-ACCESS  not-accessible
    STATUS      current
    DESCRIPTION
        "The list of OAS modules."
    ::= { auxEquipmentList 1 }

auxEquipmentEntry OBJECT-TYPE
    SYNTAX      AuxEquipmentEntry
    MAX-ACCESS  not-accessible
    STATUS      current
    DESCRIPTION
        "An entry in the OAS module list.

"
    INDEX { auxEquipmentIndex }
    ::= { auxEquipmentTable 1 }

AuxEquipmentEntry ::=
    SEQUENCE {
        auxEquipmentIndex               Unsigned32,
        auxEquipmentName                MgmtNameString,
        auxEquipmentDescr               DisplayString,
        auxEquipmentSubrack             SubrackNumber,
        auxEquipmentSlot                SlotNumber,
        -- auxEquipmentInvPhysIndexOrZero Unsigned32,
        auxEquipmentAdminStatus BoardOrInterfaceAdminStatus,
        auxEquipmentOperStatus  BoardOrInterfaceOperStatus,
        auxEquipmentPowerFailure     FaultStatus,
        auxEquipmentFanProblem       FaultStatus,
        auxEquipmentObjectProperty   ObjectProperty,
        auxEquipmentPumpsEol         FaultStatus,
        auxEquipmentSelfTestFailure  FaultStatus,
        auxEquipmentAmbientTemp      Integer32,
        auxEquipmentRebootEquipment CommandString,
        auxEquipmentPowerAMissing   FaultStatus,
        auxEquipmentPowerBMissing   FaultStatus,
        auxEquipmentConfigurationMismatch FaultStatus}

auxEquipmentIndex OBJECT-TYPE
    SYNTAX      Unsigned32 (1..2147483647)
    MAX-ACCESS  read-only
    STATUS      current
    DESCRIPTION
        "An arbitrary index assigned to each
        configuration equipment.

"
    ::= { auxEquipmentEntry 1 }

auxEquipmentName OBJECT-TYPE
    SYNTAX      MgmtNameString
    MAX-ACCESS  read-only
    STATUS      current
    DESCRIPTION
        "The name of the equipment.

"
    ::= { auxEquipmentEntry 2 }

auxEquipmentDescr OBJECT-TYPE
    SYNTAX      DisplayString
    MAX-ACCESS  read-write
    STATUS      current
    DESCRIPTION
        "User configurable label.

"
    DEFVAL { "" }
    ::= { auxEquipmentEntry 3 }

auxEquipmentSubrack OBJECT-TYPE
    SYNTAX      SubrackNumber
    MAX-ACCESS  read-only
    STATUS      current
    DESCRIPTION
        "The number of the subrack where the interface
        is located.

"
    ::= { auxEquipmentEntry 4 }

auxEquipmentSlot OBJECT-TYPE
    SYNTAX      SlotNumber
    MAX-ACCESS  read-only
    STATUS      current
    DESCRIPTION
        "The number of the slot where the interface is
        located.

"
    ::= { auxEquipmentEntry 5 }

auxEquipmentAdminStatus OBJECT-TYPE
    SYNTAX      BoardOrInterfaceAdminStatus
    MAX-ACCESS  read-write
    STATUS      current
    DESCRIPTION
        "The administrative state for the interface.

        down - The interface should be inactive.

        service - The interface is activated but alarms
        are suppressed. Intended for use during service
        or re-configuration. When service is concluded
        adminStatus should be set to 'up' again.

        up - The interface should be activated when
        it becomes available. Alarms are not suppressed.

"
    DEFVAL { up }
    ::= { auxEquipmentEntry 6 }

auxEquipmentOperStatus OBJECT-TYPE
    SYNTAX      BoardOrInterfaceOperStatus
    MAX-ACCESS  read-only
    STATUS      current
    DESCRIPTION
        "The operational state for the interface.

        notPresent - The interface is not available.

        down - The interface is de-activated or there are
        faults preventing it from going to the 'up'-state.

        up - The interface is active.

"
    DEFVAL { notPresent }
    ::= { auxEquipmentEntry 7 }

auxEquipmentPowerFailure OBJECT-TYPE
    SYNTAX      FaultStatus
    MAX-ACCESS  read-only
    STATUS      current
    DESCRIPTION
        "Remote equipment reports power failure.

        A(ctivation): Power failure detected

        D(e-activation): Power failure no longer active

"
    ::= { auxEquipmentEntry 8 }

auxEquipmentFanProblem OBJECT-TYPE
    SYNTAX      FaultStatus
    MAX-ACCESS  read-only
    STATUS      current
    DESCRIPTION
        "Remote equipment report problem with built-in
        fan unit.

        A(ctivation): Fan problem detected

        D(e-activation): Fan problem no longer active

"
    ::= { auxEquipmentEntry 9 }

auxEquipmentObjectProperty OBJECT-TYPE
    SYNTAX      ObjectProperty
    MAX-ACCESS  read-only
    STATUS      current
    DESCRIPTION
        "Property mask

"
    ::= { auxEquipmentEntry 10 }

auxEquipmentPumpsEol OBJECT-TYPE
    SYNTAX      FaultStatus
    MAX-ACCESS  read-only
    STATUS      current
    DESCRIPTION
        "Shows the end-of-life status of the HW.

         For the RAMAN, the alarm is active if the
         current of any of the pumps has reached its
         end-of-life threshold.

"
    ::= { auxEquipmentEntry 11 }

auxEquipmentSelfTestFailure OBJECT-TYPE
    SYNTAX      FaultStatus
    MAX-ACCESS  read-only
    STATUS      current
    DESCRIPTION
        "Indicates if the built-in self-test
         failed.

"
    ::= { auxEquipmentEntry 12 }

auxEquipmentAmbientTemp OBJECT-TYPE
    SYNTAX      Integer32
    MAX-ACCESS  read-only
    STATUS      current
    DESCRIPTION
        "Shows the ambient temperature of the
         equipment.

"
    ::= { auxEquipmentEntry 13 }

auxEquipmentRebootEquipment OBJECT-TYPE
    SYNTAX      CommandString
    MAX-ACCESS  read-only
    STATUS      current
    DESCRIPTION
        "Executing this procedure will initiate a reboot
         of the auxiliary equipment.

"
    ::= { auxEquipmentEntry 14 }

auxEquipmentPowerAMissing OBJECT-TYPE
    SYNTAX      FaultStatus
    MAX-ACCESS  read-only
    STATUS      current
    DESCRIPTION
        "Status of 1U Power A missing Alarm.

"
    ::= { auxEquipmentEntry 15 }

auxEquipmentPowerBMissing OBJECT-TYPE
    SYNTAX      FaultStatus
    MAX-ACCESS  read-only
    STATUS      current
    DESCRIPTION
        "Status of 1U Power B missing Alarm.

"
    ::= { auxEquipmentEntry 16 }

auxEquipmentConfigurationMismatch OBJECT-TYPE
    SYNTAX      FaultStatus
    MAX-ACCESS  read-only
    STATUS      current
    DESCRIPTION
        " A configuration request has failed and there might now be a mismatch in configuration between tm3000 and external system.

        A: A configuration request failed.

        D: The configuration is re-sent to external system.

"
    ::= { auxEquipmentEntry 17 }

-- ----------------------------------------------------
-- Aux raman i/f group
-- ----------------------------------------------------

auxRamanIfTable  OBJECT-TYPE
    SYNTAX      SEQUENCE OF AuxRamanIfEntry
    MAX-ACCESS  not-accessible
    STATUS      current
    DESCRIPTION
        "The list of RAMAN i/f."
    ::= { auxRamanIfList 1 }

auxRamanIfEntry OBJECT-TYPE
    SYNTAX      AuxRamanIfEntry
    MAX-ACCESS  not-accessible
    STATUS      current
    DESCRIPTION
        "An entry in the RAMAN i/f list.

"
    INDEX { auxRamanIfIndex }
    ::= { auxRamanIfTable 1 }

AuxRamanIfEntry ::=
    SEQUENCE {
        auxRamanIfIndex            Unsigned32,
        auxRamanIfName             MgmtNameString,
        auxRamanIfDescr            DisplayString,
        auxRamanIfSubrack          SubrackNumber,
        auxRamanIfSlot             SlotNumber,
        auxRamanIfRxPort           PortNumber,
        auxRamanIfTxPort           PortNumber,
        auxRamanIfInvPhysIndexOrZero Unsigned32,
        auxRamanIfAdminStatus      BoardOrInterfaceAdminStatus,
        auxRamanIfOperStatus       BoardOrInterfaceOperStatus,
        auxRamanIfObjectProperty   ObjectProperty,
        auxRamanIfPumpsOperationMode INTEGER,
        auxRamanIfModuleOperationMode  INTEGER,
        auxRamanIfPumpsOperationModeConfig CommandString,
        auxRamanIfLineFiberType         INTEGER,
        auxRamanIfAutoRestartProcTime   Unsigned32,
        auxRamanIfArpPauseStatus        INTEGER,
        auxRamanIfPumpsStatus           INTEGER,
        auxRamanIfTotalPumpsPower    Integer32,
        auxRamanIfPump1WantedPower      Unsigned32,
        auxRamanIfPump1ActualPower      Integer32,
        auxRamanIfPump1Current          Unsigned32,
        auxRamanIfPump1Temperature      Integer32,
        auxRamanIfPump2WantedPower      Unsigned32,
        auxRamanIfPump2ActualPower      Integer32,
        auxRamanIfPump2Current          Unsigned32,
        auxRamanIfPump2Temperature      Integer32,
        auxRamanIfWantedGain            Unsigned32,
        auxRamanIfActualGain            Unsigned32,
        auxRamanIfReceivedPowerLevel    Integer32,
        auxRamanIfReflectionPowerLevel  Integer32,
        auxRamanIfReflectionPowerRatio  Integer32,
        auxRamanIf1510BandReceivedPowerLevel Integer32,
        auxRamanIfOscReceivedPowerLevel  Integer32,
        auxRamanIfAPRState               INTEGER,
        auxRamanIfOscDitherState         INTEGER,
        auxRamanIfLineLossOfSignal       FaultStatus,
        auxRamanIfOscDitherLos           FaultStatus,
        auxRamanIfHighBackReflection     FaultStatus,
        auxRamanIfHighLineOutputPower       FaultStatus,
        auxRamanIfLowLineOutputPower       FaultStatus,
        auxRamanIfModuleTempTooHigh       FaultStatus,
        auxRamanIfModuleTempHigh       FaultStatus,
        auxRamanIfPumpsTempTooHigh       FaultStatus,
        auxRamanIfPumpsTempHigh       FaultStatus,
        auxRamanIfAprShutdown       FaultStatus,
        auxRamanIfLineFiberDeteriorated       FaultStatus,
        auxRamanIf1510BandPowerLos       FaultStatus,
        auxRamanIfManualRestartTrial     CommandString,
        auxRamanIfModuleTemp             Integer32,
        auxRamanIfTxSignalStatus    INTEGER,
        auxRamanIfRxSignalStatus    INTEGER }

auxRamanIfIndex OBJECT-TYPE
    SYNTAX      Unsigned32 (1..2147483647)
    MAX-ACCESS  read-only
    STATUS      current
    DESCRIPTION
        "An arbitrary index assigned to each
        configuration equipment.

"
    ::= { auxRamanIfEntry 1 }

auxRamanIfName OBJECT-TYPE
    SYNTAX      MgmtNameString
    MAX-ACCESS  read-only
    STATUS      current
    DESCRIPTION
        "The name of the FxIf.

"
    ::= { auxRamanIfEntry 2 }

auxRamanIfDescr OBJECT-TYPE
    SYNTAX      DisplayString
    MAX-ACCESS  read-write
    STATUS      current
    DESCRIPTION
        "User configurable label.

"
    DEFVAL { "" }
    ::= { auxRamanIfEntry 3 }

auxRamanIfSubrack OBJECT-TYPE
    SYNTAX      SubrackNumber
    MAX-ACCESS  read-only
    STATUS      current
    DESCRIPTION
        "The number of the subrack where the interface
        is located.

"
    ::= { auxRamanIfEntry 4 }

auxRamanIfSlot OBJECT-TYPE
    SYNTAX      SlotNumber
    MAX-ACCESS  read-only
    STATUS      current
    DESCRIPTION
        "The number of the slot where the interface is
        located.

"
    ::= { auxRamanIfEntry 5 }

auxRamanIfTxPort OBJECT-TYPE
    SYNTAX      PortNumber
    MAX-ACCESS  read-only
    STATUS      current
    DESCRIPTION
        "The number of the port where the interface is
        located.

"
    ::= { auxRamanIfEntry 6 }

auxRamanIfRxPort OBJECT-TYPE
    SYNTAX      PortNumber
    MAX-ACCESS  read-only
    STATUS      current
    DESCRIPTION
        "The number of the port where the interface is
        located.

"
    ::= { auxRamanIfEntry 7 }

auxRamanIfInvPhysIndexOrZero OBJECT-TYPE
    SYNTAX      Unsigned32 (0..2147483647)
    MAX-ACCESS  read-only
    STATUS      current
    DESCRIPTION
        "The row in the invPhysTable for this interface.
        Set to 0 if not known.

"
    ::= { auxRamanIfEntry 8 }

auxRamanIfAdminStatus OBJECT-TYPE
    SYNTAX      BoardOrInterfaceAdminStatus
    MAX-ACCESS  read-write
    STATUS      current
    DESCRIPTION
        "The administrative state for the interface.

        down - The interface should be inactive.

        service - The interface is activated but alarms
        are suppressed. Intended for use during service
        or re-configuration. When service is concluded
        adminStatus should be set to 'up' again.

        up - The interface should be activated when
        it becomes available. Alarms are not suppressed.

"
    DEFVAL { up }
    ::= { auxRamanIfEntry 9 }

auxRamanIfOperStatus OBJECT-TYPE
    SYNTAX      BoardOrInterfaceOperStatus
    MAX-ACCESS  read-only
    STATUS      current
    DESCRIPTION
        "The operational state for the interface.

        notPresent - The interface is not available.

        down - The interface is de-activated or there are
        faults preventing it from going to the 'up'-state.

        up - The interface is active.

"
    DEFVAL { notPresent }
    ::= { auxRamanIfEntry 10 }

auxRamanIfObjectProperty OBJECT-TYPE
    SYNTAX      ObjectProperty
    MAX-ACCESS  read-only
    STATUS      current
    DESCRIPTION
        "Property mask.

"
    ::= { auxRamanIfEntry 11 }

auxRamanIfModuleOperationMode OBJECT-TYPE
    SYNTAX      INTEGER {
                   coPropagating (1),
                   counterPropagating (2)
                }
    MAX-ACCESS  read-only
    STATUS      current
    DESCRIPTION
        "Module operational mode.

"
    ::= { auxRamanIfEntry 12 }

auxRamanIfPumpsOperationMode OBJECT-TYPE
    SYNTAX      INTEGER {
                   maxPumpsPower (1),
                   manualPumpsPower (2),
                   automaticalGainControl (3)
                }
    MAX-ACCESS  read-create
    STATUS      current
    DESCRIPTION
        "Pumps operational mode.

"
    DEFVAL { maxPumpsPower }
    ::= { auxRamanIfEntry 13 }

auxRamanIfPumpsOperationModeConfig OBJECT-TYPE
    SYNTAX      CommandString
    MAX-ACCESS  read-only
    STATUS      current
    DESCRIPTION
        "Configure pumps operational mode.

"
    ::= { auxRamanIfEntry 14 }


auxRamanIfLineFiberType OBJECT-TYPE
    SYNTAX      INTEGER {
                        ftSMF(1),
                        ftLeaf(2),
                        ftTrueWave(3),
                        ftG654(4),
                        ftTeralight(5),
                        ftG653(6)
                }
    MAX-ACCESS  read-write
    STATUS      current
    DESCRIPTION
        "Line fiber type (for adaptive
         gain flattening).

"
    DEFVAL { ftSMF }
    ::= { auxRamanIfEntry 15 }

auxRamanIfAutoRestartProcTime OBJECT-TYPE
    SYNTAX      Unsigned32 (0..100)
    MAX-ACCESS  read-write
    STATUS      current
    DESCRIPTION
        "Automatic Restart Procedure restart time.

"
    DEFVAL { 10 }
    ::= { auxRamanIfEntry 16 }

auxRamanIfArpPauseStatus OBJECT-TYPE
    SYNTAX      INTEGER {
                        normal (1),
                        pause (2)
                }
    MAX-ACCESS  read-only
    STATUS      current
    DESCRIPTION
        "Shows whether the Raman amplifier is in
         Automatic Restart Procedure restart
         state.

"
    ::= { auxRamanIfEntry 17 }

auxRamanIfPumpsStatus OBJECT-TYPE
    SYNTAX      INTEGER {
                        shutdown (1),
                        active (2)
                }
    MAX-ACCESS  read-only
    STATUS      current
    DESCRIPTION
        "Shows whether the pumps are active or not.

"
    ::= { auxRamanIfEntry 18 }

auxRamanIfTotalPumpsPower OBJECT-TYPE
    SYNTAX      Integer32
    MAX-ACCESS  read-only
    STATUS      current
    DESCRIPTION
        "The total power of the pumps.

"
    ::= { auxRamanIfEntry 19 }

auxRamanIfPump1WantedPower OBJECT-TYPE
    SYNTAX      Unsigned32 (100..4000)
    MAX-ACCESS  read-write
    STATUS      current
    DESCRIPTION
        "The wanted power of the higher pump.
         Used for manual configuration.

"
    DEFVAL { 100 }
    ::= { auxRamanIfEntry 20 }

auxRamanIfPump1ActualPower OBJECT-TYPE
    SYNTAX      Integer32
    MAX-ACCESS  read-only
    STATUS      current
    DESCRIPTION
        "The actual power of the higher pump.

"
    ::= { auxRamanIfEntry 21 }

auxRamanIfPump1Current OBJECT-TYPE
    SYNTAX      Unsigned32
    MAX-ACCESS  read-only
    STATUS      current
    DESCRIPTION
        "The current of the higher pump.

"
    ::= { auxRamanIfEntry 22 }

auxRamanIfPump1Temperature OBJECT-TYPE
    SYNTAX      Integer32
    MAX-ACCESS  read-only
    STATUS      current
    DESCRIPTION
        "The temperature of the higher pump.

"
    ::= { auxRamanIfEntry 23 }

auxRamanIfPump2WantedPower OBJECT-TYPE
    SYNTAX      Unsigned32 (100..4000)
    MAX-ACCESS  read-write
    STATUS      current
    DESCRIPTION
        "The wanted power of the higher pump.
         Used for manual configuration.

"
    DEFVAL { 100 }
    ::= { auxRamanIfEntry 24 }

auxRamanIfPump2ActualPower OBJECT-TYPE
    SYNTAX      Integer32
    MAX-ACCESS  read-only
    STATUS      current
    DESCRIPTION
        "The actual power of the higher pump.

"
    ::= { auxRamanIfEntry 25 }

auxRamanIfPump2Current OBJECT-TYPE
    SYNTAX      Unsigned32
    MAX-ACCESS  read-only
    STATUS      current
    DESCRIPTION
        "The current of the higher pump.

"
    ::= { auxRamanIfEntry 26 }

auxRamanIfPump2Temperature OBJECT-TYPE
    SYNTAX      Integer32
    MAX-ACCESS  read-only
    STATUS      current
    DESCRIPTION
        "The temperature of the higher pump.

"
    ::= { auxRamanIfEntry 27 }

auxRamanIfWantedGain OBJECT-TYPE
    SYNTAX      Unsigned32 (30..200)
    MAX-ACCESS  read-write
    STATUS      current
    DESCRIPTION
        "The wanted gain.
         Used in gain-mode.

"
    DEFVAL { 30 }
    ::= { auxRamanIfEntry 28 }

auxRamanIfActualGain OBJECT-TYPE
    SYNTAX      Unsigned32
    MAX-ACCESS  read-only
    STATUS      current
    DESCRIPTION
        "The actual gain.
         Used in gain-mode.

"
    ::= { auxRamanIfEntry 29 }

auxRamanIfReceivedPowerLevel OBJECT-TYPE
    SYNTAX      Integer32
    MAX-ACCESS  read-only
    STATUS      current
    DESCRIPTION
        "The received power on the line i/f.

"
    ::= { auxRamanIfEntry 30 }

auxRamanIfReflectionPowerLevel OBJECT-TYPE
    SYNTAX      Integer32
    MAX-ACCESS  read-only
    STATUS      current
    DESCRIPTION
        "The received reflection power.

"
    ::= { auxRamanIfEntry 31 }

auxRamanIfReflectionPowerRatio OBJECT-TYPE
    SYNTAX      Integer32
    MAX-ACCESS  read-only
    STATUS      current
    DESCRIPTION
        "The received reflection power in relation
         to the power of the pumps.

"
    ::= { auxRamanIfEntry 32 }

auxRamanIf1510BandReceivedPowerLevel OBJECT-TYPE
    SYNTAX      Integer32
    MAX-ACCESS  read-only
    STATUS      current
    DESCRIPTION
        "The received power in the 1510 band.

"
    ::= { auxRamanIfEntry 33 }

auxRamanIfOscReceivedPowerLevel OBJECT-TYPE
    SYNTAX      Integer32
    MAX-ACCESS  read-only
    STATUS      current
    DESCRIPTION
        "The received power of the OSC channel.

"
    ::= { auxRamanIfEntry 34 }

auxRamanIfAPRState OBJECT-TYPE
    SYNTAX      INTEGER {
                        normal (1),
                        shutdown (2)
                }
    MAX-ACCESS  read-only
    STATUS      current
    DESCRIPTION
        "Shows the state of the Automatic
        Power Reduction procedure

"
    ::= { auxRamanIfEntry 35 }

auxRamanIfOscDitherState OBJECT-TYPE
    SYNTAX      INTEGER {
                        normal (1),
                        lost (2)
                }
    MAX-ACCESS  read-only
    STATUS      current
    DESCRIPTION
        "Shows the dithering state of the
         Optical Supervisiory Channel.

"
    ::= { auxRamanIfEntry 36 }

auxRamanIfLineLossOfSignal OBJECT-TYPE
    SYNTAX      FaultStatus
    MAX-ACCESS  read-only
    STATUS      current
    DESCRIPTION
        "The input line signal is lost.


"
    ::= { auxRamanIfEntry 37 }

auxRamanIfOscDitherLos OBJECT-TYPE
    SYNTAX      FaultStatus
    MAX-ACCESS  read-only
    STATUS      current
    DESCRIPTION
        "The dithering of the OSC channel is lost.

"
    ::= { auxRamanIfEntry 38 }

auxRamanIfHighBackReflection OBJECT-TYPE
    SYNTAX      FaultStatus
    MAX-ACCESS  read-only
    STATUS      current
    DESCRIPTION
        "High back-reflection power detected.

"
    ::= { auxRamanIfEntry 39 }

auxRamanIfHighLineOutputPower OBJECT-TYPE
    SYNTAX      FaultStatus
    MAX-ACCESS  read-only
    STATUS      current
    DESCRIPTION
        "High line output power is detected.
         The power is decreased not to exceed
         the maximum power

"
    ::= { auxRamanIfEntry 40 }

auxRamanIfLowLineOutputPower OBJECT-TYPE
    SYNTAX      FaultStatus
    MAX-ACCESS  read-only
    STATUS      current
    DESCRIPTION
        "Low output power is detected.

"
    ::= { auxRamanIfEntry 41 }

auxRamanIfModuleTempTooHigh OBJECT-TYPE
    SYNTAX      FaultStatus
    MAX-ACCESS  read-only
    STATUS      current
    DESCRIPTION
        "Too high ambient temperature of the amplifier
         module causing shut down.

"
    ::= { auxRamanIfEntry 42 }

auxRamanIfModuleTempHigh OBJECT-TYPE
    SYNTAX      FaultStatus
    MAX-ACCESS  read-only
    STATUS      current
    DESCRIPTION
        "High ambient temperature of the amplifier module.
         Crossed warning threshold

"
    ::= { auxRamanIfEntry 43 }

auxRamanIfPumpsTempTooHigh OBJECT-TYPE
    SYNTAX      FaultStatus
    MAX-ACCESS  read-only
    STATUS      current
    DESCRIPTION
        "Too high temperature of the pumps causing
         shut down.

"
    ::= { auxRamanIfEntry 44 }

auxRamanIfPumpsTempHigh OBJECT-TYPE
    SYNTAX      FaultStatus
    MAX-ACCESS  read-only
    STATUS      current
    DESCRIPTION
        "High temperature of the pumps.
         Crossed warning threshold.

"
    ::= { auxRamanIfEntry 45 }

auxRamanIfAprShutdown OBJECT-TYPE
    SYNTAX      FaultStatus
    MAX-ACCESS  read-only
    STATUS      current
    DESCRIPTION
        "Shows if the pumps have been shutdown
        according to any of the APR or ALS
        schemes.

"
    ::= { auxRamanIfEntry 46 }

auxRamanIfLineFiberDeteriorated OBJECT-TYPE
    SYNTAX      FaultStatus
    MAX-ACCESS  read-only
    STATUS      current
    DESCRIPTION
        "The quality of the line fiber has
         changed (deteriorated).

"
    ::= { auxRamanIfEntry 47 }

auxRamanIf1510BandPowerLos OBJECT-TYPE
    SYNTAX      FaultStatus
    MAX-ACCESS  read-only
    STATUS      current
    DESCRIPTION
        "The power of the 1510 band has been lost.

"
    ::= { auxRamanIfEntry 48 }

auxRamanIfManualRestartTrial OBJECT-TYPE
    SYNTAX      CommandString
    MAX-ACCESS  read-only
    STATUS      current
    DESCRIPTION
        "Executing this procedure initiates a manual
         restart trial.

"
    ::= { auxRamanIfEntry 49 }


auxRamanIfModuleTemp OBJECT-TYPE
    SYNTAX      Integer32
    MAX-ACCESS  read-only
    STATUS      current
    DESCRIPTION
        "Shows the ambient temperature of the
        amplifier module.

"
    ::= { auxRamanIfEntry 50 }

auxRamanIfTxSignalStatus OBJECT-TYPE
    SYNTAX      INTEGER {
                        down (1),
                        degraded (2),
                        up (3) }
    MAX-ACCESS  read-only
    STATUS      current
    DESCRIPTION
        "The operational state for outgoing (TX) signal
        of the interface.

        down - A fault that would lead to a protection
        switch has occurred.

        degraded - The signal quality is impaired.

        up - The signal is OK.

"
    DEFVAL { up }
    ::= { auxRamanIfEntry 51 }

auxRamanIfRxSignalStatus OBJECT-TYPE
    SYNTAX      INTEGER {
                        down (1),
                        degraded (2),
                        up (3) }
    MAX-ACCESS  read-only
    STATUS      current
    DESCRIPTION
        "The operational state for incoming (RX) signal
        of the interface.

        down - A major fault has occurred

        degraded - The signal quality is impaired.

        up - The signal is OK.

"
    DEFVAL { up }
    ::= { auxRamanIfEntry 52 }

-- ----------------------------------------------------
-- Aux safety group
-- ----------------------------------------------------

auxRamanSafetyTable  OBJECT-TYPE
    SYNTAX      SEQUENCE OF AuxRamanSafetyEntry
    MAX-ACCESS  not-accessible
    STATUS      current
    DESCRIPTION
        "The list of safety modules."
    ::= { auxRamanSafetyList 1 }

auxRamanSafetyEntry OBJECT-TYPE
    SYNTAX      AuxRamanSafetyEntry
    MAX-ACCESS  not-accessible
    STATUS      current
    DESCRIPTION
        "An entry in the safety list.

"
    INDEX { auxRamanSafetyIndex }
    ::= { auxRamanSafetyTable 1 }

AuxRamanSafetyEntry ::=
    SEQUENCE {
        auxRamanSafetyIndex            Unsigned32,
        auxRamanSafetyName             MgmtNameString,
        auxRamanSafetyDescr            DisplayString,
        auxRamanSafetySubrack          SubrackNumber,
        auxRamanSafetySlot             SlotNumber,
        auxRamanSafetyRxPort           PortNumber,
        auxRamanSafetyTxPort           PortNumber,
        auxRamanSafetyInvPhysIndexOrZero Unsigned32,
        auxRamanSafetyObjectProperty   ObjectProperty,
        auxRamanSafetyShutDownAtInputLoss INTEGER,
        auxRamanSafetyShutDownAtHighTemp  INTEGER,
        auxRamanSafetyShutDownAtHighBackReflection INTEGER,
        auxRamanSafetyHighBackReflectionThreshold  Integer32,
        auxRamanSafetyShutDownAtOscLoss  INTEGER,
        auxRamanSafetyShutDownAt1510BandDrop INTEGER,
        auxRamanSafetyShutDownAtInputLossConfig CommandString,
        auxRamanSafetyShutDownAtHighTempConfig  CommandString,
        auxRamanSafetyShutDownAtHighBackReflectionConfig CommandString,
        auxRamanSafetyShutDownAtOscLossConfig CommandString,
        auxRamanSafetyShutDownAt1510BandDropConfig  CommandString,
        auxRamanSafetyPasswd                        DisplayString,
        auxRamanSafetyPasswdConfig                  CommandString,
        auxRamanSafety1510BandDropThreshold         Integer32,
        auxRamanSafetyInhibitStartAtOscLoss         INTEGER,
        auxRamanSafetyInhibitStartAtOscLossConfig   CommandString,
        auxRamanSafetyShutDownAtLowBandDrop         INTEGER,
        auxRamanSafetyLowBandScatteringThreshold    Integer32,
        auxRamanSafetyShutDownAtLowBandDropConfig   CommandString,
        auxRamanSafetyAmplifierSwitch               INTEGER,
        auxRamanSafetyAmplifierSwitchConfig         CommandString,
        auxRamanSafetyLowBandScatteringTolerance    Integer32}

auxRamanSafetyIndex OBJECT-TYPE
    SYNTAX      Unsigned32 (1..2147483647)
    MAX-ACCESS  read-only
    STATUS      current
    DESCRIPTION
        "An arbitrary index assigned to each
        configuration equipment.

"
    ::= { auxRamanSafetyEntry 1 }

auxRamanSafetyName OBJECT-TYPE
    SYNTAX      MgmtNameString
    MAX-ACCESS  read-only
    STATUS      current
    DESCRIPTION
        "The name of the ramanSafety object.

"
    ::= { auxRamanSafetyEntry 2 }

auxRamanSafetyDescr OBJECT-TYPE
    SYNTAX      DisplayString
    MAX-ACCESS  read-write
    STATUS      current
    DESCRIPTION
        "User configurable label.

"
    DEFVAL { "" }
    ::= { auxRamanSafetyEntry 3 }

auxRamanSafetySubrack OBJECT-TYPE
    SYNTAX      SubrackNumber
    MAX-ACCESS  read-only
    STATUS      current
    DESCRIPTION
        "The number of the subrack where the interface
        is located.

"
    ::= { auxRamanSafetyEntry 4 }

auxRamanSafetySlot OBJECT-TYPE
    SYNTAX      SlotNumber
    MAX-ACCESS  read-only
    STATUS      current
    DESCRIPTION
        "The number of the slot where the interface is
        located.

"
    ::= { auxRamanSafetyEntry 5 }

auxRamanSafetyTxPort OBJECT-TYPE
    SYNTAX      PortNumber
    MAX-ACCESS  read-only
    STATUS      current
    DESCRIPTION
        "The number of the port where the interface is
        located.

"
    ::= { auxRamanSafetyEntry 6 }

auxRamanSafetyRxPort OBJECT-TYPE
    SYNTAX      PortNumber
    MAX-ACCESS  read-only
    STATUS      current
    DESCRIPTION
        "The number of the port where the interface is
        located.

"
    ::= { auxRamanSafetyEntry 7 }

auxRamanSafetyInvPhysIndexOrZero OBJECT-TYPE
    SYNTAX      Unsigned32 (0..2147483647)
    MAX-ACCESS  read-only
    STATUS      current
    DESCRIPTION
        "The row in the invPhysTable for this interface.
        Set to 0 if not known.

"
    ::= { auxRamanSafetyEntry 8 }

auxRamanSafetyObjectProperty OBJECT-TYPE
    SYNTAX      ObjectProperty
    MAX-ACCESS  read-only
    STATUS      current
    DESCRIPTION
        "Property mask.

"
    ::= { auxRamanSafetyEntry 9 }

auxRamanSafetyShutDownAtInputLoss OBJECT-TYPE
    SYNTAX      INTEGER {
                  disabled (1),
                  enabled (2)
                }
    MAX-ACCESS  read-create
    STATUS      current
    DESCRIPTION
        "This parameter controls whether the
         amplifier will shut down in the following
         situation:

          Loss of input power

"
    DEFVAL { enabled }
    ::= { auxRamanSafetyEntry 10 }

auxRamanSafetyShutDownAtHighTemp OBJECT-TYPE
    SYNTAX      INTEGER {
                  disabled (1),
                  enabled (2)
                }
    MAX-ACCESS  read-create
    STATUS      current
    DESCRIPTION
        "This parameter controls whether the
         amplifier will shut down in the following
         situation:

           The temperature of the pumps or the
           modules is high.

"
    DEFVAL { enabled }
    ::= { auxRamanSafetyEntry 11 }

auxRamanSafetyShutDownAtHighBackReflection OBJECT-TYPE
    SYNTAX      INTEGER {
                  disabled (1),
                  enabled (2)
                }
    MAX-ACCESS  read-create
    STATUS      current
    DESCRIPTION
        "This parameter controls whether the
         amplifier will shut down in the following
         situation:

           There is a high back reflection of power,
           indication that there might be a fibre
           break.

"
    DEFVAL { enabled }
    ::= { auxRamanSafetyEntry 12 }

auxRamanSafetyHighBackReflectionThreshold OBJECT-TYPE
    SYNTAX      Integer32 (-28..-19)
    MAX-ACCESS  read-write
    STATUS      current
    DESCRIPTION
        "The threshold for back reflection
         causing amplifier pumps to shut down.

         The threshold is a ratio expressed in
         dB relative to the output power of the
         amplifier.

"
    DEFVAL { -22 }
    ::= { auxRamanSafetyEntry 13 }

auxRamanSafetyShutDownAtOscLoss OBJECT-TYPE
    SYNTAX      INTEGER {
                  disabled (1),
                  enabled (2)
                }
    MAX-ACCESS  read-create
    STATUS      current
    DESCRIPTION
        "This parameter controls whether the
         amplifier will shut down in the following
         situation:

           The signal from the OSC channel is lost.

"
    DEFVAL { disabled }
    ::= { auxRamanSafetyEntry 14 }

auxRamanSafetyShutDownAt1510BandDrop OBJECT-TYPE
    SYNTAX      INTEGER {
                  disabled (1),
                  enabled (2)
                }
    MAX-ACCESS  read-create
    STATUS      current
    DESCRIPTION
        "This parameter controls whether the
         amplifier will shut down in the following
         situation:

          The power from the 1510 band drops.

"
    DEFVAL { enabled }
    ::= { auxRamanSafetyEntry 15 }

auxRamanSafetyShutDownAtInputLossConfig OBJECT-TYPE
    SYNTAX      CommandString
    MAX-ACCESS  read-only
    STATUS      current
    DESCRIPTION
        ".
"
    ::= { auxRamanSafetyEntry 16 }

auxRamanSafetyShutDownAtHighTempConfig OBJECT-TYPE
    SYNTAX      CommandString
    MAX-ACCESS  read-only
    STATUS      current
    DESCRIPTION
        ".

"
    ::= { auxRamanSafetyEntry 17 }

auxRamanSafetyShutDownAtHighBackReflectionConfig OBJECT-TYPE
    SYNTAX      CommandString
    MAX-ACCESS  read-only
    STATUS      current
    DESCRIPTION
        ".

"
    ::= { auxRamanSafetyEntry 18 }

auxRamanSafetyShutDownAtOscLossConfig OBJECT-TYPE
    SYNTAX      CommandString
    MAX-ACCESS  read-only
    STATUS      current
    DESCRIPTION
        ".
"
    ::= { auxRamanSafetyEntry 19 }

auxRamanSafetyShutDownAt1510BandDropConfig OBJECT-TYPE
    SYNTAX      CommandString
    MAX-ACCESS  read-only
    STATUS      current
    DESCRIPTION
        ".
"
    ::= { auxRamanSafetyEntry 20 }

auxRamanSafetyPasswd OBJECT-TYPE
    SYNTAX      DisplayString
    MAX-ACCESS  read-create
    STATUS      current
    DESCRIPTION
        "Password protecting the safety parameters

        If password is '-' (dash), then the password
        control is disabled.

"
    DEFVAL { "-" }
    ::= { auxRamanSafetyEntry 21 }

auxRamanSafetyPasswdConfig OBJECT-TYPE
    SYNTAX      CommandString
    MAX-ACCESS  read-only
    STATUS      current
    DESCRIPTION
        ".

"
    ::= { auxRamanSafetyEntry 22 }

auxRamanSafety1510BandDropThreshold OBJECT-TYPE
    SYNTAX      Integer32 (1..50)
    MAX-ACCESS  read-write
    STATUS      current
    DESCRIPTION
        "The threshold for OSC band drop
         causing pumps shut down.

"
    DEFVAL { 20 }
    ::= { auxRamanSafetyEntry 23 }

auxRamanSafetyInhibitStartAtOscLoss OBJECT-TYPE
    SYNTAX      INTEGER {
                  disabled (1),
                  enabled (2)
                }
    MAX-ACCESS  read-create
    STATUS      current
    DESCRIPTION
        "This parameter controls whether the
         amplifier is allowed to turn on in
         a situation where the OSC is missing

"
    DEFVAL { enabled }
    ::= { auxRamanSafetyEntry 24 }


auxRamanSafetyInhibitStartAtOscLossConfig OBJECT-TYPE
    SYNTAX      CommandString
    MAX-ACCESS  read-only
    STATUS      current
    DESCRIPTION
        ".
"
    ::= { auxRamanSafetyEntry 25 }

auxRamanSafetyShutDownAtLowBandDrop OBJECT-TYPE
    SYNTAX      INTEGER {
                  disabled (1),
                  enabled (2)
                  }
    MAX-ACCESS  read-create
    STATUS      current
    DESCRIPTION
        "This parameter controls whether the
         amplifier will shut down in the following
         situation:

         Low L-band scattering is detected.

"
    DEFVAL { enabled }
    ::= { auxRamanSafetyEntry 26 }

auxRamanSafetyLowBandScatteringThreshold OBJECT-TYPE
    SYNTAX      Integer32 (-450..-250)
    MAX-ACCESS  read-write
    STATUS      current
    DESCRIPTION
        "The threshold for safety parameter 'Shut down
         at L-band power drop'.

"
    DEFVAL { -370 }
    ::= { auxRamanSafetyEntry 27 }

auxRamanSafetyShutDownAtLowBandDropConfig OBJECT-TYPE
    SYNTAX      CommandString
    MAX-ACCESS  read-only
    STATUS      current
    DESCRIPTION
        ".
"
    ::= { auxRamanSafetyEntry 28 }

auxRamanSafetyAmplifierSwitch OBJECT-TYPE
    SYNTAX      INTEGER {
                  disabled (1),
                  enabled (2)
                }
    MAX-ACCESS  read-create
    STATUS      current
    DESCRIPTION
        "Enable activating or disable of the pumps operation.
        When switch in Enabled mode,
        pumps are activated to last operation mode
        and power/current/gain settings

"
    DEFVAL { disabled }
    ::= { auxRamanSafetyEntry 29 }


auxRamanSafetyAmplifierSwitchConfig OBJECT-TYPE
    SYNTAX      CommandString
    MAX-ACCESS  read-only
    STATUS      current
    DESCRIPTION
        ".
"
    ::= { auxRamanSafetyEntry 30 }

auxRamanSafetyLowBandScatteringTolerance OBJECT-TYPE
    SYNTAX      Integer32 (10..20)
    MAX-ACCESS  read-write
    STATUS      current
    DESCRIPTION
        "The transient tolerance (expressed in dB) for safety parameter
         'Shut down at L-band drop'.

"
    DEFVAL { 15 }
    ::= { auxRamanSafetyEntry 31 }


-- ----------------------------------------------------
-- Aux PE i/f group
-- ----------------------------------------------------

auxPEIfTable  OBJECT-TYPE
    SYNTAX      SEQUENCE OF AuxPEIfEntry
    MAX-ACCESS  not-accessible
    STATUS      current
    DESCRIPTION
        "The list of PE i/f."
    ::= { auxPEIfList 1 }

auxPEIfEntry OBJECT-TYPE
    SYNTAX      AuxPEIfEntry
    MAX-ACCESS  not-accessible
    STATUS      current
    DESCRIPTION
        "An entry in the PE i/f list.

"
    INDEX { auxPEIfIndex }
    ::= { auxPEIfTable 1 }

AuxPEIfEntry ::=
    SEQUENCE {
        auxPEIfIndex                    Unsigned32,
        auxPEIfName                     MgmtNameString,
        auxPEIfDescr                    DisplayString,
        auxPEIfSubrack                  SubrackNumber,
        auxPEIfSlot                     SlotNumber,
        auxPEIfRxPort                   PortNumber,
        auxPEIfTxPort                   PortNumber,
        auxPEIfInvPhysIndexOrZero       Unsigned32,
        auxPEIfAdminStatus              BoardOrInterfaceAdminStatus,
        auxPEIfOperStatus               BoardOrInterfaceOperStatus,
        auxPEIfObjectProperty           ObjectProperty,
        auxPEIfPumpsOperationMode       INTEGER,
        auxPEIfPumpsOperationModeConfig     CommandString,
        auxPEIfAutoRestartProcTime          Unsigned32,
        auxPEIfPumpsStatus                  INTEGER,
        auxPEIfWantedPower              Integer32,
        auxPEIfWantedGain               Unsigned32,
        auxPEIfPumpsTotalCurrent        Unsigned32,
        auxPEIfPump1Temperature         Integer32,
        auxPEIfActualGain               Integer32,
        auxPEIfReceivedPowerLevel       Integer32,
        auxPEIfCombinedOutPwrLevel      Integer32,
        auxPEIfReflectionPowerLevel     Integer32,
        auxPEIfReflectionPowerRatio     Integer32,
        auxPEIfLowBandScatteredPowerLevel   Integer32,
        auxPEIfLineLossOfSignal         FaultStatus,
        auxPEIfHighBackReflection       FaultStatus,
        auxPEIfAutoPowerReduction       FaultStatus,
        auxPEIfLowLineOutputPower       FaultStatus,
        auxPEIfModuleTempTooHigh        FaultStatus,
        auxPEIfModuleTempHigh           FaultStatus,
        auxPEIfPumpsTempTooHigh         FaultStatus,
        auxPEIfPumpsTempHigh            FaultStatus,
        auxPEIfModuleTemp               Integer32,
        auxPEIfPump2Temperature         Integer32}

auxPEIfIndex OBJECT-TYPE
    SYNTAX      Unsigned32 (1..2147483647)
    MAX-ACCESS  read-only
    STATUS      current
    DESCRIPTION
        "An arbitrary index assigned to each
        configuration equipment.

"
    ::= { auxPEIfEntry 1 }

auxPEIfName OBJECT-TYPE
    SYNTAX      MgmtNameString
    MAX-ACCESS  read-only
    STATUS      current
    DESCRIPTION
        "The name of the FxIf.

"
    ::= { auxPEIfEntry 2 }

auxPEIfDescr OBJECT-TYPE
    SYNTAX      DisplayString
    MAX-ACCESS  read-write
    STATUS      current
    DESCRIPTION
        "User configurable label.

"
    DEFVAL { "" }
    ::= { auxPEIfEntry 3 }

auxPEIfSubrack OBJECT-TYPE
    SYNTAX      SubrackNumber
    MAX-ACCESS  read-only
    STATUS      current
    DESCRIPTION
        "The number of the subrack where the interface
        is located.

"
    ::= { auxPEIfEntry 4 }

auxPEIfSlot OBJECT-TYPE
    SYNTAX      SlotNumber
    MAX-ACCESS  read-only
    STATUS      current
    DESCRIPTION
        "The number of the slot where the interface is
        located.

"
    ::= { auxPEIfEntry 5 }

auxPEIfTxPort OBJECT-TYPE
    SYNTAX      PortNumber
    MAX-ACCESS  read-only
    STATUS      current
    DESCRIPTION
        "The number of the port where the interface is
        located.

"
    ::= { auxPEIfEntry 6 }

auxPEIfRxPort OBJECT-TYPE
    SYNTAX      PortNumber
    MAX-ACCESS  read-only
    STATUS      current
    DESCRIPTION
        "The number of the port where the interface is
        located.

"
    ::= { auxPEIfEntry 7 }

auxPEIfInvPhysIndexOrZero OBJECT-TYPE
    SYNTAX      Unsigned32 (0..2147483647)
    MAX-ACCESS  read-only
    STATUS      current
    DESCRIPTION
        "The row in the invPhysTable for this interface.
        Set to 0 if not known.

"
    ::= { auxPEIfEntry 8 }

auxPEIfAdminStatus OBJECT-TYPE
    SYNTAX      BoardOrInterfaceAdminStatus
    MAX-ACCESS  read-write
    STATUS      current
    DESCRIPTION
        "The administrative state for the interface.

        down - The interface should be inactive.

        service - The interface is activated but alarms
        are suppressed. Intended for use during service
        or re-configuration. When service is concluded
        adminStatus should be set to 'up' again.

        up - The interface should be activated when
        it becomes available. Alarms are not suppressed.

"
    DEFVAL { up }
    ::= { auxPEIfEntry 9 }

auxPEIfOperStatus OBJECT-TYPE
    SYNTAX      BoardOrInterfaceOperStatus
    MAX-ACCESS  read-only
    STATUS      current
    DESCRIPTION
        "The operational state for the interface.

        notPresent - The interface is not available.

        down - The interface is de-activated or there are
        faults preventing it from going to the 'up'-state.

        up - The interface is active.

"
    DEFVAL { notPresent }
    ::= { auxPEIfEntry 10 }

auxPEIfObjectProperty OBJECT-TYPE
    SYNTAX      ObjectProperty
    MAX-ACCESS  read-only
    STATUS      current
    DESCRIPTION
        "Property mask.

"
    ::= { auxPEIfEntry 11 }

auxPEIfPumpsOperationMode OBJECT-TYPE
    SYNTAX      INTEGER {
                   constantPower (1),
                   constantGain (2)
                }
    MAX-ACCESS  read-create
    STATUS      current
    DESCRIPTION
        "In constant power mode the desired power has to be set.
         In constant gain the desired output gain should be set.

"
    DEFVAL { constantGain }
    ::= { auxPEIfEntry 12 }

auxPEIfPumpsOperationModeConfig OBJECT-TYPE
    SYNTAX      CommandString
    MAX-ACCESS  read-only
    STATUS      current
    DESCRIPTION
        "Configure pumps operational mode.
         In constant power mode the desired power has to be set.
         In constant gain mode the desired output gain should be set.

"
    ::= { auxPEIfEntry 13 }

auxPEIfAutoRestartProcTime OBJECT-TYPE
    SYNTAX      Unsigned32 (0..100)
    MAX-ACCESS  read-write
    STATUS      current
    DESCRIPTION
        "Automatic Restart Procedure restart time.

"
    DEFVAL { 10 }
    ::= { auxPEIfEntry 14 }

auxPEIfPumpsStatus OBJECT-TYPE
    SYNTAX      INTEGER {
                        shutdown (1),
                        active (2)
                }
    MAX-ACCESS  read-only
    STATUS      current
    DESCRIPTION
        "Shows whether the pumps are active or not.

"
    ::= { auxPEIfEntry 15 }

auxPEIfWantedPower OBJECT-TYPE
   SYNTAX       Integer32 (100..261)
   MAX-ACCESS   read-write
   STATUS       current
   DESCRIPTION
        "Output power setting for constant power operation mode.

"
   DEFVAL { 170 }
   ::= { auxPEIfEntry 16 }

auxPEIfWantedGain OBJECT-TYPE
    SYNTAX      Unsigned32 (50..90)
    MAX-ACCESS  read-write
    STATUS      current
    DESCRIPTION
        "Required gain value in dB for constant gain operation mode.

"
    DEFVAL { 62 }
    ::= { auxPEIfEntry 17 }

auxPEIfPumpsTotalCurrent OBJECT-TYPE
    SYNTAX      Unsigned32
    MAX-ACCESS  read-only
    STATUS      current
    DESCRIPTION
        "Pumps total current

"
    ::= { auxPEIfEntry 18 }

auxPEIfPump1Temperature OBJECT-TYPE
    SYNTAX      Integer32
    MAX-ACCESS  read-only
    STATUS      current
    DESCRIPTION
        "The temperature of the higher pump.

"
    ::= { auxPEIfEntry 19 }

auxPEIfActualGain OBJECT-TYPE
    SYNTAX      Integer32
    MAX-ACCESS  read-only
    STATUS      current
    DESCRIPTION
        "The actual gain of the Amplifier (deci-dB).

"
    ::= { auxPEIfEntry 20 }

auxPEIfReceivedPowerLevel OBJECT-TYPE
    SYNTAX      Integer32
    MAX-ACCESS  read-only
    STATUS      current
    DESCRIPTION
        "Input Power (Forward mode) (deci-dBm).
         Please Note: Original value of Float type was transformed to an integer,
         therefore the MIB value is presented in deci-dBm. (i.e. 50.5 dBm transformed to 505 deci-dBm).
         Any EMS GUI should transform the value back to dBm value.

"
    ::= { auxPEIfEntry 21 }

auxPEIfCombinedOutPwrLevel OBJECT-TYPE
    SYNTAX      Integer32
    MAX-ACCESS  read-only
    STATUS  current
    DESCRIPTION
        "Line Interface combined Output Power (deci-dBm).
         Please Note: Original value of Float type was transformed to an integer,
         therefore the MIB value is presented in deci-dBm. (i.e. 50.5 dBm transformed to 505 deci-dBm).
         Any EMS GUI should transform the value back to dBm value.

"
    ::= { auxPEIfEntry 22 }

auxPEIfReflectionPowerLevel OBJECT-TYPE
    SYNTAX      Integer32
    MAX-ACCESS  read-only
    STATUS      current
    DESCRIPTION
        "The received reflection power.

"
    ::= { auxPEIfEntry 23 }

auxPEIfReflectionPowerRatio OBJECT-TYPE
    SYNTAX      Integer32
    MAX-ACCESS  read-only
    STATUS      current
    DESCRIPTION
        "The received reflection power in relation
         to the power of the pumps.

"
    ::= { auxPEIfEntry 24 }

auxPEIfLowBandScatteredPowerLevel OBJECT-TYPE
    SYNTAX      Integer32
    MAX-ACCESS  read-only
    STATUS      current
    DESCRIPTION
        "The scattered power in the L-band.

"
    ::= { auxPEIfEntry 25 }


auxPEIfLineLossOfSignal OBJECT-TYPE
    SYNTAX      FaultStatus
    MAX-ACCESS  read-only
    STATUS      current
    DESCRIPTION
        "The input line signal is lost.

"
    ::= { auxPEIfEntry 26 }

auxPEIfHighBackReflection OBJECT-TYPE
    SYNTAX      FaultStatus
    MAX-ACCESS  read-only
    STATUS      current
    DESCRIPTION
        "High back-reflection power detected.

"
    ::= { auxPEIfEntry 27 }

auxPEIfAutoPowerReduction OBJECT-TYPE
    SYNTAX      FaultStatus
    MAX-ACCESS  read-only
    STATUS      current
    DESCRIPTION
        "Automatic Power Reduction

"
    ::= { auxPEIfEntry 28 }

auxPEIfLowLineOutputPower OBJECT-TYPE
    SYNTAX      FaultStatus
    MAX-ACCESS  read-only
    STATUS      current
    DESCRIPTION
        "Low output power is detected.

"
    ::= { auxPEIfEntry 29 }

auxPEIfModuleTempTooHigh OBJECT-TYPE
    SYNTAX      FaultStatus
    MAX-ACCESS  read-only
    STATUS      current
    DESCRIPTION
        "Too high ambient temperature of the amplifier
         module causing shut down.

"
    ::= { auxPEIfEntry 30 }

auxPEIfModuleTempHigh OBJECT-TYPE
    SYNTAX      FaultStatus
    MAX-ACCESS  read-only
    STATUS      current
    DESCRIPTION
        "High ambient temperature of the amplifier module.
         Crossed warning threshold

"
    ::= { auxPEIfEntry 31 }

auxPEIfPumpsTempTooHigh OBJECT-TYPE
    SYNTAX      FaultStatus
    MAX-ACCESS  read-only
    STATUS      current
    DESCRIPTION
        "Too high temperature of the pumps causing
         shut down.

"
    ::= { auxPEIfEntry 32 }

auxPEIfPumpsTempHigh OBJECT-TYPE
    SYNTAX      FaultStatus
    MAX-ACCESS  read-only
    STATUS      current
    DESCRIPTION
        "High temperature of the pumps.
         Crossed warning threshold.

"
    ::= { auxPEIfEntry 33 }

auxPEIfModuleTemp OBJECT-TYPE
    SYNTAX      Integer32
    MAX-ACCESS  read-only
    STATUS      current
    DESCRIPTION
        "Shows the ambient temperature of the
         amplifier module.

"
    ::= { auxPEIfEntry 34 }

auxPEIfPump2Temperature OBJECT-TYPE
    SYNTAX      Integer32
    MAX-ACCESS  read-only
    STATUS      current
    DESCRIPTION
        "Pump #2 temperature.

"
    ::= { auxPEIfEntry 35 }


-- ----------------------------------------------------
-- Aux Node group
-- ----------------------------------------------------

auxNodeTable  OBJECT-TYPE
    SYNTAX      SEQUENCE OF AuxNodeEntry
    MAX-ACCESS  not-accessible
    STATUS      current
    DESCRIPTION
        "The list of Node (TM2000) stuff."
    ::= { auxNodeList 1 }

auxNodeEntry OBJECT-TYPE
    SYNTAX      AuxNodeEntry
    MAX-ACCESS  not-accessible
    STATUS      current
    DESCRIPTION
        "An entry in the Node list.

"
    INDEX { auxNodeIndex }
    ::= { auxNodeTable 1 }

AuxNodeEntry ::=
    SEQUENCE {
        auxNodeIndex                Unsigned32,
        auxNodeName                 MgmtNameString,
        auxNodeDescr                DisplayString,
        auxNodeIpAddress            IpAddress,
        auxNodePort                 Unsigned32,
        auxNodeEventPort            Unsigned32,
        auxNodeTime                 DateAndTime,
        auxNodeNtpPrimary           IpAddress,
        auxNodeNtpSecondary         IpAddress,
        auxNodeChangeLocalTime      CommandString,
        auxNodeHostUnreachable      FaultStatus}

auxNodeIndex OBJECT-TYPE
    SYNTAX      Unsigned32 (1..2147483647)
    MAX-ACCESS  read-only
    STATUS      current
    DESCRIPTION
        "An arbitrary index assigned to each
        configuration equipment.

"
    ::= { auxNodeEntry 1 }

auxNodeName OBJECT-TYPE
    SYNTAX      MgmtNameString
    MAX-ACCESS  read-only
    STATUS      current
    DESCRIPTION
        "The name of the Node.

"
    ::= { auxNodeEntry 2 }

auxNodeDescr OBJECT-TYPE
    SYNTAX      DisplayString
    MAX-ACCESS  read-write
    STATUS      current
    DESCRIPTION
        "User configurable label.

"
    DEFVAL { "" }
    ::= { auxNodeEntry 3 }

auxNodeIpAddress OBJECT-TYPE
    SYNTAX      IpAddress
    MAX-ACCESS  read-write
    STATUS      current
    DESCRIPTION
        "The IP address for the TM2000 node. The default value is set to 10.0.<subrack>.11 at system start-up.

"
    ::= { auxNodeEntry 4 }

auxNodePort OBJECT-TYPE
    SYNTAX      Unsigned32 (1024..65535)
    MAX-ACCESS  read-write
    STATUS      current
    DESCRIPTION
        "The server port number for the TM2000 node.

"
    DEFVAL { 49177 }
    ::= { auxNodeEntry 5 }

auxNodeEventPort OBJECT-TYPE
    SYNTAX      Unsigned32 (1024..65535)
    MAX-ACCESS  read-write
    STATUS      current
    DESCRIPTION
        "The event port number for the TM2000 node.

"
    DEFVAL { 50177 }
    ::= { auxNodeEntry 6 }

auxNodeTime OBJECT-TYPE
    SYNTAX      DateAndTime
    MAX-ACCESS  read-only
    STATUS      current
    DESCRIPTION
        "The date and time of the TM2000 node.

"
    ::= { auxNodeEntry 7 }

auxNodeNtpPrimary OBJECT-TYPE
    SYNTAX      IpAddress
    MAX-ACCESS  read-write
    STATUS      current
    DESCRIPTION
        "The primary NTP Server address. This will
	 default be set to master CU IP address which
	 is 10.0.1.1.

"
    ::= { auxNodeEntry 8 }

auxNodeNtpSecondary OBJECT-TYPE
    SYNTAX      IpAddress
    MAX-ACCESS  read-write
    STATUS      current
    DESCRIPTION
        "The secondary NTP Server address.

"
    ::= { auxNodeEntry 9 }

auxNodeChangeLocalTime OBJECT-TYPE
    SYNTAX      CommandString
    MAX-ACCESS  read-write
    STATUS      current
    DESCRIPTION
        "Change the local date and time.

        Year - If no century is input the
        current century is set by default.

        Month - 1 to 12

        Day - 1 to 31

        Hour - 0 to 23

        Minute - 0 to 59

        Second - 0 to 59

        Note: Setting of the local time is disabled if
        either the primary or secondary time server
        is set.

"
    ::= { auxNodeEntry 10 }

auxNodeHostUnreachable OBJECT-TYPE
    SYNTAX      FaultStatus
    MAX-ACCESS  read-only
    STATUS      current
    DESCRIPTION
        "Can not contact the remote external equipment.
        Check address and ports.

        A(ctivation): Contact lost

        D(e-activation): Contact established again

"
    ::= { auxNodeEntry 11 }


-- ----------------------------------------------------
-- Aux Cabinet group
-- ----------------------------------------------------

auxCabinetTable  OBJECT-TYPE
    SYNTAX      SEQUENCE OF AuxCabinetEntry
    MAX-ACCESS  not-accessible
    STATUS      current
    DESCRIPTION
        "The list of Cabinet stuff."
    ::= { auxCabinetList 1 }

auxCabinetEntry OBJECT-TYPE
    SYNTAX      AuxCabinetEntry
    MAX-ACCESS  not-accessible
    STATUS      current
    DESCRIPTION
        "An entry in the Cabinet list.

"
    INDEX { auxCabinetIndex }
    ::= { auxCabinetTable 1 }

AuxCabinetEntry ::=
    SEQUENCE {
        auxCabinetIndex                 Unsigned32,
        auxCabinetName                  MgmtNameString,
        auxCabinetDescr                 DisplayString,
        auxCabinetAdminStatus           AdminStatusWithNA,
        auxCabinetOperStatus            INTEGER,
        auxCabinetUpId                  Unsigned32,
        auxCabinetIndoorTemp            Signed32WithNA,
        auxCabinetOutdoorTemp           Signed32WithNA,
        auxCabinetOperMode              INTEGER,
        auxCabinetDoorAlarm             FaultStatus,
        auxCabinetSPDAlarm              FaultStatus,
        auxCabinetHighTempAlarm         FaultStatus,
        auxCabinetCtrlFailAlarm         FaultStatus,
        auxCabinetHeatFailAlarm         FaultStatus,
        auxCabinetExtTempFailAlarm      FaultStatus,
        auxCabinetIntTempFailAlarm      FaultStatus}

auxCabinetIndex OBJECT-TYPE
    SYNTAX      Unsigned32 (1..2147483647)
    MAX-ACCESS  read-only
    STATUS      current
    DESCRIPTION
        "An arbitrary index assigned to each
        configuration equipment.

"
    ::= { auxCabinetEntry 1 }

auxCabinetName OBJECT-TYPE
    SYNTAX      MgmtNameString
    MAX-ACCESS  read-only
    STATUS      current
    DESCRIPTION
        "The name of the cabinet.

"
    ::= { auxCabinetEntry 2 }

auxCabinetDescr OBJECT-TYPE
    SYNTAX      DisplayString
    MAX-ACCESS  read-write
    STATUS      current
    DESCRIPTION
        "User configurable label.

"
    DEFVAL { "" }
    ::= { auxCabinetEntry 3 }

auxCabinetAdminStatus OBJECT-TYPE
    SYNTAX     AdminStatusWithNA
    MAX-ACCESS read-write
    STATUS     current
    DESCRIPTION
        "The administrative state of the cabinet.

        down - The interface is de-activated.

        service - The interface is activated but alarms
        are suppressed. Intended for use during service
        or re-configuration. When service is concluded
        adminStatus should be set to 'up' again. Note that
        there is no difference between 'up' and 'service',
        if no alarms can be raised from this object.

        up - The interface will be activated when
        available. Alarms are not suppressed.

"
    DEFVAL { up }
    ::= { auxCabinetEntry 4 }

auxCabinetOperStatus OBJECT-TYPE
    SYNTAX      INTEGER {
                    notPresent (1),
                    down (2),
                    up (3) }
    MAX-ACCESS  read-only
    STATUS      current
    DESCRIPTION
        "Cabinet operational status

"
    ::= { auxCabinetEntry 5 }

auxCabinetUpId OBJECT-TYPE
    SYNTAX      Unsigned32   (0..2147483647)
    MAX-ACCESS  read-only
    STATUS      current
    DESCRIPTION
        "Identity in the UP for the auxCabinet entry in the traffic unit
"
    DEFVAL { 0  }
    ::= { auxCabinetEntry 6 }

auxCabinetIndoorTemp OBJECT-TYPE
    SYNTAX      Signed32WithNA
    MAX-ACCESS  read-only
    STATUS      current
    DESCRIPTION
        "The indoor temperature in the cabinet in 0.1 degrees centigrade.

"
    ::= { auxCabinetEntry 7 }

auxCabinetOutdoorTemp OBJECT-TYPE
    SYNTAX      Signed32WithNA
    MAX-ACCESS  read-only
    STATUS      current
    DESCRIPTION
        "The outdoor temperature in the cabinet in 0.1 degrees centigrade.

"
    ::= { auxCabinetEntry 8 }

-- The operating mode enum is defined in document PSAB 15:152
auxCabinetOperMode OBJECT-TYPE
    SYNTAX      INTEGER {
                    off         (0),
                    cooling     (1),
                    heating     (2),
                    nightmode   (3),
                    tsf         (4),
                    selftest    (5),
                    manual      (6)}
    MAX-ACCESS  read-only
    STATUS      current
    DESCRIPTION
        "Cabinet operating mode

"
    ::= { auxCabinetEntry 9 }

auxCabinetDoorAlarm OBJECT-TYPE
    SYNTAX      FaultStatus
    MAX-ACCESS  read-only
    STATUS      current
    DESCRIPTION
        "
        Alarm: The cabinet door is opened.

        OK: The cabinet door is closed.

"
    ::= { auxCabinetEntry 10 }

auxCabinetSPDAlarm OBJECT-TYPE
    SYNTAX      FaultStatus
    MAX-ACCESS  read-only
    STATUS      current
    DESCRIPTION
        "
        Alarm: Surge Protection Device alarm.

        OK: Surge Protection Device ok.

"
    ::= { auxCabinetEntry 11 }

auxCabinetHighTempAlarm OBJECT-TYPE
    SYNTAX      FaultStatus
    MAX-ACCESS  read-only
    STATUS      current
    DESCRIPTION
        "
        Alarm: Cabinet temperature too high.

        OK: Cabinet temperature ok.

"
    ::= { auxCabinetEntry 12 }

auxCabinetCtrlFailAlarm OBJECT-TYPE
    SYNTAX      FaultStatus
    MAX-ACCESS  read-only
    STATUS      current
    DESCRIPTION
        "
        Alarm: Cabinet controller failure.

        OK: Cabinet controller ok.

"
    ::= { auxCabinetEntry 13 }

auxCabinetHeatFailAlarm OBJECT-TYPE
    SYNTAX      FaultStatus
    MAX-ACCESS  read-only
    STATUS      current
    DESCRIPTION
        "
        Alarm: Cabinet heater failure.

        OK: Cabinet heater ok.

"
    ::= { auxCabinetEntry 14 }

auxCabinetExtTempFailAlarm OBJECT-TYPE
    SYNTAX      FaultStatus
    MAX-ACCESS  read-only
    STATUS      current
    DESCRIPTION
        "
        Alarm: Cabinet external temp sensor failure.

        OK: Cabinet external temp sensor ok.

"
    ::= { auxCabinetEntry 15 }

auxCabinetIntTempFailAlarm OBJECT-TYPE
    SYNTAX      FaultStatus
    MAX-ACCESS  read-only
    STATUS      current
    DESCRIPTION
        "
        Alarm: Cabinet internal temp sensor failure.

        OK: Cabinet internal temp sensor ok.

"
    ::= { auxCabinetEntry 16 }

-- ----------------------------------------------------
-- Aux Fan group
-- ----------------------------------------------------

auxFanTable  OBJECT-TYPE
    SYNTAX      SEQUENCE OF AuxFanEntry
    MAX-ACCESS  not-accessible
    STATUS      current
    DESCRIPTION
        "A list of Fans."
    ::= { auxFanList 1 }

auxFanEntry OBJECT-TYPE
    SYNTAX      AuxFanEntry
    MAX-ACCESS  not-accessible
    STATUS      current
    DESCRIPTION
        "An entry in the Fan list.

"
    INDEX { auxFanIndex }
    ::= { auxFanTable 1 }

AuxFanEntry ::=
    SEQUENCE {
        auxFanIndex                 Unsigned32,
        auxFanName                  MgmtNameString,
        auxFanDescr                 DisplayString,
        auxFanAdminStatus           AdminStatusWithNA,
        auxFanOperStatus            INTEGER,
        auxFanUpId                  Unsigned32,
        auxFanFailure               FaultStatus,
        auxFanRPM					Signed32WithNA}

auxFanIndex OBJECT-TYPE
    SYNTAX      Unsigned32 (1..2147483647)
    MAX-ACCESS  read-only
    STATUS      current
    DESCRIPTION
        "An arbitrary index assigned to each
        configuration equipment.

"
    ::= { auxFanEntry 1 }

auxFanName OBJECT-TYPE
    SYNTAX      MgmtNameString
    MAX-ACCESS  read-only
    STATUS      current
    DESCRIPTION
        "The name of the fan.

"
    ::= { auxFanEntry 2 }

auxFanDescr OBJECT-TYPE
    SYNTAX      DisplayString
    MAX-ACCESS  read-write
    STATUS      current
    DESCRIPTION
        "User configurable label.

"
    DEFVAL { "" }
    ::= { auxFanEntry 3 }

auxFanAdminStatus OBJECT-TYPE
    SYNTAX     AdminStatusWithNA
    MAX-ACCESS read-write
    STATUS     current
    DESCRIPTION
        "The administrative state of the fan.

        down - The interface is de-activated.

        service - The interface is activated but alarms
        are suppressed. Intended for use during service
        or re-configuration. When service is concluded
        adminStatus should be set to 'up' again. Note that
        there is no difference between 'up' and 'service',
        if no alarms can be raised from this object.

        up - The interface will be activated when
        available. Alarms are not suppressed.

"
    DEFVAL { up }
    ::= { auxFanEntry 4 }

auxFanOperStatus OBJECT-TYPE
    SYNTAX      INTEGER {
                    notPresent (1),
                    down (2),
                    up (3) }
    MAX-ACCESS  read-only
    STATUS      current
    DESCRIPTION
        "Fan operational status

"
    ::= { auxFanEntry 5 }

auxFanUpId OBJECT-TYPE
    SYNTAX      Unsigned32   (0..2147483647)
    MAX-ACCESS  read-only
    STATUS      current
    DESCRIPTION
        "Identity in the UP for the auxFan entry in the traffic unit
"
    DEFVAL { 0  }
    ::= { auxFanEntry 6 }

auxFanFailure OBJECT-TYPE
    SYNTAX      FaultStatus
    MAX-ACCESS  read-only
    STATUS      current
    DESCRIPTION
        "
        Alarm: The fan has failed.

        OK: The fan is ok.

"
    ::= { auxFanEntry 7 }

auxFanRPM OBJECT-TYPE
    SYNTAX      Signed32WithNA
    MAX-ACCESS  read-only
    STATUS      current
    DESCRIPTION
        "The fan RPM.

"
    ::= { auxFanEntry 8 }


-- ----------------------------------------------------
-- Aux Fan Group group
-- ----------------------------------------------------

auxFanGroupTable  OBJECT-TYPE
    SYNTAX      SEQUENCE OF AuxFanGroupEntry
    MAX-ACCESS  not-accessible
    STATUS      current
    DESCRIPTION
        "A list of FanGroups."
    ::= { auxFanGroupList 1 }

auxFanGroupEntry OBJECT-TYPE
    SYNTAX      AuxFanGroupEntry
    MAX-ACCESS  not-accessible
    STATUS      current
    DESCRIPTION
        "An entry in the FanGroup list.

"
    INDEX { auxFanGroupIndex }
    ::= { auxFanGroupTable 1 }

AuxFanGroupEntry ::=
    SEQUENCE {
        auxFanGroupIndex                 Unsigned32,
        auxFanGroupName                  MgmtNameString,
        auxFanGroupDescr                 DisplayString,
        auxFanGroupAdminStatus           AdminStatusWithNA,
        auxFanGroupOperStatus            INTEGER,
        auxFanGroupUpId                  Unsigned32,
        auxFanGroupFailure               FaultStatus}

auxFanGroupIndex OBJECT-TYPE
    SYNTAX      Unsigned32 (1..2147483647)
    MAX-ACCESS  read-only
    STATUS      current
    DESCRIPTION
        "An arbitrary index assigned to each
        configuration equipment.

"
    ::= { auxFanGroupEntry 1 }

auxFanGroupName OBJECT-TYPE
    SYNTAX      MgmtNameString
    MAX-ACCESS  read-only
    STATUS      current
    DESCRIPTION
        "The name of the fan group.

"
    ::= { auxFanGroupEntry 2 }

auxFanGroupDescr OBJECT-TYPE
    SYNTAX      DisplayString
    MAX-ACCESS  read-write
    STATUS      current
    DESCRIPTION
        "User configurable label.

"
    DEFVAL { "" }
    ::= { auxFanGroupEntry 3 }

auxFanGroupAdminStatus OBJECT-TYPE
    SYNTAX     AdminStatusWithNA
    MAX-ACCESS read-write
    STATUS     current
    DESCRIPTION
        "The administrative state of the fan group.

        down - The interface is de-activated.

        service - The interface is activated but alarms
        are suppressed. Intended for use during service
        or re-configuration. When service is concluded
        adminStatus should be set to 'up' again. Note that
        there is no difference between 'up' and 'service',
        if no alarms can be raised from this object.

        up - The interface will be activated when
        available. Alarms are not suppressed.

"
    DEFVAL { up }
    ::= { auxFanGroupEntry 4 }

auxFanGroupOperStatus OBJECT-TYPE
    SYNTAX      INTEGER {
                    notPresent (1),
                    down (2),
                    up (3) }
    MAX-ACCESS  read-only
    STATUS      current
    DESCRIPTION
        "FanGroup operational status

"
    ::= { auxFanGroupEntry 5 }

auxFanGroupUpId OBJECT-TYPE
    SYNTAX      Unsigned32   (0..2147483647)
    MAX-ACCESS  read-only
    STATUS      current
    DESCRIPTION
        "Identity in the UP for the auxFanGroup entry in the traffic unit
"
    DEFVAL { 0  }
    ::= { auxFanGroupEntry 6 }

auxFanGroupFailure OBJECT-TYPE
    SYNTAX      FaultStatus
    MAX-ACCESS  read-only
    STATUS      current
    DESCRIPTION
        "
        Alarm: The fan group has failed.

        OK: The fan group is ok.

"
    ::= { auxFanGroupEntry 7 }

-- ----------------------------------------------------
-- Notifications
-- ----------------------------------------------------

-- n/a


-- ----------------------------------------------------
-- Object and event groups
-- ----------------------------------------------------

auxGeneralGroup OBJECT-GROUP
    OBJECTS {
        auxGeneralTestAndIncr,
        auxGeneralStateLastChangeTime,
        auxGeneralConfigLastChangeTime,
        auxGeneralSnmpTableSize,
        auxGeneralFxIfTableSize,
        auxGeneralAuxEquipmentTableSize }
    STATUS      deprecated
    DESCRIPTION
        "The aux general objects."
    ::= { lumAuxGroups 1 }

auxSnmpGroup OBJECT-GROUP
    OBJECTS {
        auxSnmpIndex,
        auxSnmpName,
        auxSnmpDescr,
        auxSnmpAddress,
        auxSnmpPort,
        auxSnmpVersion,
        auxSnmpReadCommunity,
        auxSnmpWriteCommunity,
        auxSnmpAdminStatus,
        auxSnmpOperStatus,
        auxSnmpInvPhysIndexOrZero,
        auxSnmpHostUnreachable,
        auxSnmpSnmpError,
        auxSnmpUnexpectedEquipmentType,
        auxSnmpInconsistentConfiguration }
    STATUS      deprecated
    DESCRIPTION
        "The aux equipment objects."
    ::= { lumAuxGroups 2 }

auxFxIfGroup OBJECT-GROUP
    OBJECTS {
        auxFxIfIndex,
        auxFxIfName,
        auxFxIfDescr,
        auxFxIfSubrack,
        auxFxIfSlot,
        auxFxIfRxPort,
        auxFxIfTxPort,
        auxFxIfInvPhysIndexOrZero,
        auxFxIfAdminStatus,
        auxFxIfOperStatus,
        auxFxIfRxPowerLevel,
        auxFxIfLossOfSignalThreshold,
        auxFxIfLossOfSignal }
    STATUS      deprecated
    DESCRIPTION
        "The aux OAS module objects."
    ::= { lumAuxGroups 3 }

auxEquipmentGroup OBJECT-GROUP
    OBJECTS {
        auxEquipmentIndex,
        auxEquipmentName,
        auxEquipmentDescr,
        auxEquipmentSubrack,
        auxEquipmentSlot,
        -- auxEquipmentInvPhysIndexOrZero,
        auxEquipmentAdminStatus,
        auxEquipmentOperStatus,
        auxEquipmentPowerFailure,
        auxEquipmentFanProblem }
    STATUS      deprecated
    DESCRIPTION
        "The aux OAS module objects."
    ::= { lumAuxGroups 4 }

auxFxIfGroupV2 OBJECT-GROUP
    OBJECTS {
        auxFxIfIndex,
        auxFxIfName,
        auxFxIfDescr,
        auxFxIfSubrack,
        auxFxIfSlot,
        auxFxIfRxPort,
        auxFxIfTxPort,
        auxFxIfInvPhysIndexOrZero,
        auxFxIfAdminStatus,
        auxFxIfOperStatus,
        auxFxIfRxPowerLevel,
        auxFxIfLossOfSignalThreshold,
        auxFxIfLossOfSignal,
        auxFxIfObjectProperty }
    STATUS      current
    DESCRIPTION
        "The aux OAS module objects (4.0)."
    ::= { lumAuxGroups 5 }

auxEquipmentGroupV2 OBJECT-GROUP
    OBJECTS {
        auxEquipmentIndex,
        auxEquipmentName,
        auxEquipmentDescr,
        auxEquipmentSubrack,
        auxEquipmentSlot,
        -- auxEquipmentInvPhysIndexOrZero,
        auxEquipmentAdminStatus,
        auxEquipmentOperStatus,
        auxEquipmentPowerFailure,
        auxEquipmentFanProblem,
        auxEquipmentObjectProperty }
    STATUS      deprecated
    DESCRIPTION
        "The aux OAS module objects (4.0)."
    ::= { lumAuxGroups 6 }

auxRamanIfGroupV1 OBJECT-GROUP
    OBJECTS {
        auxRamanIfIndex,
        auxRamanIfName,
        auxRamanIfDescr,
        auxRamanIfSubrack,
        auxRamanIfSlot,
        auxRamanIfRxPort,
        auxRamanIfTxPort,
        auxRamanIfInvPhysIndexOrZero,
        auxRamanIfAdminStatus,
        auxRamanIfOperStatus,
        auxRamanIfObjectProperty,
        auxRamanIfPumpsOperationMode,
        auxRamanIfModuleOperationMode,
        auxRamanIfPumpsOperationModeConfig,
        auxRamanIfLineFiberType,
        auxRamanIfAutoRestartProcTime,
        auxRamanIfArpPauseStatus,
        auxRamanIfPumpsStatus,
        auxRamanIfTotalPumpsPower,
        auxRamanIfPump1WantedPower,
        auxRamanIfPump1ActualPower,
        auxRamanIfPump1Current,
        auxRamanIfPump1Temperature,
        auxRamanIfPump2WantedPower,
        auxRamanIfPump2ActualPower,
        auxRamanIfPump2Current,
        auxRamanIfPump2Temperature,
        auxRamanIfWantedGain,
        auxRamanIfActualGain,
        auxRamanIfReceivedPowerLevel,
        auxRamanIfReflectionPowerLevel,
        auxRamanIfReflectionPowerRatio,
        auxRamanIf1510BandReceivedPowerLevel,
        auxRamanIfOscReceivedPowerLevel,
        auxRamanIfManualRestartTrial,
        auxRamanIfModuleTemp }
    STATUS      deprecated
    DESCRIPTION
        "The aux RAMAN module objects (6.1)."
    ::= { lumAuxGroups 7 }

auxRamanSafetyGroupV1 OBJECT-GROUP
    OBJECTS {
        auxRamanSafetyIndex,
        auxRamanSafetyName,
        auxRamanSafetyDescr,
        auxRamanSafetySubrack,
        auxRamanSafetySlot,
        auxRamanSafetyRxPort,
        auxRamanSafetyTxPort,
        auxRamanSafetyInvPhysIndexOrZero,
        --auxRamanSafetyAdminStatus,
        --auxRamanSafetyOperStatus,
        auxRamanSafetyObjectProperty,
        auxRamanSafetyShutDownAtInputLoss,
        auxRamanSafetyShutDownAtHighTemp,
        auxRamanSafetyShutDownAtHighBackReflection,
        auxRamanSafetyHighBackReflectionThreshold,
        auxRamanSafetyShutDownAtOscLoss,
        auxRamanSafetyShutDownAt1510BandDrop,
        auxRamanSafetyShutDownAtInputLossConfig,
        auxRamanSafetyShutDownAtHighTempConfig,
        auxRamanSafetyShutDownAtHighBackReflectionConfig,
        auxRamanSafetyShutDownAtOscLossConfig,
        auxRamanSafetyShutDownAt1510BandDropConfig,
        auxRamanSafetyPasswd,
        auxRamanSafetyPasswdConfig,
        auxRamanSafety1510BandDropThreshold,
        auxRamanSafetyInhibitStartAtOscLoss,
        auxRamanSafetyInhibitStartAtOscLossConfig }

    STATUS     deprecated
    DESCRIPTION
        "The aux RAMAN module objects (6.1)."
    ::= { lumAuxGroups 8 }

auxEquipmentGroupV3 OBJECT-GROUP
    OBJECTS {
        auxEquipmentIndex,
        auxEquipmentName,
        auxEquipmentDescr,
        auxEquipmentSubrack,
        auxEquipmentSlot,
        -- auxEquipmentInvPhysIndexOrZero,
        auxEquipmentAdminStatus,
        auxEquipmentOperStatus,
        auxEquipmentPowerFailure,
        auxEquipmentFanProblem,
        auxEquipmentObjectProperty,
        auxEquipmentPumpsEol,
        auxEquipmentSelfTestFailure,
        auxEquipmentAmbientTemp,
        auxEquipmentRebootEquipment }
    STATUS      deprecated
    DESCRIPTION
        "The aux equipment module objects (6.1)."
    ::= { lumAuxGroups 9 }

auxSnmpGroupV2 OBJECT-GROUP
    OBJECTS {
        auxSnmpIndex,
        auxSnmpName,
        auxSnmpDescr,
        auxSnmpAddress,
        auxSnmpPort,
        auxSnmpVersion,
        auxSnmpReadCommunity,
        auxSnmpWriteCommunity,
        auxSnmpAdminStatus,
        auxSnmpOperStatus,
        auxSnmpInvPhysIndexOrZero,
        auxSnmpHostUnreachable,
        auxSnmpSnmpError,
        auxSnmpUnexpectedEquipmentType,
        auxSnmpInconsistentConfiguration,
        auxSnmpConfigurationProblem }
    STATUS      current
    DESCRIPTION
        "The aux snmp objects V2 (6.1)."
    ::= { lumAuxGroups 10 }

auxRamanSafetyGroupV2 OBJECT-GROUP
    OBJECTS {
        auxRamanSafetyIndex,
        auxRamanSafetyName,
        auxRamanSafetyDescr,
        auxRamanSafetySubrack,
        auxRamanSafetySlot,
        auxRamanSafetyRxPort,
        auxRamanSafetyTxPort,
        auxRamanSafetyInvPhysIndexOrZero,
        auxRamanSafetyObjectProperty,
        auxRamanSafetyShutDownAtInputLoss,
        auxRamanSafetyShutDownAtHighTemp,
        auxRamanSafetyShutDownAtHighBackReflection,
        auxRamanSafetyHighBackReflectionThreshold,
        auxRamanSafetyShutDownAtOscLoss,
        auxRamanSafetyShutDownAt1510BandDrop,
        auxRamanSafetyShutDownAtInputLossConfig,
        auxRamanSafetyShutDownAtHighTempConfig,
        auxRamanSafetyShutDownAtHighBackReflectionConfig,
        auxRamanSafetyShutDownAtOscLossConfig,
        auxRamanSafetyShutDownAt1510BandDropConfig,
        auxRamanSafetyPasswd,
        auxRamanSafetyPasswdConfig,
        auxRamanSafety1510BandDropThreshold,
        auxRamanSafetyInhibitStartAtOscLoss,
        auxRamanSafetyInhibitStartAtOscLossConfig,
        auxRamanSafetyShutDownAtLowBandDrop,
        auxRamanSafetyLowBandScatteringThreshold,
        auxRamanSafetyShutDownAtLowBandDropConfig,
        auxRamanSafetyAmplifierSwitch,
        auxRamanSafetyAmplifierSwitchConfig,
        auxRamanSafetyLowBandScatteringTolerance}

    STATUS      current
    DESCRIPTION
        "The aux safety module objects (6.1)."
    ::= { lumAuxGroups 11 }

auxPEIfGroupV1  OBJECT-GROUP
    OBJECTS{
        auxPEIfIndex,
        auxPEIfName,
        auxPEIfDescr,
        auxPEIfSubrack,
        auxPEIfSlot,
        auxPEIfRxPort,
        auxPEIfTxPort,
        auxPEIfInvPhysIndexOrZero,
        auxPEIfAdminStatus,
        auxPEIfOperStatus,
        auxPEIfObjectProperty,
        auxPEIfPumpsOperationMode,
        auxPEIfPumpsOperationModeConfig,
        auxPEIfAutoRestartProcTime,
        auxPEIfPumpsStatus,
        auxPEIfWantedPower,
        auxPEIfWantedGain,
        auxPEIfPumpsTotalCurrent,
        auxPEIfPump1Temperature,
        auxPEIfActualGain,
        auxPEIfReceivedPowerLevel,
        auxPEIfReflectionPowerLevel,
        auxPEIfReflectionPowerRatio,
        auxPEIfLowBandScatteredPowerLevel,
        auxPEIfLineLossOfSignal,
        auxPEIfHighBackReflection,
        auxPEIfAutoPowerReduction,
        auxPEIfLowLineOutputPower,
        auxPEIfModuleTempTooHigh,
        auxPEIfModuleTempHigh,
        auxPEIfPumpsTempTooHigh,
        auxPEIfPumpsTempHigh,
        auxPEIfModuleTemp,
        auxPEIfPump2Temperature}

    STATUS  current
    DESCRIPTION
        "the aux PE If module objects (6.1)."
    ::={ lumAuxGroups 12 }

auxEquipmentGroupV4 OBJECT-GROUP
    OBJECTS {
        auxEquipmentIndex,
        auxEquipmentName,
        auxEquipmentDescr,
        auxEquipmentSubrack,
        auxEquipmentSlot,
        -- auxEquipmentInvPhysIndexOrZero,
        auxEquipmentAdminStatus,
        auxEquipmentOperStatus,
        auxEquipmentPowerFailure,
        auxEquipmentFanProblem,
        auxEquipmentObjectProperty,
        auxEquipmentPumpsEol,
        auxEquipmentSelfTestFailure,
        auxEquipmentAmbientTemp,
        auxEquipmentRebootEquipment,
        auxEquipmentPowerAMissing,
        auxEquipmentPowerBMissing}

    STATUS      deprecated
    DESCRIPTION
        "The aux equipment module objects (6.1)."
    ::= { lumAuxGroups 13 }

auxEquipmentGroupV5 OBJECT-GROUP
    OBJECTS {
        auxEquipmentIndex,
        auxEquipmentName,
        auxEquipmentDescr,
        auxEquipmentSubrack,
        auxEquipmentSlot,
        -- auxEquipmentInvPhysIndexOrZero,
        auxEquipmentAdminStatus,
        auxEquipmentOperStatus,
        auxEquipmentPowerFailure,
        auxEquipmentFanProblem,
        auxEquipmentObjectProperty,
    auxEquipmentPumpsEol,
    auxEquipmentSelfTestFailure,
    auxEquipmentAmbientTemp,
    auxEquipmentRebootEquipment,
    auxEquipmentPowerAMissing,
    auxEquipmentPowerBMissing,
    auxEquipmentConfigurationMismatch}

    STATUS      current
    DESCRIPTION
        "The aux equipment module objects (6.1)."
    ::= { lumAuxGroups 14 }

auxNodeGroupV1  OBJECT-GROUP
    OBJECTS{
        auxNodeIndex,
        auxNodeName,
        auxNodeDescr,
        auxNodeIpAddress,
        auxNodePort,
        auxNodeEventPort,
        auxNodeTime,
        auxNodeNtpPrimary,
        auxNodeNtpSecondary,
        auxNodeChangeLocalTime,
        auxNodeHostUnreachable }

    STATUS  current
    DESCRIPTION
        "The aux node module objects, e.g. used for TM2000 (6.1)."
    ::={ lumAuxGroups 15 }

    auxRamanIfGroupV2 OBJECT-GROUP
    OBJECTS {
        auxRamanIfIndex,
        auxRamanIfName,
        auxRamanIfDescr,
        auxRamanIfSubrack,
        auxRamanIfSlot,
        auxRamanIfRxPort,
        auxRamanIfTxPort,
        auxRamanIfInvPhysIndexOrZero,
        auxRamanIfAdminStatus,
        auxRamanIfOperStatus,
        auxRamanIfObjectProperty,
        auxRamanIfPumpsOperationMode,
        auxRamanIfModuleOperationMode,
        auxRamanIfPumpsOperationModeConfig,
        auxRamanIfLineFiberType,
        auxRamanIfAutoRestartProcTime,
        auxRamanIfArpPauseStatus,
        auxRamanIfPumpsStatus,
        auxRamanIfTotalPumpsPower,
        auxRamanIfPump1WantedPower,
        auxRamanIfPump1ActualPower,
        auxRamanIfPump1Current,
        auxRamanIfPump1Temperature,
        auxRamanIfPump2WantedPower,
        auxRamanIfPump2ActualPower,
        auxRamanIfPump2Current,
        auxRamanIfPump2Temperature,
        auxRamanIfWantedGain,
        auxRamanIfActualGain,
        auxRamanIfReceivedPowerLevel,
        auxRamanIfReflectionPowerLevel,
        auxRamanIfReflectionPowerRatio,
        auxRamanIf1510BandReceivedPowerLevel,
        auxRamanIfOscReceivedPowerLevel,
        auxRamanIfManualRestartTrial,
        auxRamanIfModuleTemp,
        auxRamanIfTxSignalStatus,
        auxRamanIfRxSignalStatus
         }
    STATUS      current
    DESCRIPTION
        "The aux RAMAN module objects (6.1)."
    ::= { lumAuxGroups 16 }

auxGeneralGroupV2 OBJECT-GROUP
    OBJECTS {
        auxGeneralTestAndIncr,
        auxGeneralStateLastChangeTime,
        auxGeneralConfigLastChangeTime,
        auxGeneralSnmpTableSize,
        auxGeneralFxIfTableSize,
        auxGeneralAuxEquipmentTableSize,
        auxGeneralRamanIfTableSize,
        auxGeneralRamanSafetyTableSize,
        auxGeneralPEIfTableSize,
        auxGeneralNodeTableSize,
        auxGeneralCabinetTableSize,
        auxGeneralFanTableSize,
        auxGeneralFanGroupTableSize }
    STATUS      current
    DESCRIPTION
        "The aux general objects."
    ::= { lumAuxGroups 17 }

auxCabinetGroupV1  OBJECT-GROUP
    OBJECTS{
        auxCabinetIndex,
        auxCabinetName,
        auxCabinetDescr,
        auxCabinetAdminStatus,
        auxCabinetOperStatus,
        auxCabinetUpId,
        auxCabinetIndoorTemp,
        auxCabinetOutdoorTemp,
        auxCabinetOperMode,
        auxCabinetDoorAlarm,
        auxCabinetSPDAlarm,
        auxCabinetHighTempAlarm,
        auxCabinetCtrlFailAlarm,
        auxCabinetHeatFailAlarm,
        auxCabinetExtTempFailAlarm,
        auxCabinetIntTempFailAlarm}

    STATUS  current
    DESCRIPTION
        "The aux Cabinet module objects (28.1)."
    ::={ lumAuxGroups 18 }

auxFanGroupV1  OBJECT-GROUP
    OBJECTS{
        auxFanIndex,
        auxFanName,
        auxFanDescr,
        auxFanAdminStatus,
        auxFanOperStatus,
        auxFanUpId,
        auxFanFailure,
        auxFanRPM}

    STATUS  current
    DESCRIPTION
        "The aux Fan module objects (27.1)."
    ::={ lumAuxGroups 19 }

auxFanGroupGroupV1  OBJECT-GROUP
    OBJECTS{
        auxFanGroupIndex,
        auxFanGroupName,
        auxFanGroupDescr,
        auxFanGroupAdminStatus,
        auxFanGroupOperStatus,
        auxFanGroupUpId,
        auxFanGroupFailure}

    STATUS  current
    DESCRIPTION
        "The aux FanGroup module objects (27.1)."
    ::={ lumAuxGroups 20 }


-- ----------------------------------------------------
-- Compliance
-- ----------------------------------------------------

lumAuxBasicComplV1 MODULE-COMPLIANCE
    STATUS      deprecated
    DESCRIPTION
        "Basic implementation requirements for the aux MIB v1. (3.1)"
    MODULE
        MANDATORY-GROUPS {
            auxGeneralGroup,
            auxSnmpGroup,
            auxFxIfGroup,
            auxEquipmentGroup }
    ::= { lumAuxCompl 1 }

lumAuxBasicComplV2 MODULE-COMPLIANCE
    STATUS      deprecated
    DESCRIPTION
        "Basic implementation requirements for the aux MIB v2. (4.0)"
    MODULE
        MANDATORY-GROUPS {
            auxGeneralGroup,
            auxSnmpGroup,
            auxFxIfGroupV2,
            auxEquipmentGroupV2 }
    ::= { lumAuxCompl 2 }

lumAuxBasicComplV3 MODULE-COMPLIANCE
    STATUS     deprecated
    DESCRIPTION
        "Basic implementation requirements for the aux MIB v3. (6.1)"
    MODULE
        MANDATORY-GROUPS {
            auxGeneralGroup,
            auxSnmpGroupV2,
            auxFxIfGroupV2,
            auxEquipmentGroupV3,
            auxRamanIfGroupV1,
            auxRamanSafetyGroupV1 }
    ::= { lumAuxCompl 3 }

lumAuxBasicComplV4 MODULE-COMPLIANCE
    STATUS      deprecated
    DESCRIPTION
        "Basic implementation requirements for the aux MIB v4. (6.1)"
    MODULE
        MANDATORY-GROUPS {
            auxGeneralGroup,
            auxSnmpGroupV2,
            auxFxIfGroupV2,
            auxEquipmentGroupV4,
            auxRamanIfGroupV1,
            auxRamanSafetyGroupV2,
            auxPEIfGroupV1}
    ::= { lumAuxCompl 4 }

lumAuxBasicComplV5 MODULE-COMPLIANCE
    STATUS      deprecated
    DESCRIPTION
        "Basic implementation requirements for the aux MIB v5. (6.1)"
    MODULE
        MANDATORY-GROUPS {
            auxGeneralGroup,
            auxSnmpGroupV2,
            auxFxIfGroupV2,
            auxEquipmentGroupV5,
            auxRamanIfGroupV1,
            auxRamanSafetyGroupV2,
            auxPEIfGroupV1,
            auxNodeGroupV1}
    ::= { lumAuxCompl 5 }

lumAuxBasicComplV6 MODULE-COMPLIANCE
    STATUS      deprecated
    DESCRIPTION
        "Basic implementation requirements for the aux MIB v5. (6.1)"
    MODULE
        MANDATORY-GROUPS {
            auxGeneralGroup,
            auxSnmpGroupV2,
            auxFxIfGroupV2,
            auxEquipmentGroupV5,
            auxRamanIfGroupV2,
            auxRamanSafetyGroupV2,
            auxPEIfGroupV1,
            auxNodeGroupV1}
    ::= { lumAuxCompl 6 }

lumAuxBasicComplV7 MODULE-COMPLIANCE
    STATUS      deprecated
    DESCRIPTION
        "Basic implementation requirements for the aux MIB v7. (27.1)"
    MODULE
        MANDATORY-GROUPS {
            auxGeneralGroupV2,
            auxSnmpGroupV2,
            auxFxIfGroupV2,
            auxEquipmentGroupV5,
            auxRamanIfGroupV2,
            auxRamanSafetyGroupV2,
            auxPEIfGroupV1,
            auxNodeGroupV1,
            auxCabinetGroupV1,
            auxFanGroupV1,
            auxFanGroupGroupV1}
    ::= { lumAuxCompl 7 }

lumAuxBasicComplV8 MODULE-COMPLIANCE
    STATUS      current
    DESCRIPTION
        "Basic implementation requirements for the aux MIB v8. (30.1)"
    MODULE
        MANDATORY-GROUPS {
            auxGeneralGroupV2,
            auxSnmpGroupV2,
            auxFxIfGroupV2,
            auxEquipmentGroupV5,
            auxRamanIfGroupV2,
            auxRamanSafetyGroupV2,
            auxPEIfGroupV1,
            auxNodeGroupV1,
            auxCabinetGroupV1,
            auxFanGroupV1,
            auxFanGroupGroupV1}
    ::= { lumAuxCompl 8 }

END
