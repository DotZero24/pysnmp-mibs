-- *****************************************************************
-- INFINERA-PM-BASESCGPTP-MIB
--
-- October 2013, Rishab Joshi
--
--
-- Copyright (c) 2008-2013 by Infinera Inc.
-- All rights reserved.
-- ****************************************************************

INFINERA-PM-BASESCGPTP-MIB DEFINITIONS ::= BEGIN

IMPORTS
    MODULE-IDENTITY, OBJECT-TYPE,
    Integer32                                   FROM SNMPv2-SMI
    MODULE-COMPLIANCE, OBJECT-GROUP             FROM SNMPv2-CONF
    TruthValue                                  FROM SNMPv2-TC
    ifIndex                                     FROM IF-MIB
    FloatHundredths                             FROM INFINERA-TC-MIB
    perfMon                                     FROM INFINERA-REG-MIB;


baseScgPtpPmMIB MODULE-IDENTITY
    LAST-UPDATED  "201310080000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION      "201310080000Z"
    DESCRIPTION
        "First Version"
    ::= { perfMon 45 }


baseScgPtpPmTable OBJECT-TYPE
    SYNTAX      SEQUENCE OF BaseScgPtpPmEntry
    MAX-ACCESS  not-accessible
    STATUS      current
    DESCRIPTION
        "A list of BaseScgPtpPm entries. Each entry is uniquely identified by the value of ifIndex."
    ::= { baseScgPtpPmMIB 2 }

baseScgPtpPmEntry  OBJECT-TYPE
    SYNTAX      BaseScgPtpPmEntry
    MAX-ACCESS  not-accessible
    STATUS      current
    DESCRIPTION
        "A BaseScgPtp entry containing historical performance information pertaining to Infinera BASESCGPTP.
        This table is a subclass of IfCommon. Entries will exist in this table only for interfaces
        of type BASESCGPTP."
    INDEX { ifIndex}
    ::= { baseScgPtpPmTable 1 }


BaseScgPtpPmEntry  ::= SEQUENCE {
   baseScgPtpPmValidity         TruthValue,
   baseScgPtpPmCmnScgOptMin     FloatHundredths,
   baseScgPtpPmCmnScgOptMax     FloatHundredths,
   baseScgPtpPmCmnScgOptAve     FloatHundredths,
   baseScgPtpPmCmnScgOprMin     FloatHundredths,
   baseScgPtpPmCmnScgOprMax     FloatHundredths,
   baseScgPtpPmCmnScgOprAve     FloatHundredths
}

baseScgPtpPmValidity OBJECT-TYPE
    SYNTAX      TruthValue
    MAX-ACCESS  read-only
    STATUS      current
    DESCRIPTION "Flag indicating if data was valid for the entire interval"
    ::= { baseScgPtpPmEntry  3 }


baseScgPtpPmCmnScgOptMin OBJECT-TYPE
    SYNTAX      FloatHundredths
    MAX-ACCESS  read-only
    STATUS      current
    DESCRIPTION "Minimum FsmScg optical power min."
    ::= { baseScgPtpPmEntry  4 }


baseScgPtpPmCmnScgOptMax OBJECT-TYPE
    SYNTAX      FloatHundredths
    MAX-ACCESS  read-only
    STATUS      current
    DESCRIPTION "Maximum FsmScg optical power max."
    ::= { baseScgPtpPmEntry  5 }


baseScgPtpPmCmnScgOptAve OBJECT-TYPE
    SYNTAX      FloatHundredths
    MAX-ACCESS  read-only
    STATUS      current
    DESCRIPTION "Average FsmScg optical power ave."
    ::= { baseScgPtpPmEntry  6 }


baseScgPtpPmCmnScgOprMin OBJECT-TYPE
    SYNTAX      FloatHundredths
    MAX-ACCESS  read-only
    STATUS      current
    DESCRIPTION "Minimum FsmScg optical power min."
    ::= { baseScgPtpPmEntry  7}


baseScgPtpPmCmnScgOprMax OBJECT-TYPE
    SYNTAX      FloatHundredths
    MAX-ACCESS  read-only
    STATUS      current
    DESCRIPTION "Maximum FsmScg optical power max."
    ::= { baseScgPtpPmEntry  8}


baseScgPtpPmCmnScgOprAve OBJECT-TYPE
    SYNTAX      FloatHundredths
    MAX-ACCESS  read-only
    STATUS      current
    DESCRIPTION "Average FsmScg optical power ave."
    ::= { baseScgPtpPmEntry  9}




baseScgPtpPmRealTable OBJECT-TYPE
    SYNTAX      SEQUENCE OF BaseScgPtpPmRealEntry
    MAX-ACCESS  not-accessible
    STATUS      current
    DESCRIPTION
        "A list of FsmScgPtpPmReal entries. Each entry is uniquely identified by the value of ifIndex."
    ::= { baseScgPtpPmMIB 1 }

baseScgPtpPmRealEntry  OBJECT-TYPE
    SYNTAX      BaseScgPtpPmRealEntry
    MAX-ACCESS  not-accessible
    STATUS      current
    DESCRIPTION
        "A  baseScgPtp entry containing real-time performance information pertaining to Infinera
         baseScgPtp interfaces. This table is a subclass of IfCommon."
    INDEX { ifIndex }
    ::= { baseScgPtpPmRealTable 1 }


BaseScgPtpPmRealEntry  ::= SEQUENCE {
    baseScgPtpPmRealCmnScgOpt       FloatHundredths,
    baseScgPtpPmRealCmnScgOpr       FloatHundredths
}

baseScgPtpPmRealCmnScgOpt OBJECT-TYPE
    SYNTAX      FloatHundredths
    MAX-ACCESS  read-only
    STATUS      current
    DESCRIPTION "Total FsmScg optical power trasmit."
    ::= { baseScgPtpPmRealEntry  1 }


baseScgPtpPmRealCmnScgOpr OBJECT-TYPE
    SYNTAX      FloatHundredths
    MAX-ACCESS  read-only
    STATUS      current
    DESCRIPTION "Total FsmScg optical power receive."
    ::= { baseScgPtpPmRealEntry  2 }



-- Conformance Statements
baseScgPtpPmConformance    OBJECT IDENTIFIER ::= { baseScgPtpPmMIB 3 }
baseScgPtpPmCompliances    OBJECT IDENTIFIER ::= { baseScgPtpPmConformance 1 }
baseScgPtpPmGroups         OBJECT IDENTIFIER ::= { baseScgPtpPmConformance 2 }

baseScgPtpPmCompliance MODULE-COMPLIANCE
    STATUS current
    DESCRIPTION
    "Describes the requirements for conformance to the  baseScgPtp-MIB"
    MODULE
        MANDATORY-GROUPS { baseScgPtpPmGroup }
    ::= { baseScgPtpPmCompliances 1 }

baseScgPtpPmRealCompliance MODULE-COMPLIANCE
    STATUS current
    DESCRIPTION
    "Describes the requirements for conformance to the FsmScgPtpPmReal-MIB"
    MODULE
        MANDATORY-GROUPS { baseScgPtpPmRealGroup }
    ::= { baseScgPtpPmCompliances 2 }

baseScgPtpPmGroup OBJECT-GROUP
    OBJECTS {
        baseScgPtpPmValidity,
        baseScgPtpPmCmnScgOptMin,
        baseScgPtpPmCmnScgOptMax,
        baseScgPtpPmCmnScgOptAve,
        baseScgPtpPmCmnScgOprMin,
        baseScgPtpPmCmnScgOprMax,
        baseScgPtpPmCmnScgOprAve
    }
    STATUS current
    DESCRIPTION
        " A collection of objects for reading the historical performance of the  baseScgPtp."
    ::= { baseScgPtpPmGroups 1 }

baseScgPtpPmRealGroup OBJECT-GROUP
    OBJECTS {
        baseScgPtpPmRealCmnScgOpt,
        baseScgPtpPmRealCmnScgOpr
    }
    STATUS current
    DESCRIPTION
        " A collection of objects for reading the real-time performance of the  baseScgPtp."
    ::= { baseScgPtpPmGroups 2 }

END
