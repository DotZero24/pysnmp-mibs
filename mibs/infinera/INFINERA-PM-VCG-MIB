-- *****************************************************************
-- INFINERA-PM-VCG-MIB
--
-- October 2008, Sharfuddin Syed / Narendra Gupta
--
--
-- Copyright (c) 2008-2012 by Infinera Inc.
-- All rights reserved.
-- ****************************************************************

INFINERA-PM-VCG-MIB DEFINITIONS ::= BEGIN

IMPORTS
    MODULE-IDENTITY, OBJECT-TYPE                FROM SNMPv2-SMI
    MODULE-COMPLIANCE, OBJECT-GROUP             FROM SNMPv2-CONF
    ifIndex                                     FROM IF-MIB
    FloatHundredths                                 FROM INFINERA-TC-MIB
    perfMon                                         FROM INFINERA-REG-MIB;


vCGPmMIB MODULE-IDENTITY
    LAST-UPDATED  "200810200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION      "200810200000Z"
    DESCRIPTION
        "First Version"
    ::= { perfMon 16 }



vCGPmRealTable OBJECT-TYPE
    SYNTAX      SEQUENCE OF VCGPmRealEntry
    MAX-ACCESS  not-accessible
    STATUS      current
    DESCRIPTION
        "A list of VCGPmReal entries. Each entry is uniquely identified by the value of ifIndex."
    ::= { vCGPmMIB 1 }

vCGPmRealEntry  OBJECT-TYPE
    SYNTAX      VCGPmRealEntry
    MAX-ACCESS  not-accessible
    STATUS      current
    DESCRIPTION
        "A VCGPmReal entry containing real-time performance information pertaining to
        Infinera VCG interfaces. . This table is a subclass of IfCommon.
        Entries will exist in this table only for interfaces of type VCG."
    INDEX { ifIndex }
    ::= { vCGPmRealTable 1 }


VCGPmRealEntry  ::= SEQUENCE {
    vCGPmRealDifferentialDelay1    FloatHundredths,
    vCGPmRealDifferentialDelay2    FloatHundredths,
    vCGPmRealDifferentialDelay3    FloatHundredths,
    vCGPmRealDifferentialDelay4    FloatHundredths,
    vCGPmRealDifferentialDelay5    FloatHundredths,
    vCGPmRealDifferentialDelay6    FloatHundredths,
    vCGPmRealDifferentialDelay7    FloatHundredths,
    vCGPmRealDifferentialDelay8    FloatHundredths,
    vCGPmRealDifferentialDelay9    FloatHundredths,
    vCGPmRealDifferentialDelay10    FloatHundredths,
    vCGPmRealDifferentialDelay11    FloatHundredths,
    vCGPmRealDifferentialDelay12    FloatHundredths,
    vCGPmRealDifferentialDelay13    FloatHundredths,
    vCGPmRealDifferentialDelay14    FloatHundredths,
    vCGPmRealDifferentialDelay15    FloatHundredths,
    vCGPmRealDifferentialDelay16    FloatHundredths,
    vCGPmRealDifferentialDelay17    FloatHundredths,
    vCGPmRealDifferentialDelay18    FloatHundredths,
    vCGPmRealDifferentialDelay19    FloatHundredths,
    vCGPmRealDifferentialDelay20    FloatHundredths
}


vCGPmRealDifferentialDelay1 OBJECT-TYPE
    SYNTAX      FloatHundredths
    MAX-ACCESS  read-only
    STATUS      current
    DESCRIPTION "The differential delay (skew) value of the first constituent member of the VCG in micro seconds."
    ::= { vCGPmRealEntry  1 }


vCGPmRealDifferentialDelay2 OBJECT-TYPE
    SYNTAX      FloatHundredths
    MAX-ACCESS  read-only
    STATUS      current
    DESCRIPTION "The differential delay (skew) value of the second constituent member of the VCG in micro seconds."
    ::= { vCGPmRealEntry  2 }


vCGPmRealDifferentialDelay3 OBJECT-TYPE
    SYNTAX      FloatHundredths
    MAX-ACCESS  read-only
    STATUS      current
    DESCRIPTION "The differential delay (skew) value of the third constituent member of the VCG in micro seconds."
    ::= { vCGPmRealEntry  3 }


vCGPmRealDifferentialDelay4 OBJECT-TYPE
    SYNTAX      FloatHundredths
    MAX-ACCESS  read-only
    STATUS      current
    DESCRIPTION "The differential delay (skew) value of the fourth constituent member of the VCG in micro seconds."
    ::= { vCGPmRealEntry  4 }

vCGPmRealDifferentialDelay5 OBJECT-TYPE
    SYNTAX      FloatHundredths
    MAX-ACCESS  read-only
    STATUS      current
    DESCRIPTION "The differential delay (skew) value of the fifth constituent member of the VCG in micro seconds."
    ::= { vCGPmRealEntry  5 }

vCGPmRealDifferentialDelay6 OBJECT-TYPE
    SYNTAX      FloatHundredths
    MAX-ACCESS  read-only
    STATUS      current
    DESCRIPTION "The differential delay (skew) value of the sixth constituent member of the VCG in micro seconds."
    ::= { vCGPmRealEntry  6 }

vCGPmRealDifferentialDelay7 OBJECT-TYPE
    SYNTAX      FloatHundredths
    MAX-ACCESS  read-only
    STATUS      current
    DESCRIPTION "The differential delay (skew) value of the seventh constituent member of the VCG in micro seconds."
    ::= { vCGPmRealEntry  7 }

vCGPmRealDifferentialDelay8 OBJECT-TYPE
    SYNTAX      FloatHundredths
    MAX-ACCESS  read-only
    STATUS      current
    DESCRIPTION "The differential delay (skew) value of the eighth constituent member of the VCG in micro seconds."
    ::= { vCGPmRealEntry  8 }

vCGPmRealDifferentialDelay9 OBJECT-TYPE
    SYNTAX      FloatHundredths
    MAX-ACCESS  read-only
    STATUS      current
    DESCRIPTION "The differential delay (skew) value of the nineth constituent member of the VCG in micro seconds."
    ::= { vCGPmRealEntry  9 }

vCGPmRealDifferentialDelay10 OBJECT-TYPE
    SYNTAX      FloatHundredths
    MAX-ACCESS  read-only
    STATUS      current
    DESCRIPTION "The differential delay (skew) value of the tenth constituent member of the VCG in micro seconds."
    ::= { vCGPmRealEntry  10 }


vCGPmRealDifferentialDelay11 OBJECT-TYPE
    SYNTAX      FloatHundredths
    MAX-ACCESS  read-only
    STATUS      current
    DESCRIPTION "The differential delay (skew) value of the tenth constituent member of the VCG in micro seconds."
    ::= { vCGPmRealEntry  11 }

vCGPmRealDifferentialDelay12 OBJECT-TYPE
    SYNTAX      FloatHundredths
    MAX-ACCESS  read-only
    STATUS      current
    DESCRIPTION "The differential delay (skew) value of the tenth constituent member of the VCG in micro seconds."
    ::= { vCGPmRealEntry  12 }

vCGPmRealDifferentialDelay13 OBJECT-TYPE
    SYNTAX      FloatHundredths
    MAX-ACCESS  read-only
    STATUS      current
    DESCRIPTION "The differential delay (skew) value of the tenth constituent member of the VCG in micro seconds."
    ::= { vCGPmRealEntry  13 }

vCGPmRealDifferentialDelay14 OBJECT-TYPE
    SYNTAX      FloatHundredths
    MAX-ACCESS  read-only
    STATUS      current
    DESCRIPTION "The differential delay (skew) value of the tenth constituent member of the VCG in micro seconds."
    ::= { vCGPmRealEntry  14 }

vCGPmRealDifferentialDelay15 OBJECT-TYPE
    SYNTAX      FloatHundredths
    MAX-ACCESS  read-only
    STATUS      current
    DESCRIPTION "The differential delay (skew) value of the tenth constituent member of the VCG in micro seconds."
    ::= { vCGPmRealEntry  15 }

vCGPmRealDifferentialDelay16 OBJECT-TYPE
    SYNTAX      FloatHundredths
    MAX-ACCESS  read-only
    STATUS      current
    DESCRIPTION "The differential delay (skew) value of the tenth constituent member of the VCG in micro seconds."
    ::= { vCGPmRealEntry  16 }

vCGPmRealDifferentialDelay17 OBJECT-TYPE
    SYNTAX      FloatHundredths
    MAX-ACCESS  read-only
    STATUS      current
    DESCRIPTION "The differential delay (skew) value of the tenth constituent member of the VCG in micro seconds."
    ::= { vCGPmRealEntry  17 }

vCGPmRealDifferentialDelay18 OBJECT-TYPE
    SYNTAX      FloatHundredths
    MAX-ACCESS  read-only
    STATUS      current
    DESCRIPTION "The differential delay (skew) value of the tenth constituent member of the VCG in micro seconds."
    ::= { vCGPmRealEntry  18 }

vCGPmRealDifferentialDelay19 OBJECT-TYPE
    SYNTAX      FloatHundredths
    MAX-ACCESS  read-only
    STATUS      current
    DESCRIPTION "The differential delay (skew) value of the tenth constituent member of the VCG in micro seconds."
    ::= { vCGPmRealEntry  19 }

vCGPmRealDifferentialDelay20 OBJECT-TYPE
    SYNTAX      FloatHundredths
    MAX-ACCESS  read-only
    STATUS      current
    DESCRIPTION "The differential delay (skew) value of the tenth constituent member of the VCG in micro seconds."
    ::= { vCGPmRealEntry  20 }

-- Conformance Statements
vCGPmConformance    OBJECT IDENTIFIER ::= { vCGPmMIB 3 }
vCGPmCompliances    OBJECT IDENTIFIER ::= { vCGPmConformance 1 }
vCGPmGroups         OBJECT IDENTIFIER ::= { vCGPmConformance 2 }

vCGPmRealCompliance MODULE-COMPLIANCE
    STATUS current
    DESCRIPTION
    "Describes the requirements for conformance to the PM-VCG-MIB"
    MODULE
        MANDATORY-GROUPS { vCGPmRealGroup }
    ::= { vCGPmCompliances 1 }

vCGPmRealGroup OBJECT-GROUP
    OBJECTS {
        vCGPmRealDifferentialDelay1,
        vCGPmRealDifferentialDelay2,
        vCGPmRealDifferentialDelay3,
        vCGPmRealDifferentialDelay4,
        vCGPmRealDifferentialDelay5,
        vCGPmRealDifferentialDelay6,
        vCGPmRealDifferentialDelay7,
        vCGPmRealDifferentialDelay8,
        vCGPmRealDifferentialDelay9,
        vCGPmRealDifferentialDelay10,
	vCGPmRealDifferentialDelay11,
        vCGPmRealDifferentialDelay12,
        vCGPmRealDifferentialDelay13,
        vCGPmRealDifferentialDelay14,
        vCGPmRealDifferentialDelay15,
        vCGPmRealDifferentialDelay16,
        vCGPmRealDifferentialDelay17,
        vCGPmRealDifferentialDelay18,
        vCGPmRealDifferentialDelay19,
        vCGPmRealDifferentialDelay20

    }
    STATUS current
    DESCRIPTION
        " A collection of objects for reading the performance of the VCG."
    ::= { vCGPmGroups 1 }


END
