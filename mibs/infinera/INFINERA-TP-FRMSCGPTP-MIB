-- *****************************************************************
-- INFINERA-TP-FRMSCGPTP-MIB
-- Copyright (c) 2008-2012 by Infinera Inc
-- All rights reserved.
-- ****************************************************************

INFINERA-TP-FRMSCGPTP-MIB DEFINITIONS ::= BEGIN

IMPORTS
    MODULE-IDENTITY, OBJECT-TYPE                FROM SNMPv2-SMI
    MODULE-COMPLIANCE, OBJECT-GROUP             FROM SNMPv2-CONF
    DisplayString, TruthValue                   FROM SNMPv2-TC
    ifIndex                                     FROM IF-MIB
    FloatHundredths, InfnEnableDisable,
    InfnEqptType,InfnAutoDiscoveryState,
    InfnWaveInterfaceType, InfnAdTpType,
	InfnPmHistStatsControl, InfnTrafficMode,
	InfnPathLossCheckControlStatus,
	InfnLastPathLossCheckAttemptStatus,
	InfnLastPathLossCheckFailedReason			FROM INFINERA-TC-MIB
    terminationPoint                            FROM INFINERA-REG-MIB;

frmScgPtpMIB MODULE-IDENTITY
    LAST-UPDATED  "201310200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "201310200000Z"
    DESCRIPTION
        "First Version"
    ::= { terminationPoint 45 }

frmScgPtpTable OBJECT-TYPE
    SYNTAX      SEQUENCE OF FrmScgPtpEntry
    MAX-ACCESS  not-accessible
    STATUS      current
    DESCRIPTION
        "A list of FrmScgPtp entries. Each entry is uniquely identified by the value of ifIndex."
    ::= { frmScgPtpMIB 1 }

frmScgPtpEntry  OBJECT-TYPE
    SYNTAX      FrmScgPtpEntry
    MAX-ACCESS  not-accessible
    STATUS      current
    DESCRIPTION
        "A FrmScgPtp entry containing information pertaining to Infinera FrmScgPtp Interfaces.
        This table is a subclass of IfCommon. Entries will exist in this table only for
        interfaces of type DLM OCG PTP."
    INDEX { ifIndex }
    ::= { frmScgPtpTable 1 }


FrmScgPtpEntry  ::= SEQUENCE {

    frmScgPtpScgNumber                      Integer32,
    frmScgPtpScgSupEqptType                 InfnEqptType,
    frmScgPtpMPOAID                         DisplayString,
    frmScgPtpProvisionedFPMPO               DisplayString,
    frmScgPtpAutoDiscoveryState             InfnAutoDiscoveryState,
    frmScgPtpDiscoveredNeighborTP           DisplayString,
    frmScgPtpInterfaceType                  InfnWaveInterfaceType,
    frmScgPtpProvisionedNeighborTP          DisplayString,
    frmScgPtpProvisionedNeighborAdTpType    InfnAdTpType,
    frmScgPtpPmHistStatsEnable              InfnPmHistStatsControl,
    frmScgPtpProvisionedOpenWaveRemotePtp   DisplayString,
    frmScgPtpTrafficMode                    InfnTrafficMode,
    frmScgPtpPathLossCheckControlStatus     InfnPathLossCheckControlStatus,
    frmScgPtpLastSuccessfullPathLossCheckTS Integer32,
    frmScgPtpPathLoss                       FloatHundredths,
    frmScgPtpPathLossCheckDetectPort        DisplayString,
    frmScgPtpLastPathLossCheckAttemptTS     Integer32,
    frmScgPtpLastPathLossCheckAttemptStatus InfnLastPathLossCheckAttemptStatus,
    frmScgPtpLastPathLossCheckFailedReason  InfnLastPathLossCheckFailedReason,
    frmScgPtpPowerContolLoop                InfnEnableDisable,
    frmScgPtpAutoDiscSoakTime               Integer32,
    frmScgPtpPathLossHigh                   TruthValue,
    frmScgPtpMuxedProvisionedNeighborTPList DisplayString,
	frmScgPtpPassiveProvisionedNeighborTP	DisplayString,
    frmScgPtpMuxedProvisionedNeighborMotList DisplayString,
	frmScgPtpTxProvNbrTP					DisplayString,
	frmScgPtpRxProvNbrTP					DisplayString,
	frmScgPtpTxProvEqptType					InfnEqptType,
	frmScgPtpRxProvEqptType					InfnEqptType
}

frmScgPtpScgNumber OBJECT-TYPE
    SYNTAX      Integer32
    MAX-ACCESS  read-only
    STATUS      current
    DESCRIPTION ""
    ::= { frmScgPtpEntry 1 }

frmScgPtpScgSupEqptType OBJECT-TYPE
    SYNTAX      InfnEqptType
    MAX-ACCESS  read-write
    STATUS      current
    DESCRIPTION ""
    ::= { frmScgPtpEntry 2 }

frmScgPtpMPOAID OBJECT-TYPE
    SYNTAX      DisplayString
    MAX-ACCESS  read-write
    STATUS      current
    DESCRIPTION ""
    ::= { frmScgPtpEntry 3 }

frmScgPtpProvisionedFPMPO  OBJECT-TYPE
    SYNTAX      DisplayString
    MAX-ACCESS  read-write
    STATUS      current
    DESCRIPTION ""
    ::= { frmScgPtpEntry 4 }


frmScgPtpAutoDiscoveryState OBJECT-TYPE
    SYNTAX     InfnAutoDiscoveryState
    MAX-ACCESS  read-only
    STATUS      current
    DESCRIPTION ""
    ::= { frmScgPtpEntry 5 }

frmScgPtpDiscoveredNeighborTP OBJECT-TYPE
    SYNTAX      DisplayString
    MAX-ACCESS  read-only
    STATUS      current
    DESCRIPTION ""
    ::= { frmScgPtpEntry 6 }

frmScgPtpProvisionedNeighborTP OBJECT-TYPE
    SYNTAX      DisplayString
    MAX-ACCESS  read-only
    STATUS      current
    DESCRIPTION ""
    ::= { frmScgPtpEntry 7 }

frmScgPtpProvisionedNeighborAdTpType OBJECT-TYPE
    SYNTAX   	InfnAdTpType
    MAX-ACCESS  read-only
    STATUS      current
    DESCRIPTION ""
    ::= { frmScgPtpEntry 8 }

frmScgPtpInterfaceType OBJECT-TYPE
    SYNTAX      InfnWaveInterfaceType
    MAX-ACCESS  read-write
    STATUS      current
    DESCRIPTION ""
    ::= { frmScgPtpEntry 9 }

frmScgPtpProvisionedOpenWaveRemotePtp OBJECT-TYPE
    SYNTAX          DisplayString
    MAX-ACCESS      read-write
    STATUS          current
    DESCRIPTION     ""
    ::= { frmScgPtpEntry 10 }

frmScgPtpPmHistStatsEnable OBJECT-TYPE
    SYNTAX     		InfnPmHistStatsControl
    MAX-ACCESS      read-only
    STATUS          current
    DESCRIPTION     ""
    ::= { frmScgPtpEntry 11 }


frmScgPtpTrafficMode    OBJECT-TYPE
    SYNTAX      InfnTrafficMode
    MAX-ACCESS  read-only
    STATUS      current
    DESCRIPTION ""
    ::= { frmScgPtpEntry  12 }

frmScgPtpPathLossCheckControlStatus OBJECT-TYPE
    SYNTAX      InfnPathLossCheckControlStatus
    MAX-ACCESS  read-only
    STATUS      current
    DESCRIPTION ""
    ::= { frmScgPtpEntry  13 }

frmScgPtpLastSuccessfullPathLossCheckTS OBJECT-TYPE
    SYNTAX      Integer32
    MAX-ACCESS  read-only
    STATUS      current
    DESCRIPTION ""
    ::= { frmScgPtpEntry  14 }

frmScgPtpPathLoss   OBJECT-TYPE
    SYNTAX      FloatHundredths
    MAX-ACCESS  read-only
    STATUS      current
    DESCRIPTION ""
    ::= { frmScgPtpEntry  15 }

frmScgPtpLastPathLossCheckAttemptTS OBJECT-TYPE
    SYNTAX      Integer32
    MAX-ACCESS  read-only
    STATUS      current
    DESCRIPTION ""
    ::= { frmScgPtpEntry  16 }


frmScgPtpLastPathLossCheckAttemptStatus OBJECT-TYPE
    SYNTAX      InfnLastPathLossCheckAttemptStatus
    MAX-ACCESS  read-only
    STATUS      current
    DESCRIPTION ""
    ::= { frmScgPtpEntry  17 }

frmScgPtpLastPathLossCheckFailedReason  OBJECT-TYPE
    SYNTAX      InfnLastPathLossCheckFailedReason
    MAX-ACCESS  read-only
    STATUS      current
    DESCRIPTION ""
    ::= { frmScgPtpEntry  18 }

frmScgPtpPathLossHigh OBJECT-TYPE
    SYNTAX      TruthValue
    MAX-ACCESS  read-only
    STATUS      current
    DESCRIPTION ""
    ::= { frmScgPtpEntry 19}


frmScgPtpPowerContolLoop  OBJECT-TYPE
    SYNTAX      InfnEnableDisable
    MAX-ACCESS  read-write
    STATUS      current
    DESCRIPTION ""
    ::= { frmScgPtpEntry  20 }


frmScgPtpAutoDiscSoakTime OBJECT-TYPE
    SYNTAX      Integer32
    MAX-ACCESS  read-write
    STATUS      current
    DESCRIPTION ""
    ::= { frmScgPtpEntry 21 }

frmScgPtpPathLossCheckDetectPort    OBJECT-TYPE
    SYNTAX      DisplayString
    MAX-ACCESS  read-only
    STATUS      current
    DESCRIPTION ""
    ::= { frmScgPtpEntry  22 }

frmScgPtpMuxedProvisionedNeighborTPList OBJECT-TYPE
    SYNTAX      DisplayString
    MAX-ACCESS  read-only
    STATUS      current
    DESCRIPTION ""
    ::= { frmScgPtpEntry 23 }

frmScgPtpPassiveProvisionedNeighborTP OBJECT-TYPE
    SYNTAX      DisplayString
    MAX-ACCESS  read-write
    STATUS      current
    DESCRIPTION ""
    ::= { frmScgPtpEntry 24 }

frmScgPtpMuxedProvisionedNeighborMotList OBJECT-TYPE
    SYNTAX      DisplayString
    MAX-ACCESS  read-only
    STATUS      current
    DESCRIPTION ""
    ::= { frmScgPtpEntry 25 }

frmScgPtpTxProvNbrTP	OBJECT-TYPE
    SYNTAX      DisplayString
    MAX-ACCESS  read-write
    STATUS      current
    DESCRIPTION ""
    ::= { frmScgPtpEntry 26 }

frmScgPtpRxProvNbrTP	OBJECT-TYPE
    SYNTAX      DisplayString
    MAX-ACCESS  read-write
    STATUS      current
    DESCRIPTION ""
    ::= { frmScgPtpEntry 27 }

frmScgPtpTxProvEqptType	OBJECT-TYPE
    SYNTAX      InfnEqptType
    MAX-ACCESS  read-only
    STATUS      current
    DESCRIPTION ""
    ::= { frmScgPtpEntry 28 }

frmScgPtpRxProvEqptType	OBJECT-TYPE
    SYNTAX      InfnEqptType
    MAX-ACCESS  read-only
    STATUS      current
    DESCRIPTION ""
    ::= { frmScgPtpEntry 29 }

-- Conformance Statements
frmScgPtpConformance    OBJECT IDENTIFIER ::= { frmScgPtpMIB 3 }
frmScgPtpCompliances    OBJECT IDENTIFIER ::= { frmScgPtpConformance 1 }
frmScgPtpGroups         OBJECT IDENTIFIER ::= { frmScgPtpConformance 2 }

frmScgPtpCompliance MODULE-COMPLIANCE
    STATUS current
    DESCRIPTION
    "Describes the requirements for conformance to the FRMSCGPTP-MIB"
    MODULE
        MANDATORY-GROUPS { frmScgPtpGroup }
    ::= { frmScgPtpCompliances 1 }

frmScgPtpGroup OBJECT-GROUP
    OBJECTS {
        frmScgPtpTrafficMode,
        frmScgPtpPathLossCheckControlStatus,
        frmScgPtpLastSuccessfullPathLossCheckTS,
        frmScgPtpPathLoss,
        frmScgPtpPathLossCheckDetectPort,
        frmScgPtpLastPathLossCheckAttemptTS,
        frmScgPtpLastPathLossCheckAttemptStatus,
        frmScgPtpLastPathLossCheckFailedReason,
        frmScgPtpPowerContolLoop,
        frmScgPtpScgNumber                     ,
        frmScgPtpScgSupEqptType                ,
        frmScgPtpMPOAID                        ,
        frmScgPtpProvisionedFPMPO              ,
        frmScgPtpAutoDiscoveryState            ,
        frmScgPtpDiscoveredNeighborTP          ,
        frmScgPtpInterfaceType                 ,
        frmScgPtpProvisionedNeighborTP         ,
        frmScgPtpAutoDiscSoakTime              ,
        frmScgPtpMuxedProvisionedNeighborTPList,
        frmScgPtpProvisionedOpenWaveRemotePtp  ,
        frmScgPtpPmHistStatsEnable             ,
        frmScgPtpPathLossHigh,
        frmScgPtpProvisionedNeighborAdTpType,
		frmScgPtpPassiveProvisionedNeighborTP,
		frmScgPtpMuxedProvisionedNeighborMotList,
		frmScgPtpTxProvNbrTP,
		frmScgPtpRxProvNbrTP,
		frmScgPtpTxProvEqptType,
		frmScgPtpRxProvEqptType
    }
    STATUS current
    DESCRIPTION
        " A collection of objects for managing the frmScgPtp"
    ::= { frmScgPtpGroups 1 }
END
