-- ***********************************************************************
-- INFINERA-NOTIFICATION-MIB.txt:  Infinera notification MIB file
--
-- Jul 2010, Sharfuddin Syed / Narendra Gupta
--
-- (c) Copyright 2012 Infinera Corporation. All rights reserved.
-- ***********************************************************************
INFINERA-NOTIFICATION-MIB DEFINITIONS ::= BEGIN

IMPORTS
    OBJECT-TYPE, NOTIFICATION-TYPE, MODULE-IDENTITY,
    Integer32                            FROM SNMPv2-SMI
    NOTIFICATION-GROUP, OBJECT-GROUP     FROM SNMPv2-CONF
    DisplayString                        FROM SNMPv2-TC
    common                               FROM INFINERA-REG-MIB
    InfnManagedObjectType                FROM INFINERA-TC-MIB;

infnNotifications MODULE-IDENTITY
    LAST-UPDATED "201304241700Z"
    ORGANIZATION
        "Infinera"
    CONTACT-INFO
        "Infinera
         Sunnyvale, CA - 94089
         Contact : Technical Support
         Email   : support@infinera.com
         Phone   : 1-877-INF-5288"
    DESCRIPTION
        "Module representing notifications generated
        by Infinera Network Elements"
::= { common 2 }


-- Conformance Definitions for the Infinera NE Notifications Group

infnNotificationConformance  OBJECT IDENTIFIER ::= { infnNotifications 16 }
infnNotificationObjectGroups  OBJECT IDENTIFIER ::= { infnNotificationConformance 1 }
infnNotificationNotifGroups  OBJECT IDENTIFIER ::= { infnNotificationConformance 2 }

infnAlarmNotification  NOTIFICATION-TYPE
    OBJECTS { alarmNotificationId,
        alarmNodeId,
        alarmNodeName,
        alarmObjectType,
        alarmObjectAid,
        alarmSourceOid,
        alarmProbableCause,
        alarmSeverity,
        alarmCategory,
        alarmServiceAffecting,
        alarmOccurrenceTime,
        alarmLocation,
        alarmDirection,
        alarmProbableCauseDescription,
        alarmAdditionalText,
        alarmCorrelationId }
    STATUS     current
    DESCRIPTION
        "This definition represents the notifications generated by the Infinera network element that are categorized as alarmed conditions "
    ::= { infnNotifications 1 }

infnTcaNotification  NOTIFICATION-TYPE
    OBJECTS { tcaNotificationId,
        tcaNodeId,
        tcaNodeName,
        tcaObjectType,
        tcaObjectAid,
        tcaSourceOid,
        tcaProbableCause,
        tcaSeverity,
        tcaCategory,
        tcaServiceAffecting,
        tcaOccurrenceTime,
        tcaLocation,
        tcaDirection,
        tcaMonitoredValue,
        tcaThresholdValue,
        tcaTimePeriod,
        tcaProbableCauseDescription,
        tcaAdditionalText }
    STATUS     current
    DESCRIPTION
        "This definition represents the notifications generated by the Infinera network element that are categorized as Threshold Crossing Alerts (TCAs)."
    ::= { infnNotifications 2 }

infnAdminEventNotification  NOTIFICATION-TYPE
    OBJECTS { infnAdminNotificationId,
        infnAdminNodeId,
        infnAdminNodeName,
        infnAdminObjectType,
        infnAdminObjectAid,
        infnAdminSourceOid,
        infnAdminEventTime,
        infnAdminCause }
    STATUS     current
    DESCRIPTION
        "This definition represents the notifications generated by the Infinera network element that are categorized as events. "
    ::= { infnNotifications 3 }

infnAuditEventNotification  NOTIFICATION-TYPE
    OBJECTS { infnAuditNotificationId,
        infnAuditNodeId,
        infnAuditNodeName,
        infnAuditObjectType,
        infnAuditObjectAid,
        infnAuditSourceOid,
        infnAuditUserId,
        infnAuditHostInfo,
        infnAuditTime,
        infnAuditOperationName,
        infnAuditOperationStatus,
        infnAuditParamsList }
    STATUS     current
    DESCRIPTION
        ""
    ::= { infnNotifications 4 }

infnSecurityEventNotification  NOTIFICATION-TYPE
    OBJECTS { infnSecurityNotificationId,
        infnSecurityNodeId,
        infnSecurityNodeName,
        infnSecurityObjectType,
        infnSecurityObjectAid,
        infnSecuritySourceOid,
        infnSecurityHostInfo,
        infnSecurityEventTime,
        infnSecurityMessage }
    STATUS     current
    DESCRIPTION
        "This definition represents the notifications generated by the Infinera network element that are categorized as security events. "
    ::= { infnNotifications 5 }

-- The following are the definition of notification related tables that are present on the Infinera Network Elements.

infnAlarmTable  OBJECT-TYPE
    SYNTAX SEQUENCE OF InfnAlarmEntry
    MAX-ACCESS not-accessible
    STATUS     current
    DESCRIPTION
        "This table contains the list of all outstanding alarms currently present on the network element."
    ::= { common 3 }

infnAlarmEntry  OBJECT-TYPE
    SYNTAX     InfnAlarmEntry
    MAX-ACCESS not-accessible
    STATUS     current
    DESCRIPTION
        "A row in the alarm table. Each row in the table is identified with a notification ID and a list of variable bindings"
    INDEX { alarmNotificationId }
    ::= { infnAlarmTable 1 }

InfnAlarmEntry ::= SEQUENCE {
    alarmNotificationId        Integer32,
    alarmNodeId                DisplayString,
    alarmNodeName              DisplayString,
    alarmObjectType            InfnManagedObjectType,
    alarmObjectAid             DisplayString,
    alarmSourceOid             OBJECT IDENTIFIER,
    alarmProbableCause         INTEGER,
    alarmSeverity              INTEGER,
    alarmCategory              INTEGER,
    alarmServiceAffecting      INTEGER,
    alarmOccurrenceTime        DisplayString,
    alarmLocation              INTEGER,
    alarmDirection             INTEGER,
    alarmProbableCauseDescription        DisplayString,
    alarmAdditionalText        DisplayString,
    alarmCorrelationId         Integer32
}

-- The following are the attributes that represents various variable bindings in the notifications generated by the Network Element.

alarmNotificationId  OBJECT-TYPE
    SYNTAX     Integer32 (0..2147483647)
    MAX-ACCESS accessible-for-notify
    STATUS     current
    DESCRIPTION
        "This object represents the Notification ID generated by NE for
        each alarmed notification."
    ::= { infnAlarmEntry 1 }

alarmNodeId  OBJECT-TYPE
    SYNTAX     DisplayString (SIZE(1..128))
    MAX-ACCESS read-only
    STATUS     current
    DESCRIPTION
        "This object representsthe Node ID of the network element."
    ::= { infnAlarmEntry 2 }

alarmNodeName  OBJECT-TYPE
    SYNTAX     DisplayString (SIZE(1..128))
    MAX-ACCESS read-only
    STATUS     current
    DESCRIPTION
        "This object represents the name of the network element. This is similar to the TID representation in TL1."
    ::= { infnAlarmEntry 3 }

alarmObjectType  OBJECT-TYPE
    SYNTAX     InfnManagedObjectType
    MAX-ACCESS read-only
    STATUS     current
    DESCRIPTION
        "This object represents the managed object type that is reporting the alarm."
    ::= { infnAlarmEntry 4 }

alarmObjectAid  OBJECT-TYPE
    SYNTAX     DisplayString
    MAX-ACCESS read-only
    STATUS     current
    DESCRIPTION
        "This object represents the Object Name of the facility in the Access Identifier format."
    ::= { infnAlarmEntry 5 }

alarmSourceOid  OBJECT-TYPE
    SYNTAX     OBJECT IDENTIFIER
    MAX-ACCESS read-only
    STATUS     current
    DESCRIPTION
        "This object represents the object ID instance of the managed object on which the alarm is reported.
        It is used as a handle to query the details about the object which is in the alarmed state. "
    ::= { infnAlarmEntry 6 }

alarmProbableCause  OBJECT-TYPE
    SYNTAX     INTEGER {
        adminLock (1),
        adminMaint (2),
        adsrup (3),
        adTimeout (4),
        ais-dtp (5),
        ais-l (6),
        ais-ms (7),
        alsDisabled (8),
        ambientTempOorh (9),
        aupfail (10),
        auxEnetLoLinkCtrlA (11),
        auxEnetLoLinkCtrlB (12),
        bdi (13),
        bdi-dtp (14),
        backupMemoryLow (15),
        backupMemoryVeryLow (16),
        branMsmt (17),
        breakerOpen48v (18),
        ctrlCommFailA (19),
        ctrlCommFailB (20),
        dbMsmt (21),
        dbRestoreFail (22),
        dbRestoreFailReboot (23),
        dcnEnetLoLinkCtrlA (24),
        dcnEnetLoLinkCtrlB (25),
        deEncapAis-l (26),
        deEncapAis-ms (27),
        deEncapLof (28),
        deEncapLos (29),
        deEncapLossOfSync (30),
        eqpPer1 (31),
        eqpPer2 (32),
        eqpPer3 (33),
        eqptPartFail (34),
        eqptProtFailSlot3 (35),
        eqptProtFailSlot4 (36),
        eqptProtFailSlot5 (37),
        eqptProtFailSlot6 (38),
        eqptCpReset (39),
        eqptCpUr (40),
        eqptDegrade (41),
        eqptFail (42),
        eqptMsmt (43),
        excessiveChannels (44),
        gmplsConfigMismatch (45),
        gmplsNbrDown (46),
        impropRmvl (47),
        initFail (48),
        insufficientGain (49),
        interOamMisConn (50),
        lineTestSigGen (51),
        lineTestSigOos (52),
        loa (53),
        loc (54),
        lockOutOfPr (55),
        lockOutOfWk (56),
        lof (57),
        los (58),
        lossOfSync (59),
        lpbkFacility (60),
        lpbkTerm (61),
        misConn (62),
        misConfigIpAddr (63),
        nbrsOscIpAddrConflict (64),
        nct1EnetLolinkCtrlA (65),
        nct1EnetLolinkCtrlB (66),
        nct2EnetLolinkCtrlA (67),
        nct2EnetLolinkCtrlB (68),
        ntpServerLoss (69),
        nwDuplicateMeName (70),
        nwDuplicateNbr (71),
        nwDuplicateRouterId (72),
        olOorh (73),
        olos (74),
        oprOorh (75),
        oprOorl (76),
        optOorh (77),
        optOorl (78),
        oscCommFailA (79),
        oscCommFailB (80),
        oscIpAddrDuplicate (81),
        gccIpAddrSubnetMsmt (82),
        peerCtrlCommFail (83),
        plm (84),
        postFecBerSf (85),
        prbsGen (86),
        prbsOos (87),
        preFecBerSd (88),
        pwrAdjustIncomplete (89),
        power48vFail (90),
        pwrLoopDisabled (91),
        rfi-l (92),
        rfi-ms (93),
        spanLossOorh (94),
        spanLossOorl (95),
        sncFail (96),
        sncSetupFail (97),
        swInstallFail (98),
        swUpgradeFail (99),
        swUpgradeFailBootup (100),
        tempOorDeviceShutdown (101),
        tempOorh (102),
        tempOorhRxPicShutdown (103),
        tempOorhTxPicShutdown (104),
        tempOorl (105),
        tim-dtp (106),
        tim-dts (107),
        tim-s (108),
        tribPrbsGen (109),
        tribPrbsOos (110),
        tribTestSigGen (111),
        tribTestSigOos (112),
        txfrPriFail (113),
        txfrPriFailSna (114),
        txfrsFail (115),
        unknownFw (116),
        powerDrawExceeded (117),
        connectivityFail (118),
        gccGmplsCfgMsmt (119),
        gccGmplsNbrDown (120),
        gccIPaddrDuplicate (121),
        nbrsGccIPaddrInConflict (122),
        ocgMismatch (123),
        powerControl (124),
        greTunnelAddressMismatch (125),
        noManagementRedundancy (126),
		lolm (127),
		deEncapLolm (128),
        oloorh (129),
        ochMismatch (130),
        switchBackToWrk (131),
        manualSwitchBackToWrk (132),
        wtrStart (133),
		spectrumNotAttained(134), --DSE Output Spectrum Not Attained
		incompatibleDse(135),
		tempOorhDevAutoShutdown(136),
		rmtChnlMismatch(137),
		equipmentInit(138),
        adminXfrReqDrop(139),
        adminDBCurrupt(140),
        adminRestoreFailed(141),
        txfr-sec-fail(142),
        optTooLow(143),
        equipmentUnsupported(144),
        ccmLoc(145),
        ccmUnexpLevel(146),
        ccmMisMerge(147),
        ccmUnexpMep(148),
        ccmUnexpPeriod(149),
        ccmUnexpPrio(150),
        ccmRemMacErr(151),
        ethRdi(152),
        ethAis(153),
        vsiFail(154),
        vsiPartialFail(155),
        vsiMacLimit(156),
        macFlap(157),
        acMacLimit(158),
        cacFail(159),
        cacUnavail(160),
        freqProvPending(161),
        vsiMacLimDnlDnf(162),
        intra-sch-carrier-ripple-high(164),
        tx-tim (165),
        rx-tim (166),
        airCompressorFailure (200),
        airConditioningFailure (201),
        airDryerFailure (202),
        batteryDischarging (203),
        batteryFailure (204),
        coolingFanFailure (205),
        centralPowerFailureMajor (206),
        centralPowerFailureMinor (207),
        engineFailure (208),
        engineOperating (209),
        explosiveGas (210),
        fireDetectorFailure (211),
        fire (212),
        flood (213),
        fuseFailure (214),
        generatorFailure (215),
        highAirFlow (216),
        highHumidity (217),
        highTemperature (218),
        highWater (219),
        intrusion (220),
        lowBatteryVoltage (221),
        lowFuel (222),
        lowHumidity (223),
        lowCablePressure (224),
        lowTemperature (225),
        lowWater (226),
        misc (227),
        openDoor (228),
        pumpFailure (229),
        commercialPowerFailure (230),
        power-xFailure (231),
        rectifierFailure (232),
        rectifierHighVoltage (233),
        rectifierLowVoltage (234),
        smoke (235),
        toxicGas (236),
        ventilationSystemFailure (237),
        linePrbsGen (238),
        ais (239),              -- Alarm Indication Signal
        deg (240),              --as per RFC 3591       Degraded
        linePrbsOos  (241),
        lck (242),      --as per RFC 3591 Locked indication
        oci (243),      --Open Connection Indication
        oldRevCtrlr (244), -- Old Revision Controller present.
        protUnitAct(245), --  protection unit active
        misConfig (246),        --Mis Configurations
        lsActive(247),  -- laser shutdown active
        deEncapAis-p (248), -- De-encapsulated Alarm Indication Signal PATH
        rstPathAct (249),   -- Restoration Path Active
        ltc (250),   -- Loss Of Tandem Connection
        automaticGainCtrlNotFunctioning (251), -- Automatic Gain Control Not Functioning
		slOorh (300),
		slOorl (301),
		gainOorh (303),
		gainOorl (304),
		insufficientChanPower (305),
		uSupportedTom (306),
		ncLolink (307),
		chassisMisconn (308),
		dcnLolink (309),
		loLink (310),
		none (311),
		unknownEqpt (312),
		outputPwrFailure (313),
		inputPwrFailure (314),
		dropBandOptLow (315),
		timOtu (316),
		dropBandOprOorLow (317),
		dropBandOprOorHigh (318),
		dropBandOptOorLow (319),
		dropBandOptOorHigh (320),
		dropBandOLOS (321),
		bandOptTooLow (322),
		bandOptOorLow (323),
		bandOptOorHigh (324),
		bandOprOorLow (325),
		bandOprOorHigh (326),
		insufficientAttenuation (327),
		oprOorHighOscDisabled (328),
		switchToPr (329),
		manualSwitchToPr (330),
		adaptCommitPending (331),
		txFail (332),
		ntpAuthFail(333),
		lowCh(334),

		rf (340),
		lf (341),
		deEncapLf(342),
		deEncapRf(343),
		-- XTN ALARMS

		eqptProtFailSlot1 (500),
		eqptProtFailSlot2 (501),
		eqptProtFailSlot7 (502),
		eqptProtFailSlot8 (503),
		eqptProtFailSlot9 (504),
		eqptProtFailSlot10 (505),
		powerProtectionFail (506),
		lossOfFrameDelineation (507),
		upiMismatch (508),
		exiMismatch (509),
		clientSignalFail (510),
		tsmUnavailable (511),
		noTsmRedundancy (512),
		switchFabricFailure (513),
		switchProtUnavailable (514),
		timingSourceMismatch (515),
		muxStructureIdMismatch (516),
		powerVoltageOver(517),
		powerVoltageUnder(518),
		oscMisConnection(519),
        remmodMismatch(532),
        rx-EDFA-SPLIM(533),
        lockedSyncSourceActive(535),
        rxOPRTooLow(536),
        commFailLink(537),
		deEncapLoa(538),
		configMismatch(539),
		lossOfFrameLossOfMultiFrame(540),
        lockedSwitchModuleActive(541),
        operatingModeMismatch(542),
        powerCtrlInitiated(543),
        lossOfMultiFrame(544),
        degradedConfig(545),
        licAssignmentMsmt(546),--or brandMsMt
        licInsufficiency(547),
        licModFmtMsmt(548),
        licNwAuditMsMt(549),
        shelfDbCorrupt(550),
        tx-lossOfMultiFrame(551),
        lossOfFrameLogicalLane(552),
        lossOfLaneAllignment(554),
        igccFail(556),
        encmodeChangePending(557),
        remPortFecMsmt(558),
        aisOdu-ipath(559),
        bdiOdu-ipath(560),
        remPortEncModeMsmt(561),
        pmdOorHigh(562),
        flashFail(563),
	    preFecQSigDegrade(564),
        flashRedundancyNotAvailable(565),
        schMisConn(566),
        opt-too-low(567),
        forwarddefectindicationoverhead(568),
        forwarddefectindicationpayload(569),
        migrationfailed(570),
        backwardDefectIndicationS(571),
        openconnectionIndication(572),
        remSchParamMsmt(573),
        schNumMismatch(574),
        payloadMissingIndication(575),
        backwardDefectIndicationPayloadO(576),
        muxOprOorl(577),
        txPayloadMisMatchODUk(578),
        lossOfOpuMultiFrameIdentifier(579),
        serviceStateOOSAU(580),
        odukPELatencyFacilityOorh(581),
        odukPELatencyFacilityOorl(582),
        odukPELatencyTerminalOorh(583),
        odukPELatencyTerminalOorl(584),
        odukPSLatencyFacilityOorh(585),
        odukPSLatencyFacilityOorl(586),
        odukPSLatencyTerminalOorh(587),
        odukPSLatencyTerminalOorl(588),
        insufficientTrgtOutPwr(589),
        backwardDefectIndication(590),
        backwardDefectIndicationPayload(591),
        mainPowerFailure(592),
        pemTypMismatch(593),
        gccOspfNbrDown(595),
        gccIpSubnetMismatch(596),
        gccIpConflict(597),
        gccOspfConfigMismatch(598),
        greAddressMismatch(599),
        rem-sch-parameters-msmt(600),
        opr-too-high(601),
        opr-too-low(602),
        opr-oorl(603),
        opr-oorh(604),
        opt-oorl(605),
        opt-oorh(606),
		ocgTTIMsmt(700),
	    ocgReachThWarn (701),
	    ocgReachThExceed(702),
        tx-olos(703),
        pemGLUnavailable(704),
        registrationRequired(705),
        registrationExpired(706),
        registrationRequiredMJ(707),
		ttiMismatchXtSCH(708),
		ethCsf(709),
		linkDown (710),
        maint-req (711),
        gccFail (712),
        -- misConn (713)
        rxBDI (713),
        sbsOff (714),
        idlerSeparationOor (715)
	}
	MAX-ACCESS read-only
	STATUS     current
	DESCRIPTION
		"This object represents the probable cause of the alarm."
	::= { infnAlarmEntry 7 }

alarmSeverity  OBJECT-TYPE
    SYNTAX     INTEGER {
        psIndeterminate (1),
        psCritical (2),
        psMajor (3),
        psMinor (4),
        psWarning (5),
        psCleared (6),
        psNotReported (7)
    }
    MAX-ACCESS read-only
    STATUS     current
    DESCRIPTION
        "This object represents the severity of the alarm."
    ::= { infnAlarmEntry 8 }

alarmCategory  OBJECT-TYPE
    SYNTAX     INTEGER {
        unknown (1),
        communication (2),
        qualityOfService (3),
        environmental (4),
        equipment (5),
        softwareProcessing (6),
        facility (7),
        software (8)
    }
    MAX-ACCESS read-only
    STATUS     current
    DESCRIPTION
        ""
    ::= { infnAlarmEntry 9 }

alarmServiceAffecting  OBJECT-TYPE
    SYNTAX     INTEGER {
        saUnknown (1),
        saServiceAffecting (2),
        saNonServiceAffecting (3)
    }
    MAX-ACCESS read-only
    STATUS     current
    DESCRIPTION
        "This object indicates whether the alarm is service affecting or not."
    ::= { infnAlarmEntry 10 }

alarmOccurrenceTime  OBJECT-TYPE
    SYNTAX     DisplayString
    MAX-ACCESS read-only
    STATUS     current
    DESCRIPTION
        "This object represents the alarm occurrence date and time expressed in format YYYY-MM-DD<space>hh:mm:ss"
    ::= { infnAlarmEntry 11 }

alarmLocation  OBJECT-TYPE
    SYNTAX     INTEGER {
        nearEnd (1),
        farEnd (2),
        notApplicable (3)
    }
    MAX-ACCESS read-only
    STATUS     current
    DESCRIPTION
        "This object represents the location of the alarmed entity."
    ::= { infnAlarmEntry 12 }

alarmDirection  OBJECT-TYPE
    SYNTAX     INTEGER {
        receive (1),
        transmit (2),
        notApplicable (3)
    }
    MAX-ACCESS read-only
    STATUS     current
    DESCRIPTION
        "This object represents the direction of the alarmed entity."
    ::= { infnAlarmEntry 13 }

alarmProbableCauseDescription  OBJECT-TYPE
    SYNTAX     DisplayString (SIZE(0..255))
    MAX-ACCESS read-only
    STATUS     current
    DESCRIPTION
        "This object represents the alarm probable cause description."
    ::= { infnAlarmEntry 14 }

alarmAdditionalText  OBJECT-TYPE
    SYNTAX     DisplayString
    MAX-ACCESS read-only
    STATUS     current
    DESCRIPTION
        "This object represents the additional text describing the alarm in more concrete details."
    ::= { infnAlarmEntry 15 }

alarmCorrelationId  OBJECT-TYPE
    SYNTAX     Integer32 (0..2147483647)
    MAX-ACCESS read-only
    STATUS     current
    DESCRIPTION
        "This object represents the alarm correlation ID generated by
        the Network Element."
    ::= { infnAlarmEntry 16 }

infnTcaTable  OBJECT-TYPE
    SYNTAX SEQUENCE OF InfnTcaEntry
    MAX-ACCESS not-accessible
    STATUS     current
    DESCRIPTION
        "This table contains the list of all outstanding Threshold Crossing Alerts generated by the network element."
    ::= { common 4 }

infnTcaEntry  OBJECT-TYPE
    SYNTAX     InfnTcaEntry
    MAX-ACCESS not-accessible
    STATUS     current
    DESCRIPTION
        "A row in the TCA table. Each row in the table is identified with a notification ID and a list of variable bindings."
    INDEX { tcaNotificationId }
    ::= { infnTcaTable 1 }

InfnTcaEntry ::= SEQUENCE {
    tcaNotificationId             Integer32,
    tcaNodeId                     DisplayString,
    tcaNodeName                   DisplayString,
    tcaObjectType                 InfnManagedObjectType,
    tcaObjectAid                  DisplayString,
    tcaSourceOid                  OBJECT IDENTIFIER,
    tcaProbableCause              INTEGER,
    tcaSeverity                   INTEGER,
    tcaCategory                   INTEGER,
    tcaServiceAffecting           INTEGER,
    tcaOccurrenceTime             DisplayString,
    tcaLocation                   INTEGER,
    tcaDirection                  INTEGER,
    tcaMonitoredValue             DisplayString,
    tcaThresholdValue             DisplayString,
    tcaTimePeriod                 DisplayString,
    tcaProbableCauseDescription   DisplayString,
    tcaAdditionalText             DisplayString
}

-- Definitions for the TCA objects

tcaNotificationId  OBJECT-TYPE
    SYNTAX     Integer32 (0..2147483647)
    MAX-ACCESS accessible-for-notify
    STATUS     current
    DESCRIPTION
        "This object represents the Notification ID generated by NE for
        each TCA notification."
    ::= { infnTcaEntry 1 }

tcaNodeId  OBJECT-TYPE
    SYNTAX     DisplayString (SIZE(1..128))
    MAX-ACCESS read-only
    STATUS     current
    DESCRIPTION
        "This object represents the Node ID of the network element."
    ::= { infnTcaEntry 2 }

tcaNodeName  OBJECT-TYPE
    SYNTAX     DisplayString (SIZE(1..128))
    MAX-ACCESS read-only
    STATUS     current
    DESCRIPTION
        "This object represents the name of the network element. This is similar to the TID representation in TL1."
    ::= { infnTcaEntry 3 }

tcaObjectType  OBJECT-TYPE
    SYNTAX     InfnManagedObjectType
    MAX-ACCESS read-only
    STATUS     current
    DESCRIPTION
        "This object represents the managed object type that is reporting the alarm."
    ::= { infnTcaEntry 4 }

tcaObjectAid  OBJECT-TYPE
    SYNTAX     DisplayString
    MAX-ACCESS read-only
    STATUS     current
    DESCRIPTION
        "This object represents the Object Name of the facility in the Access Identifier format."
    ::= { infnTcaEntry 5 }

tcaSourceOid  OBJECT-TYPE
    SYNTAX     OBJECT IDENTIFIER
    MAX-ACCESS read-only
    STATUS     current
    DESCRIPTION
        "This object represents the object ID instance of the managed object on which the TCA is reported.
        It is used as a handle to query the details about the object which is in the TCA state. "
    ::= { infnTcaEntry 6 }

tcaProbableCause  OBJECT-TYPE
    SYNTAX     INTEGER {
        cvs (1),
        sess (2),
        sefss (3),
        ess (4),
        uass (5),
        cvp (6),
        sesp (7),
        sefsp (8),
        esp (9),
        uasp (10),
        be-rs (11),
        es-rs (12),
        ses-rs (13),
        ofs-rs (14),
        loss-rs (15),
        icg-pcs (16),
        es-pcs (17),
        ses-pcs (18),
        sess-pcs (19),
        jabberSeconds (20),
        ses-mac (21),
        errorOctets (22),
        jabbers (23),
        fragments (24),
        crcAlignErrors (25),
        underSized (26),
        overSized (27),
        pkts64 (28),
        pkts65to127 (29),
        pkts128to255 (30),
        pkts256to511 (31),
        pkts512to1023 (32),
        pkts1024to1518 (33),
        pkts1519tojumbo (34),
        packets (35),
        octets (36),
        broadcastPkts (37),
        multicastPkts (38),
        inPauseFrames (39),
        outPauseFrames (40),
        pkts1024to1522 (41),
        pkts1523tojumbo (42),
        invalidCrcs (43),
        frames (44),
        erroredFrames (45),
        erroredOctets (46),
        erroredBlocks  (47),
        defectSeconds   (48),
        beiCount (49),
        erroredBlocksFarEnd (50),
        defectSecondsFarEnd (51)
    }
    MAX-ACCESS read-only
    STATUS     current
    DESCRIPTION
        "This object represents the probable cause of the alarm."
    ::= { infnTcaEntry 7 }

tcaSeverity  OBJECT-TYPE
    SYNTAX     INTEGER {
        psIndeterminate (1),
        psCritical (2),
        psMajor (3),
        psMinor (4),
        psWarning (5),
        psCleared (6),
        psEvent (7),
        psNotReported (8)
    }
    MAX-ACCESS read-only
    STATUS     current
    DESCRIPTION
        "This object represents the severity of the TCA."
    ::= { infnTcaEntry 8 }

tcaCategory  OBJECT-TYPE
    SYNTAX     INTEGER {
        unknown (1),
        communication (2),
        qualityOfService (3),
        environmental (4),
        equipment (5),
        softwareProcessing (6),
        facility (7),
        software (8)
    }
    MAX-ACCESS read-only
    STATUS     current
    DESCRIPTION
        ""
    ::= { infnTcaEntry 9 }

tcaServiceAffecting  OBJECT-TYPE
    SYNTAX     INTEGER {
        saUnknown (1),
        saServiceAffecting (2),
        saNonServiceAffecting (3)
    }
    MAX-ACCESS read-only
    STATUS     current
    DESCRIPTION
        "This object indicates whether the alarm is service affecting or not."
    ::= { infnTcaEntry 10 }

tcaOccurrenceTime  OBJECT-TYPE
    SYNTAX     DisplayString
    MAX-ACCESS read-only
    STATUS     current
    DESCRIPTION
        "This object represents the tca occurrence date and time expressed in format YYYY-MM-DD<space>hh:mm:ss."
    ::= { infnTcaEntry 11 }

tcaLocation  OBJECT-TYPE
    SYNTAX     INTEGER {
        nearEnd (1),
        farEnd (2),
        notApplicable (3)
    }
    MAX-ACCESS read-only
    STATUS     current
    DESCRIPTION
        "This object represents the location of the alarmed entity."
    ::= { infnTcaEntry 12 }

tcaDirection  OBJECT-TYPE
    SYNTAX     INTEGER {
        receive (1),
        transmit (2),
        notApplicable (3)
    }
    MAX-ACCESS read-only
    STATUS     current
    DESCRIPTION
        "This object represents the direction of the alarmed entity."
    ::= { infnTcaEntry 13 }

tcaMonitoredValue  OBJECT-TYPE
    SYNTAX     DisplayString (SIZE(0..255))
    MAX-ACCESS read-only
    STATUS     current
    DESCRIPTION
        "This object represents the current threshold value."
    ::= { infnTcaEntry 14 }

tcaThresholdValue  OBJECT-TYPE
    SYNTAX     DisplayString (SIZE(0..255))
    MAX-ACCESS read-only
    STATUS     current
    DESCRIPTION
        "This object represents the configured threshold value."
    ::= { infnTcaEntry 15 }

tcaTimePeriod  OBJECT-TYPE
    SYNTAX     DisplayString (SIZE(0..255))
    MAX-ACCESS read-only
    STATUS     current
    DESCRIPTION
        "This object represents the time period (e.g. 15-MIN or 24-HR) for which the TCA has been raised."
    ::= { infnTcaEntry 16 }

tcaProbableCauseDescription  OBJECT-TYPE
    SYNTAX     DisplayString (SIZE(0..255))
    MAX-ACCESS read-only
    STATUS     current
    DESCRIPTION
        "This object represents the TCA probable cause description"
    ::= { infnTcaEntry 17 }

tcaAdditionalText  OBJECT-TYPE
    SYNTAX     DisplayString
    MAX-ACCESS read-only
    STATUS     current
    DESCRIPTION
        "This object represents the additional text describing the TCA"
    ::= { infnTcaEntry 18 }

infnAdminEventTable  OBJECT-TYPE
    SYNTAX SEQUENCE OF InfnAdminEventEntry
    MAX-ACCESS not-accessible
    STATUS     current
    DESCRIPTION
        "This table contains the list of all outstanding admin events generated by the network element."
    ::= { common 5 }

infnAdminEventEntry  OBJECT-TYPE
    SYNTAX     InfnAdminEventEntry
    MAX-ACCESS not-accessible
    STATUS     current
    DESCRIPTION
        "A row in the admin event table. Each row in the table is identified with a notification ID and a list of variable bindings."
    INDEX { infnAdminNotificationId }
    ::= { infnAdminEventTable 1 }

InfnAdminEventEntry ::= SEQUENCE {
    infnAdminNotificationId
        Integer32,
    infnAdminNodeId
        DisplayString,
    infnAdminNodeName
        DisplayString,
    infnAdminObjectType
        InfnManagedObjectType,
    infnAdminObjectAid
        DisplayString,
    infnAdminSourceOid
        OBJECT IDENTIFIER,
    infnAdminEventTime
        DisplayString,
    infnAdminCause
        DisplayString
}

infnAdminNotificationId  OBJECT-TYPE
    SYNTAX     Integer32
    MAX-ACCESS accessible-for-notify
    STATUS     current
    DESCRIPTION
        "This object represents the Notification ID generated by NE for
        each admin event notification."
    ::= { infnAdminEventEntry 1 }

infnAdminNodeId  OBJECT-TYPE
    SYNTAX     DisplayString
    MAX-ACCESS read-only
    STATUS     current
    DESCRIPTION
        "This object represents the node Id of the network element."
    ::= { infnAdminEventEntry 2 }

infnAdminNodeName  OBJECT-TYPE
    SYNTAX     DisplayString
    MAX-ACCESS read-only
    STATUS     current
    DESCRIPTION
        "This object represents the name of the network element."
    ::= { infnAdminEventEntry 3 }

infnAdminObjectType  OBJECT-TYPE
    SYNTAX     InfnManagedObjectType
    MAX-ACCESS read-only
    STATUS     current
    DESCRIPTION
        "This object represents the managed object type that is reporting the admin event."
    ::= { infnAdminEventEntry 4 }

infnAdminObjectAid  OBJECT-TYPE
    SYNTAX     DisplayString
    MAX-ACCESS read-only
    STATUS     current
    DESCRIPTION
        "This object represents the Object Name of the facility in the Access Identifier format."
    ::= { infnAdminEventEntry 5 }

infnAdminSourceOid  OBJECT-TYPE
    SYNTAX     OBJECT IDENTIFIER
    MAX-ACCESS read-only
    STATUS     current
    DESCRIPTION
        "This object represents the object ID instance of the managed object on which the admin event is reported.
        "
    ::= { infnAdminEventEntry 6 }

infnAdminEventTime  OBJECT-TYPE
    SYNTAX     DisplayString
    MAX-ACCESS read-only
    STATUS     current
    DESCRIPTION
        "This object represents the event occurrence date and time expressed in format YYYY-MM-DD<space>hh:mm:ss."
    ::= { infnAdminEventEntry 7 }

infnAdminCause  OBJECT-TYPE
    SYNTAX     DisplayString
    MAX-ACCESS read-only
    STATUS     current
    DESCRIPTION
        "This object represents the admin event description"
    ::= { infnAdminEventEntry 8 }

infnAuditEventTable  OBJECT-TYPE
    SYNTAX SEQUENCE OF InfnAuditEventEntry
    MAX-ACCESS not-accessible
    STATUS     current
    DESCRIPTION
        "This table contains the list of all outstanding audit events generated by the network element."
    ::= { common 6 }

infnAuditEventEntry  OBJECT-TYPE
    SYNTAX     InfnAuditEventEntry
    MAX-ACCESS not-accessible
    STATUS     current
    DESCRIPTION
        "A row in the AUDIT table. Each row in the table is identified with a notification ID and a list of variable bindings."
    INDEX { infnAuditNotificationId }
    ::= { infnAuditEventTable 1 }

InfnAuditEventEntry ::= SEQUENCE {
    infnAuditNotificationId
        Integer32,
    infnAuditNodeId
        DisplayString,
    infnAuditNodeName
        DisplayString,
    infnAuditObjectType
        InfnManagedObjectType,
    infnAuditObjectAid
        DisplayString,
    infnAuditSourceOid
        OBJECT IDENTIFIER,
    infnAuditUserId
        DisplayString,
    infnAuditHostInfo
        DisplayString,
    infnAuditTime
        DisplayString,
    infnAuditOperationName
        DisplayString,
    infnAuditOperationStatus
        DisplayString,
    infnAuditParamsList
        DisplayString
}

infnAuditNotificationId  OBJECT-TYPE
    SYNTAX     Integer32
    MAX-ACCESS accessible-for-notify
    STATUS     current
    DESCRIPTION
        "This object represents the Notification ID generated by NE for
        each audit notification."
    ::= { infnAuditEventEntry 1 }

infnAuditNodeId  OBJECT-TYPE
    SYNTAX     DisplayString
    MAX-ACCESS read-only
    STATUS     current
    DESCRIPTION
        "This object represents the Node ID of the network element."
    ::= { infnAuditEventEntry 2 }

infnAuditNodeName  OBJECT-TYPE
    SYNTAX     DisplayString
    MAX-ACCESS read-only
    STATUS     current
    DESCRIPTION
        "This object represents the name of the network element. "
    ::= { infnAuditEventEntry 3 }

infnAuditObjectType  OBJECT-TYPE
    SYNTAX     InfnManagedObjectType
    MAX-ACCESS read-only
    STATUS     current
    DESCRIPTION
        "This object represents the managed object type that is reporting the audit event."
    ::= { infnAuditEventEntry 4 }

infnAuditObjectAid  OBJECT-TYPE
    SYNTAX     DisplayString
    MAX-ACCESS read-only
    STATUS     current
    DESCRIPTION
        "This object represents the Object Name of the facility in the Access Identifier format."
    ::= { infnAuditEventEntry 5 }

infnAuditSourceOid  OBJECT-TYPE
    SYNTAX     OBJECT IDENTIFIER
    MAX-ACCESS read-only
    STATUS     current
    DESCRIPTION
        "This object represents the object ID instance of the managed object on which the audit is reported.
        "
    ::= { infnAuditEventEntry 6 }

infnAuditUserId  OBJECT-TYPE
    SYNTAX     DisplayString
    MAX-ACCESS read-only
    STATUS     current
    DESCRIPTION
        "This is the user name who has issued this operation"
    ::= { infnAuditEventEntry 7 }

infnAuditHostInfo  OBJECT-TYPE
    SYNTAX     DisplayString
    MAX-ACCESS read-only
    STATUS     current
    DESCRIPTION
        "This is hostname or IP address from where operation was issued."
    ::= { infnAuditEventEntry 8 }

infnAuditTime  OBJECT-TYPE
    SYNTAX     DisplayString
    MAX-ACCESS read-only
    STATUS     current
    DESCRIPTION
        "This object represents the event occurrence date and time expressed in format YYYY-MM-DD<space>hh:mm:ss."
    ::= { infnAuditEventEntry 9 }

infnAuditOperationName  OBJECT-TYPE
    SYNTAX     DisplayString
    MAX-ACCESS read-only
    STATUS     current
    DESCRIPTION
        "The name of operation which was given by user."
    ::= { infnAuditEventEntry 10 }

infnAuditOperationStatus  OBJECT-TYPE
    SYNTAX     DisplayString
    MAX-ACCESS read-only
    STATUS     current
    DESCRIPTION
        "The status of the operation for this Audit Event. Could be success or failure etc."
    ::= { infnAuditEventEntry 11 }

infnAuditParamsList  OBJECT-TYPE
    SYNTAX     DisplayString
    MAX-ACCESS read-only
    STATUS     current
    DESCRIPTION
        "This attribute contains DisplayString data in comma separated format. The data represents the attributes and their values that got affected by the operation which resulted in this Audit event."
    ::= { infnAuditEventEntry 12 }

infnSecurityEventTable  OBJECT-TYPE
    SYNTAX SEQUENCE OF InfnSecurityEventEntry
    MAX-ACCESS not-accessible
    STATUS     current
    DESCRIPTION
        ""
    ::= { common 7 }

infnSecurityEventEntry  OBJECT-TYPE
    SYNTAX     InfnSecurityEventEntry
    MAX-ACCESS not-accessible
    STATUS     current
    DESCRIPTION
        ""
    INDEX { infnSecurityNotificationId }
    ::= { infnSecurityEventTable 1 }

InfnSecurityEventEntry ::= SEQUENCE {
    infnSecurityNotificationId
        Integer32,
    infnSecurityNodeId
        DisplayString,
    infnSecurityNodeName
        DisplayString,
    infnSecurityObjectType
        InfnManagedObjectType,
    infnSecurityObjectAid
        DisplayString,
    infnSecuritySourceOid
        OBJECT IDENTIFIER,
    infnSecurityHostInfo
        DisplayString,
    infnSecurityEventTime
        DisplayString,
    infnSecurityMessage
        DisplayString
}

infnSecurityNotificationId  OBJECT-TYPE
    SYNTAX     Integer32
    MAX-ACCESS accessible-for-notify
    STATUS     current
    DESCRIPTION
        "This object represents the Notification ID generated by NE for
        each audit notification."
    ::= { infnSecurityEventEntry 1 }

infnSecurityNodeId  OBJECT-TYPE
    SYNTAX     DisplayString
    MAX-ACCESS read-only
    STATUS     current
    DESCRIPTION
        "This object represents the Node ID of the network element from which the event is generated."
    ::= { infnSecurityEventEntry 2 }

infnSecurityNodeName  OBJECT-TYPE
    SYNTAX     DisplayString
    MAX-ACCESS read-only
    STATUS     current
    DESCRIPTION
        "This object represents the name of the network element. "
    ::= { infnSecurityEventEntry 3 }

infnSecurityObjectType  OBJECT-TYPE
    SYNTAX     InfnManagedObjectType
    MAX-ACCESS read-only
    STATUS     current
    DESCRIPTION
        "This object represents the managed object type that is reporting the security event."
    ::= { infnSecurityEventEntry 4 }

infnSecurityObjectAid  OBJECT-TYPE
    SYNTAX     DisplayString
    MAX-ACCESS read-only
    STATUS     current
    DESCRIPTION
        "This object represents the user name."
    ::= { infnSecurityEventEntry 5 }

infnSecuritySourceOid  OBJECT-TYPE
    SYNTAX     OBJECT IDENTIFIER
    MAX-ACCESS read-only
    STATUS     current
    DESCRIPTION
        "This object represents the object ID instance of the user on which security event is reported.
        "
    ::= { infnSecurityEventEntry 6 }

infnSecurityHostInfo  OBJECT-TYPE
    SYNTAX     DisplayString
    MAX-ACCESS read-only
    STATUS     current
    DESCRIPTION
        "This is hostname or IP address from where command was issued."
    ::= { infnSecurityEventEntry 7 }

infnSecurityEventTime  OBJECT-TYPE
    SYNTAX     DisplayString
    MAX-ACCESS read-only
    STATUS     current
    DESCRIPTION
        "This object represents the event occurrence date and time expressed in format YYYY-MM-DD<space>hh:mm:ss."
    ::= { infnSecurityEventEntry 8 }

infnSecurityMessage  OBJECT-TYPE
    SYNTAX     DisplayString
    MAX-ACCESS read-only
    STATUS     current
    DESCRIPTION
        "This object represents the security event description"
    ::= { infnSecurityEventEntry 9 }

infnAlarmGroup  OBJECT-GROUP
    OBJECTS { alarmNotificationId,
        alarmNodeId,
        alarmNodeName,
        alarmObjectType,
        alarmObjectAid,
        alarmSourceOid,
        alarmProbableCause,
        alarmSeverity,
        alarmServiceAffecting,
        alarmOccurrenceTime,
        alarmLocation,
        alarmDirection,
        alarmProbableCauseDescription,
        alarmAdditionalText,
        alarmCorrelationId }
    STATUS     current
    DESCRIPTION
        "This group contains all the objects that are supported for the Alarm reporting functionality."
    ::= { infnNotificationObjectGroups 1 }

infnTcaGroup  OBJECT-GROUP
    OBJECTS { tcaNotificationId,
        tcaNodeId,
        tcaNodeName,
        tcaObjectType,
        tcaObjectAid,
        tcaSourceOid,
        tcaProbableCause,
        tcaSeverity,
        tcaServiceAffecting,
        tcaOccurrenceTime,
        tcaLocation,
        tcaDirection,
        tcaMonitoredValue,
        tcaThresholdValue,
        tcaTimePeriod,
        tcaProbableCauseDescription,
        tcaAdditionalText }
    STATUS     current
    DESCRIPTION
        "This group contains all the objects that are supported for the TCA functionality."
    ::= { infnNotificationObjectGroups 2 }

infnAdminEventGroup  OBJECT-GROUP
    OBJECTS { infnAdminNotificationId,
        infnAdminNodeId,
        infnAdminNodeName,
        infnAdminObjectType,
        infnAdminObjectAid,
        infnAdminSourceOid,
        infnAdminEventTime,
        infnAdminCause }
    STATUS     current
    DESCRIPTION
        ""
    ::= { infnNotificationObjectGroups 3 }

infnAuditEventGroup  OBJECT-GROUP
    OBJECTS { infnAuditNotificationId,
        infnAuditNodeId,
        infnAuditNodeName,
        infnAuditObjectType,
        infnAuditObjectAid,
        infnAuditSourceOid,
        infnAuditUserId,
        infnAuditHostInfo,
        infnAuditTime,
        infnAuditOperationName,
        infnAuditOperationStatus,
        infnAuditParamsList }
    STATUS     current
    DESCRIPTION
        ""
    ::= { infnNotificationObjectGroups 4 }

infnSecurityEventGroup  OBJECT-GROUP
    OBJECTS { infnSecurityNotificationId,
        infnSecurityNodeId,
        infnSecurityNodeName,
        infnSecurityObjectType,
        infnSecurityObjectAid,
        infnSecuritySourceOid,
        infnSecurityHostInfo,
        infnSecurityEventTime,
        infnSecurityMessage }
    STATUS     current
    DESCRIPTION
        ""
    ::= { infnNotificationObjectGroups 5 }

infnNotificationGroup  NOTIFICATION-GROUP
    NOTIFICATIONS { infnAlarmNotification,
        infnTcaNotification,
        infnAdminEventNotification,
        infnSecurityEventNotification,
        infnAuditEventNotification }
    STATUS     current
    DESCRIPTION
        " The notification group for this MIB that is implemented on the NE."
    ::= { infnNotificationNotifGroups 1 }
END
