LUM-ROADM-MIB DEFINITIONS ::= BEGIN

IMPORTS
    MODULE-IDENTITY, OBJECT-TYPE, Unsigned32, Integer32
        FROM SNMPv2-SMI
    OBJECT-GROUP, MODULE-COMPLIANCE
        FROM SNMPv2-CONF
    DisplayString, DateAndTime
        FROM SNMPv2-TC
    lumModules, lumRoadmMIB
        FROM LUM-REG
    MgmtNameString, SubrackNumber, SlotNumber, PortNumber,
    LambdaFrequency, BoardOrInterfaceOperStatus, BoardOrInterfaceAdminStatus,
    CommandString, FaultStatus, ObjectProperty
        FROM LUM-TC;

lumRoadmMIBModule MODULE-IDENTITY
    LAST-UPDATED
        "201706150000Z" -- June 15th 2017
    ORGANIZATION
        "Infinera Corporation"
    CONTACT-INFO
        "techsupport@infinera.com"
    DESCRIPTION
        "The reconfigurable add/drop module MIB.

        - General

        - Reconfigurable add/drop interfaces

"
    REVISION
        "201706150000Z" -- June 15th 2017
    DESCRIPTION
        "Changes made for release r29.0:
         - Changed ORGANIZATION and CONTACT-INFO"
    REVISION
        "201611300000Z" -- November 30th 2016
    DESCRIPTION
        "Changes made for release r28:
         - Hidden attribute spacingHwCapab introduced"
    REVISION
        "201601110000Z" -- Jan 11th 2016
    DESCRIPTION
        "Added default value notPresent for operStatus."
    REVISION
        "201112200000Z" --  December 20th 2011
    DESCRIPTION
        "Changes made for release r18:
         - MDU16 features included."
    REVISION
        "201102040000Z" --  Februar 4th 2011
    DESCRIPTION
        "Express port added."
    REVISION
        "200704030000Z" --  April 3rd 2007
    DESCRIPTION
        "The initial revision of this module."
    ::= { lumModules 31 }


-- ----------------------------------------------------
-- Conformance area, containing groups and complicance
-- specifications.
-- ----------------------------------------------------

lumRoadmConfs OBJECT IDENTIFIER ::= { lumRoadmMIB 1 }
lumRoadmGroups OBJECT IDENTIFIER ::= { lumRoadmConfs 1 }
lumRoadmCompl OBJECT IDENTIFIER ::= { lumRoadmConfs 2 }
lumRoadmMinimalGroups OBJECT IDENTIFIER ::= { lumRoadmConfs 3 }
lumRoadmMinimalCompl OBJECT IDENTIFIER ::= { lumRoadmConfs 4 }


-- ----------------------------------------------------
-- Root for objects in the roadm MIB
-- ----------------------------------------------------

lumRoadmMIBObjects OBJECT IDENTIFIER ::= { lumRoadmMIB 2 }


-- ----------------------------------------------------
-- This MIB contains the following groups:
-- ----------------------------------------------------

roadmGeneral OBJECT IDENTIFIER ::= { lumRoadmMIBObjects 1 }
roadmAddDropIfList OBJECT IDENTIFIER ::= { lumRoadmMIBObjects 2 }
roadmLineIfList OBJECT IDENTIFIER ::= { lumRoadmMIBObjects 3 }
roadmGroupRoadmList OBJECT IDENTIFIER ::= { lumRoadmMIBObjects 4 }
roadmGroupLineList OBJECT IDENTIFIER ::= { lumRoadmMIBObjects 5 }
roadmLineList OBJECT IDENTIFIER ::= { lumRoadmMIBObjects 6 }
roadmChannelList OBJECT IDENTIFIER ::= { lumRoadmMIBObjects 7 }
-- lumentisRoadmNotifications  OBJECT IDENTIFIER ::= { lumRoadmMIBObjects nn }


-- ----------------------------------------------------
-- Textual Conventions
-- ----------------------------------------------------

-- ----------------------------------------------------
-- General group
-- ----------------------------------------------------

roadmGeneralConfigLastChangeTime OBJECT-TYPE
    SYNTAX      DateAndTime
    MAX-ACCESS  read-only
    STATUS      current
    DESCRIPTION
        "The time when the configuration of the MIB
        was last changed.

"
    ::= { roadmGeneral 1 }

roadmGeneralStateLastChangeTime OBJECT-TYPE
    SYNTAX      DateAndTime
    MAX-ACCESS  read-only
    STATUS      current
    DESCRIPTION
        "The time when the state of the MIB was last
        changed.

"
    ::= { roadmGeneral 2 }

roadmGeneralRoadmAddDropIfTableSize OBJECT-TYPE
    SYNTAX      Unsigned32
    MAX-ACCESS  read-only
    STATUS      current
    DESCRIPTION
        "Size of table

"
    ::= { roadmGeneral 3 }

roadmGeneralRoadmLineIfTableSize OBJECT-TYPE
    SYNTAX      Unsigned32
    MAX-ACCESS  read-only
    STATUS      current
    DESCRIPTION
        "Size of table

"
    ::= { roadmGeneral 4 }

roadmGeneralRoadmGroupRoadmTableSize OBJECT-TYPE
    SYNTAX      Unsigned32
    MAX-ACCESS  read-only
    STATUS      current
    DESCRIPTION
        "Size of table

"
    ::= { roadmGeneral 5 }

roadmGeneralRoadmGroupLineTableSize OBJECT-TYPE
    SYNTAX      Unsigned32
    MAX-ACCESS  read-only
    STATUS      current
    DESCRIPTION
        "Size of table

"
    ::= { roadmGeneral 6 }

roadmGeneralRoadmLineTableSize OBJECT-TYPE
    SYNTAX      Unsigned32
    MAX-ACCESS  read-only
    STATUS      current
    DESCRIPTION
        "Size of table

"
    ::= { roadmGeneral 7 }

roadmGeneralChannelTableSize OBJECT-TYPE
    SYNTAX      Unsigned32
    MAX-ACCESS  read-only
    STATUS      current
    DESCRIPTION
        "Size of table

"
    ::= { roadmGeneral 8 }


-- ----------------------------------------------------
-- Reconfigurable Add-Drop interfaces
-- ----------------------------------------------------

roadmAddDropIfTable  OBJECT-TYPE
    SYNTAX      SEQUENCE OF RoadmAddDropIfEntry
    MAX-ACCESS  not-accessible
    STATUS      current
    DESCRIPTION
        "The interface list."
    ::= { roadmAddDropIfList 1 }

roadmAddDropIfEntry OBJECT-TYPE
    SYNTAX      RoadmAddDropIfEntry
    MAX-ACCESS  not-accessible
    STATUS      current
    DESCRIPTION
        "An entry in the interface list.

"
    INDEX { roadmAddDropIfIndex }
    ::= { roadmAddDropIfTable 1 }

RoadmAddDropIfEntry ::=
    SEQUENCE {
        roadmAddDropIfIndex                       Unsigned32,
        roadmAddDropIfName                        MgmtNameString,
        roadmAddDropIfDescr                       DisplayString,
        roadmAddDropIfSubrack                     SubrackNumber,
        roadmAddDropIfSlot                        SlotNumber,
        roadmAddDropIfTxPort                      PortNumber,
        roadmAddDropIfRxPort                      PortNumber,
        roadmAddDropIfInvPhysIndexOrZero          Unsigned32,
        roadmAddDropIfAdminStatus                 BoardOrInterfaceAdminStatus,
        roadmAddDropIfOperStatus                  BoardOrInterfaceOperStatus,
        roadmAddDropIfTemperature		  Integer32,
        roadmAddDropIfDropFrequencyMin		  LambdaFrequency,
        roadmAddDropIfDropFrequencyMax		  LambdaFrequency,
	roadmAddDropIfObjectProperty		  ObjectProperty,
        roadmAddDropIfConfigurationCommand        CommandString,
        roadmAddDropIfModuleFailure               FaultStatus,
        roadmAddDropIfTxSignalStatus              INTEGER,
        roadmAddDropIfMode                        INTEGER,
        roadmAddDropIfDescr2                      DisplayString,
        roadmAddDropIfSpacingMode                 INTEGER,
        roadmAddDropIfGuardChannel1               LambdaFrequency,
        roadmAddDropIfGuardChannel2               LambdaFrequency,
        roadmAddDropIfDropFrequencyLimitMin       LambdaFrequency,
        roadmAddDropIfDropFrequencyLimitMax       LambdaFrequency,
	roadmAddDropIfLimitConfigurationCommand	  CommandString,
	roadmAddDropIfGroupRoadmMode		  INTEGER,
	roadmAddDropIfPasswd			  DisplayString,
	roadmAddDropIfPasswdConfig		  CommandString,
	roadmAddDropIfGroupLineMode		  INTEGER,
	roadmAddDropIfNoOfConnectedChannels       Unsigned32,
	roadmAddDropIfViewChannelList             DisplayString,
	roadmAddDropIfConnectedChannelMask        DisplayString,
	roadmAddDropIfAddChannelCommand           CommandString,
	roadmAddDropIfUnlinkChannelCommand        CommandString,
	roadmAddDropIfUnlinkAllChannelsCommand    CommandString,
	roadmAddDropIfSetAttenuationCommand       CommandString,
	roadmAddDropIfAdjustAttenuationDeltaCommand CommandString,
        roadmAddDropIfConnectChannelCmd           Unsigned32,
        roadmAddDropIfDisconnectChannelCmd        Unsigned32,
        roadmAddDropIfGroupIndex                  Unsigned32,
	roadmAddDropIfAddAllChannelCommand        CommandString,
	roadmAddDropIfSetAdminStatusCommand       CommandString,
        roadmAddDropIfSpacingHwCapability         INTEGER}

roadmAddDropIfIndex OBJECT-TYPE
    SYNTAX      Unsigned32 (1..2147483647)
    MAX-ACCESS  read-only
    STATUS      current
    DESCRIPTION
        "An arbitrary index assigned to each entry.

"
    ::= { roadmAddDropIfEntry 1 }

roadmAddDropIfName OBJECT-TYPE
    SYNTAX      MgmtNameString
    MAX-ACCESS  read-only
    STATUS      current
    DESCRIPTION
        "The management name of the interface, for
        example 'roadmAddDrop:1:2:1-2', where the first number
        indicates sub-rack, the second slot number and
        the third is the port number.
        Examples:

        roadmAddDrop:s:s:p - reconfigurable add/drop interface

"
    ::= { roadmAddDropIfEntry 2 }

roadmAddDropIfDescr OBJECT-TYPE
    SYNTAX      DisplayString
    MAX-ACCESS  read-write
    STATUS      current
    DESCRIPTION
        "User configurable label.

        This attribute can be written via SNMP.
"
    DEFVAL { "" }
    ::= { roadmAddDropIfEntry 3 }

roadmAddDropIfSubrack OBJECT-TYPE
    SYNTAX      SubrackNumber
    MAX-ACCESS  read-create
    STATUS      current
    DESCRIPTION
        "The number of the subrack where the interface
        is located.

"
    ::= { roadmAddDropIfEntry 4 }

roadmAddDropIfSlot OBJECT-TYPE
    SYNTAX      SlotNumber
    MAX-ACCESS  read-create
    STATUS      current
    DESCRIPTION
        "The number of the slot where the interface is
        located.

"
    ::= { roadmAddDropIfEntry 5 }

roadmAddDropIfTxPort OBJECT-TYPE
    SYNTAX      PortNumber
    MAX-ACCESS  read-create
    STATUS      current
    DESCRIPTION
        "The number of the port where the TX-side of the
        interface is located.

"
    ::= { roadmAddDropIfEntry 6 }

roadmAddDropIfRxPort OBJECT-TYPE
    SYNTAX      PortNumber
    MAX-ACCESS  read-create
    STATUS      current
    DESCRIPTION
        "The number of the port where the RX-side of
        the interface is located.

"
    ::= { roadmAddDropIfEntry 7 }

roadmAddDropIfInvPhysIndexOrZero OBJECT-TYPE
    SYNTAX      Unsigned32 (0..2147483647)
    MAX-ACCESS  read-only
    STATUS      current
    DESCRIPTION
        "The row in the invPhysTable for this interface.
        Set to 0 if not known.

"
    ::= { roadmAddDropIfEntry 8 }

roadmAddDropIfAdminStatus OBJECT-TYPE
    SYNTAX      BoardOrInterfaceAdminStatus
    MAX-ACCESS  read-write
    STATUS      current
    DESCRIPTION
        "The administrative state for the interface.

        down - The interface should be inactive (i.e dark
        mode).

        service - The interface is activated but alarms
        are suppressed. Intended for use during service
        or re-configuration. When service is concluded
        adminStatus should be set to 'up' again.

        up - The interface should be activated when
        it becomes available. Alarms are not suppressed.

        This attribute can be written via SNMP.

"
    DEFVAL { down }
    ::= { roadmAddDropIfEntry 9 }

roadmAddDropIfOperStatus OBJECT-TYPE
    SYNTAX      BoardOrInterfaceOperStatus
    MAX-ACCESS  read-only
    STATUS      current
    DESCRIPTION
        "The operational state for the interface.

        notPresent - The physical resources are not
        available.

        down - The interface is de-activated or the are
        faults preventing it from going to the 'up'-state.

        up - The interface is operational.

"
    DEFVAL { notPresent }
    ::= { roadmAddDropIfEntry 10 }

roadmAddDropIfTemperature OBJECT-TYPE
    SYNTAX      Integer32 (-1000..1000)
    MAX-ACCESS  read-only
    STATUS      current
    DESCRIPTION
        "The temperature in the add/drop module in 0.1 degrees centigrade.

"
    ::= { roadmAddDropIfEntry 11 }

roadmAddDropIfDropFrequencyMin OBJECT-TYPE
    SYNTAX      LambdaFrequency
    MAX-ACCESS  read-only
    STATUS      current
    DESCRIPTION
        "Lowest added channel in hundreds of
        GHz (0.01 GHz).

        Supported range 19185 ... 19598 (ch9185 .. ch958)

        This attribute can be written via SNMP.
"
    DEFVAL { undefined }
    ::= { roadmAddDropIfEntry 12 }

roadmAddDropIfDropFrequencyMax OBJECT-TYPE
    SYNTAX      LambdaFrequency
    MAX-ACCESS  read-only
    STATUS      current
    DESCRIPTION
        "Highest added channel in hundreds of
        GHz (0.01 GHz).

        Supported range 19185 ... 19580 (ch9185 .. ch958)

        This attribute can be written via SNMP.
"
    DEFVAL { undefined }
    ::= { roadmAddDropIfEntry 13 }

roadmAddDropIfObjectProperty  OBJECT-TYPE
    SYNTAX      ObjectProperty
    MAX-ACCESS  read-only
    STATUS      current
    DESCRIPTION
        "Property mask.

"
    ::= { roadmAddDropIfEntry 14 }

roadmAddDropIfConfigurationCommand OBJECT-TYPE
    SYNTAX      CommandString
    MAX-ACCESS  read-only
    STATUS      current
    DESCRIPTION
        "Configure the drop frequencies.

        Express mode - All the channels will go through the express port
        of the drop section (Ext Tx). No channels will go through the
        drop port (A/D Tx).

        Drop mode - The channels between min and max frequency will
        go through the drop port (A/D Tx). The rest of the channels will
        go through the express port of the drop section (Ext Tx).Up to
        eight (15 if 50 GHz spacing is used) channels are possible to drop.

        Example: Drop mode with min frequency set to ch931 and max frequency
        set to ch933, will send the channels ch931, ch932 and ch933 through
        the drop port.

"
    ::= { roadmAddDropIfEntry 15 }

roadmAddDropIfModuleFailure OBJECT-TYPE
    SYNTAX      FaultStatus
    MAX-ACCESS  read-only
    STATUS      current
    DESCRIPTION
        "The module HW has detected a failure.

        A: The module has failed

        D: The module is OK again

"
    ::= { roadmAddDropIfEntry 16 }

roadmAddDropIfTxSignalStatus OBJECT-TYPE
    SYNTAX      INTEGER {
                        down (1),
                        degraded (2),
                        up (3) }
    MAX-ACCESS  read-only
    STATUS      current
    DESCRIPTION
        "The operational state for the dropped (TX) signal
        of the interface.

        down - The signal is turned off.

        degraded - The signal quality is impaired.

        up - The signal is OK.

"
    ::= { roadmAddDropIfEntry 17 }

roadmAddDropIfMode OBJECT-TYPE
    SYNTAX      INTEGER {
                    express (1),
		    drop (2) }
    MAX-ACCESS  read-only
    STATUS      current
    DESCRIPTION
        "The drop mode for the interface.

	express - No wavelengths are dropped.

	drop - Up to eight (15 if 50 GHz spacing is used) channels are possible to drop.

        This attribute can be written via SNMP.
"
    DEFVAL { express }
    ::= { roadmAddDropIfEntry 18 }

roadmAddDropIfDescr2 OBJECT-TYPE
    SYNTAX      DisplayString
    MAX-ACCESS  read-write
    STATUS      current
    DESCRIPTION
        "User configurable label.

        This attribute can be written via SNMP.
"
    DEFVAL { "" }
    ::= { roadmAddDropIfEntry 19 }

roadmAddDropIfSpacingMode OBJECT-TYPE
    SYNTAX      INTEGER {
                        spacing100GHz (1),
                        spacing50GHz (2) }
    MAX-ACCESS  read-only
    STATUS      current
    DESCRIPTION
        "The spacing mode of the interface.

         spacing100GHz: Only 100GHz channels are available
         as drop frequencies.

         spacing50GHz: Both 50GHz and 100GHz channels are
         available as drop frequencies.
"
    DEFVAL { spacing100GHz }
    ::= { roadmAddDropIfEntry 20 }

roadmAddDropIfGuardChannel1 OBJECT-TYPE
    SYNTAX      LambdaFrequency
    MAX-ACCESS  read-only
    STATUS      current
    DESCRIPTION
        "When 50GHz spacing is used, the channel before the
        minDropFrequency cannot be used for express traffic.
        This channel is considered as a guard channel.
"
    DEFVAL { undefined }
    ::= { roadmAddDropIfEntry 21 }

roadmAddDropIfGuardChannel2 OBJECT-TYPE
    SYNTAX      LambdaFrequency
    MAX-ACCESS  read-only
    STATUS      current
    DESCRIPTION
        "When 50GHz spacing is used, the channel after the
        maxDropFrequency cannot be used for express traffic.
        This channel is considered as a guard channel.
"
    DEFVAL { undefined }
    ::= { roadmAddDropIfEntry 22 }

roadmAddDropIfDropFrequencyLimitMin OBJECT-TYPE
    SYNTAX      LambdaFrequency
    MAX-ACCESS  read-create
    STATUS      current
    DESCRIPTION
        "When an Allocated Range is defined, it is not possible
        to add channels outside the range.

        The supported range is:
        roadm1x2G50:  [19185 .. 19580] (ch9185 .. ch958) 50GHz
        roadm1x4f:    [19185 .. 19580] (ch9185 .. ch958) 50GHz
        roadm1x2G100: [19190 .. 19580] (ch919 .. ch958) 100GHz
        roadm1x4G100: [19190 .. 19580] (ch919 .. ch958) 100GHz
        roadm1x8G50:  [19185 .. 19580] (ch9185 .. ch958) 50GHz
        mdu16cl50g:   [19185 .. 19580] (ch9185 .. ch958) 50GHz
        roadm1x9f:    [19185 .. 19580] (ch9185 .. ch958) 50GHz

"
    DEFVAL { undefined }
    ::= { roadmAddDropIfEntry 23 }

roadmAddDropIfDropFrequencyLimitMax OBJECT-TYPE
    SYNTAX      LambdaFrequency
    MAX-ACCESS  read-create
    STATUS      current
    DESCRIPTION
        "When an Allocated Channel Range is defined, it is not possible
        to add channels outside the range.

        The supported range is:
        roadm1x2G50:  [19185 .. 19580] (ch9185 .. ch958) 50GHz
        roadm1x4f:    [19185 .. 19580] (ch9185 .. ch958) 50GHz
        roadm1x2G100: [19190 .. 19580] (ch919 .. ch958) 100GHz
        roadm1x4G100: [19190 .. 19580] (ch919 .. ch958) 100GHz
        roadm1x8G50:  [19185 .. 19580] (ch9185 .. ch958) 50GHz
        mdu16cl50g:   [19185 .. 19580] (ch9185 .. ch958) 50GHz
        roadm1x9f:    [19185 .. 19580] (ch9185 .. ch958) 50GHz

"
    DEFVAL { undefined }
    ::= { roadmAddDropIfEntry 24 }

roadmAddDropIfLimitConfigurationCommand OBJECT-TYPE
    SYNTAX      CommandString
    MAX-ACCESS  read-only
    STATUS      current
    DESCRIPTION
        "When an Allocated Channel Range is defined, it is not possible
        to add channels outside the range.
"
    ::= { roadmAddDropIfEntry 25 }

roadmAddDropIfGroupRoadmMode OBJECT-TYPE
    SYNTAX      INTEGER {
                        disabled (1),
                        enabled (2) }
    MAX-ACCESS  read-only
    STATUS      current
    DESCRIPTION
        "Indicates whether the interface is grouped
        into a ROADM-ROADM-group.

        disabled - The interface is not grouped into
        a ROADM-ROADM-group.

        enabled - The interface is grouped into a
        ROADM-ROADM-group.
"
    DEFVAL { disabled }
    ::= { roadmAddDropIfEntry 26 }

roadmAddDropIfPasswd OBJECT-TYPE
    SYNTAX      DisplayString
    MAX-ACCESS  read-create
    STATUS      current
    DESCRIPTION
        "Password protecting the Allocated Channel Range.

	If passwd is '-' (dash), then the password
        controll is disabled.

"
    DEFVAL { "-" }
    ::= { roadmAddDropIfEntry 27 }

roadmAddDropIfPasswdConfig OBJECT-TYPE
    SYNTAX      CommandString
    MAX-ACCESS  read-only
    STATUS      current
    DESCRIPTION
        "Change the password protecting the Allocated
        Channel Range.
"
    ::= { roadmAddDropIfEntry 28 }

roadmAddDropIfGroupLineMode OBJECT-TYPE
    SYNTAX      INTEGER {
                        disabled (1),
                        enabled (2) }
    MAX-ACCESS  read-only
    STATUS      current
    DESCRIPTION
        "Indicates whether the interface is grouped
        into a ROADM-TU-group.

        disabled - The interface is not grouped into
        a ROADM-TU-group.

        enabled - The interface is grouped into a
        ROADM-TU-group.
"
    DEFVAL { disabled }
    ::= { roadmAddDropIfEntry 29 }

roadmAddDropIfNoOfConnectedChannels OBJECT-TYPE
    SYNTAX      Unsigned32
    MAX-ACCESS  read-only
    STATUS      current
    DESCRIPTION
        "The number of channels connected to this port.

"
    ::= { roadmAddDropIfEntry 30 }


roadmAddDropIfViewChannelList OBJECT-TYPE
    SYNTAX      DisplayString
    MAX-ACCESS  read-only
    STATUS      current
    DESCRIPTION
        "Shows a list of all channels connected to this port.

         This attribute is only used for presentation.

"
    ::= { roadmAddDropIfEntry 31 }

roadmAddDropIfConnectedChannelMask OBJECT-TYPE
    SYNTAX      DisplayString
    MAX-ACCESS  read-create
    STATUS      current
    DESCRIPTION
        "Shows a list of all channels connected to this port.

        Format:
	'<start-freq>:<spacing>:<bit-mask>'

	 This is the actual storage of the cross-connect info.

"
    ::= { roadmAddDropIfEntry 32 }

roadmAddDropIfAddChannelCommand OBJECT-TYPE
    SYNTAX      CommandString
    MAX-ACCESS  read-only
    STATUS      current
    DESCRIPTION
        "Specify that a new channel shall be added
         from this port.

"
    ::= { roadmAddDropIfEntry 33 }

roadmAddDropIfUnlinkChannelCommand OBJECT-TYPE
    SYNTAX      CommandString
    MAX-ACCESS  read-only
    STATUS      current
    DESCRIPTION
        "Specify that a channel shall be removed
	 (disconnected) from this port.

"
    ::= { roadmAddDropIfEntry 34 }

roadmAddDropIfUnlinkAllChannelsCommand OBJECT-TYPE
    SYNTAX      CommandString
    MAX-ACCESS  read-only
    STATUS      current
    DESCRIPTION
        "Confirm that all channels shall be removed
	 (disconnected) from this port.

"
    ::= { roadmAddDropIfEntry 35 }

roadmAddDropIfSetAttenuationCommand OBJECT-TYPE
    SYNTAX      CommandString
    MAX-ACCESS  read-only
    STATUS      current
    DESCRIPTION
        "Set a fixed attenuation for channels connected
	to this port. Control-loop regulated channels
        are not affected.

        Range: 0 to 15.0 dB

"
    ::= { roadmAddDropIfEntry 36 }

roadmAddDropIfAdjustAttenuationDeltaCommand OBJECT-TYPE
    SYNTAX      CommandString
    MAX-ACCESS  read-only
    STATUS      current
    DESCRIPTION
        "Increase or decrease the attenuation for channels
         connected to this port. Control-loop regulated channels
	 are not affected.
         The resulting attenuation will always be within the allowed range for
         the channel even if a too big or small delta value is given.

"
    ::= { roadmAddDropIfEntry 37 }

roadmAddDropIfConnectChannelCmd OBJECT-TYPE
    SYNTAX      Unsigned32 (0..20000)
    MAX-ACCESS  read-write
    STATUS      current
    DESCRIPTION
        "This is a 'write-only' parameter that the
         TNM can use to cross-connect a new channel.

        When you read the parameter, you will get
        an integer value that is incremented each time
        a new valid command is issued.

"
        DEFVAL { 0 }
    ::= { roadmAddDropIfEntry 38 }

roadmAddDropIfDisconnectChannelCmd OBJECT-TYPE
    SYNTAX      Unsigned32 (0..20000)
    MAX-ACCESS  read-write
    STATUS      current
    DESCRIPTION
        "This is a 'write-only' parameter that the
         TNM can use to disconnect a channel.

        When you read the parameter, you will get
        an integer value that is incremented each time
        a new valid command is issued.

"
        DEFVAL { 0 }
    ::= { roadmAddDropIfEntry 39 }

roadmAddDropIfGroupIndex OBJECT-TYPE
    SYNTAX      Unsigned32
    MAX-ACCESS  read-only
    STATUS      current
    DESCRIPTION
        "The index of the associated ROADM-group, if any.
         If no group is created, it is set to 0

"
    ::= { roadmAddDropIfEntry 40 }

roadmAddDropIfAddAllChannelCommand OBJECT-TYPE
    SYNTAX      CommandString
    MAX-ACCESS  read-only
    STATUS      current
    DESCRIPTION
        "All available channels shall be added
         from this port.

"
    ::= { roadmAddDropIfEntry 41 }

roadmAddDropIfSetAdminStatusCommand OBJECT-TYPE
    SYNTAX      CommandString
    MAX-ACCESS  read-only
    STATUS      current
    DESCRIPTION
        "Set administrative status for channels that are
        connected to this port.
        Control-loop regulated channels are not affected.

"
    ::= { roadmAddDropIfEntry 42 }

roadmAddDropIfSpacingHwCapability OBJECT-TYPE
    SYNTAX      INTEGER {
                        spacingHwCap100GHz (1),
                        spacingHwCap50GHz  (2),
			spacingHwCapFlex125 (3)}
    MAX-ACCESS  read-only
    STATUS      current
    DESCRIPTION
        "The hardware capability of the interface used when deciding whether
        an interface is compatible with another interface and thereby can
        form a ROADM-ROADM group

	spacingHwCap100GHz: interface with channels in 100 GHz intervals

        spacingHwCap50GHz: interface with channels in 50 GHz intervals

        spacingHwCapFlex125: flexgrid interface with minimum interval width 12.5 GHz

"
    DEFVAL { spacingHwCap100GHz }
    ::= { roadmAddDropIfEntry 43 }

-- ----------------------------------------------------
-- Line interfaces
-- ----------------------------------------------------

roadmLineIfTable  OBJECT-TYPE
    SYNTAX      SEQUENCE OF RoadmLineIfEntry
    MAX-ACCESS  not-accessible
    STATUS      current
    DESCRIPTION
        "The interface list."
    ::= { roadmLineIfList 1 }

roadmLineIfEntry OBJECT-TYPE
    SYNTAX      RoadmLineIfEntry
    MAX-ACCESS  not-accessible
    STATUS      current
    DESCRIPTION
        "An entry in the interface list.

"
    INDEX { roadmLineIfIndex }
    ::= { roadmLineIfTable 1 }

RoadmLineIfEntry ::=
    SEQUENCE {
        roadmLineIfIndex                       Unsigned32,
        roadmLineIfName                        MgmtNameString,
        roadmLineIfDescr                       DisplayString,
        roadmLineIfSubrack                     SubrackNumber,
        roadmLineIfSlot                        SlotNumber,
        roadmLineIfTxPort                      PortNumber,
        roadmLineIfRxPort                      PortNumber,
        roadmLineIfInvPhysIndexOrZero          Unsigned32,
        roadmLineIfAdminStatus                 INTEGER,
        roadmLineIfOperStatus                  BoardOrInterfaceOperStatus,
	roadmLineIfObjectProperty	       ObjectProperty,
        roadmLineIfTxSignalStatus              INTEGER,
	roadmLineIfNoOfConnectedChannels          Unsigned32,
	roadmLineIfViewChannelList             DisplayString,
	roadmLineIfSetAttenuationCommand       CommandString,
	roadmLineIfAdjustAttenuationDeltaCommand  CommandString,
	roadmLineIfMonitorInsertionLoss        Unsigned32,
	roadmLineIfSetAdminStatusCommand       CommandString}

roadmLineIfIndex OBJECT-TYPE
    SYNTAX      Unsigned32 (1..2147483647)
    MAX-ACCESS  read-only
    STATUS      current
    DESCRIPTION
        "An arbitrary index assigned to each entry.

"
    ::= { roadmLineIfEntry 1 }

roadmLineIfName OBJECT-TYPE
    SYNTAX      MgmtNameString
    MAX-ACCESS  read-only
    STATUS      current
    DESCRIPTION
        "The management name of the interface, for
        example 'roadmLine:1:2:1-2', where the first number
        indicates sub-rack, the second slot number and
        the third is the port number.
        Examples:

        roadmLine:s:s:p - line interface

"
    ::= { roadmLineIfEntry 2 }

roadmLineIfDescr OBJECT-TYPE
    SYNTAX      DisplayString
    MAX-ACCESS  read-write
    STATUS      current
    DESCRIPTION
        "User configurable label.

        This attribute can be written via SNMP.
"
    DEFVAL { "" }
    ::= { roadmLineIfEntry 3 }

roadmLineIfSubrack OBJECT-TYPE
    SYNTAX      SubrackNumber
    MAX-ACCESS  read-create
    STATUS      current
    DESCRIPTION
        "The number of the subrack where the interface
        is located.

"
    ::= { roadmLineIfEntry 4 }

roadmLineIfSlot OBJECT-TYPE
    SYNTAX      SlotNumber
    MAX-ACCESS  read-create
    STATUS      current
    DESCRIPTION
        "The number of the slot where the interface is
        located.

"
    ::= { roadmLineIfEntry 5 }

roadmLineIfTxPort OBJECT-TYPE
    SYNTAX      PortNumber
    MAX-ACCESS  read-create
    STATUS      current
    DESCRIPTION
        "The number of the port where the TX-side of the
        interface is located.

"
    ::= { roadmLineIfEntry 6 }

roadmLineIfRxPort OBJECT-TYPE
    SYNTAX      PortNumber
    MAX-ACCESS  read-create
    STATUS      current
    DESCRIPTION
        "The number of the port where the RX-side of
        the interface is located.

"
    ::= { roadmLineIfEntry 7 }

roadmLineIfInvPhysIndexOrZero OBJECT-TYPE
    SYNTAX      Unsigned32 (0..2147483647)
    MAX-ACCESS  read-only
    STATUS      current
    DESCRIPTION
        "The row in the invPhysTable for this interface.
        Set to 0 if not known.

"
    ::= { roadmLineIfEntry 8 }

roadmLineIfAdminStatus OBJECT-TYPE
    SYNTAX      BoardOrInterfaceAdminStatus
    MAX-ACCESS  read-write
    STATUS      current
    DESCRIPTION
        "The administrative state for the interface.

        down - The interface should be inactive.

        service - The interface is activated but alarms
        are suppressed. Intended for use during service
        or re-configuration. When service is concluded
        adminStatus should be set to 'up' again.

        up - The interface should be activated when
        it becomes available. Alarms are not suppressed.

        This attribute can be written via SNMP.
"
    DEFVAL { up }
    ::= { roadmLineIfEntry 9 }

roadmLineIfOperStatus OBJECT-TYPE
    SYNTAX      BoardOrInterfaceOperStatus
    MAX-ACCESS  read-only
    STATUS      current
    DESCRIPTION
        "The operational state for the interface.

        notPresent - The physical resources are not
        available.

        down - The interface is de-activated or the are
        faults preventing it from going to the 'up'-state.

        up - The interface is operational.

"
    DEFVAL { notPresent }
    ::= { roadmLineIfEntry 10 }

roadmLineIfObjectProperty  OBJECT-TYPE
    SYNTAX      ObjectProperty
    MAX-ACCESS  read-only
    STATUS      current
    DESCRIPTION
        "Property mask.

"
    ::= { roadmLineIfEntry 11 }

roadmLineIfTxSignalStatus OBJECT-TYPE
    SYNTAX      INTEGER {
                        down (1),
                        degraded (2),
                        up (3) }
    MAX-ACCESS  read-only
    STATUS      current
    DESCRIPTION
        "The operational state for outgoing (TX) signal
        of the interface.

        down - The signal is turned off.

        degraded - The signal quality is impaired.

        up - The signal is OK.

"
    ::= { roadmLineIfEntry 12 }

roadmLineIfNoOfConnectedChannels OBJECT-TYPE
    SYNTAX      Unsigned32
    MAX-ACCESS  read-only
    STATUS      current
    DESCRIPTION
        "The number of channels connected to this port.

"
    ::= { roadmLineIfEntry 13 }

roadmLineIfViewChannelList OBJECT-TYPE
    SYNTAX      DisplayString
    MAX-ACCESS  read-only
    STATUS      current
    DESCRIPTION
        "Shows a list of all channels connected to any
         add/drop port.

"
    ::= { roadmLineIfEntry 14 }

roadmLineIfSetAttenuationCommand OBJECT-TYPE
    SYNTAX      CommandString
    MAX-ACCESS  read-only
    STATUS      current
    DESCRIPTION
        "Set a fixed attenuation for channels connected to
	this port. Control-loop regulated channels
        are not affected.

        Range: 0 to 15.0 dB

"
    ::= { roadmLineIfEntry 15 }

roadmLineIfAdjustAttenuationDeltaCommand OBJECT-TYPE
    SYNTAX      CommandString
    MAX-ACCESS  read-only
    STATUS      current
    DESCRIPTION
        "Increase or decrease the attenuation for channels
         connected to this port. Control-loop regulated channels
	 are not affected.

         Range: -15.0 to 15.0 dB

"
    ::= { roadmLineIfEntry 16 }

roadmLineIfMonitorInsertionLoss OBJECT-TYPE
    SYNTAX      Unsigned32
    MAX-ACCESS  read-only
    STATUS      current
    DESCRIPTION
        "The insertion loss for the monitor port.

"
    ::= { roadmLineIfEntry 17 }

roadmLineIfSetAdminStatusCommand OBJECT-TYPE
    SYNTAX      CommandString
    MAX-ACCESS  read-only
    STATUS      current
    DESCRIPTION
        "Set administrative status for channels that are
        connected to this port.
        Control-loop regulated channels are not affected.

"
    ::= { roadmLineIfEntry 18 }

-- ----------------------------------------------------
-- Group definitions
-- ----------------------------------------------------

roadmGroupRoadmTable  OBJECT-TYPE
    SYNTAX      SEQUENCE OF RoadmGroupRoadmEntry
    MAX-ACCESS  not-accessible
    STATUS      current
    DESCRIPTION
        "The roadm group table."
    ::= { roadmGroupRoadmList 1 }

roadmGroupRoadmEntry OBJECT-TYPE
    SYNTAX      RoadmGroupRoadmEntry
    MAX-ACCESS  not-accessible
    STATUS      current
    DESCRIPTION
        "An entry in the roadm group table.
"
    INDEX { roadmGroupRoadmIndex }
    ::= { roadmGroupRoadmTable 1 }

RoadmGroupRoadmEntry ::=
    SEQUENCE {
	roadmGroupRoadmIndex			Unsigned32,
	roadmGroupRoadmName 			MgmtNameString,
	roadmGroupRoadmDescr			DisplayString,
	roadmGroupRoadmRightSubrack 		SubrackNumber,
	roadmGroupRoadmRightSlot		SlotNumber,
	roadmGroupRoadmRightPort		PortNumber,
	roadmGroupRoadmLeftSubrack 		SubrackNumber,
	roadmGroupRoadmLeftSlot  		SlotNumber,
	roadmGroupRoadmLeftPort         	PortNumber,
	roadmGroupRoadmAdminStatus		BoardOrInterfaceAdminStatus,
	roadmGroupRoadmObjectProperty           ObjectProperty,
	roadmGroupRoadmDataAdminStatus  	INTEGER,
	roadmGroupRoadmDataDropFrequencyMin	LambdaFrequency,
	roadmGroupRoadmDataDropFrequencyMax	LambdaFrequency,
	roadmGroupRoadmDataDropFrequencyLimitMin	LambdaFrequency,
	roadmGroupRoadmDataDropFrequencyLimitMax	LambdaFrequency,
	roadmGroupRoadmDataMode	         	INTEGER,
	roadmGroupRoadmDataSpacingMode  	INTEGER,
	roadmGroupRoadmConfigurationCommand	CommandString,
	roadmGroupRoadmLimitConfigurationCommand CommandString,
	roadmGroupRoadmPasswd	    	        DisplayString,
	roadmGroupRoadmPasswdConfig	        CommandString,
        roadmGroupRoadmDataGuardChannel1        LambdaFrequency,
        roadmGroupRoadmDataGuardChannel2        LambdaFrequency,
	roadmGroupRoadmNoOfConnectedChannels       Unsigned32,
	roadmGroupRoadmViewChannelList             DisplayString,
	roadmGroupRoadmConnectedChannelMask        DisplayString,
	roadmGroupRoadmAddChannelCommand           CommandString,
	roadmGroupRoadmUnlinkChannelCommand        CommandString,
	roadmGroupRoadmUnlinkAllChannelsCommand    CommandString,
        roadmGroupRoadmConnectChannelCmd           Unsigned32,
        roadmGroupRoadmDisconnectChannelCmd        Unsigned32,
	roadmGroupRoadmAddAllChannelCommand           CommandString}

roadmGroupRoadmIndex OBJECT-TYPE
    SYNTAX      Unsigned32 (1..2147483647)
    MAX-ACCESS  read-only
    STATUS      current
    DESCRIPTION
        "An arbitrary index assigned to each entry.

"
    ::= { roadmGroupRoadmEntry 1 }

roadmGroupRoadmName OBJECT-TYPE
    SYNTAX      MgmtNameString
    MAX-ACCESS  read-only
    STATUS      current
    DESCRIPTION
	"The name of the object, for example
	'roadm:1:2:1:1:3:1', where the numbers indicate the
	subrack, slot and TX port number for the left and
	right add-drop interfaces of the group.

	Both left and right interfaces are add-drop interfaces.

"
    DEFVAL { "" }
    ::= { roadmGroupRoadmEntry 2 }

roadmGroupRoadmDescr OBJECT-TYPE
    SYNTAX      DisplayString
    MAX-ACCESS  read-write
    STATUS      current
    DESCRIPTION
        "User configurable label.

"
    DEFVAL { "" }
    ::= { roadmGroupRoadmEntry 3 }

roadmGroupRoadmRightSubrack OBJECT-TYPE
    SYNTAX      SubrackNumber
    MAX-ACCESS  read-create
    STATUS      current
    DESCRIPTION
        "The subrack number for the right add-drop
        interface.

"
    DEFVAL { 0 }
    ::= { roadmGroupRoadmEntry 4 }

roadmGroupRoadmRightSlot OBJECT-TYPE
    SYNTAX      SlotNumber
    MAX-ACCESS  read-create
    STATUS      current
    DESCRIPTION
        "The slot number for the right add-drop
        interface.

"
    DEFVAL { 0 }
    ::= { roadmGroupRoadmEntry 5 }

roadmGroupRoadmRightPort OBJECT-TYPE
    SYNTAX      PortNumber
    MAX-ACCESS  read-create
    STATUS      current
    DESCRIPTION
        "The port number for the TX side of the right
        add-drop interface.

"
    DEFVAL { 0 }
    ::= { roadmGroupRoadmEntry 6 }

roadmGroupRoadmLeftSubrack OBJECT-TYPE
    SYNTAX      SubrackNumber
    MAX-ACCESS  read-create
    STATUS      current
    DESCRIPTION
        "The subrack number for the left add-drop
        interface.

"
    DEFVAL { 0 }
    ::= { roadmGroupRoadmEntry 7 }

roadmGroupRoadmLeftSlot OBJECT-TYPE
    SYNTAX      SlotNumber
    MAX-ACCESS  read-create
    STATUS      current
    DESCRIPTION
        "The slot number for the left add-drop
        interface.

"
    DEFVAL { 0 }
    ::= { roadmGroupRoadmEntry 8 }

roadmGroupRoadmLeftPort OBJECT-TYPE
    SYNTAX      PortNumber
    MAX-ACCESS  read-create
    STATUS      current
    DESCRIPTION
        "The port number for the TX side of the left
        add-drop interface.

"
    DEFVAL { 0 }
    ::= { roadmGroupRoadmEntry 9 }

roadmGroupRoadmAdminStatus OBJECT-TYPE
    SYNTAX      BoardOrInterfaceAdminStatus
    MAX-ACCESS  read-write
    STATUS      current
    DESCRIPTION
        "The administrative state for the interface.

        down - The interface should be inactive.

        service - The interface is activated but alarms
        are suppressed. Intended for use during service
        or re-configuration. When service is concluded
        adminStatus should be set to 'up' again.

        up - The interface should be activated when
        it becomes available. Alarms are not suppressed.

	This attribute can be written via SNMP.

"
    DEFVAL { down }
    ::= { roadmGroupRoadmEntry 11 }

roadmGroupRoadmObjectProperty OBJECT-TYPE
    SYNTAX      ObjectProperty
    MAX-ACCESS  read-only
    STATUS      current
    DESCRIPTION
        "Property mask.

"
    ::= { roadmGroupRoadmEntry 12 }

roadmGroupRoadmDataAdminStatus OBJECT-TYPE
    SYNTAX      BoardOrInterfaceAdminStatus
    MAX-ACCESS  read-write
    STATUS      current
    DESCRIPTION
        "The administrative state for the master/slave add-
        drop interfaces.

        down - The interface should be inactive.

        service - The interface is activated but alarms
        are suppressed. Intended for use during service
        or re-configuration. When service is concluded
        adminStatus should be set to 'up' again.

        up - The interface should be activated when
        it becomes available. Alarms are not suppressed.

        This attribute can be written via SNMP.
"
    DEFVAL { up }
    ::= { roadmGroupRoadmEntry 14 }

roadmGroupRoadmDataDropFrequencyMin OBJECT-TYPE
    SYNTAX      LambdaFrequency
    MAX-ACCESS  read-only
    STATUS      current
    DESCRIPTION
        "Lowest added freqency in hundreds of GHz
        (0.01 GHz) for the master/slave add-drop
        interfaces.

        Supported range 19185 ... 19580 (ch9185 .. ch958)

        This attribute can be written via SNMP.
"
    DEFVAL { undefined }
    ::= { roadmGroupRoadmEntry 15 }

roadmGroupRoadmDataDropFrequencyMax OBJECT-TYPE
    SYNTAX      LambdaFrequency
    MAX-ACCESS  read-only
    STATUS      current
    DESCRIPTION
        "Highest added channel in hundreds of GHz
        (0.01 GHz)

        Supported range 19185 ... 19580 (ch9185 .. ch958)

        This attribute can be written via SNMP.
"
    DEFVAL { undefined }
    ::= { roadmGroupRoadmEntry 16 }

roadmGroupRoadmDataDropFrequencyLimitMin OBJECT-TYPE
    SYNTAX      LambdaFrequency
    MAX-ACCESS  read-create
    STATUS      current
    DESCRIPTION
        "When an Allocated Range is defined for the two
        add-drop interfaces, it is not possible
        to add channels outside the range.

        Supported range 19185 ... 19580 (ch9185 .. ch958)

        This attribute can be written via SNMP.
"
    DEFVAL { undefined }
    ::= { roadmGroupRoadmEntry 17 }

roadmGroupRoadmDataDropFrequencyLimitMax OBJECT-TYPE
    SYNTAX      LambdaFrequency
    MAX-ACCESS  read-create
    STATUS      current
    DESCRIPTION
        "When an Allocated Range is defined for the two
        add-drop interfaces, it is not possible
        to add channels outside the range.

        Supported range 19185 ... 19598 (ch9185 .. ch958)

	The highest dropped frequency can be set from
	the lowest dropped frequency up to next 7
	following frequencies.

        This attribute can be written via SNMP.
"
    DEFVAL { undefined }
    ::= { roadmGroupRoadmEntry 18 }

roadmGroupRoadmDataMode OBJECT-TYPE
    SYNTAX      INTEGER {
                    express (1),
		    drop (2) }
    MAX-ACCESS  read-create
    STATUS      current
    DESCRIPTION
        "The drop mode for the master/slave add-drop interface.

	express - No wavelengths are dropped.

	drop - Up to eight (15 if 50 GHz spacing is used) channels are possible to drop.

        This attribute can be written via SNMP.
"
    DEFVAL { express }
    ::= { roadmGroupRoadmEntry 19 }

roadmGroupRoadmDataSpacingMode OBJECT-TYPE
    SYNTAX      INTEGER {
                        spacing100GHz (1),
                        spacing50GHz (2) }
    MAX-ACCESS  read-create
    STATUS      current
    DESCRIPTION
        "The spacing mode of the add-drop interfaces.

        spacing100GHz: Only 100GHz channels are available
        as drop frequencies.

        spacing50GHz: Both 50GHz and 100GHz channels are
        available as drop frequencies.
"
    DEFVAL { spacing100GHz }
    ::= { roadmGroupRoadmEntry 20 }

roadmGroupRoadmConfigurationCommand OBJECT-TYPE
    SYNTAX      CommandString
    MAX-ACCESS  read-only
    STATUS      current
    DESCRIPTION
        "Configure the drop frequencies for the master/slave add-
        drop interfaces.

        Express mode - All the channels will go through the express port
        of the drop section (Ext Tx). No channels will go through the
        drop port (A/D Tx).

        Drop mode - The channels between min and max frequency will
        go through the drop port (A/D Tx). The rest of the channels will
        go through the express port of the drop section (Ext Tx). Up to
        eight (15 if 50 GHz spacing is used) channels are possible to drop.

        Example: Drop mode with min frequency set to ch931 and max frequency
        set to ch933, will send the channels ch931, ch932 and ch933 through
        the drop port.

"
    ::= { roadmGroupRoadmEntry 21 }

roadmGroupRoadmLimitConfigurationCommand OBJECT-TYPE
    SYNTAX      CommandString
    MAX-ACCESS  read-only
    STATUS      current
    DESCRIPTION
        "Configure the Allocated Channel Range for the two
        add-drop interfaces.
        When an Allocated Range is defined, it is not possible
        to add channels outside the range.

"
    ::= { roadmGroupRoadmEntry 22 }

roadmGroupRoadmPasswd OBJECT-TYPE
    SYNTAX      DisplayString
    MAX-ACCESS  read-create
    STATUS      current
    DESCRIPTION
        "Password protecting the Allocated Channel Range.

	If passwd is '-' (dash), then the password
        controll is disabled.

"
    DEFVAL { "" }
    ::= { roadmGroupRoadmEntry 23 }

roadmGroupRoadmPasswdConfig OBJECT-TYPE
    SYNTAX      CommandString
    MAX-ACCESS  read-only
    STATUS      current
    DESCRIPTION
        "Change the password protecting the Allocated
        Channel Range for the master/slave add-drop
        interfaces.

"
    ::= { roadmGroupRoadmEntry 24 }

roadmGroupRoadmDataGuardChannel1 OBJECT-TYPE
    SYNTAX      LambdaFrequency
    MAX-ACCESS  read-only
    STATUS      current
    DESCRIPTION
        "When 50GHz spacing is used, the channel before the
        minDropFrequency cannot be used for express traffic.
        This channel is considered as a guard channel.
"
    DEFVAL { undefined }
    ::= { roadmGroupRoadmEntry 25 }

roadmGroupRoadmDataGuardChannel2 OBJECT-TYPE
    SYNTAX      LambdaFrequency
    MAX-ACCESS  read-only
    STATUS      current
    DESCRIPTION
        "When 50GHz spacing is used, the channel after the
        maxDropFrequency cannot be used for express traffic.
        This channel is considered as a guard channel.
"
    DEFVAL { undefined }
    ::= { roadmGroupRoadmEntry 26 }

roadmGroupRoadmNoOfConnectedChannels OBJECT-TYPE
    SYNTAX      Unsigned32
    MAX-ACCESS  read-only
    STATUS      current
    DESCRIPTION
        "The number of channels connected to this group

"
    ::= { roadmGroupRoadmEntry 27 }


roadmGroupRoadmViewChannelList OBJECT-TYPE
    SYNTAX      DisplayString
    MAX-ACCESS  read-only
    STATUS      current
    DESCRIPTION
        "Shows a list of all channels connected to this group

         This attribute is only used for presentation.

"
    ::= { roadmGroupRoadmEntry 28 }

roadmGroupRoadmConnectedChannelMask OBJECT-TYPE
    SYNTAX      DisplayString
    MAX-ACCESS  read-create
    STATUS      current
    DESCRIPTION
        "Shows a list of all channels connected to this group

        Format:
	'<start-freq>:<spacing>:<bit-mask>'

	 This is the actual storage of the cross-connect info.

"
    ::= { roadmGroupRoadmEntry 29 }

roadmGroupRoadmAddChannelCommand OBJECT-TYPE
    SYNTAX      CommandString
    MAX-ACCESS  read-only
    STATUS      current
    DESCRIPTION
        "Specify that a new channel shall be added
         from this group.

"
    ::= { roadmGroupRoadmEntry 30 }

roadmGroupRoadmUnlinkChannelCommand OBJECT-TYPE
    SYNTAX      CommandString
    MAX-ACCESS  read-only
    STATUS      current
    DESCRIPTION
        "Specify that a channel shall be removed
	 (disconnected) from this group

"
    ::= { roadmGroupRoadmEntry 31 }

roadmGroupRoadmUnlinkAllChannelsCommand OBJECT-TYPE
    SYNTAX      CommandString
    MAX-ACCESS  read-only
    STATUS      current
    DESCRIPTION
        "Confirm that all channels shall be removed
	 (disconnected) from this group

"
    ::= { roadmGroupRoadmEntry 32 }

roadmGroupRoadmConnectChannelCmd OBJECT-TYPE
    SYNTAX      Unsigned32 (0..20000)
    MAX-ACCESS  read-write
    STATUS      current
    DESCRIPTION
        "This is a 'write-only' parameter that the
         TNM can use to cross-connect a new channel.

        When you read the parameter, you will get
        an integer value that is incremented each time
        a new valid command is issued.

"
        DEFVAL { 0 }
    ::= { roadmGroupRoadmEntry 33 }

roadmGroupRoadmDisconnectChannelCmd OBJECT-TYPE
    SYNTAX      Unsigned32 (0..20000)
    MAX-ACCESS  read-write
    STATUS      current
    DESCRIPTION
        "This is a 'write-only' parameter that the
         TNM can use to disconnect a channel.

        When you read the parameter, you will get
        an integer value that is incremented each time
        a new valid command is issued.

"
        DEFVAL { 0 }
    ::= { roadmGroupRoadmEntry 34 }

roadmGroupRoadmAddAllChannelCommand OBJECT-TYPE
    SYNTAX      CommandString
    MAX-ACCESS  read-only
    STATUS      current
    DESCRIPTION
        "All available channels shall be added
         to this group.

"
    ::= { roadmGroupRoadmEntry 35 }

-- ----------------------------------------------------
-- Line-Group definitions
-- ----------------------------------------------------

roadmGroupLineTable  OBJECT-TYPE
    SYNTAX      SEQUENCE OF RoadmGroupLineEntry
    MAX-ACCESS  not-accessible
    STATUS      current
    DESCRIPTION
        "The roadm-line group table."
    ::= { roadmGroupLineList 1 }

roadmGroupLineEntry OBJECT-TYPE
    SYNTAX      RoadmGroupLineEntry
    MAX-ACCESS  not-accessible
    STATUS      current
    DESCRIPTION
        "An entry in the roadm-line group table.
"
    INDEX { roadmGroupLineIndex }
    ::= { roadmGroupLineTable 1 }

RoadmGroupLineEntry ::=
    SEQUENCE {
	roadmGroupLineIndex	 	   Unsigned32,
	roadmGroupLineName 		   MgmtNameString,
	roadmGroupLineDescr		   DisplayString,
	roadmGroupLineSubrack 		   SubrackNumber,
	roadmGroupLineSlot		   SlotNumber,
	roadmGroupLinePort	  	   PortNumber,
	roadmGroupLineAdminStatus    	   BoardOrInterfaceAdminStatus,
	roadmGroupLineObjectProperty       ObjectProperty,
	roadmGroupLineCreateLineCommand    CommandString,
	roadmGroupLineDeleteLineCommand    CommandString,
	roadmGroupLineNoOfLines	 	   Unsigned32 }

roadmGroupLineIndex OBJECT-TYPE
    SYNTAX      Unsigned32 (1..2147483647)
    MAX-ACCESS  read-only
    STATUS      current
    DESCRIPTION
        "An arbitrary index assigned to each entry.

"
    ::= { roadmGroupLineEntry 1 }

roadmGroupLineName OBJECT-TYPE
    SYNTAX      MgmtNameString
    MAX-ACCESS  read-only
    STATUS      current
    DESCRIPTION
	"The name of the object, for example 'roadm:1:2:1',
        where the numbers indicate the subrack, slot and
        TX port number for the add-drop interface of the group.

"
    DEFVAL { "" }
    ::= { roadmGroupLineEntry 2 }

roadmGroupLineDescr OBJECT-TYPE
    SYNTAX      DisplayString
    MAX-ACCESS  read-write
    STATUS      current
    DESCRIPTION
        "User configurable label.

"
    DEFVAL { "" }
    ::= { roadmGroupLineEntry 3 }

roadmGroupLineSubrack OBJECT-TYPE
    SYNTAX      SubrackNumber
    MAX-ACCESS  read-create
    STATUS      current
    DESCRIPTION
        "The subrack number for the add-drop
        interface.

"
    DEFVAL { 0 }
    ::= { roadmGroupLineEntry 4 }

roadmGroupLineSlot OBJECT-TYPE
    SYNTAX      SlotNumber
    MAX-ACCESS  read-create
    STATUS      current
    DESCRIPTION
        "The slot number for the add-drop
        interface.

"
    DEFVAL { 0 }
    ::= { roadmGroupLineEntry 5 }

roadmGroupLinePort OBJECT-TYPE
    SYNTAX      PortNumber
    MAX-ACCESS  read-create
    STATUS      current
    DESCRIPTION
        "The port number for the TX side of the
        add-drop interface.

"
    DEFVAL { 0 }
    ::= { roadmGroupLineEntry 6 }

roadmGroupLineAdminStatus OBJECT-TYPE
    SYNTAX      BoardOrInterfaceAdminStatus
    MAX-ACCESS  read-only
    STATUS      current
    DESCRIPTION
        "The administrative state for the interface.

        down - The interface should be inactive. The ROADM add-drop
        interface and the line interface are working independently.

        service - The interface is activated but alarms are suppressed.
        Intended for use during service or re-configuration. When
        service is concluded adminStatus should be set to 'up' again.

        up - The interface should be activate. Alarms are not suppressed.
        All line interface belonging to this ROADM-line group are only
        allowed to transmit traffic if the channel matches the drop band
        of the add-drop interface.
        If ROADM add-drop interface is in express mode, the line interface
        are not allowed to transmit traffic.

"
    DEFVAL { up }
    ::= { roadmGroupLineEntry 7 }

roadmGroupLineObjectProperty OBJECT-TYPE
    SYNTAX      ObjectProperty
    MAX-ACCESS  read-only
    STATUS      current
    DESCRIPTION
        "Property mask.

"
    ::= { roadmGroupLineEntry 8 }

roadmGroupLineCreateLineCommand OBJECT-TYPE
    SYNTAX      CommandString
    MAX-ACCESS  read-only
    STATUS      current
    DESCRIPTION
        "Create a new line associated to the ROADM in the ROADM-line group.

	This will create an entry in the line table

"
    ::= { roadmGroupLineEntry 9 }

roadmGroupLineDeleteLineCommand OBJECT-TYPE
    SYNTAX      CommandString
    MAX-ACCESS  read-only
    STATUS      current
    DESCRIPTION
        "Delete a line from the ROADM-line group.

"
    ::= { roadmGroupLineEntry 10 }

roadmGroupLineNoOfLines OBJECT-TYPE
    SYNTAX      Unsigned32 (0..2000)
    MAX-ACCESS  read-only
    STATUS      current
    DESCRIPTION
        "The current number of lines associated to this ROADM-line group.

"
    DEFVAL { 0 }
    ::= { roadmGroupLineEntry 11 }

-- ----------------------------------------------------
-- Line definitions
-- ----------------------------------------------------

roadmLineTable  OBJECT-TYPE
    SYNTAX      SEQUENCE OF RoadmLineEntry
    MAX-ACCESS  not-accessible
    STATUS      current
    DESCRIPTION
        "The roadm-line table."
    ::= { roadmLineList 1 }

roadmLineEntry OBJECT-TYPE
    SYNTAX      RoadmLineEntry
    MAX-ACCESS  not-accessible
    STATUS      current
    DESCRIPTION
        "An entry in the roadm-line table.
"
    INDEX { roadmLineIndex }
    ::= { roadmLineTable 1 }

RoadmLineEntry ::=
    SEQUENCE {
	roadmLineIndex	 	   Unsigned32,
	roadmLineName 		   MgmtNameString,
	roadmLineDescr		   DisplayString,
	roadmLineSubrack 	   SubrackNumber,
	roadmLineSlot		   SlotNumber,
	roadmLinePort	  	   PortNumber,
	roadmLineObjectProperty    ObjectProperty,
	roadmLineGroupId           DisplayString,
        roadmLineFrequencyMismatch FaultStatus,
        roadmLineFrequencyUsed     FaultStatus,
        roadmLineAdminStatus       BoardOrInterfaceAdminStatus }

roadmLineIndex OBJECT-TYPE
    SYNTAX      Unsigned32 (1..2147483647)
    MAX-ACCESS  read-only
    STATUS      current
    DESCRIPTION
        "An arbitrary index assigned to each entry.

"
    ::= { roadmLineEntry 1 }

roadmLineName OBJECT-TYPE
    SYNTAX      MgmtNameString
    MAX-ACCESS  read-only
    STATUS      current
    DESCRIPTION
	"The name of the object, for example
	'line:1:2:3-4', where the numbers indicate the
	subrack, slot and TX port number for the line interface.

"
    DEFVAL { "" }
    ::= { roadmLineEntry 2 }

roadmLineDescr OBJECT-TYPE
    SYNTAX      DisplayString
    MAX-ACCESS  read-write
    STATUS      current
    DESCRIPTION
        "User configurable label.

"
    DEFVAL { "" }
    ::= { roadmLineEntry 3 }

roadmLineSubrack OBJECT-TYPE
    SYNTAX      SubrackNumber
    MAX-ACCESS  read-create
    STATUS      current
    DESCRIPTION
        "The subrack number for this line interface.

"
    DEFVAL { 0 }
    ::= { roadmLineEntry 4 }

roadmLineSlot OBJECT-TYPE
    SYNTAX      SlotNumber
    MAX-ACCESS  read-create
    STATUS      current
    DESCRIPTION
        "The slot number for this line interface.

"
    DEFVAL { 0 }
    ::= { roadmLineEntry 5 }

roadmLinePort OBJECT-TYPE
    SYNTAX      PortNumber
    MAX-ACCESS  read-create
    STATUS      current
    DESCRIPTION
        "The port number for the TX side of this line interface.

"
    DEFVAL { 0 }
    ::= { roadmLineEntry 6 }

roadmLineObjectProperty OBJECT-TYPE
    SYNTAX      ObjectProperty
    MAX-ACCESS  read-only
    STATUS      current
    DESCRIPTION
        "Property mask.

"
    ::= { roadmLineEntry 7 }

roadmLineGroupId OBJECT-TYPE
    SYNTAX      DisplayString
    MAX-ACCESS  read-create
    STATUS      current
    DESCRIPTION
        "The name of the ROADM-line group, to which this line
        interface belongs.

	Persistent cross-reference to ROADM-line group table

"
    ::= { roadmLineEntry 8 }

roadmLineFrequencyMismatch OBJECT-TYPE
    SYNTAX      FaultStatus
    MAX-ACCESS  read-only
    STATUS      current
    DESCRIPTION
        "Frequency mismatch.

        A: The actual frequency of the line interface of the
        traffic unit, is outside the drop frequency band of
        the ROADM.

        D: The actual frequency is within the drop frequency
        band.

"
    ::= { roadmLineEntry 9 }

roadmLineFrequencyUsed OBJECT-TYPE
    SYNTAX      FaultStatus
    MAX-ACCESS  read-only
    STATUS      current
    DESCRIPTION
        "Indicates whether the frequency is already used by another
        line in the ROADM-line group.

        A: The frequency is not unique within the ROADM-line group.

        D: The frequency is unique within the ROADM-line group.

"
    ::= { roadmLineEntry 10 }

roadmLineAdminStatus OBJECT-TYPE
    SYNTAX      BoardOrInterfaceAdminStatus
    MAX-ACCESS  read-write
    STATUS      current
    DESCRIPTION
        "The administrative state for the interface.

        down - The interface should be inactive (i.e dark
        mode).

        service - The interface is activated but alarms
        are suppressed. Intended for use during service
        or re-configuration. When service is concluded
        adminStatus should be set to 'up' again.

        up - The interface should be activated when
        it becomes available. Alarms are not suppressed.

        This attribute can be written via SNMP.
"
    DEFVAL { up }
    ::= { roadmLineEntry 11 }

-- ----------------------------------------------------
-- Roadm Channel definitions
-- ----------------------------------------------------

roadmChannelTable  OBJECT-TYPE
    SYNTAX      SEQUENCE OF RoadmChannelEntry
    MAX-ACCESS  not-accessible
    STATUS      current
    DESCRIPTION
        "The roadm channel table."
    ::= { roadmChannelList 1 }

roadmChannelEntry OBJECT-TYPE
    SYNTAX      RoadmChannelEntry
    MAX-ACCESS  not-accessible
    STATUS      current
    DESCRIPTION
        "An entry in the roadm channel table.
"
    INDEX { roadmChannelIndex }
    ::= { roadmChannelTable 1 }

RoadmChannelEntry ::=
    SEQUENCE {
	roadmChannelIndex	 	   Unsigned32,
	roadmChannelName 		   MgmtNameString,
	roadmChannelFrequency 		   LambdaFrequency,
	roadmChannelRoadmLineIfIndex       Unsigned32,
	roadmChannelRoadmAddDropIfIndex    Unsigned32,
	roadmChannelAdminStatus    	   BoardOrInterfaceAdminStatus,
        roadmChannelOperStatus             BoardOrInterfaceOperStatus,
	roadmChannelAttenuation            Unsigned32,
	roadmChannelConnectedToInterface   DisplayString,
	roadmChannelConnectDisconnectCommand         CommandString }

roadmChannelIndex OBJECT-TYPE
    SYNTAX      Unsigned32 (1..2147483647)
    MAX-ACCESS  read-only
    STATUS      current
    DESCRIPTION
        "An arbitrary index assigned to each entry.

"
    ::= { roadmChannelEntry 1 }

roadmChannelName OBJECT-TYPE
    SYNTAX      MgmtNameString
    MAX-ACCESS  read-only
    STATUS      current
    DESCRIPTION
	"The name of the object, for example 'roadm:1:2:1',
        where the numbers indicate the subrack, slot and
        TX port number for the add-drop interface of the group.

"
    DEFVAL { "" }
    ::= { roadmChannelEntry 2 }

roadmChannelFrequency OBJECT-TYPE
    SYNTAX      LambdaFrequency
    MAX-ACCESS  read-only
    STATUS      current
    DESCRIPTION
	"The frequncy of the channel.

"
    DEFVAL { 0 }
    ::= { roadmChannelEntry 3 }


roadmChannelRoadmLineIfIndex OBJECT-TYPE
    SYNTAX      Unsigned32 (1..2147483647)
    MAX-ACCESS  read-only
    STATUS      current
    DESCRIPTION
        "The index of the roadm line i/f carrying this
         channel.

"
    DEFVAL { 1 }
    ::= { roadmChannelEntry 4 }

roadmChannelRoadmAddDropIfIndex OBJECT-TYPE
    SYNTAX      Unsigned32 (0..2147483647)
    MAX-ACCESS  read-only
    STATUS      current
    DESCRIPTION
        "The index of the roadm add/drop i/f connected to this
         channel. Zero (0) if not connected.

"
    DEFVAL { 0 }
    ::= { roadmChannelEntry 5 }

roadmChannelAdminStatus OBJECT-TYPE
    SYNTAX      BoardOrInterfaceAdminStatus
    MAX-ACCESS  read-write
    STATUS      current
    DESCRIPTION
        "The administrative state for the channel.

        down - The channel is blocked, i.e. the cross
               connection to addDrop i/f removed.
	       The channel is blocked on the line.

        up - The channel can be used. If a cross connection
             to an addDrop i/f exists, it will be connected.

	This attribute can be written via SNMP.

"
    DEFVAL { up }
    ::= { roadmChannelEntry 6 }

roadmChannelOperStatus OBJECT-TYPE
    SYNTAX      BoardOrInterfaceOperStatus
    MAX-ACCESS  read-only
    STATUS      current
    DESCRIPTION
        "The operational state for the channel.

        notPresent - The physical resources are not
        available.

        down - The channel is de-activated or the are
        faults preventing it from going to the 'up'-state.

        up - The channel is operational.

"
    DEFVAL { notPresent }
    ::= { roadmChannelEntry 7 }

roadmChannelAttenuation OBJECT-TYPE
    SYNTAX      Unsigned32 (0..150)
    MAX-ACCESS  read-write
    STATUS      current
    DESCRIPTION
        "The additional attenuation applied to the channel excluding
        the insertion loss.

"
    DEFVAL { 150 }
    ::= { roadmChannelEntry 8 }

roadmChannelConnectedToInterface OBJECT-TYPE
    SYNTAX      DisplayString
    MAX-ACCESS  read-only
    STATUS      current
    DESCRIPTION
        "The name of the addDrop i/f conencted

"
    DEFVAL { "" }
    ::= { roadmChannelEntry 9 }

roadmChannelConnectDisconnectCommand OBJECT-TYPE
    SYNTAX      CommandString
    MAX-ACCESS  read-only
    STATUS      current
    DESCRIPTION
        "Connect the channel to an add/drop interface.

	 This command is not available in group mode.

"
    ::= { roadmChannelEntry 10 }


-- ----------------------------------------------------
-- Notifications
-- ----------------------------------------------------

-- n/a

-- ----------------------------------------------------
-- Object and event groups
-- ----------------------------------------------------

roadmGeneralGroup OBJECT-GROUP
    OBJECTS {
        roadmGeneralConfigLastChangeTime,
        roadmGeneralStateLastChangeTime,
	roadmGeneralRoadmLineIfTableSize,
	roadmGeneralRoadmAddDropIfTableSize }
    STATUS      deprecated
    DESCRIPTION
        "The general objects."
    ::= { lumRoadmGroups 1 }

roadmAddDropIfGroup OBJECT-GROUP
    OBJECTS {
        roadmAddDropIfIndex,
        roadmAddDropIfName,
        roadmAddDropIfDescr,
        roadmAddDropIfDescr2,
        roadmAddDropIfSubrack,
        roadmAddDropIfSlot,
        roadmAddDropIfTxPort,
        roadmAddDropIfRxPort,
        roadmAddDropIfInvPhysIndexOrZero,
        roadmAddDropIfAdminStatus,
        roadmAddDropIfOperStatus,
	roadmAddDropIfTemperature,
	roadmAddDropIfDropFrequencyMin,
	roadmAddDropIfDropFrequencyMax,
	roadmAddDropIfObjectProperty,
	roadmAddDropIfConfigurationCommand,
	roadmAddDropIfModuleFailure,
        roadmAddDropIfTxSignalStatus,
        roadmAddDropIfMode }
    STATUS      deprecated
    DESCRIPTION
        "The ROADM interface objects."
    ::= { lumRoadmGroups 2 }

roadmLineIfGroup OBJECT-GROUP
    OBJECTS {
        roadmLineIfIndex,
        roadmLineIfName,
        roadmLineIfDescr,
        roadmLineIfSubrack,
        roadmLineIfSlot,
        roadmLineIfTxPort,
        roadmLineIfRxPort,
        roadmLineIfInvPhysIndexOrZero,
        roadmLineIfAdminStatus,
        roadmLineIfOperStatus,
	roadmLineIfObjectProperty,
        roadmLineIfTxSignalStatus }
    STATUS      deprecated
    DESCRIPTION
        "The ROADM interface objects."
    ::= { lumRoadmGroups 3 }

roadmAddDropIfGroupV2 OBJECT-GROUP
    OBJECTS {
        roadmAddDropIfIndex,
        roadmAddDropIfName,
        roadmAddDropIfDescr,
        roadmAddDropIfDescr2,
        roadmAddDropIfSubrack,
        roadmAddDropIfSlot,
        roadmAddDropIfTxPort,
        roadmAddDropIfRxPort,
        roadmAddDropIfInvPhysIndexOrZero,
        roadmAddDropIfAdminStatus,
        roadmAddDropIfOperStatus,
	roadmAddDropIfTemperature,
	roadmAddDropIfDropFrequencyMin,
	roadmAddDropIfDropFrequencyMax,
	roadmAddDropIfObjectProperty,
	roadmAddDropIfConfigurationCommand,
	roadmAddDropIfModuleFailure,
        roadmAddDropIfTxSignalStatus,
        roadmAddDropIfMode,
        roadmAddDropIfSpacingMode,
        roadmAddDropIfGuardChannel1,
        roadmAddDropIfGuardChannel2,
        roadmAddDropIfDropFrequencyLimitMin,
        roadmAddDropIfDropFrequencyLimitMax,
	roadmAddDropIfLimitConfigurationCommand,
        roadmAddDropIfGroupRoadmMode,
        roadmAddDropIfPasswd,
        roadmAddDropIfPasswdConfig,
        roadmAddDropIfGroupLineMode }
    STATUS      deprecated
    DESCRIPTION
        "The ROADM interface objects."
    ::= { lumRoadmGroups 4 }

roadmGroupRoadmGroup OBJECT-GROUP
    OBJECTS {
        roadmGroupRoadmIndex,
        roadmGroupRoadmName,
        roadmGroupRoadmDescr,
        roadmGroupRoadmRightSubrack,
        roadmGroupRoadmRightSlot,
        roadmGroupRoadmRightPort,
        roadmGroupRoadmLeftSubrack,
        roadmGroupRoadmLeftSlot,
        roadmGroupRoadmLeftPort,
	roadmGroupRoadmAdminStatus,
	roadmGroupRoadmObjectProperty,
	roadmGroupRoadmDataAdminStatus,
	roadmGroupRoadmDataDropFrequencyMin,
	roadmGroupRoadmDataDropFrequencyMax,
	roadmGroupRoadmDataDropFrequencyLimitMin,
	roadmGroupRoadmDataDropFrequencyLimitMax,
	roadmGroupRoadmDataMode,
	roadmGroupRoadmDataSpacingMode,
	roadmGroupRoadmConfigurationCommand,
	roadmGroupRoadmLimitConfigurationCommand,
        roadmGroupRoadmPasswd,
        roadmGroupRoadmPasswdConfig,
        roadmGroupRoadmDataGuardChannel1,
        roadmGroupRoadmDataGuardChannel2 }
    STATUS      deprecated
    DESCRIPTION
        "The ROADM interface objects."
    ::= { lumRoadmGroups 5 }

roadmGeneralGroupV2 OBJECT-GROUP
    OBJECTS {
        roadmGeneralConfigLastChangeTime,
        roadmGeneralStateLastChangeTime,
	roadmGeneralRoadmLineIfTableSize,
	roadmGeneralRoadmAddDropIfTableSize,
	roadmGeneralRoadmGroupRoadmTableSize,
	roadmGeneralRoadmGroupLineTableSize,
	roadmGeneralRoadmLineTableSize }
    STATUS      deprecated
    DESCRIPTION
        "The general objects v2."
    ::= { lumRoadmGroups 6 }

roadmGroupLineGroup OBJECT-GROUP
    OBJECTS {
        roadmGroupLineIndex,
        roadmGroupLineName,
        roadmGroupLineDescr,
        roadmGroupLineSubrack,
        roadmGroupLineSlot,
        roadmGroupLinePort,
	roadmGroupLineAdminStatus,
	roadmGroupLineObjectProperty,
	roadmGroupLineCreateLineCommand,
	roadmGroupLineDeleteLineCommand,
        roadmGroupLineNoOfLines }
    STATUS      current
    DESCRIPTION
        "The ROADM Line Group objects."
    ::= { lumRoadmGroups 7 }

roadmLineGroup OBJECT-GROUP
    OBJECTS {
        roadmLineIndex,
        roadmLineName,
        roadmLineDescr,
        roadmLineSubrack,
        roadmLineSlot,
        roadmLinePort,
	roadmLineObjectProperty,
	roadmLineGroupId,
        roadmLineFrequencyMismatch,
        roadmLineFrequencyUsed,
        roadmLineAdminStatus }
    STATUS      current
    DESCRIPTION
        "The ROADM Line objects."
    ::= { lumRoadmGroups 8 }

roadmChannelGroup OBJECT-GROUP
    OBJECTS {
        roadmChannelIndex,
	roadmChannelName,
	roadmChannelFrequency,
	roadmChannelRoadmLineIfIndex,
	roadmChannelRoadmAddDropIfIndex,
	roadmChannelAdminStatus,
	roadmChannelOperStatus,
	roadmChannelAttenuation,
	roadmChannelConnectedToInterface,
	roadmChannelConnectDisconnectCommand
    }
    STATUS      current
    DESCRIPTION
        "The ROADM Channel objects. (12.0)"
    ::= { lumRoadmGroups 9 }

roadmAddDropIfGroupV3 OBJECT-GROUP
    OBJECTS {
        roadmAddDropIfIndex,
        roadmAddDropIfName,
        roadmAddDropIfDescr,
        roadmAddDropIfDescr2,
        roadmAddDropIfSubrack,
        roadmAddDropIfSlot,
        roadmAddDropIfTxPort,
        roadmAddDropIfRxPort,
        roadmAddDropIfInvPhysIndexOrZero,
        roadmAddDropIfAdminStatus,
        roadmAddDropIfOperStatus,
	roadmAddDropIfTemperature,
	roadmAddDropIfDropFrequencyMin,
	roadmAddDropIfDropFrequencyMax,
	roadmAddDropIfObjectProperty,
	roadmAddDropIfConfigurationCommand,
	roadmAddDropIfModuleFailure,
        roadmAddDropIfTxSignalStatus,
        roadmAddDropIfMode,
        roadmAddDropIfSpacingMode,
        roadmAddDropIfGuardChannel1,
        roadmAddDropIfGuardChannel2,
        roadmAddDropIfDropFrequencyLimitMin,
        roadmAddDropIfDropFrequencyLimitMax,
	roadmAddDropIfLimitConfigurationCommand,
        roadmAddDropIfGroupRoadmMode,
        roadmAddDropIfPasswd,
        roadmAddDropIfPasswdConfig,
        roadmAddDropIfGroupLineMode,
	roadmAddDropIfNoOfConnectedChannels,
	roadmAddDropIfViewChannelList,
	roadmAddDropIfConnectedChannelMask,
	roadmAddDropIfAddChannelCommand,
	roadmAddDropIfUnlinkChannelCommand,
	roadmAddDropIfUnlinkAllChannelsCommand,
	roadmAddDropIfSetAttenuationCommand,
	roadmAddDropIfAdjustAttenuationDeltaCommand,
        roadmAddDropIfConnectChannelCmd,
        roadmAddDropIfDisconnectChannelCmd,
        roadmAddDropIfGroupIndex
	}
    STATUS      deprecated
    DESCRIPTION
        "The ROADM interface objects. (12.0)"
    ::= { lumRoadmGroups 10 }

roadmLineIfGroupV2 OBJECT-GROUP
    OBJECTS {
        roadmLineIfIndex,
        roadmLineIfName,
        roadmLineIfDescr,
        roadmLineIfSubrack,
        roadmLineIfSlot,
        roadmLineIfTxPort,
        roadmLineIfRxPort,
        roadmLineIfInvPhysIndexOrZero,
        roadmLineIfAdminStatus,
        roadmLineIfOperStatus,
	roadmLineIfObjectProperty,
        roadmLineIfTxSignalStatus,
	roadmLineIfNoOfConnectedChannels,
	roadmLineIfViewChannelList,
	roadmLineIfSetAttenuationCommand,
	roadmLineIfAdjustAttenuationDeltaCommand,
	roadmLineIfMonitorInsertionLoss
	 }
    STATUS      deprecated
    DESCRIPTION
        "The ROADM interface objects V2 (12.0)."
    ::= { lumRoadmGroups 11 }

roadmGroupRoadmGroupV2 OBJECT-GROUP
    OBJECTS {
        roadmGroupRoadmIndex,
        roadmGroupRoadmName,
        roadmGroupRoadmDescr,
        roadmGroupRoadmRightSubrack,
        roadmGroupRoadmRightSlot,
        roadmGroupRoadmRightPort,
        roadmGroupRoadmLeftSubrack,
        roadmGroupRoadmLeftSlot,
        roadmGroupRoadmLeftPort,
	roadmGroupRoadmAdminStatus,
	roadmGroupRoadmObjectProperty,
	roadmGroupRoadmDataAdminStatus,
	roadmGroupRoadmDataDropFrequencyMin,
	roadmGroupRoadmDataDropFrequencyMax,
	roadmGroupRoadmDataDropFrequencyLimitMin,
	roadmGroupRoadmDataDropFrequencyLimitMax,
	roadmGroupRoadmDataMode,
	roadmGroupRoadmDataSpacingMode,
	roadmGroupRoadmConfigurationCommand,
	roadmGroupRoadmLimitConfigurationCommand,
        roadmGroupRoadmPasswd,
        roadmGroupRoadmPasswdConfig,
        roadmGroupRoadmDataGuardChannel1,
        roadmGroupRoadmDataGuardChannel2,
	roadmGroupRoadmNoOfConnectedChannels,
	roadmGroupRoadmViewChannelList,
	roadmGroupRoadmConnectedChannelMask,
	roadmGroupRoadmAddChannelCommand,
	roadmGroupRoadmUnlinkChannelCommand,
	roadmGroupRoadmUnlinkAllChannelsCommand,
	roadmGroupRoadmConnectChannelCmd,
	roadmGroupRoadmDisconnectChannelCmd }
    STATUS      deprecated
    DESCRIPTION
        "The ROADM interface objects V2.(12.0)"
    ::= { lumRoadmGroups 12 }

roadmGeneralGroupV3 OBJECT-GROUP
    OBJECTS {
        roadmGeneralConfigLastChangeTime,
        roadmGeneralStateLastChangeTime,
	roadmGeneralRoadmLineIfTableSize,
	roadmGeneralRoadmAddDropIfTableSize,
	roadmGeneralRoadmGroupRoadmTableSize,
	roadmGeneralRoadmGroupLineTableSize,
	roadmGeneralRoadmLineTableSize,
	roadmGeneralChannelTableSize }
    STATUS      current
    DESCRIPTION
        "The general objects v3. (12.0)"
    ::= { lumRoadmGroups 13 }

roadmAddDropIfGroupV4 OBJECT-GROUP
    OBJECTS {
        roadmAddDropIfIndex,
        roadmAddDropIfName,
        roadmAddDropIfDescr,
        roadmAddDropIfDescr2,
        roadmAddDropIfSubrack,
        roadmAddDropIfSlot,
        roadmAddDropIfTxPort,
        roadmAddDropIfRxPort,
        roadmAddDropIfInvPhysIndexOrZero,
        roadmAddDropIfAdminStatus,
        roadmAddDropIfOperStatus,
	roadmAddDropIfTemperature,
	roadmAddDropIfDropFrequencyMin,
	roadmAddDropIfDropFrequencyMax,
	roadmAddDropIfObjectProperty,
	roadmAddDropIfConfigurationCommand,
	roadmAddDropIfModuleFailure,
        roadmAddDropIfTxSignalStatus,
        roadmAddDropIfMode,
        roadmAddDropIfSpacingMode,
        roadmAddDropIfGuardChannel1,
        roadmAddDropIfGuardChannel2,
        roadmAddDropIfDropFrequencyLimitMin,
        roadmAddDropIfDropFrequencyLimitMax,
	roadmAddDropIfLimitConfigurationCommand,
        roadmAddDropIfGroupRoadmMode,
        roadmAddDropIfPasswd,
        roadmAddDropIfPasswdConfig,
        roadmAddDropIfGroupLineMode,
	roadmAddDropIfNoOfConnectedChannels,
	roadmAddDropIfViewChannelList,
	roadmAddDropIfConnectedChannelMask,
	roadmAddDropIfAddChannelCommand,
	roadmAddDropIfUnlinkChannelCommand,
	roadmAddDropIfUnlinkAllChannelsCommand,
	roadmAddDropIfSetAttenuationCommand,
	roadmAddDropIfAdjustAttenuationDeltaCommand,
        roadmAddDropIfConnectChannelCmd,
        roadmAddDropIfDisconnectChannelCmd,
        roadmAddDropIfGroupIndex,
	roadmAddDropIfAddAllChannelCommand,
	roadmAddDropIfSetAdminStatusCommand
	}
    STATUS      deprecated
    DESCRIPTION
        "The ROADM interface objects v4. (15.0)"
    ::= { lumRoadmGroups 14 }

roadmGroupRoadmGroupV3 OBJECT-GROUP
    OBJECTS {
        roadmGroupRoadmIndex,
        roadmGroupRoadmName,
        roadmGroupRoadmDescr,
        roadmGroupRoadmRightSubrack,
        roadmGroupRoadmRightSlot,
        roadmGroupRoadmRightPort,
        roadmGroupRoadmLeftSubrack,
        roadmGroupRoadmLeftSlot,
        roadmGroupRoadmLeftPort,
	roadmGroupRoadmAdminStatus,
	roadmGroupRoadmObjectProperty,
	roadmGroupRoadmDataAdminStatus,
	roadmGroupRoadmDataDropFrequencyMin,
	roadmGroupRoadmDataDropFrequencyMax,
	roadmGroupRoadmDataDropFrequencyLimitMin,
	roadmGroupRoadmDataDropFrequencyLimitMax,
	roadmGroupRoadmDataMode,
	roadmGroupRoadmDataSpacingMode,
	roadmGroupRoadmConfigurationCommand,
	roadmGroupRoadmLimitConfigurationCommand,
        roadmGroupRoadmPasswd,
        roadmGroupRoadmPasswdConfig,
        roadmGroupRoadmDataGuardChannel1,
        roadmGroupRoadmDataGuardChannel2,
	roadmGroupRoadmNoOfConnectedChannels,
	roadmGroupRoadmViewChannelList,
	roadmGroupRoadmConnectedChannelMask,
	roadmGroupRoadmAddChannelCommand,
	roadmGroupRoadmUnlinkChannelCommand,
	roadmGroupRoadmUnlinkAllChannelsCommand,
	roadmGroupRoadmConnectChannelCmd,
	roadmGroupRoadmDisconnectChannelCmd,
	roadmGroupRoadmAddChannelCommand}
    STATUS      current
    DESCRIPTION
        "The ROADM interface objects V3.(15.0)"
    ::= { lumRoadmGroups 15 }

roadmLineIfGroupV3 OBJECT-GROUP
    OBJECTS {
        roadmLineIfIndex,
        roadmLineIfName,
        roadmLineIfDescr,
        roadmLineIfSubrack,
        roadmLineIfSlot,
        roadmLineIfTxPort,
        roadmLineIfRxPort,
        roadmLineIfInvPhysIndexOrZero,
        roadmLineIfAdminStatus,
        roadmLineIfOperStatus,
	roadmLineIfObjectProperty,
        roadmLineIfTxSignalStatus,
	roadmLineIfNoOfConnectedChannels,
	roadmLineIfViewChannelList,
	roadmLineIfSetAttenuationCommand,
	roadmLineIfAdjustAttenuationDeltaCommand,
	roadmLineIfMonitorInsertionLoss,
	roadmLineIfSetAdminStatusCommand
	}
    STATUS      current
    DESCRIPTION
        "The ROADM interface objects V3 (15.0)."
    ::= { lumRoadmGroups 16 }

roadmAddDropIfGroupV5 OBJECT-GROUP
    OBJECTS {
        roadmAddDropIfIndex,
        roadmAddDropIfName,
        roadmAddDropIfDescr,
        roadmAddDropIfDescr2,
        roadmAddDropIfSubrack,
        roadmAddDropIfSlot,
        roadmAddDropIfTxPort,
        roadmAddDropIfRxPort,
        roadmAddDropIfInvPhysIndexOrZero,
        roadmAddDropIfAdminStatus,
        roadmAddDropIfOperStatus,
        roadmAddDropIfTemperature,
        roadmAddDropIfDropFrequencyMin,
        roadmAddDropIfDropFrequencyMax,
        roadmAddDropIfObjectProperty,
        roadmAddDropIfConfigurationCommand,
	roadmAddDropIfModuleFailure,
        roadmAddDropIfTxSignalStatus,
        roadmAddDropIfMode,
        roadmAddDropIfSpacingMode,
        roadmAddDropIfGuardChannel1,
        roadmAddDropIfGuardChannel2,
        roadmAddDropIfDropFrequencyLimitMin,
        roadmAddDropIfDropFrequencyLimitMax,
        roadmAddDropIfLimitConfigurationCommand,
        roadmAddDropIfGroupRoadmMode,
        roadmAddDropIfPasswd,
        roadmAddDropIfPasswdConfig,
        roadmAddDropIfGroupLineMode,
        roadmAddDropIfNoOfConnectedChannels,
        roadmAddDropIfViewChannelList,
        roadmAddDropIfConnectedChannelMask,
        roadmAddDropIfAddChannelCommand,
        roadmAddDropIfUnlinkChannelCommand,
        roadmAddDropIfUnlinkAllChannelsCommand,
        roadmAddDropIfSetAttenuationCommand,
        roadmAddDropIfAdjustAttenuationDeltaCommand,
        roadmAddDropIfConnectChannelCmd,
        roadmAddDropIfDisconnectChannelCmd,
        roadmAddDropIfGroupIndex,
        roadmAddDropIfAddAllChannelCommand,
        roadmAddDropIfSetAdminStatusCommand,
        roadmAddDropIfSpacingHwCapability
        }
    STATUS      current
    DESCRIPTION
        "The ROADM interface objects v5. (28.0)"
    ::= { lumRoadmGroups 17 }

-- ----------------------------------------------------
-- Compliance
-- ----------------------------------------------------

lumRoadmBasicComplV1 MODULE-COMPLIANCE
    STATUS      deprecated
    DESCRIPTION
        "Basic implementation requirements for the ROADM MIB V1."
    MODULE
        MANDATORY-GROUPS {
            roadmGeneralGroup,
            roadmAddDropIfGroup,
            roadmLineIfGroup}
    ::= { lumRoadmCompl 1 }

lumRoadmBasicComplV2 MODULE-COMPLIANCE
    STATUS      deprecated
    DESCRIPTION
        "Basic implementation requirements for the ROADM MIB V2. (10.0)"
    MODULE
        MANDATORY-GROUPS {
            roadmGeneralGroupV2,
            roadmAddDropIfGroupV2,
            roadmLineIfGroup,
            roadmGroupRoadmGroup,
            roadmGroupLineGroup,
            roadmLineGroup}
    ::= { lumRoadmCompl 2 }

lumRoadmBasicComplV3 MODULE-COMPLIANCE
    STATUS      deprecated
    DESCRIPTION
        "Basic implementation requirements for the ROADM MIB V3. (12.0)"
    MODULE
        MANDATORY-GROUPS {
            roadmGeneralGroupV3,
            roadmAddDropIfGroupV3,
            roadmLineIfGroupV2,
            roadmGroupRoadmGroup,
            roadmGroupLineGroup,
            roadmLineGroup,
	    roadmChannelGroup}
    ::= { lumRoadmCompl 3 }

lumRoadmBasicComplV4 MODULE-COMPLIANCE
    STATUS      deprecated
    DESCRIPTION
        "Basic implementation requirements for the ROADM MIB V4. (14.0)"
    MODULE
        MANDATORY-GROUPS {
            roadmGeneralGroupV3,
            roadmAddDropIfGroupV3,
            roadmLineIfGroupV2,
            roadmGroupRoadmGroup,
            roadmGroupLineGroup,
            roadmLineGroup,
	    roadmChannelGroup}
    ::= { lumRoadmCompl 4 }

lumRoadmBasicComplV5 MODULE-COMPLIANCE
    STATUS      deprecated
    DESCRIPTION
        "Basic implementation requirements for the ROADM MIB V5. (15.0)"
    MODULE
        MANDATORY-GROUPS {
            roadmGeneralGroupV3,
            roadmAddDropIfGroupV3,
            roadmLineIfGroupV2,
            roadmGroupRoadmGroup,
            roadmGroupLineGroup,
            roadmLineGroup,
	    roadmChannelGroup}
    ::= { lumRoadmCompl 5 }


lumRoadmBasicComplV6 MODULE-COMPLIANCE
    STATUS      deprecated
    DESCRIPTION
        "Basic implementation requirements for the ROADM MIB V5. (15.0)"
    MODULE
        MANDATORY-GROUPS {
            roadmGeneralGroupV3,
            roadmAddDropIfGroupV4,
            roadmLineIfGroupV3,
            roadmGroupRoadmGroupV3,
            roadmGroupLineGroup,
            roadmLineGroup,
	    roadmChannelGroup}
    ::= { lumRoadmCompl 6 }

lumRoadmBasicComplV7 MODULE-COMPLIANCE
    STATUS      current
    DESCRIPTION
        "Basic implementation requirements for the ROADM MIB V7. (28.0)"
    MODULE
        MANDATORY-GROUPS {
            roadmGeneralGroupV3,
            roadmAddDropIfGroupV5,
            roadmLineIfGroupV3,
            roadmGroupRoadmGroupV3,
            roadmGroupLineGroup,
            roadmLineGroup,
	    roadmChannelGroup}
    ::= { lumRoadmCompl 7 }
END
