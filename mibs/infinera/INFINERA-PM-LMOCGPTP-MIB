-- *****************************************************************
-- INFINERA-PM-LMOCGPTP-MIB
--
-- October 2008, Sharfuddin Syed / Narendra Gupta
--
--
-- Copyright (c) 2011-2012 by Infinera Inc.
-- All rights reserved.
-- ****************************************************************

INFINERA-PM-LMOCGPTP-MIB DEFINITIONS ::= BEGIN

IMPORTS
    MODULE-IDENTITY, OBJECT-TYPE,
    Integer32                                   FROM SNMPv2-SMI
    MODULE-COMPLIANCE, OBJECT-GROUP             FROM SNMPv2-CONF
    DisplayString                               FROM SNMPv2-TC
    ifIndex                                     FROM IF-MIB
    FloatHundredths                             FROM INFINERA-TC-MIB
    perfMon                                     FROM INFINERA-REG-MIB;


lmOcgPtpPmMIB MODULE-IDENTITY
    LAST-UPDATED  "200810200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION      "200810200000Z"
    DESCRIPTION
        "First Version"
    ::= { perfMon 32 }



lmOcgPtpPmRealTable OBJECT-TYPE
    SYNTAX      SEQUENCE OF LmOcgPtpPmRealEntry
    MAX-ACCESS  not-accessible
    STATUS      current
    DESCRIPTION
        "A list of lmOcgPtpPmReal entries. Each entry is uniquely identified by the value of ifIndex."
    ::= { lmOcgPtpPmMIB 1 }

lmOcgPtpPmRealEntry  OBJECT-TYPE
    SYNTAX      LmOcgPtpPmRealEntry
    MAX-ACCESS  not-accessible
    STATUS      current
    DESCRIPTION
        "A lmOcgPtpPmReal entry containing real-time performance information pertaining to Infinera lmOcgPtp interfaces.
        This table is a subclass of IfCommon.
        Entries will exist in this table only for interfaces of type lmOcgPtp."
    INDEX { ifIndex }
    ::= { lmOcgPtpPmRealTable 1 }


LmOcgPtpPmRealEntry  ::= SEQUENCE {
    lmOcgPtpPmRealLmOcgOpt        FloatHundredths,
    lmOcgPtpPmRealLmOcgOpr        FloatHundredths,
    lmOcgPtpPmRealLmOcgTxEdfaOpr    FloatHundredths,
    lmOcgPtpPmRealLmOcgTxEdfaOpt    FloatHundredths,
    lmOcgPtpPmRealLmOcgTxEdfaLbc    FloatHundredths,
    lmOcgPtpPmRealLmOcgRxEdfaOpr    FloatHundredths,
    lmOcgPtpPmRealLmOcgRxEdfaOpt    FloatHundredths,
    lmOcgPtpPmRealLmOcgRxEdfaLbc    FloatHundredths,
    lmOcgPtpPmRealLmOcgPmd          FloatHundredths,
    lmOcgPtpPmRealLmOcgSoPmd        FloatHundredths
}

lmOcgPtpPmRealLmOcgOpt OBJECT-TYPE
    SYNTAX      FloatHundredths
    MAX-ACCESS  read-only
    STATUS      current
    DESCRIPTION "OCG optical power transmitted."
    ::= { lmOcgPtpPmRealEntry  1 }


lmOcgPtpPmRealLmOcgOpr OBJECT-TYPE
    SYNTAX      FloatHundredths
    MAX-ACCESS  read-only
    STATUS      current
    DESCRIPTION "OCG optical power received."
    ::= { lmOcgPtpPmRealEntry  2 }

lmOcgPtpPmRealLmOcgTxEdfaOpr OBJECT-TYPE
    SYNTAX      FloatHundredths
    MAX-ACCESS  read-only
    STATUS      current
    DESCRIPTION "."
    ::= { lmOcgPtpPmRealEntry  3 }

lmOcgPtpPmRealLmOcgTxEdfaOpt OBJECT-TYPE
    SYNTAX      FloatHundredths
    MAX-ACCESS  read-only
    STATUS      current
    DESCRIPTION ""
    ::= { lmOcgPtpPmRealEntry  4 }

lmOcgPtpPmRealLmOcgTxEdfaLbc OBJECT-TYPE
    SYNTAX      FloatHundredths
    MAX-ACCESS  read-only
    STATUS      current
    DESCRIPTION ""
    ::= { lmOcgPtpPmRealEntry  5 }

lmOcgPtpPmRealLmOcgRxEdfaOpr OBJECT-TYPE
    SYNTAX      FloatHundredths
    MAX-ACCESS  read-only
    STATUS      current
    DESCRIPTION ""
    ::= { lmOcgPtpPmRealEntry  6 }

lmOcgPtpPmRealLmOcgRxEdfaOpt OBJECT-TYPE
    SYNTAX      FloatHundredths
    MAX-ACCESS  read-only
    STATUS      current
    DESCRIPTION ""
    ::= { lmOcgPtpPmRealEntry  7 }

lmOcgPtpPmRealLmOcgRxEdfaLbc OBJECT-TYPE
    SYNTAX      FloatHundredths
    MAX-ACCESS  read-only
    STATUS      current
    DESCRIPTION ""
    ::= { lmOcgPtpPmRealEntry  8 }

lmOcgPtpPmRealLmOcgPmd OBJECT-TYPE
    SYNTAX      FloatHundredths
    MAX-ACCESS  read-only
    STATUS      current
    DESCRIPTION ""
    ::= { lmOcgPtpPmRealEntry  9 }

lmOcgPtpPmRealLmOcgSoPmd OBJECT-TYPE
    SYNTAX      FloatHundredths
    MAX-ACCESS  read-only
    STATUS      current
    DESCRIPTION ""
    ::= { lmOcgPtpPmRealEntry  10 }


-- Conformance Statements
lmOcgPtpPmConformance    OBJECT IDENTIFIER ::= { lmOcgPtpPmMIB 3 }
lmOcgPtpPmCompliances    OBJECT IDENTIFIER ::= { lmOcgPtpPmConformance 1 }
lmOcgPtpPmGroups         OBJECT IDENTIFIER ::= { lmOcgPtpPmConformance 2 }

lmOcgPtpPmRealCompliance MODULE-COMPLIANCE
    STATUS current
    DESCRIPTION
    "Describes the requirements for conformance to the PM-LMOCGPTP-MIB"
    MODULE
        MANDATORY-GROUPS { lmOcgPtpPmRealGroup }
    ::= { lmOcgPtpPmCompliances 1 }

lmOcgPtpPmRealGroup OBJECT-GROUP
    OBJECTS {
        lmOcgPtpPmRealLmOcgOpt,
        lmOcgPtpPmRealLmOcgOpr,
        lmOcgPtpPmRealLmOcgTxEdfaOpr,
        lmOcgPtpPmRealLmOcgTxEdfaOpt,
        lmOcgPtpPmRealLmOcgTxEdfaLbc,
        lmOcgPtpPmRealLmOcgRxEdfaOpr,
        lmOcgPtpPmRealLmOcgRxEdfaOpt,
        lmOcgPtpPmRealLmOcgRxEdfaLbc,
        lmOcgPtpPmRealLmOcgPmd,
        lmOcgPtpPmRealLmOcgSoPmd
    }
    STATUS current
    DESCRIPTION
        " A collection of objects for reading the current real-time performance of the lmOcgPtp."
    ::= { lmOcgPtpPmGroups 1 }


END
