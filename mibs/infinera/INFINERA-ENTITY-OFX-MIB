-- ***************************************************************
-- INFINERA-ENTITY-OFX-MIB
--
--
-- Copyright (c) 2011-2012 by Infinera Inc.
-- All rights reserved.
-- ****************************************************************

INFINERA-ENTITY-OFX-MIB DEFINITIONS ::= BEGIN

IMPORTS
    OBJECT-TYPE, MODULE-IDENTITY        	FROM SNMPv2-SMI
    OBJECT-GROUP, MODULE-COMPLIANCE     	FROM SNMPv2-CONF
    DisplayString            	            FROM SNMPv2-TC
    entLPPhysicalIndex                  	FROM ENTITY-MIB
    equipment                           	FROM INFINERA-REG-MIB
    InfnEqptType,InfnOtnOtuType,
	FloatTenths,InfnEnforcementMode,
	InfnLicenseModulationType           	FROM INFINERA-TC-MIB;

ofxMIB MODULE-IDENTITY
    LAST-UPDATED  "201110200000Z"
    ORGANIZATION "INFINERA"
    CONTACT-INFO
        "Infinera
        169 Java Drive
        Sunnyvale, CA - 94089

        Contact : Technical Support
        Email   : support@infinera.com
        Phone   : 1-877-INF-5288 "
        DESCRIPTION
        "This MIB is modeling for OFX equipment table"

::= { equipment 34 }

ofxConformance       OBJECT IDENTIFIER ::= { ofxMIB 3 }
ofxCompliances       OBJECT IDENTIFIER ::= { ofxConformance 1 }
ofxGroups            OBJECT IDENTIFIER ::= { ofxConformance 2 }

ofxTable  OBJECT-TYPE
    SYNTAX SEQUENCE OF OfxEntry
    MAX-ACCESS not-accessible
    STATUS     current
    DESCRIPTION
        "This table contains all OFX modules that are currently present in a network element.
        "
    ::= { ofxMIB 1 }

ofxEntry  OBJECT-TYPE
    SYNTAX     OfxEntry
    MAX-ACCESS not-accessible
    STATUS     current
    DESCRIPTION
        "A row in the OFX table. Each row in the table is identified with a unique entPhysicalIndexID."
    INDEX { entLPPhysicalIndex }
    ::= { ofxTable 1 }

OfxEntry ::= SEQUENCE {
   ofxMoId                                  DisplayString,
   ofxProvEqptType                          InfnEqptType,
   ofxOTNContainerRepresentation            InfnOtnOtuType,
   ofxActvTimingSource						DisplayString,
   ofxPicDspVer                             DisplayString,
   ofxMaxFruGain                            FloatTenths,
   ofxRxEdfaOutputPowerTarget               FloatTenths,
   ofxRxEdfaGain                            FloatTenths,
   ofxRecommendedGain                       FloatTenths,
   ofxBwQmax                                FloatTenths,
   ofxBwQused                               FloatTenths,
   ofxBwQlicensed                           FloatTenths,
   ofxBwBmax                                FloatTenths,
   ofxBwBused                               FloatTenths,
   ofxBwBlicensed                           FloatTenths,
   ofxLicensedServicesDisabled              Integer32,
   ofxLicenseEnforced                       InfnEnforcementMode,
   ofxDefFlexLicModFormat                   InfnLicenseModulationType,
   ofxBwUsgWaterMarkGranularity             FloatTenths,
   ofxAvailableTunableSuperChNumbers        DisplayString,
   ofxBw3Qmax                               FloatTenths,
   ofxBw3Qused                              FloatTenths,
   ofxBw3Qlicensed                          FloatTenths
}

ofxMoId     OBJECT-TYPE
    SYNTAX      DisplayString
    MAX-ACCESS  read-write
    STATUS      current
    DESCRIPTION ""
    ::= { ofxEntry 1 }

ofxProvEqptType     OBJECT-TYPE
    SYNTAX      InfnEqptType
    MAX-ACCESS  read-write
    STATUS      current
    DESCRIPTION ""
    ::= { ofxEntry 2 }

ofxOTNContainerRepresentation OBJECT-TYPE
    SYNTAX      InfnOtnOtuType
    MAX-ACCESS  read-write
    STATUS      current
    DESCRIPTION ""
    ::= { ofxEntry  3 }


ofxActvTimingSource OBJECT-TYPE
	SYNTAX     DisplayString
    MAX-ACCESS read-only
    STATUS     current
    DESCRIPTION ""
    ::= { ofxEntry 4 }

ofxPicDspVer    OBJECT-TYPE
    SYNTAX      DisplayString
    MAX-ACCESS  read-only
    STATUS      current
    DESCRIPTION ""
    ::= { ofxEntry  5 }

ofxMaxFruGain   OBJECT-TYPE
    SYNTAX      FloatTenths
    MAX-ACCESS  read-only
    STATUS      current
    DESCRIPTION ""
    ::= { ofxEntry  6 }

ofxRecommendedGain OBJECT-TYPE
    SYNTAX          FloatTenths
    MAX-ACCESS      read-only
    STATUS          current
    DESCRIPTION     ""
    ::= { ofxEntry 7 }

ofxRxEdfaOutputPowerTarget  OBJECT-TYPE
    SYNTAX      FloatTenths
    MAX-ACCESS  read-only
    STATUS      current
    DESCRIPTION ""
    ::= { ofxEntry  8 }

ofxRxEdfaGain   OBJECT-TYPE
    SYNTAX      FloatTenths
    MAX-ACCESS  read-write
    STATUS      current
    DESCRIPTION ""
    ::= { ofxEntry  9 }

ofxBwQmax   OBJECT-TYPE
    SYNTAX      FloatTenths
    MAX-ACCESS  read-only
    STATUS      current
    DESCRIPTION ""
    ::= { ofxEntry 10 }

ofxBwQused      OBJECT-TYPE
    SYNTAX      FloatTenths
    MAX-ACCESS  read-only
    STATUS      current
    DESCRIPTION ""
    ::= { ofxEntry 11 }

ofxBwQlicensed  OBJECT-TYPE
    SYNTAX      FloatTenths
    MAX-ACCESS  read-only
    STATUS      current
    DESCRIPTION ""
    ::= { ofxEntry 12 }

ofxBwBmax       OBJECT-TYPE
    SYNTAX      FloatTenths
    MAX-ACCESS  read-write
    STATUS      current
    DESCRIPTION ""
    ::= { ofxEntry 13 }

ofxBwBused      OBJECT-TYPE
    SYNTAX      FloatTenths
    MAX-ACCESS  read-write
    STATUS      current
    DESCRIPTION ""
    ::= { ofxEntry 14 }

ofxBwBlicensed      OBJECT-TYPE
    SYNTAX      FloatTenths
    MAX-ACCESS  read-write
    STATUS      current
    DESCRIPTION ""
    ::=  { ofxEntry 15 }


ofxLicensedServicesDisabled OBJECT-TYPE
    SYNTAX      Integer32
    MAX-ACCESS  read-only
    STATUS      current
    DESCRIPTION ""
    ::= { ofxEntry 16 }

ofxLicenseEnforced      OBJECT-TYPE
    SYNTAX     InfnEnforcementMode
    MAX-ACCESS  read-only
    STATUS      current
    DESCRIPTION ""
    ::= { ofxEntry 17 }

ofxDefFlexLicModFormat  OBJECT-TYPE
    SYNTAX     InfnLicenseModulationType
    MAX-ACCESS  read-write
    STATUS      current
    DESCRIPTION ""
    ::= { ofxEntry 18 }

ofxBwUsgWaterMarkGranularity    OBJECT-TYPE
    SYNTAX      FloatTenths
    MAX-ACCESS  read-write
    STATUS      current
    DESCRIPTION ""
    ::= { ofxEntry 19 }

ofxAvailableTunableSuperChNumbers OBJECT-TYPE
    SYNTAX      DisplayString
    MAX-ACCESS  read-only
    STATUS      current
    DESCRIPTION ""
    ::= { ofxEntry  20 }

ofxBw3Qmax   OBJECT-TYPE
    SYNTAX      FloatTenths
    MAX-ACCESS  read-only
    STATUS      current
    DESCRIPTION ""
    ::= { ofxEntry 21 }

ofxBw3Qused      OBJECT-TYPE
    SYNTAX      FloatTenths
    MAX-ACCESS  read-only
    STATUS      current
    DESCRIPTION ""
    ::= { ofxEntry 22 }

ofxBw3Qlicensed  OBJECT-TYPE
    SYNTAX      FloatTenths
    MAX-ACCESS  read-only
    STATUS      current
    DESCRIPTION ""
    ::= { ofxEntry 23 }

ofxCompliance  MODULE-COMPLIANCE
    STATUS      current
    DESCRIPTION ""
    MODULE
        MANDATORY-GROUPS { ofxGroup }
    ::= { ofxCompliances 1 }

ofxGroup  OBJECT-GROUP
    OBJECTS {
        ofxMoId,
        ofxProvEqptType,
   	    ofxActvTimingSource,
        ofxPicDspVer,
        ofxMaxFruGain,
        ofxRxEdfaOutputPowerTarget,
        ofxRxEdfaGain,
        ofxOTNContainerRepresentation,
        ofxRecommendedGain,
        ofxBwQmax,
        ofxBwQused,
        ofxBwQlicensed,
        ofxBwBmax,
        ofxBwBused,
        ofxBwBlicensed,
        ofxLicensedServicesDisabled,
        ofxLicenseEnforced,
        ofxDefFlexLicModFormat,
        ofxBwUsgWaterMarkGranularity,
        ofxAvailableTunableSuperChNumbers,
        ofxBw3Qmax,
        ofxBw3Qused,
        ofxBw3Qlicensed
    }
    STATUS     current
    DESCRIPTION
        ""
    ::= { ofxGroups 1 }
END
