-- *****************************************************************
-- INFINERA-TP-OSAPTP-MIB
--
-- October 2008, Sharfuddin Syed / Narendra Gupta
--
--
-- Copyright (c) 2008-2012 by Infinera Inc.
-- All rights reserved.
-- ****************************************************************

INFINERA-TP-OSAPTP-MIB DEFINITIONS ::= BEGIN

IMPORTS
    MODULE-IDENTITY, OBJECT-TYPE,
    Integer32                                   FROM SNMPv2-SMI
    MODULE-COMPLIANCE, OBJECT-GROUP             FROM SNMPv2-CONF
    DisplayString, TruthValue                   FROM SNMPv2-TC
    ifIndex                                     FROM IF-MIB
    FloatTenths, InfnServiceType                FROM INFINERA-TC-MIB
    terminationPoint                            FROM INFINERA-REG-MIB;

osaPtpMIB MODULE-IDENTITY
    LAST-UPDATED  "200810200000Z"
    ORGANIZATION
        "Infinera"
    CONTACT-INFO
        "Infinera
                1322 Bordeaux Drive
                Sunnyvale, CA - 94089

                Contact : Technical Support
                Email   : support@infinera.com
                Phone   : 1-877-INF-5288"
    DESCRIPTION
        " "

    REVISION  "200810200000Z"
    DESCRIPTION
        "First Version"
::= { terminationPoint 21 }


-- Conformance Statements

osaPtpConformance  OBJECT IDENTIFIER ::= { osaPtpMIB 3 }
osaPtpCompliances  OBJECT IDENTIFIER ::= { osaPtpConformance 1 }
osaPtpGroups  OBJECT IDENTIFIER ::= { osaPtpConformance 2 }

osaPtpTable  OBJECT-TYPE
    SYNTAX SEQUENCE OF OsaPtpEntry
    MAX-ACCESS not-accessible
    STATUS     current
    DESCRIPTION
        "A list of osaPtp entries. Each entry is uniquely identified by the value of ifIndex."
    ::= { osaPtpMIB 1 }

osaPtpEntry  OBJECT-TYPE
    SYNTAX     OsaPtpEntry
    MAX-ACCESS not-accessible
    STATUS     current
    DESCRIPTION
        "A osaPtp entry containing information pertaining to Infinera osaPtp interfaces.
                This table is a subclass of IfCommon. Entries will exist in this table only for interfaces of
                type osaPtp."
    INDEX { ifIndex }
    ::= { osaPtpTable 1 }

OsaPtpEntry  ::= SEQUENCE {
    osaPtpPmHistStatsEnable  INTEGER
}

osaPtpPmHistStatsEnable OBJECT-TYPE
    SYNTAX  INTEGER {
        enabled(1),
        disabled(2)
    }
    MAX-ACCESS  read-write
    STATUS      current
    DESCRIPTION "This objects control the collection of historical PM."
    DEFVAL      { enabled }
    ::= { osaPtpEntry  1 }


osaPtpCompliance  MODULE-COMPLIANCE
    STATUS     current
    DESCRIPTION
        "Describes the requirements for conformance to the OSAPTP-MIB"
    MODULE
        MANDATORY-GROUPS { osaPtpGroup }
    ::= { osaPtpCompliances 1 }

osaPtpGroup  OBJECT-GROUP
    OBJECTS {
        osaPtpPmHistStatsEnable
        }
    STATUS     current
    DESCRIPTION
        " A collection of objects for managing the osaPtp"
    ::= { osaPtpGroups 1 }
END
