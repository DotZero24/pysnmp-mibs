-- ***************************************************************
-- INFINERA-ENTITY-DSE-MIB
--
-- October 2008, Sharfuddin Syed / Narendra Gupta
--
--
-- Copyright (c) 2008-2012 by Infinera Inc.
-- All rights reserved.
-- ****************************************************************

INFINERA-ENTITY-DSE-MIB DEFINITIONS ::= BEGIN

IMPORTS
    OBJECT-TYPE, MODULE-IDENTITY        FROM SNMPv2-SMI
    OBJECT-GROUP, MODULE-COMPLIANCE     FROM SNMPv2-CONF
    RowStatus, DisplayString            FROM SNMPv2-TC
    entLPPhysicalIndex                  FROM ENTITY-MIB
    equipment                           FROM INFINERA-REG-MIB
    InfnEqptType, InfnEqualizationCtrlLoop, InfnConvergenceStatus, FloatTenths    FROM INFINERA-TC-MIB;

dseMIB MODULE-IDENTITY
    LAST-UPDATED  "200810200000Z"
    ORGANIZATION
        "INFINERA"
    CONTACT-INFO
        "Infinera
        169 Java Drive
        Sunnyvale, CA - 94089

        Contact : Technical Support
        Email   : support@infinera.com
        Phone   : 1-877-INF-5288"
    DESCRIPTION
        "This MIB is modeling for DSE equipment table."

::= { equipment 17 }

dseConformance       OBJECT IDENTIFIER ::= { dseMIB 3 }
dseCompliances       OBJECT IDENTIFIER ::= { dseConformance 1 }
dseGroups            OBJECT IDENTIFIER ::= { dseConformance 2 }

dseTable  OBJECT-TYPE
    SYNTAX SEQUENCE OF DseEntry
    MAX-ACCESS not-accessible
    STATUS     current
    DESCRIPTION
        "This table contains all DSE modules that are currently present in a network element.
        "
    ::= { dseMIB 1 }

dseEntry  OBJECT-TYPE
    SYNTAX     DseEntry
    MAX-ACCESS not-accessible
    STATUS     current
    DESCRIPTION
        "A row in the DSE table. Each row in the table is identified with a unique entPhysicalIndexID.
        "
    INDEX { entLPPhysicalIndex }
    ::= { dseTable 1 }

DseEntry ::= SEQUENCE {
    dseMoId             DisplayString,
    dseProvEqptType     InfnEqptType,
    dseSpectrumTiltOffset    FloatTenths,
    dseEqualizationCtrlLoop InfnEqualizationCtrlLoop,
    dseConvergenceStatus InfnConvergenceStatus,
    dseRowStatus        RowStatus,
    dseCtrlLoopTimer     Integer32
}

dseMoId  OBJECT-TYPE
    SYNTAX     DisplayString
    MAX-ACCESS read-create
    STATUS     current
    DESCRIPTION
        "This is the primary Key of the objects e.g 1-A-1"
    ::= { dseEntry 1 }

dseProvEqptType  OBJECT-TYPE
    SYNTAX     InfnEqptType
    MAX-ACCESS read-create
    STATUS     current
    DESCRIPTION
        "User provisioned DSE type."
    ::= { dseEntry 2 }

dseSpectrumTiltOffset  OBJECT-TYPE
    SYNTAX     FloatTenths
    MAX-ACCESS read-create
    STATUS     current
    DESCRIPTION
        "DSE Specrtrum Tilt Offset."
    ::= { dseEntry 3 }

dseEqualizationCtrlLoop OBJECT-TYPE
    SYNTAX     InfnEqualizationCtrlLoop
    MAX-ACCESS read-write
    STATUS     current
    DESCRIPTION
        "DSE Equalization Control Loop."
    ::= { dseEntry 4 }

dseConvergenceStatus OBJECT-TYPE
    SYNTAX     InfnConvergenceStatus
    MAX-ACCESS read-only
    STATUS     current
    DESCRIPTION
        "DSE Convergence Status."
    ::= { dseEntry 5 }

dseRowStatus  OBJECT-TYPE
    SYNTAX     RowStatus
    MAX-ACCESS read-create
    STATUS     current
    DESCRIPTION
        "The row status of this DSE entry.
                Because rows in this table are indexed by entPhysicalIndex, to create a new row one must
                choose a value of entPhysicalIndex that is not already in use.

                A side-effect of the creation of a row in this table is the creation of a corresponding
                row in the eqptTable and the entPhysicalTable.

                The status may not be set to active if the dseMoId and dseProvEqptType are not set to valid values.

                This row may only be deleted if it was a pre-provisioned row and the hardware is not present.

                If this row is deleted, the associated row in the Eqpt Table and entPhysicalTable will be
                deleted by the agent."
    ::= { dseEntry 6 }

dseCtrlLoopTimer OBJECT-TYPE
    SYNTAX     Integer32
    MAX-ACCESS read-write
    STATUS     current
    DESCRIPTION
        "DSE Control loop Timer."
    ::= { dseEntry 7 }

dseCompliance  MODULE-COMPLIANCE
    STATUS     current
    DESCRIPTION
        ""
    MODULE
        MANDATORY-GROUPS { dseGroup }
    ::= { dseCompliances 1 }

dseGroup  OBJECT-GROUP
    OBJECTS { dseMoId,
        dseProvEqptType,
        dseSpectrumTiltOffset,
        dseEqualizationCtrlLoop,
        dseConvergenceStatus,
        dseRowStatus,
        dseCtrlLoopTimer }
    STATUS     current
    DESCRIPTION
        ""
    ::= { dseGroups 1 }
END
