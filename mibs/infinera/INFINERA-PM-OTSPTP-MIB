-- *****************************************************************
-- INFINERA-PM-OTSPTP-MIB
--
-- October 2008, Sharfuddin Syed / Narendra Gupta
--
--
-- Copyright (c) 2008-2012 by Infinera Inc.
-- All rights reserved.
-- ****************************************************************

INFINERA-PM-OTSPTP-MIB DEFINITIONS ::= BEGIN

IMPORTS
    MODULE-IDENTITY, OBJECT-TYPE,
    Integer32                                   FROM SNMPv2-SMI
    MODULE-COMPLIANCE, OBJECT-GROUP             FROM SNMPv2-CONF
    DisplayString, TruthValue                   FROM SNMPv2-TC
    ifIndex                                     FROM IF-MIB
    FloatHundredths                             FROM INFINERA-TC-MIB
    perfMon                        FROM INFINERA-REG-MIB;


otsPtpPmMIB MODULE-IDENTITY
    LAST-UPDATED  "200810200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION      "200810200000Z"
    DESCRIPTION
        "First Version"
    ::= { perfMon 12 }



otsPtpPmTable OBJECT-TYPE
    SYNTAX      SEQUENCE OF OTSPtpPmEntry
    MAX-ACCESS  not-accessible
    STATUS      current
    DESCRIPTION
        "A list of OTSPtpPm entries. Each entry is uniquely identified by the value of ifIndex, sampleDuration and otsPtpPmTimestamp."
    ::= { otsPtpPmMIB 2 }

otsPtpPmEntry  OBJECT-TYPE
    SYNTAX      OTSPtpPmEntry
    MAX-ACCESS  not-accessible
    STATUS      current
    DESCRIPTION
        "An OtsPTP entry containing historical performance information pertaining to
        Infinera OTS PTP Interfaces. This table is a subclass of IfCommon.
        Entries will exist in this table only for interfaces of type OTS PTP.
        Each interface may have a number of entries in this table, each with a different combination
        of timestamp and sample duration."
    INDEX { ifIndex, otsPtpPmSampleDuration, otsPtpPmTimestamp }
    ::= { otsPtpPmTable 1 }


OTSPtpPmEntry  ::= SEQUENCE {
    otsPtpPmTimestamp        Integer32,
    otsPtpPmSampleDuration   INTEGER,
    otsPtpPmValidity         TruthValue,
    otsPtpPmOtsOptMin        FloatHundredths,
    otsPtpPmOtsOptMax        FloatHundredths,
    otsPtpPmOtsOptAve        FloatHundredths,
    otsPtpPmOtsOprMin        FloatHundredths,
    otsPtpPmOtsOprMax        FloatHundredths,
    otsPtpPmOtsOprAve        FloatHundredths,
    otsPtpPmOtsLbc1Min       FloatHundredths,
    otsPtpPmOtsLbc1Max       FloatHundredths,
    otsPtpPmOtsLbc1Ave       FloatHundredths,
    otsPtpPmOtsLbc2Min       FloatHundredths,
    otsPtpPmOtsLbc2Max       FloatHundredths,
    otsPtpPmOtsLbc2Ave       FloatHundredths,
    otsPtpPmOtsLbc3Min       FloatHundredths,
    otsPtpPmOtsLbc3Max       FloatHundredths,
    otsPtpPmOtsLbc3Ave       FloatHundredths,
    otsPtpPmOtsLbc4Min       FloatHundredths,
    otsPtpPmOtsLbc4Max       FloatHundredths,
    otsPtpPmOtsLbc4Ave       FloatHundredths,
    otsPtpPmOtsLpwr1Min      FloatHundredths,
    otsPtpPmOtsLpwr1Max      FloatHundredths,
    otsPtpPmOtsLpwr1Ave      FloatHundredths,
    otsPtpPmOtsLpwr2Min      FloatHundredths,
    otsPtpPmOtsLpwr2Max      FloatHundredths,
    otsPtpPmOtsLpwr2Ave      FloatHundredths,
    otsPtpPmOtsLpwr3Min      FloatHundredths,
    otsPtpPmOtsLpwr3Max      FloatHundredths,
    otsPtpPmOtsLpwr3Ave      FloatHundredths,
    otsPtpPmOtsLpwr4Min      FloatHundredths,
    otsPtpPmOtsLpwr4Max      FloatHundredths,
    otsPtpPmOtsLpwr4Ave      FloatHundredths,
    otsPtpOtsAlsOprMin       FloatHundredths,
    otsPtpOtsAlsOprMax       FloatHundredths,
    otsPtpOtsAlsOprAve       FloatHundredths,
    otsPtpOtsAlsOptMin       FloatHundredths,
    otsPtpOtsAlsOptMax       FloatHundredths,
    otsPtpOtsAlsOptAve       FloatHundredths,
    otsPtpOtsAlsLbcMin       FloatHundredths,
    otsPtpOtsAlsLbcMax       FloatHundredths,
    otsPtpOtsAlsLbcAve       FloatHundredths
}

otsPtpPmTimestamp OBJECT-TYPE
    SYNTAX      Integer32 (0..2147483647)
    MAX-ACCESS  not-accessible
    STATUS      current
    DESCRIPTION
        "End Time stamp for this interval. If this time is later than the current time,
        then the data for this bucket is currently being collected."
    ::= { otsPtpPmEntry  1 }


otsPtpPmSampleDuration OBJECT-TYPE
    SYNTAX      INTEGER {
                    fifteenMinutes(1),
                    day(2)
                }
    MAX-ACCESS  not-accessible
    STATUS      current
    DESCRIPTION
        "The duration of this sample."
    ::= { otsPtpPmEntry  2 }


otsPtpPmValidity OBJECT-TYPE
    SYNTAX      TruthValue
    MAX-ACCESS  read-only
    STATUS      current
    DESCRIPTION "Flag indicating if data was valid for the entire interval"
    ::= { otsPtpPmEntry  3 }


otsPtpPmOtsOptMin OBJECT-TYPE
    SYNTAX      FloatHundredths
    MAX-ACCESS  read-only
    STATUS      current
    DESCRIPTION "OTS Optical Power Transmitted, minimum (dBm)"
    ::= { otsPtpPmEntry  4 }


otsPtpPmOtsOptMax OBJECT-TYPE
    SYNTAX      FloatHundredths
    MAX-ACCESS  read-only
    STATUS      current
    DESCRIPTION "OTS Optical Power Transmitted, maximum (dBm)"
    ::= { otsPtpPmEntry  5 }


otsPtpPmOtsOptAve OBJECT-TYPE
    SYNTAX      FloatHundredths
    MAX-ACCESS  read-only
    STATUS      current
    DESCRIPTION "OTS Optical Power Transmitted, average (dBm)"
    ::= { otsPtpPmEntry  6 }


otsPtpPmOtsOprMin OBJECT-TYPE
    SYNTAX      FloatHundredths
    MAX-ACCESS  read-only
    STATUS      current
    DESCRIPTION "OTS Optical Power Received, minimum (dBm)"
    ::= { otsPtpPmEntry  7 }


otsPtpPmOtsOprMax OBJECT-TYPE
    SYNTAX      FloatHundredths
    MAX-ACCESS  read-only
    STATUS      current
    DESCRIPTION "OTS Optical Power Received, maximum (dBm)"
    ::= { otsPtpPmEntry  8 }


otsPtpPmOtsOprAve OBJECT-TYPE
    SYNTAX      FloatHundredths
    MAX-ACCESS  read-only
    STATUS      current
    DESCRIPTION "OTS Optical Power Received, average (dBm)"
    ::= { otsPtpPmEntry  9 }


otsPtpPmOtsLbc1Min OBJECT-TYPE
    SYNTAX      FloatHundredths
    MAX-ACCESS  read-only
    STATUS      current
    DESCRIPTION "OTS Laser Bias Current for Pump 1, minimum (mA)"
    ::= { otsPtpPmEntry  10 }


otsPtpPmOtsLbc1Max OBJECT-TYPE
    SYNTAX      FloatHundredths
    MAX-ACCESS  read-only
    STATUS      current
    DESCRIPTION "OTS Laser Bias Current for Pump 1, maximum (mA)"
    ::= { otsPtpPmEntry  11 }


otsPtpPmOtsLbc1Ave OBJECT-TYPE
    SYNTAX      FloatHundredths
    MAX-ACCESS  read-only
    STATUS      current
    DESCRIPTION "OTS Laser Bias Current for Pump 1, average (mA)"
    ::= { otsPtpPmEntry  12 }


otsPtpPmOtsLbc2Min OBJECT-TYPE
    SYNTAX      FloatHundredths
    MAX-ACCESS  read-only
    STATUS      current
    DESCRIPTION "OTS Laser Bias Current for Pump 2, minimum (mA)"
    ::= { otsPtpPmEntry  13 }


otsPtpPmOtsLbc2Max OBJECT-TYPE
    SYNTAX      FloatHundredths
    MAX-ACCESS  read-only
    STATUS      current
    DESCRIPTION "OTS Laser Bias Current for Pump 2, maximum (mA)"
    ::= { otsPtpPmEntry  14 }


otsPtpPmOtsLbc2Ave OBJECT-TYPE
    SYNTAX      FloatHundredths
    MAX-ACCESS  read-only
    STATUS      current
    DESCRIPTION "OTS Laser Bias Current for Pump 2, average (mA)"
    ::= { otsPtpPmEntry  15 }


otsPtpPmOtsLbc3Min OBJECT-TYPE
    SYNTAX      FloatHundredths
    MAX-ACCESS  read-only
    STATUS      current
    DESCRIPTION "OTS Laser Bias Current for Pump 3, minimum (mA)"
    ::= { otsPtpPmEntry  16 }


otsPtpPmOtsLbc3Max OBJECT-TYPE
    SYNTAX      FloatHundredths
    MAX-ACCESS  read-only
    STATUS      current
    DESCRIPTION "OTS Laser Bias Current for Pump 3, maximum (mA)"
    ::= { otsPtpPmEntry  17 }


otsPtpPmOtsLbc3Ave OBJECT-TYPE
    SYNTAX      FloatHundredths
    MAX-ACCESS  read-only
    STATUS      current
    DESCRIPTION "OTS Laser Bias Current for Pump 3, average (mA)"
    ::= { otsPtpPmEntry  18 }


otsPtpPmOtsLbc4Min OBJECT-TYPE
    SYNTAX      FloatHundredths
    MAX-ACCESS  read-only
    STATUS      current
    DESCRIPTION "OTS Laser Bias Current for Pump 4, average (mA)"
    ::= { otsPtpPmEntry  19 }


otsPtpPmOtsLbc4Max OBJECT-TYPE
    SYNTAX      FloatHundredths
    MAX-ACCESS  read-only
    STATUS      current
    DESCRIPTION "OTS Laser Bias Current for Pump 4, maximum (mA)"
    ::= { otsPtpPmEntry  20 }


otsPtpPmOtsLbc4Ave OBJECT-TYPE
    SYNTAX      FloatHundredths
    MAX-ACCESS  read-only
    STATUS      current
    DESCRIPTION "OTS Laser Bias Current for Pump 4, average (mA)"
    ::= { otsPtpPmEntry  21 }


otsPtpPmOtsLpwr1Min OBJECT-TYPE
    SYNTAX      FloatHundredths
    MAX-ACCESS  read-only
    STATUS      current
    DESCRIPTION "OTS Laser Pump Power for Pump 1, minimum (dBm)"
    ::= { otsPtpPmEntry  22 }


otsPtpPmOtsLpwr1Max OBJECT-TYPE
    SYNTAX      FloatHundredths
    MAX-ACCESS  read-only
    STATUS      current
    DESCRIPTION "OTS Laser Pump Power for Pump 1, maximum (dBm)"
    ::= { otsPtpPmEntry  23 }


otsPtpPmOtsLpwr1Ave OBJECT-TYPE
    SYNTAX      FloatHundredths
    MAX-ACCESS  read-only
    STATUS      current
    DESCRIPTION "OTS Laser Pump Power for Pump 1, average (dBm)"
    ::= { otsPtpPmEntry  24 }


otsPtpPmOtsLpwr2Min OBJECT-TYPE
    SYNTAX      FloatHundredths
    MAX-ACCESS  read-only
    STATUS      current
    DESCRIPTION "OTS Laser Pump Power for Pump 2, minimum (dBm)"
    ::= { otsPtpPmEntry  25 }


otsPtpPmOtsLpwr2Max OBJECT-TYPE
    SYNTAX      FloatHundredths
    MAX-ACCESS  read-only
    STATUS      current
    DESCRIPTION "OTS Laser Pump Power for Pump 2, maximum (dBm)"
    ::= { otsPtpPmEntry  26 }


otsPtpPmOtsLpwr2Ave OBJECT-TYPE
    SYNTAX      FloatHundredths
    MAX-ACCESS  read-only
    STATUS      current
    DESCRIPTION "OTS Laser Pump Power for Pump 2, average (dBm)"
    ::= { otsPtpPmEntry  27 }


otsPtpPmOtsLpwr3Min OBJECT-TYPE
    SYNTAX      FloatHundredths
    MAX-ACCESS  read-only
    STATUS      current
    DESCRIPTION "OTS Laser Pump Power for Pump 3, minimum (dBm)"
    ::= { otsPtpPmEntry  28 }


otsPtpPmOtsLpwr3Max OBJECT-TYPE
    SYNTAX      FloatHundredths
    MAX-ACCESS  read-only
    STATUS      current
    DESCRIPTION "OTS Laser Pump Power for Pump 3, maximum (dBm)"
    ::= { otsPtpPmEntry  29 }


otsPtpPmOtsLpwr3Ave OBJECT-TYPE
    SYNTAX      FloatHundredths
    MAX-ACCESS  read-only
    STATUS      current
    DESCRIPTION "OTS Laser Pump Power for Pump 3, average (dBm)"
    ::= { otsPtpPmEntry  30 }


otsPtpPmOtsLpwr4Min OBJECT-TYPE
    SYNTAX      FloatHundredths
    MAX-ACCESS  read-only
    STATUS      current
    DESCRIPTION "OTS Laser Pump Power for Pump 4, minimum (dBm)"
    ::= { otsPtpPmEntry  31 }


otsPtpPmOtsLpwr4Max OBJECT-TYPE
    SYNTAX      FloatHundredths
    MAX-ACCESS  read-only
    STATUS      current
    DESCRIPTION "OTS Laser Pump Power for Pump 4, maximum (dBm)"
    ::= { otsPtpPmEntry  32 }


otsPtpPmOtsLpwr4Ave OBJECT-TYPE
    SYNTAX      FloatHundredths
    MAX-ACCESS  read-only
    STATUS      current
    DESCRIPTION "OTS Laser Pump Power for Pump 4, average (dBm)"
    ::= { otsPtpPmEntry  33 }


otsPtpOtsAlsOprMin OBJECT-TYPE
    SYNTAX      FloatHundredths
    MAX-ACCESS  read-only
    STATUS      current
    DESCRIPTION "Optical power received by the ALS pilot laser, minimum (dBm)."
    ::= { otsPtpPmEntry  34 }


otsPtpOtsAlsOprMax OBJECT-TYPE
    SYNTAX      FloatHundredths
    MAX-ACCESS  read-only
    STATUS      current
    DESCRIPTION "Optical power received by the ALS pilot laser, maximum (dBm)."
    ::= { otsPtpPmEntry  35 }


otsPtpOtsAlsOprAve OBJECT-TYPE
    SYNTAX      FloatHundredths
    MAX-ACCESS  read-only
    STATUS      current
    DESCRIPTION "Optical power received by the ALS pilot laser, average (dBm)."
    ::= { otsPtpPmEntry  36 }


otsPtpOtsAlsOptMin OBJECT-TYPE
    SYNTAX      FloatHundredths
    MAX-ACCESS  read-only
    STATUS      current
    DESCRIPTION "Optical power transmitted by the ALS pilot laser, minimum (dBm)."
    ::= { otsPtpPmEntry  37 }


otsPtpOtsAlsOptMax OBJECT-TYPE
    SYNTAX      FloatHundredths
    MAX-ACCESS  read-only
    STATUS      current
    DESCRIPTION "Optical power transmitted by the ALS pilot laser, maximum (dBm)."
    ::= { otsPtpPmEntry  38 }


otsPtpOtsAlsOptAve OBJECT-TYPE
    SYNTAX      FloatHundredths
    MAX-ACCESS  read-only
    STATUS      current
    DESCRIPTION "Optical power transmitted by the ALS pilot laser, average (dBm)."
    ::= { otsPtpPmEntry  39 }


otsPtpOtsAlsLbcMin OBJECT-TYPE
    SYNTAX      FloatHundredths
    MAX-ACCESS  read-only
    STATUS      current
    DESCRIPTION "Laser biased current of the ALS pilot laser, minimum (dBm)."
    ::= { otsPtpPmEntry  40 }


otsPtpOtsAlsLbcMax OBJECT-TYPE
    SYNTAX      FloatHundredths
    MAX-ACCESS  read-only
    STATUS      current
    DESCRIPTION "Laser biased current of the ALS pilot laser, maximum (dBm)."
    ::= { otsPtpPmEntry  41 }


otsPtpOtsAlsLbcAve OBJECT-TYPE
    SYNTAX      FloatHundredths
    MAX-ACCESS  read-only
    STATUS      current
    DESCRIPTION "Laser biased current of the ALS pilot laser, average (dBm)."
    ::= { otsPtpPmEntry  42 }


otsPtpPmRealTable OBJECT-TYPE
    SYNTAX      SEQUENCE OF OTSPtpPmRealEntry
    MAX-ACCESS  not-accessible
    STATUS      current
    DESCRIPTION
        "A list of OTSPtpPmReal entries. Each entry is uniquely identified by the value of ifIndex."
    ::= { otsPtpPmMIB 1 }

otsPtpPmRealEntry  OBJECT-TYPE
    SYNTAX      OTSPtpPmRealEntry
    MAX-ACCESS  not-accessible
    STATUS      current
    DESCRIPTION
        "An OtsPTP entry containing real-time performance information pertaining to
        Infinera OTS PTP Interfaces. This table is a subclass of IfCommon.
        Entries will exist in this table only for interfaces of type OTS PTP."
    INDEX { ifIndex }
    ::= { otsPtpPmRealTable 1 }


OTSPtpPmRealEntry  ::= SEQUENCE {
    otsPtpPmRealOtsOpt               FloatHundredths,
    otsPtpPmRealOtsOptOsaTapRatio    FloatHundredths,
    otsPtpPmRealOtsOpr               FloatHundredths,
    otsPtpPmRealOtsOprOsaTapRatio    FloatHundredths,
    otsPtpPmRealOtsLbc1              FloatHundredths,
    otsPtpPmRealOtsLbc2              FloatHundredths,
    otsPtpPmRealOtsLbc3              FloatHundredths,
    otsPtpPmRealOtsLbc4              FloatHundredths,
    otsPtpPmRealOtsLpwr1             FloatHundredths,
    otsPtpPmRealOtsLpwr2             FloatHundredths,
    otsPtpPmRealOtsLpwr3             FloatHundredths,
    otsPtpPmRealOtsLpwr4             FloatHundredths,
    otsPtpPmRealOtsAlsOpr            FloatHundredths,
    otsPtpPmRealOtsAlsOpt            FloatHundredths,
    otsPtpPmRealOtsAlsLbc            FloatHundredths,
    otsPtpPmRealRxPostEdfaOsaTapRatio  FloatHundredths,
    otsPtpPmRealOprQ                 DisplayString
}

otsPtpPmRealOtsOpt OBJECT-TYPE
    SYNTAX      FloatHundredths
    MAX-ACCESS  read-only
    STATUS      current
    DESCRIPTION "OTS Optical Power Transmitted"
    ::= { otsPtpPmRealEntry  1 }


otsPtpPmRealOtsOptOsaTapRatio OBJECT-TYPE
    SYNTAX      FloatHundredths
    MAX-ACCESS  read-only
    STATUS      current
    DESCRIPTION "OPT to OSA Tap Ratio."
    ::= { otsPtpPmRealEntry  2 }


otsPtpPmRealOtsOpr OBJECT-TYPE
    SYNTAX      FloatHundredths
    MAX-ACCESS  read-only
    STATUS      current
    DESCRIPTION "OTS Optical Power Received"
    ::= { otsPtpPmRealEntry  3 }


otsPtpPmRealOtsOprOsaTapRatio OBJECT-TYPE
    SYNTAX      FloatHundredths
    MAX-ACCESS  read-only
    STATUS      current
    DESCRIPTION "OPR to OSA Tap Ratio."
    ::= { otsPtpPmRealEntry  4 }


otsPtpPmRealOtsLbc1 OBJECT-TYPE
    SYNTAX      FloatHundredths
    MAX-ACCESS  read-only
    STATUS      current
    DESCRIPTION "OTS Laser Bias Current for Pump 1"
    ::= { otsPtpPmRealEntry  5 }


otsPtpPmRealOtsLbc2 OBJECT-TYPE
    SYNTAX      FloatHundredths
    MAX-ACCESS  read-only
    STATUS      current
    DESCRIPTION "OTS Laser Bias Current for Pump 2"
    ::= { otsPtpPmRealEntry  6 }


otsPtpPmRealOtsLbc3 OBJECT-TYPE
    SYNTAX      FloatHundredths
    MAX-ACCESS  read-only
    STATUS      current
    DESCRIPTION "OTS Laser Bias Current for Pump 3"
    ::= { otsPtpPmRealEntry  7 }


otsPtpPmRealOtsLbc4 OBJECT-TYPE
    SYNTAX      FloatHundredths
    MAX-ACCESS  read-only
    STATUS      current
    DESCRIPTION "OTS Laser Bias Current for Pump 4"
    ::= { otsPtpPmRealEntry  8 }


otsPtpPmRealOtsLpwr1 OBJECT-TYPE
    SYNTAX      FloatHundredths
    MAX-ACCESS  read-only
    STATUS      current
    DESCRIPTION "OTS Laser Pump Power for Pump 1"
    ::= { otsPtpPmRealEntry  9 }


otsPtpPmRealOtsLpwr2 OBJECT-TYPE
    SYNTAX      FloatHundredths
    MAX-ACCESS  read-only
    STATUS      current
    DESCRIPTION "OTS Laser Pump Power for Pump 2"
    ::= { otsPtpPmRealEntry  10 }


otsPtpPmRealOtsLpwr3 OBJECT-TYPE
    SYNTAX      FloatHundredths
    MAX-ACCESS  read-only
    STATUS      current
    DESCRIPTION "OTS Laser Pump Power for Pump 3"
    ::= { otsPtpPmRealEntry  11 }


otsPtpPmRealOtsLpwr4 OBJECT-TYPE
    SYNTAX      FloatHundredths
    MAX-ACCESS  read-only
    STATUS      current
    DESCRIPTION "OTS Laser Pump Power for Pump 4"
    ::= { otsPtpPmRealEntry  12 }

otsPtpPmRealOtsAlsOpr OBJECT-TYPE
    SYNTAX      FloatHundredths
    MAX-ACCESS  read-only
    STATUS      current
    DESCRIPTION "Optical power received by the ALS pilot laser."
    ::= { otsPtpPmRealEntry  13 }


otsPtpPmRealOtsAlsOpt OBJECT-TYPE
    SYNTAX      FloatHundredths
    MAX-ACCESS  read-only
    STATUS      current
    DESCRIPTION "Optical power transmitted by the ALS pilot laser."
    ::= { otsPtpPmRealEntry  14 }


otsPtpPmRealOtsAlsLbc OBJECT-TYPE
    SYNTAX      FloatHundredths
    MAX-ACCESS  read-only
    STATUS      current
    DESCRIPTION "Laser biased current of the ALS pilot laser(dBm)."
    ::= { otsPtpPmRealEntry  15 }


otsPtpPmRealRxPostEdfaOsaTapRatio OBJECT-TYPE
    SYNTAX      FloatHundredths
    MAX-ACCESS  read-only
    STATUS      current
    DESCRIPTION "Rx Post Edfa Osa Tap Ratio"
    ::= { otsPtpPmRealEntry  16 }

otsPtpPmRealOprQ OBJECT-TYPE
    SYNTAX      DisplayString
    MAX-ACCESS  read-only
    STATUS      current
    DESCRIPTION "Operational Qualifier"
    ::= { otsPtpPmRealEntry  17 }

-- Conformance Statements
otsPtpPmConformance    OBJECT IDENTIFIER ::= { otsPtpPmMIB 3 }
otsPtpPmCompliances    OBJECT IDENTIFIER ::= { otsPtpPmConformance 1 }
otsPtpPmGroups         OBJECT IDENTIFIER ::= { otsPtpPmConformance 2 }

otsPtpPmCompliance MODULE-COMPLIANCE
    STATUS current
    DESCRIPTION
    "Describes the requirements for conformance to the PM-OTSPTP-MIB"
    MODULE
        MANDATORY-GROUPS { otsPtpPmGroup }
    ::= { otsPtpPmCompliances 1 }

otsPtpPmRealCompliance MODULE-COMPLIANCE
    STATUS current
    DESCRIPTION
    "Describes the requirements for conformance to the otsPtpPmReal-MIB"
    MODULE
        MANDATORY-GROUPS { otsPtpPmRealGroup }
    ::= { otsPtpPmCompliances 2 }

otsPtpPmGroup OBJECT-GROUP
    OBJECTS {
        otsPtpPmValidity,
        otsPtpPmOtsOptMin,
        otsPtpPmOtsOptMax,
        otsPtpPmOtsOptAve,
        otsPtpPmOtsOprMin,
        otsPtpPmOtsOprMax,
        otsPtpPmOtsOprAve,
        otsPtpPmOtsLbc1Min,
        otsPtpPmOtsLbc1Max,
        otsPtpPmOtsLbc1Ave,
        otsPtpPmOtsLbc2Min,
        otsPtpPmOtsLbc2Max,
        otsPtpPmOtsLbc2Ave,
        otsPtpPmOtsLbc3Min,
        otsPtpPmOtsLbc3Max,
        otsPtpPmOtsLbc3Ave,
        otsPtpPmOtsLbc4Min,
        otsPtpPmOtsLbc4Max,
        otsPtpPmOtsLbc4Ave,
        otsPtpPmOtsLpwr1Min,
        otsPtpPmOtsLpwr1Max,
        otsPtpPmOtsLpwr1Ave,
        otsPtpPmOtsLpwr2Min,
        otsPtpPmOtsLpwr2Max,
        otsPtpPmOtsLpwr2Ave,
        otsPtpPmOtsLpwr3Min,
        otsPtpPmOtsLpwr3Max,
        otsPtpPmOtsLpwr3Ave,
        otsPtpPmOtsLpwr4Min,
        otsPtpPmOtsLpwr4Max,
        otsPtpPmOtsLpwr4Ave,
        otsPtpOtsAlsOprMin,
        otsPtpOtsAlsOprMax,
        otsPtpOtsAlsOprAve,
        otsPtpOtsAlsOptMin,
        otsPtpOtsAlsOptMax,
        otsPtpOtsAlsOptAve,
        otsPtpOtsAlsLbcMin,
        otsPtpOtsAlsLbcMax,
        otsPtpOtsAlsLbcAve
    }
    STATUS current
    DESCRIPTION
        " A collection of objects for reading the performance of the otsPtp."
    ::= { otsPtpPmGroups 1 }

otsPtpPmRealGroup OBJECT-GROUP
    OBJECTS {
        otsPtpPmRealOtsOpt,
        otsPtpPmRealOtsOptOsaTapRatio,
        otsPtpPmRealOtsOpr,
        otsPtpPmRealOtsOprOsaTapRatio,
        otsPtpPmRealOtsLbc1,
        otsPtpPmRealOtsLbc2,
        otsPtpPmRealOtsLbc3,
        otsPtpPmRealOtsLbc4,
        otsPtpPmRealOtsLpwr1,
        otsPtpPmRealOtsLpwr2,
        otsPtpPmRealOtsLpwr3,
        otsPtpPmRealOtsLpwr4,
        otsPtpPmRealOtsAlsOpr,
        otsPtpPmRealOtsAlsOpt,
        otsPtpPmRealOtsAlsLbc,
        otsPtpPmRealRxPostEdfaOsaTapRatio,
        otsPtpPmRealOprQ
    }
    STATUS current
    DESCRIPTION
        " A collection of objects for reading the real-time performance of the otsPtp."
    ::= { otsPtpPmGroups 2 }

END
