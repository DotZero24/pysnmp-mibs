-- ***************************************************************
-- INFINERA-ENTITY-XMM-MIB
--
-- September 2014, Anusree Bhattacharjee
--
--
-- Copyright (c) 2014 by Infinera Inc.
-- All rights reserved.
-- ****************************************************************

INFINERA-ENTITY-XMM-MIB DEFINITIONS ::= BEGIN

IMPORTS
    OBJECT-TYPE, MODULE-IDENTITY           FROM SNMPv2-SMI
    OBJECT-GROUP, MODULE-COMPLIANCE        FROM SNMPv2-CONF
    RowStatus, TruthValue, DisplayString   FROM SNMPv2-TC
    entLPPhysicalIndex                     FROM ENTITY-MIB
    equipment                              FROM INFINERA-REG-MIB
    InfnEqptType                           FROM INFINERA-TC-MIB;

xmmMIB MODULE-IDENTITY
    LAST-UPDATED  "200810200000Z"
    ORGANIZATION
        "INFINERA"
    CONTACT-INFO
        "Infinera
        169 Java Drive
        Sunnyvale, CA - 94089

        Contact : Technical Support
        Email   : support@infinera.com
        Phone   : 1-877-INF-5288"
    DESCRIPTION
        "This MIB is modeling for XMM equipment table."

::= { equipment 36 }

xmmConformance       OBJECT IDENTIFIER ::= { xmmMIB 3 }
xmmCompliances       OBJECT IDENTIFIER ::= { xmmConformance 1 }
xmmGroups            OBJECT IDENTIFIER ::= { xmmConformance 2 }

xmmTable  OBJECT-TYPE
    SYNTAX SEQUENCE OF XmmEntry
    MAX-ACCESS not-accessible
    STATUS     current
    DESCRIPTION
        "This table contains all XMM modules that are currently present in a network element.
        "
    ::= { xmmMIB 1 }

xmmEntry  OBJECT-TYPE
    SYNTAX     XmmEntry
    MAX-ACCESS not-accessible
    STATUS     current
    DESCRIPTION
        "A row in the XMM table. Each row in the table is identified with a unique entPhysicalIndexID.
        "
    INDEX { entLPPhysicalIndex }
    ::= { xmmTable 1 }

XmmEntry ::= SEQUENCE {
    xmmMoId               DisplayString,
    xmmProvType           InfnEqptType,
    xmmBrandingFault      TruthValue,
    xmmRowStatus          RowStatus
}

xmmMoId  OBJECT-TYPE
    SYNTAX     DisplayString
    MAX-ACCESS read-create
    STATUS     current
    DESCRIPTION
        "The object identifier."
    ::= { xmmEntry 1 }

xmmProvType  OBJECT-TYPE
    SYNTAX     InfnEqptType
    MAX-ACCESS read-create
    STATUS     current
    DESCRIPTION
        "The configured XMM type."
    ::= { xmmEntry 2 }

xmmBrandingFault  OBJECT-TYPE
    SYNTAX     TruthValue
    MAX-ACCESS read-only
    STATUS     current
    DESCRIPTION
        "Indicates XMM branding faults."
    ::= { xmmEntry 3 }

xmmRowStatus  OBJECT-TYPE
    SYNTAX     RowStatus
    MAX-ACCESS read-create
    STATUS     current
    DESCRIPTION
        "The row status of this XMM entry.
         Because rows in this table are indexed by entPhysicalIndex, to create a new row one must
         choose a value of entPhysicalIndex that is not already in use.

         A side-effect of the creation of a row in this table is the creation of a corresponding
         row in the eqptTable and the entPhysicalTable.

         The status may not be set to active if the xmmMoId and xmmProvEqptType are not set to valid values.

         This row may only be deleted if it was a pre-provisioned row and the hardware is not present.

         If this row is deleted, the associated row in the Eqpt Table and entPhysicalTable will be
         deleted by the agent."
    ::= { xmmEntry 4 }

xmmCompliance  MODULE-COMPLIANCE
    STATUS     current
    DESCRIPTION
        ""
    MODULE
        MANDATORY-GROUPS { xmmGroup }
    ::= { xmmCompliances 1 }

xmmGroup  OBJECT-GROUP
    OBJECTS { xmmBrandingFault,
        xmmMoId,
        xmmProvType,
        xmmRowStatus }
    STATUS     current
    DESCRIPTION
        ""
    ::= { xmmGroups 1 }
END
