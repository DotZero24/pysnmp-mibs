-- ***************************************************************
-- INFINERA-TP-PXMMEP-MIB
--
-- May 2016, Kavitha Manjunatha / Divyank Rastogi
--
--
-- Copyright (c) 2008-2012 by Infinera Inc.
-- All rights reserved.
-- ****************************************************************
INFINERA-TP-PXMMEP-MIB DEFINITIONS ::= BEGIN

IMPORTS
    OBJECT-TYPE, MODULE-IDENTITY, Unsigned32    FROM SNMPv2-SMI
    OBJECT-GROUP, MODULE-COMPLIANCE             FROM SNMPv2-CONF
    DisplayString                               FROM SNMPv2-TC
    ifIndex                          			FROM IF-MIB
    terminationPoint                            FROM INFINERA-REG-MIB
    InfnMepRole, InfnIsEnabled, InfnMepDirection,
    InfnAISInterval, InfnPortStatusTLV,
    InfnInterfaceStatusTLV, InfnLowestPriDef,
    InfnCFMAction, InfnEqptType,
    InfnEnableDisable, InfnCSFInterval,
	InfnEnableDisableType				        FROM INFINERA-TC-MIB;

mepMIB MODULE-IDENTITY
    LAST-UPDATED  "201605200000Z"
    ORGANIZATION
        "INFINERA"
    CONTACT-INFO
        "Infinera
        169 Java Drive
        Sunnyvale, CA - 94089

        Contact : Technical Support
        Email   : support@infinera.com
        Phone   : 1-877-INF-5288"
    DESCRIPTION
        "This MIB is modeling for MEP equipment table."
::= { terminationPoint 43 }

mepConformance       OBJECT IDENTIFIER ::= { mepMIB 3 }
mepCompliances       OBJECT IDENTIFIER ::= { mepConformance 1 }
mepGroups            OBJECT IDENTIFIER ::= { mepConformance 2 }

mepTable  OBJECT-TYPE
    SYNTAX SEQUENCE OF MepEntry
    MAX-ACCESS not-accessible
    STATUS     current
    DESCRIPTION
        "This table contains all MEP  modules that are currently present in a network element.
        "
    ::= { mepMIB 1 }

mepEntry  OBJECT-TYPE
    SYNTAX     MepEntry
    MAX-ACCESS not-accessible
    STATUS     current
    DESCRIPTION
        "A row in the MEP table. Each row in the table is identified with a unique entPhysicalIndexID."
    INDEX { ifIndex }
    ::= { mepTable 1 }

MepEntry ::= SEQUENCE {
    mepMaaId                            DisplayString,
    mepRole                             InfnMepRole,
    mepCCIEnabled                       InfnIsEnabled,
    mepMDLevel                          Integer32,
    mepOuterPrimaryVID                  Integer32,
    mepInnerPrimaryVID                  Integer32,
    mepId                               Integer32,
    mepRMEPCrossCheck                   InfnEnableDisable,
    mepDirection                        InfnMepDirection,
    mepCcmPriority                      Integer32,
    mepCcmDEI                           InfnIsEnabled,
    mepMacAddress                       DisplayString,
    mepLowestPriorityDefect             InfnLowestPriDef,
    mepPortStatusTLV                    InfnPortStatusTLV,
    mepInterfaceStatusTLV               InfnInterfaceStatusTLV,
    mepSomeRMEPDefectCFMAction          InfnCFMAction,
    mepXconnDefectCFMAction             InfnCFMAction,
    mepErrorCCMDefectCFMAction          InfnCFMAction,
    mepSomeMACStatusDefectCFMaction     InfnCFMAction,
    mepAISCapability                    InfnIsEnabled,
    mepClientMDLevel                    Integer32,
    mepAISInterval                      InfnAISInterval,
    mepAisPriority                      Integer32,
    mepAisDEI                           InfnIsEnabled,
    mepPmHistStatsEnable                InfnEnableDisable,
	mepCSFSupport						InfnEnableDisableType,
	mepCSFInterval						InfnCSFInterval,
	mepCSFPriority						Integer32,
	mepCSFDEI							InfnIsEnabled
}

mepMaaId  OBJECT-TYPE
    SYNTAX     DisplayString
    MAX-ACCESS read-only
    STATUS     current
    DESCRIPTION
        ""
    ::= { mepEntry 1 }

mepRole  OBJECT-TYPE
    SYNTAX     InfnMepRole
    MAX-ACCESS read-only
    STATUS     current
    DESCRIPTION
        ""
    ::= { mepEntry 2 }

mepCCIEnabled  OBJECT-TYPE
    SYNTAX     InfnIsEnabled
    MAX-ACCESS read-write
    STATUS     current
    DESCRIPTION
        ""
    ::= { mepEntry 3 }

mepMDLevel  OBJECT-TYPE
    SYNTAX     Integer32
    MAX-ACCESS read-only
    STATUS     current
    DESCRIPTION
        ""
    ::= { mepEntry 4 }

mepOuterPrimaryVID  OBJECT-TYPE
    SYNTAX     Integer32
    MAX-ACCESS read-write
    STATUS     current
    DESCRIPTION
        ""
    ::= { mepEntry 5 }

mepInnerPrimaryVID  OBJECT-TYPE
    SYNTAX     Integer32
    MAX-ACCESS read-write
    STATUS     current
    DESCRIPTION
        ""
    ::= { mepEntry 6 }

mepId  OBJECT-TYPE
    SYNTAX     Integer32
    MAX-ACCESS read-write
    STATUS     current
    DESCRIPTION
        ""
    ::= { mepEntry 7 }

mepRMEPCrossCheck  OBJECT-TYPE
    SYNTAX     InfnEnableDisable
    MAX-ACCESS read-write
    STATUS     current
    DESCRIPTION
        ""
    ::= { mepEntry 8 }

mepDirection  OBJECT-TYPE
    SYNTAX     InfnMepDirection
    MAX-ACCESS read-write
    STATUS     current
    DESCRIPTION
        ""
    ::= { mepEntry 9 }

mepCcmPriority  OBJECT-TYPE
    SYNTAX     Integer32
    MAX-ACCESS read-write
    STATUS     current
    DESCRIPTION
        ""
    ::= { mepEntry 10 }

mepCcmDEI  OBJECT-TYPE
    SYNTAX     InfnIsEnabled
    MAX-ACCESS read-write
    STATUS     current
    DESCRIPTION
        ""
    ::= { mepEntry 11 }

mepMacAddress  OBJECT-TYPE
    SYNTAX     DisplayString
    MAX-ACCESS read-only
    STATUS     current
    DESCRIPTION
        ""
    ::= { mepEntry 12 }

mepLowestPriorityDefect  OBJECT-TYPE
    SYNTAX     InfnLowestPriDef
    MAX-ACCESS read-write
    STATUS     current
    DESCRIPTION
        ""
    ::= { mepEntry 13 }

mepPortStatusTLV  OBJECT-TYPE
    SYNTAX     InfnPortStatusTLV
    MAX-ACCESS read-only
    STATUS     current
    DESCRIPTION
        ""
    ::= { mepEntry 14 }

mepInterfaceStatusTLV  OBJECT-TYPE
    SYNTAX     InfnInterfaceStatusTLV
    MAX-ACCESS read-only
    STATUS     current
    DESCRIPTION
        ""
    ::= { mepEntry 15 }

mepSomeRMEPDefectCFMAction  OBJECT-TYPE
    SYNTAX     InfnCFMAction
    MAX-ACCESS read-write
    STATUS     current
    DESCRIPTION
        ""
    ::= { mepEntry 16 }

mepXconnDefectCFMAction  OBJECT-TYPE
    SYNTAX     InfnCFMAction
    MAX-ACCESS read-write
    STATUS     current
    DESCRIPTION
        ""
    ::= { mepEntry 17 }

mepErrorCCMDefectCFMAction  OBJECT-TYPE
    SYNTAX     InfnCFMAction
    MAX-ACCESS read-write
    STATUS     current
    DESCRIPTION
        ""
    ::= { mepEntry 18 }

mepSomeMACStatusDefectCFMaction  OBJECT-TYPE
    SYNTAX     InfnCFMAction
    MAX-ACCESS read-write
    STATUS     current
    DESCRIPTION
        ""
    ::= { mepEntry 19 }

mepAISCapability  OBJECT-TYPE
    SYNTAX     InfnIsEnabled
    MAX-ACCESS read-write
    STATUS     current
    DESCRIPTION
        ""
    ::= { mepEntry 20 }

mepClientMDLevel  OBJECT-TYPE
    SYNTAX     Integer32
    MAX-ACCESS read-write
    STATUS     current
    DESCRIPTION
        ""
    ::= { mepEntry 21 }

mepAISInterval  OBJECT-TYPE
    SYNTAX     InfnAISInterval
    MAX-ACCESS read-write
    STATUS     current
    DESCRIPTION
        ""
    ::= { mepEntry 22 }

mepAisPriority  OBJECT-TYPE
    SYNTAX     Integer32
    MAX-ACCESS read-write
    STATUS     current
    DESCRIPTION
        ""
    ::= { mepEntry 23 }

mepAisDEI  OBJECT-TYPE
    SYNTAX     InfnIsEnabled
    MAX-ACCESS read-write
    STATUS     current
    DESCRIPTION
        ""
    ::= { mepEntry 24 }

mepPmHistStatsEnable  OBJECT-TYPE
    SYNTAX     InfnEnableDisable
    MAX-ACCESS read-write
    STATUS     current
    DESCRIPTION
        ""
    ::= { mepEntry 25 }

mepCSFSupport		OBJECT-TYPE
    SYNTAX     InfnEnableDisableType
    MAX-ACCESS read-write
    STATUS     current
    DESCRIPTION
        ""
    ::= { mepEntry 26 }

mepCSFInterval  OBJECT-TYPE
    SYNTAX     InfnCSFInterval
    MAX-ACCESS read-write
    STATUS     current
    DESCRIPTION
        ""
    ::= { mepEntry 27 }

mepCSFPriority  OBJECT-TYPE
    SYNTAX     Integer32
    MAX-ACCESS read-write
    STATUS     current
    DESCRIPTION
        ""
    ::= { mepEntry 28 }

mepCSFDEI  OBJECT-TYPE
    SYNTAX     InfnIsEnabled
    MAX-ACCESS read-write
    STATUS     current
    DESCRIPTION
        ""
    ::= { mepEntry 29 }

mepCompliance  MODULE-COMPLIANCE
    STATUS     current
    DESCRIPTION ""
    MODULE
        MANDATORY-GROUPS { mepGroup }
    ::= { mepCompliances 1 }

mepGroup  OBJECT-GROUP
    OBJECTS {
        mepMaaId,
        mepRole,
        mepCCIEnabled,
        mepMDLevel,
        mepOuterPrimaryVID,
        mepInnerPrimaryVID,
        mepId,
        mepRMEPCrossCheck,
        mepDirection,
        mepCcmPriority,
        mepCcmDEI,
        mepMacAddress,
        mepLowestPriorityDefect,
        mepPortStatusTLV,
        mepInterfaceStatusTLV,
        mepSomeRMEPDefectCFMAction,
        mepXconnDefectCFMAction,
        mepErrorCCMDefectCFMAction,
        mepSomeMACStatusDefectCFMaction,
        mepAISCapability,
        mepClientMDLevel,
        mepAISInterval,
        mepAisPriority,
        mepAisDEI,
        mepPmHistStatsEnable,
		mepCSFSupport,
		mepCSFInterval,
		mepCSFPriority,
		mepCSFDEI
    }
    STATUS     current
    DESCRIPTION ""
    ::= { mepGroups 1 }
END
