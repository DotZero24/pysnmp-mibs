-- ***************************************************************
-- INFINERA-ENTITY-FBM-MIB
-- Copyright (c) 2008-2017 by Infinera Inc.
-- All rights reserved.
-- ****************************************************************

INFINERA-ENTITY-FBM-MIB DEFINITIONS ::= BEGIN

IMPORTS
    OBJECT-TYPE, MODULE-IDENTITY, Integer32        FROM SNMPv2-SMI
    OBJECT-GROUP, MODULE-COMPLIANCE                FROM SNMPv2-CONF
    TruthValue, DisplayString                      FROM SNMPv2-TC
    entPhysicalIndex                               FROM ENTITY-MIB
    equipment                                      FROM INFINERA-REG-MIB
	InfnEqptType                                   FROM INFINERA-TC-MIB;

fbmMIB MODULE-IDENTITY
    LAST-UPDATED  "201701170000Z"
    ORGANIZATION
        "Infinera"
    CONTACT-INFO
        "Infinera
                1322 Bordeaux Drive
                Sunnyvale, CA - 94089
                Contact : Technical Support
                Email   : support@infinera.com
                Phone   : 1-877-INF-5288"
    DESCRIPTION
        " "
::= { equipment 55 }

-- Conformance Statements

fbmConformance       OBJECT IDENTIFIER ::= { fbmMIB 3 }
fbmCompliances       OBJECT IDENTIFIER ::= { fbmConformance 1 }
fbmGroups            OBJECT IDENTIFIER ::= { fbmConformance 2 }

fbmTable  OBJECT-TYPE
    SYNTAX SEQUENCE OF FbmEntry
    MAX-ACCESS not-accessible
    STATUS     current
    DESCRIPTION
        "A list of FBM entries. Each entry is uniquely identified by the value
                of entPhysicalIndex."
    ::= { fbmMIB 1 }

fbmEntry  OBJECT-TYPE
    SYNTAX     FbmEntry
    MAX-ACCESS not-accessible
    STATUS     current
    DESCRIPTION
        "A FBM entry containing information pertaining to
            Infinera FBM modules. Entries will exist in this table for
            entPhysicalEntries of type FBM."
    INDEX { entPhysicalIndex }
    ::= { fbmTable 1 }

FbmEntry ::= SEQUENCE {
    fbmMoId                      DisplayString,
    fbmProvEqptType              InfnEqptType,
    fbmUsbUpstreamNbr            DisplayString,
    fbmUsbDownstreamNbr          DisplayString
}

fbmMoId     OBJECT-TYPE
    SYNTAX      DisplayString
    MAX-ACCESS  read-write
    STATUS      current
    DESCRIPTION ""
    ::= { fbmEntry 1 }

fbmProvEqptType OBJECT-TYPE
    SYNTAX      InfnEqptType
    MAX-ACCESS  read-write
    STATUS      current
    DESCRIPTION ""
    ::= { fbmEntry 2 }


fbmUsbUpstreamNbr   OBJECT-TYPE
    SYNTAX      DisplayString
    MAX-ACCESS  read-only
    STATUS      current
    DESCRIPTION ""
    ::= { fbmEntry 3 }

fbmUsbDownstreamNbr OBJECT-TYPE
    SYNTAX      DisplayString
    MAX-ACCESS  read-only
    STATUS      current
    DESCRIPTION ""
    ::= { fbmEntry 4 }

fbmCompliance  MODULE-COMPLIANCE
    STATUS     current
    DESCRIPTION
        "Describes the requirements for conformance to the FMMC-MIB"
    MODULE
        MANDATORY-GROUPS { fbmGroup }
    ::= { fbmCompliances 1 }


fbmGroup  OBJECT-GROUP
    OBJECTS {
        fbmMoId,
        fbmProvEqptType,
        fbmUsbUpstreamNbr,
        fbmUsbDownstreamNbr

    }
    STATUS     current
    DESCRIPTION
        " A collection of objects for managing a FMMC module"
    ::= { fbmGroups 1 }


END
