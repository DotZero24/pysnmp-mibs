LUM-CLIENT-MIB DEFINITIONS ::= BEGIN

IMPORTS
    MODULE-IDENTITY, OBJECT-TYPE, Unsigned32, Integer32, NOTIFICATION-TYPE, Gauge32
        FROM SNMPv2-SMI
    OBJECT-GROUP, MODULE-COMPLIANCE, NOTIFICATION-GROUP
        FROM SNMPv2-CONF
    DisplayString, DateAndTime
        FROM SNMPv2-TC
    lumModules, lumClientMIB
        FROM LUM-REG
    FaultStatus, MgmtNameString, SubrackNumber, SlotNumber, PortNumber,
    BoardOrInterfaceOperStatus, BoardOrInterfaceAdminStatus, CommandString,
    LambdaFrequency, SignalFormat, TrxMedia, ObjectProperty, BerLevelMTOSI,
    OpticalLayerMappingType, LaneFrequency, TrxRxState, TrxTxState, PhysicalLayerMappingType, SignalDirection,
    SignalStatusWithNA, EnableDisable, OnOff, InterfaceType
        FROM LUM-TC;

lumClientMIBModule MODULE-IDENTITY
    LAST-UPDATED
        "201808230000Z" -- August 23rd 2018
    ORGANIZATION
        "Infinera Corporation"
    CONTACT-INFO
        "techsupport@infinera.com"
    DESCRIPTION
        "The generic client interface MIB.

        - General

        - Generic client interfaces

"
    REVISION
        "201808230000Z" -- August 23rd 2018
    DESCRIPTION
        "Changes made for release r31.1:
         - added trxPowerOutOfRange for HDEA1600"
    REVISION
        "201804130000Z" -- April 13th 2018
    DESCRIPTION
        "Changes made for release r30.1:
         - added configureSNMP"
    REVISION
        "201712150000Z" -- December 15th 2017
    DESCRIPTION
        "Changes made for release r30.0:
         - added the emxp440 board.
         - added ifType attribute"
    REVISION
        "201706150000Z" -- June 15th 2017
    DESCRIPTION
        "Changes made for release r29.0:
         - Changed ORGANIZATION and CONTACT-INFO
         - added clientIfTrxCommunicationFailure."
    REVISION
        "201611300000Z" -- November 2016
    DESCRIPTION
        "Changes made for release r28.0:
        - added AID and physical location."
    REVISION
        "201607150000Z" -- July 2016
    DESCRIPTION
        "Changes made for release r28.1:
        - added the ptio100g board."
    REVISION
        "201605240000Z" -- May 2016
    DESCRIPTION
        "Changes made for release r27:
        - added the ptio10g board.
        - Added clientMpoLanesTable."
    REVISION
        "201512150000Z" -- Dec 2015
    DESCRIPTION
        "Changes made for release r26:
        - added the emxp3 board.
        - Added clientIfIfNo to clientIfTable.
        - added clientIfIdx to clientIfTable.
        - added clientIfIdxIf to clientIfTable.
        - added clientIfUpPortId to clientIfTable
        - added clientIfFecCorrectedBits to clientIfTable
        - added clientIfOSNRMargin to clientIfTable
        - added clientIfNoOfLanes to clientIfTable
        - added clientLanesReceivedPowerLow to clientIfTable
        - added clientLanesIfNo to clientIfTable
        - added clientLanesIdx to clientIfTable
        - added clientLanesClientIfIdx to clientIfTable"
    REVISION
        "201501140000Z" -- January 14th 2015
    DESCRIPTION
        "Changes made for release r25:
        - Added all emxp240iie board."
    REVISION
        "201408150000Z" -- August 15th 2014
    DESCRIPTION
        "Changes made for release r23.1:
        - Added all EMXPGII boards to farendloopback.
        - Added sdFec format on 'clientIfFecType'.
        - Added TxState and RxState.
        - Added ChromaticDispersion and DifferentialGroupDelay.
        - Changed help text for clientIfTrxMode.
        - Started using 'BerLevelMTOSI' for clientIfSignalDegradeThreshold
          adding two new values compared to 'BerLevel'"
    REVISION
        "201405160000Z" -- May 16th 2014
    DESCRIPTION
        "Changes made for release r23:
        - Board emxp220iie, lanes tables is used for emxp220iie.
                            added optical layer mapping.
                            added configure mismatch alarm
        - Added fhmxp10g board."
    REVISION
        "201309300000Z" -- Sep 30th 2013
    DESCRIPTION
        "Changes made for release r22:
        - Extended loopback times to 120 hours"

    REVISION
        "201305010000Z" -- May 1st 2013
    DESCRIPTION
        "Changes made for release r21:
        - Added near end client loopback for tpq10gfec and tpq10gfeci.
        - Added tpq10gfeci board.
        - Near End Loopback added for msMxp and gbeMxp10GFEC"

    REVISION
        "201212200000Z" -- Dec 20th 2012
    DESCRIPTION
        "Changes made for release r20:
        - Boards msTp40G, msMxp40G added.
        - Boards msTp40G, added new Lanes table to msTp40G.
                          added new alarm Lane Alignment Error.
          Added  Fec Corrected Zeros.
                 Fec Corrected ones.
                 new alarm Signal Degraded."

    REVISION
        "201203300000Z" -- March 30th 2012
    DESCRIPTION
        "Changes made for R19.0
        -Board msMxp10G, added near end loopback functionalty,
                         added a new alarm Transceiver not supporting Loopback.
    -Added fec failure alarm"
    REVISION
        "201112200000Z" -- Dec 20th 2011
    DESCRIPTION
        "Changes made for release r18:
        - Boards tpqmp, tpq10GfecReg and emxp40Gii added.
        - Signal format help text updated for tpqmp.
        - Long alias for Trunk side AIS changed.
        - Help text for attribute Speed changed.
        - Changed/Corrected help text for Ethernet utilization.
        - Attribute Client side AIS-L and Ethernet utilization added for tpq10Gfec."
    REVISION
        "201104120000Z" -- April 12th 2011
    DESCRIPTION
        "Added new compliance group to mark adding write support for trail trace."
    REVISION
        "200601270000Z" -- January 27th 2006
    DESCRIPTION
        "Added TS-1100 specific alarms."
    REVISION
        "200509140000Z" -- September 14th 2005
    DESCRIPTION
        "Added minimal compliance statemets for the TS-family."
    REVISION
        "200404160000Z" -- April 16th 2004
    DESCRIPTION
        "The initial revision of this module."
    ::= { lumModules 27 }


-- ----------------------------------------------------
-- Conformance area, containing groups and complicance
-- specifications.
-- ----------------------------------------------------

lumClientConfs OBJECT IDENTIFIER ::= { lumClientMIB 1 }
lumClientGroups OBJECT IDENTIFIER ::= { lumClientConfs 1 }
lumClientCompl OBJECT IDENTIFIER ::= { lumClientConfs 2 }
lumClientMinimalGroups OBJECT IDENTIFIER ::= { lumClientConfs 3 }
lumClientMinimalCompl OBJECT IDENTIFIER ::= { lumClientConfs 4 }


-- ----------------------------------------------------
-- Root for objects in the generic client i/f MIB
-- ----------------------------------------------------

lumClientMIBObjects OBJECT IDENTIFIER ::= { lumClientMIB 2 }


-- ----------------------------------------------------
-- This MIB contains the following groups:
-- ----------------------------------------------------

clientGeneral OBJECT IDENTIFIER ::= { lumClientMIBObjects 1 }
clientIfList OBJECT IDENTIFIER ::= { lumClientMIBObjects 2 }
clientVc4List OBJECT IDENTIFIER ::= { lumClientMIBObjects 3 }
lumentisClientNotifications  OBJECT IDENTIFIER ::= { lumClientMIBObjects 4 }
clientLanesList OBJECT IDENTIFIER ::= { lumClientMIBObjects 5 }
clientMpoLanesList OBJECT IDENTIFIER ::= { lumClientMIBObjects 6 }


-- ----------------------------------------------------
-- Textual Conventions
-- ----------------------------------------------------

-- ----------------------------------------------------
-- General group
-- ----------------------------------------------------


clientGeneralLastChangeTime OBJECT-TYPE
    SYNTAX      DateAndTime
    MAX-ACCESS  read-only
    STATUS      current
    DESCRIPTION
        "The time when the configuration of the MIB was
        last changed.

"
    ::= { clientGeneral 1 }

clientGeneralStateLastChangeTime OBJECT-TYPE
    SYNTAX      DateAndTime
    MAX-ACCESS  read-only
    STATUS      current
    DESCRIPTION
        "The time when the state of the MIB was last
        changed.

"
    ::= { clientGeneral 2 }

clientGeneralClientIfTableSize OBJECT-TYPE
    SYNTAX      Unsigned32
    MAX-ACCESS  read-only
    STATUS      current
    DESCRIPTION
        "Size of table

"
    ::= { clientGeneral 3 }

clientGeneralVc4TableSize OBJECT-TYPE
    SYNTAX       Unsigned32
    MAX-ACCESS   read-only
    STATUS       current
    DESCRIPTION
        "Size of table

"
   ::= { clientGeneral 4 }

clientGeneralLanesTableSize OBJECT-TYPE
    SYNTAX       Unsigned32
    MAX-ACCESS   read-only
    STATUS       current
    DESCRIPTION
        "Size of table

"
   ::= { clientGeneral 5 }

clientGeneralMpoLanesTableSize OBJECT-TYPE
    SYNTAX       Unsigned32
    MAX-ACCESS   read-only
    STATUS       current
    DESCRIPTION
        "Size of table

"
   ::= { clientGeneral 6 }

-- ----------------------------------------------------
-- Generic client interfaces
-- ----------------------------------------------------

clientIfTable  OBJECT-TYPE
    SYNTAX      SEQUENCE OF ClientIfEntry
    MAX-ACCESS  not-accessible
    STATUS      current
    DESCRIPTION
        "The interface list."
    ::= { clientIfList 1 }

clientIfEntry OBJECT-TYPE
    SYNTAX      ClientIfEntry
    MAX-ACCESS  not-accessible
    STATUS      current
    DESCRIPTION
        "An entry in the interface list.

"
    INDEX { clientIfIndex }
    ::= { clientIfTable 1 }

ClientIfEntry ::=
    SEQUENCE {
        -- Administrativa
        clientIfIndex                   Unsigned32,
        clientIfName                    MgmtNameString,
        clientIfDescr                   DisplayString,
        clientIfSubrack                 SubrackNumber,
        clientIfSlot                    SlotNumber,
        clientIfTxPort                  PortNumber,
        clientIfRxPort                  PortNumber,
        clientIfInvPhysIndexOrZero      Unsigned32,
        clientIfEntityId                Unsigned32,
        clientIfIdx                     Integer32,
        clientIfIdxIf                   Integer32,
        clientIfUpPortId                Integer32,

        -- Operational
        clientIfAdminStatus             BoardOrInterfaceAdminStatus,
        clientIfOperStatus              BoardOrInterfaceOperStatus,
        clientIfLaserStatus             INTEGER,
        clientIfTxSignalStatus          SignalStatusWithNA,
        clientIfForwardAls              INTEGER,
        clientIfSuppressRemoteAlarms    INTEGER,
        clientIfFarEndLoopback          INTEGER,
        clientIfNearEndLoopback         INTEGER,
        clientIfRxSignalStatus          SignalStatusWithNA,
        clientIfTxState                 TrxTxState,
        clientIfRxState                 TrxRxState,
        clientIfIfNo                    PortNumber,
        clientIfIfType                  InterfaceType,
        clientIfAid                     DisplayString,
        clientIfPhysicalLocation        DisplayString,
        -- Functional
        clientIfFormat                  SignalFormat,

        -- ETH
        clientIfAutoNegotiationMode     INTEGER,
        clientIfAutoNegotiationStatus   INTEGER,
        clientIfDuplexCapability        INTEGER,
        clientIfFlowControlMode         INTEGER,
        clientIfInterPacketGap          Gauge32,
        clientIfFrameSize               Gauge32,
        clientIfGfpMode                 INTEGER,
        clientIfBandWidth               Integer32,
        clientIfRateLimit               Integer32,
        clientIfGbeUtilization          Unsigned32,

        -- TRX
        clientIfTrxClass                DisplayString,
        clientIfTrxMedia                TrxMedia,

        -- Analogue
        clientIfLaserBias                      Unsigned32,
        clientIfPowerLevel                     Integer32,
        clientIfReceiverSensitivity            Integer32,
        clientIfPowerLevelLowRelativeThreshold Integer32,

        -- Alarms
        clientIfLossOfSignal               FaultStatus,
        clientIfLossOfFrame                FaultStatus,
        clientIfLossOfSync                 FaultStatus,
        clientIfBitrateMismatch            FaultStatus,
        clientIfAuAlarmIndicationSignalW2C FaultStatus,
        clientIfTransmitterFailed          FaultStatus,
        clientIfDisabled                   FaultStatus,

        clientIfTrxCodeMismatch            FaultStatus,
        clientIfTrxBitrateUnavailable      FaultStatus,
        clientIfTrxMissing                 FaultStatus,
        clientIfTrxFailed                  FaultStatus,
        clientIfTrxCommunicationFailure    FaultStatus,

        clientIfReceivedPowerHigh          FaultStatus,
        clientIfReceivedPowerLow           FaultStatus,
        clientIfLinkDown                   FaultStatus,

        clientIfMsAlarmIndicationSignalC2W      FaultStatus,
        clientIfMsAlarmIndicationSignalW2C      FaultStatus,
        clientIfRemoteDefectIndication          FaultStatus,
        clientIfIllegalSignalFormat             FaultStatus,

        clientIfAuAlarmIndicationSignalW2CSonet FaultStatus,
        clientIfAuAlarmIndicationSignalC2WSonet FaultStatus,
        clientIfAuLossOfPointerC2WSonet         FaultStatus,
        clientIfAuLossOfPointerW2CSonet         FaultStatus,

        -- Command
        clientIfConfigurationCommand       CommandString,
        clientIfConfigurationCommandSNMP   CommandString,
        -- CWDM
        clientIfConfigureTrxModeCommand    CommandString,
        clientIfTrxMode                    INTEGER,
        clientIfExpectedTxFrequency        LambdaFrequency,
        clientIfTxFrequency                LambdaFrequency,
        clientIfUnexpectedTxFrequency      FaultStatus,
        clientIfIllegalFrequency           FaultStatus,
        clientIfLaserForcedOn              INTEGER,
        clientIfTrxMediaMismatch           FaultStatus,

        clientIfTruncAutoNegotiationMode   INTEGER,
        clientIfObjectProperty             ObjectProperty,
        clientIfTxPowerLevel               Integer32,
        clientIfLaserTempActual            Integer32,

        -- Trace
        clientIfTraceIntrusionMode         INTEGER,
        clientIfTraceTransmitted           DisplayString,
        clientIfTraceReceived              DisplayString,
        clientIfTraceExpected              DisplayString,
        clientIfTraceAlarmMode             INTEGER,
        clientIfTraceMismatch              FaultStatus,

        -- J1 Trace
        clientIfJ1TxTrailTrace             DisplayString,
        clientIfJ1TxTrailTraceInsertionMode  INTEGER,

        clientIfVcGroupFailedW2C        FaultStatus,
        clientIfReadJ1                  CommandString,

        clientIfLoopback                FaultStatus,
        clientIfClientSignalFailed      FaultStatus,
        clientIfAuLossOfPointer         FaultStatus,
        clientIfGfpLossOfFrame          FaultStatus,

        clientIfHighSpeed               Gauge32,
        clientIfActualFormat            SignalFormat,
        clientIfRdiIntrusionMode        INTEGER,
        clientIfMuxQuadVc4              Unsigned32,
        clientIfDemuxQuadVc4            Unsigned32,
        clientIfCcConnectionMode        INTEGER,
        clientIfCcConfigurationCommand  CommandString,

        clientIfSynchProtPortId           INTEGER,
        clientIfSynchProtGroupMemberPort  PortNumber,
        clientIfSynchProtGroupStatus      INTEGER,
        clientIfSynchProtActivePort       INTEGER,
        clientIfSynchProtPortStatus       INTEGER,
        clientIfSynchProtToggleActivePort CommandString,

        clientIfNearEndLoopbackTimeout         INTEGER,
        clientIfNearEndLoopbackEnabled         FaultStatus,
        clientIfChangeNearEndLoopbackCommand   CommandString,
        clientIfFarEndLoopbackEnabled          FaultStatus,
        clientIfFarEndLoopbackTimeout          INTEGER,
        clientIfChangeFarEndLoopbackCommand    CommandString,
        clientIfFormatNotSupportedByHw         FaultStatus,
        clientIfLaserMode                      INTEGER,
        clientIfAlarmIndicationSignalLineC2W   FaultStatus,
        clientIfFarEndClientFailure            FaultStatus,
        clientIfOHTransparency                 INTEGER,
        clientIfConnectedLine                  Unsigned32,
        clientIfForwardingErrorCorrectionMode  INTEGER,
        clientIfNoFrequencySet                 FaultStatus,
        clientIfJitterAttenuatorBW             INTEGER,
        clientIfConnectionStatus               DisplayString,
        clientIfLoopFilterUnlocked             FaultStatus,
        clientIfCableLength                    INTEGER,
        clientIfConnectedForeignIndex          Unsigned32,
        clientIfDisconnect                     CommandString,
        clientIfOHTransparencyBitMask          Unsigned32,
        clientIfOHTransparencyString           DisplayString,
        clientIfOHTransparencySet              CommandString,
        clientIfAuAlarmIndicationSignalC2W     FaultStatus,
        clientIfAuLossOfPointerC2W             FaultStatus,
        clientIfAuLossOfPointerW2C             FaultStatus,
        clientIfEthStandbyIndicator            INTEGER,
        clientIfTransceiverNoLoopback          FaultStatus,
        clientIfFecFailure                     FaultStatus,
        clientIfLaneAlignmentError             FaultStatus,

        clientIfFecCorrectedZeros              Unsigned32,
        clientIfFecCorrectedOnes               Unsigned32,
        clientIfFecCorrectedBits               Unsigned32,
        clientIfOSNRMargin                     Integer32,
        clientIfSignalDegraded                 FaultStatus,
        clientIfFecType                        INTEGER,
        clientIfSignalDegradeThreshold         BerLevelMTOSI,
        clientIfExpectedPhysicalLayerMapping   PhysicalLayerMappingType,
        clientIfSignalDirection                SignalDirection,

        -- 100g optical layer mapping
        clientIfExpectedOpticalLayerMapping    OpticalLayerMappingType,
        clientIfActualOpticalLayerMapping      OpticalLayerMappingType,
        clientIfConfigurationMismatch          FaultStatus,
        clientIfChromaticDispersion            Integer32,
        clientIfNoOfLanes                      Integer32,
        clientIfDifferentialGroupDelay         Unsigned32,
        clientIfTribPortId                     Unsigned32,
        clientIfTrxPowerOutOfRange             FaultStatus}

clientIfIndex OBJECT-TYPE
    SYNTAX      Unsigned32 (1..2147483647)
    MAX-ACCESS  read-create
    STATUS      current
    DESCRIPTION
        "An arbitrary index assigned to each entry.

"
    ::= { clientIfEntry 1 }

clientIfName OBJECT-TYPE
    SYNTAX      MgmtNameString
    MAX-ACCESS  read-create
    STATUS      current
    DESCRIPTION
        "The management name of the interface, for
        example 'client:1:2:1', where the first number
        indicates sub-rack, the second slot number and
        the third is the port number.
        Examples:

        client:s:s:p - Generic client interface

"
    DEFVAL { "" }
    ::= { clientIfEntry 2 }

clientIfDescr OBJECT-TYPE
    SYNTAX      DisplayString
    MAX-ACCESS  read-write
    STATUS      current
    DESCRIPTION
        "User configurable label.

        This attribute can be written via SNMP.
"
    DEFVAL { "" }
    ::= { clientIfEntry 3 }

clientIfSubrack OBJECT-TYPE
    SYNTAX      SubrackNumber
    MAX-ACCESS  read-create
    STATUS      current
    DESCRIPTION
        "The number of the subrack where the interface
        is located.

"
    DEFVAL { 0 }
    ::= { clientIfEntry 4 }

clientIfSlot OBJECT-TYPE
    SYNTAX      SlotNumber
    MAX-ACCESS  read-create
    STATUS      current
    DESCRIPTION
        "The number of the slot where the interface is
        located.

"
    DEFVAL { 0 }
    ::= { clientIfEntry 5 }

clientIfTxPort OBJECT-TYPE
    SYNTAX      PortNumber
    MAX-ACCESS  read-create
    STATUS      current
    DESCRIPTION
        "The number of the port where the TX-side of the
        interface is located.

"
    DEFVAL { 0 }
    ::= { clientIfEntry 6 }

clientIfRxPort OBJECT-TYPE
    SYNTAX      PortNumber
    MAX-ACCESS  read-create
    STATUS      current
    DESCRIPTION
        "The number of the port where the RX-side of the
        interface is located.

"
    DEFVAL { 0 }
    ::= { clientIfEntry 7 }

clientIfInvPhysIndexOrZero OBJECT-TYPE
    SYNTAX      Unsigned32 (0..2147483647)
    MAX-ACCESS  read-create
    STATUS      current
    DESCRIPTION
        "The row in the invPhysTable for this interface.
        Set to 0 if not known.

"
    DEFVAL { 0 }
    ::= { clientIfEntry 8 }

clientIfEntityId OBJECT-TYPE
    SYNTAX      Unsigned32 (1..2147483647)
    MAX-ACCESS  read-create
    STATUS      current
    DESCRIPTION
        "Index in entity table.

        -- Only used for notifications

"
    DEFVAL { 1 }
    ::= { clientIfEntry 9 }


clientIfAdminStatus OBJECT-TYPE
    SYNTAX      BoardOrInterfaceAdminStatus
    MAX-ACCESS  read-write
    STATUS      current
    DESCRIPTION
        "The administrative state for the interface.

        down - The interface is de-activated.

        service - The interface is activated but alarms are
        suppressed. Intended for use during service or
        re-configuration. When service is concluded
        adminStatus should be set to 'up' again.

        up - The interface will be activated when
        available. Alarms are not suppressed.

        This attribute can be written via SNMP.
"
    DEFVAL { up }
    ::= { clientIfEntry 10 }

clientIfOperStatus OBJECT-TYPE
    SYNTAX      BoardOrInterfaceOperStatus
    MAX-ACCESS  read-only
    STATUS      current
    DESCRIPTION
        "The operational state for the interface.

        notPresent - The physical resources are not
        available.

        down - The interface is de-activated or there are
        faults preventing its transition to the 'up' state.

        up - The interface is operational.

"
    DEFVAL { notPresent }
    ::= { clientIfEntry 11 }

clientIfLaserStatus OBJECT-TYPE
    SYNTAX      INTEGER {
                    off (1),
                    on (2) }
    MAX-ACCESS  read-only
    STATUS      current
    DESCRIPTION
        "The operational state of the laser.

        off - The laser is turned off.

        on - The laser is turned on.

"
    DEFVAL { off }
    ::= { clientIfEntry 12 }

clientIfTxSignalStatus OBJECT-TYPE
    SYNTAX      SignalStatusWithNA
    MAX-ACCESS  read-only
    STATUS      current
    DESCRIPTION
        "The operational state for outgoing (TX) signal
        of the interface.

        down - A fault that would lead to a protection
        switch has occurred.

        degraded - The signal quality is impaired.

        up - The signal is OK.

"
    DEFVAL { down }
    ::= { clientIfEntry 13 }

clientIfForwardAls OBJECT-TYPE
    SYNTAX      INTEGER {
                    disabled (1),
                    enabled (2) }
    MAX-ACCESS  read-write
    STATUS      current
    DESCRIPTION
        "Forward Automatic Laser Shut-down. Decides if
        laser shutdown of the client should occur when
        a defect on the line or remote client is detected.

        disabled - The laser is NOT turned off at defect
        detection.

        enabled - The laser is turned off at defect
        detection.

"
    DEFVAL { disabled }
    ::= { clientIfEntry 14 }

clientIfSuppressRemoteAlarms OBJECT-TYPE
    SYNTAX      INTEGER {
                    disabled (1),
                    enabled (2) }
    MAX-ACCESS  read-write
    STATUS      current
    DESCRIPTION
        "Suppress AIS in the alarm list.
        The fault status on the port object can, however,
        be seen.

        disabled - alarms are not suppressed.

        enabled - alarms are suppressed.

"
    DEFVAL { disabled }
    ::= { clientIfEntry 15 }

clientIfFarEndLoopback OBJECT-TYPE
    SYNTAX      INTEGER {
                    disabled (1),
                    enabled (2) }
    MAX-ACCESS  read-write
    STATUS      current
    DESCRIPTION
        "Loop the client TX signal back to the client RX.
        This is also called Terminal loopback.

        disabled - the signal is not looped

        enabled - the signal is looped.

"
    DEFVAL { disabled }
    ::= { clientIfEntry 16 }

clientIfFormat OBJECT-TYPE
    SYNTAX      SignalFormat
    MAX-ACCESS  read-create
    STATUS      current
    DESCRIPTION
        "The expected signal format.

        The default value is board dependent. For information
        about the default value for this particular board,
        please refer to the user manual.

"
    DEFVAL { unused }
    ::= { clientIfEntry 17 }

clientIfGfpMode OBJECT-TYPE
    SYNTAX      INTEGER {
                  transparent (1),
                  framed (2)
                }
    MAX-ACCESS  read-create
    STATUS      current
    DESCRIPTION
        "Generic framing procedure mode

"
    DEFVAL { transparent }
    ::= { clientIfEntry 18 }

clientIfBandWidth OBJECT-TYPE
    SYNTAX      Integer32 (0..48)
    MAX-ACCESS  read-create
    STATUS      current
    DESCRIPTION
        "Band-width in VC-3 or VC-4.

        The parameter is interpreted as VC-3 or VC-4
        depending on the traffic combination:

        - VC-3 is used in framedGbEx10
        - VC-4 is used in framedGbEx10Vc4

"
    DEFVAL { 0 }
    ::= { clientIfEntry 19 }

clientIfRateLimit OBJECT-TYPE
    SYNTAX      Integer32 (0..1000)
    MAX-ACCESS  read-write
    STATUS      current
    DESCRIPTION
        "Rate limit of link in 1,000,000 bits
        (Mb) per second.

        Zero (0) is a special value meaning that the
        rate-limiting procedure is disabled.

        The legal range is: 10...1000, in step of 1

"
    DEFVAL { 0 }
    ::= { clientIfEntry 20 }

clientIfAutoNegotiationMode OBJECT-TYPE
    SYNTAX      INTEGER {
                         off (1),
                         on (2) }
    MAX-ACCESS  read-write
    STATUS      current
    DESCRIPTION
        "The wanted auto negotiation mode.

        off - auto negotiation process is disabled

        on - auto negotiation process is enabled

"
    DEFVAL { on }
    ::= { clientIfEntry 21 }

clientIfAutoNegotiationStatus OBJECT-TYPE
    SYNTAX      INTEGER {
                         incomplete (1),
                         half (2),
                         full (3) }
    MAX-ACCESS  read-only
    STATUS      current
    DESCRIPTION
        "The result of the auto negotiation procedure

         incomplete - the result is still pending

         half - half duplex

         full - full duplex

"
    DEFVAL { incomplete }
    ::= { clientIfEntry 22 }

clientIfDuplexCapability OBJECT-TYPE
    SYNTAX      INTEGER {
                        half (1),
                        full (2) }
    MAX-ACCESS  read-only
    STATUS      current
    DESCRIPTION
        "The duplex capability of the HW.

         half - supports half duplex

         full - supports full duplex

"
    DEFVAL { half }
    ::= { clientIfEntry 23 }

clientIfFlowControlMode OBJECT-TYPE
    SYNTAX      INTEGER {
                        noPause (1),
                        rxPause (2),
                        txPause (3),
                        bothPause (4) }
    MAX-ACCESS  read-write
    STATUS      current
    DESCRIPTION
        "The mode for handling flow control between
         the local device and link partner.

         The PAUSE settings has the following meaning
         when auto-negotiation is enabled.

         Setting    802.3 equivalent
         -------    ----------------

         noPause    No PAUSE.

         txPause    Asymmetric PAUSE toward link partner
                    (send only).

         bothPause  Symmetric PAUSE (send and receive).

         rxPause    Both symmetric PAUSE and asymmetric
                    PAUSE toward local device (send
                    and/or receive).


         The PAUSE settings has the following meaning
         when auto-negotiation is disabled.

         Setting    Result
         -------    ------

         noPause    PAUSE frame reception and transmission
                    is disabled.

         txPause    PAUSE frame transmission is enabled.

         bothPause  PAUSE frame reception and transmission
                    is enabled.

         rxPause    PAUSE frame reception is enabled.


"
    DEFVAL { rxPause }
    ::= { clientIfEntry 24 }

clientIfInterPacketGap OBJECT-TYPE
    SYNTAX      Gauge32 (64..456)
    MAX-ACCESS  read-write
    STATUS      current
    DESCRIPTION
        "Time between the frames in nano seconds.

        Legal values are 64, 72, 80, ... 200, 320, 328,
        336, ... 456

"
    DEFVAL { 96 }
    ::= { clientIfEntry 25 }

clientIfFrameSize OBJECT-TYPE
    SYNTAX      Gauge32 (1518..9600)
    MAX-ACCESS  read-write
    STATUS      current
    DESCRIPTION
        "The maximum size of the transmitted and
        received frames (in bytes).

"
    DEFVAL { 9600 }
    ::= { clientIfEntry 26 }

clientIfTrxClass OBJECT-TYPE
    SYNTAX      DisplayString
    MAX-ACCESS  read-only
    STATUS      current
    DESCRIPTION
        "String that describes the transceiver class.
"
    DEFVAL { "" }
    ::= { clientIfEntry 27 }

clientIfLaserBias OBJECT-TYPE
    SYNTAX      Unsigned32
    MAX-ACCESS  read-only
    STATUS      current
    DESCRIPTION
        "Measures laser bias current value in tenths of
        mA (0.1 mA).

"
    ::= { clientIfEntry 28 }

clientIfPowerLevel OBJECT-TYPE
    SYNTAX      Integer32
    MAX-ACCESS  read-only
    STATUS      current
    DESCRIPTION
        "The received power level in units of 0.1 dBm.

"
    ::= { clientIfEntry 29 }

clientIfReceiverSensitivity OBJECT-TYPE
    SYNTAX      Integer32
    MAX-ACCESS  read-only
    STATUS      current
    DESCRIPTION
        "The lowest power that the receiver is guaranteed
        to handle, in units of 0.1 dBm.

"
    ::= { clientIfEntry 30 }

clientIfPowerLevelLowRelativeThreshold OBJECT-TYPE
    SYNTAX      Integer32 (-50..100)
    MAX-ACCESS  read-write
    STATUS      current
    DESCRIPTION
        "The lower threshold for received power level in
        units of 0.1 dB, relative to the receiver
        sensitivity.

"
    DEFVAL { 30 }
    ::= { clientIfEntry 31 }


clientIfLossOfSignal OBJECT-TYPE
    SYNTAX      FaultStatus
    MAX-ACCESS  read-only
    STATUS      current
    DESCRIPTION
        "Loss of signal.
        Applicable for all signal formats.

        A(ctivation): Active loss of signal HW
        indication.

        D(e-activation): Inactive loss of signal HW
        indication.

"
    ::= { clientIfEntry 32 }


clientIfLossOfFrame OBJECT-TYPE
    SYNTAX      FaultStatus
    MAX-ACCESS  read-only
    STATUS      current
    DESCRIPTION
        "Loss of frame.
        All forms of sync loss.

"
    ::= { clientIfEntry 33 }

clientIfBitrateMismatch OBJECT-TYPE
    SYNTAX      FaultStatus
    MAX-ACCESS  read-only
    STATUS      current
    DESCRIPTION
        "Bitrate mismatch (Other).
        Applicable for other signal formats.

        D: The interface is unable to lock to the
        inserted signal.

        D: The interface is able to lock to the
        inserted signal.

"
    ::= { clientIfEntry 34 }

clientIfAuAlarmIndicationSignalW2C OBJECT-TYPE
    SYNTAX      FaultStatus
    MAX-ACCESS  read-only
    STATUS      current
    DESCRIPTION
        "Alarm indication signal (AIS) on the trunk-side.
        Applicable for SDH/Sonet signal formats.

        A: An 'all ones' SDH signal is detected.

        D: SDH signal recovered.
"
    ::= { clientIfEntry 35 }

clientIfTransmitterFailed OBJECT-TYPE
    SYNTAX      FaultStatus
    MAX-ACCESS  read-only
    STATUS      current
    DESCRIPTION
        "The transceiver HW has detected a failure
         in the transmitter part.

        A: The transmitter has failed

        D: The transmitter is OK again


"
    ::= { clientIfEntry 36 }

clientIfTrxCodeMismatch OBJECT-TYPE
    SYNTAX      FaultStatus
    MAX-ACCESS  read-only
    STATUS      current
    DESCRIPTION
        "The inserted transceiver does not have a legal
        manufacturer code.

        A: A transceiver with illegal code is inserted.

        D: The transceiver with illegal code is removed.

"
    ::= { clientIfEntry 37 }

clientIfTrxBitrateUnavailable OBJECT-TYPE
    SYNTAX      FaultStatus
    MAX-ACCESS  read-only
    STATUS      current
    DESCRIPTION
        "The inserted transceiver does not support the
        requested bit rate.

        A: A transceiver with other supported bit rate than
           the requested bit rate is inserted.

        D: The transceiver with the non-requested bit rate
           is removed, or the object is reconfigured.

"
    ::= { clientIfEntry 38 }

clientIfTrxMissing OBJECT-TYPE
    SYNTAX      FaultStatus
    MAX-ACCESS  read-only
    STATUS      current
    DESCRIPTION
        "An expected transceiver is missing.

        A: An expected transceiver is missing.

        D: The missing transceiver is inserted.

"
    ::= { clientIfEntry 39 }

clientIfReceivedPowerHigh OBJECT-TYPE
    SYNTAX      FaultStatus
    MAX-ACCESS  read-only
    STATUS      current
    DESCRIPTION
        "Received power level is too high.
        Applicable for all signal formats.

        A: The received power level exceeds the
        the built-in overload threshold.

        D: The received power level is 0.5 dB below the
        overload threshold.

"
    ::= { clientIfEntry 40 }

clientIfReceivedPowerLow OBJECT-TYPE
    SYNTAX      FaultStatus
    MAX-ACCESS  read-only
    STATUS      current
    DESCRIPTION
        "Received power level low threshold exceeded.
        Applicable for all signal formats.

        A: The received power level is below the
        associated threshold.

        D: The received power level is 0.5 dB above the
        threshold.

"
    ::= { clientIfEntry 41 }


clientIfLinkDown OBJECT-TYPE
    SYNTAX      FaultStatus
    MAX-ACCESS  read-only
    STATUS      current
    DESCRIPTION
        "A: Failure to negotiate a connection with the
        other party.

         D: A connection is negotiated.

"
    ::= { clientIfEntry 42 }

clientIfConfigurationCommand OBJECT-TYPE
    SYNTAX      CommandString
    MAX-ACCESS  read-only
    STATUS      current
    DESCRIPTION
        "Command to change the signal format, and, if
        applicable, also the mode (framed, transparent).

"
    ::= { clientIfEntry 43 }

clientIfGbeUtilization OBJECT-TYPE
    SYNTAX      Unsigned32 (0..1000 | 2147483646)
    MAX-ACCESS  read-only
    STATUS      current
    DESCRIPTION
        "Shows  the current bandwidth utilization
         measured at the physical (802.3 PHY) layer.
         The value represents a snapshot of the utilization
         during the latest second. It is expressed in per cent (%)
         of the nominal maximum rate.

"
    ::= { clientIfEntry 44 }

clientIfLossOfSync OBJECT-TYPE
    SYNTAX      FaultStatus
    MAX-ACCESS  read-only
    STATUS      current
    DESCRIPTION
        "Loss of sync.
        All forms of sync loss.

        A: GbE 'frame' can not be located.

        D: GbE 'frame' is located.

"
    ::= { clientIfEntry 45 }

clientIfConfigureTrxModeCommand OBJECT-TYPE
    SYNTAX      CommandString
    MAX-ACCESS  read-only
    STATUS      current
    DESCRIPTION
        "Command to change the TRX mode (client or line) and/or
         TRX media (optical or electrical).

"
    ::= { clientIfEntry 46 }

clientIfTrxMode OBJECT-TYPE
    SYNTAX      INTEGER {
                  client (1),
                  line (2) }
    MAX-ACCESS  read-create
    STATUS      current
    DESCRIPTION
        "Shows if the port is configured as:

         - normal CLIENT interface connected to a non XTM Series
           client equipment, with non-colored, or colored TRXes.

         - a LINE interface connected to other XTM Series
           equipment or another Infinera system that optically
           and management wise can interop over this interface,
           typically with WDM TRXes. This should be used in
           cascade connections.

           Important1: Do not use 'line' mode unless you
           really have to.

           Important2: If this port constitute the edge of
           the Transmode/Infinera supplied network, and it is
           connected to other client equipment, then you
           must use 'client' mode in order to make use of
           the circuit supervision in TNM.

"
    DEFVAL { client }
    ::= { clientIfEntry 47 }


clientIfExpectedTxFrequency OBJECT-TYPE
    SYNTAX      LambdaFrequency
    MAX-ACCESS  read-write
    STATUS      current
    DESCRIPTION
        "The expected frequency given in hundreds of GHz
        (0.01 GHz).

"
    DEFVAL { 0 }
    ::= { clientIfEntry 48 }

clientIfTxFrequency OBJECT-TYPE
    SYNTAX      LambdaFrequency
    MAX-ACCESS  read-only
    STATUS      current
    DESCRIPTION
        "The transmitted frequency given in hundreds of
        GHz (0.01 GHz).

"
    ::= { clientIfEntry 49 }

clientIfUnexpectedTxFrequency OBJECT-TYPE
    SYNTAX      FaultStatus
    MAX-ACCESS  read-only
    STATUS      current
    DESCRIPTION
        "The actual frequency does not match the
        pre-configured frequency.

        A pre-configured frequency of '0' matches
        all actual frequencies.

        A: The configured frequency does not match the
        actual frequency.

        D: The configured frequency matches the actual
        frequency.

"
    ::= { clientIfEntry 50 }

clientIfIllegalFrequency OBJECT-TYPE
    SYNTAX      FaultStatus
    MAX-ACCESS  read-only
    STATUS      current
    DESCRIPTION
        "The frequency supported by the transceiver is not
        recognized by the system.

        A: Invalid or unknown frequency information is
           detected in the (pluggable) transceiver or
           board production data.

        D: The (pluggable) transceiver or board is
           replaced.

"
    ::= { clientIfEntry 51 }

clientIfLaserForcedOn OBJECT-TYPE
    SYNTAX      INTEGER {
                    disabled (1),
                    enabled (2) }
    MAX-ACCESS  read-write
    STATUS      current
    DESCRIPTION
        "When enabled, the laser is on regardless of whether
         there is a trunc signal present or not.

         disabled - the laser is only on when there is a
                    trunc signal.

         enabled  - the laser is always on. This is intended
                    to be used together with some switches
                    when the link does not come up without
                    this setting.

"
    DEFVAL { disabled }
    ::= { clientIfEntry 52 }

clientIfTrxMedia OBJECT-TYPE
    SYNTAX      TrxMedia
    MAX-ACCESS  read-create
    STATUS      current
    DESCRIPTION
        "Defines the media and capability of the TRX.

"
    DEFVAL { optical }
    ::= { clientIfEntry 53 }

clientIfTrxMediaMismatch OBJECT-TYPE
    SYNTAX      FaultStatus
    MAX-ACCESS  read-only
    STATUS      current
    DESCRIPTION
        "The TRX media does not match the expected one.

        A: Invalid or mismatching trx media is
           detected.

        D: The (pluggable) transceiver or board is
           replaced, or the configuration is changed.

"
    ::= { clientIfEntry 54 }

clientIfTruncAutoNegotiationMode OBJECT-TYPE
    SYNTAX      INTEGER {
                    disabled (1),
                    enabled (2) }
    MAX-ACCESS  read-write
    STATUS      current
    DESCRIPTION
        "Decides whether auto negotiation shall
         be performed over the trunc connection.

         This is applicable when the terminating
         node at the other side of the
         trunc is configured as follows:

           - it has an optical client interface
           - its client equipment (e.g. a router)
             requires auto negotiation.

        disabled - Do not perform auto neg over the
                   trunc


        enabled  - Perform auto neg over the trunc.

"
    DEFVAL { disabled }
    ::= { clientIfEntry 55 }

clientIfObjectProperty OBJECT-TYPE
    SYNTAX      ObjectProperty
    MAX-ACCESS  read-only
    STATUS      current
    DESCRIPTION
        "Property mask.

"
    ::= { clientIfEntry 56 }

clientIfTxPowerLevel OBJECT-TYPE
    SYNTAX      Integer32
    MAX-ACCESS  read-only
    STATUS      current
    DESCRIPTION
        "The transmitted power level in units of 0.1 dBm.

"
    ::= { clientIfEntry 57 }

clientIfLaserTempActual OBJECT-TYPE
    SYNTAX      Integer32
    MAX-ACCESS  read-only
    STATUS      current
    DESCRIPTION
        "The actual laser temperature in units of
        0.1 degrees centigrade.

"
    ::= { clientIfEntry 58 }

clientIfTraceIntrusionMode      OBJECT-TYPE
    SYNTAX      INTEGER {
                    disabled (1),
                    enabled (2) }
    MAX-ACCESS  read-write
    STATUS      current
    DESCRIPTION
        "Indicates whether the trace identifier should be
        inserted into the transmitted signal or to be
        transparent.

        disabled - The trace identifier is taken from
        the recevied signal if possible.

        enabled -  The trace identifier set is inserted
        in the transmitted signal.

"
    DEFVAL { disabled }
    ::= { clientIfEntry 59 }

clientIfTraceTransmitted        OBJECT-TYPE
    SYNTAX      DisplayString (SIZE(0..62))
    MAX-ACCESS  read-write
    STATUS      current
    DESCRIPTION
        "The trace identifier to be transmitted from this
        interface.

        The identifier length is by default 0 to 15. For
        mxp8iiSonet board the length i 0 to 62.

        Set to empty string for default value:

        <IP address>:<subrack>:<slot>:<port>

        Note that only the last part of the address
        is used.
"
    DEFVAL { "" }
    ::= { clientIfEntry 60 }

clientIfTraceReceived OBJECT-TYPE
    SYNTAX      DisplayString (SIZE(0..62))
    MAX-ACCESS  read-only
    STATUS      current
    DESCRIPTION
        "The received trace identifier for this interface.

"
    ::= { clientIfEntry 61 }

clientIfTraceExpected OBJECT-TYPE
    SYNTAX      DisplayString (SIZE(0..62))
    MAX-ACCESS  read-write
    STATUS      current
    DESCRIPTION
        "Trace identifier used for matching against
        the received trace identifier.

        The identifier length is by default 0 to 15. For
        mxp8iiSonet board the length is 0 to 62.

"
    DEFVAL { "" }
    ::= { clientIfEntry 62 }

clientIfTraceAlarmMode OBJECT-TYPE
    SYNTAX      INTEGER {
                    disabled (1),
                    enabled (2) }
    MAX-ACCESS  read-write
    STATUS      current
    DESCRIPTION
        "Controls if the trace identifier mismatch alarm
        should be raised.

        disabled - The alarm is disabled.

        enabled - The alarm is raised if expected trace
        identifier differs from the received trace
        identifier.

"
    DEFVAL { disabled }
    ::= { clientIfEntry 63 }

clientIfTraceMismatch OBJECT-TYPE
    SYNTAX      FaultStatus
    MAX-ACCESS  read-only
    STATUS      current
    DESCRIPTION
        "Indicates if the expected trace identifier
        differs from the received trace identifier.

        A: The received trace identifier differs from
        the expected trace identifier.

        D: The identifiers match.

"
    ::= { clientIfEntry 64 }

clientIfNearEndLoopback OBJECT-TYPE
    SYNTAX      INTEGER {
                    disabled (1),
                    enabled (2) }
    MAX-ACCESS  read-write
    STATUS      current
    DESCRIPTION
        "Loop the client RX signal back to the client TX.
        This is also called Facility loopback

        disabled - the signal is not looped

        enabled - the signal is looped.

"
    DEFVAL { disabled }
    ::= { clientIfEntry 65 }

clientIfRxSignalStatus OBJECT-TYPE
    SYNTAX      SignalStatusWithNA
    MAX-ACCESS  read-only
    STATUS      current
    DESCRIPTION
        "The operational state for incoming (RX) signal
        of the interface.

        down - A major fault has occurred

        degraded - The signal quality is impaired.

        up - The signal is OK.

"
        DEFVAL { down }
    ::= { clientIfEntry 66 }

clientIfMsAlarmIndicationSignalC2W OBJECT-TYPE
    SYNTAX      FaultStatus
    MAX-ACCESS  read-only
    STATUS      current
    DESCRIPTION
        "MS Alarm indication signal (MS-AIS) on the
        client side.
        Applicable for SDH/Sonet signal formats.

        A: An 'all ones' pattern is detected.

        D: The signal is recovered.

"
    ::= { clientIfEntry 67 }

clientIfMsAlarmIndicationSignalW2C OBJECT-TYPE
    SYNTAX      FaultStatus
    MAX-ACCESS  read-only
    STATUS      current
    DESCRIPTION
        "MS Alarm indication signal (MS-AIS) on the trunc
        side. Applicable for SDH/Sonet/IWDM signal formats.

        A: An 'all ones' pattern is detected.

        D: The signal is recovered.

"
    ::= { clientIfEntry 68 }

clientIfRemoteDefectIndication OBJECT-TYPE
    SYNTAX      FaultStatus
    MAX-ACCESS  read-only
    STATUS      current
    DESCRIPTION
        "Remote defect indication.
        Applicable for SDH/Sonet signal formats.

        A: RDI indication (in SDH/Sonet frame) active.

        D: RDI indication inactive.

"
    ::= { clientIfEntry 69 }

clientIfJ1TxTrailTrace        OBJECT-TYPE
    SYNTAX      DisplayString (SIZE(0..15))
    MAX-ACCESS  read-write
    STATUS      current
    DESCRIPTION
        "The J1 trail trace identifier(s) to be
        transmitted for the VC4s/VC3s related to this
        interface, in the line signal (STM16/OC48).

        This parameter can be used in two different
        modes, see j1TxTrailTraceInsertionMode.
        The insertionMode therefore decides what
        the transmitted string actually will look
        like.

        Set to empty string for default value:

        <IP address><space><subrack><slot><interface>
        xx.xx               y        w     z
        => 'xx.xx ywz'
        where:
        <IP address>: xx.xx
           The last 2 octets coded in hex.
           5 bytes.
        <space>:      1 byte.
        <subrack>:    y
           The subrack number coded in hex.
           1 byte.
        <slot>:       w
           The slot position coded n hex.
           Slot 16 and 17 will be coded as 0
           and 1 respectively.
           1 byte.
        <interface>:       z
            The logical numbering of the client interface
            coded in hex.
            Interface 1 <=> ports 1-2
                      2 <=>       3-4
                     10 <=>      19-20
            1 byte

"
    DEFVAL { "" }
    ::= { clientIfEntry 70 }

clientIfJ1TxTrailTraceInsertionMode OBJECT-TYPE
    SYNTAX      INTEGER {
                    vcGroupLevel (1),
                    individualVcLevel (2) }
    MAX-ACCESS  read-write
    STATUS      current
    DESCRIPTION
        "Controls how the J1 trail trace insertion
         should work, i.e. how the j1TxTrailTrace
         parameter shall be inserted in the line
         signal.

         Important: there is only one j1TxTrailTrace
         per interface, while each interface may
         me mapped to one or more VC4s/VC3s.

         For that reason there are two modes:

         - vcGroupLevel:
           The string j1TxTrailTrace is used identically
           for each VC (4/3) in the VC-group related to
           the interface.
           Each VC transmits exactly the same string.
           The string may be 15 bytes (1 byte CRC
           as added in HW).

         - individualVcLevel:
           In this mode the system adds a unique suffix
           for each VC (3/4). The trace for each VC
           will therefore be unique. The suffix will be 6
           bytes and contain the following information:

           <VCG Size><Seq number><VC position>
           ss         nn         pp
           => 'ssnnpp'
           where
           <VCG Size>:    ss
              The size of the VC group, i.e. the
              number of contained VCs.
              Value coded in hex
              2 bytes
           <Seq number>:  nn
              Sequence number of the VC within the
              VC group coded in hex.
              2 bytes
           <VC position>: pp
              The position of the VC (3/4) within
              the STM16 frame, coded in hex.
              2 bytes.

           The user part of the string is 9 bytes.
           6 bytes is added as suffix + 1 CRC byte.
"
    DEFVAL { individualVcLevel }
    ::= { clientIfEntry 71 }

clientIfTrxFailed OBJECT-TYPE
    SYNTAX      FaultStatus
    MAX-ACCESS  read-only
    STATUS      current
    DESCRIPTION
        "A transceiver hardware failure is detected.

        A: The transceiver fails.

        D: The transceiver is replaced.

"
    ::= { clientIfEntry 72 }

clientIfDisabled OBJECT-TYPE
    SYNTAX      FaultStatus
    MAX-ACCESS  read-only
    STATUS      current
    DESCRIPTION
        "The interface is disabled.

        A: Interface disabled.

        D: Interface enabled.

"
    ::= { clientIfEntry 73 }

clientIfLoopback OBJECT-TYPE
    SYNTAX      FaultStatus
    MAX-ACCESS  read-only
    STATUS      current
    DESCRIPTION
        "The interface is set in loopback mode.

        A: Loopback enabled.

        D: Loopback disabled.

"
    ::= { clientIfEntry 74 }

clientIfVcGroupFailedW2C OBJECT-TYPE
    SYNTAX      FaultStatus
    MAX-ACCESS  read-only
    STATUS      current
    DESCRIPTION
        "The received line signal contains a VC
         mapped to this interface, that is
         faulty, e.g. unequipped.

         Please note that this fault is in the
         LINE SIGNAL, but is presented at the client.

        A: Some VC(3/4) is failed

        D: All VCs (3/4) are OK

"
    ::= { clientIfEntry 75 }

clientIfReadJ1 OBJECT-TYPE
    SYNTAX      CommandString
    MAX-ACCESS  read-only
    STATUS      current
    DESCRIPTION
        "Read the received J1 for the VC4/VC3 in the
         STM16 frame associated to this interface.

        Synopsis: readJ1

"
    ::= { clientIfEntry 76 }


clientIfClientSignalFailed OBJECT-TYPE
    SYNTAX      FaultStatus
    MAX-ACCESS  read-only
    STATUS      current
    DESCRIPTION
        "The received line signal contains a VC
         mapped to this interface, that is
         faulty, e.g. unequipped.

         Please note that this fault is in the
         LINE SIGNAL, but is presented at the client.

"
    ::= { clientIfEntry 77 }


clientIfAuLossOfPointer OBJECT-TYPE
    SYNTAX      FaultStatus
    MAX-ACCESS  read-only
    STATUS      current
    DESCRIPTION
        "Loss of pointer.

"
    ::= { clientIfEntry 78 }


clientIfGfpLossOfFrame OBJECT-TYPE
    SYNTAX      FaultStatus
    MAX-ACCESS  read-only
    STATUS      current
    DESCRIPTION
        "GFP Loss of frame.

"
    ::= { clientIfEntry 79 }

clientIfHighSpeed OBJECT-TYPE
    SYNTAX      Gauge32 (12500..491520)
    MAX-ACCESS  read-create
    STATUS      current
    DESCRIPTION
        "The expected signal bit rate in units of
        1,000,000 bits (Mb) per second. If this object
        reports a value of 'n' then the speed of the
        interface is somewhere in the range of 'n-500,000'
        to 'n+499,999'. Board tpQMri has a upper limit of
        2700Mb/s.

"
    DEFVAL { 125000 }
    ::= { clientIfEntry 80 }

clientIfActualFormat OBJECT-TYPE
    SYNTAX      SignalFormat
    MAX-ACCESS  read-only
    STATUS      current
    DESCRIPTION
        "The actual signal format.

"
    DEFVAL { unused }
    ::= { clientIfEntry 81 }

clientIfRdiIntrusionMode OBJECT-TYPE
    SYNTAX      INTEGER {
                    disabled (1),
                    enabled (2) }
    MAX-ACCESS  read-only
    STATUS      current
    DESCRIPTION
        "Indicates whether RDI information should be
        inserted in the transmitted signal.

        disabled - No RDI information is inserted in the
                   transmitted signal.

        enabled - RDI information is inserted in the
                  transmitted signal.

"
    DEFVAL { disabled }
    ::= { clientIfEntry 82 }

clientIfMuxQuadVc4 OBJECT-TYPE
    SYNTAX      Unsigned32 (1..4)
    MAX-ACCESS  read-create
    STATUS      current
    DESCRIPTION
        "States which quadrant of the payload
         that the interface is connected to
         in rx direction. (outgoing line)

"
    DEFVAL { 1 }
    ::= { clientIfEntry 83 }

clientIfDemuxQuadVc4 OBJECT-TYPE
    SYNTAX      Unsigned32 (1..4)
    MAX-ACCESS  read-create
    STATUS      current
    DESCRIPTION
        "States whitch quadrant of the payload
         that the interface is connected to
         in tx direction. (outgoing client)

"
    DEFVAL { 1 }
    ::= { clientIfEntry 84 }

clientIfCcConnectionMode OBJECT-TYPE
    SYNTAX       INTEGER {
                     connected (1),
                     disconnected (2) }
    MAX-ACCESS   read-create
    STATUS       current
    DESCRIPTION
        "controls if DemuxPayloadQuad is same
         as MuxPayloadQuad
         (same => connected, not same => disconnected)

"
   DEFVAL { 1 }
   ::= { clientIfEntry 85 }

clientIfCcConfigurationCommand OBJECT-TYPE
    SYNTAX      CommandString
    MAX-ACCESS  read-only
    STATUS      current
    DESCRIPTION
        "Command to change the crossconnect,

        If no arguments are given, the user will be prompted.

"
    ::= { clientIfEntry 86 }

clientIfIllegalSignalFormat OBJECT-TYPE
    SYNTAX      FaultStatus
    MAX-ACCESS  read-only
    STATUS      current
    DESCRIPTION
        "IllegalSignalFormat.

        A(ctivation): Actual Format does NOT match
        expected Format.

        D(e-activation): Actual Format does match
        expected Format.

"
    ::= { clientIfEntry 87 }

clientIfSynchProtPortId OBJECT-TYPE
    SYNTAX      INTEGER {
                        portA (1),
                        portB (2) }
    MAX-ACCESS  read-only
    STATUS      current
    DESCRIPTION
        "The Id for this port in the synch prot group,
        to identify the port. (A or B)

"
    DEFVAL { portA }
    ::= { clientIfEntry 88 }

clientIfSynchProtGroupMemberPort OBJECT-TYPE
    SYNTAX      PortNumber
    MAX-ACCESS  read-only
    STATUS      current
    DESCRIPTION
        "The port number for the TX side of the port
        that is in this synch protection group.

"
    DEFVAL { 0 }
    ::= { clientIfEntry 89 }

clientIfSynchProtGroupStatus OBJECT-TYPE
    SYNTAX      INTEGER {
                    bothDown (1),
                    bothUp (2),
                    portADownBUp (3),
                    portAUpBDown (4) }
    MAX-ACCESS  read-only
    STATUS      current
    DESCRIPTION
        "Note: This object is deprecated.

        The operational state for the protection group.

        bothDown - both sides down

        bothUp   - both sides up

        ADownBUp - left side down, right side up

        AUpBDown - left side up, right side down

"
    DEFVAL { 1 }
    ::= { clientIfEntry 90 }

clientIfSynchProtActivePort OBJECT-TYPE
    SYNTAX      INTEGER {
                    none (1),
                    portA (2),
                    portB (3) }
    MAX-ACCESS  read-only
    STATUS      current
    DESCRIPTION
        "The operational state for the protection group.

        none - no side is active.

        A - the A port is active.

        B - the B port is active.

"
    DEFVAL { 1 }
    ::= { clientIfEntry 91 }

clientIfSynchProtPortStatus OBJECT-TYPE
    SYNTAX      INTEGER {
                    down (1),
                    up (2) }
    MAX-ACCESS  read-only
    STATUS      current
    DESCRIPTION
        "The operational synch protection state
        for this port in the synch protection group.

        down - this port is out of service.

        up - this port is active.

"
    DEFVAL { 1 }
    ::= { clientIfEntry 92 }

clientIfSynchProtToggleActivePort OBJECT-TYPE
    SYNTAX      CommandString
    MAX-ACCESS  read-only
    STATUS      current
    DESCRIPTION
        "Command to toggle which port is active in the synch
        prot group

"
    ::= { clientIfEntry 93 }

clientIfNearEndLoopbackTimeout OBJECT-TYPE
    SYNTAX      Integer32 (0..1200)
    MAX-ACCESS  read-create
    STATUS      current
    DESCRIPTION
        "Timeout for near end loopback (a.k.a. facility
        loopback) to make sure connection to node is not
        lost if ppp link is broken.
        The unit is hours. 0.1 means 6 minutes.

"
    DEFVAL { 10 }
    ::= { clientIfEntry 94 }

clientIfNearEndLoopbackEnabled OBJECT-TYPE
    SYNTAX      FaultStatus
    MAX-ACCESS  read-only
    STATUS      current
    DESCRIPTION
        "Near end loopback (a.k.a. facility loopback)
        is enabled.

"
    ::= { clientIfEntry 95 }

clientIfChangeNearEndLoopbackCommand OBJECT-TYPE
    SYNTAX      CommandString
    MAX-ACCESS  read-only
    STATUS      current
    DESCRIPTION
        "Command to change near end loopback (a.k.a.
        facility loopback) and loopbacktimeout

"
    ::= { clientIfEntry 96 }

clientIfFarEndLoopbackEnabled OBJECT-TYPE
    SYNTAX      FaultStatus
    MAX-ACCESS  read-only
    STATUS      current
    DESCRIPTION
        "Far end loopback (a.k.a. terminal loopback)
        is enabled.

"
    ::= { clientIfEntry 97 }

clientIfFarEndLoopbackTimeout OBJECT-TYPE
    SYNTAX      Integer32 (0..1200)
    MAX-ACCESS  read-create
    STATUS      current
    DESCRIPTION
        "Timeout for far end loopback (a.k.a. terminal
        loopback) to make sure connection to node is
        not lost if ppp link is broken.
        The unit is hours. 0.1 means 6 minutes.

"
    DEFVAL { 10 }
    ::= { clientIfEntry 98 }

clientIfChangeFarEndLoopbackCommand OBJECT-TYPE
    SYNTAX      CommandString
    MAX-ACCESS  read-only
    STATUS      current
    DESCRIPTION
        "Command to change far end loopback (a.k.a.
        terminal loopback) and loopbacktimeout

"
    ::= { clientIfEntry 99 }

clientIfFormatNotSupportedByHw OBJECT-TYPE
    SYNTAX      FaultStatus
    MAX-ACCESS  read-only
    STATUS      current
    DESCRIPTION
        "The HW revision does not support
        the selected signal format.

"
    ::= { clientIfEntry 100 }

clientIfLaserMode OBJECT-TYPE
    SYNTAX      INTEGER {
                    on (1),
                    als (2) }
    MAX-ACCESS  read-write
    STATUS      current
    DESCRIPTION
        "The administrative state of the TX-side laser.
        This is only used when signal format is ddgbeLine.

        on - The laser is turned on.

        als - Automatic Laser Shutdown/Turn-Off
        when lossOfSignal is detected on the RX side of
        the trunk interface.

"
    DEFVAL { als }
    ::= { clientIfEntry 101 }

clientIfAlarmIndicationSignalLineC2W OBJECT-TYPE
    SYNTAX      FaultStatus
    MAX-ACCESS  read-only
    STATUS      current
    DESCRIPTION
        "Alarm indication signal Line (AIS-L) on the
        client side.
        Applicable for Sonet signal formats.

        A: An 'all ones' Sonet signal is detected.

        D: Sonet signal recovered.

"
    ::= { clientIfEntry 102 }

clientIfFarEndClientFailure OBJECT-TYPE
    SYNTAX      FaultStatus
    MAX-ACCESS  read-only
    STATUS      current
    DESCRIPTION
        "Failure on far end client.

"
    ::= { clientIfEntry 103 }

clientIfOHTransparency OBJECT-TYPE
    SYNTAX      INTEGER {
                    off (1),
                    on (2) }
    MAX-ACCESS  read-write
    STATUS      current
    DESCRIPTION

        "The 'OH Transparency' setting shall be set to 'off'
        for standard SDH/SONET mode. Does not work when
        client wrapper is enabled.

        When set to 'on', the following tributary OH-bytes
        are transparently transported:
        E1, E2, F1, D1-D3, D4-D12, K1, K2, J0

        The following are always terminated:
        B1, B2, M1 and S1.

"
   DEFVAL { off }
   ::= { clientIfEntry 104 }

clientIfConnectedLine OBJECT-TYPE
    SYNTAX       Unsigned32 (0..2147483647)
    MAX-ACCESS   read-only
    STATUS       current
    DESCRIPTION
      "The line ports that this client port is connected to.

"
    ::= { clientIfEntry 105 }

clientIfForwardingErrorCorrectionMode OBJECT-TYPE
    SYNTAX      INTEGER {
                    disabled (1),
                    enabled (2),
                    auto (3) }
    MAX-ACCESS  read-write
    STATUS      current
    DESCRIPTION
        "The administrative state of the forwarding error
        correction function.

        disabled - FEC is disabled.

        enabled - FEC is activated.

        auto - autonegotiation is used to enable or disable
               FEC.  Note, auto is not available for all
               boards.

"
    DEFVAL { enabled }
    ::= { clientIfEntry 106 }

clientIfNoFrequencySet OBJECT-TYPE
    SYNTAX      FaultStatus
    MAX-ACCESS  read-only
    STATUS      current
    DESCRIPTION
        "The tunable laser frequency has not been set.

        A: Tunable laser frequency is not set.

        D: Tunable laser frequency is set.

"
    ::= { clientIfEntry 107 }

clientIfJitterAttenuatorBW OBJECT-TYPE
    SYNTAX      INTEGER {
                    option1 (0),
                    option2 (1),
                    notUsed (2) }
    MAX-ACCESS  read-write
    STATUS      current
    DESCRIPTION
        "Determines the wander/jitter transfer bandwidth
        of the wander/jitter attenuator.
        With Option 1, the bandwidth is within 1 - 10 Hz,
        and with Option 2, the bandwidth is below 0.1 Hz.

        The values are defined according to
             - G.813 for SDH, and
             - G.8262 for synchronous ethernet

"
    DEFVAL { option1 }
    ::= { clientIfEntry 108 }

clientIfConnectionStatus OBJECT-TYPE
    SYNTAX      DisplayString
    MAX-ACCESS  read-only
    STATUS      current
    DESCRIPTION
        "Shows the name of the wdm port and
        possible subchannel/vc4 that it is connected to
        or Unconnected if not connected.

"
    DEFVAL { "Not connected" }
    ::= { clientIfEntry 109 }

clientIfLoopFilterUnlocked OBJECT-TYPE
    SYNTAX      FaultStatus
    MAX-ACCESS  read-only
    STATUS      current
    DESCRIPTION
        "The loopfilter is unlocked.
         This is applicable for synchronous formats.

        A: Loopfilter is unlocked

        D: Loopfilter is locked

"
    ::= { clientIfEntry 110 }

clientIfCableLength OBJECT-TYPE
    SYNTAX      INTEGER {
                    feet133 (0),
                    feet266 (1),
                    feet399 (2),
                    feet533 (3),
                    feet655 (4)
                }
    MAX-ACCESS  read-write
    STATUS      current
    DESCRIPTION
        "The 'Cable length' is applicable for SONET mode
        (T1).

         The settings are for short haul (intra-building) T1
         networks and will adjust the power of the
         transmitted signal to compensate for the
         attenuation of the cable. This is important when
         connecting to older T1 equipment.

         This setting can also be used to equalize the
         signal at the far-end receiver to avoid cross-talk
         with other signals.

         The values below are for an obsolete ABAM 600 cable
         (Western Electric), but a modern CAT5e cable will
         have similar performance.

         LINE BUILD-OUT
         Attenuation values are measured at 0.772 MHz
         0  -  133 ft,  0     - 40.5 m,   0.6 dB
         133 - 266 ft,  40.5  - 81.1 m,   1.2 dB
         266 - 399 ft,  81.1  - 121.6 m,  1.8 dB
         399 - 533 ft,  121.6 - 162.5 m,  2.4 dB
         533 - 655 ft,  162.5 - 199.6 m,  3.0 dB

"
   DEFVAL { feet133 }
   ::= { clientIfEntry 111 }

clientIfConnectedForeignIndex OBJECT-TYPE
    SYNTAX      Unsigned32 (0..2147483647)
    MAX-ACCESS  read-write
    STATUS      current
    DESCRIPTION
        "Shows the index of the connected interface.
        Or 0 if unconnected.

"
    DEFVAL { 0 }
    ::= { clientIfEntry 112 }

clientIfDisconnect OBJECT-TYPE
    SYNTAX      CommandString
    MAX-ACCESS  read-only
    STATUS      current
    DESCRIPTION
        "Disconnect existing crossConnections

"
    ::= { clientIfEntry 113 }

clientIfOHTransparencyBitMask OBJECT-TYPE
    SYNTAX       Unsigned32 (0..2147483647)
    MAX-ACCESS   read-create
    STATUS       current
    DESCRIPTION
      "The OH transparency bitmask.
       Bits:
       K1K2   = 0x01
       E1E2   = 0x02
       F1     = 0x04
       D1-D3  = 0x08
       D4-D12 = 0x10
       B1     = 0x20
       B2     = 0x40
       E1     = 0x80
       E2     = 0x100
       J0     = 0x200

"
     DEFVAL { 0 }
    ::= { clientIfEntry 114 }

clientIfOHTransparencyString OBJECT-TYPE
    SYNTAX      DisplayString
    MAX-ACCESS  read-only
    STATUS      current
    DESCRIPTION
        "OH transparency bytes tells if J0, rest
        of RSOH/Section OH and/or MSOH/Line OH are
        transparent or not.
        When RSOH/Section OH is set to transparent the bytes
        E1, F1, D1-D3 and B1 is transported tran-
        sparent from client to line and vice versa.
        When MSOH is set to transparent the bytes E2,
        D4-D12, B2 and K1K2 are sent transported
        transparent from client to line.

"
    DEFVAL { "" }
    ::= { clientIfEntry 115 }

clientIfOHTransparencySet OBJECT-TYPE
    SYNTAX      CommandString
    MAX-ACCESS  read-only
    STATUS      current
    DESCRIPTION
        "Set which bytes that should be OH transparent

"
    ::= { clientIfEntry 116 }

clientIfAuAlarmIndicationSignalC2W OBJECT-TYPE
    SYNTAX      FaultStatus
    MAX-ACCESS  read-only
    STATUS      current
    DESCRIPTION
        "Alarm indication signal (AIS) on the
        client-side.
        Applicable for SDH/Sonet signal formats.

        A: An 'all ones' SDH signal is detected.

        D: SDH signal recovered.
"
    ::= { clientIfEntry 117 }

clientIfAuLossOfPointerC2W OBJECT-TYPE
    SYNTAX      FaultStatus
    MAX-ACCESS  read-only
    STATUS      current
    DESCRIPTION
        "Loss of pointer detected on the client-side.
        Applicable for SDH/Sonet signal formats.

        A: A loss of pointer is detected.

        D: SDH signal recovered.

"
    ::= { clientIfEntry 118 }

clientIfAuLossOfPointerW2C OBJECT-TYPE
    SYNTAX      FaultStatus
    MAX-ACCESS  read-only
    STATUS      current
    DESCRIPTION
        "Loss of pointer detected on the line-side.
        Applicable for SDH/Sonet signal formats.

        A: A loss of pointer is detected.

        D: SDH signal recovered.

"
    ::= { clientIfEntry 119 }

clientIfEthStandbyIndicator OBJECT-TYPE
    SYNTAX      INTEGER {
                    disabled (1),
                    enabled (2) }
    MAX-ACCESS  read-only
    STATUS      current
    DESCRIPTION
        "Shows if this port is in standby state.
        Used with hub protection.

"
        DEFVAL { disabled }
    ::= { clientIfEntry 120 }

clientIfAuAlarmIndicationSignalW2CSonet OBJECT-TYPE
    SYNTAX      FaultStatus
    MAX-ACCESS  read-only
    STATUS      current
    DESCRIPTION
        "Alarm indication signal (AIS-P) on the line-side.

        A: An 'all ones' Sonet signal is detected.

        D: Sonet signal recovered.
"
    ::= { clientIfEntry 121 }

clientIfAuAlarmIndicationSignalC2WSonet OBJECT-TYPE
    SYNTAX      FaultStatus
    MAX-ACCESS  read-only
    STATUS      current
    DESCRIPTION
        "Alarm indication signal (AIS-P) on the
        client-side.

        A: An 'all ones' Sonet signal is detected.

        D: Sonet signal recovered.
"
    ::= { clientIfEntry 122 }

clientIfAuLossOfPointerC2WSonet OBJECT-TYPE
    SYNTAX      FaultStatus
    MAX-ACCESS  read-only
    STATUS      current
    DESCRIPTION
        "Loss of pointer detected on the client-side.

        A: A loss of pointer is detected.

        D: Sonet signal recovered.

"
    ::= { clientIfEntry 123 }

clientIfAuLossOfPointerW2CSonet OBJECT-TYPE
    SYNTAX      FaultStatus
    MAX-ACCESS  read-only
    STATUS      current
    DESCRIPTION
        "Loss of pointer detected on the line-side.

        A: A loss of pointer is detected.

        D: Sonet signal recovered.

"
    ::= { clientIfEntry 124 }

clientIfTransceiverNoLoopback OBJECT-TYPE
SYNTAX      FaultStatus
MAX-ACCESS  read-only
STATUS      current
DESCRIPTION
    "The inserted transceiver does not support
     the given loopback command.

"
::= { clientIfEntry 125 }

clientIfFecFailure OBJECT-TYPE
    SYNTAX      FaultStatus
    MAX-ACCESS  read-only
    STATUS      current
    DESCRIPTION
        "Too many errors to get valid FEC statistics. It is not
         possible to run control loops based on FEC statistics.

        A: Too many errors to get valid FEC statistics.

        D: The FEC statistics is valid.

"
    ::= { clientIfEntry 126 }

clientIfLaneAlignmentError OBJECT-TYPE
    SYNTAX      FaultStatus
    MAX-ACCESS  read-only
    STATUS      current
    DESCRIPTION
        "Indicates whether multi-lane
        BASE-R PCS (Physical Coding Sublayer)
        has locked and aligned all received lanes.

        A: PCS receive lanes not locked and aligned.

        D: PCS receive lanes locked and aligned.

"
    ::= { clientIfEntry 127 }

clientIfFecCorrectedZeros OBJECT-TYPE
    SYNTAX      Unsigned32
    MAX-ACCESS  read-only
    STATUS      current
    DESCRIPTION
        "The number of corrected zeros.
"
    ::= { clientIfEntry 128 }

clientIfFecCorrectedOnes OBJECT-TYPE
    SYNTAX      Unsigned32
    MAX-ACCESS  read-only
    STATUS      current
    DESCRIPTION
        "The number of corrected ones.
"
    ::= { clientIfEntry 129 }

clientIfSignalDegraded OBJECT-TYPE
    SYNTAX      FaultStatus
    MAX-ACCESS  read-only
    STATUS      current
    DESCRIPTION
        "Too many error corrected.
        If more errors are corrected
        it might effect the client signal
        in a negative way.
"
    ::= { clientIfEntry 130 }

clientIfFecType OBJECT-TYPE
    SYNTAX      INTEGER {
                    disabled (1),
                    gFec (2),
                    superFecI4 (3),
                    superFecI7 (4),
                    sdFec (5) }
    MAX-ACCESS  read-write
    STATUS      current
    DESCRIPTION
        "Set FEC scheme.
        disabled   -- none specific FEC scheme is enabled.
        gFec       -- GFEC RS(255,239) FEC scheme,
                      according to ITU.T G.975
        superFecI4 -- Super FEC I.4 FEC scheme,
                      according to ITU-T G.975.1
        superFecI7 -- Super FEC I.7 FEC scheme,
                      according to ITU-T G.975.1
        sdFec      -- Proprietary Soft Decision FEC scheme.

"
    DEFVAL { disabled }
    ::= { clientIfEntry 131 }

clientIfSignalDegradeThreshold OBJECT-TYPE
    SYNTAX      BerLevelMTOSI
    MAX-ACCESS  read-write
    STATUS      current
    DESCRIPTION
        "The alarm Signal Degraded shall be signalled
         when BER reaches a limit.
         The value will be affecting all ports.

         Predefined BER levels
         rxBerLevel1 = 1E-12
         rxBerLevel2 = 1E-13
         rxBerLevel3 = 1E-15

         OSNRMargin1 = 0.5 dB margin with respect to FEC cliff
         OSNRMargin2 = 1.0 dB margin with respect to FEC cliff

"
    DEFVAL { rxBerLevel2 }
    ::= { clientIfEntry 132 }

clientIfExpectedOpticalLayerMapping OBJECT-TYPE
    SYNTAX      OpticalLayerMappingType
    MAX-ACCESS  read-write
    STATUS      current
    DESCRIPTION
        "The expected optical layer mapping.

"
    DEFVAL { singleOpticalChannel }
    ::= { clientIfEntry 133 }

clientIfActualOpticalLayerMapping OBJECT-TYPE
    SYNTAX      OpticalLayerMappingType
    MAX-ACCESS  read-only
    STATUS      current
    DESCRIPTION
        "The actual optical layer mapping.

"
    ::= { clientIfEntry 134 }

clientIfConfigurationMismatch OBJECT-TYPE
    SYNTAX      FaultStatus
    MAX-ACCESS  read-only
    STATUS      current
    DESCRIPTION
        "The inserted transceiver does not support the
        configuration of the optical layer mapping.

        A: A transceiver with other supported optical layer
           mapping than the requested mapping is inserted.

        D: The transceiver with the non-requested optical
           layer mapping is removed, or the object is reconfigured.

"
    ::= { clientIfEntry 135 }

clientIfChromaticDispersion OBJECT-TYPE
    SYNTAX      Integer32
    MAX-ACCESS  read-only
    STATUS      current
    DESCRIPTION
        "Received chromatic dispersion that describe the spreading of a light
         pulse as it travels down a fiber when light pulses launched close together.

"
    ::= { clientIfEntry 136 }

clientIfDifferentialGroupDelay OBJECT-TYPE
    SYNTAX      Unsigned32
    MAX-ACCESS  read-only
    STATUS      current
    DESCRIPTION
        "The arrival time difference between two polarization states at
         the output of the media (fiber).

"
    ::= { clientIfEntry 137 }

clientIfTxState OBJECT-TYPE
    SYNTAX      TrxTxState
    MAX-ACCESS  read-only
    STATUS      current
    DESCRIPTION
        "The operational state of the transiver for outgoing (TX) signal.
          - Init started
          - Init ready
          - Data path locked
          - Laser ready off
          - Laser ready
          - Laser bias ready
          - Ready

"
    ::= { clientIfEntry 138 }

clientIfRxState OBJECT-TYPE
    SYNTAX      TrxRxState
    MAX-ACCESS  read-only
    STATUS      current
    DESCRIPTION
        "The operational state of the transiver for outgoing (RX) signal.
          - Init started
          - Init ready
          - Frequency ready
          - Input signal received
          - A/D Converter ready
          - Dispersion compensated
          - Ready

"
    ::= { clientIfEntry 139 }

clientIfIdx OBJECT-TYPE
    SYNTAX      Integer32   (-1..2147483647)
    MAX-ACCESS  read-create
    STATUS      current
    DESCRIPTION
        "Internal object reference

"
    DEFVAL { -1  }
    ::= { clientIfEntry 140 }

clientIfIfNo OBJECT-TYPE
    SYNTAX      PortNumber
    MAX-ACCESS  read-create
    STATUS      current
    DESCRIPTION
        "The physical interface number of the actual multi-connector port.

"
    DEFVAL { 1 }
    ::= { clientIfEntry 141 }

clientIfIdxIf OBJECT-TYPE
    SYNTAX      Integer32   (-1..2147483647)
    MAX-ACCESS  read-create
    STATUS      current
    DESCRIPTION
        "Internal object reference  of the actual multi-connector port.

"
    DEFVAL { -1  }
    ::= { clientIfEntry 142 }

clientIfUpPortId OBJECT-TYPE
    SYNTAX      Integer32   (-1..2147483647)
    MAX-ACCESS  read-only
    STATUS      current
    DESCRIPTION
        "Internal port reference for traffic unit.
"
    DEFVAL { -1  }
    ::= { clientIfEntry 143 }


clientIfNoOfLanes OBJECT-TYPE
    SYNTAX      Integer32   (-1..2147483647)
    MAX-ACCESS  read-create
    STATUS      current
    DESCRIPTION
        "Number of lanes on port
"
    DEFVAL { -1  }
    ::= { clientIfEntry 144 }

clientIfFecCorrectedBits OBJECT-TYPE
    SYNTAX      Unsigned32
    MAX-ACCESS  read-only
    STATUS      current
    DESCRIPTION
        "FEC counter. Number of corrected bits
"
    ::= { clientIfEntry 145 }

clientIfOSNRMargin OBJECT-TYPE
    SYNTAX      Integer32
    MAX-ACCESS  read-only
    STATUS      current
    DESCRIPTION
        "Optical signal-to-noise ratio margin (dB/0.1nm), based on calculation from rate of corrected bits.
"
    ::= { clientIfEntry 146 }

clientIfExpectedPhysicalLayerMapping OBJECT-TYPE
    SYNTAX      PhysicalLayerMappingType
    MAX-ACCESS  read-write
    STATUS      current
    DESCRIPTION
        "The expected physical layer mapping.

"
    DEFVAL { dualFiber }
    ::= { clientIfEntry 147 }

clientIfSignalDirection OBJECT-TYPE
    SYNTAX      SignalDirection
    MAX-ACCESS  read-only
    STATUS      current
    DESCRIPTION
        "Indicates the direction of the signal.

        rx    - Inbound direction

        tx    - Outbound direction

        biDir - Bidirectional

        txRx  - Both Tx and Rx

"
    DEFVAL { notAvailable }
    ::= { clientIfEntry 148 }


clientIfAid OBJECT-TYPE
    SYNTAX      DisplayString
    MAX-ACCESS  read-only
    STATUS      current
    DESCRIPTION
        "The access identifier (AID) of the interface.
         The format is according to GR-833.

"
    ::= { clientIfEntry 149 }

clientIfPhysicalLocation OBJECT-TYPE
    SYNTAX      DisplayString
    MAX-ACCESS  read-only
    STATUS      current
    DESCRIPTION
        "The physical location of the if.
         The format is according to GR-833.

"
    ::= { clientIfEntry 150 }

clientIfTrxCommunicationFailure OBJECT-TYPE
     SYNTAX      FaultStatus
    MAX-ACCESS  read-only
    STATUS      current
    DESCRIPTION
        "The board is unable to communicate with the transceiver.

        alarm: Protocol errors detected on the transceiver control link.

        ok: No communication errors detected on the transceiver control link.

"
    ::= { clientIfEntry 151 }

clientIfTribPortId OBJECT-TYPE
    SYNTAX      Unsigned32
    MAX-ACCESS  read-only
    STATUS      current
    DESCRIPTION
        "Tributary port id.

"
    DEFVAL { 0 }
    ::= { clientIfEntry 152 }

clientIfIfType OBJECT-TYPE
    SYNTAX      InterfaceType
    MAX-ACCESS  read-write
    STATUS      current
    DESCRIPTION
        "Type of interface (Individual or bundled).

"
    DEFVAL { individual }
    ::= { clientIfEntry 153 }

clientIfConfigurationCommandSNMP OBJECT-TYPE
    SYNTAX      CommandString
    MAX-ACCESS  read-only
    STATUS      current
    DESCRIPTION
        "Command to change the signal format, and, if
        applicable, also the mode (framed, transparent) via SNMP.

"
    ::= { clientIfEntry 154 }

clientIfTrxPowerOutOfRange OBJECT-TYPE
    SYNTAX      FaultStatus
    MAX-ACCESS  read-only
    STATUS      current
    DESCRIPTION
        "The power classification of the transceiver exceeds the design limit of the board.

        alarm: A transceiver with a power classification that exceeds
               the design limit of the board is inserted.

        ok: The transceiver with a power classification that exceeds
            the design limit of the board is removed.

"
    ::= { clientIfEntry 155 }

-- ----------------------------------------------------
-- CLIENT VC-4 objects
-- ----------------------------------------------------

clientVc4Table  OBJECT-TYPE
    SYNTAX      SEQUENCE OF ClientVc4Entry
    MAX-ACCESS  not-accessible
    STATUS      current
    DESCRIPTION
        "The interface list."
    ::= { clientVc4List 1 }

clientVc4Entry OBJECT-TYPE
    SYNTAX      ClientVc4Entry
    MAX-ACCESS  not-accessible
    STATUS      current
    DESCRIPTION
        "An entry in the interface list.

"
    INDEX { clientVc4Index }
    ::= { clientVc4Table 1 }

ClientVc4Entry ::=
    SEQUENCE {
        clientVc4Index                     Unsigned32,
        clientVc4Name                      MgmtNameString,
        clientVc4Descr                     DisplayString,
        clientVc4Subrack                   SubrackNumber,
        clientVc4Slot                      SlotNumber,
        clientVc4TxPort                    PortNumber,
        clientVc4RxPort                    PortNumber,
        clientVc4Vc4                       Unsigned32,
        clientVc4ObjectProperty            ObjectProperty,
        clientVc4AuAlarmIndicationSignal   INTEGER,
        clientVc4AuLossOfPointer           INTEGER,
        clientVc4RxSignalStatus            INTEGER,
        clientVc4ConcatenationStatus       INTEGER,
        clientVc4PayloadStatus             INTEGER,
        clientVc4ConnectionStatus          DisplayString }

clientVc4Index OBJECT-TYPE
    SYNTAX      Unsigned32 (1..2147483647)
    MAX-ACCESS  read-only
    STATUS      current
    DESCRIPTION
        "An arbitrary index assigned to each if entry.

"
    ::= { clientVc4Entry 1 }

clientVc4Name OBJECT-TYPE
    SYNTAX      MgmtNameString
    MAX-ACCESS  read-only
    STATUS      current
    DESCRIPTION
        "The management name of the vc4,
        e.g. vc4:1:2:1-2:8 where the first number
        indicates sub-rack, the second slot number and
        the third/forth are the port numbers. The last
        number is the vc4 id within the STM16 frame.

"
    ::= { clientVc4Entry 2 }

clientVc4Descr OBJECT-TYPE
    SYNTAX      DisplayString
    MAX-ACCESS  read-write
    STATUS      current
    DESCRIPTION
        "User configurable label.

"
    DEFVAL { "" }
    ::= { clientVc4Entry 3 }

clientVc4Subrack OBJECT-TYPE
    SYNTAX      SubrackNumber
    MAX-ACCESS  read-only
    STATUS      current
    DESCRIPTION
        "The number of the subrack where the vc4 is
        located.

"
    ::= { clientVc4Entry 4 }

clientVc4Slot OBJECT-TYPE
    SYNTAX      SlotNumber
    MAX-ACCESS  read-only
    STATUS      current
    DESCRIPTION
        "The number of the slot where the vc4 is
        located.

"
    ::= { clientVc4Entry 5 }

clientVc4TxPort OBJECT-TYPE
    SYNTAX      PortNumber
    MAX-ACCESS  read-only
    STATUS      current
    DESCRIPTION
        "The number of the port where the TX-side of the
        vc4 is located.

"
    ::= { clientVc4Entry 6 }

clientVc4RxPort OBJECT-TYPE
    SYNTAX      PortNumber
    MAX-ACCESS  read-only
    STATUS      current
    DESCRIPTION
        "The number of the port where the RX-side of the
        vc4 is located.

"
    ::= { clientVc4Entry 7 }

clientVc4Vc4 OBJECT-TYPE
    SYNTAX      Unsigned32 (1..16)
    MAX-ACCESS  read-only
    STATUS      current
    DESCRIPTION
        "The id of the vc4/STS3/STS1 within the STM16/OC192 frame.

"
    ::= { clientVc4Entry 8 }

clientVc4ObjectProperty OBJECT-TYPE
    SYNTAX      ObjectProperty
    MAX-ACCESS  read-only
    STATUS      current
    DESCRIPTION
        "Property mask.

"
    ::= { clientVc4Entry 9 }

clientVc4AuAlarmIndicationSignal OBJECT-TYPE
    SYNTAX      INTEGER {
                    ok (1),
                    alarm (2) }
    MAX-ACCESS  read-only
    STATUS      current
    DESCRIPTION
        "Alarm indication signal (AIS).
        Applicable for SDH/Sonet signal formats.

        A: An 'all ones' SDH/Sonet signal is detected.

        D: SDH/Sonet signal recovered.
"
    ::= { clientVc4Entry 10 }

clientVc4AuLossOfPointer OBJECT-TYPE
    SYNTAX      INTEGER {
                    ok (1),
                    alarm (2) }
    MAX-ACCESS  read-only
    STATUS      current
    DESCRIPTION
        "Loss of pointer detected.
        Applicable for SDH/Sonet signal formats.

        A: A loss of pointer is detected.

        D: SDH/Sonet signal recovered.

"
    ::= { clientVc4Entry 11 }

clientVc4RxSignalStatus OBJECT-TYPE
    SYNTAX      INTEGER {
                        down (1),
                        degraded (2),
                        up (3) }
    MAX-ACCESS  read-only
    STATUS      current
    DESCRIPTION
        "The operational state for incoming (RX) signal
        of the interface.

        down - A fault that would lead to a protection
        switch has occurred.

        degraded - The signal quality is impaired.

        up - The signal is OK.

"
    ::= { clientVc4Entry 12 }

clientVc4ConcatenationStatus OBJECT-TYPE
    SYNTAX      INTEGER {
                        on (1),
                        off (2),
                        vc3 (3),
                        vc4 (4),
                        vc4x4c (5),
                        vc4x16c (6),
                        vc4x64c (7),
            sts1 (8),
            sts3c (9),
            sts12c (10),
                        unknown (11) }
    MAX-ACCESS  read-only
    STATUS      current
    DESCRIPTION
        "Describes if and how the VC4s are concatenated.

        on - Concatenation is used.

        off - No concatenation is used.

        can be vc3 (STS-1),
        vc4 (STS-3, STM1/OC3),
        vc4x4c (STS-12, STM4/OC12),
        vc4x16c (STS-48, STM16/OC48),
        vc4x64c (STS-128, STM64/OC192),
        sts1    (STS-1),
    sts3c   (STS-3 concatenated),
    sts12c  (STS-12 concatenated).

"
    ::= { clientVc4Entry 13 }

clientVc4PayloadStatus OBJECT-TYPE
    SYNTAX      INTEGER {
                        equipped (1),
                        unequipped (2) }
    MAX-ACCESS  read-only
    STATUS      current
    DESCRIPTION
        "Describes if the VC4/STS3 contains payload.

        equipped - VC4/STS3 contains payload.

        unequipped - No payload in VC4/STS3.

"
    ::= { clientVc4Entry 14 }

clientVc4ConnectionStatus OBJECT-TYPE
    SYNTAX      DisplayString
    MAX-ACCESS  read-only
    STATUS      current
    DESCRIPTION
        "Shows the name of the client port and
        possible subchannel/vc4 that it is connected to
        or Unconnected if not connected.

"
    DEFVAL { "Not connected" }
    ::= { clientVc4Entry 15 }

-- ----------------------------------------------------
-- CLIENT Lanes objects
-- ----------------------------------------------------
clientLanesTable  OBJECT-TYPE
    SYNTAX      SEQUENCE OF ClientLanesEntry
    MAX-ACCESS  not-accessible
    STATUS      current
    DESCRIPTION
        "The interface list."
    ::= { clientLanesList 1 }

clientLanesEntry OBJECT-TYPE
    SYNTAX      ClientLanesEntry
    MAX-ACCESS  not-accessible
    STATUS      current
    DESCRIPTION
        "An entry in the interface list.

"
    INDEX { clientLanesIndex }
    ::= { clientLanesTable 1 }

ClientLanesEntry ::=
    SEQUENCE {
        clientLanesIndex                     Unsigned32,
        clientLanesName                      MgmtNameString,
        clientLanesSubrack                   SubrackNumber,
        clientLanesSlot                      SlotNumber,
        clientLanesTxPort                    PortNumber,
        clientLanesRxPort                    PortNumber,
        clientLanesLaneId                    Unsigned32,
        clientLanesRxPowerLevel              Integer32,
        clientLanesWaveLength                LaneFrequency,
        clientLanesBE                        Gauge32,
        clientLanesResetBE                   INTEGER,
        clientLanesLossOfSignal              FaultStatus,
        clientLanesObjectProperty            ObjectProperty,
        clientLanesLossOfSync                FaultStatus,
        clientLanesLocalLinkFault            FaultStatus,
        clientLanesRemoteLinkFault           FaultStatus,
        clientLanesHighBitErrorRate          FaultStatus,
        clientLanesReceiverSensitivity       Integer32,
        clientLanesReceivedPowerLow          FaultStatus,
        clientLanesIfNo                      PortNumber,
        clientLanesIdx                       Integer32,
        clientLanesClientIfIdx               Integer32,
        clientLanesAdminStatus               BoardOrInterfaceAdminStatus,
        clientLanesOperStatus                BoardOrInterfaceOperStatus,
        clientLanesUpPortId                  Integer32}

clientLanesIndex OBJECT-TYPE
    SYNTAX      Unsigned32 (1..2147483647)
    MAX-ACCESS  read-create
    STATUS      current
    DESCRIPTION
        "An arbitrary index assigned to each if entry.

"
    ::= { clientLanesEntry 1 }

clientLanesName OBJECT-TYPE
    SYNTAX      MgmtNameString
    MAX-ACCESS  read-create
    STATUS      current
    DESCRIPTION
        "The management name of the Lanes,
        e.g. Lane:1:2:1:4 where the first number
        indicates sub-rack, the second slot number and
        the third is the interface number. The last
        number is the lane id within the Client frame.

"
    ::= { clientLanesEntry 2 }

clientLanesSubrack OBJECT-TYPE
    SYNTAX      SubrackNumber
    MAX-ACCESS  read-create
    STATUS      current
    DESCRIPTION
        "The number of the subrack where the lane is
        located.

"
    ::= { clientLanesEntry 3 }

clientLanesSlot OBJECT-TYPE
    SYNTAX      SlotNumber
    MAX-ACCESS  read-create
    STATUS      current
    DESCRIPTION
        "The number of the slot where the lane is
        located.

"
    ::= { clientLanesEntry 4 }

clientLanesTxPort OBJECT-TYPE
    SYNTAX      PortNumber
    MAX-ACCESS  read-create
    STATUS      current
    DESCRIPTION
        "The number of the port where the TX-side of the
        lane is located.

"
    ::= { clientLanesEntry 5 }

clientLanesRxPort OBJECT-TYPE
    SYNTAX      PortNumber
    MAX-ACCESS  read-create
    STATUS      current
    DESCRIPTION
        "The number of the port where the RX-side of the
        lane is located.

"
    ::= { clientLanesEntry 6 }

clientLanesLaneId OBJECT-TYPE
    SYNTAX      Unsigned32 (1..16)
    MAX-ACCESS  read-create
    STATUS      current
    DESCRIPTION
        "The id of the lane within the Client frame.

"
    ::= { clientLanesEntry 7 }

clientLanesRxPowerLevel OBJECT-TYPE
    SYNTAX      Integer32
    MAX-ACCESS  read-only
    STATUS      current
    DESCRIPTION
        "The received power level in units of 0.1 dBm.

"
    ::= { clientLanesEntry 8 }

clientLanesWaveLength OBJECT-TYPE
    SYNTAX      LaneFrequency
    MAX-ACCESS  read-only
    STATUS      current
    DESCRIPTION
        "The wavelength/frequency associated with the lane.
         ch871 means the frequency  187.1 THz.
         w1310 means the  wavelength 1310 nm.

        undefined if no wavelength is applicable.

"
    ::= { clientLanesEntry 9 }

clientLanesBE OBJECT-TYPE
    SYNTAX      Gauge32
    MAX-ACCESS  read-only
    STATUS      current
    DESCRIPTION
        "The counter associated with the number of
        Bit Interleave Parity errors in a particular lane.

"
    ::= { clientLanesEntry 10 }

clientLanesResetBE OBJECT-TYPE
    SYNTAX  INTEGER {
         normal (1),
         reset (2)  }
    MAX-ACCESS  read-write
    STATUS      current
    DESCRIPTION
        "Command to reset the BIP-8 error counter value.

"
        DEFVAL { normal }
    ::= { clientLanesEntry 11 }

clientLanesLossOfSignal OBJECT-TYPE
    SYNTAX      FaultStatus
    MAX-ACCESS  read-only
    STATUS      current
    DESCRIPTION
        "Loss of signal.
         Applicable for all signal formats.

        A(ctivation): Active loss of signal HW
        indication.

        D(e-activation): Inactive loss of signal HW
        indication.
"
    ::= { clientLanesEntry 12 }

clientLanesObjectProperty OBJECT-TYPE
    SYNTAX      ObjectProperty
    MAX-ACCESS  read-only
    STATUS      current
    DESCRIPTION
        "Property mask.

"
    ::= { clientLanesEntry 13 }

clientLanesLossOfSync OBJECT-TYPE
    SYNTAX      FaultStatus
    MAX-ACCESS  read-only
    STATUS      current
    DESCRIPTION
        "Loss of sync.
         All forms of sync loss.

        A(ctivation): GbE 'frame' can not be located.

        D(e-activation): GbE 'frame' is located.

"
    ::= { clientLanesEntry 14 }

clientLanesLocalLinkFault OBJECT-TYPE
    SYNTAX      FaultStatus
    MAX-ACCESS  read-only
    STATUS      current
    DESCRIPTION
        "Local link fault. IEEE 802.3ah

        A(ctivation): Active local link fault indication.

        D(e-activation): Inactive local link fault indication.

"
    ::= { clientLanesEntry 15 }

clientLanesRemoteLinkFault OBJECT-TYPE
    SYNTAX      FaultStatus
    MAX-ACCESS  read-only
    STATUS      current
    DESCRIPTION
        "Remote link fault. IEEE 802.3ah

        A(ctivation): Active remote link fault indication.

        D(e-activation): Inactive remote link fault indication.

"
    ::= { clientLanesEntry 16 }

clientLanesHighBitErrorRate OBJECT-TYPE
    SYNTAX      FaultStatus
    MAX-ACCESS  read-only
    STATUS      current
    DESCRIPTION
        "High bit error rate (Hi-Ber). IEEE 802.3ah

        A(ctivation): Active high bit error rate.

        D(e-activation): Inactive high bit error rate.

"
    ::= { clientLanesEntry 17 }

clientLanesReceiverSensitivity OBJECT-TYPE
    SYNTAX      Integer32
    MAX-ACCESS  read-only
    STATUS      current
    DESCRIPTION
        "The lowest power that the receiver is guaranteed
        to handle, in units of 0.1 dBm.

"
    ::= { clientLanesEntry 18 }

clientLanesReceivedPowerLow OBJECT-TYPE
    SYNTAX      FaultStatus
    MAX-ACCESS  read-only
    STATUS      current
    DESCRIPTION
        "Received power level low threshold exceeded.
        Relative to the threshold in the port interface
        table.
        Applicable for all signal formats.

        alarm: The received power level is below the
        associated threshold.

        ok: The received power level is at least 0.5 dBm
        above the threshold.

"
    ::= { clientLanesEntry 19 }

clientLanesIfNo OBJECT-TYPE
    SYNTAX      PortNumber
    MAX-ACCESS  read-create
    STATUS      current
    DESCRIPTION
        "The physical interface number.

"
        DEFVAL { 0  }
    ::= { clientLanesEntry 20 }

clientLanesIdx OBJECT-TYPE
    SYNTAX      Integer32   (-1..2147483647)
    MAX-ACCESS  read-create
    STATUS      current
    DESCRIPTION
        "Internal object reference

"
    DEFVAL { -1  }
    ::= { clientLanesEntry 21  }

clientLanesClientIfIdx OBJECT-TYPE
    SYNTAX      Integer32   (-1..2147483647)
    MAX-ACCESS  read-create
    STATUS      current
    DESCRIPTION
        "Internal object reference of the clientIf

"
    DEFVAL { -1  }
    ::= { clientLanesEntry 22  }



clientLanesAdminStatus OBJECT-TYPE
    SYNTAX      BoardOrInterfaceAdminStatus
    MAX-ACCESS  read-write
    STATUS      current
    DESCRIPTION
        "The administrative state for the interface.

        down - The interface is de-activated.

        service - The interface is activated but alarms are
        suppressed. Intended for use during service or
        re-configuration. When service is concluded
        adminStatus should be set to 'up' again.

        up - The interface will be activated when
        available. Alarms are not suppressed.

        This attribute can be written via SNMP.
"
    DEFVAL { up }
    ::= { clientLanesEntry 23 }

clientLanesOperStatus OBJECT-TYPE
    SYNTAX      BoardOrInterfaceOperStatus
    MAX-ACCESS  read-only
    STATUS      current
    DESCRIPTION
        "The operational state for the interface.

        notPresent - The physical resources are not
        available.

        down - The interface is de-activated or there are
        faults preventing its transition to the 'up' state.

        up - The interface is operational.

"
    DEFVAL { notPresent }
    ::= { clientLanesEntry 24 }

clientLanesUpPortId OBJECT-TYPE
    SYNTAX      Integer32   (-1..2147483647)
    MAX-ACCESS  read-only
    STATUS      current
    DESCRIPTION
        "Internal port reference for traffic unit.
"
    DEFVAL { -1  }
    ::= { clientLanesEntry 25 }


-- ----------------------------------------------------
-- MPO Lanes objects
-- ----------------------------------------------------
clientMpoLanesTable  OBJECT-TYPE
    SYNTAX      SEQUENCE OF ClientMpoLanesEntry
    MAX-ACCESS  not-accessible
    STATUS      current
    DESCRIPTION
        "The interface list."
    ::= { clientMpoLanesList 1 }

clientMpoLanesEntry OBJECT-TYPE
    SYNTAX      ClientMpoLanesEntry
    MAX-ACCESS  not-accessible
    STATUS      current
    DESCRIPTION
        "An entry in the interface list.

"
    INDEX { clientMpoLanesIndex }
    ::= { clientMpoLanesTable 1 }

ClientMpoLanesEntry ::=
    SEQUENCE {
        clientMpoLanesIndex                     Unsigned32,
        clientMpoLanesName                      MgmtNameString,
        clientMpoLanesSubrack                   SubrackNumber,
        clientMpoLanesSlot                      SlotNumber,
        clientMpoLanesIfNo                      PortNumber,
        clientMpoLanesLaneId                    Unsigned32,
        clientMpoLanesAdminStatus               BoardOrInterfaceAdminStatus,
        clientMpoLanesOperStatus                BoardOrInterfaceOperStatus,
        clientMpoLanesLaserStatus               OnOff,
        clientMpoLanesRxSensitivity             Integer32,
        clientMpoLanesRxPowerLevel              Integer32,
        clientMpoLanesPowerLevelLowRelativeThreshold   Integer32,
        clientMpoLanesWaveLength                LaneFrequency,
        clientMpoLanesObjectProperty            ObjectProperty,
        clientMpoLanesForwardAls                EnableDisable,
        clientMpoLanesLossOfSignal              FaultStatus,
        clientMpoLanesRxPowerLow                FaultStatus}

clientMpoLanesIndex OBJECT-TYPE
    SYNTAX      Unsigned32 (1..2147483647)
    MAX-ACCESS  read-create
    STATUS      current
    DESCRIPTION
        "An arbitrary index assigned to each if entry.

"
    ::= { clientMpoLanesEntry 1 }

clientMpoLanesName OBJECT-TYPE
    SYNTAX      MgmtNameString
    MAX-ACCESS  read-create
    STATUS      current
    DESCRIPTION
        "The management name of the Lanes,
        e.g. Lane:1:2:1:4 where the first number
        indicates sub-rack, the second slot number and
        the third is the interface number. The last
        number is the lane id.

"
    ::= { clientMpoLanesEntry 2 }

clientMpoLanesSubrack OBJECT-TYPE
    SYNTAX      SubrackNumber
    MAX-ACCESS  read-create
    STATUS      current
    DESCRIPTION
        "The number of the subrack where the lane is
        located.

"
    ::= { clientMpoLanesEntry 3 }

clientMpoLanesSlot OBJECT-TYPE
    SYNTAX      SlotNumber
    MAX-ACCESS  read-create
    STATUS      current
    DESCRIPTION
        "The number of the slot where the lane is
        located.

"
    ::= { clientMpoLanesEntry 4 }

clientMpoLanesIfNo OBJECT-TYPE
    SYNTAX      PortNumber
    MAX-ACCESS  read-create
    STATUS      current
    DESCRIPTION
        "The physical interface number.

"
        DEFVAL { 0  }
    ::= { clientMpoLanesEntry 5 }

clientMpoLanesLaneId OBJECT-TYPE
    SYNTAX      Unsigned32 (1..16)
    MAX-ACCESS  read-create
    STATUS      current
    DESCRIPTION
        "The identity of the lane within the Client frame.

"
    ::= { clientMpoLanesEntry 6 }

clientMpoLanesAdminStatus OBJECT-TYPE
    SYNTAX      BoardOrInterfaceAdminStatus
    MAX-ACCESS  read-write
    STATUS      current
    DESCRIPTION
        "The administrative state for the interface.

        down - The interface is de-activated.

        service - The interface is activated but alarms are
        suppressed. Intended for use during service or
        re-configuration. When service is concluded
        adminStatus should be set to 'up' again.

        up - The interface will be activated when
        available. Alarms are not suppressed.

        This attribute can be written via SNMP.
"
    DEFVAL { up }
    ::= { clientMpoLanesEntry 7 }

clientMpoLanesOperStatus OBJECT-TYPE
    SYNTAX      BoardOrInterfaceOperStatus
    MAX-ACCESS  read-only
    STATUS      current
    DESCRIPTION
        "The operational state for the interface.

        notPresent - The physical resources are not
        available.

        down - The interface is de-activated or there are
        faults preventing its transition to the 'up' state.

        up - The interface is operational.

"
    DEFVAL { notPresent }
    ::= { clientMpoLanesEntry 8 }

clientMpoLanesLaserStatus OBJECT-TYPE
    SYNTAX      OnOff
    MAX-ACCESS  read-only
    STATUS      current
    DESCRIPTION
        "The operational state of the laser.

        off - The laser is turned off.

        on - The laser is turned on.

"
    DEFVAL { off }
    ::= { clientMpoLanesEntry 9 }

clientMpoLanesRxSensitivity OBJECT-TYPE
    SYNTAX      Integer32
    MAX-ACCESS  read-only
    STATUS      current
    DESCRIPTION
        "The lowest power that the receiver is guaranteed
        to handle, in units of 0.1 dBm.

"
    ::= { clientMpoLanesEntry 10 }

clientMpoLanesRxPowerLevel OBJECT-TYPE
    SYNTAX      Integer32
    MAX-ACCESS  read-only
    STATUS      current
    DESCRIPTION
        "The received power level in units of 0.1 dBm.

"
    ::= { clientMpoLanesEntry 11 }

clientMpoLanesPowerLevelLowRelativeThreshold OBJECT-TYPE
    SYNTAX      Integer32 (-50..100)
    MAX-ACCESS  read-write
    STATUS      current
    DESCRIPTION
        "The lower threshold for received power level in
        units of 0.1 dB, relative to the receiver
        sensitivity.

"
    DEFVAL { 30 }
    ::= { clientMpoLanesEntry 12 }

clientMpoLanesWaveLength OBJECT-TYPE
    SYNTAX      LaneFrequency
    MAX-ACCESS  read-only
    STATUS      current
    DESCRIPTION
        "The wavelength/frequency associated with the lane.
         ch871 means the frequency  187.1 THz.
         w1310 means the  wavelength 1310 nm.

        undefined if no wavelength is applicable.

"
    ::= { clientMpoLanesEntry 13 }

clientMpoLanesObjectProperty OBJECT-TYPE
    SYNTAX      ObjectProperty
    MAX-ACCESS  read-only
    STATUS      current
    DESCRIPTION
        "Property mask.

"
    ::= { clientMpoLanesEntry 14 }

clientMpoLanesForwardAls OBJECT-TYPE
    SYNTAX      EnableDisable
    MAX-ACCESS  read-write
    STATUS      current
    DESCRIPTION
        "Forward Automatic Laser Shut-down. Decides if
        laser shutdown of the client should occur when
        a defect on the line or remote client is detected.

        disabled - The laser is NOT turned off at defect
        detection.

        enabled - The laser is turned off at defect
        detection.

"
    DEFVAL { disabled }
    ::= { clientMpoLanesEntry 15 }

clientMpoLanesLossOfSignal OBJECT-TYPE
    SYNTAX      FaultStatus
    MAX-ACCESS  read-only
    STATUS      current
    DESCRIPTION
        "Loss of signal.
         Applicable for all signal formats.

        A(ctivation): Active loss of signal HW
        indication.

        D(e-activation): Inactive loss of signal HW
        indication.
"
    ::= { clientMpoLanesEntry 16 }

clientMpoLanesRxPowerLow OBJECT-TYPE
    SYNTAX      FaultStatus
    MAX-ACCESS  read-only
    STATUS      current
    DESCRIPTION
        "Received power level low threshold exceeded.
        Relative to the threshold in the port interface
        table.
        Applicable for all signal formats.

        alarm: The received power level is below the
        associated threshold.

        ok: The received power level is at least 0.5 dBm
        above the threshold.

"
    ::= { clientMpoLanesEntry 17 }

-- ----------------------------------------------------
-- Notifications
-- ----------------------------------------------------

clientNotifyPrefix OBJECT IDENTIFIER ::= { lumentisClientNotifications 0 }

clientIfTxSignalStatusDown NOTIFICATION-TYPE
    OBJECTS {
        clientIfIndex,
        clientIfName,
        clientIfSubrack,
        clientIfSlot,
        clientIfTxPort,
        clientIfRxPort,
        clientIfEntityId,
        clientIfTxSignalStatus }
    STATUS      current
    DESCRIPTION
        "Sent when the signal status attribute of an
        interface changes.

"
    ::= { clientNotifyPrefix 1 }

clientIfTxSignalStatusUp NOTIFICATION-TYPE
    OBJECTS {
        clientIfIndex,
        clientIfName,
        clientIfSubrack,
        clientIfSlot,
        clientIfTxPort,
        clientIfRxPort,
        clientIfEntityId,
        clientIfTxSignalStatus }
    STATUS      current
    DESCRIPTION
        "Sent when the signal status attribute of an
        interface changes.

"
    ::= { clientNotifyPrefix 2 }

clientIfTxSignalStatusDegraded NOTIFICATION-TYPE
    OBJECTS {
        clientIfIndex,
        clientIfName,
        clientIfSubrack,
        clientIfSlot,
        clientIfTxPort,
        clientIfRxPort,
        clientIfEntityId,
        clientIfTxSignalStatus }

    STATUS      current
    DESCRIPTION
        "Sent when the signal status attribute of an
        interface changes.

"
    ::= { clientNotifyPrefix 3 }


-- ----------------------------------------------------
-- Object and event groups
-- ----------------------------------------------------


clientGeneralGroupV1 OBJECT-GROUP
    OBJECTS {
        clientGeneralLastChangeTime,
        clientGeneralStateLastChangeTime }
    STATUS      deprecated
    DESCRIPTION
        "The generic client interface MIB general objects v1."
    ::= { lumClientGroups 1 }

clientNotificationGroupV1 NOTIFICATION-GROUP
    NOTIFICATIONS {
        clientIfTxSignalStatusDown,
        clientIfTxSignalStatusUp,
        clientIfTxSignalStatusDegraded }
    STATUS      current
    DESCRIPTION
        "The generic client interface notifications."
    ::= { lumClientGroups 2 }

clientIfGroupV1 OBJECT-GROUP
    OBJECTS {
        clientIfIndex,
        clientIfName,
        clientIfSubrack,
        clientIfSlot,
        clientIfTxPort,
        clientIfRxPort,
        clientIfEntityId,
        clientIfAdminStatus,
        clientIfOperStatus,
        clientIfLaserStatus,
        clientIfTxSignalStatus,
        clientIfForwardAls,
        clientIfSuppressRemoteAlarms,
        clientIfFarEndLoopback,

        clientIfFormat,

        clientIfAutoNegotiationMode,
        clientIfAutoNegotiationStatus,
        clientIfDuplexCapability,
        clientIfFlowControlMode,
        clientIfInterPacketGap,
        clientIfFrameSize,
        clientIfGfpMode,
        clientIfBandWidth,
        clientIfRateLimit,

        clientIfTrxClass,

        clientIfLaserBias,
        clientIfPowerLevel,
        clientIfReceiverSensitivity,
        clientIfPowerLevelLowRelativeThreshold,

        clientIfLossOfSignal,
        clientIfLossOfFrame,
        clientIfBitrateMismatch,
        clientIfAuAlarmIndicationSignalW2C,
        clientIfTransmitterFailed,

        clientIfTrxCodeMismatch,
        clientIfTrxBitrateUnavailable,
        clientIfTrxMissing,
        clientIfTrxFailed,

        clientIfReceivedPowerHigh,
        clientIfReceivedPowerLow,
        clientIfLinkDown,
        clientIfConfigurationCommand,
        clientIfGbeUtilization }

    STATUS      deprecated
    DESCRIPTION
        "The interface objects V1 (3.0)."
    ::= { lumClientGroups 3 }

clientIfGroupV2 OBJECT-GROUP
    OBJECTS {
        clientIfIndex,
        clientIfName,
        clientIfSubrack,
        clientIfSlot,
        clientIfTxPort,
        clientIfRxPort,
        clientIfEntityId,
        clientIfAdminStatus,
        clientIfOperStatus,
        clientIfLaserStatus,
        clientIfTxSignalStatus,
        clientIfForwardAls,
        clientIfSuppressRemoteAlarms,
        clientIfFarEndLoopback,

        clientIfFormat,

        clientIfAutoNegotiationMode,
        clientIfAutoNegotiationStatus,
        clientIfDuplexCapability,
        clientIfFlowControlMode,
        clientIfInterPacketGap,
        clientIfFrameSize,
        clientIfGfpMode,
        clientIfBandWidth,
        clientIfRateLimit,

        clientIfTrxClass,

        clientIfLaserBias,
        clientIfPowerLevel,
        clientIfReceiverSensitivity,
        clientIfPowerLevelLowRelativeThreshold,

        clientIfLossOfSignal,
        clientIfLossOfFrame,
        clientIfBitrateMismatch,
        clientIfAuAlarmIndicationSignalW2C,
        clientIfTransmitterFailed,

        clientIfTrxCodeMismatch,
        clientIfTrxBitrateUnavailable,
        clientIfTrxMissing,

        clientIfReceivedPowerHigh,
        clientIfReceivedPowerLow,
        clientIfLinkDown,
        clientIfConfigurationCommand,
        clientIfGbeUtilization,
        clientIfLossOfSync,

        clientIfConfigureTrxModeCommand,
        clientIfTrxMode,
        clientIfExpectedTxFrequency,
        clientIfTxFrequency,
        clientIfUnexpectedTxFrequency,
        clientIfIllegalFrequency,
        clientIfLaserForcedOn,
        clientIfRxSignalStatus }

    STATUS      deprecated
    DESCRIPTION
        "The interface objects V2 (3.1)."
    ::= { lumClientGroups 4 }

clientGeneralGroupV2 OBJECT-GROUP
    OBJECTS {
        clientGeneralLastChangeTime,
        clientGeneralStateLastChangeTime,
        clientGeneralClientIfTableSize }
    STATUS      current
    DESCRIPTION
        "The generic client interface MIB general objects V2 (3.1)."
    ::= { lumClientGroups 5 }

clientIfGroupV3 OBJECT-GROUP
    OBJECTS {
        clientIfIndex,
        clientIfName,
        clientIfSubrack,
        clientIfSlot,
        clientIfTxPort,
        clientIfRxPort,
        clientIfEntityId,
        clientIfAdminStatus,
        clientIfOperStatus,
        clientIfLaserStatus,
        clientIfTxSignalStatus,
        clientIfForwardAls,
        clientIfSuppressRemoteAlarms,
        clientIfFarEndLoopback,

        clientIfFormat,

        clientIfAutoNegotiationMode,
        clientIfAutoNegotiationStatus,
        clientIfDuplexCapability,
        clientIfFlowControlMode,
        clientIfInterPacketGap,
        clientIfFrameSize,
        clientIfGfpMode,
        clientIfBandWidth,
        clientIfRateLimit,

        clientIfTrxClass,

        clientIfLaserBias,
        clientIfPowerLevel,
        clientIfReceiverSensitivity,
        clientIfPowerLevelLowRelativeThreshold,

        clientIfLossOfSignal,
        clientIfLossOfFrame,
        clientIfBitrateMismatch,
        clientIfAuAlarmIndicationSignalW2C,
        clientIfTransmitterFailed,

        clientIfTrxCodeMismatch,
        clientIfTrxBitrateUnavailable,
        clientIfTrxMissing,

        clientIfReceivedPowerHigh,
        clientIfReceivedPowerLow,
        clientIfLinkDown,
        clientIfConfigurationCommand,
        clientIfGbeUtilization,
        clientIfLossOfSync,

        clientIfConfigureTrxModeCommand,
        clientIfTrxMode,
        clientIfExpectedTxFrequency,
        clientIfTxFrequency,
        clientIfUnexpectedTxFrequency,
        clientIfIllegalFrequency,
        clientIfLaserForcedOn,
        clientIfTrxMedia,
        clientIfTrxMediaMismatch,
        clientIfTruncAutoNegotiationMode }

    STATUS      deprecated
    DESCRIPTION
        "The interface objects V3 (3.2)."
    ::= { lumClientGroups 6 }

clientIfGroupV4 OBJECT-GROUP
    OBJECTS {
        clientIfIndex,
        clientIfName,
        clientIfSubrack,
        clientIfSlot,
        clientIfTxPort,
        clientIfRxPort,
        clientIfEntityId,
        clientIfAdminStatus,
        clientIfOperStatus,
        clientIfLaserStatus,
        clientIfTxSignalStatus,
        clientIfForwardAls,
        clientIfSuppressRemoteAlarms,
        clientIfFarEndLoopback,

        clientIfFormat,

        clientIfAutoNegotiationMode,
        clientIfAutoNegotiationStatus,
        clientIfDuplexCapability,
        clientIfFlowControlMode,
        clientIfInterPacketGap,
        clientIfFrameSize,
        clientIfGfpMode,
        clientIfBandWidth,
        clientIfRateLimit,

        clientIfTrxClass,

        clientIfLaserBias,
        clientIfPowerLevel,
        clientIfReceiverSensitivity,
        clientIfPowerLevelLowRelativeThreshold,

        clientIfLossOfSignal,
        clientIfLossOfFrame,
        clientIfBitrateMismatch,
        clientIfAuAlarmIndicationSignalW2C,
        clientIfTransmitterFailed,

        clientIfTrxCodeMismatch,
        clientIfTrxBitrateUnavailable,
        clientIfTrxMissing,

        clientIfReceivedPowerHigh,
        clientIfReceivedPowerLow,
        clientIfLinkDown,
        clientIfConfigurationCommand,
        clientIfGbeUtilization,
        clientIfLossOfSync,

        clientIfConfigureTrxModeCommand,
        clientIfTrxMode,
        clientIfExpectedTxFrequency,
        clientIfTxFrequency,
        clientIfUnexpectedTxFrequency,
        clientIfIllegalFrequency,
        clientIfLaserForcedOn,
        clientIfTrxMedia,
        clientIfTrxMediaMismatch,

        clientIfTruncAutoNegotiationMode,
        clientIfObjectProperty,
        clientIfTxPowerLevel,
        clientIfLaserTempActual,

        clientIfTraceIntrusionMode,
        clientIfTraceTransmitted,
        clientIfTraceReceived,
        clientIfTraceExpected,
        clientIfTraceAlarmMode,
        clientIfTraceMismatch,
        clientIfNearEndLoopback
         }

    STATUS      deprecated
    DESCRIPTION
        "The interface objects V4 (4.0)."
    ::= { lumClientGroups 7 }

clientIfGroupV5 OBJECT-GROUP
    OBJECTS {
        clientIfIndex,
        clientIfName,
        clientIfSubrack,
        clientIfSlot,
        clientIfTxPort,
        clientIfRxPort,
        clientIfEntityId,
        clientIfAdminStatus,
        clientIfOperStatus,
        clientIfLaserStatus,
        clientIfTxSignalStatus,
        clientIfForwardAls,
        clientIfSuppressRemoteAlarms,
        clientIfFarEndLoopback,

        clientIfFormat,

        clientIfAutoNegotiationMode,
        clientIfAutoNegotiationStatus,
        clientIfDuplexCapability,
        clientIfFlowControlMode,
        clientIfInterPacketGap,
        clientIfFrameSize,
        clientIfGfpMode,
        clientIfBandWidth,
        clientIfRateLimit,

        clientIfTrxClass,

        clientIfLaserBias,
        clientIfPowerLevel,
        clientIfReceiverSensitivity,
        clientIfPowerLevelLowRelativeThreshold,

        clientIfLossOfSignal,
        clientIfLossOfFrame,
        clientIfBitrateMismatch,
        clientIfAuAlarmIndicationSignalW2C,
        clientIfTransmitterFailed,

        clientIfTrxCodeMismatch,
        clientIfTrxBitrateUnavailable,
        clientIfTrxMissing,

        clientIfReceivedPowerHigh,
        clientIfReceivedPowerLow,
        clientIfLinkDown,
        clientIfConfigurationCommand,
        clientIfGbeUtilization,
        clientIfLossOfSync,

        clientIfConfigureTrxModeCommand,
        clientIfTrxMode,
        clientIfExpectedTxFrequency,
        clientIfTxFrequency,
        clientIfUnexpectedTxFrequency,
        clientIfIllegalFrequency,
        clientIfLaserForcedOn,
        clientIfTrxMedia,
        clientIfTrxMediaMismatch,

        clientIfTruncAutoNegotiationMode,
        clientIfObjectProperty,
        clientIfTxPowerLevel,
        clientIfLaserTempActual,

        clientIfTraceIntrusionMode,
        clientIfTraceTransmitted,
        clientIfTraceReceived,
        clientIfTraceExpected,
        clientIfTraceAlarmMode,
        clientIfTraceMismatch,
        clientIfNearEndLoopback,
        clientIfMsAlarmIndicationSignalC2W,
        clientIfMsAlarmIndicationSignalW2C,
        clientIfRemoteDefectIndication
         }

    STATUS      deprecated
    DESCRIPTION
        "The interface objects V5 (4.1)."
    ::= { lumClientGroups 8 }

clientIfGroupV6 OBJECT-GROUP
    OBJECTS {
        clientIfIndex,
        clientIfName,
        clientIfSubrack,
        clientIfSlot,
        clientIfTxPort,
        clientIfRxPort,
        clientIfEntityId,
        clientIfAdminStatus,
        clientIfOperStatus,
        clientIfLaserStatus,
        clientIfTxSignalStatus,
        clientIfForwardAls,
        clientIfSuppressRemoteAlarms,
        clientIfFarEndLoopback,

        clientIfFormat,

        clientIfAutoNegotiationMode,
        clientIfAutoNegotiationStatus,
        clientIfDuplexCapability,
        clientIfFlowControlMode,
        clientIfInterPacketGap,
        clientIfFrameSize,
        clientIfGfpMode,
        clientIfBandWidth,
        clientIfRateLimit,

        clientIfTrxClass,

        clientIfLaserBias,
        clientIfPowerLevel,
        clientIfReceiverSensitivity,
        clientIfPowerLevelLowRelativeThreshold,

        clientIfLossOfSignal,
        clientIfLossOfFrame,
        clientIfBitrateMismatch,
        clientIfAuAlarmIndicationSignalW2C,
        clientIfTransmitterFailed,

        clientIfTrxCodeMismatch,
        clientIfTrxBitrateUnavailable,
        clientIfTrxMissing,

        clientIfReceivedPowerHigh,
        clientIfReceivedPowerLow,
        clientIfLinkDown,
        clientIfConfigurationCommand,
        clientIfGbeUtilization,
        clientIfLossOfSync,

        clientIfConfigureTrxModeCommand,
        clientIfTrxMode,
        clientIfExpectedTxFrequency,
        clientIfTxFrequency,
        clientIfUnexpectedTxFrequency,
        clientIfIllegalFrequency,
        clientIfLaserForcedOn,
        clientIfTrxMedia,
        clientIfTrxMediaMismatch,

        clientIfTruncAutoNegotiationMode,
        clientIfObjectProperty,
        clientIfTxPowerLevel,
        clientIfLaserTempActual,

        clientIfTraceIntrusionMode,
        clientIfTraceTransmitted,
        clientIfTraceReceived,
        clientIfTraceExpected,
        clientIfTraceAlarmMode,
        clientIfTraceMismatch,
        clientIfNearEndLoopback,
        clientIfMsAlarmIndicationSignalC2W,
        clientIfMsAlarmIndicationSignalW2C,
        clientIfRemoteDefectIndication,
        clientIfJ1TxTrailTrace,
        clientIfJ1TxTrailTraceInsertionMode,
        clientIfVcGroupFailedW2C,
        clientIfReadJ1
         }

    STATUS      deprecated
    DESCRIPTION
        "The interface objects V6 (5.0)."
    ::= { lumClientGroups 9 }

clientIfGroupV7 OBJECT-GROUP
    OBJECTS {
        clientIfIndex,
        clientIfName,
        clientIfSubrack,
        clientIfSlot,
        clientIfTxPort,
        clientIfRxPort,
        clientIfEntityId,
        clientIfAdminStatus,
        clientIfOperStatus,
        clientIfLaserStatus,
        clientIfTxSignalStatus,
        clientIfForwardAls,
        clientIfSuppressRemoteAlarms,
        clientIfFarEndLoopback,

        clientIfFormat,

        clientIfAutoNegotiationMode,
        clientIfAutoNegotiationStatus,
        clientIfDuplexCapability,
        clientIfFlowControlMode,
        clientIfInterPacketGap,
        clientIfFrameSize,
        clientIfGfpMode,
        clientIfBandWidth,
        clientIfRateLimit,

        clientIfTrxClass,

        clientIfLaserBias,
        clientIfPowerLevel,
        clientIfReceiverSensitivity,
        clientIfPowerLevelLowRelativeThreshold,

        clientIfLossOfSignal,
        clientIfLossOfFrame,
        clientIfBitrateMismatch,
        clientIfAuAlarmIndicationSignalW2C,
        clientIfTransmitterFailed,

        clientIfTrxCodeMismatch,
        clientIfTrxBitrateUnavailable,
        clientIfTrxMissing,

        clientIfReceivedPowerHigh,
        clientIfReceivedPowerLow,
        clientIfLinkDown,
        clientIfConfigurationCommand,
        clientIfGbeUtilization,
        clientIfLossOfSync,

        clientIfConfigureTrxModeCommand,
        clientIfTrxMode,
        clientIfExpectedTxFrequency,
        clientIfTxFrequency,
        clientIfUnexpectedTxFrequency,
        clientIfIllegalFrequency,
        clientIfLaserForcedOn,
        clientIfTrxMedia,
        clientIfTrxMediaMismatch,

        clientIfTruncAutoNegotiationMode,
        clientIfObjectProperty,
        clientIfTxPowerLevel,
        clientIfLaserTempActual,

        clientIfTraceIntrusionMode,
        clientIfTraceTransmitted,
        clientIfTraceReceived,
        clientIfTraceExpected,
        clientIfTraceAlarmMode,
        clientIfTraceMismatch,
        clientIfNearEndLoopback,
        clientIfMsAlarmIndicationSignalC2W,
        clientIfMsAlarmIndicationSignalW2C,
        clientIfRemoteDefectIndication,
        clientIfJ1TxTrailTrace,
        clientIfJ1TxTrailTraceInsertionMode,
        clientIfVcGroupFailedW2C,
        clientIfReadJ1,
        clientIfHighSpeed,
        clientIfActualFormat
         }

    STATUS      deprecated
    DESCRIPTION
        "The interface objects V7 (7.0)."
    ::= { lumClientGroups 10 }

clientIfGroupV8 OBJECT-GROUP
    OBJECTS {
        clientIfIndex,
        clientIfName,
        clientIfSubrack,
        clientIfSlot,
        clientIfTxPort,
        clientIfRxPort,
        clientIfEntityId,
        clientIfAdminStatus,
        clientIfOperStatus,
        clientIfLaserStatus,
        clientIfTxSignalStatus,
        clientIfForwardAls,
        clientIfSuppressRemoteAlarms,
        clientIfFarEndLoopback,

        clientIfFormat,

        clientIfAutoNegotiationMode,
        clientIfAutoNegotiationStatus,
        clientIfDuplexCapability,
        clientIfFlowControlMode,
        clientIfInterPacketGap,
        clientIfFrameSize,
        clientIfGfpMode,
        clientIfBandWidth,
        clientIfRateLimit,

        clientIfTrxClass,

        clientIfLaserBias,
        clientIfPowerLevel,
        clientIfReceiverSensitivity,
        clientIfPowerLevelLowRelativeThreshold,

        clientIfLossOfSignal,
        clientIfLossOfFrame,
        clientIfBitrateMismatch,
        clientIfAuAlarmIndicationSignalW2C,
        clientIfTransmitterFailed,

        clientIfTrxCodeMismatch,
        clientIfTrxBitrateUnavailable,
        clientIfTrxMissing,

        clientIfReceivedPowerHigh,
        clientIfReceivedPowerLow,
        clientIfLinkDown,
        clientIfConfigurationCommand,
        clientIfGbeUtilization,
        clientIfLossOfSync,

        clientIfConfigureTrxModeCommand,
        clientIfTrxMode,
        clientIfExpectedTxFrequency,
        clientIfTxFrequency,
        clientIfUnexpectedTxFrequency,
        clientIfIllegalFrequency,
        clientIfLaserForcedOn,
        clientIfTrxMedia,
        clientIfTrxMediaMismatch,

        clientIfTruncAutoNegotiationMode,
        clientIfObjectProperty,
        clientIfTxPowerLevel,
        clientIfLaserTempActual,

        clientIfTraceIntrusionMode,
        clientIfTraceTransmitted,
        clientIfTraceReceived,
        clientIfTraceExpected,
        clientIfTraceAlarmMode,
        clientIfTraceMismatch,
        clientIfNearEndLoopback,
        clientIfMsAlarmIndicationSignalC2W,
        clientIfMsAlarmIndicationSignalW2C,
        clientIfRemoteDefectIndication,
        clientIfJ1TxTrailTrace,
        clientIfJ1TxTrailTraceInsertionMode,
        clientIfVcGroupFailedW2C,
        clientIfReadJ1,
        clientIfHighSpeed,
        clientIfActualFormat,
        clientIfRdiIntrusionMode }

    STATUS      deprecated
    DESCRIPTION
        "The interface objects V8 (8.0)."
    ::= { lumClientGroups 11 }

clientVc4Group OBJECT-GROUP
    OBJECTS {
        clientVc4Index,
        clientVc4Name,
        clientVc4Descr,
        clientVc4Subrack,
        clientVc4Slot,
        clientVc4TxPort,
        clientVc4RxPort,
        clientVc4Vc4,
        clientVc4ObjectProperty,
        clientVc4AuAlarmIndicationSignal,
        clientVc4AuLossOfPointer,
        clientVc4RxSignalStatus,
        clientVc4ConcatenationStatus,
        clientVc4PayloadStatus }
    STATUS    deprecated
    DESCRIPTION
        "The vc4 objects (10.0)."
    ::= { lumClientGroups 12 }

clientGeneralGroupV3 OBJECT-GROUP
    OBJECTS {
        clientGeneralLastChangeTime,
        clientGeneralStateLastChangeTime,
        clientGeneralClientIfTableSize,
        clientGeneralVc4TableSize }
    STATUS      current
    DESCRIPTION
        "The generic client interface MIB general objects V2 (10.0)."
    ::= { lumClientGroups 13 }

clientIfGroupV9 OBJECT-GROUP
    OBJECTS {
        clientIfIndex,
        clientIfName,
        clientIfSubrack,
        clientIfSlot,
        clientIfTxPort,
        clientIfRxPort,
        clientIfEntityId,
        clientIfAdminStatus,
        clientIfOperStatus,
        clientIfLaserStatus,
        clientIfTxSignalStatus,
        clientIfForwardAls,
        clientIfSuppressRemoteAlarms,
        clientIfFarEndLoopback,

        clientIfFormat,

        clientIfAutoNegotiationMode,
        clientIfAutoNegotiationStatus,
        clientIfDuplexCapability,
        clientIfFlowControlMode,
        clientIfInterPacketGap,
        clientIfFrameSize,
        clientIfGfpMode,
        clientIfBandWidth,
        clientIfRateLimit,

        clientIfTrxClass,

        clientIfLaserBias,
        clientIfPowerLevel,
        clientIfReceiverSensitivity,
        clientIfPowerLevelLowRelativeThreshold,

        clientIfLossOfSignal,
        clientIfLossOfFrame,
        clientIfBitrateMismatch,
        clientIfAuAlarmIndicationSignalW2C,
        clientIfTransmitterFailed,

        clientIfTrxCodeMismatch,
        clientIfTrxBitrateUnavailable,
        clientIfTrxMissing,

        clientIfReceivedPowerHigh,
        clientIfReceivedPowerLow,
        clientIfLinkDown,
        clientIfConfigurationCommand,
        clientIfGbeUtilization,
        clientIfLossOfSync,

        clientIfConfigureTrxModeCommand,
        clientIfTrxMode,
        clientIfExpectedTxFrequency,
        clientIfTxFrequency,
        clientIfUnexpectedTxFrequency,
        clientIfIllegalFrequency,
        clientIfLaserForcedOn,
        clientIfTrxMedia,
        clientIfTrxMediaMismatch,

        clientIfTruncAutoNegotiationMode,
        clientIfObjectProperty,
        clientIfTxPowerLevel,
        clientIfLaserTempActual,

        clientIfTraceIntrusionMode,
        clientIfTraceTransmitted,
        clientIfTraceReceived,
        clientIfTraceExpected,
        clientIfTraceAlarmMode,
        clientIfTraceMismatch,
        clientIfNearEndLoopback,
        clientIfMsAlarmIndicationSignalC2W,
        clientIfMsAlarmIndicationSignalW2C,
        clientIfRemoteDefectIndication,
        clientIfJ1TxTrailTrace,
        clientIfJ1TxTrailTraceInsertionMode,
        clientIfVcGroupFailedW2C,
        clientIfReadJ1,
        clientIfHighSpeed,
        clientIfActualFormat,
        clientIfRdiIntrusionMode,
        clientIfMuxQuadVc4,
        clientIfDemuxQuadVc4,
        clientIfCcConnectionMode,
        clientIfCcConfigurationCommand }

    STATUS      deprecated
    DESCRIPTION
        "The interface objects V9 (11.0)."
    ::= { lumClientGroups 14 }

clientIfGroupV10 OBJECT-GROUP
    OBJECTS {
        clientIfIndex,
        clientIfName,
        clientIfSubrack,
        clientIfSlot,
        clientIfTxPort,
        clientIfRxPort,
        clientIfEntityId,
        clientIfAdminStatus,
        clientIfOperStatus,
        clientIfLaserStatus,
        clientIfTxSignalStatus,
        clientIfForwardAls,
        clientIfSuppressRemoteAlarms,
        clientIfFarEndLoopback,

        clientIfFormat,

        clientIfAutoNegotiationMode,
        clientIfAutoNegotiationStatus,
        clientIfDuplexCapability,
        clientIfFlowControlMode,
        clientIfInterPacketGap,
        clientIfFrameSize,
        clientIfGfpMode,
        clientIfBandWidth,
        clientIfRateLimit,

        clientIfTrxClass,

        clientIfLaserBias,
        clientIfPowerLevel,
        clientIfReceiverSensitivity,
        clientIfPowerLevelLowRelativeThreshold,

        clientIfLossOfSignal,
        clientIfLossOfFrame,
        clientIfBitrateMismatch,
        clientIfAuAlarmIndicationSignalW2C,
        clientIfTransmitterFailed,

        clientIfTrxCodeMismatch,
        clientIfTrxBitrateUnavailable,
        clientIfTrxMissing,

        clientIfReceivedPowerHigh,
        clientIfReceivedPowerLow,
        clientIfLinkDown,
        clientIfConfigurationCommand,
        clientIfGbeUtilization,
        clientIfLossOfSync,

        clientIfConfigureTrxModeCommand,
        clientIfTrxMode,
        clientIfExpectedTxFrequency,
        clientIfTxFrequency,
        clientIfUnexpectedTxFrequency,
        clientIfIllegalFrequency,
        clientIfLaserForcedOn,
        clientIfTrxMedia,
        clientIfTrxMediaMismatch,

        clientIfTruncAutoNegotiationMode,
        clientIfObjectProperty,
        clientIfTxPowerLevel,
        clientIfLaserTempActual,

        clientIfTraceIntrusionMode,
        clientIfTraceTransmitted,
        clientIfTraceReceived,
        clientIfTraceExpected,
        clientIfTraceAlarmMode,
        clientIfTraceMismatch,
        clientIfNearEndLoopback,
        clientIfMsAlarmIndicationSignalC2W,
        clientIfMsAlarmIndicationSignalW2C,
        clientIfRemoteDefectIndication,
        clientIfJ1TxTrailTrace,
        clientIfJ1TxTrailTraceInsertionMode,
        clientIfVcGroupFailedW2C,
        clientIfReadJ1,
        clientIfHighSpeed,
        clientIfActualFormat,
        clientIfRdiIntrusionMode,
        clientIfMuxQuadVc4,
        clientIfDemuxQuadVc4,
        clientIfCcConnectionMode,
        clientIfCcConfigurationCommand,
        clientIfIllegalSignalFormat,
        clientIfSynchProtPortId,
        clientIfSynchProtGroupMemberPort,
        clientIfSynchProtGroupStatus,
        clientIfSynchProtActivePort,
        clientIfSynchProtPortStatus,
        clientIfSynchProtToggleActivePort,
        clientIfNearEndLoopbackTimeout,
        clientIfNearEndLoopbackEnabled,
        clientIfChangeNearEndLoopbackCommand,
        clientIfFarEndLoopbackEnabled }

    STATUS      deprecated
    DESCRIPTION
        "The interface objects V10 (12.0)."
    ::= { lumClientGroups 15 }

clientIfGroupV11 OBJECT-GROUP
    OBJECTS {
        clientIfIndex,
        clientIfName,
        clientIfSubrack,
        clientIfSlot,
        clientIfTxPort,
        clientIfRxPort,
        clientIfEntityId,
        clientIfAdminStatus,
        clientIfOperStatus,
        clientIfLaserStatus,
        clientIfTxSignalStatus,
        clientIfForwardAls,
        clientIfSuppressRemoteAlarms,
        clientIfFarEndLoopback,

        clientIfFormat,

        clientIfAutoNegotiationMode,
        clientIfAutoNegotiationStatus,
        clientIfDuplexCapability,
        clientIfFlowControlMode,
        clientIfInterPacketGap,
        clientIfFrameSize,
        clientIfGfpMode,
        clientIfBandWidth,
        clientIfRateLimit,

        clientIfTrxClass,

        clientIfLaserBias,
        clientIfPowerLevel,
        clientIfReceiverSensitivity,
        clientIfPowerLevelLowRelativeThreshold,

        clientIfLossOfSignal,
        clientIfLossOfFrame,
        clientIfBitrateMismatch,
        clientIfAuAlarmIndicationSignalW2C,
        clientIfTransmitterFailed,

        clientIfTrxCodeMismatch,
        clientIfTrxBitrateUnavailable,
        clientIfTrxMissing,

        clientIfReceivedPowerHigh,
        clientIfReceivedPowerLow,
        clientIfLinkDown,
        clientIfConfigurationCommand,
        clientIfGbeUtilization,
        clientIfLossOfSync,

        clientIfConfigureTrxModeCommand,
        clientIfTrxMode,
        clientIfExpectedTxFrequency,
        clientIfTxFrequency,
        clientIfUnexpectedTxFrequency,
        clientIfIllegalFrequency,
        clientIfLaserForcedOn,
        clientIfTrxMedia,
        clientIfTrxMediaMismatch,

        clientIfTruncAutoNegotiationMode,
        clientIfObjectProperty,
        clientIfTxPowerLevel,
        clientIfLaserTempActual,

        clientIfTraceIntrusionMode,
        clientIfTraceTransmitted,
        clientIfTraceReceived,
        clientIfTraceExpected,
        clientIfTraceAlarmMode,
        clientIfTraceMismatch,
        clientIfNearEndLoopback,
        clientIfMsAlarmIndicationSignalC2W,
        clientIfMsAlarmIndicationSignalW2C,
        clientIfRemoteDefectIndication,
        clientIfJ1TxTrailTrace,
        clientIfJ1TxTrailTraceInsertionMode,
        clientIfVcGroupFailedW2C,
        clientIfReadJ1,
        clientIfHighSpeed,
        clientIfActualFormat,
        clientIfRdiIntrusionMode,
        clientIfMuxQuadVc4,
        clientIfDemuxQuadVc4,
        clientIfCcConnectionMode,
        clientIfCcConfigurationCommand,
        clientIfIllegalSignalFormat,
        clientIfSynchProtPortId,
        clientIfSynchProtGroupMemberPort,
        clientIfSynchProtGroupStatus,
        clientIfSynchProtActivePort,
        clientIfSynchProtPortStatus,
        clientIfSynchProtToggleActivePort,
        clientIfNearEndLoopbackTimeout,
        clientIfNearEndLoopbackEnabled,
        clientIfChangeNearEndLoopbackCommand,
        clientIfFarEndLoopbackEnabled,
        clientIfFarEndLoopbackTimeout,
        clientIfChangeFarEndLoopbackCommand,
        clientIfFormatNotSupportedByHw,
        clientIfLaserMode,
        clientIfAlarmIndicationSignalLineC2W,
        clientIfFarEndClientFailure,
        clientIfOHTransparency,
        clientIfConnectedLine }

    STATUS      deprecated
    DESCRIPTION
        "The interface objects V11 (13.0)."
    ::= { lumClientGroups 16 }

clientIfGroupV12 OBJECT-GROUP
    OBJECTS {
        clientIfIndex,
        clientIfName,
        clientIfSubrack,
        clientIfSlot,
        clientIfTxPort,
        clientIfRxPort,
        clientIfEntityId,
        clientIfAdminStatus,
        clientIfOperStatus,
        clientIfLaserStatus,
        clientIfTxSignalStatus,
        clientIfForwardAls,
        clientIfSuppressRemoteAlarms,
        clientIfFarEndLoopback,

        clientIfFormat,

        clientIfAutoNegotiationMode,
        clientIfAutoNegotiationStatus,
        clientIfDuplexCapability,
        clientIfFlowControlMode,
        clientIfInterPacketGap,
        clientIfFrameSize,
        clientIfGfpMode,
        clientIfBandWidth,
        clientIfRateLimit,

        clientIfTrxClass,

        clientIfLaserBias,
        clientIfPowerLevel,
        clientIfReceiverSensitivity,
        clientIfPowerLevelLowRelativeThreshold,

        clientIfLossOfSignal,
        clientIfLossOfFrame,
        clientIfBitrateMismatch,
        clientIfAuAlarmIndicationSignalW2C,
        clientIfTransmitterFailed,

        clientIfTrxCodeMismatch,
        clientIfTrxBitrateUnavailable,
        clientIfTrxMissing,

        clientIfReceivedPowerHigh,
        clientIfReceivedPowerLow,
        clientIfLinkDown,
        clientIfConfigurationCommand,
        clientIfGbeUtilization,
        clientIfLossOfSync,

        clientIfConfigureTrxModeCommand,
        clientIfTrxMode,
        clientIfExpectedTxFrequency,
        clientIfTxFrequency,
        clientIfUnexpectedTxFrequency,
        clientIfIllegalFrequency,
        clientIfLaserForcedOn,
        clientIfTrxMedia,
        clientIfTrxMediaMismatch,

        clientIfTruncAutoNegotiationMode,
        clientIfObjectProperty,
        clientIfTxPowerLevel,
        clientIfLaserTempActual,

        clientIfTraceIntrusionMode,
        clientIfTraceTransmitted,
        clientIfTraceReceived,
        clientIfTraceExpected,
        clientIfTraceAlarmMode,
        clientIfTraceMismatch,
        clientIfNearEndLoopback,
        clientIfMsAlarmIndicationSignalC2W,
        clientIfMsAlarmIndicationSignalW2C,
        clientIfRemoteDefectIndication,
        clientIfJ1TxTrailTrace,
        clientIfJ1TxTrailTraceInsertionMode,
        clientIfVcGroupFailedW2C,
        clientIfReadJ1,
        clientIfHighSpeed,
        clientIfActualFormat,
        clientIfRdiIntrusionMode,
        clientIfMuxQuadVc4,
        clientIfDemuxQuadVc4,
        clientIfCcConnectionMode,
        clientIfCcConfigurationCommand,
        clientIfIllegalSignalFormat,
        clientIfSynchProtPortId,
        clientIfSynchProtGroupMemberPort,
        clientIfSynchProtGroupStatus,
        clientIfSynchProtActivePort,
        clientIfSynchProtPortStatus,
        clientIfSynchProtToggleActivePort,
        clientIfNearEndLoopbackTimeout,
        clientIfNearEndLoopbackEnabled,
        clientIfChangeNearEndLoopbackCommand,
        clientIfFarEndLoopbackEnabled,
        clientIfFarEndLoopbackTimeout,
        clientIfChangeFarEndLoopbackCommand,
        clientIfFormatNotSupportedByHw,
        clientIfLaserMode,
        clientIfAlarmIndicationSignalLineC2W,
        clientIfFarEndClientFailure,
        clientIfOHTransparency,
        clientIfConnectedLine,
        clientIfForwardingErrorCorrectionMode,
        clientIfNoFrequencySet,
        clientIfJitterAttenuatorBW,
        clientIfConnectionStatus,
        clientIfLoopFilterUnlocked,
        clientIfCableLength,
        clientIfConnectedForeignIndex,
        clientIfDisconnect }

    STATUS      deprecated
    DESCRIPTION
        "The interface objects V11 (15.0)."
    ::= { lumClientGroups 17 }

clientIfGroupV13 OBJECT-GROUP
    OBJECTS {
        clientIfIndex,
        clientIfName,
        clientIfSubrack,
        clientIfSlot,
        clientIfTxPort,
        clientIfRxPort,
        clientIfEntityId,
        clientIfAdminStatus,
        clientIfOperStatus,
        clientIfLaserStatus,
        clientIfTxSignalStatus,
        clientIfForwardAls,
        clientIfSuppressRemoteAlarms,
        clientIfFarEndLoopback,

        clientIfFormat,

        clientIfAutoNegotiationMode,
        clientIfAutoNegotiationStatus,
        clientIfDuplexCapability,
        clientIfFlowControlMode,
        clientIfInterPacketGap,
        clientIfFrameSize,
        clientIfGfpMode,
        clientIfBandWidth,
        clientIfRateLimit,

        clientIfTrxClass,

        clientIfLaserBias,
        clientIfPowerLevel,
        clientIfReceiverSensitivity,
        clientIfPowerLevelLowRelativeThreshold,

        clientIfLossOfSignal,
        clientIfLossOfFrame,
        clientIfBitrateMismatch,
        clientIfAuAlarmIndicationSignalW2C,
        clientIfTransmitterFailed,

        clientIfTrxCodeMismatch,
        clientIfTrxBitrateUnavailable,
        clientIfTrxMissing,

        clientIfReceivedPowerHigh,
        clientIfReceivedPowerLow,
        clientIfLinkDown,
        clientIfConfigurationCommand,
        clientIfGbeUtilization,
        clientIfLossOfSync,

        clientIfConfigureTrxModeCommand,
        clientIfTrxMode,
        clientIfExpectedTxFrequency,
        clientIfTxFrequency,
        clientIfUnexpectedTxFrequency,
        clientIfIllegalFrequency,
        clientIfLaserForcedOn,
        clientIfTrxMedia,
        clientIfTrxMediaMismatch,

        clientIfTruncAutoNegotiationMode,
        clientIfObjectProperty,
        clientIfTxPowerLevel,
        clientIfLaserTempActual,

        clientIfTraceIntrusionMode,
        clientIfTraceTransmitted,
        clientIfTraceReceived,
        clientIfTraceExpected,
        clientIfTraceAlarmMode,
        clientIfTraceMismatch,
        clientIfNearEndLoopback,
        clientIfMsAlarmIndicationSignalC2W,
        clientIfMsAlarmIndicationSignalW2C,
        clientIfRemoteDefectIndication,
        clientIfJ1TxTrailTrace,
        clientIfJ1TxTrailTraceInsertionMode,
        clientIfVcGroupFailedW2C,
        clientIfReadJ1,
        clientIfHighSpeed,
        clientIfActualFormat,
        clientIfRdiIntrusionMode,
        clientIfMuxQuadVc4,
        clientIfDemuxQuadVc4,
        clientIfCcConnectionMode,
        clientIfCcConfigurationCommand,
        clientIfIllegalSignalFormat,
        clientIfSynchProtPortId,
        clientIfSynchProtGroupMemberPort,
        clientIfSynchProtGroupStatus,
        clientIfSynchProtActivePort,
        clientIfSynchProtPortStatus,
        clientIfSynchProtToggleActivePort,
        clientIfNearEndLoopbackTimeout,
        clientIfNearEndLoopbackEnabled,
        clientIfChangeNearEndLoopbackCommand,
        clientIfFarEndLoopbackEnabled,
        clientIfFarEndLoopbackTimeout,
        clientIfChangeFarEndLoopbackCommand,
        clientIfFormatNotSupportedByHw,
        clientIfLaserMode,
        clientIfAlarmIndicationSignalLineC2W,
        clientIfFarEndClientFailure,
        clientIfOHTransparency,
        clientIfConnectedLine,
        clientIfForwardingErrorCorrectionMode,
        clientIfNoFrequencySet,
        clientIfJitterAttenuatorBW,
        clientIfConnectionStatus,
        clientIfLoopFilterUnlocked,
        clientIfCableLength,
        clientIfConnectedForeignIndex,
        clientIfDisconnect,
        clientIfOHTransparencyBitMask,
        clientIfOHTransparencyString,
        clientIfOHTransparencySet,
        clientIfAuAlarmIndicationSignalC2W,
        clientIfAuLossOfPointerC2W,
        clientIfAuLossOfPointerW2C }

    STATUS      deprecated
    DESCRIPTION
        "The interface objects V13 (16.0)."
    ::= { lumClientGroups 18 }

clientVc4GroupV2 OBJECT-GROUP
    OBJECTS {
        clientVc4Index,
        clientVc4Name,
        clientVc4Descr,
        clientVc4Subrack,
        clientVc4Slot,
        clientVc4TxPort,
        clientVc4RxPort,
        clientVc4Vc4,
        clientVc4ObjectProperty,
        clientVc4AuAlarmIndicationSignal,
        clientVc4AuLossOfPointer,
        clientVc4RxSignalStatus,
        clientVc4ConcatenationStatus,
        clientVc4PayloadStatus,
        clientVc4ConnectionStatus}

    STATUS    current
    DESCRIPTION
        "The vc4 objects V2 (16.0)."
    ::= { lumClientGroups 19 }


clientIfGroupV14 OBJECT-GROUP
    OBJECTS {
        clientIfIndex,
        clientIfName,
        clientIfSubrack,
        clientIfSlot,
        clientIfTxPort,
        clientIfRxPort,
        clientIfEntityId,
        clientIfAdminStatus,
        clientIfOperStatus,
        clientIfLaserStatus,
        clientIfTxSignalStatus,
        clientIfForwardAls,
        clientIfSuppressRemoteAlarms,
        clientIfFarEndLoopback,
        clientIfFormat,
        clientIfAutoNegotiationMode,
        clientIfAutoNegotiationStatus,
        clientIfDuplexCapability,
        clientIfFlowControlMode,
        clientIfInterPacketGap,
        clientIfFrameSize,
        clientIfGfpMode,
        clientIfBandWidth,
        clientIfRateLimit,
        clientIfTrxClass,
        clientIfLaserBias,
        clientIfPowerLevel,
        clientIfReceiverSensitivity,
        clientIfPowerLevelLowRelativeThreshold,
        clientIfLossOfSignal,
        clientIfLossOfFrame,
        clientIfBitrateMismatch,
        clientIfAuAlarmIndicationSignalW2C,
        clientIfTransmitterFailed,
        clientIfTrxCodeMismatch,
        clientIfTrxBitrateUnavailable,
        clientIfTrxMissing,
        clientIfReceivedPowerHigh,
        clientIfReceivedPowerLow,
        clientIfLinkDown,
        clientIfConfigurationCommand,
        clientIfGbeUtilization,
        clientIfLossOfSync,
        clientIfConfigureTrxModeCommand,
        clientIfTrxMode,
        clientIfExpectedTxFrequency,
        clientIfTxFrequency,
        clientIfUnexpectedTxFrequency,
        clientIfIllegalFrequency,
        clientIfLaserForcedOn,
        clientIfTrxMedia,
        clientIfTrxMediaMismatch,
        clientIfTruncAutoNegotiationMode,
        clientIfObjectProperty,
        clientIfTxPowerLevel,
        clientIfLaserTempActual,
        clientIfTraceIntrusionMode,
        clientIfTraceTransmitted,
        clientIfTraceReceived,
        clientIfTraceExpected,
        clientIfTraceAlarmMode,
        clientIfTraceMismatch,
        clientIfNearEndLoopback,
        clientIfMsAlarmIndicationSignalC2W,
        clientIfMsAlarmIndicationSignalW2C,
        clientIfRemoteDefectIndication,
        clientIfJ1TxTrailTrace,
        clientIfJ1TxTrailTraceInsertionMode,
        clientIfVcGroupFailedW2C,
        clientIfReadJ1,
        clientIfHighSpeed,
        clientIfActualFormat,
        clientIfRdiIntrusionMode,
        clientIfMuxQuadVc4,
        clientIfDemuxQuadVc4,
        clientIfCcConnectionMode,
        clientIfCcConfigurationCommand,
        clientIfIllegalSignalFormat,
        clientIfSynchProtPortId,
        clientIfSynchProtGroupMemberPort,
        clientIfSynchProtGroupStatus,
        clientIfSynchProtActivePort,
        clientIfSynchProtPortStatus,
        clientIfSynchProtToggleActivePort,
        clientIfNearEndLoopbackTimeout,
        clientIfNearEndLoopbackEnabled,
        clientIfChangeNearEndLoopbackCommand,
        clientIfFarEndLoopbackEnabled,
        clientIfFarEndLoopbackTimeout,
        clientIfChangeFarEndLoopbackCommand,
        clientIfFormatNotSupportedByHw,
        clientIfLaserMode,
        clientIfAlarmIndicationSignalLineC2W,
        clientIfFarEndClientFailure,
        clientIfOHTransparency,
        clientIfConnectedLine,
        clientIfForwardingErrorCorrectionMode,
        clientIfNoFrequencySet,
        clientIfJitterAttenuatorBW,
        clientIfConnectionStatus,
        clientIfLoopFilterUnlocked,
        clientIfCableLength,
        clientIfConnectedForeignIndex,
        clientIfDisconnect,
        clientIfOHTransparencyBitMask,
        clientIfOHTransparencyString,
        clientIfOHTransparencySet,
        clientIfAuAlarmIndicationSignalC2W,
        clientIfAuLossOfPointerC2W,
        clientIfAuLossOfPointerW2C,
        clientIfEthStandbyIndicator }
--16.1 was never released!
    STATUS      deprecated
    DESCRIPTION
        "The interface objects V14 (16.1)."
    ::= { lumClientGroups 20 }

clientIfGroupV15 OBJECT-GROUP
    OBJECTS {
        clientIfIndex,
        clientIfName,
        clientIfSubrack,
        clientIfSlot,
        clientIfTxPort,
        clientIfRxPort,
        clientIfEntityId,
        clientIfAdminStatus,
        clientIfOperStatus,
        clientIfLaserStatus,
        clientIfTxSignalStatus,
        clientIfForwardAls,
        clientIfSuppressRemoteAlarms,
        clientIfFarEndLoopback,

        clientIfFormat,

        clientIfAutoNegotiationMode,
        clientIfAutoNegotiationStatus,
        clientIfDuplexCapability,
        clientIfFlowControlMode,
        clientIfInterPacketGap,
        clientIfFrameSize,
        clientIfGfpMode,
        clientIfBandWidth,
        clientIfRateLimit,

        clientIfTrxClass,

        clientIfLaserBias,
        clientIfPowerLevel,
        clientIfReceiverSensitivity,
        clientIfPowerLevelLowRelativeThreshold,

        clientIfLossOfSignal,
        clientIfLossOfFrame,
        clientIfBitrateMismatch,
        clientIfAuAlarmIndicationSignalW2C,
        clientIfTransmitterFailed,

        clientIfTrxCodeMismatch,
        clientIfTrxBitrateUnavailable,
        clientIfTrxMissing,

        clientIfReceivedPowerHigh,
        clientIfReceivedPowerLow,
        clientIfLinkDown,
        clientIfConfigurationCommand,
        clientIfGbeUtilization,
        clientIfLossOfSync,

        clientIfConfigureTrxModeCommand,
        clientIfTrxMode,
        clientIfExpectedTxFrequency,
        clientIfTxFrequency,
        clientIfUnexpectedTxFrequency,
        clientIfIllegalFrequency,
        clientIfLaserForcedOn,
        clientIfTrxMedia,
        clientIfTrxMediaMismatch,

        clientIfTruncAutoNegotiationMode,
        clientIfObjectProperty,
        clientIfTxPowerLevel,
        clientIfLaserTempActual,

        clientIfTraceIntrusionMode,
        clientIfTraceTransmitted,
        clientIfTraceReceived,
        clientIfTraceExpected,
        clientIfTraceAlarmMode,
        clientIfTraceMismatch,
        clientIfNearEndLoopback,
        clientIfMsAlarmIndicationSignalC2W,
        clientIfMsAlarmIndicationSignalW2C,
        clientIfRemoteDefectIndication,
        clientIfJ1TxTrailTrace,
        clientIfJ1TxTrailTraceInsertionMode,
        clientIfVcGroupFailedW2C,
        clientIfReadJ1,
        clientIfHighSpeed,
        clientIfActualFormat,
        clientIfRdiIntrusionMode,
        clientIfMuxQuadVc4,
        clientIfDemuxQuadVc4,
        clientIfCcConnectionMode,
        clientIfCcConfigurationCommand,
        clientIfIllegalSignalFormat,
        clientIfSynchProtPortId,
        clientIfSynchProtGroupMemberPort,
        clientIfSynchProtGroupStatus,
        clientIfSynchProtActivePort,
        clientIfSynchProtPortStatus,
        clientIfSynchProtToggleActivePort,
        clientIfNearEndLoopbackTimeout,
        clientIfNearEndLoopbackEnabled,
        clientIfChangeNearEndLoopbackCommand,
        clientIfFarEndLoopbackEnabled,
        clientIfFarEndLoopbackTimeout,
        clientIfChangeFarEndLoopbackCommand,
        clientIfFormatNotSupportedByHw,
        clientIfLaserMode,
        clientIfAlarmIndicationSignalLineC2W,
        clientIfFarEndClientFailure,
        clientIfOHTransparency,
        clientIfConnectedLine,
        clientIfForwardingErrorCorrectionMode,
        clientIfNoFrequencySet,
        clientIfJitterAttenuatorBW,
        clientIfConnectionStatus,
        clientIfLoopFilterUnlocked,
        clientIfCableLength,
        clientIfConnectedForeignIndex,
        clientIfDisconnect,
        clientIfOHTransparencyBitMask,
        clientIfOHTransparencyString,
        clientIfOHTransparencySet,
        clientIfAuAlarmIndicationSignalC2W,
        clientIfAuLossOfPointerC2W,
        clientIfAuLossOfPointerW2C,
        clientIfEthStandbyIndicator,
        clientIfAuAlarmIndicationSignalW2CSonet,
        clientIfAuAlarmIndicationSignalC2WSonet,
        clientIfAuLossOfPointerC2WSonet,
        clientIfAuLossOfPointerW2CSonet}

    STATUS      deprecated
    DESCRIPTION
        "The interface objects V15 (17.0)."
    ::= { lumClientGroups 21 }

clientIfGroupV16 OBJECT-GROUP
    OBJECTS {
        clientIfIndex,
        clientIfName,
        clientIfSubrack,
        clientIfSlot,
        clientIfTxPort,
        clientIfRxPort,
        clientIfEntityId,
        clientIfAdminStatus,
        clientIfOperStatus,
        clientIfLaserStatus,
        clientIfTxSignalStatus,
        clientIfForwardAls,
        clientIfSuppressRemoteAlarms,
        clientIfFarEndLoopback,

        clientIfFormat,

        clientIfAutoNegotiationMode,
        clientIfAutoNegotiationStatus,
        clientIfDuplexCapability,
        clientIfFlowControlMode,
        clientIfInterPacketGap,
        clientIfFrameSize,
        clientIfGfpMode,
        clientIfBandWidth,
        clientIfRateLimit,

        clientIfTrxClass,

        clientIfLaserBias,
        clientIfPowerLevel,
        clientIfReceiverSensitivity,
        clientIfPowerLevelLowRelativeThreshold,

        clientIfLossOfSignal,
        clientIfLossOfFrame,
        clientIfBitrateMismatch,
        clientIfAuAlarmIndicationSignalW2C,
        clientIfTransmitterFailed,

        clientIfTrxCodeMismatch,
        clientIfTrxBitrateUnavailable,
        clientIfTrxMissing,

        clientIfReceivedPowerHigh,
        clientIfReceivedPowerLow,
        clientIfLinkDown,
        clientIfConfigurationCommand,
        clientIfGbeUtilization,
        clientIfLossOfSync,

        clientIfConfigureTrxModeCommand,
        clientIfTrxMode,
        clientIfExpectedTxFrequency,
        clientIfTxFrequency,
        clientIfUnexpectedTxFrequency,
        clientIfIllegalFrequency,
        clientIfLaserForcedOn,
        clientIfTrxMedia,
        clientIfTrxMediaMismatch,

        clientIfTruncAutoNegotiationMode,
        clientIfObjectProperty,
        clientIfTxPowerLevel,
        clientIfLaserTempActual,

        clientIfTraceIntrusionMode,
        clientIfTraceTransmitted,
        clientIfTraceReceived,
        clientIfTraceExpected,
        clientIfTraceAlarmMode,
        clientIfTraceMismatch,
        clientIfNearEndLoopback,
        clientIfMsAlarmIndicationSignalC2W,
        clientIfMsAlarmIndicationSignalW2C,
        clientIfRemoteDefectIndication,
        clientIfJ1TxTrailTrace,
        clientIfJ1TxTrailTraceInsertionMode,
        clientIfVcGroupFailedW2C,
        clientIfReadJ1,
        clientIfHighSpeed,
        clientIfActualFormat,
        clientIfRdiIntrusionMode,
        clientIfMuxQuadVc4,
        clientIfDemuxQuadVc4,
        clientIfCcConnectionMode,
        clientIfCcConfigurationCommand,
        clientIfIllegalSignalFormat,
        clientIfSynchProtPortId,
        clientIfSynchProtGroupMemberPort,
        clientIfSynchProtGroupStatus,
        clientIfSynchProtActivePort,
        clientIfSynchProtPortStatus,
        clientIfSynchProtToggleActivePort,
        clientIfNearEndLoopbackTimeout,
        clientIfNearEndLoopbackEnabled,
        clientIfChangeNearEndLoopbackCommand,
        clientIfFarEndLoopbackEnabled,
        clientIfFarEndLoopbackTimeout,
        clientIfChangeFarEndLoopbackCommand,
        clientIfFormatNotSupportedByHw,
        clientIfLaserMode,
        clientIfAlarmIndicationSignalLineC2W,
        clientIfFarEndClientFailure,
        clientIfOHTransparency,
        clientIfConnectedLine,
        clientIfForwardingErrorCorrectionMode,
        clientIfNoFrequencySet,
        clientIfJitterAttenuatorBW,
        clientIfConnectionStatus,
        clientIfLoopFilterUnlocked,
        clientIfCableLength,
        clientIfConnectedForeignIndex,
        clientIfDisconnect,
        clientIfOHTransparencyBitMask,
        clientIfOHTransparencyString,
        clientIfOHTransparencySet,
        clientIfAuAlarmIndicationSignalC2W,
        clientIfAuLossOfPointerC2W,
        clientIfAuLossOfPointerW2C,
        clientIfEthStandbyIndicator,
        clientIfAuAlarmIndicationSignalW2CSonet,
        clientIfAuAlarmIndicationSignalC2WSonet,
        clientIfAuLossOfPointerC2WSonet,
        clientIfAuLossOfPointerW2CSonet,
        clientIfTransceiverNoLoopback,
        clientIfFecFailure}

    STATUS      deprecated
    DESCRIPTION
        "The interface objects V16 (19.0)."
    ::= { lumClientGroups 22 }

clientIfGroupV17 OBJECT-GROUP
    OBJECTS {
        clientIfIndex,
        clientIfName,
        clientIfSubrack,
        clientIfSlot,
        clientIfTxPort,
        clientIfRxPort,
        clientIfEntityId,
        clientIfAdminStatus,
        clientIfOperStatus,
        clientIfLaserStatus,
        clientIfTxSignalStatus,
        clientIfForwardAls,
        clientIfSuppressRemoteAlarms,
        clientIfFarEndLoopback,

        clientIfFormat,

        clientIfAutoNegotiationMode,
        clientIfAutoNegotiationStatus,
        clientIfDuplexCapability,
        clientIfFlowControlMode,
        clientIfInterPacketGap,
        clientIfFrameSize,
        clientIfGfpMode,
        clientIfBandWidth,
        clientIfRateLimit,

        clientIfTrxClass,

        clientIfLaserBias,
        clientIfPowerLevel,
        clientIfReceiverSensitivity,
        clientIfPowerLevelLowRelativeThreshold,

        clientIfLossOfSignal,
        clientIfLossOfFrame,
        clientIfBitrateMismatch,
        clientIfAuAlarmIndicationSignalW2C,
        clientIfTransmitterFailed,

        clientIfTrxCodeMismatch,
        clientIfTrxBitrateUnavailable,
        clientIfTrxMissing,

        clientIfReceivedPowerHigh,
        clientIfReceivedPowerLow,
        clientIfLinkDown,
        clientIfConfigurationCommand,
        clientIfGbeUtilization,
        clientIfLossOfSync,

        clientIfConfigureTrxModeCommand,
        clientIfTrxMode,
        clientIfExpectedTxFrequency,
        clientIfTxFrequency,
        clientIfUnexpectedTxFrequency,
        clientIfIllegalFrequency,
        clientIfLaserForcedOn,
        clientIfTrxMedia,
        clientIfTrxMediaMismatch,

        clientIfTruncAutoNegotiationMode,
        clientIfObjectProperty,
        clientIfTxPowerLevel,
        clientIfLaserTempActual,

        clientIfTraceIntrusionMode,
        clientIfTraceTransmitted,
        clientIfTraceReceived,
        clientIfTraceExpected,
        clientIfTraceAlarmMode,
        clientIfTraceMismatch,
        clientIfNearEndLoopback,
        clientIfMsAlarmIndicationSignalC2W,
        clientIfMsAlarmIndicationSignalW2C,
        clientIfRemoteDefectIndication,
        clientIfJ1TxTrailTrace,
        clientIfJ1TxTrailTraceInsertionMode,
        clientIfVcGroupFailedW2C,
        clientIfReadJ1,
        clientIfHighSpeed,
        clientIfActualFormat,
        clientIfRdiIntrusionMode,
        clientIfMuxQuadVc4,
        clientIfDemuxQuadVc4,
        clientIfCcConnectionMode,
        clientIfCcConfigurationCommand,
        clientIfIllegalSignalFormat,
        clientIfSynchProtPortId,
        clientIfSynchProtGroupMemberPort,
        clientIfSynchProtGroupStatus,
        clientIfSynchProtActivePort,
        clientIfSynchProtPortStatus,
        clientIfSynchProtToggleActivePort,
        clientIfNearEndLoopbackTimeout,
        clientIfNearEndLoopbackEnabled,
        clientIfChangeNearEndLoopbackCommand,
        clientIfFarEndLoopbackEnabled,
        clientIfFarEndLoopbackTimeout,
        clientIfChangeFarEndLoopbackCommand,
        clientIfFormatNotSupportedByHw,
        clientIfLaserMode,
        clientIfAlarmIndicationSignalLineC2W,
        clientIfFarEndClientFailure,
        clientIfOHTransparency,
        clientIfConnectedLine,
        clientIfForwardingErrorCorrectionMode,
        clientIfNoFrequencySet,
        clientIfJitterAttenuatorBW,
        clientIfConnectionStatus,
        clientIfLoopFilterUnlocked,
        clientIfCableLength,
        clientIfConnectedForeignIndex,
        clientIfDisconnect,
        clientIfOHTransparencyBitMask,
        clientIfOHTransparencyString,
        clientIfOHTransparencySet,
        clientIfAuAlarmIndicationSignalC2W,
        clientIfAuLossOfPointerC2W,
        clientIfAuLossOfPointerW2C,
        clientIfEthStandbyIndicator,
        clientIfAuAlarmIndicationSignalW2CSonet,
        clientIfAuAlarmIndicationSignalC2WSonet,
        clientIfAuLossOfPointerC2WSonet,
        clientIfAuLossOfPointerW2CSonet,
        clientIfTransceiverNoLoopback,
        clientIfFecFailure,
        clientIfLaneAlignmentError}

    STATUS      deprecated
    DESCRIPTION
        "The interface objects V17 (20.0)."
    ::= { lumClientGroups 23 }

clientLanesGroup OBJECT-GROUP
    OBJECTS {
        clientLanesIndex,
        clientLanesName,
        clientLanesSubrack,
        clientLanesSlot,
        clientLanesTxPort,
        clientLanesRxPort,
        clientLanesLaneId,
        clientLanesRxPowerLevel,
        clientLanesWaveLength,
        clientLanesBE,
        clientLanesResetBE,
        clientLanesLossOfSignal,
        clientLanesObjectProperty,
        clientLanesLossOfSync,
        clientLanesLocalLinkFault,
        clientLanesRemoteLinkFault,
        clientLanesHighBitErrorRate}

    STATUS    deprecated
    DESCRIPTION
        "The lane objects (20.0)."
    ::= { lumClientGroups 24 }

clientIfGroupV18 OBJECT-GROUP
    OBJECTS {
        clientIfIndex,
        clientIfName,
        clientIfSubrack,
        clientIfSlot,
        clientIfTxPort,
        clientIfRxPort,
        clientIfEntityId,
        clientIfAdminStatus,
        clientIfOperStatus,
        clientIfLaserStatus,
        clientIfTxSignalStatus,
        clientIfForwardAls,
        clientIfSuppressRemoteAlarms,
        clientIfFarEndLoopback,

        clientIfFormat,

        clientIfAutoNegotiationMode,
        clientIfAutoNegotiationStatus,
        clientIfDuplexCapability,
        clientIfFlowControlMode,
        clientIfInterPacketGap,
        clientIfFrameSize,
        clientIfGfpMode,
        clientIfBandWidth,
        clientIfRateLimit,

        clientIfTrxClass,

        clientIfLaserBias,
        clientIfPowerLevel,
        clientIfReceiverSensitivity,
        clientIfPowerLevelLowRelativeThreshold,

        clientIfLossOfSignal,
        clientIfLossOfFrame,
        clientIfBitrateMismatch,
        clientIfAuAlarmIndicationSignalW2C,
        clientIfTransmitterFailed,

        clientIfTrxCodeMismatch,
        clientIfTrxBitrateUnavailable,
        clientIfTrxMissing,

        clientIfReceivedPowerHigh,
        clientIfReceivedPowerLow,
        clientIfLinkDown,
        clientIfConfigurationCommand,
        clientIfGbeUtilization,
        clientIfLossOfSync,

        clientIfConfigureTrxModeCommand,
        clientIfTrxMode,
        clientIfExpectedTxFrequency,
        clientIfTxFrequency,
        clientIfUnexpectedTxFrequency,
        clientIfIllegalFrequency,
        clientIfLaserForcedOn,
        clientIfTrxMedia,
        clientIfTrxMediaMismatch,

        clientIfTruncAutoNegotiationMode,
        clientIfObjectProperty,
        clientIfTxPowerLevel,
        clientIfLaserTempActual,

        clientIfTraceIntrusionMode,
        clientIfTraceTransmitted,
        clientIfTraceReceived,
        clientIfTraceExpected,
        clientIfTraceAlarmMode,
        clientIfTraceMismatch,
        clientIfNearEndLoopback,
        clientIfMsAlarmIndicationSignalC2W,
        clientIfMsAlarmIndicationSignalW2C,
        clientIfRemoteDefectIndication,
        clientIfJ1TxTrailTrace,
        clientIfJ1TxTrailTraceInsertionMode,
        clientIfVcGroupFailedW2C,
        clientIfReadJ1,
        clientIfHighSpeed,
        clientIfActualFormat,
        clientIfRdiIntrusionMode,
        clientIfMuxQuadVc4,
        clientIfDemuxQuadVc4,
        clientIfCcConnectionMode,
        clientIfCcConfigurationCommand,
        clientIfIllegalSignalFormat,
        clientIfSynchProtPortId,
        clientIfSynchProtGroupMemberPort,
        clientIfSynchProtGroupStatus,
        clientIfSynchProtActivePort,
        clientIfSynchProtPortStatus,
        clientIfSynchProtToggleActivePort,
        clientIfNearEndLoopbackTimeout,
        clientIfNearEndLoopbackEnabled,
        clientIfChangeNearEndLoopbackCommand,
        clientIfFarEndLoopbackEnabled,
        clientIfFarEndLoopbackTimeout,
        clientIfChangeFarEndLoopbackCommand,
        clientIfFormatNotSupportedByHw,
        clientIfLaserMode,
        clientIfAlarmIndicationSignalLineC2W,
        clientIfFarEndClientFailure,
        clientIfOHTransparency,
        clientIfConnectedLine,
        clientIfForwardingErrorCorrectionMode,
        clientIfNoFrequencySet,
        clientIfJitterAttenuatorBW,
        clientIfConnectionStatus,
        clientIfLoopFilterUnlocked,
        clientIfCableLength,
        clientIfConnectedForeignIndex,
        clientIfDisconnect,
        clientIfOHTransparencyBitMask,
        clientIfOHTransparencyString,
        clientIfOHTransparencySet,
        clientIfAuAlarmIndicationSignalC2W,
        clientIfAuLossOfPointerC2W,
        clientIfAuLossOfPointerW2C,
        clientIfEthStandbyIndicator,
        clientIfAuAlarmIndicationSignalW2CSonet,
        clientIfAuAlarmIndicationSignalC2WSonet,
        clientIfAuLossOfPointerC2WSonet,
        clientIfAuLossOfPointerW2CSonet,
        clientIfTransceiverNoLoopback,
        clientIfFecFailure,
        clientIfLaneAlignmentError,
        clientIfFecCorrectedZeros,
        clientIfFecCorrectedOnes,
        clientIfSignalDegraded}

    STATUS      deprecated
    DESCRIPTION
        "The interface objects V18 (20.0)."
    ::= { lumClientGroups 25 }

clientIfGroupV19 OBJECT-GROUP
    OBJECTS {
        clientIfIndex,
        clientIfName,
        clientIfSubrack,
        clientIfSlot,
        clientIfTxPort,
        clientIfRxPort,
        clientIfEntityId,
        clientIfAdminStatus,
        clientIfOperStatus,
        clientIfLaserStatus,
        clientIfTxSignalStatus,
        clientIfForwardAls,
        clientIfSuppressRemoteAlarms,
        clientIfFarEndLoopback,

        clientIfFormat,

        clientIfAutoNegotiationMode,
        clientIfAutoNegotiationStatus,
        clientIfDuplexCapability,
        clientIfFlowControlMode,
        clientIfInterPacketGap,
        clientIfFrameSize,
        clientIfGfpMode,
        clientIfBandWidth,
        clientIfRateLimit,

        clientIfTrxClass,

        clientIfLaserBias,
        clientIfPowerLevel,
        clientIfReceiverSensitivity,
        clientIfPowerLevelLowRelativeThreshold,

        clientIfLossOfSignal,
        clientIfLossOfFrame,
        clientIfBitrateMismatch,
        clientIfAuAlarmIndicationSignalW2C,
        clientIfTransmitterFailed,

        clientIfTrxCodeMismatch,
        clientIfTrxBitrateUnavailable,
        clientIfTrxMissing,

        clientIfReceivedPowerHigh,
        clientIfReceivedPowerLow,
        clientIfLinkDown,
        clientIfConfigurationCommand,
        clientIfGbeUtilization,
        clientIfLossOfSync,

        clientIfConfigureTrxModeCommand,
        clientIfTrxMode,
        clientIfExpectedTxFrequency,
        clientIfTxFrequency,
        clientIfUnexpectedTxFrequency,
        clientIfIllegalFrequency,
        clientIfLaserForcedOn,
        clientIfTrxMedia,
        clientIfTrxMediaMismatch,

        clientIfTruncAutoNegotiationMode,
        clientIfObjectProperty,
        clientIfTxPowerLevel,
        clientIfLaserTempActual,

        clientIfTraceIntrusionMode,
        clientIfTraceTransmitted,
        clientIfTraceReceived,
        clientIfTraceExpected,
        clientIfTraceAlarmMode,
        clientIfTraceMismatch,
        clientIfNearEndLoopback,
        clientIfMsAlarmIndicationSignalC2W,
        clientIfMsAlarmIndicationSignalW2C,
        clientIfRemoteDefectIndication,
        clientIfJ1TxTrailTrace,
        clientIfJ1TxTrailTraceInsertionMode,
        clientIfVcGroupFailedW2C,
        clientIfReadJ1,
        clientIfHighSpeed,
        clientIfActualFormat,
        clientIfRdiIntrusionMode,
        clientIfMuxQuadVc4,
        clientIfDemuxQuadVc4,
        clientIfCcConnectionMode,
        clientIfCcConfigurationCommand,
        clientIfIllegalSignalFormat,
        clientIfSynchProtPortId,
        clientIfSynchProtGroupMemberPort,
        clientIfSynchProtGroupStatus,
        clientIfSynchProtActivePort,
        clientIfSynchProtPortStatus,
        clientIfSynchProtToggleActivePort,
        clientIfNearEndLoopbackTimeout,
        clientIfNearEndLoopbackEnabled,
        clientIfChangeNearEndLoopbackCommand,
        clientIfFarEndLoopbackEnabled,
        clientIfFarEndLoopbackTimeout,
        clientIfChangeFarEndLoopbackCommand,
        clientIfFormatNotSupportedByHw,
        clientIfLaserMode,
        clientIfAlarmIndicationSignalLineC2W,
        clientIfFarEndClientFailure,
        clientIfOHTransparency,
        clientIfConnectedLine,
        clientIfForwardingErrorCorrectionMode,
        clientIfNoFrequencySet,
        clientIfJitterAttenuatorBW,
        clientIfConnectionStatus,
        clientIfLoopFilterUnlocked,
        clientIfCableLength,
        clientIfConnectedForeignIndex,
        clientIfDisconnect,
        clientIfOHTransparencyBitMask,
        clientIfOHTransparencyString,
        clientIfOHTransparencySet,
        clientIfAuAlarmIndicationSignalC2W,
        clientIfAuLossOfPointerC2W,
        clientIfAuLossOfPointerW2C,
        clientIfEthStandbyIndicator,
        clientIfAuAlarmIndicationSignalW2CSonet,
        clientIfAuAlarmIndicationSignalC2WSonet,
        clientIfAuLossOfPointerC2WSonet,
        clientIfAuLossOfPointerW2CSonet,
        clientIfTransceiverNoLoopback,
        clientIfFecFailure,
        clientIfLaneAlignmentError,
        clientIfFecCorrectedZeros,
        clientIfFecCorrectedOnes,
        clientIfSignalDegraded,
        clientIfFecType,
        clientIfSignalDegradeThreshold}

    STATUS      deprecated
    DESCRIPTION
        "The interface objects V19 (21.0)."
    ::= { lumClientGroups 26 }

clientIfGroupV20 OBJECT-GROUP
    OBJECTS {
        clientIfIndex,
        clientIfName,
        clientIfSubrack,
        clientIfSlot,
        clientIfTxPort,
        clientIfRxPort,
        clientIfEntityId,
        clientIfAdminStatus,
        clientIfOperStatus,
        clientIfLaserStatus,
        clientIfTxSignalStatus,
        clientIfForwardAls,
        clientIfSuppressRemoteAlarms,
        clientIfFarEndLoopback,

        clientIfFormat,

        clientIfAutoNegotiationMode,
        clientIfAutoNegotiationStatus,
        clientIfDuplexCapability,
        clientIfFlowControlMode,
        clientIfInterPacketGap,
        clientIfFrameSize,
        clientIfGfpMode,
        clientIfBandWidth,
        clientIfRateLimit,

        clientIfTrxClass,

        clientIfLaserBias,
        clientIfPowerLevel,
        clientIfReceiverSensitivity,
        clientIfPowerLevelLowRelativeThreshold,

        clientIfLossOfSignal,
        clientIfLossOfFrame,
        clientIfBitrateMismatch,
        clientIfAuAlarmIndicationSignalW2C,
        clientIfTransmitterFailed,

        clientIfTrxCodeMismatch,
        clientIfTrxBitrateUnavailable,
        clientIfTrxMissing,

        clientIfReceivedPowerHigh,
        clientIfReceivedPowerLow,
        clientIfLinkDown,
        clientIfConfigurationCommand,
        clientIfGbeUtilization,
        clientIfLossOfSync,

        clientIfConfigureTrxModeCommand,
        clientIfTrxMode,
        clientIfExpectedTxFrequency,
        clientIfTxFrequency,
        clientIfUnexpectedTxFrequency,
        clientIfIllegalFrequency,
        clientIfLaserForcedOn,
        clientIfTrxMedia,
        clientIfTrxMediaMismatch,

        clientIfTruncAutoNegotiationMode,
        clientIfObjectProperty,
        clientIfTxPowerLevel,
        clientIfLaserTempActual,

        clientIfTraceIntrusionMode,
        clientIfTraceTransmitted,
        clientIfTraceReceived,
        clientIfTraceExpected,
        clientIfTraceAlarmMode,
        clientIfTraceMismatch,
        clientIfNearEndLoopback,
        clientIfMsAlarmIndicationSignalC2W,
        clientIfMsAlarmIndicationSignalW2C,
        clientIfRemoteDefectIndication,
        clientIfJ1TxTrailTrace,
        clientIfJ1TxTrailTraceInsertionMode,
        clientIfVcGroupFailedW2C,
        clientIfReadJ1,
        clientIfHighSpeed,
        clientIfActualFormat,
        clientIfRdiIntrusionMode,
        clientIfMuxQuadVc4,
        clientIfDemuxQuadVc4,
        clientIfCcConnectionMode,
        clientIfCcConfigurationCommand,
        clientIfIllegalSignalFormat,
        clientIfSynchProtPortId,
        clientIfSynchProtGroupMemberPort,
        clientIfSynchProtGroupStatus,
        clientIfSynchProtActivePort,
        clientIfSynchProtPortStatus,
        clientIfSynchProtToggleActivePort,
        clientIfNearEndLoopbackTimeout,
        clientIfNearEndLoopbackEnabled,
        clientIfChangeNearEndLoopbackCommand,
        clientIfFarEndLoopbackEnabled,
        clientIfFarEndLoopbackTimeout,
        clientIfChangeFarEndLoopbackCommand,
        clientIfFormatNotSupportedByHw,
        clientIfLaserMode,
        clientIfAlarmIndicationSignalLineC2W,
        clientIfFarEndClientFailure,
        clientIfOHTransparency,
        clientIfConnectedLine,
        clientIfForwardingErrorCorrectionMode,
        clientIfNoFrequencySet,
        clientIfJitterAttenuatorBW,
        clientIfConnectionStatus,
        clientIfLoopFilterUnlocked,
        clientIfCableLength,
        clientIfConnectedForeignIndex,
        clientIfDisconnect,
        clientIfOHTransparencyBitMask,
        clientIfOHTransparencyString,
        clientIfOHTransparencySet,
        clientIfAuAlarmIndicationSignalC2W,
        clientIfAuLossOfPointerC2W,
        clientIfAuLossOfPointerW2C,
        clientIfEthStandbyIndicator,
        clientIfAuAlarmIndicationSignalW2CSonet,
        clientIfAuAlarmIndicationSignalC2WSonet,
        clientIfAuLossOfPointerC2WSonet,
        clientIfAuLossOfPointerW2CSonet,
        clientIfTransceiverNoLoopback,
        clientIfFecFailure,
        clientIfLaneAlignmentError,
        clientIfFecCorrectedZeros,
        clientIfFecCorrectedOnes,
        clientIfSignalDegraded,
        clientIfFecType,
        clientIfSignalDegradeThreshold,
        clientIfExpectedOpticalLayerMapping,
        clientIfActualOpticalLayerMapping,
        clientIfConfigurationMismatch}

    STATUS      deprecated
    DESCRIPTION
        "The interface objects V20 (23.0)."
    ::= { lumClientGroups 27 }

clientLanesGroupV2 OBJECT-GROUP
    OBJECTS {
        clientLanesIndex,
        clientLanesName,
        clientLanesSubrack,
        clientLanesSlot,
        clientLanesTxPort,
        clientLanesRxPort,
        clientLanesLaneId,
        clientLanesRxPowerLevel,
        clientLanesWaveLength,
        clientLanesBE,
        clientLanesResetBE,
        clientLanesLossOfSignal,
        clientLanesObjectProperty,
        clientLanesLossOfSync,
        clientLanesLocalLinkFault,
        clientLanesRemoteLinkFault,
        clientLanesHighBitErrorRate,
        clientLanesReceiverSensitivity,
        clientLanesReceivedPowerLow}

    STATUS    deprecated
    DESCRIPTION
        "The lane objects V2 (23.0)."
    ::= { lumClientGroups 28 }


clientIfGroupV21 OBJECT-GROUP
    OBJECTS {
        clientIfIndex,
        clientIfName,
        clientIfSubrack,
        clientIfSlot,
        clientIfTxPort,
        clientIfRxPort,
        clientIfEntityId,
        clientIfAdminStatus,
        clientIfOperStatus,
        clientIfLaserStatus,
        clientIfTxSignalStatus,
        clientIfForwardAls,
        clientIfSuppressRemoteAlarms,
        clientIfFarEndLoopback,

        clientIfFormat,

        clientIfAutoNegotiationMode,
        clientIfAutoNegotiationStatus,
        clientIfDuplexCapability,
        clientIfFlowControlMode,
        clientIfInterPacketGap,
        clientIfFrameSize,
        clientIfGfpMode,
        clientIfBandWidth,
        clientIfRateLimit,

        clientIfTrxClass,

        clientIfLaserBias,
        clientIfPowerLevel,
        clientIfReceiverSensitivity,
        clientIfPowerLevelLowRelativeThreshold,

        clientIfLossOfSignal,
        clientIfLossOfFrame,
        clientIfBitrateMismatch,
        clientIfAuAlarmIndicationSignalW2C,
        clientIfTransmitterFailed,

        clientIfTrxCodeMismatch,
        clientIfTrxBitrateUnavailable,
        clientIfTrxMissing,

        clientIfReceivedPowerHigh,
        clientIfReceivedPowerLow,
        clientIfLinkDown,
        clientIfConfigurationCommand,
        clientIfGbeUtilization,
        clientIfLossOfSync,

        clientIfConfigureTrxModeCommand,
        clientIfTrxMode,
        clientIfExpectedTxFrequency,
        clientIfTxFrequency,
        clientIfUnexpectedTxFrequency,
        clientIfIllegalFrequency,
        clientIfLaserForcedOn,
        clientIfTrxMedia,
        clientIfTrxMediaMismatch,

        clientIfTruncAutoNegotiationMode,
        clientIfObjectProperty,
        clientIfTxPowerLevel,
        clientIfLaserTempActual,

        clientIfTraceIntrusionMode,
        clientIfTraceTransmitted,
        clientIfTraceReceived,
        clientIfTraceExpected,
        clientIfTraceAlarmMode,
        clientIfTraceMismatch,
        clientIfNearEndLoopback,
        clientIfMsAlarmIndicationSignalC2W,
        clientIfMsAlarmIndicationSignalW2C,
        clientIfRemoteDefectIndication,
        clientIfJ1TxTrailTrace,
        clientIfJ1TxTrailTraceInsertionMode,
        clientIfVcGroupFailedW2C,
        clientIfReadJ1,
        clientIfHighSpeed,
        clientIfActualFormat,
        clientIfRdiIntrusionMode,
        clientIfMuxQuadVc4,
        clientIfDemuxQuadVc4,
        clientIfCcConnectionMode,
        clientIfCcConfigurationCommand,
        clientIfIllegalSignalFormat,
        clientIfSynchProtPortId,
        clientIfSynchProtGroupMemberPort,
        clientIfSynchProtGroupStatus,
        clientIfSynchProtActivePort,
        clientIfSynchProtPortStatus,
        clientIfSynchProtToggleActivePort,
        clientIfNearEndLoopbackTimeout,
        clientIfNearEndLoopbackEnabled,
        clientIfChangeNearEndLoopbackCommand,
        clientIfFarEndLoopbackEnabled,
        clientIfFarEndLoopbackTimeout,
        clientIfChangeFarEndLoopbackCommand,
        clientIfFormatNotSupportedByHw,
        clientIfLaserMode,
        clientIfAlarmIndicationSignalLineC2W,
        clientIfFarEndClientFailure,
        clientIfOHTransparency,
        clientIfConnectedLine,
        clientIfForwardingErrorCorrectionMode,
        clientIfNoFrequencySet,
        clientIfJitterAttenuatorBW,
        clientIfConnectionStatus,
        clientIfLoopFilterUnlocked,
        clientIfCableLength,
        clientIfConnectedForeignIndex,
        clientIfDisconnect,
        clientIfOHTransparencyBitMask,
        clientIfOHTransparencyString,
        clientIfOHTransparencySet,
        clientIfAuAlarmIndicationSignalC2W,
        clientIfAuLossOfPointerC2W,
        clientIfAuLossOfPointerW2C,
        clientIfEthStandbyIndicator,
        clientIfAuAlarmIndicationSignalW2CSonet,
        clientIfAuAlarmIndicationSignalC2WSonet,
        clientIfAuLossOfPointerC2WSonet,
        clientIfAuLossOfPointerW2CSonet,
        clientIfTransceiverNoLoopback,
        clientIfFecFailure,
        clientIfLaneAlignmentError,
        clientIfFecCorrectedZeros,
        clientIfFecCorrectedOnes,
        clientIfSignalDegraded,
        clientIfFecType,
        clientIfSignalDegradeThreshold,
        clientIfExpectedOpticalLayerMapping,
        clientIfActualOpticalLayerMapping,
        clientIfConfigurationMismatch,
        clientIfChromaticDispersion,
        clientIfDifferentialGroupDelay,
        clientIfTxState,
        clientIfRxState}

    STATUS      deprecated
    DESCRIPTION
        "The interface objects V20 (23.1)."
    ::= { lumClientGroups 29 }


clientIfGroupV22 OBJECT-GROUP
    OBJECTS {
        clientIfIndex,
        clientIfName,
        clientIfDescr,
        clientIfSubrack,
        clientIfSlot,
        clientIfTxPort,
        clientIfRxPort,
        clientIfInvPhysIndexOrZero,
        clientIfEntityId,
        clientIfAdminStatus,
        clientIfOperStatus,
        clientIfLaserStatus,
        clientIfTxSignalStatus,
        clientIfForwardAls,
        clientIfSuppressRemoteAlarms,
        clientIfFarEndLoopback,

        clientIfFormat,

        clientIfAutoNegotiationMode,
        clientIfAutoNegotiationStatus,
        clientIfDuplexCapability,
        clientIfFlowControlMode,
        clientIfInterPacketGap,
        clientIfFrameSize,
        clientIfGfpMode,
        clientIfBandWidth,
        clientIfRateLimit,

        clientIfTrxClass,

        clientIfLaserBias,
        clientIfPowerLevel,
        clientIfReceiverSensitivity,
        clientIfPowerLevelLowRelativeThreshold,

        clientIfLossOfSignal,
        clientIfLossOfFrame,
        clientIfBitrateMismatch,
        clientIfAuAlarmIndicationSignalW2C,
        clientIfTransmitterFailed,

        clientIfTrxCodeMismatch,
        clientIfTrxBitrateUnavailable,
        clientIfTrxMissing,

        clientIfReceivedPowerHigh,
        clientIfReceivedPowerLow,
        clientIfLinkDown,
        clientIfConfigurationCommand,
        clientIfGbeUtilization,
        clientIfLossOfSync,
        clientIfRxSignalStatus,
        clientIfTrxFailed,
        clientIfDisabled,
        clientIfLoopback,
        clientIfClientSignalFailed,
        clientIfAuLossOfPointer,
        clientIfGfpLossOfFrame,

        clientIfConfigureTrxModeCommand,
        clientIfTrxMode,
        clientIfExpectedTxFrequency,
        clientIfTxFrequency,
        clientIfUnexpectedTxFrequency,
        clientIfIllegalFrequency,
        clientIfLaserForcedOn,
        clientIfTrxMedia,
        clientIfTrxMediaMismatch,

        clientIfTruncAutoNegotiationMode,
        clientIfObjectProperty,
        clientIfTxPowerLevel,
        clientIfLaserTempActual,

        clientIfTraceIntrusionMode,
        clientIfTraceTransmitted,
        clientIfTraceReceived,
        clientIfTraceExpected,
        clientIfTraceAlarmMode,
        clientIfTraceMismatch,
        clientIfNearEndLoopback,
        clientIfMsAlarmIndicationSignalC2W,
        clientIfMsAlarmIndicationSignalW2C,
        clientIfRemoteDefectIndication,
        clientIfJ1TxTrailTrace,
        clientIfJ1TxTrailTraceInsertionMode,
        clientIfVcGroupFailedW2C,
        clientIfReadJ1,
        clientIfHighSpeed,
        clientIfActualFormat,
        clientIfRdiIntrusionMode,
        clientIfMuxQuadVc4,
        clientIfDemuxQuadVc4,
        clientIfCcConnectionMode,
        clientIfCcConfigurationCommand,
        clientIfIllegalSignalFormat,
        clientIfSynchProtPortId,
        clientIfSynchProtGroupMemberPort,
        clientIfSynchProtGroupStatus,
        clientIfSynchProtActivePort,
        clientIfSynchProtPortStatus,
        clientIfSynchProtToggleActivePort,
        clientIfNearEndLoopbackTimeout,
        clientIfNearEndLoopbackEnabled,
        clientIfChangeNearEndLoopbackCommand,
        clientIfFarEndLoopbackEnabled,
        clientIfFarEndLoopbackTimeout,
        clientIfChangeFarEndLoopbackCommand,
        clientIfFormatNotSupportedByHw,
        clientIfLaserMode,
        clientIfAlarmIndicationSignalLineC2W,
        clientIfFarEndClientFailure,
        clientIfOHTransparency,
        clientIfConnectedLine,
        clientIfForwardingErrorCorrectionMode,
        clientIfNoFrequencySet,
        clientIfJitterAttenuatorBW,
        clientIfConnectionStatus,
        clientIfLoopFilterUnlocked,
        clientIfCableLength,
        clientIfConnectedForeignIndex,
        clientIfDisconnect,
        clientIfOHTransparencyBitMask,
        clientIfOHTransparencyString,
        clientIfOHTransparencySet,
        clientIfAuAlarmIndicationSignalC2W,
        clientIfAuLossOfPointerC2W,
        clientIfAuLossOfPointerW2C,
        clientIfEthStandbyIndicator,
        clientIfAuAlarmIndicationSignalW2CSonet,
        clientIfAuAlarmIndicationSignalC2WSonet,
        clientIfAuLossOfPointerC2WSonet,
        clientIfAuLossOfPointerW2CSonet,
        clientIfTransceiverNoLoopback,
        clientIfFecFailure,
        clientIfLaneAlignmentError,
        clientIfFecCorrectedZeros,
        clientIfFecCorrectedOnes,
        clientIfSignalDegraded,
        clientIfFecType,
        clientIfSignalDegradeThreshold,
        clientIfExpectedOpticalLayerMapping,
        clientIfActualOpticalLayerMapping,
        clientIfConfigurationMismatch,
        clientIfChromaticDispersion,
        clientIfDifferentialGroupDelay,
        clientIfTxState,
        clientIfRxState,
        clientIfIdx,
        clientIfIfNo,
        clientIfIdxIf,
        clientIfUpPortId,
        clientIfNoOfLanes,
        clientIfFecCorrectedBits,
        clientIfOSNRMargin,
        clientIfExpectedPhysicalLayerMapping,
        clientIfSignalDirection}

    STATUS      deprecated
    DESCRIPTION
        "The interface objects V22 (26.1)."
    ::= { lumClientGroups 30 }

    clientLanesGroupV3 OBJECT-GROUP
    OBJECTS {
        clientLanesIndex,
        clientLanesName,
        clientLanesSubrack,
        clientLanesSlot,
        clientLanesTxPort,
        clientLanesRxPort,
        clientLanesLaneId,
        clientLanesRxPowerLevel,
        clientLanesWaveLength,
        clientLanesBE,
        clientLanesResetBE,
        clientLanesLossOfSignal,
        clientLanesObjectProperty,
        clientLanesLossOfSync,
        clientLanesLocalLinkFault,
        clientLanesRemoteLinkFault,
        clientLanesHighBitErrorRate,
        clientLanesReceiverSensitivity,
        clientLanesReceivedPowerLow,
        clientLanesIfNo,
        clientLanesIdx,
        clientLanesClientIfIdx}

    STATUS    deprecated
    DESCRIPTION
        "The lane objects V3 (26.1)."
    ::= { lumClientGroups 31 }


    clientLanesGroupV4 OBJECT-GROUP
    OBJECTS {
        clientLanesIndex,
        clientLanesName,
        clientLanesSubrack,
        clientLanesSlot,
        clientLanesTxPort,
        clientLanesRxPort,
        clientLanesLaneId,
        clientLanesRxPowerLevel,
        clientLanesWaveLength,
        clientLanesBE,
        clientLanesResetBE,
        clientLanesLossOfSignal,
        clientLanesObjectProperty,
        clientLanesLossOfSync,
        clientLanesLocalLinkFault,
        clientLanesRemoteLinkFault,
        clientLanesHighBitErrorRate,
        clientLanesReceiverSensitivity,
        clientLanesReceivedPowerLow,
        clientLanesIfNo,
        clientLanesIdx,
        clientLanesClientIfIdx,
        clientLanesAdminStatus,
        clientLanesOperStatus}

    STATUS    deprecated
    DESCRIPTION
        "The lane objects V4 (26.1)."
    ::= { lumClientGroups 32 }

    clientMpoLanesGroupV1 OBJECT-GROUP
    OBJECTS {
        clientMpoLanesIndex,
        clientMpoLanesName,
        clientMpoLanesSubrack,
        clientMpoLanesSlot,
        clientMpoLanesLaneId,
        clientMpoLanesRxPowerLevel,
        clientMpoLanesRxSensitivity,
        clientMpoLanesWaveLength,
        clientMpoLanesLossOfSignal,
        clientMpoLanesObjectProperty,
        clientMpoLanesRxPowerLow,
        clientMpoLanesIfNo,
        clientMpoLanesAdminStatus,
        clientMpoLanesOperStatus,
        clientMpoLanesForwardAls,
        clientMpoLanesPowerLevelLowRelativeThreshold,
        clientMpoLanesLaserStatus}

    STATUS    current
    DESCRIPTION
        "The mpo lane objects (release 27.0)."
    ::= { lumClientGroups 33 }

    clientLanesGroupV5 OBJECT-GROUP
    OBJECTS {
        clientLanesIndex,
        clientLanesName,
        clientLanesSubrack,
        clientLanesSlot,
        clientLanesTxPort,
        clientLanesRxPort,
        clientLanesLaneId,
        clientLanesRxPowerLevel,
        clientLanesWaveLength,
        clientLanesBE,
        clientLanesResetBE,
        clientLanesLossOfSignal,
        clientLanesObjectProperty,
        clientLanesLossOfSync,
        clientLanesLocalLinkFault,
        clientLanesRemoteLinkFault,
        clientLanesHighBitErrorRate,
        clientLanesReceiverSensitivity,
        clientLanesReceivedPowerLow,
        clientLanesIfNo,
        clientLanesIdx,
        clientLanesClientIfIdx,
        clientLanesAdminStatus,
        clientLanesOperStatus,
        clientLanesUpPortId}

    STATUS    current
    DESCRIPTION
        "The lane objects V5 (28.1)."
    ::= { lumClientGroups 34 }

clientIfGroupV23 OBJECT-GROUP
    OBJECTS {
        clientIfIndex,
        clientIfName,
        clientIfDescr,
        clientIfSubrack,
        clientIfSlot,
        clientIfTxPort,
        clientIfRxPort,
        clientIfInvPhysIndexOrZero,
        clientIfEntityId,
        clientIfAdminStatus,
        clientIfOperStatus,
        clientIfLaserStatus,
        clientIfTxSignalStatus,
        clientIfForwardAls,
        clientIfSuppressRemoteAlarms,
        clientIfFarEndLoopback,

        clientIfFormat,

        clientIfAutoNegotiationMode,
        clientIfAutoNegotiationStatus,
        clientIfDuplexCapability,
        clientIfFlowControlMode,
        clientIfInterPacketGap,
        clientIfFrameSize,
        clientIfGfpMode,
        clientIfBandWidth,
        clientIfRateLimit,

        clientIfTrxClass,

        clientIfLaserBias,
        clientIfPowerLevel,
        clientIfReceiverSensitivity,
        clientIfPowerLevelLowRelativeThreshold,

        clientIfLossOfSignal,
        clientIfLossOfFrame,
        clientIfBitrateMismatch,
        clientIfAuAlarmIndicationSignalW2C,
        clientIfTransmitterFailed,

        clientIfTrxCodeMismatch,
        clientIfTrxBitrateUnavailable,
        clientIfTrxMissing,

        clientIfReceivedPowerHigh,
        clientIfReceivedPowerLow,
        clientIfLinkDown,
        clientIfConfigurationCommand,
        clientIfGbeUtilization,
        clientIfLossOfSync,
        clientIfRxSignalStatus,
        clientIfTrxFailed,
        clientIfDisabled,
        clientIfLoopback,
        clientIfClientSignalFailed,
        clientIfAuLossOfPointer,
        clientIfGfpLossOfFrame,

        clientIfConfigureTrxModeCommand,
        clientIfTrxMode,
        clientIfExpectedTxFrequency,
        clientIfTxFrequency,
        clientIfUnexpectedTxFrequency,
        clientIfIllegalFrequency,
        clientIfLaserForcedOn,
        clientIfTrxMedia,
        clientIfTrxMediaMismatch,

        clientIfTruncAutoNegotiationMode,
        clientIfObjectProperty,
        clientIfTxPowerLevel,
        clientIfLaserTempActual,

        clientIfTraceIntrusionMode,
        clientIfTraceTransmitted,
        clientIfTraceReceived,
        clientIfTraceExpected,
        clientIfTraceAlarmMode,
        clientIfTraceMismatch,
        clientIfNearEndLoopback,
        clientIfMsAlarmIndicationSignalC2W,
        clientIfMsAlarmIndicationSignalW2C,
        clientIfRemoteDefectIndication,
        clientIfJ1TxTrailTrace,
        clientIfJ1TxTrailTraceInsertionMode,
        clientIfVcGroupFailedW2C,
        clientIfReadJ1,
        clientIfHighSpeed,
        clientIfActualFormat,
        clientIfRdiIntrusionMode,
        clientIfMuxQuadVc4,
        clientIfDemuxQuadVc4,
        clientIfCcConnectionMode,
        clientIfCcConfigurationCommand,
        clientIfIllegalSignalFormat,
        clientIfSynchProtPortId,
        clientIfSynchProtGroupMemberPort,
        clientIfSynchProtGroupStatus,
        clientIfSynchProtActivePort,
        clientIfSynchProtPortStatus,
        clientIfSynchProtToggleActivePort,
        clientIfNearEndLoopbackTimeout,
        clientIfNearEndLoopbackEnabled,
        clientIfChangeNearEndLoopbackCommand,
        clientIfFarEndLoopbackEnabled,
        clientIfFarEndLoopbackTimeout,
        clientIfChangeFarEndLoopbackCommand,
        clientIfFormatNotSupportedByHw,
        clientIfLaserMode,
        clientIfAlarmIndicationSignalLineC2W,
        clientIfFarEndClientFailure,
        clientIfOHTransparency,
        clientIfConnectedLine,
        clientIfForwardingErrorCorrectionMode,
        clientIfNoFrequencySet,
        clientIfJitterAttenuatorBW,
        clientIfConnectionStatus,
        clientIfLoopFilterUnlocked,
        clientIfCableLength,
        clientIfConnectedForeignIndex,
        clientIfDisconnect,
        clientIfOHTransparencyBitMask,
        clientIfOHTransparencyString,
        clientIfOHTransparencySet,
        clientIfAuAlarmIndicationSignalC2W,
        clientIfAuLossOfPointerC2W,
        clientIfAuLossOfPointerW2C,
        clientIfEthStandbyIndicator,
        clientIfAuAlarmIndicationSignalW2CSonet,
        clientIfAuAlarmIndicationSignalC2WSonet,
        clientIfAuLossOfPointerC2WSonet,
        clientIfAuLossOfPointerW2CSonet,
        clientIfTransceiverNoLoopback,
        clientIfFecFailure,
        clientIfLaneAlignmentError,
        clientIfFecCorrectedZeros,
        clientIfFecCorrectedOnes,
        clientIfSignalDegraded,
        clientIfFecType,
        clientIfSignalDegradeThreshold,
        clientIfExpectedOpticalLayerMapping,
        clientIfActualOpticalLayerMapping,
        clientIfConfigurationMismatch,
        clientIfChromaticDispersion,
        clientIfDifferentialGroupDelay,
        clientIfTxState,
        clientIfRxState,
        clientIfIdx,
        clientIfIfNo,
        clientIfIdxIf,
        clientIfUpPortId,
        clientIfNoOfLanes,
        clientIfFecCorrectedBits,
        clientIfOSNRMargin,
        clientIfExpectedPhysicalLayerMapping,
        clientIfSignalDirection,
        clientIfAid,
        clientIfPhysicalLocation}

    STATUS     deprecated
    DESCRIPTION
        "The interface objects V23 (28.0)."
    ::= { lumClientGroups 35 }

    clientIfGroupV24 OBJECT-GROUP
        OBJECTS {
            clientIfIndex,
            clientIfName,
            clientIfDescr,
            clientIfSubrack,
            clientIfSlot,
            clientIfTxPort,
            clientIfRxPort,
            clientIfInvPhysIndexOrZero,
            clientIfEntityId,
            clientIfAdminStatus,
            clientIfOperStatus,
            clientIfLaserStatus,
            clientIfTxSignalStatus,
            clientIfForwardAls,
            clientIfSuppressRemoteAlarms,
            clientIfFarEndLoopback,

            clientIfFormat,

            clientIfAutoNegotiationMode,
            clientIfAutoNegotiationStatus,
            clientIfDuplexCapability,
            clientIfFlowControlMode,
            clientIfInterPacketGap,
            clientIfFrameSize,
            clientIfGfpMode,
            clientIfBandWidth,
            clientIfRateLimit,

            clientIfTrxClass,

            clientIfLaserBias,
            clientIfPowerLevel,
            clientIfReceiverSensitivity,
            clientIfPowerLevelLowRelativeThreshold,

            clientIfLossOfSignal,
            clientIfLossOfFrame,
            clientIfBitrateMismatch,
            clientIfAuAlarmIndicationSignalW2C,
            clientIfTransmitterFailed,

            clientIfTrxCodeMismatch,
            clientIfTrxBitrateUnavailable,
            clientIfTrxMissing,

            clientIfReceivedPowerHigh,
            clientIfReceivedPowerLow,
            clientIfLinkDown,
            clientIfConfigurationCommand,
            clientIfGbeUtilization,
            clientIfLossOfSync,
            clientIfRxSignalStatus,
            clientIfTrxFailed,
            clientIfDisabled,
            clientIfLoopback,
            clientIfClientSignalFailed,
            clientIfAuLossOfPointer,
            clientIfGfpLossOfFrame,

            clientIfConfigureTrxModeCommand,
            clientIfTrxMode,
            clientIfExpectedTxFrequency,
            clientIfTxFrequency,
            clientIfUnexpectedTxFrequency,
            clientIfIllegalFrequency,
            clientIfLaserForcedOn,
            clientIfTrxMedia,
            clientIfTrxMediaMismatch,

            clientIfTruncAutoNegotiationMode,
            clientIfObjectProperty,
            clientIfTxPowerLevel,
            clientIfLaserTempActual,

            clientIfTraceIntrusionMode,
            clientIfTraceTransmitted,
            clientIfTraceReceived,
            clientIfTraceExpected,
            clientIfTraceAlarmMode,
            clientIfTraceMismatch,
            clientIfNearEndLoopback,
            clientIfMsAlarmIndicationSignalC2W,
            clientIfMsAlarmIndicationSignalW2C,
            clientIfRemoteDefectIndication,
            clientIfJ1TxTrailTrace,
            clientIfJ1TxTrailTraceInsertionMode,
            clientIfVcGroupFailedW2C,
            clientIfReadJ1,
            clientIfHighSpeed,
            clientIfActualFormat,
            clientIfRdiIntrusionMode,
            clientIfMuxQuadVc4,
            clientIfDemuxQuadVc4,
            clientIfCcConnectionMode,
            clientIfCcConfigurationCommand,
            clientIfIllegalSignalFormat,
            clientIfSynchProtPortId,
            clientIfSynchProtGroupMemberPort,
            clientIfSynchProtGroupStatus,
            clientIfSynchProtActivePort,
            clientIfSynchProtPortStatus,
            clientIfSynchProtToggleActivePort,
            clientIfNearEndLoopbackTimeout,
            clientIfNearEndLoopbackEnabled,
            clientIfChangeNearEndLoopbackCommand,
            clientIfFarEndLoopbackEnabled,
            clientIfFarEndLoopbackTimeout,
            clientIfChangeFarEndLoopbackCommand,
            clientIfFormatNotSupportedByHw,
            clientIfLaserMode,
            clientIfAlarmIndicationSignalLineC2W,
            clientIfFarEndClientFailure,
            clientIfOHTransparency,
            clientIfConnectedLine,
            clientIfForwardingErrorCorrectionMode,
            clientIfNoFrequencySet,
            clientIfJitterAttenuatorBW,
            clientIfConnectionStatus,
            clientIfLoopFilterUnlocked,
            clientIfCableLength,
            clientIfConnectedForeignIndex,
            clientIfDisconnect,
            clientIfOHTransparencyBitMask,
            clientIfOHTransparencyString,
            clientIfOHTransparencySet,
            clientIfAuAlarmIndicationSignalC2W,
            clientIfAuLossOfPointerC2W,
            clientIfAuLossOfPointerW2C,
            clientIfEthStandbyIndicator,
            clientIfAuAlarmIndicationSignalW2CSonet,
            clientIfAuAlarmIndicationSignalC2WSonet,
            clientIfAuLossOfPointerC2WSonet,
            clientIfAuLossOfPointerW2CSonet,
            clientIfTransceiverNoLoopback,
            clientIfFecFailure,
            clientIfLaneAlignmentError,
            clientIfFecCorrectedZeros,
            clientIfFecCorrectedOnes,
            clientIfSignalDegraded,
            clientIfFecType,
            clientIfSignalDegradeThreshold,
            clientIfExpectedOpticalLayerMapping,
            clientIfActualOpticalLayerMapping,
            clientIfConfigurationMismatch,
            clientIfChromaticDispersion,
            clientIfDifferentialGroupDelay,
            clientIfTxState,
            clientIfRxState,
            clientIfIdx,
            clientIfIfNo,
            clientIfIdxIf,
            clientIfUpPortId,
            clientIfNoOfLanes,
            clientIfFecCorrectedBits,
            clientIfOSNRMargin,
            clientIfExpectedPhysicalLayerMapping,
            clientIfSignalDirection,
            clientIfAid,
            clientIfPhysicalLocation,
            clientIfTrxCommunicationFailure
            }

        STATUS      deprecated
        DESCRIPTION
            "The interface objects V24 (29.0)."
        ::= { lumClientGroups 36 }


    clientIfGroupV25 OBJECT-GROUP
        OBJECTS {
            clientIfIndex,
            clientIfName,
            clientIfDescr,
            clientIfSubrack,
            clientIfSlot,
            clientIfTxPort,
            clientIfRxPort,
            clientIfInvPhysIndexOrZero,
            clientIfEntityId,
            clientIfAdminStatus,
            clientIfOperStatus,
            clientIfLaserStatus,
            clientIfTxSignalStatus,
            clientIfForwardAls,
            clientIfSuppressRemoteAlarms,
            clientIfFarEndLoopback,

            clientIfFormat,

            clientIfAutoNegotiationMode,
            clientIfAutoNegotiationStatus,
            clientIfDuplexCapability,
            clientIfFlowControlMode,
            clientIfInterPacketGap,
            clientIfFrameSize,
            clientIfGfpMode,
            clientIfBandWidth,
            clientIfRateLimit,

            clientIfTrxClass,

            clientIfLaserBias,
            clientIfPowerLevel,
            clientIfReceiverSensitivity,
            clientIfPowerLevelLowRelativeThreshold,

            clientIfLossOfSignal,
            clientIfLossOfFrame,
            clientIfBitrateMismatch,
            clientIfAuAlarmIndicationSignalW2C,
            clientIfTransmitterFailed,

            clientIfTrxCodeMismatch,
            clientIfTrxBitrateUnavailable,
            clientIfTrxMissing,

            clientIfReceivedPowerHigh,
            clientIfReceivedPowerLow,
            clientIfLinkDown,
            clientIfConfigurationCommand,
            clientIfGbeUtilization,
            clientIfLossOfSync,
            clientIfRxSignalStatus,
            clientIfTrxFailed,
            clientIfDisabled,
            clientIfLoopback,
            clientIfClientSignalFailed,
            clientIfAuLossOfPointer,
            clientIfGfpLossOfFrame,

            clientIfConfigureTrxModeCommand,
            clientIfTrxMode,
            clientIfExpectedTxFrequency,
            clientIfTxFrequency,
            clientIfUnexpectedTxFrequency,
            clientIfIllegalFrequency,
            clientIfLaserForcedOn,
            clientIfTrxMedia,
            clientIfTrxMediaMismatch,

            clientIfTruncAutoNegotiationMode,
            clientIfObjectProperty,
            clientIfTxPowerLevel,
            clientIfLaserTempActual,

            clientIfTraceIntrusionMode,
            clientIfTraceTransmitted,
            clientIfTraceReceived,
            clientIfTraceExpected,
            clientIfTraceAlarmMode,
            clientIfTraceMismatch,
            clientIfNearEndLoopback,
            clientIfMsAlarmIndicationSignalC2W,
            clientIfMsAlarmIndicationSignalW2C,
            clientIfRemoteDefectIndication,
            clientIfJ1TxTrailTrace,
            clientIfJ1TxTrailTraceInsertionMode,
            clientIfVcGroupFailedW2C,
            clientIfReadJ1,
            clientIfHighSpeed,
            clientIfActualFormat,
            clientIfRdiIntrusionMode,
            clientIfMuxQuadVc4,
            clientIfDemuxQuadVc4,
            clientIfCcConnectionMode,
            clientIfCcConfigurationCommand,
            clientIfIllegalSignalFormat,
            clientIfSynchProtPortId,
            clientIfSynchProtGroupMemberPort,
            clientIfSynchProtGroupStatus,
            clientIfSynchProtActivePort,
            clientIfSynchProtPortStatus,
            clientIfSynchProtToggleActivePort,
            clientIfNearEndLoopbackTimeout,
            clientIfNearEndLoopbackEnabled,
            clientIfChangeNearEndLoopbackCommand,
            clientIfFarEndLoopbackEnabled,
            clientIfFarEndLoopbackTimeout,
            clientIfChangeFarEndLoopbackCommand,
            clientIfFormatNotSupportedByHw,
            clientIfLaserMode,
            clientIfAlarmIndicationSignalLineC2W,
            clientIfFarEndClientFailure,
            clientIfOHTransparency,
            clientIfConnectedLine,
            clientIfForwardingErrorCorrectionMode,
            clientIfNoFrequencySet,
            clientIfJitterAttenuatorBW,
            clientIfConnectionStatus,
            clientIfLoopFilterUnlocked,
            clientIfCableLength,
            clientIfConnectedForeignIndex,
            clientIfDisconnect,
            clientIfOHTransparencyBitMask,
            clientIfOHTransparencyString,
            clientIfOHTransparencySet,
            clientIfAuAlarmIndicationSignalC2W,
            clientIfAuLossOfPointerC2W,
            clientIfAuLossOfPointerW2C,
            clientIfEthStandbyIndicator,
            clientIfAuAlarmIndicationSignalW2CSonet,
            clientIfAuAlarmIndicationSignalC2WSonet,
            clientIfAuLossOfPointerC2WSonet,
            clientIfAuLossOfPointerW2CSonet,
            clientIfTransceiverNoLoopback,
            clientIfFecFailure,
            clientIfLaneAlignmentError,
            clientIfFecCorrectedZeros,
            clientIfFecCorrectedOnes,
            clientIfSignalDegraded,
            clientIfFecType,
            clientIfSignalDegradeThreshold,
            clientIfExpectedOpticalLayerMapping,
            clientIfActualOpticalLayerMapping,
            clientIfConfigurationMismatch,
            clientIfChromaticDispersion,
            clientIfDifferentialGroupDelay,
            clientIfTxState,
            clientIfRxState,
            clientIfIdx,
            clientIfIfNo,
            clientIfIdxIf,
            clientIfUpPortId,
            clientIfNoOfLanes,
            clientIfFecCorrectedBits,
            clientIfOSNRMargin,
            clientIfExpectedPhysicalLayerMapping,
            clientIfSignalDirection,
            clientIfAid,
            clientIfPhysicalLocation,
            clientIfTrxCommunicationFailure,
            clientIfTribPortId,
            clientIfIfType
            }

        STATUS     deprecated
        DESCRIPTION
            "The interface objects V25 (30.0)."
        ::= { lumClientGroups 37 }

    clientIfGroupV26 OBJECT-GROUP
        OBJECTS {
            clientIfIndex,
            clientIfName,
            clientIfDescr,
            clientIfSubrack,
            clientIfSlot,
            clientIfTxPort,
            clientIfRxPort,
            clientIfInvPhysIndexOrZero,
            clientIfEntityId,
            clientIfAdminStatus,
            clientIfOperStatus,
            clientIfLaserStatus,
            clientIfTxSignalStatus,
            clientIfForwardAls,
            clientIfSuppressRemoteAlarms,
            clientIfFarEndLoopback,

            clientIfFormat,

            clientIfAutoNegotiationMode,
            clientIfAutoNegotiationStatus,
            clientIfDuplexCapability,
            clientIfFlowControlMode,
            clientIfInterPacketGap,
            clientIfFrameSize,
            clientIfGfpMode,
            clientIfBandWidth,
            clientIfRateLimit,

            clientIfTrxClass,

            clientIfLaserBias,
            clientIfPowerLevel,
            clientIfReceiverSensitivity,
            clientIfPowerLevelLowRelativeThreshold,

            clientIfLossOfSignal,
            clientIfLossOfFrame,
            clientIfBitrateMismatch,
            clientIfAuAlarmIndicationSignalW2C,
            clientIfTransmitterFailed,

            clientIfTrxCodeMismatch,
            clientIfTrxBitrateUnavailable,
            clientIfTrxMissing,

            clientIfReceivedPowerHigh,
            clientIfReceivedPowerLow,
            clientIfLinkDown,
            clientIfConfigurationCommand,
            clientIfGbeUtilization,
            clientIfLossOfSync,
            clientIfRxSignalStatus,
            clientIfTrxFailed,
            clientIfDisabled,
            clientIfLoopback,
            clientIfClientSignalFailed,
            clientIfAuLossOfPointer,
            clientIfGfpLossOfFrame,

            clientIfConfigureTrxModeCommand,
            clientIfTrxMode,
            clientIfExpectedTxFrequency,
            clientIfTxFrequency,
            clientIfUnexpectedTxFrequency,
            clientIfIllegalFrequency,
            clientIfLaserForcedOn,
            clientIfTrxMedia,
            clientIfTrxMediaMismatch,

            clientIfTruncAutoNegotiationMode,
            clientIfObjectProperty,
            clientIfTxPowerLevel,
            clientIfLaserTempActual,

            clientIfTraceIntrusionMode,
            clientIfTraceTransmitted,
            clientIfTraceReceived,
            clientIfTraceExpected,
            clientIfTraceAlarmMode,
            clientIfTraceMismatch,
            clientIfNearEndLoopback,
            clientIfMsAlarmIndicationSignalC2W,
            clientIfMsAlarmIndicationSignalW2C,
            clientIfRemoteDefectIndication,
            clientIfJ1TxTrailTrace,
            clientIfJ1TxTrailTraceInsertionMode,
            clientIfVcGroupFailedW2C,
            clientIfReadJ1,
            clientIfHighSpeed,
            clientIfActualFormat,
            clientIfRdiIntrusionMode,
            clientIfMuxQuadVc4,
            clientIfDemuxQuadVc4,
            clientIfCcConnectionMode,
            clientIfCcConfigurationCommand,
            clientIfIllegalSignalFormat,
            clientIfSynchProtPortId,
            clientIfSynchProtGroupMemberPort,
            clientIfSynchProtGroupStatus,
            clientIfSynchProtActivePort,
            clientIfSynchProtPortStatus,
            clientIfSynchProtToggleActivePort,
            clientIfNearEndLoopbackTimeout,
            clientIfNearEndLoopbackEnabled,
            clientIfChangeNearEndLoopbackCommand,
            clientIfFarEndLoopbackEnabled,
            clientIfFarEndLoopbackTimeout,
            clientIfChangeFarEndLoopbackCommand,
            clientIfFormatNotSupportedByHw,
            clientIfLaserMode,
            clientIfAlarmIndicationSignalLineC2W,
            clientIfFarEndClientFailure,
            clientIfOHTransparency,
            clientIfConnectedLine,
            clientIfForwardingErrorCorrectionMode,
            clientIfNoFrequencySet,
            clientIfJitterAttenuatorBW,
            clientIfConnectionStatus,
            clientIfLoopFilterUnlocked,
            clientIfCableLength,
            clientIfConnectedForeignIndex,
            clientIfDisconnect,
            clientIfOHTransparencyBitMask,
            clientIfOHTransparencyString,
            clientIfOHTransparencySet,
            clientIfAuAlarmIndicationSignalC2W,
            clientIfAuLossOfPointerC2W,
            clientIfAuLossOfPointerW2C,
            clientIfEthStandbyIndicator,
            clientIfAuAlarmIndicationSignalW2CSonet,
            clientIfAuAlarmIndicationSignalC2WSonet,
            clientIfAuLossOfPointerC2WSonet,
            clientIfAuLossOfPointerW2CSonet,
            clientIfTransceiverNoLoopback,
            clientIfFecFailure,
            clientIfLaneAlignmentError,
            clientIfFecCorrectedZeros,
            clientIfFecCorrectedOnes,
            clientIfSignalDegraded,
            clientIfFecType,
            clientIfSignalDegradeThreshold,
            clientIfExpectedOpticalLayerMapping,
            clientIfActualOpticalLayerMapping,
            clientIfConfigurationMismatch,
            clientIfChromaticDispersion,
            clientIfDifferentialGroupDelay,
            clientIfTxState,
            clientIfRxState,
            clientIfIdx,
            clientIfIfNo,
            clientIfIdxIf,
            clientIfUpPortId,
            clientIfNoOfLanes,
            clientIfFecCorrectedBits,
            clientIfOSNRMargin,
            clientIfExpectedPhysicalLayerMapping,
            clientIfSignalDirection,
            clientIfAid,
            clientIfPhysicalLocation,
            clientIfTrxCommunicationFailure,
            clientIfTribPortId,
            clientIfIfType,
            clientIfConfigurationCommandSNMP
            }

        STATUS      deprecated
        DESCRIPTION
            "The interface objects V26 (30.1)."
        ::= { lumClientGroups 38 }

    clientIfGroupV27 OBJECT-GROUP
        OBJECTS {
            clientIfIndex,
            clientIfName,
            clientIfDescr,
            clientIfSubrack,
            clientIfSlot,
            clientIfTxPort,
            clientIfRxPort,
            clientIfInvPhysIndexOrZero,
            clientIfEntityId,
            clientIfAdminStatus,
            clientIfOperStatus,
            clientIfLaserStatus,
            clientIfTxSignalStatus,
            clientIfForwardAls,
            clientIfSuppressRemoteAlarms,
            clientIfFarEndLoopback,

            clientIfFormat,

            clientIfAutoNegotiationMode,
            clientIfAutoNegotiationStatus,
            clientIfDuplexCapability,
            clientIfFlowControlMode,
            clientIfInterPacketGap,
            clientIfFrameSize,
            clientIfGfpMode,
            clientIfBandWidth,
            clientIfRateLimit,

            clientIfTrxClass,

            clientIfLaserBias,
            clientIfPowerLevel,
            clientIfReceiverSensitivity,
            clientIfPowerLevelLowRelativeThreshold,

            clientIfLossOfSignal,
            clientIfLossOfFrame,
            clientIfBitrateMismatch,
            clientIfAuAlarmIndicationSignalW2C,
            clientIfTransmitterFailed,

            clientIfTrxCodeMismatch,
            clientIfTrxBitrateUnavailable,
            clientIfTrxMissing,

            clientIfReceivedPowerHigh,
            clientIfReceivedPowerLow,
            clientIfLinkDown,
            clientIfConfigurationCommand,
            clientIfGbeUtilization,
            clientIfLossOfSync,
            clientIfRxSignalStatus,
            clientIfTrxFailed,
            clientIfDisabled,
            clientIfLoopback,
            clientIfClientSignalFailed,
            clientIfAuLossOfPointer,
            clientIfGfpLossOfFrame,

            clientIfConfigureTrxModeCommand,
            clientIfTrxMode,
            clientIfExpectedTxFrequency,
            clientIfTxFrequency,
            clientIfUnexpectedTxFrequency,
            clientIfIllegalFrequency,
            clientIfLaserForcedOn,
            clientIfTrxMedia,
            clientIfTrxMediaMismatch,

            clientIfTruncAutoNegotiationMode,
            clientIfObjectProperty,
            clientIfTxPowerLevel,
            clientIfLaserTempActual,

            clientIfTraceIntrusionMode,
            clientIfTraceTransmitted,
            clientIfTraceReceived,
            clientIfTraceExpected,
            clientIfTraceAlarmMode,
            clientIfTraceMismatch,
            clientIfNearEndLoopback,
            clientIfMsAlarmIndicationSignalC2W,
            clientIfMsAlarmIndicationSignalW2C,
            clientIfRemoteDefectIndication,
            clientIfJ1TxTrailTrace,
            clientIfJ1TxTrailTraceInsertionMode,
            clientIfVcGroupFailedW2C,
            clientIfReadJ1,
            clientIfHighSpeed,
            clientIfActualFormat,
            clientIfRdiIntrusionMode,
            clientIfMuxQuadVc4,
            clientIfDemuxQuadVc4,
            clientIfCcConnectionMode,
            clientIfCcConfigurationCommand,
            clientIfIllegalSignalFormat,
            clientIfSynchProtPortId,
            clientIfSynchProtGroupMemberPort,
            clientIfSynchProtGroupStatus,
            clientIfSynchProtActivePort,
            clientIfSynchProtPortStatus,
            clientIfSynchProtToggleActivePort,
            clientIfNearEndLoopbackTimeout,
            clientIfNearEndLoopbackEnabled,
            clientIfChangeNearEndLoopbackCommand,
            clientIfFarEndLoopbackEnabled,
            clientIfFarEndLoopbackTimeout,
            clientIfChangeFarEndLoopbackCommand,
            clientIfFormatNotSupportedByHw,
            clientIfLaserMode,
            clientIfAlarmIndicationSignalLineC2W,
            clientIfFarEndClientFailure,
            clientIfOHTransparency,
            clientIfConnectedLine,
            clientIfForwardingErrorCorrectionMode,
            clientIfNoFrequencySet,
            clientIfJitterAttenuatorBW,
            clientIfConnectionStatus,
            clientIfLoopFilterUnlocked,
            clientIfCableLength,
            clientIfConnectedForeignIndex,
            clientIfDisconnect,
            clientIfOHTransparencyBitMask,
            clientIfOHTransparencyString,
            clientIfOHTransparencySet,
            clientIfAuAlarmIndicationSignalC2W,
            clientIfAuLossOfPointerC2W,
            clientIfAuLossOfPointerW2C,
            clientIfEthStandbyIndicator,
            clientIfAuAlarmIndicationSignalW2CSonet,
            clientIfAuAlarmIndicationSignalC2WSonet,
            clientIfAuLossOfPointerC2WSonet,
            clientIfAuLossOfPointerW2CSonet,
            clientIfTransceiverNoLoopback,
            clientIfFecFailure,
            clientIfLaneAlignmentError,
            clientIfFecCorrectedZeros,
            clientIfFecCorrectedOnes,
            clientIfSignalDegraded,
            clientIfFecType,
            clientIfSignalDegradeThreshold,
            clientIfExpectedOpticalLayerMapping,
            clientIfActualOpticalLayerMapping,
            clientIfConfigurationMismatch,
            clientIfChromaticDispersion,
            clientIfDifferentialGroupDelay,
            clientIfTxState,
            clientIfRxState,
            clientIfIdx,
            clientIfIfNo,
            clientIfIdxIf,
            clientIfUpPortId,
            clientIfNoOfLanes,
            clientIfFecCorrectedBits,
            clientIfOSNRMargin,
            clientIfExpectedPhysicalLayerMapping,
            clientIfSignalDirection,
            clientIfAid,
            clientIfPhysicalLocation,
            clientIfTrxCommunicationFailure,
            clientIfTribPortId,
            clientIfIfType,
            clientIfConfigurationCommandSNMP,
            clientIfTrxPowerOutOfRange
            }

        STATUS      current
        DESCRIPTION
            "The interface objects V27 (31.1)."
        ::= { lumClientGroups 39 }

-- ----------------------------------------------------
-- Compliance
-- ----------------------------------------------------

lumClientBasicComplV1 MODULE-COMPLIANCE
    STATUS      deprecated
    DESCRIPTION
        "Basic implementation requirements for the client MIB V1 (3.0)."
    MODULE
        MANDATORY-GROUPS {
            clientGeneralGroupV1,
            clientIfGroupV1 }
    ::= { lumClientCompl 1 }

lumClientBasicComplV2 MODULE-COMPLIANCE
    STATUS      deprecated
    DESCRIPTION
        "Basic implementation requirements for the client MIB V2 (3.1)."
    MODULE
        MANDATORY-GROUPS {
            clientGeneralGroupV2,
            clientIfGroupV2 }
    ::= { lumClientCompl 2 }

lumClientBasicComplV3 MODULE-COMPLIANCE
    STATUS      deprecated
    DESCRIPTION
        "Basic implementation requirements for the client MIB V3 (3.2)."
    MODULE
        MANDATORY-GROUPS {
            clientGeneralGroupV2,
            clientIfGroupV3 }
    ::= { lumClientCompl 3 }

lumClientBasicComplV4 MODULE-COMPLIANCE
    STATUS      deprecated
    DESCRIPTION
        "Basic implementation requirements for the client MIB V4 (4.0)."
    MODULE
        MANDATORY-GROUPS {
            clientGeneralGroupV2,
            clientIfGroupV4 }
    ::= { lumClientCompl 4 }

lumClientBasicComplV5 MODULE-COMPLIANCE
    STATUS      deprecated
    DESCRIPTION
        "Basic implementation requirements for the client MIB V5 (4.1)."
    MODULE
        MANDATORY-GROUPS {
            clientGeneralGroupV2,
            clientIfGroupV5 }
    ::= { lumClientCompl 5 }

lumClientBasicComplV6 MODULE-COMPLIANCE
    STATUS      deprecated
    DESCRIPTION
        "Basic implementation requirements for the client MIB V6 (5.0)."
    MODULE
        MANDATORY-GROUPS {
            clientGeneralGroupV2,
            clientIfGroupV6 }
    ::= { lumClientCompl 6 }

lumClientBasicComplV7 MODULE-COMPLIANCE
    STATUS      deprecated
    DESCRIPTION
        "Basic implementation requirements for the client MIB V7 (7.0)."
    MODULE
        MANDATORY-GROUPS {
            clientGeneralGroupV2,
            clientIfGroupV7 }
    ::= { lumClientCompl 7 }

lumClientBasicComplV8 MODULE-COMPLIANCE
    STATUS      deprecated
    DESCRIPTION
        "Basic implementation requirements for the client MIB V8 (8.0)."
    MODULE
        MANDATORY-GROUPS {
            clientGeneralGroupV2,
            clientIfGroupV8 }
    ::= { lumClientCompl 8 }

lumClientBasicComplV9 MODULE-COMPLIANCE
    STATUS      deprecated
    DESCRIPTION
        "Basic implementation requirements for the client MIB v9 (10.0)."
    MODULE
        MANDATORY-GROUPS {
            clientGeneralGroupV3,
            clientIfGroupV8,
            clientVc4Group }
    ::= { lumClientCompl 9 }

lumClientBasicComplV10 MODULE-COMPLIANCE
    STATUS      deprecated
    DESCRIPTION
        "Basic implementation requirements for the client MIB v10 (11.0)."
    MODULE
        MANDATORY-GROUPS {
            clientGeneralGroupV3,
            clientIfGroupV9,
            clientVc4Group }
    ::= { lumClientCompl 10 }

lumClientBasicComplV11 MODULE-COMPLIANCE
    STATUS      deprecated
    DESCRIPTION
        "Basic implementation requirements for the client MIB v11 (12.0)."
    MODULE
        MANDATORY-GROUPS {
            clientGeneralGroupV3,
            clientIfGroupV10,
            clientVc4Group }
    ::= { lumClientCompl 11 }

lumClientBasicComplV12 MODULE-COMPLIANCE
    STATUS      deprecated
    DESCRIPTION
        "Basic implementation requirements for the client MIB v12 (13.0)."
    MODULE
        MANDATORY-GROUPS {
            clientGeneralGroupV3,
            clientIfGroupV11,
            clientVc4Group }
    ::= { lumClientCompl 12 }

lumClientBasicComplV13 MODULE-COMPLIANCE
    STATUS      deprecated
    DESCRIPTION
        "Basic implementation requirements for the client MIB v13 (15.0)."
    MODULE
        MANDATORY-GROUPS {
            clientGeneralGroupV3,
            clientIfGroupV12,
            clientVc4Group }
    ::= { lumClientCompl 13 }

lumClientBasicComplV14 MODULE-COMPLIANCE
    STATUS      deprecated
    DESCRIPTION
        "Basic implementation requirements for the client MIB v14 (16.0)."
    MODULE
        MANDATORY-GROUPS {
            clientGeneralGroupV3,
            clientIfGroupV13,
            clientVc4GroupV2 }
    ::= { lumClientCompl 14 }

lumClientBasicComplV15 MODULE-COMPLIANCE
    STATUS      deprecated
    DESCRIPTION
        "Basic implementation requirements for the client MIB v15 (16.1).
        16.1 was never released"
    MODULE
        MANDATORY-GROUPS {
            clientGeneralGroupV3,
            clientIfGroupV14,
            clientVc4GroupV2 }
    ::= { lumClientCompl 15 }

lumClientBasicComplV16 MODULE-COMPLIANCE
    STATUS      deprecated
    DESCRIPTION
        "Basic implementation requirements for the client MIB v16 (17.0)."
    MODULE
        MANDATORY-GROUPS {
            clientGeneralGroupV3,
            clientIfGroupV15,
            clientVc4GroupV2 }
    ::= { lumClientCompl 16 }

lumClientBasicComplV17 MODULE-COMPLIANCE
    STATUS      deprecated
    DESCRIPTION
        "Basic implementation requirements for the client MIB v17 (19.0)."
    MODULE
        MANDATORY-GROUPS {
            clientGeneralGroupV3,
            clientIfGroupV16,
            clientVc4GroupV2 }
    ::= { lumClientCompl 17 }

lumClientBasicComplV18 MODULE-COMPLIANCE
    STATUS      deprecated
    DESCRIPTION
        "Basic implementation requirements for the client MIB v18 (20.0)."
    MODULE
        MANDATORY-GROUPS {
            clientGeneralGroupV3,
            clientIfGroupV17,
            clientVc4GroupV2,
            clientLanesGroup }
    ::= { lumClientCompl 18 }

lumClientBasicComplV19 MODULE-COMPLIANCE
    STATUS      deprecated
    DESCRIPTION
        "Basic implementation requirements for the client MIB v18 (20.0)."
    MODULE
        MANDATORY-GROUPS {
            clientGeneralGroupV3,
            clientIfGroupV18,
            clientVc4GroupV2,
            clientLanesGroup }
    ::= { lumClientCompl 19 }

lumClientBasicComplV20 MODULE-COMPLIANCE
    STATUS      deprecated
    DESCRIPTION
        "Basic implementation requirements for the client MIB v20 (21.0)."
    MODULE
        MANDATORY-GROUPS {
            clientGeneralGroupV3,
            clientIfGroupV19,
            clientVc4GroupV2,
            clientLanesGroup }
    ::= { lumClientCompl 20 }

lumClientBasicComplV21 MODULE-COMPLIANCE
    STATUS      deprecated
    DESCRIPTION
        "Basic implementation requirements for the client MIB v21 (23.0)."
    MODULE
        MANDATORY-GROUPS {
            clientGeneralGroupV3,
            clientIfGroupV20,
            clientVc4GroupV2,
            clientLanesGroupV2 }
    ::= { lumClientCompl 21 }

lumClientBasicComplV22 MODULE-COMPLIANCE
    STATUS      deprecated
    DESCRIPTION
        "Basic implementation requirements for the client MIB v22 (23.1)."
    MODULE
        MANDATORY-GROUPS {
            clientGeneralGroupV3,
            clientIfGroupV21,
            clientVc4GroupV2,
            clientLanesGroupV2 }
    ::= { lumClientCompl 22 }

lumClientBasicComplV23 MODULE-COMPLIANCE
    STATUS      deprecated
    DESCRIPTION
        "Basic implementation requirements for the client MIB v23 (26.1)."
    MODULE
        MANDATORY-GROUPS {
            clientGeneralGroupV3,
            clientIfGroupV22,
            clientVc4GroupV2,
            clientLanesGroupV3 }
    ::= { lumClientCompl 23 }


lumClientBasicComplV24 MODULE-COMPLIANCE
    STATUS      deprecated
    DESCRIPTION
        "Basic implementation requirements for the client MIB v24 (27)."
    MODULE
        MANDATORY-GROUPS {
            clientGeneralGroupV3,
            clientIfGroupV22,
            clientVc4GroupV2,
            clientLanesGroupV4,
            clientMpoLanesGroupV1 }
    ::= { lumClientCompl 24 }

lumClientBasicComplV25 MODULE-COMPLIANCE
    STATUS      deprecated
    DESCRIPTION
        "Basic implementation requirements for the client MIB v25 (28.1)."
    MODULE
        MANDATORY-GROUPS {
            clientGeneralGroupV3,
            clientIfGroupV22,
            clientVc4GroupV2,
            clientLanesGroupV5,
            clientMpoLanesGroupV1 }
    ::= { lumClientCompl 25 }

lumClientBasicComplV26 MODULE-COMPLIANCE
    STATUS      deprecated
    DESCRIPTION
        "Basic implementation requirements for the client MIB v26 (28.0)."
    MODULE
        MANDATORY-GROUPS {
            clientGeneralGroupV3,
            clientIfGroupV23,
            clientVc4GroupV2,
            clientLanesGroupV5,
            clientMpoLanesGroupV1 }
    ::= { lumClientCompl 26 }

lumClientBasicComplV27 MODULE-COMPLIANCE
    STATUS      deprecated
    DESCRIPTION
        "Basic implementation requirements for the client MIB v27 (29.0)."
    MODULE
        MANDATORY-GROUPS {
            clientGeneralGroupV3,
            clientIfGroupV24,
            clientVc4GroupV2,
            clientLanesGroupV5,
            clientMpoLanesGroupV1 }
    ::= { lumClientCompl 27 }

lumClientBasicComplV28 MODULE-COMPLIANCE
    STATUS      deprecated
    DESCRIPTION
        "Basic implementation requirements for the client MIB v28 (30.0)."
    MODULE
        MANDATORY-GROUPS {
            clientGeneralGroupV3,
            clientIfGroupV25,
            clientVc4GroupV2,
            clientLanesGroupV5,
            clientMpoLanesGroupV1 }
    ::= { lumClientCompl 28 }

lumClientBasicComplV29 MODULE-COMPLIANCE
    STATUS      deprecated
    DESCRIPTION
        "Basic implementation requirements for the client MIB v29 (30.1)."
    MODULE
        MANDATORY-GROUPS {
            clientGeneralGroupV3,
            clientIfGroupV26,
            clientVc4GroupV2,
            clientLanesGroupV5,
            clientMpoLanesGroupV1 }
    ::= { lumClientCompl 29 }

lumClientBasicComplV30 MODULE-COMPLIANCE
    STATUS      current
    DESCRIPTION
        "Basic implementation requirements for the client MIB v30 (31.1)."
    MODULE
        MANDATORY-GROUPS {
            clientGeneralGroupV3,
            clientIfGroupV27,
            clientVc4GroupV2,
            clientLanesGroupV5,
            clientMpoLanesGroupV1 }
    ::= { lumClientCompl 30 }

-- ----------------------------------------------------
-- Minimal object and event groups
-- ----------------------------------------------------

clientIfMinimalGroupV1 OBJECT-GROUP
    OBJECTS {
        clientIfIndex,
        clientIfName,
        clientIfDescr,
        clientIfSubrack,
        clientIfSlot,
        clientIfTxPort,
        clientIfRxPort,
        clientIfInvPhysIndexOrZero,
        clientIfEntityId,
        clientIfAdminStatus,
        clientIfOperStatus,
        clientIfTxSignalStatus,
        clientIfFormat,
        clientIfLossOfSignal,
        clientIfLossOfFrame,
        clientIfBitrateMismatch,
        clientIfAuAlarmIndicationSignalW2C,
        clientIfTransmitterFailed,
        clientIfTrxCodeMismatch,
        clientIfTrxBitrateUnavailable,
        clientIfTrxMissing,
        clientIfReceivedPowerHigh,
        clientIfReceivedPowerLow,
        clientIfLinkDown,
        clientIfLossOfSync,
        clientIfRxSignalStatus }
    STATUS      deprecated
    DESCRIPTION
        "The minimal interface objects."
    ::= { lumClientMinimalGroups 1 }

clientIfMinimalGroupV2 OBJECT-GROUP
    OBJECTS {
        clientIfIndex,
        clientIfName,
        clientIfDescr,
        clientIfSubrack,
        clientIfSlot,
        clientIfTxPort,
        clientIfRxPort,
        clientIfInvPhysIndexOrZero,
        clientIfEntityId,
        clientIfAdminStatus,
        clientIfOperStatus,
        clientIfTxSignalStatus,
        clientIfFormat,
        clientIfLossOfSignal,
        clientIfLossOfFrame,
        clientIfBitrateMismatch,
        clientIfAuAlarmIndicationSignalW2C,
        clientIfTransmitterFailed,
        clientIfTrxCodeMismatch,
        clientIfTrxBitrateUnavailable,
        clientIfTrxMissing,
        clientIfReceivedPowerHigh,
        clientIfReceivedPowerLow,
        clientIfLinkDown,
        clientIfLossOfSync,
        clientIfRxSignalStatus,
        clientIfTrxFailed,
        clientIfDisabled,
        clientIfLoopback,
        clientIfClientSignalFailed,
        clientIfAuLossOfPointer,
        clientIfGfpLossOfFrame
        }
    STATUS      current
    DESCRIPTION
        "The minimal interface objects."
    ::= { lumClientMinimalGroups 2 }


-- ----------------------------------------------------
-- Minimal Compliance
-- ----------------------------------------------------

lumClientMinimalComplV1 MODULE-COMPLIANCE
    STATUS      deprecated
    DESCRIPTION
        "Minimal implementation requirements for the client MIB v1."
    MODULE
        MANDATORY-GROUPS {
            clientGeneralGroupV2,
            clientIfMinimalGroupV1 }
    ::= { lumClientMinimalCompl 1 }

lumClientMinimalComplV2 MODULE-COMPLIANCE
    STATUS      current
    DESCRIPTION
        "Minimal implementation requirements for the client MIB v2."
    MODULE
        MANDATORY-GROUPS {
            clientGeneralGroupV2,
            clientIfMinimalGroupV2 }
    ::= { lumClientMinimalCompl 2 }

END
