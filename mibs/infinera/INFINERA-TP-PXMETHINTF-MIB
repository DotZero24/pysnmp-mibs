-- *****************************************************************
-- INFINERA-TP-PXMETHINTF-MIB
--
-- Mithun Murthy/ Divyank Rastogi
--
--
-- Copyright (c) 2008-2012 by Infinera Inc.
-- All rights reserved.
-- ****************************************************************

INFINERA-TP-PXMETHINTF-MIB DEFINITIONS ::= BEGIN

IMPORTS
    MODULE-IDENTITY, OBJECT-TYPE, Integer32     FROM SNMPv2-SMI
    MODULE-COMPLIANCE, OBJECT-GROUP             FROM SNMPv2-CONF
    DisplayString                               FROM SNMPv2-TC
    ifIndex                                     FROM IF-MIB
	FloatTenths, FloatHundredths,
	InfnPXMInterfaceType, InfnEnableDisableType,
    InfnLoopbackBehavior,
	InfnAcceptableFrameType						FROM INFINERA-TC-MIB
    terminationPoint                            FROM INFINERA-REG-MIB;

pxmEthIntfMIB MODULE-IDENTITY
    LAST-UPDATED  "201605200000Z"
    ORGANIZATION
        "Infinera"
    CONTACT-INFO
        "Infinera
                1322 Bordeaux Drive
                Sunnyvale, CA - 94089

                Contact : Technical Support
                Email   : support@infinera.com
                Phone   : 1-877-INF-5288"
    DESCRIPTION
        " "

    REVISION  "201605200000Z"
    DESCRIPTION
        " "
::= { terminationPoint 76 }


pxmEthIntfConformance   OBJECT IDENTIFIER ::= { pxmEthIntfMIB 3 }
pxmEthIntfCompliances   OBJECT IDENTIFIER ::= { pxmEthIntfConformance 1 }
pxmEthIntfGroups        OBJECT IDENTIFIER ::= { pxmEthIntfConformance 2 }

pxmEthIntfTable  OBJECT-TYPE
    SYNTAX SEQUENCE OF PxmEthIntfEntry
    MAX-ACCESS not-accessible
    STATUS     current
    DESCRIPTION
        "A list of PxmEthIntf entries. Each entry is uniquely identified by
                the value of ifIndex."
    ::= { pxmEthIntfMIB 1 }

pxmEthIntfEntry  OBJECT-TYPE
    SYNTAX     PxmEthIntfEntry
    MAX-ACCESS not-accessible
    STATUS     current
    DESCRIPTION
        "A PxmEthIntf entry containing information pertaining to
                Infinera PxmEthIntf interfaces. This table is a subclass of IfCommon.
                Entries will exist in this table only for interfaces of type PxmEthIntf."
    INDEX { ifIndex }
    ::= { pxmEthIntfTable 1 }

PxmEthIntfEntry  ::= SEQUENCE {
    pxmEthIntfMTUSize               Integer32,
    pxmEthIntfInterfaceType         InfnPXMInterfaceType,
    pxmEthIntfOuterTPID             Integer32,
    pxmEthIntfInnerTPID             Integer32,
    pxmEthIntfDefaultVLANID         Integer32,
    pxmEthIntfDefaultPriority       Integer32,
    pxmEthIntfIngressTrafficClass   Integer32,
    pxmEthIntfFacTestSignalGen      InfnEnableDisableType,
    pxmEthIntfFacTestSignalMon      InfnEnableDisableType,
    pxmEthIntfTerminalTestSignalGen InfnEnableDisableType,
    pxmEthIntfTerminalTestSignalMon InfnEnableDisableType,
    pxmEthIntfInterfaceRate         Integer32,
    pxmEthIntfAcceptableFrameType   InfnAcceptableFrameType,
    pxmEthIntfOverBookingFactor     FloatTenths,
    pxmEthIntfMaxReservableBW		FloatHundredths,
    pxmEthIntfAvailableBW           FloatHundredths,
    pxmEthIntfLoopbackBehavior      InfnLoopbackBehavior,
    pxmEthIntfMacAddress            DisplayString,
	pxmEthIntfCSFAsTDATrigger		InfnEnableDisableType
}

 pxmEthIntfMTUSize OBJECT-TYPE
    SYNTAX     Integer32
    MAX-ACCESS read-only
    STATUS     current
    DESCRIPTION
        ""
    ::= { pxmEthIntfEntry 1 }

 pxmEthIntfInterfaceType   OBJECT-TYPE
    SYNTAX    InfnPXMInterfaceType
    MAX-ACCESS read-write
    STATUS     current
    DESCRIPTION
        ""
    ::= { pxmEthIntfEntry 2 }

pxmEthIntfOuterTPID   OBJECT-TYPE
    SYNTAX     Integer32
    MAX-ACCESS read-write
    STATUS     current
    DESCRIPTION
        ""
    ::= { pxmEthIntfEntry 3 }

pxmEthIntfInnerTPID   OBJECT-TYPE
    SYNTAX     Integer32
    MAX-ACCESS read-write
    STATUS     current
    DESCRIPTION
        ""
    ::= { pxmEthIntfEntry 4 }

pxmEthIntfDefaultVLANID   OBJECT-TYPE
    SYNTAX     Integer32
    MAX-ACCESS read-write
    STATUS     current
    DESCRIPTION
        ""
    ::= { pxmEthIntfEntry 5 }

pxmEthIntfDefaultPriority   OBJECT-TYPE
    SYNTAX     Integer32
    MAX-ACCESS read-write
    STATUS     current
    DESCRIPTION
        ""
    ::= { pxmEthIntfEntry 6 }

pxmEthIntfIngressTrafficClass   OBJECT-TYPE
    SYNTAX     Integer32
    MAX-ACCESS read-write
    STATUS     current
    DESCRIPTION
        ""
    ::= { pxmEthIntfEntry 7 }

pxmEthIntfFacTestSignalGen   OBJECT-TYPE
    SYNTAX     InfnEnableDisableType
    MAX-ACCESS read-write
    STATUS     current
    DESCRIPTION
        ""
    ::= { pxmEthIntfEntry 8 }

pxmEthIntfFacTestSignalMon   OBJECT-TYPE
    SYNTAX     InfnEnableDisableType
    MAX-ACCESS read-write
    STATUS     current
    DESCRIPTION
        ""
    ::= { pxmEthIntfEntry 9 }

pxmEthIntfTerminalTestSignalGen    OBJECT-TYPE
    SYNTAX     InfnEnableDisableType
    MAX-ACCESS read-write
    STATUS     current
    DESCRIPTION
        ""
    ::= { pxmEthIntfEntry 10 }

pxmEthIntfTerminalTestSignalMon  OBJECT-TYPE
    SYNTAX     InfnEnableDisableType
    MAX-ACCESS read-write
    STATUS     current
    DESCRIPTION
        ""
    ::= { pxmEthIntfEntry 11 }

pxmEthIntfInterfaceRate   OBJECT-TYPE
    SYNTAX     Integer32
    MAX-ACCESS read-only
    STATUS     current
    DESCRIPTION
        ""
    ::= { pxmEthIntfEntry 12 }

pxmEthIntfAcceptableFrameType   OBJECT-TYPE
    SYNTAX     InfnAcceptableFrameType
    MAX-ACCESS read-write
    STATUS     current
    DESCRIPTION
        ""
    ::= { pxmEthIntfEntry 13 }

pxmEthIntfOverBookingFactor		OBJECT-TYPE
    SYNTAX     FloatTenths
    MAX-ACCESS read-write
    STATUS     current
    DESCRIPTION
        ""
    ::= { pxmEthIntfEntry 14 }

pxmEthIntfMaxReservableBW   OBJECT-TYPE
    SYNTAX     FloatHundredths
    MAX-ACCESS read-only
    STATUS     current
    DESCRIPTION
        ""
    ::= { pxmEthIntfEntry 15 }

pxmEthIntfAvailableBW   OBJECT-TYPE
    SYNTAX     FloatHundredths
    MAX-ACCESS read-only
    STATUS     current
    DESCRIPTION
        ""
    ::= { pxmEthIntfEntry 16 }

pxmEthIntfLoopbackBehavior   OBJECT-TYPE
    SYNTAX     InfnLoopbackBehavior
    MAX-ACCESS read-write
    STATUS     current
    DESCRIPTION
        ""
    ::= { pxmEthIntfEntry 17 }

pxmEthIntfMacAddress   OBJECT-TYPE
    SYNTAX     DisplayString
    MAX-ACCESS read-only
    STATUS     current
    DESCRIPTION
        ""
    ::= { pxmEthIntfEntry 18 }

pxmEthIntfCSFAsTDATrigger	OBJECT-TYPE
    SYNTAX     InfnEnableDisableType
    MAX-ACCESS read-write
    STATUS     current
    DESCRIPTION
        ""
    ::= { pxmEthIntfEntry 19 }


pxmEthIntfCompliance  MODULE-COMPLIANCE
    STATUS     current
    DESCRIPTION
        "Describes the requirements for conformance to the TRIBPTP-MIB"
    MODULE
        MANDATORY-GROUPS { pxmEthIntfGroup }
    ::= { pxmEthIntfCompliances 1 }

pxmEthIntfGroup  OBJECT-GROUP
    OBJECTS {
        pxmEthIntfMTUSize,
        pxmEthIntfInterfaceType,
        pxmEthIntfOuterTPID,
        pxmEthIntfInnerTPID,
        pxmEthIntfDefaultVLANID,
        pxmEthIntfDefaultPriority,
        pxmEthIntfIngressTrafficClass,
        pxmEthIntfFacTestSignalGen,
        pxmEthIntfFacTestSignalMon,
        pxmEthIntfTerminalTestSignalGen,
        pxmEthIntfTerminalTestSignalMon,
        pxmEthIntfInterfaceRate,
        pxmEthIntfAcceptableFrameType,
        pxmEthIntfOverBookingFactor,
        pxmEthIntfMaxReservableBW,
        pxmEthIntfAvailableBW,
        pxmEthIntfLoopbackBehavior,
        pxmEthIntfMacAddress,
		pxmEthIntfCSFAsTDATrigger
    }
    STATUS     current
    DESCRIPTION
        " A collection of objects for managing pxmEthIntf interfaces."
    ::= { pxmEthIntfGroups 1 }
END
