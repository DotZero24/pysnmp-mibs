-- *****************************************************************
-- INFINERA-TP-DTPCTP-MIB
--
-- October 2008, Sharfuddin Syed / Narendra Gupta
--
--
-- Copyright (c) 2008-2012 by Infinera Inc.
-- All rights reserved.
-- ****************************************************************

INFINERA-TP-DTPCTP-MIB DEFINITIONS ::= BEGIN

IMPORTS
    MODULE-IDENTITY, OBJECT-TYPE,
    Integer32, Counter64                        FROM SNMPv2-SMI
    MODULE-COMPLIANCE, OBJECT-GROUP             FROM SNMPv2-CONF
    DisplayString, TruthValue                   FROM SNMPv2-TC
    ifIndex                                     FROM IF-MIB
    InfnServiceType                             FROM INFINERA-TC-MIB
    terminationPoint                            FROM INFINERA-REG-MIB;


dtpCtpMIB MODULE-IDENTITY
    LAST-UPDATED  "200810200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "200810200000Z"
    DESCRIPTION
        "First Version"
    ::= { terminationPoint 7 }



dtpCtpTable OBJECT-TYPE
    SYNTAX      SEQUENCE OF DtpCtpEntry
    MAX-ACCESS  not-accessible
    STATUS      current
    DESCRIPTION
        "A list of DtpCtp entries. Each entry is uniquely identified by the value of ifIndex."
    ::= { dtpCtpMIB 1 }

dtpCtpEntry  OBJECT-TYPE
    SYNTAX      DtpCtpEntry
    MAX-ACCESS  not-accessible
    STATUS      current
    DESCRIPTION
        "A DtpCtp entry containing information pertaining to Infinera DtpCtp interfaces. This table is a subclass
        of IfCommon. Entries will exist in this table only for interfaces of type DtpCtp."
    INDEX { ifIndex }
    ::= { dtpCtpTable 1 }


DtpCtpEntry  ::= SEQUENCE {
    dtpCtpCfgProtSt                        INTEGER,
    dtpCtpProtMod                          INTEGER,
    dtpCtpSwReason                         INTEGER,
    dtpCtpSupportingTP                     DisplayString,
    dtpCtpExpectedPayload                  InfnServiceType,
    dtpCtpSupportingCircuitIdList          DisplayString,
    dtpCtpDetectedPayload                  InfnServiceType,
    dtpCtpDataRate                         INTEGER,
    dtpCtpLoopback                         INTEGER,
    dtpCtpInsertDtpTti                     TruthValue,
    dtpCtpTtiAlarmReporting                INTEGER,
    dtpCtpTxTtiAlarmReporting              INTEGER,
    dtpCtpTxDtpTti                         DisplayString,
    dtpCtpRxDtpTtiWrite                    DisplayString,
    dtpCtpExpectedDtpTti                   DisplayString,
    dtpCtpExpectedTxDtpTti                 DisplayString,
    dtpCtpRxDtpTti                         DisplayString,
    dtpCtpRecvTxDtpTti                     DisplayString,
    dtpCtpDtpRxCv15MinutesTce              Counter64,
    dtpCtpDtpRxEs15MinutesTce              Integer32,
    dtpCtpDtpRxSes15MinutesTce             Integer32,
    dtpCtpDtpRxUas15MinutesTce             Integer32,
    dtpCtpDtpRxCvDayTce                    Counter64,
    dtpCtpDtpRxEsDayTce                    Integer32,
    dtpCtpDtpRxSesDayTce                   Integer32,
    dtpCtpDtpRxUasDayTce                   Integer32,
    dtpCtpDtpTxCv15MinutesTce              Counter64,
    dtpCtpDtpTxEs15MinutesTce              Integer32,
    dtpCtpDtpTxSes15MinutesTce             Integer32,
    dtpCtpDtpTxUas15MinutesTce             Integer32,
    dtpCtpDtpTxCvDayTce                    Counter64,
    dtpCtpDtpTxEsDayTce                    Integer32,
    dtpCtpDtpTxSesDayTce                   Integer32,
    dtpCtpDtpTxUasDayTce                   Integer32,
    dtpCtpDtpRxCv15MinutesTceReporting     TruthValue,
    dtpCtpDtpRxEs15MinutesTceReporting     TruthValue,
    dtpCtpDtpRxSes15MinutesTceReporting    TruthValue,
    dtpCtpDtpRxUas15MinutesTceReporting    TruthValue,
    dtpCtpDtpRxCvDayTceReporting           TruthValue,
    dtpCtpDtpRxEsDayTceReporting           TruthValue,
    dtpCtpDtpRxSesDayTceReporting          TruthValue,
    dtpCtpDtpRxUasDayTceReporting          TruthValue,
    dtpCtpDtpTxCv15MinutesTceReporting     TruthValue,
    dtpCtpDtpTxEs15MinutesTceReporting     TruthValue,
    dtpCtpDtpTxSes15MinutesTceReporting    TruthValue,
    dtpCtpDtpTxUas15MinutesTceReporting    TruthValue,
    dtpCtpDtpTxCvDayTceReporting           TruthValue,
    dtpCtpDtpTxEsDayTceReporting           TruthValue,
    dtpCtpDtpTxSesDayTceReporting          TruthValue,
    dtpCtpDtpTxUasDayTceReporting          TruthValue,
    dtpCtpPrbsGenerationMode               INTEGER,
    dtpCtpPrbsMonitoringMode               INTEGER,
    dtpCtpNumDtpSubCh                      Integer32,
    dtpCtpMuxMode                          TruthValue,
    dtpCtpPmHistStatsEnable                INTEGER,
    dtpCtpCrossConnectType                 INTEGER
}

dtpCtpCfgProtSt OBJECT-TYPE
    SYNTAX  INTEGER {
        unknown(1),
        wrk(2),
        prot(3),
        relb(4),
        pU(5)
    }
    MAX-ACCESS  read-only
    STATUS      current
    DESCRIPTION "The preferred state of the protection unit."
    DEFVAL      { unknown }
    ::= { dtpCtpEntry  1 }


dtpCtpProtMod OBJECT-TYPE
    SYNTAX  INTEGER {
        none(1),
        dtDSNCP(2),
        stDSNCP(3)
    }
    MAX-ACCESS  read-only
    STATUS      current
    DESCRIPTION "Protection type viz STDSNCP, DTSNCP or None."
    DEFVAL      { none }
    ::= { dtpCtpEntry  2 }


dtpCtpSwReason OBJECT-TYPE
    SYNTAX  INTEGER {
        mSwP(1),
        mSwW(2),
        wLck(3),
        pLck(4),
        auto(5),
        none(6),
        revert(7),
        admLck(8),
        unProv(9),
        eqFlt(10),
        liFlt(11),
        liSF(12),
        clRxFlt(13),
        clTxFlt(14),
        sysLof(15)
    }
    MAX-ACCESS  read-only
    STATUS      current
    DESCRIPTION "Sw Reason"
    DEFVAL      { none }
    ::= { dtpCtpEntry  3 }


dtpCtpSupportingTP OBJECT-TYPE
    SYNTAX      DisplayString
    MAX-ACCESS  read-write
    STATUS      current
    DESCRIPTION "The corresponding AID of that particular DTPCTP."
    ::= { dtpCtpEntry  4 }


dtpCtpExpectedPayload OBJECT-TYPE
    SYNTAX  InfnServiceType
    MAX-ACCESS  read-only
    STATUS      current
    DESCRIPTION "Payload expected at this termination point."
    ::= { dtpCtpEntry  5 }


dtpCtpSupportingCircuitIdList OBJECT-TYPE
    SYNTAX      DisplayString
    MAX-ACCESS  read-only
    STATUS      current
    DESCRIPTION
        "An unordered list of the CircuitId's associated with this groupTp object.
        This string contains the string representation of each supporting
        CircuitId, separated by a ';' (semicolon) if there is more than one."
    ::= { dtpCtpEntry  6 }


dtpCtpDetectedPayload OBJECT-TYPE
    SYNTAX  InfnServiceType
    MAX-ACCESS  read-only
    STATUS      current
    DESCRIPTION "Payload detected at this termination point."
    ::= { dtpCtpEntry  7 }


dtpCtpDataRate OBJECT-TYPE
    SYNTAX  INTEGER {
        rateNotSet(1),
        rate10GigAny(2),
        rate2g500mAny(3),
        rate1GogAny(4),
        rate40GigAny(5)
    }
    MAX-ACCESS  read-only
    STATUS      current
    DESCRIPTION "Applicable to line DTPCTP and indicates the line data rate namley, 2.5G or 10G."
    ::= { dtpCtpEntry  8 }


dtpCtpLoopback OBJECT-TYPE
    SYNTAX  INTEGER {
        none(1),
        terminal(2),
        facility(3)
    }
    MAX-ACCESS  read-write
    STATUS      current
    DESCRIPTION "Flag to enable the loopback."
    DEFVAL      { none }
    ::= { dtpCtpEntry  9 }


dtpCtpInsertDtpTti OBJECT-TYPE
    SYNTAX      TruthValue
    MAX-ACCESS  read-write
    STATUS      current
    DESCRIPTION "Flag that enables the TTI string to be entered and monitored at the far end."
    DEFVAL      { false }
    ::= { dtpCtpEntry  10 }


dtpCtpTtiAlarmReporting OBJECT-TYPE
    SYNTAX  INTEGER {
        disabled(1),
        enabled(2)
    }
    MAX-ACCESS  read-write
    STATUS      current
    DESCRIPTION "Flag that indicates whether TTI alarm should be reported or not."
    DEFVAL      { disabled }
    ::= { dtpCtpEntry  11 }


dtpCtpTxTtiAlarmReporting OBJECT-TYPE
    SYNTAX  INTEGER {
        disabled(1),
        enabled(2)
    }
    MAX-ACCESS  read-write
    STATUS      current
    DESCRIPTION "Flag that indicates whether TTI alarm will be reported or not."
    DEFVAL      { disabled }
    ::= { dtpCtpEntry  12 }


dtpCtpTxDtpTti OBJECT-TYPE
    SYNTAX      DisplayString
    MAX-ACCESS  read-write
    STATUS      current
    DESCRIPTION "The transmitted Dtp trail trace identifier."
    ::= { dtpCtpEntry  13 }


dtpCtpRxDtpTtiWrite OBJECT-TYPE
    SYNTAX      DisplayString
    MAX-ACCESS  read-write
    STATUS      current
    DESCRIPTION "Applicable only for DTPCTP on GT-TAM to transmit the TTI in receive direction."
    ::= { dtpCtpEntry  14 }


dtpCtpExpectedDtpTti OBJECT-TYPE
    SYNTAX      DisplayString
    MAX-ACCESS  read-write
    STATUS      current
    DESCRIPTION "The expected Dtp trail trace identifier."
    ::= { dtpCtpEntry  15 }


dtpCtpExpectedTxDtpTti OBJECT-TYPE
    SYNTAX      DisplayString
    MAX-ACCESS  read-write
    STATUS      current
    DESCRIPTION "The Expected Tx TTI. If this is not equal to the zero-length string and it doesn't match the recived TTI, an alarm will be raised."
    ::= { dtpCtpEntry  16 }


dtpCtpRxDtpTti OBJECT-TYPE
    SYNTAX      DisplayString
    MAX-ACCESS  read-only
    STATUS      current
    DESCRIPTION "The received Dtp trail trace identifier."
    ::= { dtpCtpEntry  17 }


dtpCtpRecvTxDtpTti OBJECT-TYPE
    SYNTAX      DisplayString
    MAX-ACCESS  read-only
    STATUS      current
    DESCRIPTION "The received transmit Dtp trail trace identifier."
    ::= { dtpCtpEntry  18 }


dtpCtpDtpRxCv15MinutesTce OBJECT-TYPE
    SYNTAX      Counter64
    MAX-ACCESS  read-write
    STATUS      current
    DESCRIPTION "Count of bit errors detected at the DTF path layer in 15 minutes."
    ::= { dtpCtpEntry  19 }


dtpCtpDtpRxEs15MinutesTce OBJECT-TYPE
    SYNTAX      Integer32
    MAX-ACCESS  read-write
    STATUS      current
    DESCRIPTION "Count of the number of seconds during which at least one DTF Path layer BIP error was detected or an AIS-P defect was present in 15 minutes."
    DEFVAL      { 120 }
    ::= { dtpCtpEntry  20 }


dtpCtpDtpRxSes15MinutesTce OBJECT-TYPE
    SYNTAX      Integer32
    MAX-ACCESS  read-write
    STATUS      current
    DESCRIPTION "Count of the seconds during which K (= 2,400 as specified in GR-253-CORE Issue 3 specification) or more DTF Path layer BIP errors were detected or an AIS-P defect was present in 15 minutes."
    DEFVAL      { 3 }
    ::= { dtpCtpEntry  21 }


dtpCtpDtpRxUas15MinutesTce OBJECT-TYPE
    SYNTAX      Integer32
    MAX-ACCESS  read-write
    STATUS      current
    DESCRIPTION "Count of the seconds during which the DTF Path considered unavailable. A DTF Path becomes unavailable at the onset of 10 consecutive seconds that qualify as DTF-DLMSES-P, and continues to be unavailable until the onset of 10 consecutive seconds that do not qualify as DTFDLM-SES-P in 15 minutes."
    DEFVAL      { 10 }
    ::= { dtpCtpEntry  22 }


dtpCtpDtpRxCvDayTce OBJECT-TYPE
    SYNTAX      Counter64
    MAX-ACCESS  read-write
    STATUS      current
    DESCRIPTION "Count of bit errors detected at the DTF path layer in 24 hours"
    ::= { dtpCtpEntry  23 }


dtpCtpDtpRxEsDayTce OBJECT-TYPE
    SYNTAX      Integer32
    MAX-ACCESS  read-write
    STATUS      current
    DESCRIPTION "Count of the number of seconds during which at least one DTF Path layer BIP error was detected or an AIS-P defect was present in 24 hours."
    DEFVAL      { 1200 }
    ::= { dtpCtpEntry  24 }


dtpCtpDtpRxSesDayTce OBJECT-TYPE
    SYNTAX      Integer32
    MAX-ACCESS  read-write
    STATUS      current
    DESCRIPTION "Count of the seconds during which K (= 2,400 as specified in GR-253-CORE Issue 3 specification) or more DTF Path layer BIP errors were detected or an AIS-P defect was present in 24 hours."
    DEFVAL      { 7 }
    ::= { dtpCtpEntry  25 }


dtpCtpDtpRxUasDayTce OBJECT-TYPE
    SYNTAX      Integer32
    MAX-ACCESS  read-write
    STATUS      current
    DESCRIPTION "Count of the seconds during which the DTF Path considered unavailable. A DTF Path becomes unavailable at the onset of 10 consecutive seconds that qualify as DTF-DLMSES-P, and continues to be unavailable until the onset of 10 consecutive seconds that do not qualify as DTFDLM-SES-P in 24 hours."
    DEFVAL      { 10 }
    ::= { dtpCtpEntry  26 }


dtpCtpDtpTxCv15MinutesTce OBJECT-TYPE
    SYNTAX      Counter64
    MAX-ACCESS  read-write
    STATUS      current
    DESCRIPTION "Count of bit errors detected at the DTF path layer in 15 minutes."
    ::= { dtpCtpEntry  27 }


dtpCtpDtpTxEs15MinutesTce OBJECT-TYPE
    SYNTAX      Integer32
    MAX-ACCESS  read-write
    STATUS      current
    DESCRIPTION "Count of the number of seconds during which (at any point during the second) at least one DTF Path layer BIP error was detected or an AIS-P defect was present in 15 minutes."
    DEFVAL      { 120 }
    ::= { dtpCtpEntry  28 }


dtpCtpDtpTxSes15MinutesTce OBJECT-TYPE
    SYNTAX      Integer32
    MAX-ACCESS  read-write
    STATUS      current
    DESCRIPTION "Count of the seconds during which K (= 2,400 as specified in GR-253-CORE Issue 3 specification)or more DTF Path layer BIP errors were detected or an AIS-P defect was present in 15 minutes."
    DEFVAL      { 3 }
    ::= { dtpCtpEntry  29 }


dtpCtpDtpTxUas15MinutesTce OBJECT-TYPE
    SYNTAX      Integer32
    MAX-ACCESS  read-write
    STATUS      current
    DESCRIPTION "Count of the seconds during which the DTF Path considered unavailable. A DTF Path becomes unavailable at the onset of 10 consecutive seconds that qualify as DTF-DLMSES-P, and continues to be unavailable until the onset of 10 consecutive seconds that do not qualify as DTFDLM-SES-P in 15 minutes."
    DEFVAL      { 10 }
    ::= { dtpCtpEntry  30 }


dtpCtpDtpTxCvDayTce OBJECT-TYPE
    SYNTAX      Counter64
    MAX-ACCESS  read-write
    STATUS      current
    DESCRIPTION "Count of bit errors detected at the DTF path layer in 24 hours."
    ::= { dtpCtpEntry  31 }


dtpCtpDtpTxEsDayTce OBJECT-TYPE
    SYNTAX      Integer32
    MAX-ACCESS  read-write
    STATUS      current
    DESCRIPTION "Count of the number of seconds during which (at any point during the second) at least one DTF Path layer BIP error was detected or an AIS-P defect was present in 24 hours."
    DEFVAL      { 1200 }
    ::= { dtpCtpEntry  32 }


dtpCtpDtpTxSesDayTce OBJECT-TYPE
    SYNTAX      Integer32
    MAX-ACCESS  read-write
    STATUS      current
    DESCRIPTION "Count of the seconds during which K (= 2,400 as specified in GR-253-CORE Issue 3 specification)or more DTF Path layer BIP errors were detected or an AIS-P defect was present in 24 hours."
    DEFVAL      { 7 }
    ::= { dtpCtpEntry  33 }


dtpCtpDtpTxUasDayTce OBJECT-TYPE
    SYNTAX      Integer32
    MAX-ACCESS  read-write
    STATUS      current
    DESCRIPTION "Count of the seconds during which the DTF Path considered unavailable. A DTF Path becomes unavailable at the onset of 10 consecutive seconds that qualify as DTF-DLMSES-P, and continues to be unavailable until the onset of 10 consecutive seconds that do not qualify as DTFDLM-SES-P in 24 hours."
    DEFVAL      { 10 }
    ::= { dtpCtpEntry  34 }


dtpCtpDtpRxCv15MinutesTceReporting OBJECT-TYPE
    SYNTAX      TruthValue
    MAX-ACCESS  read-write
    STATUS      current
    DESCRIPTION "Flag that enables DtpRxCv15MinutesTce threshold crossing."
    DEFVAL      { false }
    ::= { dtpCtpEntry  35 }


dtpCtpDtpRxEs15MinutesTceReporting OBJECT-TYPE
    SYNTAX      TruthValue
    MAX-ACCESS  read-write
    STATUS      current
    DESCRIPTION "Flag that enables the reporting of DtpRxEs15MinutesTce crossing."
    DEFVAL      { false }
    ::= { dtpCtpEntry  36 }


dtpCtpDtpRxSes15MinutesTceReporting OBJECT-TYPE
    SYNTAX      TruthValue
    MAX-ACCESS  read-write
    STATUS      current
    DESCRIPTION "Flag that enables the reporting of DtpRxSes15MinutesTce crossing."
    DEFVAL      { false }
    ::= { dtpCtpEntry  37 }


dtpCtpDtpRxUas15MinutesTceReporting OBJECT-TYPE
    SYNTAX      TruthValue
    MAX-ACCESS  read-write
    STATUS      current
    DESCRIPTION "Flag that enables the reporting of DtpRxUas15MinutesTce crossing."
    DEFVAL      { false }
    ::= { dtpCtpEntry  38 }


dtpCtpDtpRxCvDayTceReporting OBJECT-TYPE
    SYNTAX      TruthValue
    MAX-ACCESS  read-write
    STATUS      current
    DESCRIPTION "Flag that enables DtpRxCvDayTce threshold crossing."
    DEFVAL      { false }
    ::= { dtpCtpEntry  39 }


dtpCtpDtpRxEsDayTceReporting OBJECT-TYPE
    SYNTAX      TruthValue
    MAX-ACCESS  read-write
    STATUS      current
    DESCRIPTION "Flag that enables the reporting of DtpEsDayTce crossing."
    DEFVAL      { false }
    ::= { dtpCtpEntry  40 }


dtpCtpDtpRxSesDayTceReporting OBJECT-TYPE
    SYNTAX      TruthValue
    MAX-ACCESS  read-write
    STATUS      current
    DESCRIPTION "Flag that enables the reporting of DtpRxSesDayTce crossing."
    DEFVAL      { false }
    ::= { dtpCtpEntry  41 }


dtpCtpDtpRxUasDayTceReporting OBJECT-TYPE
    SYNTAX      TruthValue
    MAX-ACCESS  read-write
    STATUS      current
    DESCRIPTION "Flag that enables the reporting of DtpRxUasDayTce crossing."
    DEFVAL      { false }
    ::= { dtpCtpEntry  42 }


dtpCtpDtpTxCv15MinutesTceReporting OBJECT-TYPE
    SYNTAX      TruthValue
    MAX-ACCESS  read-write
    STATUS      current
    DESCRIPTION "Flag that enables the reporting of DtpTxCv15MinutesTce crossing."
    DEFVAL      { false }
    ::= { dtpCtpEntry  43 }


dtpCtpDtpTxEs15MinutesTceReporting OBJECT-TYPE
    SYNTAX      TruthValue
    MAX-ACCESS  read-write
    STATUS      current
    DESCRIPTION "Flag that enables the reporting of DtpTxEs15MinutesTce crossing."
    DEFVAL      { false }
    ::= { dtpCtpEntry  44 }


dtpCtpDtpTxSes15MinutesTceReporting OBJECT-TYPE
    SYNTAX      TruthValue
    MAX-ACCESS  read-write
    STATUS      current
    DESCRIPTION "Flag that enables the reporting of DtpTxSes15MinutesTce crossing."
    DEFVAL      { false }
    ::= { dtpCtpEntry  45 }


dtpCtpDtpTxUas15MinutesTceReporting OBJECT-TYPE
    SYNTAX      TruthValue
    MAX-ACCESS  read-write
    STATUS      current
    DESCRIPTION "Flag that enables the reporting of DtpTxUas15MinutesTce crossing."
    DEFVAL      { false }
    ::= { dtpCtpEntry  46 }


dtpCtpDtpTxCvDayTceReporting OBJECT-TYPE
    SYNTAX      TruthValue
    MAX-ACCESS  read-write
    STATUS      current
    DESCRIPTION "Flag that enables the reporting of DtpTxCvDayTce crossing."
    DEFVAL      { false }
    ::= { dtpCtpEntry  47 }


dtpCtpDtpTxEsDayTceReporting OBJECT-TYPE
    SYNTAX      TruthValue
    MAX-ACCESS  read-write
    STATUS      current
    DESCRIPTION "Flag that enables the reporting of DtpTxEsDayTce crossing."
    DEFVAL      { false }
    ::= { dtpCtpEntry  48 }


dtpCtpDtpTxSesDayTceReporting OBJECT-TYPE
    SYNTAX      TruthValue
    MAX-ACCESS  read-write
    STATUS      current
    DESCRIPTION "Flag that enables the reporting of DtpTxSesDayTce crossing."
    DEFVAL      { false }
    ::= { dtpCtpEntry  49 }


dtpCtpDtpTxUasDayTceReporting OBJECT-TYPE
    SYNTAX      TruthValue
    MAX-ACCESS  read-write
    STATUS      current
    DESCRIPTION "Flag that enables the reporting of DtpTxUasDayTce crossing."
    DEFVAL      { false }
    ::= { dtpCtpEntry  50 }


dtpCtpPrbsGenerationMode OBJECT-TYPE
    SYNTAX  INTEGER {
        disabled(1),
        enabled(2)
    }
    MAX-ACCESS  read-write
    STATUS      current
    DESCRIPTION "Flag which enables the generation of PRBS data on the transmit side."
    DEFVAL      { disabled }
    ::= { dtpCtpEntry  51 }


dtpCtpPrbsMonitoringMode OBJECT-TYPE
    SYNTAX  INTEGER {
        disabled(1),
        enabled(2)
    }
    MAX-ACCESS  read-write
    STATUS      current
    DESCRIPTION "Flag which enables the monitoring of bit errors."
    DEFVAL      { disabled }
    ::= { dtpCtpEntry  52 }


dtpCtpNumDtpSubCh OBJECT-TYPE
    SYNTAX      Integer32
    MAX-ACCESS  read-only
    STATUS      current
    DESCRIPTION "Number of channels muxed to a channlized cross-connect/snc."
    DEFVAL      { 0 }
    ::= { dtpCtpEntry  53 }


dtpCtpMuxMode OBJECT-TYPE
    SYNTAX      TruthValue
    MAX-ACCESS  read-only
    STATUS      current
    DESCRIPTION "Flag that indicates whether the DTF is operating in multiplexed-mode (encapsulation of two GbE client tributaries) or not. For 8x1GbE TAM, the Mux mode is ‘on’ by default."
    DEFVAL      { false }
    ::= { dtpCtpEntry  54 }


dtpCtpPmHistStatsEnable OBJECT-TYPE
    SYNTAX  INTEGER {
        enabled(1),
        disabled(2)
    }
    MAX-ACCESS  read-write
    STATUS      current
    DESCRIPTION "Flag to enable PM collection."
    DEFVAL      { disabled }
    ::= { dtpCtpEntry  55 }


dtpCtpCrossConnectType OBJECT-TYPE
    SYNTAX  INTEGER {
        none(1),
        unidirectionFrom(2),
        unidirectionTo(3),
        unidirectionToAndFrom(4),
        bidirection(5),
        bidirectionUnidirectionFrom(6),
        bidirectionUnidirectionTo(7),
        bidirectionUnidirectionToAndFrom(8)
    }
    MAX-ACCESS  read-only
    STATUS      current
    DESCRIPTION "The type of cross-connect."
    DEFVAL      { none }
    ::= { dtpCtpEntry  56 }


-- Conformance Statements
dtpCtpConformance    OBJECT IDENTIFIER ::= { dtpCtpMIB 3 }
dtpCtpCompliances    OBJECT IDENTIFIER ::= { dtpCtpConformance 1 }
dtpCtpGroups         OBJECT IDENTIFIER ::= { dtpCtpConformance 2 }

dtpCtpCompliance MODULE-COMPLIANCE
    STATUS current
    DESCRIPTION
    "Describes the requirements for conformance to the DTPCTP-MIB"
    MODULE
        MANDATORY-GROUPS { dtpCtpGroup }
    ::= { dtpCtpCompliances 1 }

dtpCtpGroup OBJECT-GROUP
    OBJECTS {
        dtpCtpCfgProtSt,
        dtpCtpProtMod,
        dtpCtpSwReason,
        dtpCtpSupportingTP,
        dtpCtpExpectedPayload,
        dtpCtpSupportingCircuitIdList,
        dtpCtpDetectedPayload,
        dtpCtpDataRate,
        dtpCtpLoopback,
        dtpCtpInsertDtpTti,
        dtpCtpTtiAlarmReporting,
        dtpCtpTxTtiAlarmReporting,
        dtpCtpTxDtpTti,
        dtpCtpRxDtpTtiWrite,
        dtpCtpExpectedDtpTti,
        dtpCtpExpectedTxDtpTti,
        dtpCtpRxDtpTti,
        dtpCtpRecvTxDtpTti,
        dtpCtpDtpRxCv15MinutesTce,
        dtpCtpDtpRxEs15MinutesTce,
        dtpCtpDtpRxSes15MinutesTce,
        dtpCtpDtpRxUas15MinutesTce,
        dtpCtpDtpRxCvDayTce,
        dtpCtpDtpRxEsDayTce,
        dtpCtpDtpRxSesDayTce,
        dtpCtpDtpRxUasDayTce,
        dtpCtpDtpTxCv15MinutesTce,
        dtpCtpDtpTxEs15MinutesTce,
        dtpCtpDtpTxSes15MinutesTce,
        dtpCtpDtpTxUas15MinutesTce,
        dtpCtpDtpTxCvDayTce,
        dtpCtpDtpTxEsDayTce,
        dtpCtpDtpTxSesDayTce,
        dtpCtpDtpTxUasDayTce,
        dtpCtpDtpRxCv15MinutesTceReporting,
        dtpCtpDtpRxEs15MinutesTceReporting,
        dtpCtpDtpRxSes15MinutesTceReporting,
        dtpCtpDtpRxUas15MinutesTceReporting,
        dtpCtpDtpRxCvDayTceReporting,
        dtpCtpDtpRxEsDayTceReporting,
        dtpCtpDtpRxSesDayTceReporting,
        dtpCtpDtpRxUasDayTceReporting,
        dtpCtpDtpTxCv15MinutesTceReporting,
        dtpCtpDtpTxEs15MinutesTceReporting,
        dtpCtpDtpTxSes15MinutesTceReporting,
        dtpCtpDtpTxUas15MinutesTceReporting,
        dtpCtpDtpTxCvDayTceReporting,
        dtpCtpDtpTxEsDayTceReporting,
        dtpCtpDtpTxSesDayTceReporting,
        dtpCtpDtpTxUasDayTceReporting,
        dtpCtpPrbsGenerationMode,
        dtpCtpPrbsMonitoringMode,
        dtpCtpNumDtpSubCh,
        dtpCtpMuxMode,
        dtpCtpPmHistStatsEnable,
        dtpCtpCrossConnectType
    }
    STATUS current
    DESCRIPTION
        " A collection of objects for managing the dtpCtp"
    ::= { dtpCtpGroups 1 }


END
