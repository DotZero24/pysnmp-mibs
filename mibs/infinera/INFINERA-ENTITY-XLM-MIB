-- ***************************************************************
-- INFINERA-ENTITY-XLM-MIB
--
-- October 2008, Sharfuddin Syed / Narendra Gupta
--
--
-- Copyright (c) 2008-2012 by Infinera Inc.
-- All rights reserved.
-- ****************************************************************

INFINERA-ENTITY-XLM-MIB DEFINITIONS ::= BEGIN

IMPORTS
    OBJECT-TYPE, MODULE-IDENTITY        FROM SNMPv2-SMI
    OBJECT-GROUP, MODULE-COMPLIANCE     FROM SNMPv2-CONF
    RowStatus, DisplayString            FROM SNMPv2-TC
    entLPPhysicalIndex                  FROM ENTITY-MIB
    equipment                           FROM INFINERA-REG-MIB
    InfnOperatingMode,
    InfnEqptType                        FROM INFINERA-TC-MIB;

xlmMIB MODULE-IDENTITY
    LAST-UPDATED  "200810200000Z"
    ORGANIZATION
        "INFINERA"
    CONTACT-INFO
        "Infinera
        169 Java Drive
        Sunnyvale, CA - 94089

        Contact : Technical Support
        Email   : support@infinera.com
        Phone   : 1-877-INF-5288"
    DESCRIPTION
        "This MIB is modeling for XLM equipment table."

::= { equipment 5 }

xlmConformance       OBJECT IDENTIFIER ::= { xlmMIB 3 }
xlmCompliances       OBJECT IDENTIFIER ::= { xlmConformance 1 }
xlmGroups            OBJECT IDENTIFIER ::= { xlmConformance 2 }

xlmTable  OBJECT-TYPE
    SYNTAX SEQUENCE OF XlmEntry
    MAX-ACCESS not-accessible
    STATUS     current
    DESCRIPTION
        "This table contains all XLM modules that are currently present in a network element.
        "
    ::= { xlmMIB 1 }

xlmEntry  OBJECT-TYPE
    SYNTAX     XlmEntry
    MAX-ACCESS not-accessible
    STATUS     current
    DESCRIPTION
        "A row in the XLM table. Each row in the table is identified with a unique entPhysicalIndexID.
        "
    INDEX { entLPPhysicalIndex }
    ::= { xlmTable 1 }

XlmEntry ::= SEQUENCE {
    xlmMoId                              DisplayString,
    xlmProvEqptType                      InfnEqptType,
    xlmPicDspVer                         DisplayString,
    xlmOperatingMode                     InfnOperatingMode,
    xlmAvailableTunableOcgNumbers        Integer32,
    xlmProvisionedOcgNumber              Integer32,
    xlmInstalledOcgNumber                Integer32,
    xlmRowStatus                         RowStatus
}

xlmMoId  OBJECT-TYPE
    SYNTAX     DisplayString
    MAX-ACCESS read-create
    STATUS     current
    DESCRIPTION
        "This is the primary Key of the objects e.g 1-A-3"
    ::= { xlmEntry 1 }

xlmProvEqptType  OBJECT-TYPE
    SYNTAX     InfnEqptType
    MAX-ACCESS read-create
    STATUS     current
    DESCRIPTION
        "The configured XLM type."
    ::= { xlmEntry 2 }

xlmPicDspVer  OBJECT-TYPE
    SYNTAX     DisplayString
    MAX-ACCESS read-only
    STATUS     current
    DESCRIPTION
        "The hardware version of the PIC on the XLM."
    ::= { xlmEntry 3 }

xlmOperatingMode  OBJECT-TYPE
    SYNTAX     InfnOperatingMode
    MAX-ACCESS read-create
    STATUS     current
    DESCRIPTION
        "This objects controls the operating mode for  XLM and DLM in Gen1 and Gen2 modes."
    DEFVAL  { gen2 }
    ::= { xlmEntry 4 }

xlmAvailableTunableOcgNumbers  OBJECT-TYPE
    SYNTAX     Integer32
    MAX-ACCESS read-only
    STATUS     current
    DESCRIPTION
        "This objects represents the available ocgs in bits being set.
         For example if cards available OCG on AXLM-T4-1-C4 are 1, 9, 2and 10 then
         value will be 0x303, i.e. bit 1,9,2 and 10 are set."
    ::= { xlmEntry 5 }

xlmProvisionedOcgNumber  OBJECT-TYPE
    SYNTAX     Integer32
    MAX-ACCESS read-create
    STATUS     current
    DESCRIPTION
        "This represents the OCG number for which tunable line module will be tuned."
    ::= { xlmEntry 6 }

xlmInstalledOcgNumber  OBJECT-TYPE
    SYNTAX     Integer32
    MAX-ACCESS read-create
    STATUS     current
    DESCRIPTION
        "This represents the OCG number for which the line module is tuned."
    ::= { xlmEntry 7 }


xlmRowStatus  OBJECT-TYPE
    SYNTAX     RowStatus
    MAX-ACCESS read-create
    STATUS     current
    DESCRIPTION
        "The row status of this XLM entry.
                Because rows in this table are indexed by entPhysicalIndex, to create a new row one must
                choose a value of entPhysicalIndex that is not already in use.

                A side-effect of the creation of a row in this table is the creation of a corresponding
                row in the eqptTable and the entPhysicalTable.

                The status may not be set to active if the xlmMoId and xlmProvEqptType are not set to valid values.

                This row may only be deleted if it was a pre-provisioned row and the hardware is not present.

                If this row is deleted, the associated row in the Eqpt Table and entPhysicalTable will be
                deleted by the agent."
    ::= { xlmEntry 8 }

xlmCompliance  MODULE-COMPLIANCE
    STATUS     current
    DESCRIPTION
        ""
    MODULE
        MANDATORY-GROUPS { xlmGroup }
    ::= { xlmCompliances 1 }

xlmGroup  OBJECT-GROUP
    OBJECTS {
        xlmAvailableTunableOcgNumbers,
        xlmMoId,
        xlmOperatingMode,
        xlmPicDspVer,
        xlmProvEqptType,
        xlmOperatingMode,
        xlmAvailableTunableOcgNumbers,
        xlmProvisionedOcgNumber,
        xlmInstalledOcgNumber,
        xlmRowStatus  }
    STATUS     current
    DESCRIPTION
        ""
    ::= { xlmGroups 1 }
END
