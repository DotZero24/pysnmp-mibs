-- ***************************************************************
-- INFINERA-ENTITY-OTM-MIB
--
-- October 2011, Sharfuddin Syed / Narendra Gupta
--
--
-- Copyright (c) 2011-2012 by Infinera Inc.
-- All rights reserved.
-- ****************************************************************

INFINERA-ENTITY-OTM-MIB DEFINITIONS ::= BEGIN

IMPORTS
 	OBJECT-TYPE, MODULE-IDENTITY      	FROM SNMPv2-SMI
 	OBJECT-GROUP, MODULE-COMPLIANCE   	FROM SNMPv2-CONF
 	RowStatus, DisplayString          	FROM SNMPv2-TC
 	entLPPhysicalIndex                	FROM ENTITY-MIB
 	equipment                         	FROM INFINERA-REG-MIB
 	InfnEqptType		 		FROM INFINERA-TC-MIB;

otmMIB MODULE-IDENTITY
    LAST-UPDATED  "201110200000Z"
    ORGANIZATION
        "INFINERA"
    CONTACT-INFO
        "Infinera
        169 Java Drive
        Sunnyvale, CA - 94089

        Contact : Technical Support
        Email   : support@infinera.com
        Phone   : 1-877-INF-5288"
    DESCRIPTION
        "This MIB is modeling for OTM equipment table."

::= { equipment 24 }

otmConformance       OBJECT IDENTIFIER ::= { otmMIB 3 }
otmCompliances       OBJECT IDENTIFIER ::= { otmConformance 1 }
otmGroups            OBJECT IDENTIFIER ::= { otmConformance 2 }

otmTable  OBJECT-TYPE
    SYNTAX SEQUENCE OF OtmEntry
    MAX-ACCESS not-accessible
    STATUS     current
    DESCRIPTION
        "This table contains all OTM modules that are currently present in a network element.
        "
    ::= { otmMIB 1 }

otmEntry  OBJECT-TYPE
    SYNTAX     OtmEntry
    MAX-ACCESS not-accessible
    STATUS     current
    DESCRIPTION
        "A row in the OTM table. Each row in the table is identified with a unique entPhysicalIndexID.
        "
    INDEX { entLPPhysicalIndex }
    ::= { otmTable 1 }

OtmEntry ::= SEQUENCE {
    	otmMoId                        DisplayString,
	otmProvEqptType                InfnEqptType,
    	otmRowStatus                   RowStatus,
    	actvTimingSource				DisplayString
}

otmMoId  OBJECT-TYPE
    SYNTAX     DisplayString
    MAX-ACCESS read-create
    STATUS     current
    DESCRIPTION
        "This is the primary Key of the objects"
    ::= { otmEntry 1 }

otmProvEqptType  OBJECT-TYPE
    SYNTAX     InfnEqptType
    MAX-ACCESS read-create
    STATUS     current
    DESCRIPTION
        "The configured OTM type."
    ::= { otmEntry 2 }


otmRowStatus  OBJECT-TYPE
    SYNTAX     RowStatus
    MAX-ACCESS read-create
    STATUS     current
    DESCRIPTION
        "The row status of this OTM entry.
                Because rows in this table are indexed by entPhysicalIndex, to create a new row one must
                choose a value of entPhysicalIndex that is not already in use.

                A side-effect of the creation of a row in this table is the creation of a corresponding
                row in the eqptTable and the entPhysicalTable.

                The status may not be set to active if the otmMoId, otmProvEqptType,  objects are not set
                to valid values.

                This row may only be deleted if it was a pre-provisioned row and the hardware is not present.

                If this row is deleted, the associated row in the Eqpt Table and entPhysicalTable will be
                deleted by the agent."
    ::= { otmEntry 3 }

actvTimingSource OBJECT-TYPE
		SYNTAX     DisplayString
		MAX-ACCESS read-only
    	STATUS     current
    	DESCRIPTION "" ::= { otmEntry 4 }

otmCompliance  MODULE-COMPLIANCE
    STATUS     current
    DESCRIPTION
        ""
    MODULE
        MANDATORY-GROUPS { otmGroup }
    ::= { otmCompliances 1 }

otmGroup  OBJECT-GROUP
    OBJECTS {

        otmMoId,
	otmProvEqptType,
        otmRowStatus,
        actvTimingSource}
    STATUS     current
    DESCRIPTION
        ""
    ::= { otmGroups 1 }
END
