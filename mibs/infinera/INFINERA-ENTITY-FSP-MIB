-- ***************************************************************
-- INFINERA-ENTITY-FSP-MIB
--
--
-- Copyright (c) 2011-2012 by Infinera Inc.
-- All rights reserved.
-- ****************************************************************

INFINERA-ENTITY-FSP-MIB DEFINITIONS ::= BEGIN

IMPORTS
    OBJECT-TYPE, MODULE-IDENTITY        	FROM SNMPv2-SMI
    OBJECT-GROUP, MODULE-COMPLIANCE     	FROM SNMPv2-CONF
    DisplayString            	            FROM SNMPv2-TC
    entLPPhysicalIndex                  	FROM ENTITY-MIB
    equipment                           	FROM INFINERA-REG-MIB;

fspMIB MODULE-IDENTITY
    LAST-UPDATED  "201310200000Z"
    ORGANIZATION "INFINERA"
    CONTACT-INFO
        "Infinera
        169 Java Drive
        Sunnyvale, CA - 94089

        Contact : Technical Support
        Email   : support@infinera.com
        Phone   : 1-877-INF-5288 "
        DESCRIPTION
        "This MIB is modeling for FSP equipment table"

::= { equipment 35 }

fspConformance       OBJECT IDENTIFIER ::= { fspMIB 3 }
fspCompliances       OBJECT IDENTIFIER ::= { fspConformance 1 }
fspGroups            OBJECT IDENTIFIER ::= { fspConformance 2 }

fspTable  OBJECT-TYPE
    SYNTAX SEQUENCE OF FspEntry
    MAX-ACCESS not-accessible
    STATUS     current
    DESCRIPTION
        "This table contains all FSP modules that are currently present in a network element.
        "
    ::= { fspMIB 1 }

fspEntry  OBJECT-TYPE
    SYNTAX     FspEntry
    MAX-ACCESS not-accessible
    STATUS     current
    DESCRIPTION
        "A row in the FSP table. Each row in the table is identified with a unique entPhysicalIndexID."
    INDEX { entLPPhysicalIndex }
    ::= { fspTable 1 }

FspEntry ::= SEQUENCE {
   fspType                  INTEGER,
   fspProvSerialNumber      DisplayString,
   fspLabel                 DisplayString,
   fspAid                   DisplayString
}


fspType OBJECT-TYPE
    SYNTAX  INTEGER {
        fspE9D18MPO(7805),
        fspS4D8MPO(7806),
        fspC1D1MPO(7807),
        fmpC8fourLcMPO(7808)
    }
    MAX-ACCESS  read-write
    STATUS      current
    DESCRIPTION ""
    ::= { fspEntry 1 }

fspProvSerialNumber OBJECT-TYPE
	SYNTAX     DisplayString
    MAX-ACCESS read-write
    STATUS     current
    DESCRIPTION ""
    ::= { fspEntry 2 }

fspLabel    OBJECT-TYPE
    SYNTAX      DisplayString
    MAX-ACCESS  read-write
    STATUS      current
    DESCRIPTION ""
    ::= { fspEntry  3 }

fspAid   OBJECT-TYPE
    SYNTAX      DisplayString
    MAX-ACCESS  read-write
    STATUS      current
    DESCRIPTION ""
    ::= { fspEntry  4 }

fspCompliance  MODULE-COMPLIANCE
    STATUS      current
    DESCRIPTION ""
    MODULE
        MANDATORY-GROUPS { fspGroup }
    ::= { fspCompliances 1 }

fspGroup  OBJECT-GROUP
    OBJECTS {
        fspType,
        fspProvSerialNumber,
        fspLabel,
        fspAid
    }
    STATUS     current
    DESCRIPTION
        ""
    ::= { fspGroups 1 }
END
