-- *****************************************************************
-- INFINERA-TP-ODUCLIENTCTP-MIB
-- Copyright (c) 2009-2012 by Infinera Inc.
-- All rights reserved.
-- ****************************************************************

INFINERA-TP-ODUCLIENTCTP-MIB DEFINITIONS ::= BEGIN

IMPORTS
    MODULE-IDENTITY, OBJECT-TYPE,
    Integer32, Counter64                        FROM SNMPv2-SMI
    MODULE-COMPLIANCE, OBJECT-GROUP             FROM SNMPv2-CONF
    DisplayString, TruthValue                   FROM SNMPv2-TC
    ifIndex                                     FROM IF-MIB
    InfnServiceType,InfnEqptType,InfnArc,
    InfnEnableDisable,
    InfnTcmList,InfnServiceMode,
    InfnMonitoringMode,InfnSMQ,InfnRate,
    InfnXconType,FloatTenths, InfnTsgType,
    InfnNwLatencyMeasurementMode                FROM INFINERA-TC-MIB
    terminationPoint                            FROM INFINERA-REG-MIB;


oduClientCtpMIB MODULE-IDENTITY
    LAST-UPDATED  "200907200000Z"
    ORGANIZATION  "Infinera"
    CONTACT-INFO
        "Infinera
        1322 Bordeaux Drive
        Sunnyvale, CA - 94089

        Contact : Technical Support
        Email   : support@infinera.com
        Phone   : 1-877-INF-5288"
    DESCRIPTION
        " "
    REVISION  "200907200000Z"
    DESCRIPTION
        "First Version"
    ::= { terminationPoint 23 }



oduClientCtpTable OBJECT-TYPE
    SYNTAX      SEQUENCE OF OduClientCtpEntry
    MAX-ACCESS  not-accessible
    STATUS      current
    DESCRIPTION
        "A list of OduClientCtp entries. Each entry is uniquely identified by the value of ifIndex."
    ::= { oduClientCtpMIB 1 }

oduClientCtpEntry  OBJECT-TYPE
    SYNTAX      OduClientCtpEntry
    MAX-ACCESS  not-accessible
    STATUS      current
    DESCRIPTION
        "A OduClientCtp entry containing information pertaining to Infinera OduClientCtp interfaces. Entries will exist in this table for interfaces of type oduclientCtp."
    INDEX { ifIndex }
    ::= { oduClientCtpTable 1 }


OduClientCtpEntry  ::= SEQUENCE {
    oduClientCtpServiceMode                     InfnServiceMode,
    oduClientCtpServiceModeQualifier            InfnSMQ,
    oduClientCtpFacMonitoringMode               InfnMonitoringMode,
    oduClientCtpFacTxTTI                        DisplayString,
    oduClientCtpFacExpectedSAPI                 DisplayString,
    oduClientCtpFacExpectedDAPI                 DisplayString,


    oduClientCtpTermTxTTI                       DisplayString,
    oduClientCtpTermExpectedSAPI                DisplayString,
    oduClientCtpTermExpectedDAPI                DisplayString,

    oduClientCtpFacReceivedTTI                  DisplayString,
    oduClientCtpTermReceivedTTI                 DisplayString,

    oduClientCtpRxEb15MinutesTce                Integer32,
    oduClientCtpTxEb15MinutesTce                Integer32,
    oduClientCtpRxEbDayTce                      Integer32,
    oduClientCtpTxEbDayTce                      Integer32,

    oduClientCtpRxDs15MinutesTce                Integer32,
    oduClientCtpTxDs15MinutesTce                Integer32,
    oduClientCtpRxDsDayTce                      Integer32,
    oduClientCtpTxDsDayTce                      Integer32,

    oduClientCtpRxEbDayTceReporting             TruthValue,
    oduClientCtpRxEb15MinutesTceReporting       TruthValue,
    oduClientCtpTxEbDayTceReporting             TruthValue,
    oduClientCtpTxEb15MinutesTceReporting       TruthValue,

    oduClientCtpRxDsDayTceReporting             TruthValue,
    oduClientCtpRxDs15MinutesTceReporting       TruthValue,
    oduClientCtpTxDsDayTceReporting             TruthValue,
    oduClientCtpTxDs15MinutesTceReporting       TruthValue,

    oduClientCtpFacTimDetMode                   INTEGER,
    oduClientCtpTermTimDetMode                  INTEGER,

    oduClientCtpTcmList                         BITS,
    oduClientCtpConfiguredServiceType           InfnServiceType,
    oduClientCtpTamType                         InfnEqptType,
    oduClientCtpFacPmHistStatsEnable            InfnEnableDisable,
    oduClientCtpTermPmHistStatsEnable           InfnEnableDisable,
    oduClientCtpAlarmReportControl              InfnArc,
    oduClientCtpSupportingCircuitIdList         DisplayString,
    oduClientCtpFacDSThreshold                  Integer32,
    oduClientCtpTermDSThreshold                 Integer32,
--    oduClientCtpTermSDThreshold                 Integer32,
    oduClientCtpTermMonitoringMode              InfnMonitoringMode,
    oduClientCtpRxBei15MinutesTce                Integer32,
    oduClientCtpTxBei15MinutesTce                Integer32,
    oduClientCtpRxBeiDayTce                      Integer32,
    oduClientCtpTxBeiDayTce                      Integer32,

    oduClientCtpRxBeiDayTceReporting             TruthValue,
    oduClientCtpRxBei15MinutesTceReporting       TruthValue,
    oduClientCtpTxBeiDayTceReporting             TruthValue,
    oduClientCtpTxBei15MinutesTceReporting       TruthValue,

    oduClientCtpTSCount                         Integer32,
    oduClientCtprate                            DisplayString,
    oduClientCtpTributaryPortNumber             Integer32,
    oduClientCtpExpectedTPNs                    Integer32,
    oduClientCtpDetectedTPNs                    Integer32,
    oduClientCtpuserConfigured                  TruthValue,
    oduClientCtpsupportingOPUTributarySlots     DisplayString,
    oduClientCtpavailableOPUTributarySlots      DisplayString,
    oduClientCtpdatarate                        InfnRate,
    oduClientCtpCrossConnectType                InfnXconType,
    oduClientCtpSupportingTP                    DisplayString,
    oduClientCtpTsg                             InfnTsgType,
    oduClientCtpExpectedPayload                 InfnServiceType,
    oduClientCtpLoopBack                        INTEGER,
    oduClientCtpFacSDThreshold                  Integer32,
    oduClientCtpFacPrbsGenMode                 InfnEnableDisable,
    oduClientCtpFacPrbsMonMode                 InfnEnableDisable,
    oduClientCtpTermPrbsGenMode                 InfnEnableDisable,
    oduClientCtpTermPrbsMonMode                 InfnEnableDisable,
    oduClientCtpDetectedPayloadType             InfnServiceType,
    oduClientCtpFacDMPELatencyMode              InfnNwLatencyMeasurementMode,
    oduClientCtpFacDMPSLatencyMode              InfnNwLatencyMeasurementMode,
    oduClientCtpTermDMPELatencyMode             InfnNwLatencyMeasurementMode,
    oduClientCtpTermDMPSLatencyMode             InfnNwLatencyMeasurementMode,
    oduClientCtpFacDMPELatHighThreshold         FloatTenths,
    oduClientCtpFacDMPELatLowThreshold          FloatTenths,
    oduClientCtpTermDMPELatHighThreshold        FloatTenths,
    oduClientCtpTermDMPELatLowThreshold         FloatTenths,
    oduClientCtpFacDMPSLatHighThreshold         FloatTenths,
    oduClientCtpFacDMPSLatLowThreshold          FloatTenths,
    oduClientCtpTermDMPSLatHighThreshold        FloatTenths,
    oduClientCtpTermDMPSLatLowThreshold         FloatTenths,
    oduClientCtpDetectedTPNList                 DisplayString
}

oduClientCtpServiceMode  OBJECT-TYPE
    SYNTAX      InfnServiceMode
    MAX-ACCESS  read-only
    STATUS      current
    DESCRIPTION "The Service Mode (SM) of the ODU client CTP (i.e., the mode/type of service in which
        this ODU client CTP is being used,)."
    DEFVAL      {none}
    ::= { oduClientCtpEntry  1 }

oduClientCtpServiceModeQualifier  OBJECT-TYPE
    SYNTAX      InfnSMQ
    MAX-ACCESS  read-only
    STATUS      current
    DESCRIPTION "The Service Mode Qualifier (SMQ) of the ODU client CTP
    (i.e., the mode/type of service in which this ODU client CTP is being used,)."
    DEFVAL      {none}
    ::= { oduClientCtpEntry  2 }

oduClientCtpFacMonitoringMode OBJECT-TYPE
    SYNTAX  InfnMonitoringMode
    MAX-ACCESS  read-write
    STATUS      current
    DESCRIPTION "Allowed Section Monitoring / Path  Monitoring / TCM Attribute Value(s)
        (For side corresponding to MonitoringMode) (Fac-Side/Term-Side)."
    ::= { oduClientCtpEntry 3 }


oduClientCtpFacTxTTI OBJECT-TYPE
    SYNTAX      DisplayString  (SIZE(1..64))
    MAX-ACCESS  read-write
    STATUS      current
    DESCRIPTION  "The TTI message that needs to be transmitted in the Facility direction (e.g., from  Line to Trib direction).
    This message is inserted based on appropriate setting of FacMonitoringMode"
    ::= { oduClientCtpEntry  4 }

oduClientCtpFacExpectedSAPI OBJECT-TYPE
    SYNTAX      DisplayString  (SIZE(1..16))
    MAX-ACCESS  read-write
    STATUS      current
    DESCRIPTION "The Source Access Point Identifier that is expected from the Facility side (e.g., Trib to Line direction). "
    ::= { oduClientCtpEntry  5 }

oduClientCtpFacExpectedDAPI OBJECT-TYPE
    SYNTAX      DisplayString (SIZE(1..16))
    MAX-ACCESS  read-write
    STATUS      current
    DESCRIPTION "The Destination Access Point Identifier that is expected from the Facility side(e.g., Trib to Line direction)."
    ::= { oduClientCtpEntry  6 }


oduClientCtpTermTxTTI OBJECT-TYPE
    SYNTAX      DisplayString (SIZE(1..64))
    MAX-ACCESS  read-write
    STATUS      current
    DESCRIPTION "The TTI message that needs to be transmitted in the Terminal direction (e.g., from Trib to Line direction). This message
    is inserted based on appropriate setting of TermMonitoringMode"
    ::= { oduClientCtpEntry  7 }

oduClientCtpTermExpectedSAPI OBJECT-TYPE
    SYNTAX      DisplayString (SIZE(1..16))
    MAX-ACCESS  read-write
    STATUS      current
    DESCRIPTION "The Source Access Point Identifier that is expected from the Terminal side (e.g., in the Line to Trib direction)."
    ::= { oduClientCtpEntry  8 }

oduClientCtpTermExpectedDAPI OBJECT-TYPE
    SYNTAX      DisplayString (SIZE(1..16))
    MAX-ACCESS  read-write
    STATUS      current
    DESCRIPTION "The Destination Access Point Identifier that is expected from the Terminal side (e.g., in the Line to Trib direction)."
    ::= { oduClientCtpEntry  9 }

oduClientCtpFacReceivedTTI  OBJECT-TYPE
    SYNTAX      DisplayString (SIZE(1..64))
    MAX-ACCESS  read-only
    STATUS      current
    DESCRIPTION "The TTI message received from the Facility side (e.g., in the Trib to Term direction) of an OTU Trib Interface."
    ::= { oduClientCtpEntry  10 }

oduClientCtpTermReceivedTTI  OBJECT-TYPE
    SYNTAX      DisplayString (SIZE(1..64))
    MAX-ACCESS  read-only
    STATUS      current
    DESCRIPTION    "The TTI message received from the Terminal side (e.g., in the Line to Trib direction) of an ODU Trib Interface."
    ::= { oduClientCtpEntry  11 }


oduClientCtpRxEb15MinutesTce  OBJECT-TYPE
    SYNTAX      Integer32
    MAX-ACCESS  read-write
    STATUS      current
    DESCRIPTION "Number of Error Block in received direction during 15 minutes interval."
    DEFVAL      { 1500 }
    ::= { oduClientCtpEntry  12 }

oduClientCtpTxEb15MinutesTce  OBJECT-TYPE
    SYNTAX      Integer32
    MAX-ACCESS  read-write
    STATUS      current
    DESCRIPTION "Number of Error Block in transmitted direction during 15 minutes interval."
    DEFVAL      { 1500 }
    ::= { oduClientCtpEntry  13 }

oduClientCtpRxEbDayTce OBJECT-TYPE
    SYNTAX      Integer32
    MAX-ACCESS  read-write
    STATUS      current
    DESCRIPTION "Number of Error Block in received direction during 24 hours interval."
    DEFVAL      { 15000 }
    ::= { oduClientCtpEntry  14 }

oduClientCtpTxEbDayTce OBJECT-TYPE
    SYNTAX      Integer32
    MAX-ACCESS  read-write
    STATUS      current
    DESCRIPTION "Number of Error Block in transmitted direction during 24 hours interval."
    DEFVAL      { 15000 }
    ::= { oduClientCtpEntry  15 }

oduClientCtpRxDs15MinutesTce  OBJECT-TYPE
    SYNTAX      Integer32
    MAX-ACCESS  read-write
    STATUS      current
    DESCRIPTION "Number of Defect Seconds in received direction during 15 minutes interval."
    DEFVAL      { 120 }
    ::= { oduClientCtpEntry  16 }

oduClientCtpTxDs15MinutesTce  OBJECT-TYPE
    SYNTAX      Integer32
    MAX-ACCESS  read-write
    STATUS      current
    DESCRIPTION "Number of Defect Seconds in transmitted direction during 15 minutes interval."
    DEFVAL      { 120 }
    ::= { oduClientCtpEntry  17 }

oduClientCtpRxDsDayTce OBJECT-TYPE
    SYNTAX      Integer32
    MAX-ACCESS  read-write
    STATUS      current
    DESCRIPTION "Number of Defect Seconds in received direction during 24 hours interval."
    DEFVAL      { 1200 }
    ::= { oduClientCtpEntry  18 }

oduClientCtpTxDsDayTce OBJECT-TYPE
    SYNTAX      Integer32
    MAX-ACCESS  read-write
    STATUS      current
    DESCRIPTION "Number of Defect Seconds in transmitted direction during 24 hours interval."
    DEFVAL      { 1200 }
    ::= { oduClientCtpEntry  19 }


oduClientCtpRxEbDayTceReporting OBJECT-TYPE
    SYNTAX      TruthValue
    MAX-ACCESS  read-write
    STATUS      current
    DESCRIPTION " Flag that enables/disables the reporting of RxEbDayTce threshold crossing."
    DEFVAL      { false }
    ::= { oduClientCtpEntry  20 }

oduClientCtpRxEb15MinutesTceReporting OBJECT-TYPE
    SYNTAX      TruthValue
    MAX-ACCESS  read-write
    STATUS      current
    DESCRIPTION "  Flag that enables/disables the reporting of RxEb15MinutesTce threshold crossing."
    DEFVAL      { false }
    ::= { oduClientCtpEntry  21 }

oduClientCtpTxEbDayTceReporting OBJECT-TYPE
    SYNTAX      TruthValue
    MAX-ACCESS  read-write
    STATUS      current
    DESCRIPTION " Flag that enables/disables the reporting of TxEbDayTce threshold crossing."
    DEFVAL      { false }
    ::= { oduClientCtpEntry  22 }

oduClientCtpTxEb15MinutesTceReporting OBJECT-TYPE
    SYNTAX      TruthValue
    MAX-ACCESS  read-write
    STATUS      current
    DESCRIPTION " Flag that enables/disables the reporting of TxEb15MinutesTce threshold crossing."
    DEFVAL      { false }
    ::= { oduClientCtpEntry  23 }

oduClientCtpRxDsDayTceReporting OBJECT-TYPE
    SYNTAX      TruthValue
    MAX-ACCESS  read-write
    STATUS      current
    DESCRIPTION " Flag that enables/disables the reporting of RxDsDayTce threshold crossing."
    DEFVAL      { false }
    ::= { oduClientCtpEntry  24 }

oduClientCtpRxDs15MinutesTceReporting OBJECT-TYPE
    SYNTAX      TruthValue
    MAX-ACCESS  read-write
    STATUS      current
    DESCRIPTION " Flag that enables/disables the reporting of RxDs15MinutesTce threshold crossing."
    DEFVAL      { false }
    ::= { oduClientCtpEntry  25 }

oduClientCtpTxDsDayTceReporting OBJECT-TYPE
    SYNTAX      TruthValue
    MAX-ACCESS  read-write
    STATUS      current
    DESCRIPTION " Flag that enables/disables the reporting of RxDsDayTce threshold crossing."
    DEFVAL      { false }
    ::= { oduClientCtpEntry  26 }

oduClientCtpTxDs15MinutesTceReporting OBJECT-TYPE
    SYNTAX      TruthValue
    MAX-ACCESS  read-write
    STATUS      current
    DESCRIPTION " Flag that enables/disables the reporting of RxDs15MinutesTce threshold crossing."
    DEFVAL      { false }
    ::= { oduClientCtpEntry  27 }


oduClientCtpFacTimDetMode  OBJECT-TYPE
    SYNTAX  INTEGER {
    off(1),
    sapi(2),
    dapi(3),
    sapidapi(4)
    }
    MAX-ACCESS  read-write
    STATUS      current
    DESCRIPTION "This attribute is used to configure if the TIM-S alarm shall be reported on mismatch of Expected and Received TTI message. The following are the values and their meaning:
        OFF: TIM-S is not reported.
        DAPI: TIM-S is reported only if the DAPI message mismatch occurs.
        SAPI: TIM-S is reported only if the SAPI message mismatch occurs.
        DAPISAPI: Either the DAPI or    the SAPI messages are in a mis- match state."
    DEFVAL      { off }
    ::= { oduClientCtpEntry 28 }

oduClientCtpTermTimDetMode  OBJECT-TYPE
    SYNTAX  INTEGER {
    off(1),
    sapi(2),
    dapi(3),
    sapidapi(4)
    }
    MAX-ACCESS  read-write
    STATUS      current
    DESCRIPTION "This attribute is used to configure if the TIM-S alarm shall be reported on mismatch of Expected and Received TTI
        message (on Terminal side). The following are the values and their meaning:
        OFF: TIM-S is not reported.
        DAPI: TIM-S is reported only if the DAPI message mismatch occurs.
        SAPI: TIM-S is reported only if the SAPI message mismatch occurs.
        DAPI_SAPI: Either the DAPI or the SAPI messages are in a mismatch state. "
    DEFVAL      { off }
    ::= { oduClientCtpEntry 29 }

oduClientCtpTcmList OBJECT-TYPE
    SYNTAX  InfnTcmList
    MAX-ACCESS  read-only
    STATUS      current
    DESCRIPTION "List of active tandem connection monitoring points (list of (contained) ODUkT
        CTP objects). The default of NONE(BITS 0) implies that none of the TCM fields are in use
        no contained ODUkT CTP objects). Note that a maximum of 3 TCM IDs can be active at any given time,
        each with one or both sides (facility and/or terminal) active (e.g., there can be up to 6 ODUkT
        CTP object instances, but only for 3 TCM IDs).
        Each entry in the TCMList is active and will have a corresponding ODUkT client CTP created.
        For OTUk-based adaptation, TCMs can only be enabled on the Facility-side."
    ::= { oduClientCtpEntry  30 }

oduClientCtpConfiguredServiceType  OBJECT-TYPE
    SYNTAX  InfnServiceType
    MAX-ACCESS  read-only
    STATUS      current
    DESCRIPTION "The ODU Service type that is configured on this generic OduClientCtp managed object. "
      ::= { oduClientCtpEntry 31 }


oduClientCtpTamType   OBJECT-TYPE
    SYNTAX     InfnEqptType
    MAX-ACCESS read-only
    STATUS     obsolete
    DESCRIPTION "The equipment type where this ODU client is residing."
    ::= { oduClientCtpEntry  32 }


oduClientCtpFacPmHistStatsEnable OBJECT-TYPE
    SYNTAX  InfnEnableDisable
    MAX-ACCESS  read-write
    STATUS      current
    DESCRIPTION " Flag to enable or disable the collection of PMs on the Facility side of ODU Clients"
    DEFVAL      { enabled }
    ::= { oduClientCtpEntry  33 }

oduClientCtpTermPmHistStatsEnable OBJECT-TYPE
    SYNTAX  InfnEnableDisable
    MAX-ACCESS  read-write
    STATUS      current
    DESCRIPTION "Flag to enable or disable the collection of PMs on the Terminal side of ODU Clients."
    DEFVAL      { enabled }
    ::= { oduClientCtpEntry  34 }

oduClientCtpAlarmReportControl OBJECT-TYPE
    SYNTAX InfnArc
    MAX-ACCESS  read-write
    STATUS      current
    DESCRIPTION " The Alarm Reporting Control Flag for the ODU Clients."
    DEFVAL      { allowed }
    ::= { oduClientCtpEntry  35 }

oduClientCtpSupportingCircuitIdList  OBJECT-TYPE
    SYNTAX      DisplayString
    MAX-ACCESS  read-only
    STATUS      current
    DESCRIPTION "The Supporting Circuit ID List that is this client is using. "
    ::= { oduClientCtpEntry   36 }


oduClientCtpFacDSThreshold OBJECT-TYPE
    SYNTAX      Integer32 (1..100)
    MAX-ACCESS  read-write
    STATUS      current
    DESCRIPTION "This attribute indicates the Facility-side threshold level for declaring a performance monitoring (PM)
        Second to be bad. A PM Second is declared bad if the percentage of detected errored blocks in that second is
        greater than or equal to the specified threshold level. This attribute maps to the DEGThr MIB of RFC-3591"
    DEFVAL      { 30 }
    ::= { oduClientCtpEntry  37 }


oduClientCtpTermDSThreshold OBJECT-TYPE
    SYNTAX      Integer32 (1..100)
    MAX-ACCESS  read-write
    STATUS      current
    DESCRIPTION "This attribute indicates the Terminal side (e.g., Line side) threshold level for declaring a
    performance monitoring (PM) Second to be bad. A PM Second is  declared bad if the percentage of detected  errored blocks in that second is greater than or equal to
    the specified threshold level. This attribute maps to the DEGThr MIB of RFC-3591"
    DEFVAL      { 30 }
    ::= { oduClientCtpEntry  38 }

-- oduClientCtpTermSDThreshold  OBJECT-TYPE
--    SYNTAX      Integer32 (2..10)
--    MAX-ACCESS  read-write
--    STATUS      current
--    DESCRIPTION "This attribute indicates the Terminal side (e.g., Line side) threshold level for declaring a Degraded Signal defect.
--        A Degraded Signal defect shall be declared if SDThreshold consecutive bad PM Seconds are detected.
--        This attribute maps to the DEGM MIB of RFC-3591"
--    DEFVAL      { 7 }
--    ::= { oduClientCtpEntry  40 }

oduClientCtpTermMonitoringMode OBJECT-TYPE
    SYNTAX  InfnMonitoringMode
    MAX-ACCESS  read-write
    STATUS      current
    DESCRIPTION "Allowed Section Monitoring / Path  Monitoring / TCM Attribute Value(s)
        (For side corresponding to MonitoringMode) (Fac-Side/Term-Side)."
    ::= { oduClientCtpEntry 39 }

oduClientCtpRxBei15MinutesTce  OBJECT-TYPE
    SYNTAX      Integer32
    MAX-ACCESS  read-write
    STATUS      current
    DESCRIPTION "Number of Error Block in received direction during 15 minutes interval."
    DEFVAL      { 1500 }
    ::= { oduClientCtpEntry  40 }

oduClientCtpTxBei15MinutesTce  OBJECT-TYPE
    SYNTAX      Integer32
    MAX-ACCESS  read-write
    STATUS      current
    DESCRIPTION "Number of Error Block in transmitted direction during 15 minutes interval."
    DEFVAL      { 1500 }
    ::= { oduClientCtpEntry  41 }

oduClientCtpRxBeiDayTce OBJECT-TYPE
    SYNTAX      Integer32
    MAX-ACCESS  read-write
    STATUS      current
    DESCRIPTION "Number of Error Block in received direction during 24 hours interval."
    DEFVAL      { 15000 }
    ::= { oduClientCtpEntry  42 }

oduClientCtpTxBeiDayTce OBJECT-TYPE
    SYNTAX      Integer32
    MAX-ACCESS  read-write
    STATUS      current
    DESCRIPTION "Number of Error Block in transmitted direction during 24 hours interval."
    DEFVAL      { 15000 }
    ::= { oduClientCtpEntry  43 }

oduClientCtpRxBeiDayTceReporting OBJECT-TYPE
    SYNTAX      TruthValue
    MAX-ACCESS  read-write
    STATUS      current
    DESCRIPTION " Flag that enables/disables the reporting of RxEbDayTce threshold crossing."
    DEFVAL      { false }
    ::= { oduClientCtpEntry  44 }

oduClientCtpRxBei15MinutesTceReporting OBJECT-TYPE
    SYNTAX      TruthValue
    MAX-ACCESS  read-write
    STATUS      current
    DESCRIPTION "  Flag that enables/disables the reporting of RxEb15MinutesTce threshold crossing."
    DEFVAL      { false }
    ::= { oduClientCtpEntry  45 }

oduClientCtpTxBeiDayTceReporting OBJECT-TYPE
    SYNTAX      TruthValue
    MAX-ACCESS  read-write
    STATUS      current
    DESCRIPTION " Flag that enables/disables the reporting of TxEbDayTce threshold crossing."
    DEFVAL      { false }
    ::= { oduClientCtpEntry  46 }

oduClientCtpTxBei15MinutesTceReporting OBJECT-TYPE
    SYNTAX      TruthValue
    MAX-ACCESS  read-write
    STATUS      current
    DESCRIPTION " Flag that enables/disables the reporting of TxEb15MinutesTce threshold crossing."
    DEFVAL      { false }
    ::= { oduClientCtpEntry  47 }


oduClientCtpTSCount OBJECT-TYPE
    SYNTAX  Integer32
    MAX-ACCESS  read-only
    STATUS      current
    DESCRIPTION ""
    ::= { oduClientCtpEntry 48 }

oduClientCtprate 	 OBJECT-TYPE
    SYNTAX  DisplayString
    MAX-ACCESS  read-only
    STATUS      current
    DESCRIPTION "."
    ::= { oduClientCtpEntry 49 }

oduClientCtpTributaryPortNumber OBJECT-TYPE
    SYNTAX  Integer32
    MAX-ACCESS  read-only
    STATUS      current
    DESCRIPTION ""
    ::= { oduClientCtpEntry 50 }

oduClientCtpExpectedTPNs  OBJECT-TYPE
    SYNTAX  Integer32
    MAX-ACCESS  read-only
    STATUS      current
    DESCRIPTION ""
    ::= { oduClientCtpEntry 51 }

oduClientCtpDetectedTPNs   OBJECT-TYPE
    SYNTAX  Integer32
    MAX-ACCESS  read-only
    STATUS      current
    DESCRIPTION ""
    ::= { oduClientCtpEntry 52 }

oduClientCtpuserConfigured   OBJECT-TYPE
    SYNTAX  TruthValue
    MAX-ACCESS  read-write
    STATUS      obsolete
    DESCRIPTION ""
    ::= { oduClientCtpEntry 53 }

oduClientCtpsupportingOPUTributarySlots  OBJECT-TYPE
    SYNTAX  DisplayString
    MAX-ACCESS  read-write
    STATUS      current
    DESCRIPTION ""
    ::= { oduClientCtpEntry 54 }

oduClientCtpavailableOPUTributarySlots  OBJECT-TYPE
    SYNTAX  DisplayString
    MAX-ACCESS  read-only
    STATUS      current
    DESCRIPTION ""
    ::= { oduClientCtpEntry 55 }

oduClientCtpdatarate 	 OBJECT-TYPE
    SYNTAX  InfnRate
    MAX-ACCESS  read-only
    STATUS      current
    DESCRIPTION ""
    ::= { oduClientCtpEntry 56 }

oduClientCtpCrossConnectType  OBJECT-TYPE
    SYNTAX  InfnXconType
    MAX-ACCESS  read-only
    STATUS      current
    DESCRIPTION ""
    ::= { oduClientCtpEntry 57 }


oduClientCtpSupportingTP    OBJECT-TYPE
    SYNTAX  DisplayString
    MAX-ACCESS  read-write
    STATUS      current
    DESCRIPTION ""
    ::= { oduClientCtpEntry 58 }

oduClientCtpTsg   OBJECT-TYPE
    SYNTAX  InfnTsgType
    MAX-ACCESS  read-write
    STATUS      current
    DESCRIPTION ""
    ::= { oduClientCtpEntry 59 }

oduClientCtpExpectedPayload   OBJECT-TYPE
    SYNTAX  InfnServiceType
    MAX-ACCESS  read-only
    STATUS      current
    DESCRIPTION ""
    ::= { oduClientCtpEntry 60  }

oduClientCtpLoopBack OBJECT-TYPE
    SYNTAX  INTEGER {
        none(1),
        terminal(2),
        facility(3)
    }
    MAX-ACCESS  read-write
    STATUS      current
    DESCRIPTION "Flag to enable the loopback."
    DEFVAL      { none }
    ::= {oduClientCtpEntry   61 }

oduClientCtpFacSDThreshold  OBJECT-TYPE
    SYNTAX      Integer32 (2..10)
    MAX-ACCESS  read-write
    STATUS      current
    DESCRIPTION "This attribute indicates the Facility-side (e.g., Trib-side/Client-side) threshold level for declaring a
        Degraded Signal defect. A Degraded Signal defect shall be declared if SDThreshold consecutive bad PM Seconds are detected.
        This attribute maps to the DEGM MIB of RFC-3591"
    DEFVAL      { 7 }
    ::= { oduClientCtpEntry  62 }

oduClientCtpFacPrbsGenMode  OBJECT-TYPE
    SYNTAX      InfnEnableDisable
    MAX-ACCESS  read-write
    STATUS      current
    DESCRIPTION ""
    ::= { oduClientCtpEntry  63 }

oduClientCtpFacPrbsMonMode  OBJECT-TYPE
    SYNTAX      InfnEnableDisable
    MAX-ACCESS  read-write
    STATUS      current
    DESCRIPTION ""
    ::= { oduClientCtpEntry  64 }

oduClientCtpTermPrbsGenMode  OBJECT-TYPE
    SYNTAX      InfnEnableDisable
    MAX-ACCESS  read-write
    STATUS      current
    DESCRIPTION ""
    ::= { oduClientCtpEntry  65 }

oduClientCtpTermPrbsMonMode  OBJECT-TYPE
    SYNTAX      InfnEnableDisable
    MAX-ACCESS  read-write
    STATUS      current
    DESCRIPTION ""
    ::= { oduClientCtpEntry  66 }


oduClientCtpDetectedPayloadType   OBJECT-TYPE
    SYNTAX  InfnServiceType
    MAX-ACCESS  read-only
    STATUS      current
    DESCRIPTION ""
    ::= { oduClientCtpEntry 67  }

oduClientCtpFacDMPELatencyMode  OBJECT-TYPE
    SYNTAX      InfnNwLatencyMeasurementMode
    MAX-ACCESS  read-write
    STATUS      current
    DESCRIPTION ""
    ::= { oduClientCtpEntry  68 }

oduClientCtpFacDMPSLatencyMode  OBJECT-TYPE
    SYNTAX      InfnNwLatencyMeasurementMode
    MAX-ACCESS  read-write
    STATUS      current
    DESCRIPTION ""
    ::= { oduClientCtpEntry  69 }

oduClientCtpTermDMPELatencyMode  OBJECT-TYPE
    SYNTAX      InfnNwLatencyMeasurementMode
    MAX-ACCESS  read-write
    STATUS      current
    DESCRIPTION ""
    ::= { oduClientCtpEntry  70 }

oduClientCtpTermDMPSLatencyMode  OBJECT-TYPE
    SYNTAX      InfnNwLatencyMeasurementMode
    MAX-ACCESS  read-write
    STATUS      current
    DESCRIPTION ""
    ::= { oduClientCtpEntry  71 }


oduClientCtpFacDMPELatHighThreshold  OBJECT-TYPE
    SYNTAX      FloatTenths
    MAX-ACCESS  read-write
    STATUS      current
    DESCRIPTION ""
    ::= { oduClientCtpEntry  72 }

oduClientCtpFacDMPELatLowThreshold  OBJECT-TYPE
    SYNTAX      FloatTenths
    MAX-ACCESS  read-write
    STATUS      current
    DESCRIPTION ""
    ::= { oduClientCtpEntry  73 }

oduClientCtpTermDMPELatHighThreshold  OBJECT-TYPE
    SYNTAX      FloatTenths
    MAX-ACCESS  read-write
    STATUS      current
    DESCRIPTION ""
    ::= { oduClientCtpEntry  74 }

oduClientCtpTermDMPELatLowThreshold  OBJECT-TYPE
    SYNTAX      FloatTenths
    MAX-ACCESS  read-write
    STATUS      current
    DESCRIPTION ""
    ::= { oduClientCtpEntry  75 }

oduClientCtpFacDMPSLatHighThreshold  OBJECT-TYPE
    SYNTAX      FloatTenths
    MAX-ACCESS  read-write
    STATUS      current
    DESCRIPTION ""
    ::= { oduClientCtpEntry  76 }

oduClientCtpFacDMPSLatLowThreshold  OBJECT-TYPE
    SYNTAX      FloatTenths
    MAX-ACCESS  read-write
    STATUS      current
    DESCRIPTION ""
    ::= { oduClientCtpEntry  77 }

oduClientCtpTermDMPSLatHighThreshold  OBJECT-TYPE
    SYNTAX      FloatTenths
    MAX-ACCESS  read-write
    STATUS      current
    DESCRIPTION ""
    ::= { oduClientCtpEntry  78 }

oduClientCtpTermDMPSLatLowThreshold  OBJECT-TYPE
    SYNTAX      FloatTenths
    MAX-ACCESS  read-write
    STATUS      current
    DESCRIPTION ""
    ::= { oduClientCtpEntry  79 }

oduClientCtpDetectedTPNList  OBJECT-TYPE
    SYNTAX      DisplayString
    MAX-ACCESS  read-write
    STATUS      current
    DESCRIPTION ""
    ::= { oduClientCtpEntry  80 }

-- Conformance Statements
oduClientCtpConformance    OBJECT IDENTIFIER ::= { oduClientCtpMIB 3 }
oduClientCtpCompliances    OBJECT IDENTIFIER ::= { oduClientCtpConformance 1 }
oduClientCtpGroups         OBJECT IDENTIFIER ::= { oduClientCtpConformance 2 }

oduClientCtpCompliance MODULE-COMPLIANCE
    STATUS current
    DESCRIPTION
    "Describes the requirements for conformance to the ODUCLIENTCTP-MIB"
    MODULE
        MANDATORY-GROUPS { oduClientCtpGroup }
    ::= { oduClientCtpCompliances 1 }

oduClientCtpGroup OBJECT-GROUP
    OBJECTS {
    oduClientCtpServiceMode,
    oduClientCtpFacMonitoringMode,
    oduClientCtpFacTxTTI,
    oduClientCtpFacExpectedSAPI,
    oduClientCtpFacExpectedDAPI,

    oduClientCtpTermTxTTI,
    oduClientCtpTermExpectedSAPI,
    oduClientCtpTermExpectedDAPI,

    oduClientCtpFacReceivedTTI,
    oduClientCtpTermReceivedTTI,

    oduClientCtpRxEb15MinutesTce,
    oduClientCtpTxEb15MinutesTce,
    oduClientCtpRxEbDayTce,
    oduClientCtpTxEbDayTce,

    oduClientCtpRxDs15MinutesTce,
    oduClientCtpTxDs15MinutesTce,
    oduClientCtpRxDsDayTce,
    oduClientCtpTxDsDayTce,

    oduClientCtpRxEbDayTceReporting,
    oduClientCtpRxEb15MinutesTceReporting,
    oduClientCtpTxEbDayTceReporting,
    oduClientCtpTxEb15MinutesTceReporting,

    oduClientCtpRxDsDayTceReporting,
    oduClientCtpRxDs15MinutesTceReporting,
    oduClientCtpTxDsDayTceReporting,
    oduClientCtpTxDs15MinutesTceReporting,

    oduClientCtpFacTimDetMode,
    oduClientCtpTermTimDetMode,

    oduClientCtpTcmList,
    oduClientCtpConfiguredServiceType,
    oduClientCtpTamType,
    oduClientCtpFacPmHistStatsEnable,
    oduClientCtpTermPmHistStatsEnable,
    oduClientCtpAlarmReportControl,
    oduClientCtpSupportingCircuitIdList,
    oduClientCtpFacDSThreshold,
    oduClientCtpTermDSThreshold,
--    oduClientCtpTermSDThreshold,
    oduClientCtpRxBei15MinutesTce,
    oduClientCtpTxBei15MinutesTce,
    oduClientCtpRxBeiDayTce,
    oduClientCtpTxBeiDayTce,
    oduClientCtpRxBeiDayTceReporting,
    oduClientCtpRxBei15MinutesTceReporting,
    oduClientCtpTxBeiDayTceReporting,
    oduClientCtpTxBei15MinutesTceReporting,
    oduClientCtpTermMonitoringMode,
    oduClientCtpTSCount,
    oduClientCtprate,
    oduClientCtpTributaryPortNumber,
    oduClientCtpExpectedTPNs,
    oduClientCtpDetectedTPNs,
    oduClientCtpuserConfigured,
    oduClientCtpsupportingOPUTributarySlots,
    oduClientCtpavailableOPUTributarySlots,
    oduClientCtpdatarate,
    oduClientCtpCrossConnectType,
    oduClientCtpSupportingTP,
    oduClientCtpTsg,
    oduClientCtpExpectedPayload ,
    oduClientCtpLoopBack ,
    oduClientCtpFacSDThreshold,
    oduClientCtpFacPrbsGenMode,
    oduClientCtpFacPrbsMonMode,
    oduClientCtpTermPrbsGenMode,
    oduClientCtpTermPrbsMonMode,
    oduClientCtpDetectedPayloadType,
    oduClientCtpFacDMPELatencyMode,
    oduClientCtpFacDMPSLatencyMode,
    oduClientCtpTermDMPELatencyMode,
    oduClientCtpTermDMPSLatencyMode,
    oduClientCtpFacDMPELatHighThreshold,
    oduClientCtpFacDMPELatLowThreshold,
    oduClientCtpTermDMPELatHighThreshold,
    oduClientCtpTermDMPELatLowThreshold,
    oduClientCtpFacDMPSLatHighThreshold,
    oduClientCtpFacDMPSLatLowThreshold,
    oduClientCtpTermDMPSLatHighThreshold,
    oduClientCtpTermDMPSLatLowThreshold,
    oduClientCtpDetectedTPNList
    }
    STATUS current
    DESCRIPTION
        " A collection of objects for managing the oduClientCtp"
    ::= { oduClientCtpGroups 1 }


END
