-- *****************************************************************
-- INFINERA-TP-PXMCOSMAPPROFILE-MIB
--
-- Mithun Murthy/ Divyank Rastogi
--
--
-- Copyright (c) 2008-2016 by Infinera Inc.
-- All rights reserved.
-- ****************************************************************

INFINERA-TP-PXMCOSMAPPROFILE-MIB DEFINITIONS ::= BEGIN

IMPORTS
    MODULE-IDENTITY, OBJECT-TYPE, Integer32     FROM SNMPv2-SMI
    MODULE-COMPLIANCE, OBJECT-GROUP             FROM SNMPv2-CONF
    TruthValue, DisplayString                   FROM SNMPv2-TC
    ifIndex                                     FROM IF-MIB
	InfnCosType									FROM INFINERA-TC-MIB
    commonProfile								FROM INFINERA-REG-MIB;

pxmCosMapProfileMIB MODULE-IDENTITY
    LAST-UPDATED  "201605200000Z"
    ORGANIZATION
        "Infinera"
    CONTACT-INFO
        "Infinera
                1322 Bordeaux Drive
                Sunnyvale, CA - 94089

                Contact : Technical Support
                Email   : support@infinera.com
                Phone   : 1-877-INF-5288"
    DESCRIPTION
        " "

    REVISION  "201605200000Z"
    DESCRIPTION
        " "
::= { commonProfile 6 }


pxmCosMapProfileConformance   OBJECT IDENTIFIER ::= { pxmCosMapProfileMIB 3 }
pxmCosMapProfileCompliances   OBJECT IDENTIFIER ::= { pxmCosMapProfileConformance 1 }
pxmCosMapProfileGroups        OBJECT IDENTIFIER ::= { pxmCosMapProfileConformance 2 }

pxmCosMapProfileTable  OBJECT-TYPE
    SYNTAX SEQUENCE OF PxmCosMapProfileEntry
    MAX-ACCESS not-accessible
    STATUS     current
    DESCRIPTION
        "A list of PxmCosMapProfile entries. Each entry is uniquely identified by
                the value of ifIndex."
    ::= { pxmCosMapProfileMIB 1 }

pxmCosMapProfileEntry  OBJECT-TYPE
    SYNTAX     PxmCosMapProfileEntry
    MAX-ACCESS not-accessible
    STATUS     current
    DESCRIPTION
        "A PxmCosMapProfile entry containing information pertaining to
                Infinera PxmCosMapProfile interfaces. This table is a subclass of IfCommon.
                Entries will exist in this table only for interfaces of type PxmCosMapProfile."
    INDEX { ifIndex }
    ::= { pxmCosMapProfileTable 1 }

PxmCosMapProfileEntry  ::= SEQUENCE {
    pxmCosMapProfileFromCosType		InfnCosType,
    pxmCosMapProfileToCosType		InfnCosType,
	pxmCosMapProfileInUse			TruthValue
}

pxmCosMapProfileFromCosType		OBJECT-TYPE
    SYNTAX     InfnCosType
    MAX-ACCESS read-create
    STATUS     current
    DESCRIPTION
        "PXM from cos type"
    ::= { pxmCosMapProfileEntry 1 }

pxmCosMapProfileToCosType	OBJECT-TYPE
    SYNTAX     InfnCosType
    MAX-ACCESS read-create
    STATUS     current
    DESCRIPTION
        ""
    ::= { pxmCosMapProfileEntry 2 }

pxmCosMapProfileInUse	OBJECT-TYPE
    SYNTAX     TruthValue
    MAX-ACCESS read-only
    STATUS     current
    DESCRIPTION
        ""
    ::= { pxmCosMapProfileEntry 3 }

pxmCosMapProfileCompliance  MODULE-COMPLIANCE
    STATUS     current
    DESCRIPTION
        "Describes the requirements for conformance to the TRIBPTP-MIB"
    MODULE
        MANDATORY-GROUPS { pxmCosMapProfileGroup }
    ::= { pxmCosMapProfileCompliances 1 }

pxmCosMapProfileGroup  OBJECT-GROUP
    OBJECTS {
        pxmCosMapProfileFromCosType,
        pxmCosMapProfileToCosType,
		pxmCosMapProfileInUse
    }
    STATUS     current
    DESCRIPTION
        " A collection of objects for managing pxmCosMapProfile interfaces."
    ::= { pxmCosMapProfileGroups 1 }
END
