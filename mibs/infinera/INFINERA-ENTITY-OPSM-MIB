-- ***************************************************************
-- INFINERA-ENTITY-OPSM-MIB
--
-- Copyright (c) 2008-2015 by Infinera Inc.
-- All rights reserved.
-- ****************************************************************

INFINERA-ENTITY-OPSM-MIB DEFINITIONS ::= BEGIN

IMPORTS
    OBJECT-TYPE, MODULE-IDENTITY, Integer32        FROM SNMPv2-SMI
    OBJECT-GROUP, MODULE-COMPLIANCE                FROM SNMPv2-CONF
    TruthValue, DisplayString                      FROM SNMPv2-TC
    entPhysicalIndex                               FROM ENTITY-MIB
    equipment                                      FROM INFINERA-REG-MIB
    InfnEqptType                                   FROM INFINERA-TC-MIB;

opsmMIB MODULE-IDENTITY
    LAST-UPDATED  "201505100000Z"
    ORGANIZATION
        "Infinera"
    CONTACT-INFO
        "Infinera
                1322 Bordeaux Drive
                Sunnyvale, CA - 94089

                Contact : Technical Support
                Email   : support@infinera.com
                Phone   : 1-877-INF-5288"
    DESCRIPTION
        " "
::= { equipment 43 }


-- Conformance Statements

opsmConformance       OBJECT IDENTIFIER ::= { opsmMIB 3 }
opsmCompliances       OBJECT IDENTIFIER ::= { opsmConformance 1 }
opsmGroups            OBJECT IDENTIFIER ::= { opsmConformance 2 }

opsmTable  OBJECT-TYPE
    SYNTAX SEQUENCE OF OpsmEntry
    MAX-ACCESS not-accessible
    STATUS     current
    DESCRIPTION
        "A list of OPSM entries. Each entry is uniquely identified by the value
                of entPhysicalIndex."
    ::= { opsmMIB 1 }

opsmEntry  OBJECT-TYPE
    SYNTAX     OpsmEntry
    MAX-ACCESS not-accessible
    STATUS     current
    DESCRIPTION
        "A OPSM entry containing information pertaining to
            Infinera OPSM modules. Entries will exist in this table for
            entPhysicalEntries of type OPSM."
    INDEX { entPhysicalIndex }
    ::= { opsmTable 1 }

OpsmEntry ::= SEQUENCE {
    opsmMoId                      DisplayString,
    opsmProvEqptType              InfnEqptType,
    opsmNodeId                    DisplayString
}

opsmMoId     OBJECT-TYPE
    SYNTAX      DisplayString
    MAX-ACCESS  read-write
    STATUS      current
    DESCRIPTION ""
    ::= { opsmEntry 1 }

opsmProvEqptType OBJECT-TYPE
    SYNTAX      InfnEqptType
    MAX-ACCESS  read-write
    STATUS      current
    DESCRIPTION ""
    ::= { opsmEntry 2 }

opsmNodeId OBJECT-TYPE
    SYNTAX      DisplayString
    MAX-ACCESS  read-only
    STATUS      current
    DESCRIPTION ""
    ::= { opsmEntry  3 }


opsmCompliance  MODULE-COMPLIANCE
    STATUS     current
    DESCRIPTION
        "Describes the requirements for conformance to the OPSM-MIB"
    MODULE
        MANDATORY-GROUPS { opsmGroup }
    ::= { opsmCompliances 1 }

opsmGroup  OBJECT-GROUP
    OBJECTS {
        opsmMoId,
        opsmProvEqptType,
        opsmNodeId
    }
    STATUS     current
    DESCRIPTION
        " A collection of objects for managing a OPSM module"
    ::= { opsmGroups 1 }
END
