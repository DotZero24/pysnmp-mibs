-- ***************************************************************
-- INFINERA-ENTITY-PXMSTATICUNICASTFDB-MIB
--
-- May 2016, Kavitha Manjunatha / Divyank Rastogi
--
--
-- Copyright (c) 2008-2012 by Infinera Inc.
-- All rights reserved.
-- ****************************************************************
INFINERA-ENTITY-PXMSTATICUNICASTFDB-MIB DEFINITIONS ::= BEGIN

IMPORTS
    OBJECT-TYPE, MODULE-IDENTITY, Unsigned32    FROM SNMPv2-SMI
    OBJECT-GROUP, MODULE-COMPLIANCE             FROM SNMPv2-CONF
    DisplayString                               FROM SNMPv2-TC
    ifIndex                                     FROM IF-MIB
    terminationPoint                            FROM INFINERA-REG-MIB;

pxmStaticUnicastFdbMIB MODULE-IDENTITY
    LAST-UPDATED  "201605200000Z"
    ORGANIZATION
        "INFINERA"
    CONTACT-INFO
        "Infinera
        169 Java Drive
        Sunnyvale, CA - 94089

        Contact : Technical Support
        Email   : support@infinera.com
        Phone   : 1-877-INF-5288"
    DESCRIPTION
        "This MIB is modeling for PXMSTATICUNICASTFDB equipment table."
::= { terminationPoint 65 }

pxmStaticUnicastFdbConformance       OBJECT IDENTIFIER ::= { pxmStaticUnicastFdbMIB 3 }
pxmStaticUnicastFdbCompliances       OBJECT IDENTIFIER ::= { pxmStaticUnicastFdbConformance 1 }
pxmStaticUnicastFdbGroups            OBJECT IDENTIFIER ::= { pxmStaticUnicastFdbConformance 2 }

pxmStaticUnicastFdbTable  OBJECT-TYPE
    SYNTAX SEQUENCE OF PxmStaticUnicastFdbEntry
    MAX-ACCESS not-accessible
    STATUS     current
    DESCRIPTION
        "This table contains all PXMSTATICUNICASTFDB  modules that are currently present
        in a network element."
    ::= { pxmStaticUnicastFdbMIB 1 }

pxmStaticUnicastFdbEntry  OBJECT-TYPE
    SYNTAX     PxmStaticUnicastFdbEntry
    MAX-ACCESS not-accessible
    STATUS     current
    DESCRIPTION
        "A row in the MEP table. Each row in the table is identified with a unique entPhysicalIndexID."
    INDEX { ifIndex }
    ::= { pxmStaticUnicastFdbTable 1 }

PxmStaticUnicastFdbEntry ::= SEQUENCE {
    pxmStaticUnicastFdbMacAddress         DisplayString
}

pxmStaticUnicastFdbMacAddress  OBJECT-TYPE
    SYNTAX     DisplayString
    MAX-ACCESS read-only
    STATUS     current
    DESCRIPTION
        ""
    ::= { pxmStaticUnicastFdbEntry 1 }

pxmStaticUnicastFdbCompliance  MODULE-COMPLIANCE
    STATUS     current
    DESCRIPTION ""
    MODULE
        MANDATORY-GROUPS { pxmStaticUnicastFdbGroup }
    ::= { pxmStaticUnicastFdbCompliances 1 }

pxmStaticUnicastFdbGroup  OBJECT-GROUP
    OBJECTS {
        pxmStaticUnicastFdbMacAddress
    }
    STATUS     current
    DESCRIPTION ""
    ::= { pxmStaticUnicastFdbGroups 1 }
END
