-- *****************************************************************
-- INFINERA-TP-GBECLIENTCTP-MIB
--
-- October 2008, Sharfuddin Syed / Narendra Gupta
--
--
-- Copyright (c) 2008-2012 by Infinera Inc.
-- All rights reserved.
-- ****************************************************************

INFINERA-TP-GBECLIENTCTP-MIB DEFINITIONS ::= BEGIN

IMPORTS
    OBJECT-TYPE, MODULE-IDENTITY, Integer32        FROM SNMPv2-SMI
    OBJECT-GROUP, MODULE-COMPLIANCE                FROM SNMPv2-CONF
    TruthValue, DisplayString                      FROM SNMPv2-TC
    ifIndex                                        FROM IF-MIB
    terminationPoint                               FROM INFINERA-REG-MIB
    InfnServiceType, InfnLoopbackType,InfnServiceMode,
	InfnSMQ, InfnClientAction, InfnEnableDisable,
    InfnPmHistStatsControl, InfnGigeMaxPacketLen,
    InfnTribDisableAction                          FROM INFINERA-TC-MIB;
gbeClientCtpMIB MODULE-IDENTITY
    LAST-UPDATED  "200810200000Z"
    ORGANIZATION
        "Infinera"
    CONTACT-INFO
        "???"
    DESCRIPTION
        " "
::= { terminationPoint 19 }


-- Confirmance Statements

gbeClientCtpConformance  OBJECT IDENTIFIER ::= { gbeClientCtpMIB 3 }
gbeClientCtpCompliances  OBJECT IDENTIFIER ::= { gbeClientCtpConformance 1 }
gbeClientCtpGroups   OBJECT IDENTIFIER ::= { gbeClientCtpConformance 2 }

-- January 11, 2008

gbeClientCtpTable  OBJECT-TYPE
    SYNTAX SEQUENCE OF GbeClientCtpEntry
    MAX-ACCESS not-accessible
    STATUS     current
    DESCRIPTION
        " A list of gbeClientCtp entries. The number of entries is give by value of MOId."
    ::= { gbeClientCtpMIB 1 }

gbeClientCtpEntry  OBJECT-TYPE
    SYNTAX     GbeClientCtpEntry
    MAX-ACCESS not-accessible
    STATUS     current
    DESCRIPTION
        " A  gbeClientCtp entry containing all the information
         pertaining to Infinera gbeClientCtp."
    INDEX { ifIndex }
    ::= { gbeClientCtpTable 1 }

GbeClientCtpEntry ::= SEQUENCE {
    gbeClientCtpSupportingCircuitIdList        DisplayString,
    gbeClientCtpLoopback                       InfnLoopbackType,
    gbeClientCtpPmHistStatsEnable              InfnPmHistStatsControl,
    gbeClientCtpConfiguredServiceType          InfnServiceType,
    gbeClientCtpTribTestSigGenMode             InfnEnableDisable,
    gbeClientCtpTribTestSigMonMode             InfnEnableDisable,
    gbeClientCtpLineTestSigGenMode             InfnEnableDisable,
    gbeClientCtpLineTestSigMonMode             InfnEnableDisable,
    gbeClientCtpMaxPacketLen                   InfnGigeMaxPacketLen,
    gbeClientCtpRxPcsICG15MinTce               Integer32,
    gbeClientCtpRxPcsES15MinTce                Integer32,
    gbeClientCtpRxPcsSES15MinTce               Integer32,
    gbeClientCtpRxPcsSESS15MinTce              Integer32,
    gbeClientCtpRxPcsICGDayTce                 Integer32,
    gbeClientCtpRxPcsESDayTce                  Integer32,
    gbeClientCtpRxPcsSESDayTce                 Integer32,
    gbeClientCtpRxPcsSESSDayTce                Integer32,
    gbeClientCtpRxMacJS15MinTce                Integer32,
    gbeClientCtpRxMacSES15MinTce               Integer32,
    gbeClientCtpRxMacErrOctet15MinTce          Integer32,
    gbeClientCtpRxMacJabber15MinTce            Integer32,
    gbeClientCtpRxMacFragment15MinTce          Integer32,
    gbeClientCtpRxMacCrcAligned15MinTce        Integer32,
    gbeClientCtpRxMacUndersized15MinTce        Integer32,
    gbeClientCtpRxMacOversize15MinTce          Integer32,
    gbeClientCtpRxSize64P15MinTce              Integer32,
    gbeClientCtpRxSize65to127P15MinTce         Integer32,
    gbeClientCtpRxSize128to255P15MinTce        Integer32,
    gbeClientCtpRxSize256to511P15MinTce        Integer32,
    gbeClientCtpRxSize512to1023P15MinTce       Integer32,
    gbeClientCtpRxSize1024to1518P15MinTce      Integer32,
    gbeClientCtpRxSize1519toJumboP15MinTce     Integer32,
    gbeClientCtpRxPackets15MinTce              Integer32,
    gbeClientCtpRxOctets15MinTce               Integer32,
    gbeClientCtpRxBroadcastPkts15MinTce        Integer32,
    gbeClientCtpRxMulticastPkts15MinTce        Integer32,
    gbeClientCtpRxInPauseFrames15MinTce        Integer32,
    gbeClientCtpRxMacJSDayTce                  Integer32,
    gbeClientCtpRxMacSESDayTce                 Integer32,
    gbeClientCtpRxMacErrOctetDayTce            Integer32,
    gbeClientCtpRxMacJabberDayTce              Integer32,
    gbeClientCtpRxMacFragmentDayTce            Integer32,
    gbeClientCtpRxMacCrcAlignedDayTce          Integer32,
    gbeClientCtpRxMacUndersizedDayTce          Integer32,
    gbeClientCtpRxMacOversizeDayTce            Integer32,
    gbeClientCtpRxSize64DayTce                 Integer32,
    gbeClientCtpRxSize65to127DayTce            Integer32,
    gbeClientCtpRxSize128to255DayTce           Integer32,
    gbeClientCtpRxSize256to511DayTce           Integer32,
    gbeClientCtpRxSize512to1023DayTce          Integer32,
    gbeClientCtpRxSize1024to1518DayTce         Integer32,
    gbeClientCtpRxSize1519toJumboDayTce        Integer32,
    gbeClientCtpRxPacketsDayTce                Integer32,
    gbeClientCtpRxOctetsDayTce                 Integer32,
    gbeClientCtpRxBroadcastPktsDayTce          Integer32,
    gbeClientCtpRxMulticastPktsDayTce          Integer32,
    gbeClientCtpRxInPauseFramesDayTce          Integer32,
    gbeClientCtpTxPcsICG15MinTce               Integer32,
    gbeClientCtpTxPcsES15MinTce                Integer32,
    gbeClientCtpTxPcsSES15MinTce               Integer32,
    gbeClientCtpTxPcsSESS15MinTce              Integer32,
    gbeClientCtpTxPcsICGDayTce                 Integer32,
    gbeClientCtpTxPcsESDayTce                  Integer32,
    gbeClientCtpTxPcsSESDayTce                 Integer32,
    gbeClientCtpTxPcsSESSDayTce                Integer32,
    gbeClientCtpTxMacJS15MinTce                Integer32,
    gbeClientCtpTxMacSES15MinTce               Integer32,
    gbeClientCtpTxMacErrOctet15MinTce          Integer32,
    gbeClientCtpTxMacJabber15MinTce            Integer32,
    gbeClientCtpTxMacFragment15MinTce          Integer32,
    gbeClientCtpTxMacCrcAligned15MinTce        Integer32,
    gbeClientCtpTxMacUndersized15MinTce        Integer32,
    gbeClientCtpTxMacOversize15MinTce          Integer32,
    gbeClientCtpTxSize64P15MinTce              Integer32,
    gbeClientCtpTxSize65to127P15MinTce         Integer32,
    gbeClientCtpTxSize128to255P15MinTce        Integer32,
    gbeClientCtpTxSize256to511P15MinTce        Integer32,
    gbeClientCtpTxSize512to1023P15MinTce       Integer32,
    gbeClientCtpTxSize1024to1518P15MinTce      Integer32,
    gbeClientCtpTxSize1519toJumboP15MinTce     Integer32,
    gbeClientCtpTxPackets15MinTce              Integer32,
    gbeClientCtpTxOctets15MinTce               Integer32,
    gbeClientCtpTxBroadcastPkts15MinTce        Integer32,
    gbeClientCtpTxMulticastPkts15MinTce        Integer32,
    gbeClientCtpTxOutPauseFrames15MinTce       Integer32,
    gbeClientCtpTxMacJSDayTce                  Integer32,
    gbeClientCtpTxMacSESDayTce                 Integer32,
    gbeClientCtpTxMacErrOctetDayTce            Integer32,
    gbeClientCtpTxMacJabberDayTce              Integer32,
    gbeClientCtpTxMacFragmentDayTce            Integer32,
    gbeClientCtpTxMacCrcAlignedDayTce          Integer32,
    gbeClientCtpTxMacUndersizedDayTce          Integer32,
    gbeClientCtpTxMacOversizeDayTce            Integer32,
    gbeClientCtpTxSize64DayTce                 Integer32,
    gbeClientCtpTxSize65to127DayTce            Integer32,
    gbeClientCtpTxSize128to255DayTce           Integer32,
    gbeClientCtpTxSize256to511DayTce           Integer32,
    gbeClientCtpTxSize512to1023DayTce          Integer32,
    gbeClientCtpTxSize1024to1518DayTce         Integer32,
    gbeClientCtpTxSize1519toJumboDayTce        Integer32,
    gbeClientCtpTxPacketsDayTce                Integer32,
    gbeClientCtpTxOctetsDayTce                 Integer32,
    gbeClientCtpTxBroadcastPktsDayTce          Integer32,
    gbeClientCtpTxMulticastPktsDayTce          Integer32,
    gbeClientCtpTxOutPauseFramesDayTce         Integer32,
    gbeClientCtpRxPcsICG15MinTceRept           TruthValue,
    gbeClientCtpRxPcsES15MinTceRept            TruthValue,
    gbeClientCtpRxPcsSES15MinTceRept           TruthValue,
    gbeClientCtpRxPcsSESS15MinTceRept          TruthValue,
    gbeClientCtpRxPcsICGDayTceRept             TruthValue,
    gbeClientCtpRxPcsESDayTceRept              TruthValue,
    gbeClientCtpRxPcsSESDayTceRept             TruthValue,
    gbeClientCtpRxPcsSESSDayTceRept            TruthValue,
    gbeClientCtpRxMacJS15MinTceRept            TruthValue,
    gbeClientCtpRxMacSES15MinTceRept           TruthValue,
    gbeClientCtpRxMacErrOctet15MinTceRept      TruthValue,
    gbeClientCtpRxMacJabber15MinTceRept        TruthValue,
    gbeClientCtpRxMacFragment15MinTceRept      TruthValue,
    gbeClientCtpRxMacCrcAligned15MinTceRept    TruthValue,
    gbeClientCtpRxMacUndersized15MinTceRept    TruthValue,
    gbeClientCtpRxMacOversize15MinTceRept      TruthValue,
    gbeClientCtpRxSize64P15MinTceRept          TruthValue,
    gbeClientCtpRxSize65to127P15MinTceRept     TruthValue,
    gbeClientCtpRxSize128to255P15MinTceRept    TruthValue,
    gbeClientCtpRxSize256to511P15MinTceRept    TruthValue,
    gbeClientCtpRxSize512to1023P15MinTceRept   TruthValue,
    gbeClientCtpRxSize1024to1518P15MinTceRept  TruthValue,
    gbeClientCtpRxSize1519toJumboP15MinTceRept TruthValue,
    gbeClientCtpRxPackets15MinTceRept          TruthValue,
    gbeClientCtpRxOctets15MinTceRept           TruthValue,
    gbeClientCtpRxBroadcastPkts15MinTceRept    TruthValue,
    gbeClientCtpRxMulticastPkts15MinTceRept    TruthValue,
    gbeClientCtpRxInPauseFrames15MinTceRept    TruthValue,
    gbeClientCtpRxMacJSDayTceRept              TruthValue,
    gbeClientCtpRxMacSESDayTceRept             TruthValue,
    gbeClientCtpRxMacErrOctetDayTceRept        TruthValue,
    gbeClientCtpRxMacJabberDayTceRept          TruthValue,
    gbeClientCtpRxMacFragmentDayTceRept        TruthValue,
    gbeClientCtpRxMacCrcAlignedDayTceRept      TruthValue,
    gbeClientCtpRxMacUndersizedDayTceRept      TruthValue,
    gbeClientCtpRxMacOversizeDayTceRept        TruthValue,
    gbeClientCtpRxSize64DayTceRept             TruthValue,
    gbeClientCtpRxSize65to127DayTceRept        TruthValue,
    gbeClientCtpRxSize128to255DayTceRept       TruthValue,
    gbeClientCtpRxSize256to511DayTceRept       TruthValue,
    gbeClientCtpRxSize512to1023DayTceRept      TruthValue,
    gbeClientCtpRxSize1024to1518DayTceRept     TruthValue,
    gbeClientCtpRxSize1519toJumboDayTceRept    TruthValue,
    gbeClientCtpRxPacketsDayTceRept            TruthValue,
    gbeClientCtpRxOctetsDayTceRept             TruthValue,
    gbeClientCtpRxBroadcastPktsDayTceRept      TruthValue,
    gbeClientCtpRxMulticastPktsDayTceRept      TruthValue,
    gbeClientCtpRxInPauseFramesDayTceRept      TruthValue,
    gbeClientCtpTxPcsICG15MinTceRept           TruthValue,
    gbeClientCtpTxPcsES15MinTceRept            TruthValue,
    gbeClientCtpTxPcsSES15MinTceRept           TruthValue,
    gbeClientCtpTxPcsSESS15MinTceRept          TruthValue,
    gbeClientCtpTxPcsICGDayTceRept             TruthValue,
    gbeClientCtpTxPcsESDayTceRept              TruthValue,
    gbeClientCtpTxPcsSESDayTceRept             TruthValue,
    gbeClientCtpTxPcsSESSDayTceRept            TruthValue,
    gbeClientCtpTxMacJS15MinTceRept            TruthValue,
    gbeClientCtpTxMacSES15MinTceRept           TruthValue,
    gbeClientCtpTxMacErrOctet15MinTceRept      TruthValue,
    gbeClientCtpTxMacJabber15MinTceRept        TruthValue,
    gbeClientCtpTxMacFragment15MinTceRept      TruthValue,
    gbeClientCtpTxMacCrcAligned15MinTceRept    TruthValue,
    gbeClientCtpTxMacUndersized15MinTceRept    TruthValue,
    gbeClientCtpTxMacOversize15MinTceRept      TruthValue,
    gbeClientCtpTxSize64P15MinTceRept          TruthValue,
    gbeClientCtpTxSize65to127P15MinTceRept     TruthValue,
    gbeClientCtpTxSize128to255P15MinTceRept    TruthValue,
    gbeClientCtpTxSize256to511P15MinTceRept    TruthValue,
    gbeClientCtpTxSize512to1023P15MinTceRept   TruthValue,
    gbeClientCtpTxSize1024to1518P15MinTceRept  TruthValue,
    gbeClientCtpTxSize1519toJumboP15MinTceRept TruthValue,
    gbeClientCtpTxPackets15MinTceRept          TruthValue,
    gbeClientCtpTxOctets15MinTceRept           TruthValue,
    gbeClientCtpTxBroadcastPkts15MinTceRept    TruthValue,
    gbeClientCtpTxMulticastPkts15MinTceRept    TruthValue,
    gbeClientCtpTxOutPauseFrames15MinTceRept   TruthValue,
    gbeClientCtpTxMacJSDayTceRept              TruthValue,
    gbeClientCtpTxMacSESDayTceRept             TruthValue,
    gbeClientCtpTxMacErrOctetDayTceRept        TruthValue,
    gbeClientCtpTxMacJabberDayTceRept          TruthValue,
    gbeClientCtpTxMacFragmentDayTceRept        TruthValue,
    gbeClientCtpTxMacCrcAlignedDayTceRept      TruthValue,
    gbeClientCtpTxMacUndersizedDayTceRept      TruthValue,
    gbeClientCtpTxMacOversizeDayTceRept        TruthValue,
    gbeClientCtpTxSize64DayTceRept             TruthValue,
    gbeClientCtpTxSize65to127DayTceRept        TruthValue,
    gbeClientCtpTxSize128to255DayTceRept       TruthValue,
    gbeClientCtpTxSize256to511DayTceRept       TruthValue,
    gbeClientCtpTxSize512to1023DayTceRept      TruthValue,
    gbeClientCtpTxSize1024to1518DayTceRept     TruthValue,
    gbeClientCtpTxSize1519toJumboDayTceRept    TruthValue,
    gbeClientCtpTxPacketsDayTceRept            TruthValue,
    gbeClientCtpTxOctetsDayTceRept             TruthValue,
    gbeClientCtpTxBroadcastPktsDayTceRept      TruthValue,
    gbeClientCtpTxMulticastPktsDayTceRept      TruthValue,
    gbeClientCtpTxOutPauseFramesDayTceRept     TruthValue,
    gbeClientCtpRxSize1024to1522P15MinTce      Integer32,
    gbeClientCtpRxSize1523toJumboP15MinTce     Integer32,
    gbeClientCtpRxSize1024to1522DayTce         Integer32,
    gbeClientCtpRxSize1523toJumboDayTce        Integer32,
    gbeClientCtpTxSize1024to1522P15MinTce      Integer32,
    gbeClientCtpTxSize1523toJumboP15MinTce     Integer32,
    gbeClientCtpTxSize1024to1522DayTce         Integer32,
    gbeClientCtpTxSize1523toJumboDayTce        Integer32,
    gbeClientCtpRxSize1024to1522P15MinTceRept  TruthValue,
    gbeClientCtpRxSize1523toJumboP15MinTceRept TruthValue,
    gbeClientCtpRxSize1024to1522DayTceRept     TruthValue,
    gbeClientCtpRxSize1523toJumboDayTceRept    TruthValue,
    gbeClientCtpTxSize1024to1522P15MinTceRept  TruthValue,
    gbeClientCtpTxSize1523toJumboP15MinTceRept TruthValue,
    gbeClientCtpTxSize1024to1522DayTceRept     TruthValue,
    gbeClientCtpTxSize1523toJumboDayTceRept    TruthValue,
    gbeClientCtpEncapTribDisableAction         InfnTribDisableAction,
    gbeClientCtpServiceMode			           InfnServiceMode,
    gbeClientCtpServiceModeQualifier		   InfnSMQ,
    gbeClientCtpHostAddress			           DisplayString,
    gbeClientCtpHostControlTableSize		   DisplayString,
    gbeClientCtpEncapClientDisableAction       InfnClientAction,
    gbeClientCtpLLDPSnoopingEnable             TruthValue,
    gbeClientCtpFecMode                        TruthValue,
    gbeClientCtpMaxMTUsize					   Integer32
}

gbeClientCtpSupportingCircuitIdList  OBJECT-TYPE
    SYNTAX     DisplayString
    MAX-ACCESS read-only
    STATUS     current
    DESCRIPTION
        "An unordered list of the Circuit Id's which support this entry.
         This string contains the string representation of each supporting
          CircuitId, separated by a ',' (comma) if there is more than one."
    ::= { gbeClientCtpEntry 1 }

gbeClientCtpLoopback  OBJECT-TYPE
    SYNTAX     InfnLoopbackType
    MAX-ACCESS read-write
    STATUS     current
    DESCRIPTION
        "Flag that indicates if loopback is enabled or disabled."
    ::= { gbeClientCtpEntry 2 }

gbeClientCtpPmHistStatsEnable  OBJECT-TYPE
    SYNTAX     InfnPmHistStatsControl
    MAX-ACCESS read-write
    STATUS     current
    DESCRIPTION
        "Flag to enable or disable PM collection."
    ::= { gbeClientCtpEntry 3 }

gbeClientCtpConfiguredServiceType  OBJECT-TYPE
    SYNTAX     InfnServiceType
    MAX-ACCESS read-only
    STATUS     current
    DESCRIPTION
        "The configured service type."
    ::= { gbeClientCtpEntry 4 }

gbeClientCtpTribTestSigGenMode  OBJECT-TYPE
    SYNTAX    InfnEnableDisable
    MAX-ACCESS read-write
    STATUS     current
    DESCRIPTION
        "Flag for enabling or disabling trib side test signal generation."
    ::= { gbeClientCtpEntry 5 }

gbeClientCtpTribTestSigMonMode  OBJECT-TYPE
    SYNTAX    InfnEnableDisable
    MAX-ACCESS read-write
    STATUS     current
    DESCRIPTION
        "Flag for enabling or disabling trib side test signal monitoring."
    ::= { gbeClientCtpEntry 6 }

gbeClientCtpLineTestSigGenMode  OBJECT-TYPE
    SYNTAX    InfnEnableDisable
    MAX-ACCESS read-write
    STATUS     current
    DESCRIPTION
        "Flag for enabling or disabling line side test signal generation."
    ::= { gbeClientCtpEntry 7 }

gbeClientCtpLineTestSigMonMode  OBJECT-TYPE
    SYNTAX    InfnEnableDisable
    MAX-ACCESS read-write
    STATUS     current
    DESCRIPTION
        "Flag for enabling or disabling line side test signal monitoring."
    ::= { gbeClientCtpEntry 8 }

gbeClientCtpMaxPacketLen  OBJECT-TYPE
    SYNTAX    InfnGigeMaxPacketLen
    MAX-ACCESS read-write
    STATUS     current
    DESCRIPTION
        "Flag to select the maximum packet length (in bytes) that can be supported."
    ::= { gbeClientCtpEntry 9 }

gbeClientCtpRxPcsICG15MinTce  OBJECT-TYPE
    SYNTAX     Integer32
    MAX-ACCESS read-write
    STATUS     current
    DESCRIPTION
        "Count of the Invalid Code Group detected by the Physical Coding
        Sublayer(PCS) in 15 minutes."
    ::= { gbeClientCtpEntry 10 }

gbeClientCtpRxPcsES15MinTce  OBJECT-TYPE
    SYNTAX     Integer32
    MAX-ACCESS read-write
    STATUS     current
    DESCRIPTION
        "Count of the errored seconds detected by the Physical Coding
        Sublayer(PCS) in 15 minutes."
    ::= { gbeClientCtpEntry 11 }

gbeClientCtpRxPcsSES15MinTce  OBJECT-TYPE
    SYNTAX     Integer32
    MAX-ACCESS read-write
    STATUS     current
    DESCRIPTION
        "Count of the severely errored seconds detected by the Physical Coding
         Sublayer(PCS) in 15 minutes."
    ::= { gbeClientCtpEntry 12 }

gbeClientCtpRxPcsSESS15MinTce  OBJECT-TYPE
    SYNTAX     Integer32
    MAX-ACCESS read-write
    STATUS     current
    DESCRIPTION
        "Count of the Severely Errored Sync Seconds detected by the Physical Coding
         Sublayer(PCS) in 15 minutes"
    ::= { gbeClientCtpEntry 13 }

gbeClientCtpRxPcsICGDayTce  OBJECT-TYPE
    SYNTAX     Integer32
    MAX-ACCESS read-write
    STATUS     current
    DESCRIPTION
        "Count of the Invalid Code Group detected by the Physical Coding
        Sublayer(PCS) in 24 hours."
    ::= { gbeClientCtpEntry 14 }

gbeClientCtpRxPcsESDayTce  OBJECT-TYPE
    SYNTAX     Integer32
    MAX-ACCESS read-write
    STATUS     current
    DESCRIPTION
        "Count of the errored seconds detected by the Physical Coding
        Sublayer(PCS) in 24 hours."
    ::= { gbeClientCtpEntry 15 }

gbeClientCtpRxPcsSESDayTce  OBJECT-TYPE
    SYNTAX     Integer32
    MAX-ACCESS read-write
    STATUS     current
    DESCRIPTION
        "Count of the severely errored seconds detected by the Physical Coding
         Sublayer(PCS) in 24 hours."
    ::= { gbeClientCtpEntry 16 }

gbeClientCtpRxPcsSESSDayTce  OBJECT-TYPE
    SYNTAX     Integer32
    MAX-ACCESS read-write
    STATUS     current
    DESCRIPTION
        "Count of the Severely Errored Sync  Seconds detected by the Physical
        Coding Sublayer(PCS) in 24 hours."
    ::= { gbeClientCtpEntry 17 }

gbeClientCtpRxMacJS15MinTce  OBJECT-TYPE
    SYNTAX     Integer32
    MAX-ACCESS read-write
    STATUS     current
    DESCRIPTION
        "Count of number of jabber seconds found by the media access control
        layer in 15 minutes."
    ::= { gbeClientCtpEntry 18 }

gbeClientCtpRxMacSES15MinTce  OBJECT-TYPE
    SYNTAX     Integer32
    MAX-ACCESS read-write
    STATUS     current
    DESCRIPTION
        "Count of number of severely errored seconds found by the media access
         control layer in 15 minutes."
    ::= { gbeClientCtpEntry 19 }

gbeClientCtpRxMacErrOctet15MinTce  OBJECT-TYPE
    SYNTAX     Integer32
    MAX-ACCESS read-write
    STATUS     current
    DESCRIPTION
        "Count of number of errored octets found by the media access control
        layer in 15 minutes."
    ::= { gbeClientCtpEntry 20 }

gbeClientCtpRxMacJabber15MinTce  OBJECT-TYPE
    SYNTAX     Integer32
    MAX-ACCESS read-write
    STATUS     current
    DESCRIPTION
        "Count of number of jabbers found by the media access control layer
        in 15 minutes."
    ::= { gbeClientCtpEntry 21 }

gbeClientCtpRxMacFragment15MinTce  OBJECT-TYPE
    SYNTAX     Integer32
    MAX-ACCESS read-write
    STATUS     current
    DESCRIPTION
        "Count of number of fragment packets found by the media access control
        layer in 15 minutes."
    ::= { gbeClientCtpEntry 22 }

gbeClientCtpRxMacCrcAligned15MinTce  OBJECT-TYPE
    SYNTAX     Integer32
    MAX-ACCESS read-write
    STATUS     current
    DESCRIPTION
        "Count of number of CRC align errors found by the media access control
        layer in 15 minutes."
    ::= { gbeClientCtpEntry 23 }

gbeClientCtpRxMacUndersized15MinTce  OBJECT-TYPE
    SYNTAX     Integer32
    MAX-ACCESS read-write
    STATUS     current
    DESCRIPTION
        "Count of number of undersize packet errors found by the media access
        control layer in 15 minutes."
    ::= { gbeClientCtpEntry 24 }

gbeClientCtpRxMacOversize15MinTce  OBJECT-TYPE
    SYNTAX     Integer32
    MAX-ACCESS read-write
    STATUS     current
    DESCRIPTION
        "Count of number of oversize packet errors found by the media access
        control layer in 15 min."
    ::= { gbeClientCtpEntry 25 }

gbeClientCtpRxSize64P15MinTce  OBJECT-TYPE
    SYNTAX     Integer32
    MAX-ACCESS read-write
    STATUS     current
    DESCRIPTION
        "The total number of packets (including bad packets) received that were
        64 octets in length (excluding framing bits but including FCS octets)
        in 15 minutes."
    ::= { gbeClientCtpEntry 26 }

gbeClientCtpRxSize65to127P15MinTce  OBJECT-TYPE
    SYNTAX     Integer32
    MAX-ACCESS read-write
    STATUS     current
    DESCRIPTION
        "The total number of packets (including bad packets) received that were
         between 65 and 127 octets in length inclusive (excluding framing bits
          but including FCS octets) in 15 minutes."
    ::= { gbeClientCtpEntry 27 }

gbeClientCtpRxSize128to255P15MinTce  OBJECT-TYPE
    SYNTAX     Integer32
    MAX-ACCESS read-write
    STATUS     current
    DESCRIPTION
        "The total number of packets(including bad packets)received that were
         between 128 and 255 octets in length inclusive (excluding framingbits
          but including FCS octets) in 15 minutes"
    ::= { gbeClientCtpEntry 28 }

gbeClientCtpRxSize256to511P15MinTce  OBJECT-TYPE
    SYNTAX     Integer32
    MAX-ACCESS read-write
    STATUS     current
    DESCRIPTION
        "The total number of packets(including bad packets)received that were
         between 256 and 511 octets in length inclusive (excluding framing bits
         but including FCS octets) in 15 minutes."
    ::= { gbeClientCtpEntry 29 }

gbeClientCtpRxSize512to1023P15MinTce  OBJECT-TYPE
    SYNTAX     Integer32
    MAX-ACCESS read-write
    STATUS     current
    DESCRIPTION
        "The total number of packets(including bad packets) received that were
         between 512 and 1023 octets in length inclusive (excluding framing
         bits but including FCS octets)  in 15 minutes."
    ::= { gbeClientCtpEntry 30 }

gbeClientCtpRxSize1024to1518P15MinTce  OBJECT-TYPE
    SYNTAX     Integer32
    MAX-ACCESS read-write
    STATUS     current
    DESCRIPTION
        "The total number of packets (including bad packets) received that were
         between 1024 and 1518 octets in length inclusive (excluding framing
         bits but including FCS octets) in 15 minutes."
    ::= { gbeClientCtpEntry 31 }

gbeClientCtpRxSize1519toJumboP15MinTce  OBJECT-TYPE
    SYNTAX     Integer32
    MAX-ACCESS read-write
    STATUS     current
    DESCRIPTION
        "The total number of packets (including bad packets) received that were
         between 1519 and Jumbo octets in length inclusive (excluding framing
         bits but including FCS octets) in 24 hours."
    ::= { gbeClientCtpEntry 32 }

gbeClientCtpRxPackets15MinTce  OBJECT-TYPE
    SYNTAX     Integer32
    MAX-ACCESS read-write
    STATUS     current
    DESCRIPTION
        "Received packets in 15 minutes."
    ::= { gbeClientCtpEntry 33 }

gbeClientCtpRxOctets15MinTce  OBJECT-TYPE
    SYNTAX     Integer32
    MAX-ACCESS read-write
    STATUS     current
    DESCRIPTION
        "The total number of octets of data (including those in bad packets)
        received on the network (excluding framing bits but including FCS
        octets) in 15 minutes."
    ::= { gbeClientCtpEntry 34 }

gbeClientCtpRxBroadcastPkts15MinTce  OBJECT-TYPE
    SYNTAX     Integer32
    MAX-ACCESS read-write
    STATUS     current
    DESCRIPTION
        "The total number of good packets received that were directed to the
        broadcast address in 15 minutes. This does not include multicast packets."
    ::= { gbeClientCtpEntry 35 }

gbeClientCtpRxMulticastPkts15MinTce  OBJECT-TYPE
    SYNTAX     Integer32
    MAX-ACCESS read-write
    STATUS     current
    DESCRIPTION
        "The total number of good packets received that were directed to a
        multicast address in 15 minutes. This number does not include packets
        directed to the broadcast address."
    ::= { gbeClientCtpEntry 36 }

gbeClientCtpRxInPauseFrames15MinTce  OBJECT-TYPE
    SYNTAX     Integer32
    MAX-ACCESS read-write
    STATUS     current
    DESCRIPTION
        "A count of MAC Control frames received on this interface with an
        opcode indicating the PAUSE operation. This counter does not increment
        when the interface is operating in half-duplex mode in 15 minutes."
    ::= { gbeClientCtpEntry 37 }

gbeClientCtpRxMacJSDayTce  OBJECT-TYPE
    SYNTAX     Integer32
    MAX-ACCESS read-write
    STATUS     current
    DESCRIPTION
        "Count of number of jabber seconds found by the media access control
         layer in 24 hours."
    ::= { gbeClientCtpEntry 38 }

gbeClientCtpRxMacSESDayTce  OBJECT-TYPE
    SYNTAX     Integer32
    MAX-ACCESS read-write
    STATUS     current
    DESCRIPTION
        "Count of number of severely errored seconds found by the media access
         control layer in 24 hours."
    ::= { gbeClientCtpEntry 39 }

gbeClientCtpRxMacErrOctetDayTce  OBJECT-TYPE
    SYNTAX     Integer32
    MAX-ACCESS read-write
    STATUS     current
    DESCRIPTION
        "Count of number of errored octets found by the media access control
        layer in 24 hours."
    ::= { gbeClientCtpEntry 40 }

gbeClientCtpRxMacJabberDayTce  OBJECT-TYPE
    SYNTAX     Integer32
    MAX-ACCESS read-write
    STATUS     current
    DESCRIPTION
        "Count of number of jabbers found by the media access control layer
        in 24 hours."
    ::= { gbeClientCtpEntry 41 }

gbeClientCtpRxMacFragmentDayTce  OBJECT-TYPE
    SYNTAX     Integer32
    MAX-ACCESS read-write
    STATUS     current
    DESCRIPTION
        "Count of number of fragment packets found by the media access control
         layer in 24 hours."
    ::= { gbeClientCtpEntry 42 }

gbeClientCtpRxMacCrcAlignedDayTce  OBJECT-TYPE
    SYNTAX     Integer32
    MAX-ACCESS read-write
    STATUS     current
    DESCRIPTION
        "Count of number of CRC align errors found by the media access control
         layer in 24 hours."
    ::= { gbeClientCtpEntry 43 }

gbeClientCtpRxMacUndersizedDayTce  OBJECT-TYPE
    SYNTAX     Integer32
    MAX-ACCESS read-write
    STATUS     current
    DESCRIPTION
        "Count of number of undersize packet errors found by the media access
         control layer in 24 hours."
    ::= { gbeClientCtpEntry 44 }

gbeClientCtpRxMacOversizeDayTce  OBJECT-TYPE
    SYNTAX     Integer32
    MAX-ACCESS read-write
    STATUS     current
    DESCRIPTION
        "Count of number of oversize packet errors found by the media access
         control layer in 24 hours."
    ::= { gbeClientCtpEntry 45 }

gbeClientCtpRxSize64DayTce  OBJECT-TYPE
    SYNTAX     Integer32
    MAX-ACCESS read-write
    STATUS     current
    DESCRIPTION
        "The total number of packets (including bad packets) received that
        were 64 octets in length (excluding framing bits but including FCS
        octets) in 24 hours."
    ::= { gbeClientCtpEntry 46 }

gbeClientCtpRxSize65to127DayTce  OBJECT-TYPE
    SYNTAX     Integer32
    MAX-ACCESS read-write
    STATUS     current
    DESCRIPTION
        "The total number of packets (including bad packets) received that
        were between 65 and 127 octets in length inclusive (excluding framing
        bits but including FCS octets) in 24 hours."
    ::= { gbeClientCtpEntry 47 }

gbeClientCtpRxSize128to255DayTce  OBJECT-TYPE
    SYNTAX     Integer32
    MAX-ACCESS read-write
    STATUS     current
    DESCRIPTION
        "The total number of packets(including bad packets)received that were
         between 128 and 255 octets in length inclusive (excluding framingbits
         but including FCS octets) in 24 hours."
    ::= { gbeClientCtpEntry 48 }

gbeClientCtpRxSize256to511DayTce  OBJECT-TYPE
    SYNTAX     Integer32
    MAX-ACCESS read-write
    STATUS     current
    DESCRIPTION
        "The total number of packets(including bad packets)received that were
        between 256 and 511 octets in length inclusive (excluding framing bits
        but including FCS octets) in 24 hours."
    ::= { gbeClientCtpEntry 49 }

gbeClientCtpRxSize512to1023DayTce  OBJECT-TYPE
    SYNTAX     Integer32
    MAX-ACCESS read-write
    STATUS     current
    DESCRIPTION
        "The total number of packets(including bad packets) received that
        were between 512 and 1023 octets in length inclusive (excluding framing
        bits but including FCS octets)  in 24 hours."
    ::= { gbeClientCtpEntry 50 }

gbeClientCtpRxSize1024to1518DayTce  OBJECT-TYPE
    SYNTAX     Integer32
    MAX-ACCESS read-write
    STATUS     current
    DESCRIPTION
        "The total number of packets (including bad packets) received that were
         between 1024 and 1518 octets in length inclusive (excluding framing bits
         but including FCS octets) in 24 hours."
    ::= { gbeClientCtpEntry 51 }

gbeClientCtpRxSize1519toJumboDayTce  OBJECT-TYPE
    SYNTAX     Integer32
    MAX-ACCESS read-write
    STATUS     current
    DESCRIPTION
        "The total number of packets (including bad packets) received that were
         between 1519 and Jumbo octets in length inclusive (excluding framing
         bits but including FCS octets) in 24 hours."
    ::= { gbeClientCtpEntry 52 }

gbeClientCtpRxPacketsDayTce  OBJECT-TYPE
    SYNTAX     Integer32
    MAX-ACCESS read-write
    STATUS     current
    DESCRIPTION
        "Received packers in 24 hours."
    ::= { gbeClientCtpEntry 53 }

gbeClientCtpRxOctetsDayTce  OBJECT-TYPE
    SYNTAX     Integer32
    MAX-ACCESS read-write
    STATUS     current
    DESCRIPTION
        "The total number of octets of data (including those in bad packets)
        received on the network (excluding framing bits but including FCS
        octets) in 24 hours."
    ::= { gbeClientCtpEntry 54 }

gbeClientCtpRxBroadcastPktsDayTce  OBJECT-TYPE
    SYNTAX     Integer32
    MAX-ACCESS read-write
    STATUS     current
    DESCRIPTION
        "The total number of good packets received that were directed to the
        broadcast address in 24 hours. This does not include multicast packets."
    ::= { gbeClientCtpEntry 55 }

gbeClientCtpRxMulticastPktsDayTce  OBJECT-TYPE
    SYNTAX     Integer32
    MAX-ACCESS read-write
    STATUS     current
    DESCRIPTION
        "The total number of good packets received that were directed to a
        multicast address in 24 hours. This number does not include packets
        directed to the broadcast address."
    ::= { gbeClientCtpEntry 56 }

gbeClientCtpRxInPauseFramesDayTce  OBJECT-TYPE
    SYNTAX     Integer32
    MAX-ACCESS read-write
    STATUS     current
    DESCRIPTION
        "A count of MAC Control frames received on this interface with an
        opcode indicating the PAUSE operation. This counter does not increment
        when the interface is operating in half-duplex mode in 24 hours."
    ::= { gbeClientCtpEntry 57 }

gbeClientCtpTxPcsICG15MinTce  OBJECT-TYPE
    SYNTAX     Integer32
    MAX-ACCESS read-write
    STATUS     current
    DESCRIPTION
        "Count of the Invalid Code Group detected by the Physical Coding
        Sublayer(PCS) in 15 minutes."
    ::= { gbeClientCtpEntry 58 }

gbeClientCtpTxPcsES15MinTce  OBJECT-TYPE
    SYNTAX     Integer32
    MAX-ACCESS read-write
    STATUS     current
    DESCRIPTION
        "Count of the errored seconds detected by the Physical Coding Sublayer
        (PCS) in 15 minutes."
    ::= { gbeClientCtpEntry 59 }

gbeClientCtpTxPcsSES15MinTce  OBJECT-TYPE
    SYNTAX     Integer32
    MAX-ACCESS read-write
    STATUS     current
    DESCRIPTION
        "Count of the severely errored seconds detected by the Physical Coding
        Sublayer(PCS) in 15 minutes."
    ::= { gbeClientCtpEntry 60 }

gbeClientCtpTxPcsSESS15MinTce  OBJECT-TYPE
    SYNTAX     Integer32
    MAX-ACCESS read-write
    STATUS     current
    DESCRIPTION
        "Count of the Severely Errored Sync Seconds detected by the Physical
        Coding Sublayer(PCS) in 15 minutes."
    ::= { gbeClientCtpEntry 61 }

gbeClientCtpTxPcsICGDayTce  OBJECT-TYPE
    SYNTAX     Integer32
    MAX-ACCESS read-write
    STATUS     current
    DESCRIPTION
        "Count of the Invalid Code Group detected by the Physical Coding
        Sublayer(PCS) in 24 hours."
    ::= { gbeClientCtpEntry 62 }

gbeClientCtpTxPcsESDayTce  OBJECT-TYPE
    SYNTAX     Integer32
    MAX-ACCESS read-write
    STATUS     current
    DESCRIPTION
        "Count of the errored seconds detected by the Physical Coding
        Sublayer(PCS) in 24 hours."
    ::= { gbeClientCtpEntry 63 }

gbeClientCtpTxPcsSESDayTce  OBJECT-TYPE
    SYNTAX     Integer32
    MAX-ACCESS read-write
    STATUS     current
    DESCRIPTION
        "Count of the severely errored seconds detected by the Physical Coding
        Sublayer(PCS) in 24 hours."
    ::= { gbeClientCtpEntry 64 }

gbeClientCtpTxPcsSESSDayTce  OBJECT-TYPE
    SYNTAX     Integer32
    MAX-ACCESS read-write
    STATUS     current
    DESCRIPTION
        "Count of the Severely Errored Sync Seconds detected by the Physical Coding
         Sublayer(PCS) in 24 hours."
    ::= { gbeClientCtpEntry 65 }

gbeClientCtpTxMacJS15MinTce  OBJECT-TYPE
    SYNTAX     Integer32
    MAX-ACCESS read-write
    STATUS     current
    DESCRIPTION
        "Count of number of jabber seconds found by the media access control
        layer in 15 minutes."
    ::= { gbeClientCtpEntry 66 }

gbeClientCtpTxMacSES15MinTce  OBJECT-TYPE
    SYNTAX     Integer32
    MAX-ACCESS read-write
    STATUS     current
    DESCRIPTION
        "Count of number of severely errored seconds found by the media access
         control layer in 15 minutes."
    ::= { gbeClientCtpEntry 67 }

gbeClientCtpTxMacErrOctet15MinTce  OBJECT-TYPE
    SYNTAX     Integer32
    MAX-ACCESS read-write
    STATUS     current
    DESCRIPTION
        "Count of number of errored octets found by the media access control
        layer in 15 minutes."
    ::= { gbeClientCtpEntry 68 }

gbeClientCtpTxMacJabber15MinTce  OBJECT-TYPE
    SYNTAX     Integer32
    MAX-ACCESS read-write
    STATUS     current
    DESCRIPTION
        "Count of number of jabbers found by the media access control
         layer in 15 minutes."
    ::= { gbeClientCtpEntry 69 }

gbeClientCtpTxMacFragment15MinTce  OBJECT-TYPE
    SYNTAX     Integer32
    MAX-ACCESS read-write
    STATUS     current
    DESCRIPTION
        "Count of number of fragment packets found by the media access
        control layer in 15 minutes."
    ::= { gbeClientCtpEntry 70 }

gbeClientCtpTxMacCrcAligned15MinTce  OBJECT-TYPE
    SYNTAX     Integer32
    MAX-ACCESS read-write
    STATUS     current
    DESCRIPTION
        "Count of number of CRC align errors found by the media access
        control layer in 15 minutes."
    ::= { gbeClientCtpEntry 71 }

gbeClientCtpTxMacUndersized15MinTce  OBJECT-TYPE
    SYNTAX     Integer32
    MAX-ACCESS read-write
    STATUS     current
    DESCRIPTION
        "Count of number of undersize packet errors found by the media
         access control layer in 15 minutes."
    ::= { gbeClientCtpEntry 72 }

gbeClientCtpTxMacOversize15MinTce  OBJECT-TYPE
    SYNTAX     Integer32
    MAX-ACCESS read-write
    STATUS     current
    DESCRIPTION
        "Count of number of oversize packet errors found by the media access
         control layer in 15 minutes."
    ::= { gbeClientCtpEntry 73 }

gbeClientCtpTxSize64P15MinTce  OBJECT-TYPE
    SYNTAX     Integer32
    MAX-ACCESS read-write
    STATUS     current
    DESCRIPTION
        "The total number of packets (including bad packets) received that
         were 64 octets in length (excluding framing bits but including
         FCS octets) in 15 minutes."
    ::= { gbeClientCtpEntry 74 }

gbeClientCtpTxSize65to127P15MinTce  OBJECT-TYPE
    SYNTAX     Integer32
    MAX-ACCESS read-write
    STATUS     current
    DESCRIPTION
        "The total number of packets (including bad packets) received that
         were between 65 and 127 octets in length inclusive (excluding framing
         bits but including FCS octets) in 15 minutes."
    ::= { gbeClientCtpEntry 75 }

gbeClientCtpTxSize128to255P15MinTce  OBJECT-TYPE
    SYNTAX     Integer32
    MAX-ACCESS read-write
    STATUS     current
    DESCRIPTION
        "The total number of packets(including bad packets)received that were
         between 128 and 255 octets in length inclusive (excluding framingbits
         but including FCS octets) in 15 minutes."
    ::= { gbeClientCtpEntry 76 }

gbeClientCtpTxSize256to511P15MinTce  OBJECT-TYPE
    SYNTAX     Integer32
    MAX-ACCESS read-write
    STATUS     current
    DESCRIPTION
        "The total number of packets(including bad packets)received that were
         between 256 and 511 octets in length inclusive (excluding framing bits
         but including FCS octets) in 15 minutes."
    ::= { gbeClientCtpEntry 77 }

gbeClientCtpTxSize512to1023P15MinTce  OBJECT-TYPE
    SYNTAX     Integer32
    MAX-ACCESS read-write
    STATUS     current
    DESCRIPTION
        "The total number of packets(including bad packets) received that were
         between 512 and 1023 octets in length inclusive (excluding framing bits
         but including FCS octets)  in 15 minutes."
    ::= { gbeClientCtpEntry 78 }

gbeClientCtpTxSize1024to1518P15MinTce  OBJECT-TYPE
    SYNTAX     Integer32
    MAX-ACCESS read-write
    STATUS     current
    DESCRIPTION
        "The total number of packets (including bad packets) received that were
         between 1024 and 1518 octets in length inclusive (excluding framing bits
         but including FCS octets) in 15 minutes."
    ::= { gbeClientCtpEntry 79 }

gbeClientCtpTxSize1519toJumboP15MinTce  OBJECT-TYPE
    SYNTAX     Integer32
    MAX-ACCESS read-write
    STATUS     current
    DESCRIPTION
        "The total number of packets (including bad packets)  received that
         were between 1519 and Jumbo octets in length inclusive (excluding
         framing bits but including FCS octets) in 15 minutes.
        "
    ::= { gbeClientCtpEntry 80 }

gbeClientCtpTxPackets15MinTce  OBJECT-TYPE
    SYNTAX     Integer32
    MAX-ACCESS read-write
    STATUS     current
    DESCRIPTION
        "Transmitted packets in 15 minutes."
    ::= { gbeClientCtpEntry 81 }

gbeClientCtpTxOctets15MinTce  OBJECT-TYPE
    SYNTAX     Integer32
    MAX-ACCESS read-write
    STATUS     current
    DESCRIPTION
        "The total number of octets of data (including those in bad packets)
        received on the net work (excluding framing bits but including FCS
        octets) in 15 minutes."
    ::= { gbeClientCtpEntry 82 }

gbeClientCtpTxBroadcastPkts15MinTce  OBJECT-TYPE
    SYNTAX     Integer32
    MAX-ACCESS read-write
    STATUS     current
    DESCRIPTION
        "The total number of good packets received that were directed to the
        broadcast address in 15 minutes. This does not include multicast packets"
    ::= { gbeClientCtpEntry 83 }

gbeClientCtpTxMulticastPkts15MinTce  OBJECT-TYPE
    SYNTAX     Integer32
    MAX-ACCESS read-write
    STATUS     current
    DESCRIPTION
        "The total number of good packets received that were directed to a
        multicast address. This number does not include packets directed to
        the broadcast address."
    ::= { gbeClientCtpEntry 84 }

gbeClientCtpTxOutPauseFrames15MinTce  OBJECT-TYPE
    SYNTAX     Integer32
    MAX-ACCESS read-write
    STATUS     current
    DESCRIPTION
        "A count of MAC Control frames received on this interface with an
        opcode indicating the PAUSE operation. This counter does not increment
        when the interface is operating in half-duplex mode in 15 minutes."
    ::= { gbeClientCtpEntry 85 }

gbeClientCtpTxMacJSDayTce  OBJECT-TYPE
    SYNTAX     Integer32
    MAX-ACCESS read-write
    STATUS     current
    DESCRIPTION
        "Count of number of jabber seconds found by the media access control
        layer in 24 hours."
    ::= { gbeClientCtpEntry 86 }

gbeClientCtpTxMacSESDayTce  OBJECT-TYPE
    SYNTAX     Integer32
    MAX-ACCESS read-write
    STATUS     current
    DESCRIPTION
        "Count of number of severely errored seconds found by the media access
         control layer in 24 hours."
    ::= { gbeClientCtpEntry 87 }

gbeClientCtpTxMacErrOctetDayTce  OBJECT-TYPE
    SYNTAX     Integer32
    MAX-ACCESS read-write
    STATUS     current
    DESCRIPTION
        "Count of number of errored octets found by the media access control
        layer in 24 hours."
    ::= { gbeClientCtpEntry 88 }

gbeClientCtpTxMacJabberDayTce  OBJECT-TYPE
    SYNTAX     Integer32
    MAX-ACCESS read-write
    STATUS     current
    DESCRIPTION
        "Count of number of jabbers found by the media access control layer in 24 hours."
    ::= { gbeClientCtpEntry 89 }

gbeClientCtpTxMacFragmentDayTce  OBJECT-TYPE
    SYNTAX     Integer32
    MAX-ACCESS read-write
    STATUS     current
    DESCRIPTION
        "Count of number of fragment packets found by the media access control
        layer in 24 hours."
    ::= { gbeClientCtpEntry 90 }

gbeClientCtpTxMacCrcAlignedDayTce  OBJECT-TYPE
    SYNTAX     Integer32
    MAX-ACCESS read-write
    STATUS     current
    DESCRIPTION
        "Count of number of CRC align errors found by the media access control
        layer in 24 hours."
    ::= { gbeClientCtpEntry 91 }

gbeClientCtpTxMacUndersizedDayTce  OBJECT-TYPE
    SYNTAX     Integer32
    MAX-ACCESS read-write
    STATUS     current
    DESCRIPTION
        "Count of number of undersize packet errors found by the media access
        control layer in 24 hours."
    ::= { gbeClientCtpEntry 92 }

gbeClientCtpTxMacOversizeDayTce  OBJECT-TYPE
    SYNTAX     Integer32
    MAX-ACCESS read-write
    STATUS     current
    DESCRIPTION
        "Count of number of oversize packet errors found by the media access
        control layer in 24 hours."
    ::= { gbeClientCtpEntry 93 }

gbeClientCtpTxSize64DayTce  OBJECT-TYPE
    SYNTAX     Integer32
    MAX-ACCESS read-write
    STATUS     current
    DESCRIPTION
        "The total number of packets (including bad packets) received that were
         64 octets in length (excluding framing bits but including FCS octets)
         in 24 hours."
    ::= { gbeClientCtpEntry 94 }

gbeClientCtpTxSize65to127DayTce  OBJECT-TYPE
    SYNTAX     Integer32
    MAX-ACCESS read-write
    STATUS     current
    DESCRIPTION
        "The total number of packets (including bad packets) received that were
         between 65 and 127 octets in length inclusive (excluding framing bits
         but including FCS octets) in 24 hours."
    ::= { gbeClientCtpEntry 95 }

gbeClientCtpTxSize128to255DayTce  OBJECT-TYPE
    SYNTAX     Integer32
    MAX-ACCESS read-write
    STATUS     current
    DESCRIPTION
        "The total number of packets(including bad packets)received that were
        between 128 and 255 octets in length inclusive (excluding framingbits
        but including FCS octets) in 24 hours."
    ::= { gbeClientCtpEntry 96 }

gbeClientCtpTxSize256to511DayTce  OBJECT-TYPE
    SYNTAX     Integer32
    MAX-ACCESS read-write
    STATUS     current
    DESCRIPTION
        "The total number of packets(including bad packets)received that were
        between 256 and 511 octets in length inclusive (excluding framing bits
        but including FCS octets) in 24 hours."
    ::= { gbeClientCtpEntry 97 }

gbeClientCtpTxSize512to1023DayTce  OBJECT-TYPE
    SYNTAX     Integer32
    MAX-ACCESS read-write
    STATUS     current
    DESCRIPTION
        "The total number of packets (including bad packets) received that were
         between 512 and 1023 octets in length inclusive (excluding framing bits
         but including FCS octets) in 24 hours."
    ::= { gbeClientCtpEntry 98 }

gbeClientCtpTxSize1024to1518DayTce  OBJECT-TYPE
    SYNTAX     Integer32
    MAX-ACCESS read-write
    STATUS     current
    DESCRIPTION
        "The total number of packets (including bad packets) received that were
         between 1024 and 1518 octets in length inclusive (excluding framing bits
         but including FCS octets) in 24 hours."
    ::= { gbeClientCtpEntry 99 }

gbeClientCtpTxSize1519toJumboDayTce  OBJECT-TYPE
    SYNTAX     Integer32
    MAX-ACCESS read-write
    STATUS     current
    DESCRIPTION
        "The total number of packets (including bad packets) received that were
         between 1519 and Jumbo octets in length inclusive (excluding framing
         bits but including FCS octets) in 24 hours."
    ::= { gbeClientCtpEntry 100 }

gbeClientCtpTxPacketsDayTce  OBJECT-TYPE
    SYNTAX     Integer32
    MAX-ACCESS read-write
    STATUS     current
    DESCRIPTION
        "Tramitted packets in 24 hours."
    ::= { gbeClientCtpEntry 101 }

gbeClientCtpTxOctetsDayTce  OBJECT-TYPE
    SYNTAX     Integer32
    MAX-ACCESS read-write
    STATUS     current
    DESCRIPTION
        "The total number of octets of data (including those in bad packets)
        received on the net work (excluding framing bits but including FCS
        octets) in 24 hours."
    ::= { gbeClientCtpEntry 102 }

gbeClientCtpTxBroadcastPktsDayTce  OBJECT-TYPE
    SYNTAX     Integer32
    MAX-ACCESS read-write
    STATUS     current
    DESCRIPTION
        "The total number of good packets received that were directed to the
        broadcast address in 24 hours. This does not include multicast packets."
    ::= { gbeClientCtpEntry 103 }

gbeClientCtpTxMulticastPktsDayTce  OBJECT-TYPE
    SYNTAX     Integer32
    MAX-ACCESS read-write
    STATUS     current
    DESCRIPTION
        "The total number of good packets received that were directed to a
        multicast address in 24 hours. This number does not include packets
        directed to the broadcast address."
    ::= { gbeClientCtpEntry 104 }

gbeClientCtpTxOutPauseFramesDayTce  OBJECT-TYPE
    SYNTAX     Integer32
    MAX-ACCESS read-write
    STATUS     current
    DESCRIPTION
        "A count of MAC Control frames received on this interface with an
        opcode indicating the PAUSE operation. This counter does not increment
         when the interface is operating in half-duplex mode in 24 hours."
    ::= { gbeClientCtpEntry 105 }

gbeClientCtpRxPcsICG15MinTceRept  OBJECT-TYPE
    SYNTAX     TruthValue
    MAX-ACCESS read-write
    STATUS     current
    DESCRIPTION
        "Flag that enables the reporting of the RxPcsICG15MinTce threshold crossing."
    ::= { gbeClientCtpEntry 106 }

gbeClientCtpRxPcsES15MinTceRept  OBJECT-TYPE
    SYNTAX     TruthValue
    MAX-ACCESS read-write
    STATUS     current
    DESCRIPTION
        "Flag that enables the reporting of the RxPcsES15MinTce threshold crossing."
    ::= { gbeClientCtpEntry 107 }

gbeClientCtpRxPcsSES15MinTceRept  OBJECT-TYPE
    SYNTAX     TruthValue
    MAX-ACCESS read-write
    STATUS     current
    DESCRIPTION
        "Flag that enables the reporting of the RxPcsSES15MinTce threshold crossing."
    ::= { gbeClientCtpEntry 108 }

gbeClientCtpRxPcsSESS15MinTceRept  OBJECT-TYPE
    SYNTAX     TruthValue
    MAX-ACCESS read-write
    STATUS     current
    DESCRIPTION
        "Flag that enables the reporting of the RxPcsSESS15MinTce threshold crossing."
    ::= { gbeClientCtpEntry 109 }

gbeClientCtpRxPcsICGDayTceRept  OBJECT-TYPE
    SYNTAX     TruthValue
    MAX-ACCESS read-write
    STATUS     current
    DESCRIPTION
        "Flag that enables the reporting of the RxPcsICGDayTce threshold crossing."
    ::= { gbeClientCtpEntry 110 }

gbeClientCtpRxPcsESDayTceRept  OBJECT-TYPE
    SYNTAX     TruthValue
    MAX-ACCESS read-write
    STATUS     current
    DESCRIPTION
        "Flag that enables the reporting of the RxPcsESDayTce threshold crossing."
    ::= { gbeClientCtpEntry 111 }

gbeClientCtpRxPcsSESDayTceRept  OBJECT-TYPE
    SYNTAX     TruthValue
    MAX-ACCESS read-write
    STATUS     current
    DESCRIPTION
        "Flag that enables the reporting of the RxPcsSESDayTce threshold crossing."
    ::= { gbeClientCtpEntry 112 }

gbeClientCtpRxPcsSESSDayTceRept  OBJECT-TYPE
    SYNTAX     TruthValue
    MAX-ACCESS read-write
    STATUS     current
    DESCRIPTION
        "Flag that enables the reporting of the RxPcsSESSDayTce  threshold crossing."
    ::= { gbeClientCtpEntry 113 }

gbeClientCtpRxMacJS15MinTceRept  OBJECT-TYPE
    SYNTAX     TruthValue
    MAX-ACCESS read-write
    STATUS     current
    DESCRIPTION
        "Flag that enables the reporting of the RxMacJS15MinTce  threshold crossing."
    ::= { gbeClientCtpEntry 114 }

gbeClientCtpRxMacSES15MinTceRept  OBJECT-TYPE
    SYNTAX     TruthValue
    MAX-ACCESS read-write
    STATUS     current
    DESCRIPTION
        "Flag that enables the reporting of the RxMacSES15MinTce  threshold crossing."
    ::= { gbeClientCtpEntry 115 }

gbeClientCtpRxMacErrOctet15MinTceRept  OBJECT-TYPE
    SYNTAX     TruthValue
    MAX-ACCESS read-write
    STATUS     current
    DESCRIPTION
        "Flag that enables the reporting of the RxMacErrOctet15MinTce threshold crossing."
    ::= { gbeClientCtpEntry 116 }

gbeClientCtpRxMacJabber15MinTceRept  OBJECT-TYPE
    SYNTAX     TruthValue
    MAX-ACCESS read-write
    STATUS     current
    DESCRIPTION
        "Flag that enables the reporting of the RxMacJabber15MinTce threshold crossing."
    ::= { gbeClientCtpEntry 117 }

gbeClientCtpRxMacFragment15MinTceRept  OBJECT-TYPE
    SYNTAX     TruthValue
    MAX-ACCESS read-write
    STATUS     current
    DESCRIPTION
        "Flag that enables the reporting of the RxMacFragment15MinTce threshold crossing."
    ::= { gbeClientCtpEntry 118 }

gbeClientCtpRxMacCrcAligned15MinTceRept  OBJECT-TYPE
    SYNTAX     TruthValue
    MAX-ACCESS read-write
    STATUS     current
    DESCRIPTION
        "Flag that enables the reporting of the RxMacCrcAligned15MinTce threshold crossing."
    ::= { gbeClientCtpEntry 119 }

gbeClientCtpRxMacUndersized15MinTceRept  OBJECT-TYPE
    SYNTAX     TruthValue
    MAX-ACCESS read-write
    STATUS     current
    DESCRIPTION
        "Flag that enables the reporting of the RxMacUndersized15MinTce threshold."
    ::= { gbeClientCtpEntry 120 }

gbeClientCtpRxMacOversize15MinTceRept  OBJECT-TYPE
    SYNTAX     TruthValue
    MAX-ACCESS read-write
    STATUS     current
    DESCRIPTION
        "Flag that enables the reporting of the RxMacOversize15MinTce threshold crossing."
    ::= { gbeClientCtpEntry 121 }

gbeClientCtpRxSize64P15MinTceRept  OBJECT-TYPE
    SYNTAX     TruthValue
    MAX-ACCESS read-write
    STATUS     current
    DESCRIPTION
        "Flag that enables the reporting of the RxSize64_15MinTce threshold crossing."
    ::= { gbeClientCtpEntry 122 }

gbeClientCtpRxSize65to127P15MinTceRept  OBJECT-TYPE
    SYNTAX     TruthValue
    MAX-ACCESS read-write
    STATUS     current
    DESCRIPTION
        "Flag that enables the reporting of the RxSize65to127_15MinTce threshold."
    ::= { gbeClientCtpEntry 123 }

gbeClientCtpRxSize128to255P15MinTceRept  OBJECT-TYPE
    SYNTAX     TruthValue
    MAX-ACCESS read-write
    STATUS     current
    DESCRIPTION
        "Flag that enables the reporting of the RxSize128to255_15MinTc threshold."
    ::= { gbeClientCtpEntry 124 }

gbeClientCtpRxSize256to511P15MinTceRept  OBJECT-TYPE
    SYNTAX     TruthValue
    MAX-ACCESS read-write
    STATUS     current
    DESCRIPTION
        "Flag that enables the reporting of the RxSize256to511_15MinTce threshold."
    ::= { gbeClientCtpEntry 125 }

gbeClientCtpRxSize512to1023P15MinTceRept  OBJECT-TYPE
    SYNTAX     TruthValue
    MAX-ACCESS read-write
    STATUS     current
    DESCRIPTION
        "Flag that enables the reporting of the RxSize512to1023_15MinTce threshold."
    ::= { gbeClientCtpEntry 126 }

gbeClientCtpRxSize1024to1518P15MinTceRept  OBJECT-TYPE
    SYNTAX     TruthValue
    MAX-ACCESS read-write
    STATUS     current
    DESCRIPTION
        "Flag that enables the reporting of RxSize1024to1518P15Min threshold."
    ::= { gbeClientCtpEntry 127 }

gbeClientCtpRxSize1519toJumboP15MinTceRept  OBJECT-TYPE
    SYNTAX     TruthValue
    MAX-ACCESS read-write
    STATUS     current
    DESCRIPTION
        "Flag that enables the reporting of RxSize1519toJumboP15Min threshold."
    ::= { gbeClientCtpEntry 128 }

gbeClientCtpRxPackets15MinTceRept  OBJECT-TYPE
    SYNTAX     TruthValue
    MAX-ACCESS read-write
    STATUS     current
    DESCRIPTION
        "Flag that enables the reporting of the CtpRxPackets15MinTce threshold"
    ::= { gbeClientCtpEntry 129 }

gbeClientCtpRxOctets15MinTceRept  OBJECT-TYPE
    SYNTAX     TruthValue
    MAX-ACCESS read-write
    STATUS     current
    DESCRIPTION
        "Flag that enables the reporting of the RxOctets15MinTce threshold."
    ::= { gbeClientCtpEntry 130 }

gbeClientCtpRxBroadcastPkts15MinTceRept  OBJECT-TYPE
    SYNTAX     TruthValue
    MAX-ACCESS read-write
    STATUS     current
    DESCRIPTION
        "Flag that enables the reporting of the RxBroadcastPkts15MinTce threshold."
    ::= { gbeClientCtpEntry 131 }

gbeClientCtpRxMulticastPkts15MinTceRept  OBJECT-TYPE
    SYNTAX     TruthValue
    MAX-ACCESS read-write
    STATUS     current
    DESCRIPTION
        "Flag that enables the reporting of the RxMulticastPkts15MinTce threshold."
    ::= { gbeClientCtpEntry 132 }

gbeClientCtpRxInPauseFrames15MinTceRept  OBJECT-TYPE
    SYNTAX     TruthValue
    MAX-ACCESS read-write
    STATUS     current
    DESCRIPTION
        "Flag that enables the reporting of the RxInPauseFrames15MinTce threshold."
    ::= { gbeClientCtpEntry 133 }

gbeClientCtpRxMacJSDayTceRept  OBJECT-TYPE
    SYNTAX     TruthValue
    MAX-ACCESS read-write
    STATUS     current
    DESCRIPTION
        "Flag that enables the reporting of the RxMacJSDayTce threshold crossing."
    ::= { gbeClientCtpEntry 134 }

gbeClientCtpRxMacSESDayTceRept  OBJECT-TYPE
    SYNTAX     TruthValue
    MAX-ACCESS read-write
    STATUS     current
    DESCRIPTION
        "Flag that enables the reporting of the RxMacSESDayTce threshold crossing."
    ::= { gbeClientCtpEntry 135 }

gbeClientCtpRxMacErrOctetDayTceRept  OBJECT-TYPE
    SYNTAX     TruthValue
    MAX-ACCESS read-write
    STATUS     current
    DESCRIPTION
        "Flag that enables the reporting of the RxMacErrOctetDayTce threshold crossing."
    ::= { gbeClientCtpEntry 136 }

gbeClientCtpRxMacJabberDayTceRept  OBJECT-TYPE
    SYNTAX     TruthValue
    MAX-ACCESS read-write
    STATUS     current
    DESCRIPTION
        "Flag that enables the reporting of the RxMacJabberDayTce threshold crossing."
    ::= { gbeClientCtpEntry 137 }

gbeClientCtpRxMacFragmentDayTceRept  OBJECT-TYPE
    SYNTAX     TruthValue
    MAX-ACCESS read-write
    STATUS     current
    DESCRIPTION
        "Flag that enables the reporting of the RxMacFragmentDayTce threshold crossing."
    ::= { gbeClientCtpEntry 138 }

gbeClientCtpRxMacCrcAlignedDayTceRept  OBJECT-TYPE
    SYNTAX     TruthValue
    MAX-ACCESS read-write
    STATUS     current
    DESCRIPTION
        "Flag that enables the reporting of the RxMacCrcAlignedDayTce threshold crossing."
    ::= { gbeClientCtpEntry 139 }

gbeClientCtpRxMacUndersizedDayTceRept  OBJECT-TYPE
    SYNTAX     TruthValue
    MAX-ACCESS read-write
    STATUS     current
    DESCRIPTION
        "Flag that enables the reporting of the RxMacUndersizedDayTce threshold crossing"
    ::= { gbeClientCtpEntry 140 }

gbeClientCtpRxMacOversizeDayTceRept  OBJECT-TYPE
    SYNTAX     TruthValue
    MAX-ACCESS read-write
    STATUS     current
    DESCRIPTION
        "Flag that enables the reporting of the RxMacOversizeDayTce threshold crossing."
    ::= { gbeClientCtpEntry 141 }

gbeClientCtpRxSize64DayTceRept  OBJECT-TYPE
    SYNTAX     TruthValue
    MAX-ACCESS read-write
    STATUS     current
    DESCRIPTION
        "Flag that enables the reporting of the RxSize64_DayTce threshold."
    ::= { gbeClientCtpEntry 142 }

gbeClientCtpRxSize65to127DayTceRept  OBJECT-TYPE
    SYNTAX     TruthValue
    MAX-ACCESS read-write
    STATUS     current
    DESCRIPTION
        "Flag that enables the reporting of the RxSize65to127_DayTce threshold."
    ::= { gbeClientCtpEntry 143 }

gbeClientCtpRxSize128to255DayTceRept  OBJECT-TYPE
    SYNTAX     TruthValue
    MAX-ACCESS read-write
    STATUS     current
    DESCRIPTION
        "Flag that enables the reporting of the RxSize128to255_DayTce threshold."
    ::= { gbeClientCtpEntry 144 }

gbeClientCtpRxSize256to511DayTceRept  OBJECT-TYPE
    SYNTAX     TruthValue
    MAX-ACCESS read-write
    STATUS     current
    DESCRIPTION
        "Flag that enables the reporting of the RxSize256to511_DayTce threshold."
    ::= { gbeClientCtpEntry 145 }

gbeClientCtpRxSize512to1023DayTceRept  OBJECT-TYPE
    SYNTAX     TruthValue
    MAX-ACCESS read-write
    STATUS     current
    DESCRIPTION
        "Flag that enables the reporting of the RxSize512to1023_DayTce threshold."
    ::= { gbeClientCtpEntry 146 }

gbeClientCtpRxSize1024to1518DayTceRept  OBJECT-TYPE
    SYNTAX     TruthValue
    MAX-ACCESS read-write
    STATUS     current
    DESCRIPTION
        "Flag that enables the reporting of the TxSize1024to1518_15MinTce threshold."
    ::= { gbeClientCtpEntry 147 }

gbeClientCtpRxSize1519toJumboDayTceRept  OBJECT-TYPE
    SYNTAX     TruthValue
    MAX-ACCESS read-write
    STATUS     current
    DESCRIPTION
        "Flag that enables the reporting of the TxSize1519toJumbo_DayTce threshold."
    ::= { gbeClientCtpEntry 148 }

gbeClientCtpRxPacketsDayTceRept  OBJECT-TYPE
    SYNTAX     TruthValue
    MAX-ACCESS read-write
    STATUS     current
    DESCRIPTION
        "Flag that enables the reporting of the CtpRxPacketsDayTce threshold."
    ::= { gbeClientCtpEntry 149 }

gbeClientCtpRxOctetsDayTceRept  OBJECT-TYPE
    SYNTAX     TruthValue
    MAX-ACCESS read-write
    STATUS     current
    DESCRIPTION
        "Flag that enables the reporting of the RxOctetsDayTce threshold."
    ::= { gbeClientCtpEntry 150 }

gbeClientCtpRxBroadcastPktsDayTceRept  OBJECT-TYPE
    SYNTAX     TruthValue
    MAX-ACCESS read-write
    STATUS     current
    DESCRIPTION
        "Flag that enables the reporting of the RxBroadcastPktsDayTce threshold."
    ::= { gbeClientCtpEntry 151 }

gbeClientCtpRxMulticastPktsDayTceRept  OBJECT-TYPE
    SYNTAX     TruthValue
    MAX-ACCESS read-write
    STATUS     current
    DESCRIPTION
        "Flag that enables the reporting of theRxMulticastPktsDayTce threshold."
    ::= { gbeClientCtpEntry 152 }

gbeClientCtpRxInPauseFramesDayTceRept  OBJECT-TYPE
    SYNTAX     TruthValue
    MAX-ACCESS read-write
    STATUS     current
    DESCRIPTION
        "Flag that enables the reporting of the RxInPauseFramesDayTce threshold."
    ::= { gbeClientCtpEntry 153 }

gbeClientCtpTxPcsICG15MinTceRept  OBJECT-TYPE
    SYNTAX     TruthValue
    MAX-ACCESS read-write
    STATUS     current
    DESCRIPTION
        "Flag that enables the reporting of the TxPcsICG15MinTce threshold crossing."
    ::= { gbeClientCtpEntry 154 }

gbeClientCtpTxPcsES15MinTceRept  OBJECT-TYPE
    SYNTAX     TruthValue
    MAX-ACCESS read-write
    STATUS     current
    DESCRIPTION
        "Flag that enables the reporting of the TxPcsES15MinTce threshold crossing."
    ::= { gbeClientCtpEntry 155 }

gbeClientCtpTxPcsSES15MinTceRept  OBJECT-TYPE
    SYNTAX     TruthValue
    MAX-ACCESS read-write
    STATUS     current
    DESCRIPTION
        "Flag that enables the reporting of the TxPcsSES15MinTce threshold crossing."
    ::= { gbeClientCtpEntry 156 }

gbeClientCtpTxPcsSESS15MinTceRept  OBJECT-TYPE
    SYNTAX     TruthValue
    MAX-ACCESS read-write
    STATUS     current
    DESCRIPTION
        "Flag that enables the reporting of the TxPcsSESS15MinTce threshold crossing."
    ::= { gbeClientCtpEntry 157 }

gbeClientCtpTxPcsICGDayTceRept  OBJECT-TYPE
    SYNTAX     TruthValue
    MAX-ACCESS read-write
    STATUS     current
    DESCRIPTION
        "Flag that enables the reporting of the TxPcsICGDayTce threshold crossing."
    ::= { gbeClientCtpEntry 158 }

gbeClientCtpTxPcsESDayTceRept  OBJECT-TYPE
    SYNTAX     TruthValue
    MAX-ACCESS read-write
    STATUS     current
    DESCRIPTION
        "Flag that enables the reporting of the TxPcsESDayTce threshold crossing."
    ::= { gbeClientCtpEntry 159 }

gbeClientCtpTxPcsSESDayTceRept  OBJECT-TYPE
    SYNTAX     TruthValue
    MAX-ACCESS read-write
    STATUS     current
    DESCRIPTION
        "Flag that enables the reporting of the TxPcsSESDayTce threshold crossing."
    ::= { gbeClientCtpEntry 160 }

gbeClientCtpTxPcsSESSDayTceRept  OBJECT-TYPE
    SYNTAX     TruthValue
    MAX-ACCESS read-write
    STATUS     current
    DESCRIPTION
        "Count of the Severely Errored Sync Seconds detected by the Physical Coding Sublayer(PCS) in 24 hours."
    ::= { gbeClientCtpEntry 161 }

gbeClientCtpTxMacJS15MinTceRept  OBJECT-TYPE
    SYNTAX     TruthValue
    MAX-ACCESS read-write
    STATUS     current
    DESCRIPTION
        "Flag that enables the reporting of the TxMacJS15MinTce threshold crossing."
    ::= { gbeClientCtpEntry 162 }

gbeClientCtpTxMacSES15MinTceRept  OBJECT-TYPE
    SYNTAX     TruthValue
    MAX-ACCESS read-write
    STATUS     current
    DESCRIPTION
        "Flag that enables the reporting of the TxMacSES15MinTce threshold crossing."
    ::= { gbeClientCtpEntry 163 }

gbeClientCtpTxMacErrOctet15MinTceRept  OBJECT-TYPE
    SYNTAX     TruthValue
    MAX-ACCESS read-write
    STATUS     current
    DESCRIPTION
        "Flag that enables the reporting of the TxMacErrOctet15MinTce threshold crossing."
    ::= { gbeClientCtpEntry 164 }

gbeClientCtpTxMacJabber15MinTceRept  OBJECT-TYPE
    SYNTAX     TruthValue
    MAX-ACCESS read-write
    STATUS     current
    DESCRIPTION
        "Flag that enables the reporting of the TxMacJabber15MinTce threshold crossing."
    ::= { gbeClientCtpEntry 165 }

gbeClientCtpTxMacFragment15MinTceRept  OBJECT-TYPE
    SYNTAX     TruthValue
    MAX-ACCESS read-write
    STATUS     current
    DESCRIPTION
        "Flag that enables the reporting of the TxMacFragment15MinTce threshold crossing."
    ::= { gbeClientCtpEntry 166 }

gbeClientCtpTxMacCrcAligned15MinTceRept  OBJECT-TYPE
    SYNTAX     TruthValue
    MAX-ACCESS read-write
    STATUS     current
    DESCRIPTION
        "Flag that enables the reporting of the TxMacCrcAligned15MinTce threshold crossing."
    ::= { gbeClientCtpEntry 167 }

gbeClientCtpTxMacUndersized15MinTceRept  OBJECT-TYPE
    SYNTAX     TruthValue
    MAX-ACCESS read-write
    STATUS     current
    DESCRIPTION
        "Flag that enables the reporting of the TxMacUndersized15MinTce threshold crossing."
    ::= { gbeClientCtpEntry 168 }

gbeClientCtpTxMacOversize15MinTceRept  OBJECT-TYPE
    SYNTAX     TruthValue
    MAX-ACCESS read-write
    STATUS     current
    DESCRIPTION
        "Flag that enables the reporting of the TxMacOversize15MinTce threshold."
    ::= { gbeClientCtpEntry 169 }

gbeClientCtpTxSize64P15MinTceRept  OBJECT-TYPE
    SYNTAX     TruthValue
    MAX-ACCESS read-write
    STATUS     current
    DESCRIPTION
        "Flag that enables the reporting of the TxSize64_15MinTce threshold."
    ::= { gbeClientCtpEntry 170 }

gbeClientCtpTxSize65to127P15MinTceRept  OBJECT-TYPE
    SYNTAX     TruthValue
    MAX-ACCESS read-write
    STATUS     current
    DESCRIPTION
        "Flag that enables the reporting of the TxSize65to127_15MinTce threshold."
    ::= { gbeClientCtpEntry 171 }

gbeClientCtpTxSize128to255P15MinTceRept  OBJECT-TYPE
    SYNTAX     TruthValue
    MAX-ACCESS read-write
    STATUS     current
    DESCRIPTION
        "Flag that enables the reporting of the TxSize128to255_15MinTce threshold."
    ::= { gbeClientCtpEntry 172 }

gbeClientCtpTxSize256to511P15MinTceRept  OBJECT-TYPE
    SYNTAX     TruthValue
    MAX-ACCESS read-write
    STATUS     current
    DESCRIPTION
        "Flag that enables the reporting of the TxSize256to511_15MinTce threshold."
    ::= { gbeClientCtpEntry 173 }

gbeClientCtpTxSize512to1023P15MinTceRept  OBJECT-TYPE
    SYNTAX     TruthValue
    MAX-ACCESS read-write
    STATUS     current
    DESCRIPTION
        "Flag that enables the reporting of the TxSize512to1023_15MinTce threshold."
    ::= { gbeClientCtpEntry 174 }

gbeClientCtpTxSize1024to1518P15MinTceRept  OBJECT-TYPE
    SYNTAX     TruthValue
    MAX-ACCESS read-write
    STATUS     current
    DESCRIPTION
        "Flag that enables the reporting of the TxSize1024to1518_15MinTce threshold."
    ::= { gbeClientCtpEntry 175 }

gbeClientCtpTxSize1519toJumboP15MinTceRept  OBJECT-TYPE
    SYNTAX     TruthValue
    MAX-ACCESS read-write
    STATUS     current
    DESCRIPTION
        "Flag that enables the reporting of the TxSize1519toJumbo_15MinTce threshold."
    ::= { gbeClientCtpEntry 176 }

gbeClientCtpTxPackets15MinTceRept  OBJECT-TYPE
    SYNTAX     TruthValue
    MAX-ACCESS read-write
    STATUS     current
    DESCRIPTION
        "Flag that enables the reporting of the CtpTxPackets15MinTce threshold."
    ::= { gbeClientCtpEntry 177 }

gbeClientCtpTxOctets15MinTceRept  OBJECT-TYPE
    SYNTAX     TruthValue
    MAX-ACCESS read-write
    STATUS     current
    DESCRIPTION
        "Flag that enables the reporting of the TxOctets15MinTce threshold."
    ::= { gbeClientCtpEntry 178 }

gbeClientCtpTxBroadcastPkts15MinTceRept  OBJECT-TYPE
    SYNTAX     TruthValue
    MAX-ACCESS read-write
    STATUS     current
    DESCRIPTION
        "Flag that enables the reporting of the TxBroadcastPkts15MinTce threshold."
    ::= { gbeClientCtpEntry 179 }

gbeClientCtpTxMulticastPkts15MinTceRept  OBJECT-TYPE
    SYNTAX     TruthValue
    MAX-ACCESS read-write
    STATUS     current
    DESCRIPTION
        "Flag that enables the reporting of the TxMulticastPkts15MinTce threshold."
    ::= { gbeClientCtpEntry 180 }

gbeClientCtpTxOutPauseFrames15MinTceRept  OBJECT-TYPE
    SYNTAX     TruthValue
    MAX-ACCESS read-write
    STATUS     current
    DESCRIPTION
        "Flag that enables the reporting of the TxOutPauseFrames15MinTce threshold."
    ::= { gbeClientCtpEntry 181 }

gbeClientCtpTxMacJSDayTceRept  OBJECT-TYPE
    SYNTAX     TruthValue
    MAX-ACCESS read-write
    STATUS     current
    DESCRIPTION
        "Flag that enables the reporting of the TxMacJSDayTce threshold crossing."
    ::= { gbeClientCtpEntry 182 }

gbeClientCtpTxMacSESDayTceRept  OBJECT-TYPE
    SYNTAX     TruthValue
    MAX-ACCESS read-write
    STATUS     current
    DESCRIPTION
        "Flag that enables the reporting of the TxMacSESDayTce threshold crossing."
    ::= { gbeClientCtpEntry 183 }

gbeClientCtpTxMacErrOctetDayTceRept  OBJECT-TYPE
    SYNTAX     TruthValue
    MAX-ACCESS read-write
    STATUS     current
    DESCRIPTION
        "Flag that enables the reporting of the TxMacErrOctetDayTce threshold crossing."
    ::= { gbeClientCtpEntry 184 }

gbeClientCtpTxMacJabberDayTceRept  OBJECT-TYPE
    SYNTAX     TruthValue
    MAX-ACCESS read-write
    STATUS     current
    DESCRIPTION
        "Flag that enables the reporting of the TxMacJabberDayTce threshold crossing."
    ::= { gbeClientCtpEntry 185 }

gbeClientCtpTxMacFragmentDayTceRept  OBJECT-TYPE
    SYNTAX     TruthValue
    MAX-ACCESS read-write
    STATUS     current
    DESCRIPTION
        "Flag that enables the reporting of the TxMacFragmentDayTce threshold crossing."
    ::= { gbeClientCtpEntry 186 }

gbeClientCtpTxMacCrcAlignedDayTceRept  OBJECT-TYPE
    SYNTAX     TruthValue
    MAX-ACCESS read-write
    STATUS     current
    DESCRIPTION
        "Flag that enables the reporting of the TxMacCrcAlignedDayTce threshold crossing."
    ::= { gbeClientCtpEntry 187 }

gbeClientCtpTxMacUndersizedDayTceRept  OBJECT-TYPE
    SYNTAX     TruthValue
    MAX-ACCESS read-write
    STATUS     current
    DESCRIPTION
        "Flag that enables the reporting of the TxMacUndersizedDayTce threshold crossing."
    ::= { gbeClientCtpEntry 188 }

gbeClientCtpTxMacOversizeDayTceRept  OBJECT-TYPE
    SYNTAX     TruthValue
    MAX-ACCESS read-write
    STATUS     current
    DESCRIPTION
        "Flag that enables the reporting of the TxMacOversizeDayTce threshold."
    ::= { gbeClientCtpEntry 189 }

gbeClientCtpTxSize64DayTceRept  OBJECT-TYPE
    SYNTAX     TruthValue
    MAX-ACCESS read-write
    STATUS     current
    DESCRIPTION
        "Flag that enables the reporting of the TxSize64_DayTce threshold."
    ::= { gbeClientCtpEntry 190 }

gbeClientCtpTxSize65to127DayTceRept  OBJECT-TYPE
    SYNTAX     TruthValue
    MAX-ACCESS read-write
    STATUS     current
    DESCRIPTION
        "Flag that enables the reporting of the TxSize65to127_DayTce threshold."
    ::= { gbeClientCtpEntry 191 }

gbeClientCtpTxSize128to255DayTceRept  OBJECT-TYPE
    SYNTAX     TruthValue
    MAX-ACCESS read-write
    STATUS     current
    DESCRIPTION
        "Flag that enables the reporting of the TxSize128to255_DayTce threshold."
    ::= { gbeClientCtpEntry 192 }

gbeClientCtpTxSize256to511DayTceRept  OBJECT-TYPE
    SYNTAX     TruthValue
    MAX-ACCESS read-write
    STATUS     current
    DESCRIPTION
        "Flag that enables the reporting of the TxSize256to511_DayTce threshold."
    ::= { gbeClientCtpEntry 193 }

gbeClientCtpTxSize512to1023DayTceRept  OBJECT-TYPE
    SYNTAX     TruthValue
    MAX-ACCESS read-write
    STATUS     current
    DESCRIPTION
        "Flag that enables the reporting of the TxSize512to1023_DayTce threshold."
    ::= { gbeClientCtpEntry 194 }

gbeClientCtpTxSize1024to1518DayTceRept  OBJECT-TYPE
    SYNTAX     TruthValue
    MAX-ACCESS read-write
    STATUS     current
    DESCRIPTION
        "Flag that enables the reporting of the TxSize1024to1518_DayTce threshold."
    ::= { gbeClientCtpEntry 195 }

gbeClientCtpTxSize1519toJumboDayTceRept  OBJECT-TYPE
    SYNTAX     TruthValue
    MAX-ACCESS read-write
    STATUS     current
    DESCRIPTION
        "Flag that enables the reporting of the TxSize1519toJumbo_DayTce threshold."
    ::= { gbeClientCtpEntry 196 }

gbeClientCtpTxPacketsDayTceRept  OBJECT-TYPE
    SYNTAX     TruthValue
    MAX-ACCESS read-write
    STATUS     current
    DESCRIPTION
        "Flag that enables the reporting of the CtpTxPacketsDayTce threshold."
    ::= { gbeClientCtpEntry 197 }

gbeClientCtpTxOctetsDayTceRept  OBJECT-TYPE
    SYNTAX     TruthValue
    MAX-ACCESS read-write
    STATUS     current
    DESCRIPTION
        "Flag that enables the reporting of the TxOctetsDayTce threshold."
    ::= { gbeClientCtpEntry 198 }

gbeClientCtpTxBroadcastPktsDayTceRept  OBJECT-TYPE
    SYNTAX     TruthValue
    MAX-ACCESS read-write
    STATUS     current
    DESCRIPTION
        "Flag that enables the reporting of the TxBroadcastPktsDayTce threshold."
    ::= { gbeClientCtpEntry 199 }

gbeClientCtpTxMulticastPktsDayTceRept  OBJECT-TYPE
    SYNTAX     TruthValue
    MAX-ACCESS read-write
    STATUS     current
    DESCRIPTION
        "Flag that enables the reporting of the TxMulticastPktsDayTce threshold."
    ::= { gbeClientCtpEntry 200 }

gbeClientCtpTxOutPauseFramesDayTceRept  OBJECT-TYPE
    SYNTAX     TruthValue
    MAX-ACCESS read-write
    STATUS     current
    DESCRIPTION
        "Flag that enables the reporting of the TxOutPauseFramesDayTce threshold."
    ::= { gbeClientCtpEntry 201 }

gbeClientCtpRxSize1024to1522P15MinTce  OBJECT-TYPE
    SYNTAX     Integer32
    MAX-ACCESS read-write
    STATUS     current
    DESCRIPTION
        "The total number of packets (including bad packets) received that were
         between 1024 and 1522 octets in length inclusive (excluding framing
         bits but including FCS octets) in 15 minutes."
    ::= { gbeClientCtpEntry 202 }

gbeClientCtpRxSize1523toJumboP15MinTce  OBJECT-TYPE
    SYNTAX     Integer32
    MAX-ACCESS read-write
    STATUS     current
    DESCRIPTION
        "The total number of packets (including bad packets) received that were
         between 1523 and Jumbo octets in length inclusive (excluding framing
         bits but including FCS octets) in 15 minutes."
    ::= { gbeClientCtpEntry 203 }

gbeClientCtpRxSize1024to1522DayTce  OBJECT-TYPE
    SYNTAX     Integer32
    MAX-ACCESS read-write
    STATUS     current
    DESCRIPTION
        "The total number of packets (including bad packets) received that were
         between 1024 and 1522 octets in length inclusive (excluding framing
         bits but including FCS octets) in 24 hours."
    ::= { gbeClientCtpEntry 204 }

gbeClientCtpRxSize1523toJumboDayTce  OBJECT-TYPE
    SYNTAX     Integer32
    MAX-ACCESS read-write
    STATUS     current
    DESCRIPTION
        "The total number of packets (including bad packets) received that were
         between 1523 and Jumbo octets in length inclusive (excluding framing
         bits but including FCS octets) in 24 hours."
    ::= { gbeClientCtpEntry 205 }

gbeClientCtpTxSize1024to1522P15MinTce  OBJECT-TYPE
    SYNTAX     Integer32
    MAX-ACCESS read-write
    STATUS     current
    DESCRIPTION
        "The total number of packets (including bad packets) received that were
         between 1024 and 1522 octets in length inclusive (excluding framing
         bits but including FCS octets) in 15 minutes."
    ::= { gbeClientCtpEntry 206 }

gbeClientCtpTxSize1523toJumboP15MinTce  OBJECT-TYPE
    SYNTAX     Integer32
    MAX-ACCESS read-write
    STATUS     current
    DESCRIPTION
        "The total number of packets (including bad packets) received that were
         between 1523 and Jumbo octets in length inclusive (excluding framing
         bits but including FCS octets) in 15 minutes."
    ::= { gbeClientCtpEntry 207 }

gbeClientCtpTxSize1024to1522DayTce  OBJECT-TYPE
    SYNTAX     Integer32
    MAX-ACCESS read-write
    STATUS     current
    DESCRIPTION
        "The total number of packets (including bad packets) received that were
         between 1024 and 1522 octets in length inclusive (excluding framing
         bits but including FCS octets) in 24 hours."
    ::= { gbeClientCtpEntry 208 }

gbeClientCtpTxSize1523toJumboDayTce  OBJECT-TYPE
    SYNTAX     Integer32
    MAX-ACCESS read-write
    STATUS     current
    DESCRIPTION
        "The total number of packets (including bad packets) received that were
         between 1523 and Jumbo octets in length inclusive (excluding framing
         bits but including FCS octets) in 24 hours."
    ::= { gbeClientCtpEntry 209 }

gbeClientCtpRxSize1024to1522P15MinTceRept  OBJECT-TYPE
    SYNTAX     TruthValue
    MAX-ACCESS read-write
    STATUS     current
    DESCRIPTION
        "Flag that enables the reporting of the RxSize1024to1522_15MinTce threshold."
    ::= { gbeClientCtpEntry 210 }

gbeClientCtpRxSize1523toJumboP15MinTceRept  OBJECT-TYPE
    SYNTAX     TruthValue
    MAX-ACCESS read-write
    STATUS     current
    DESCRIPTION
        "Flag that enables the reporting of the RxSize1523toJumbo_15MinTce threshold."
    ::= { gbeClientCtpEntry 211 }

gbeClientCtpRxSize1024to1522DayTceRept  OBJECT-TYPE
    SYNTAX     TruthValue
    MAX-ACCESS read-write
    STATUS     current
    DESCRIPTION
        "Flag that enables the reporting of the RxSize1024to1522_DayTce threshold."
    ::= { gbeClientCtpEntry 212 }

gbeClientCtpRxSize1523toJumboDayTceRept  OBJECT-TYPE
    SYNTAX     TruthValue
    MAX-ACCESS read-write
    STATUS     current
    DESCRIPTION
        "Flag that enables the reporting of the RxSize1523toJumbo_DayTce threshold."
    ::= { gbeClientCtpEntry 213 }

gbeClientCtpTxSize1024to1522P15MinTceRept  OBJECT-TYPE
    SYNTAX     TruthValue
    MAX-ACCESS read-write
    STATUS     current
    DESCRIPTION
        "Flag that enables the reporting of the TxSize1024to1522_15MinTce threshold."
    ::= { gbeClientCtpEntry 214 }

gbeClientCtpTxSize1523toJumboP15MinTceRept  OBJECT-TYPE
    SYNTAX     TruthValue
    MAX-ACCESS read-write
    STATUS     current
    DESCRIPTION
        "Flag that enables the reporting of the TxSize1523toJumbo_15MinTce threshold."
    ::= { gbeClientCtpEntry 215 }

gbeClientCtpTxSize1024to1522DayTceRept  OBJECT-TYPE
    SYNTAX     TruthValue
    MAX-ACCESS read-write
    STATUS     current
    DESCRIPTION
        "Flag that enables the reporting of the TxSize1024to1522_DayTce threshold."
    ::= { gbeClientCtpEntry 216 }

gbeClientCtpTxSize1523toJumboDayTceRept  OBJECT-TYPE
    SYNTAX     TruthValue
    MAX-ACCESS read-write
    STATUS     current
    DESCRIPTION
        "Flag that enables the reporting of the TxSize1523toJumbo_DayTce threshold."
    ::= { gbeClientCtpEntry 217 }


gbeClientCtpEncapTribDisableAction  OBJECT-TYPE
    SYNTAX      InfnTribDisableAction
    MAX-ACCESS read-write
    STATUS     current
    DESCRIPTION
        "Encapsulated Trib disable action."
    DEFVAL  { none }
    ::= { gbeClientCtpEntry 218 }

gbeClientCtpServiceMode 	OBJECT-TYPE
    SYNTAX     InfnServiceMode
    MAX-ACCESS read-only
    STATUS     current
    DESCRIPTION
        "The Service Mode (SM) of the client CTP (i.e., the mode/type of service in which
        this GBE client CTP is being used."
    ::= { gbeClientCtpEntry 219 }

gbeClientCtpServiceModeQualifier 	OBJECT-TYPE
    SYNTAX     InfnSMQ
    MAX-ACCESS read-only
    STATUS     current
    DESCRIPTION
        "The Service Mode Qualifier (SMQ) of the GBE client CTP
    (i.e., the mode/type of service in which this GBE client CTP is being used."
    ::= { gbeClientCtpEntry 220 }

gbeClientCtpHostAddress 	OBJECT-TYPE
    SYNTAX     DisplayString
    MAX-ACCESS read-write
    STATUS     current
    DESCRIPTION
        "."
    ::= { gbeClientCtpEntry 221 }

gbeClientCtpHostControlTableSize 	OBJECT-TYPE
    SYNTAX     DisplayString
    MAX-ACCESS read-write
    STATUS     current
    DESCRIPTION
        "."
    ::= { gbeClientCtpEntry 222 }

gbeClientCtpEncapClientDisableAction 	OBJECT-TYPE
    SYNTAX    InfnClientAction
    MAX-ACCESS read-write
    STATUS     current
    DESCRIPTION
        "."
    ::= { gbeClientCtpEntry 223 }

gbeClientCtpLLDPSnoopingEnable  OBJECT-TYPE
    SYNTAX     TruthValue
    MAX-ACCESS read-write
    STATUS     current
    DESCRIPTION
        "Flag that checks if the LLDP Snooping is enabled"
    ::= { gbeClientCtpEntry 224 }

gbeClientCtpFecMode  OBJECT-TYPE
    SYNTAX     TruthValue
    MAX-ACCESS read-write
    STATUS     current
    DESCRIPTION
        "Flag that checks if the FEC is enabled"
    ::= { gbeClientCtpEntry 225 }

gbeClientCtpMaxMTUsize	OBJECT-TYPE
    SYNTAX     Integer32
    MAX-ACCESS read-only
    STATUS     current
    DESCRIPTION
        "Maximum MTU size"
    ::= { gbeClientCtpEntry 226 }


gbeClientCtpCompliance  MODULE-COMPLIANCE
    STATUS     current
    DESCRIPTION
        "Describes the requirements for conformance to the GBECLIENTCTP-MIB"
    MODULE
        MANDATORY-GROUPS { gbeClientCtpGroup }
    ::= { gbeClientCtpCompliances 1 }

gbeClientCtpGroup  OBJECT-GROUP
    OBJECTS { gbeClientCtpSupportingCircuitIdList,
        gbeClientCtpLoopback,
        gbeClientCtpPmHistStatsEnable,
        gbeClientCtpConfiguredServiceType,
        gbeClientCtpConfiguredServiceType,
        gbeClientCtpTribTestSigGenMode,
        gbeClientCtpTribTestSigMonMode,
        gbeClientCtpLineTestSigGenMode,
        gbeClientCtpLineTestSigMonMode,
        gbeClientCtpMaxPacketLen,
        gbeClientCtpRxPcsICG15MinTce,
        gbeClientCtpRxPcsES15MinTce,
        gbeClientCtpRxPcsSES15MinTce,
        gbeClientCtpRxPcsSESS15MinTce,
        gbeClientCtpRxPcsICGDayTce,
        gbeClientCtpRxPcsESDayTce,
        gbeClientCtpRxPcsSESDayTce,
        gbeClientCtpRxPcsSESSDayTce,
        gbeClientCtpRxMacJS15MinTce,
        gbeClientCtpRxMacSES15MinTce,
        gbeClientCtpRxMacErrOctet15MinTce,
        gbeClientCtpRxMacJabber15MinTce,
        gbeClientCtpRxMacFragment15MinTce,
        gbeClientCtpRxMacCrcAligned15MinTce,
        gbeClientCtpRxMacUndersized15MinTce,
        gbeClientCtpRxMacOversize15MinTce,
        gbeClientCtpRxSize64P15MinTce,
        gbeClientCtpRxSize65to127P15MinTce,
        gbeClientCtpRxSize128to255P15MinTce,
        gbeClientCtpRxSize256to511P15MinTce,
        gbeClientCtpRxSize512to1023P15MinTce,
        gbeClientCtpRxSize1024to1518P15MinTce,
        gbeClientCtpRxSize1519toJumboP15MinTce,
        gbeClientCtpRxPackets15MinTce,
        gbeClientCtpRxOctets15MinTce,
        gbeClientCtpRxBroadcastPkts15MinTce,
        gbeClientCtpRxMulticastPkts15MinTce,
        gbeClientCtpRxInPauseFrames15MinTce,
        gbeClientCtpRxMacJSDayTce,
        gbeClientCtpRxMacSESDayTce,
        gbeClientCtpRxMacErrOctetDayTce,
        gbeClientCtpRxMacJabberDayTce,
        gbeClientCtpRxMacFragmentDayTce,
        gbeClientCtpRxMacCrcAlignedDayTce,
        gbeClientCtpRxMacUndersizedDayTce,
        gbeClientCtpRxMacOversizeDayTce,
        gbeClientCtpRxSize64DayTce,
        gbeClientCtpRxSize65to127DayTce,
        gbeClientCtpRxSize128to255DayTce,
        gbeClientCtpRxSize256to511DayTce,
        gbeClientCtpRxSize512to1023DayTce,
        gbeClientCtpRxSize1024to1518DayTce,
        gbeClientCtpRxSize1519toJumboDayTce,
        gbeClientCtpRxPacketsDayTce,
        gbeClientCtpRxOctetsDayTce,
        gbeClientCtpRxBroadcastPktsDayTce,
        gbeClientCtpRxMulticastPktsDayTce,
        gbeClientCtpRxInPauseFramesDayTce,
        gbeClientCtpTxPcsICG15MinTce,
        gbeClientCtpTxPcsES15MinTce,
        gbeClientCtpTxPcsSES15MinTce,
        gbeClientCtpTxPcsSESS15MinTce,
        gbeClientCtpTxPcsICGDayTce,
        gbeClientCtpTxPcsESDayTce,
        gbeClientCtpTxPcsSESDayTce,
        gbeClientCtpTxPcsSESSDayTce,
        gbeClientCtpTxMacJS15MinTce,
        gbeClientCtpTxMacSES15MinTce,
        gbeClientCtpTxMacErrOctet15MinTce,
        gbeClientCtpTxMacJabber15MinTce,
        gbeClientCtpTxMacFragment15MinTce,
        gbeClientCtpTxMacCrcAligned15MinTce,
        gbeClientCtpTxMacUndersized15MinTce,
        gbeClientCtpTxMacOversize15MinTce,
        gbeClientCtpTxSize64P15MinTce,
        gbeClientCtpTxSize65to127P15MinTce,
        gbeClientCtpTxSize128to255P15MinTce,
        gbeClientCtpTxSize256to511P15MinTce,
        gbeClientCtpTxSize512to1023P15MinTce,
        gbeClientCtpTxSize1024to1518P15MinTce,
        gbeClientCtpTxSize1519toJumboP15MinTce,
        gbeClientCtpTxPackets15MinTce,
        gbeClientCtpTxOctets15MinTce,
        gbeClientCtpTxBroadcastPkts15MinTce,
        gbeClientCtpTxMulticastPkts15MinTce,
        gbeClientCtpTxOutPauseFrames15MinTce,
        gbeClientCtpTxMacJSDayTce,
        gbeClientCtpTxMacSESDayTce,
        gbeClientCtpTxMacErrOctetDayTce,
        gbeClientCtpTxMacJabberDayTce,
        gbeClientCtpTxMacFragmentDayTce,
        gbeClientCtpTxMacCrcAlignedDayTce,
        gbeClientCtpTxMacUndersizedDayTce,
        gbeClientCtpTxMacOversizeDayTce,
        gbeClientCtpTxSize64DayTce,
        gbeClientCtpTxSize65to127DayTce,
        gbeClientCtpTxSize128to255DayTce,
        gbeClientCtpTxSize256to511DayTce,
        gbeClientCtpTxSize512to1023DayTce,
        gbeClientCtpTxSize1024to1518DayTce,
        gbeClientCtpTxSize1519toJumboDayTce,
        gbeClientCtpTxPacketsDayTce,
        gbeClientCtpTxOctetsDayTce,
        gbeClientCtpTxBroadcastPktsDayTce,
        gbeClientCtpTxMulticastPktsDayTce,
        gbeClientCtpTxOutPauseFramesDayTce,
        gbeClientCtpRxPcsICG15MinTceRept,
        gbeClientCtpRxPcsES15MinTceRept,
        gbeClientCtpRxPcsSES15MinTceRept,
        gbeClientCtpRxPcsSESS15MinTceRept,
        gbeClientCtpRxPcsICGDayTceRept,
        gbeClientCtpRxPcsESDayTceRept,
        gbeClientCtpRxPcsSESDayTceRept,
        gbeClientCtpRxPcsSESSDayTceRept,
        gbeClientCtpRxMacJS15MinTceRept,
        gbeClientCtpRxMacSES15MinTceRept,
        gbeClientCtpRxMacErrOctet15MinTceRept,
        gbeClientCtpRxMacJabber15MinTceRept,
        gbeClientCtpRxMacFragment15MinTceRept,
        gbeClientCtpRxMacCrcAligned15MinTceRept,
        gbeClientCtpRxMacUndersized15MinTceRept,
        gbeClientCtpRxMacOversize15MinTceRept,
        gbeClientCtpRxSize64P15MinTceRept,
        gbeClientCtpRxSize65to127P15MinTceRept,
        gbeClientCtpRxSize128to255P15MinTceRept,
        gbeClientCtpRxSize256to511P15MinTceRept,
        gbeClientCtpRxSize512to1023P15MinTceRept,
        gbeClientCtpRxSize1024to1518P15MinTceRept,
        gbeClientCtpRxSize1519toJumboP15MinTceRept,
        gbeClientCtpRxPackets15MinTceRept,
        gbeClientCtpRxOctets15MinTceRept,
        gbeClientCtpRxBroadcastPkts15MinTceRept,
        gbeClientCtpRxMulticastPkts15MinTceRept,
        gbeClientCtpRxInPauseFrames15MinTceRept,
        gbeClientCtpRxMacJSDayTceRept,
        gbeClientCtpRxMacSESDayTceRept,
        gbeClientCtpRxMacErrOctetDayTceRept,
        gbeClientCtpRxMacJabberDayTceRept,
        gbeClientCtpRxMacFragmentDayTceRept,
        gbeClientCtpRxMacCrcAlignedDayTceRept,
        gbeClientCtpRxMacUndersizedDayTceRept,
        gbeClientCtpRxMacOversizeDayTceRept,
        gbeClientCtpRxSize64DayTceRept,
        gbeClientCtpRxSize65to127DayTceRept,
        gbeClientCtpRxSize128to255DayTceRept,
        gbeClientCtpRxSize256to511DayTceRept,
        gbeClientCtpRxSize512to1023DayTceRept,
        gbeClientCtpRxSize1024to1518DayTceRept,
        gbeClientCtpRxSize1519toJumboDayTceRept,
        gbeClientCtpRxPacketsDayTceRept,
        gbeClientCtpRxOctetsDayTceRept,
        gbeClientCtpRxBroadcastPktsDayTceRept,
        gbeClientCtpRxMulticastPktsDayTceRept,
        gbeClientCtpRxInPauseFramesDayTceRept,
        gbeClientCtpTxPcsICG15MinTceRept,
        gbeClientCtpTxPcsES15MinTceRept,
        gbeClientCtpTxPcsSES15MinTceRept,
        gbeClientCtpTxPcsSESS15MinTceRept,
        gbeClientCtpTxPcsICGDayTceRept,
        gbeClientCtpTxPcsESDayTceRept,
        gbeClientCtpTxPcsSESDayTceRept,
        gbeClientCtpTxPcsSESSDayTceRept,
        gbeClientCtpTxMacJS15MinTceRept,
        gbeClientCtpTxMacSES15MinTceRept,
        gbeClientCtpTxMacErrOctet15MinTceRept,
        gbeClientCtpTxMacJabber15MinTceRept,
        gbeClientCtpTxMacFragment15MinTceRept,
        gbeClientCtpTxMacCrcAligned15MinTceRept,
        gbeClientCtpTxMacUndersized15MinTceRept,
        gbeClientCtpTxMacOversize15MinTceRept,
        gbeClientCtpTxSize64P15MinTceRept,
        gbeClientCtpTxSize65to127P15MinTceRept,
        gbeClientCtpTxSize128to255P15MinTceRept,
        gbeClientCtpTxSize256to511P15MinTceRept,
        gbeClientCtpTxSize512to1023P15MinTceRept,
        gbeClientCtpTxSize1024to1518P15MinTceRept,
        gbeClientCtpTxSize1519toJumboP15MinTceRept,
        gbeClientCtpTxPackets15MinTceRept,
        gbeClientCtpTxOctets15MinTceRept,
        gbeClientCtpTxBroadcastPkts15MinTceRept,
        gbeClientCtpTxMulticastPkts15MinTceRept,
        gbeClientCtpTxOutPauseFrames15MinTceRept,
        gbeClientCtpTxMacJSDayTceRept,
        gbeClientCtpTxMacSESDayTceRept,
        gbeClientCtpTxMacErrOctetDayTceRept,
        gbeClientCtpTxMacJabberDayTceRept,
        gbeClientCtpTxMacFragmentDayTceRept,
        gbeClientCtpTxMacCrcAlignedDayTceRept,
        gbeClientCtpTxMacUndersizedDayTceRept,
        gbeClientCtpTxMacOversizeDayTceRept,
        gbeClientCtpTxSize64DayTceRept,
        gbeClientCtpTxSize65to127DayTceRept,
        gbeClientCtpTxSize128to255DayTceRept,
        gbeClientCtpTxSize256to511DayTceRept,
        gbeClientCtpTxSize512to1023DayTceRept,
        gbeClientCtpTxSize1024to1518DayTceRept,
        gbeClientCtpTxSize1519toJumboDayTceRept,
        gbeClientCtpTxPacketsDayTceRept,
        gbeClientCtpTxOctetsDayTceRept,
        gbeClientCtpTxBroadcastPktsDayTceRept,
        gbeClientCtpTxMulticastPktsDayTceRept,
        gbeClientCtpTxOutPauseFramesDayTceRept,
        gbeClientCtpRxSize1024to1522P15MinTce,
        gbeClientCtpRxSize1523toJumboP15MinTce,
        gbeClientCtpRxSize1024to1522DayTce,
        gbeClientCtpRxSize1523toJumboDayTce,
        gbeClientCtpTxSize1024to1522P15MinTce,
        gbeClientCtpTxSize1523toJumboP15MinTce,
        gbeClientCtpTxSize1024to1522DayTce,
        gbeClientCtpTxSize1523toJumboDayTce,
        gbeClientCtpRxSize1024to1522P15MinTceRept,
        gbeClientCtpRxSize1523toJumboP15MinTceRept,
        gbeClientCtpRxSize1024to1522DayTceRept,
        gbeClientCtpRxSize1523toJumboDayTceRept,
        gbeClientCtpTxSize1024to1522P15MinTceRept,
        gbeClientCtpTxSize1523toJumboP15MinTceRept,
        gbeClientCtpTxSize1024to1522DayTceRept,
        gbeClientCtpTxSize1523toJumboDayTceRept,
        gbeClientCtpEncapTribDisableAction,
	    gbeClientCtpServiceMode,
	    gbeClientCtpServiceModeQualifier,
	    gbeClientCtpHostAddress,
	    gbeClientCtpHostControlTableSize,
        gbeClientCtpEncapClientDisableAction,
        gbeClientCtpLLDPSnoopingEnable ,
        gbeClientCtpFecMode,
		gbeClientCtpMaxMTUsize
    }
STATUS     current
DESCRIPTION
" A collection of objects for managing the gbeClientCtp"
::= { gbeClientCtpGroups 1 }
END
