-- This file is corresponding to Release 9.1.10.101 from 2014/08/11 00:00:00


---------------------------------------------------------------------------
-- (C)opyright 2007-2014 bintec elmeg GmbH
-- $RCSfile: mib-sysiny,v $
-- $Revision: 1.6 $
-- $Date: 2014-02-07 10:37:50 $
---------------------------------------------------------------------------

FEC-SYSINY-MIB DEFINITIONS ::= BEGIN

IMPORTS
    MODULE-IDENTITY, OBJECT-TYPE, NOTIFICATION-TYPE,
    Unsigned32,
    mib-2, enterprises
        FROM SNMPv2-SMI

    DisplayString, TimeStamp, TruthValue
        FROM SNMPv2-TC

    Date
	FROM BINTEC-MIB

    MODULE-COMPLIANCE, OBJECT-GROUP, NOTIFICATION-GROUP
        FROM SNMPv2-CONF

    sys
	FROM BINTEC-MIB;

---------------------------------------------------------------------------

sysINYMIB MODULE-IDENTITY
    LAST-UPDATED "200704261756Z"
    ORGANIZATION "bintec elmeg GmbH"
    CONTACT-INFO
            "EMail:   info@bintec-elmeg.com
	     Web:     www.bintec-elmeg.com
	    "
    DESCRIPTION
            "The MIB module for INY specific parts.
            "
    REVISION      "200705021519Z"
    DESCRIPTION
            "INY specific MIB."

    ::= { sys 5 }

---------------------------------------------------------------------------
-- OID groups & all tables
---------------------------------------------------------------------------
sysInyRelais		OBJECT IDENTIFIER	::= { sysINYMIB 1 }
--        	sysInyRelaisState				1

sysInyTemperature	OBJECT IDENTIFIER	::= { sysINYMIB 2 }
--        	sysInyTemperatureCurrent		1
--        	sysInyTemperatureMax			2
--        	sysInyTemperatureMaxTime		3
--        	sysInyTemperatureMin			4
--        	sysInyTemperatureMinTime		5
--        	sysInyTemperatureUpdatePeriod	6
--        	sysInyTemperatureLowerThreshold	7
--        	sysInyTemperatureUpperThreshold	8
--        	sysInyTemperatureAlarm			9


---------------------------------------------------------------------------

---------------------------------------------------------------------------
--  sysInyRelais
---------------------------------------------------------------------------

sysInyRelaisState  OBJECT-TYPE
	SYNTAX 		INTEGER  { off(1), on(2), alarm(3) }
	MAX-ACCESS	read-write
	STATUS		current
	DESCRIPTION
		"Relais control.
		off   : Relais control coil is always off.
		on    : Relais control coil is always on.
		alarm : Relais control coil controlled by failure LED."
	DEFVAL { off }
::= { sysInyRelais 1 }

---------------------------------------------------------------------------

---------------------------------------------------------------------------
--  sysInyTemperature
---------------------------------------------------------------------------

sysInyTemperatureCurrent  OBJECT-TYPE
	SYNTAX 		INTEGER (-55..125)
	UNITS		"degree Centigrade"
	MAX-ACCESS	read-only
	STATUS		current
	DESCRIPTION
		"Temperature during the last measurement time."
::= { sysInyTemperature 1 }

sysInyTemperatureMax  OBJECT-TYPE
	SYNTAX 		INTEGER (-55..125)
	UNITS		"degree Centigrade"
	MAX-ACCESS	read-only
	STATUS		current
	DESCRIPTION
		"Maximum observed temperature."
::= { sysInyTemperature 2 }

sysInyTemperatureMaxTime  OBJECT-TYPE
	SYNTAX 		Date
	MAX-ACCESS	read-only
	STATUS		current
	DESCRIPTION
		"Point in time the maximum temperature was observed."
::= { sysInyTemperature 3 }

sysInyTemperatureMin  OBJECT-TYPE
	SYNTAX 		INTEGER (-55..125)
	UNITS		"degree Centigrade"
	MAX-ACCESS	read-only
	STATUS		current
	DESCRIPTION
		"Minimum observed temperature."
::= { sysInyTemperature 4 }

sysInyTemperatureMinTime  OBJECT-TYPE
	SYNTAX 		Date
	MAX-ACCESS	read-only
	STATUS		current
	DESCRIPTION
		"Point in time the minimum temperature was observed."
::= { sysInyTemperature 5 }

sysInyTemperatureUpdatePeriod  OBJECT-TYPE
	SYNTAX 		Unsigned32
	UNITS		"seconds"
	MAX-ACCESS	read-write
	STATUS		current
	DESCRIPTION
		"Measurement interval of temperature update in seconds.
		0: Disable measurements."
	DEFVAL { 10 }
::= { sysInyTemperature 6 }

sysInyTemperatureLowerThreshold  OBJECT-TYPE
	SYNTAX 		INTEGER (-55..125)
	UNITS		"degree Centigrade"
	MAX-ACCESS	read-write
	STATUS		current
	DESCRIPTION
		"Minimal allowed temperature. If temperature falls below
		this threshold, a syslog message is generated."
	DEFVAL { -25 }
::= { sysInyTemperature 7 }

sysInyTemperatureUpperThreshold  OBJECT-TYPE
	SYNTAX 		INTEGER (-55..125)
	UNITS		"degree Centigrade"
	MAX-ACCESS	read-write
	STATUS		current
	DESCRIPTION
		"Maximal allowed temperature. If temperature raises above
		this threshold, a syslog message is generated."
	DEFVAL { 70 }
::= { sysInyTemperature 8 }

sysInyTemperatureAlarm  OBJECT-TYPE
	SYNTAX 		TruthValue
	MAX-ACCESS	read-only
	STATUS		current
	DESCRIPTION
		"Indicates if the defined temperature thresholds are
		violated."
	DEFVAL { false }
::= { sysInyTemperature 9 }

---------------------------------------------------------------------------
END
