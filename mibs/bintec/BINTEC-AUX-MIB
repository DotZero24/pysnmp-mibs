-- This file is corresponding to Release 9.1.10.101 from 2014/08/11 00:00:00


-- (c) Copyright 2000-2014 bintec elmeg GmbH
-- All Rights reserved
-- $RCSfile: mib-aux,v $
-- $Revision: 1.12 $
-- $Date: 2014-02-07 10:37:49 $
-- Author: mmossner
--------------------------------------------------------------------------


BINTEC-AUX-MIB DEFINITIONS ::= BEGIN

IMPORTS
        MODULE-IDENTITY, OBJECT-TYPE, NOTIFICATION-TYPE,
        Integer32, Unsigned32, Counter32, Counter64, IpAddress, TimeTicks,
        mib-2, enterprises
        FROM SNMPv2-SMI

        DisplayString, TimeStamp
        FROM SNMPv2-TC

        tty, Date, BitValue, HexValue
        FROM BINTEC-MIB

        MODULE-COMPLIANCE, OBJECT-GROUP, NOTIFICATION-GROUP
        FROM SNMPv2-CONF;

auxMIB  MODULE-IDENTITY
        LAST-UPDATED "2008081100Z"
        ORGANIZATION "bintec elmeg GmbH"
        CONTACT-INFO
                "EMail: info@bintec-elmeg.com
                 Web: www.bintec-elmeg.com
                 "
        DESCRIPTION
                "MIB for Aux/Modem support"
        REVISION "2008071100Z"
        DESCRIPTION
                "Aux MIB."
        ::= { tty 3 }

aux OBJECT IDENTIFIER ::= { auxMIB 1 }

auxConfigTable OBJECT-TYPE
        SYNTAX  SEQUENCE OF AuxConfigEntry
        MAX-ACCESS      not-accessible
        STATUS          current
        DESCRIPTION
                "The auxConfigTable configures each corresponding aux device.
                "
        ::= { aux 10 }

auxConfigEntry OBJECT-TYPE
        SYNTAX AuxConfigEntry
        MAX-ACCESS not-accessible
        STATUS  current
        DESCRIPTION
                "A single auxConfigTable entry.
                "
        INDEX { auxConfigIfIndex }
        ::= { auxConfigTable 1 }

AuxConfigEntry ::=
        SEQUENCE {
                auxConfigIfIndex         INTEGER,
                auxConfigSpeed           INTEGER,
                auxConfigPIN             DisplayString,
                auxConfigModulation      INTEGER,
                auxConfigDispatch        INTEGER,
                auxConfigAPN             DisplayString,
                auxConfigInit            DisplayString,
                auxConfigEscape          INTEGER,
                auxConfigAccessType      INTEGER,       -- not needed for V.24
                auxConfigPUK             DisplayString,
                auxConfigPinData         OCTET STRING,  -- not needed for V.24
                auxConfigRoamingMode     INTEGER,       -- not needed for V.24
                auxConfigRoamingPLMN     INTEGER        -- not needed for V.24
        }

        auxConfigIfIndex OBJECT-TYPE
        SYNTAX          INTEGER
        MAX-ACCESS      read-only
        STATUS          current
        DESCRIPTION
                "The index of the corresponding tty interface.
                "
        ::= { auxConfigEntry 1 }

        auxConfigSpeed OBJECT-TYPE
        SYNTAX          INTEGER
        MAX-ACCESS      read-write
        STATUS          current
        DESCRIPTION
                "The speed of the aux device. The default value is 9600.
                "
        DEFVAL { 9600 }
        ::= { auxConfigEntry 2 }

        auxConfigPIN OBJECT-TYPE
        SYNTAX          DisplayString (SIZE(0..8))
        MAX-ACCESS      read-write
        STATUS          current
        DESCRIPTION
                "The PIN code of the SIM card. This is used to
                 authorize the access to the SIM card.
                "
        ::= { auxConfigEntry 3 }

        auxConfigModulation OBJECT-TYPE
        SYNTAX          INTEGER {
                auto(1),
                mdm-9600(2),
                mdm-14400(3),
                v110-9600(4),
                v110-14400(5),
                v120(6),
                gprs(7)
        }
        MAX-ACCESS      read-write
        STATUS          current
        DESCRIPTION
		"The Modulation used by the modem.
		 With auto(1) the modulation will be automatically chosen.
		 mdm_9600(2) sets the modulation to 9600 bps (V.32).
		 mdm_14400(3) sets the modulation to 14400 bps (V.34).
		 The values v110_9600(4) and v110_14400(5) set the
		 modulation to V110 encapsulation with the corresponding
		 speed (9600 or 14400 bps).
		 Setting the value to v120(6) v120 will be used.
		 If the value is set to gprs(7) the modulation for GSM
		 capable modems is taken from auxConfigAccessType.
		"
        DEFVAL { auto }
        ::= { auxConfigEntry 4 }

        auxConfigDispatch OBJECT-TYPE
        SYNTAX          INTEGER {
                ppp(1),
                isdnlogin(2),
                none(3)
        }
        MAX-ACCESS      read-write
        STATUS          current
        DESCRIPTION
                "The dispatch service the modem should be used for.
                 The service could be either ppp(1), isdnlogin(2) or
                 none.
                "
        DEFVAL { isdnlogin }
        ::= { auxConfigEntry 5 }

        auxConfigAPN OBJECT-TYPE
        SYNTAX          DisplayString (SIZE(0..80))
        MAX-ACCESS      read-write
        STATUS          current
        DESCRIPTION
                "GPRS Access Point Name (APN).
                "
        ::= { auxConfigEntry 6 }

        auxConfigInit OBJECT-TYPE
        SYNTAX          DisplayString (SIZE(0..80))
        MAX-ACCESS      read-write
        STATUS          current
        DESCRIPTION
		"Additional Modem init sequence.
		 This sequence will be send to the modem to initialize it.
		 Normally this string should be empty (un-used).
		"
        ::= { auxConfigEntry 7 }

        auxConfigEscape OBJECT-TYPE
        SYNTAX          INTEGER (0..255)
        MAX-ACCESS      read-write
        STATUS          current
        DESCRIPTION
		"Modem escape character.
		 This character is sent to the modem to terminate the session.
		 For GPRS/UMTS modems this parameter should be zero.
		"
        DEFVAL { 43 }
        ::= { auxConfigEntry 8 }

        auxConfigAccessType OBJECT-TYPE
        SYNTAX          INTEGER {
                auto(1),	-- factory default settings
                gprs-only(2),	-- GPRS only
                umts-only(3),	-- UMTS only
                gprs-pref(4),	-- GPRS preferred
                umts-pref(5)	-- UMTS preferred
        }
        MAX-ACCESS      read-write
        STATUS          current
        DESCRIPTION
		"The default Access Type used by a GPRS/UMTS modem.
		 This setting works only for vendors who publish the
		 AT commands needed offically in the internet.
		"
        DEFVAL { auto }
        ::= { auxConfigEntry 9 }

        auxConfigPUK OBJECT-TYPE
        SYNTAX          DisplayString (SIZE(0..16))
        MAX-ACCESS      read-write
        STATUS          current
        DESCRIPTION
		"The PUK code of the SIM card needed to reset
		 the PIN code if the PIN is invalidated.
		 This is used to enter a new PIN code.
		 The PUK isn't stored in the configuration for
		 security reasons and used only temporarily
		 if available.
		"
        ::= { auxConfigEntry 10 }

        auxConfigPinData OBJECT-TYPE
        SYNTAX          OCTET STRING (SIZE(0..16))
        MAX-ACCESS      not-accessible
        STATUS          current
        DESCRIPTION
                "Field used for storing the PIN permanently.
                "
        ::= { auxConfigEntry 11 }

        auxConfigRoamingMode OBJECT-TYPE
        SYNTAX          INTEGER {
                disabled(1),
                auto(2),
                unrestricted(3),
                international(4),
                national(5),
                fixed(6)
        }
        MAX-ACCESS      read-write
        STATUS          current
        DESCRIPTION
                "The Roaming configuration for this TTY interface.
                 Possible values are:
                     disabled      - no roaming at all
                     auto          - roaming decision by modems factory defaults
                     unrestricted  - no restrictions for roaming decision
                     international - international roaming only
                     national      - national roaming only
                     fixed         - use auxConfigRoamingPLMN exclusively
                "
        DEFVAL { auto }
        ::= { auxConfigEntry 12 }

        auxConfigRoamingPLMN OBJECT-TYPE
        SYNTAX          INTEGER
        MAX-ACCESS      read-write
        STATUS          current
        DESCRIPTION
                "The PLMN (Public Land Mobile Netword) code allowed for
                 Roaming. Used only if auxConfigRoamingMode_fixed is selected.
                "
        ::= { auxConfigEntry 13 }

--

auxStatTable OBJECT-TYPE
        SYNTAX  SEQUENCE OF AuxStatEntry
        MAX-ACCESS      not-accessible
        STATUS          current
        DESCRIPTION
                "The auxStatTable holds statistics about the corresponding
                 aux device.
                "
        ::= { aux 11 }

auxStatEntry OBJECT-TYPE
        SYNTAX AuxStatEntry
        MAX-ACCESS not-accessible
        STATUS  current
        DESCRIPTION
                "A single auxStatTable entry.
                "
        INDEX { auxStatIfIndex }
        ::= { auxStatTable 1 }

AuxStatEntry ::=
        SEQUENCE {
                auxStatIfIndex           INTEGER,
                auxStatOperStatus        INTEGER,
                auxStatErrorCode         INTEGER,
                auxStatNetwork           DisplayString,
                auxStatCommand           DisplayString,
                auxStatAnswer            DisplayString,
                auxStatCSQ               INTEGER,
                auxStatControlChannel    INTEGER,       -- not supported by V.24
                auxStatAccessType        INTEGER,       -- not supported by V.24
                auxStatInDiscards        INTEGER,
                auxStatHomePLMN          INTEGER,
                auxStatCurrentPLMN       INTEGER,
                auxStatIMEI              DisplayString, -- not supported by V.24
                auxStatIccId             DisplayString, -- not supported by V.24
                auxStatLocationAreaCode  DisplayString,
                auxStatCellId            DisplayString
        }

        auxStatIfIndex OBJECT-TYPE
        SYNTAX          INTEGER
        MAX-ACCESS      read-only
        STATUS          current
        DESCRIPTION
                "The index of the corresponding tty interface.
                "
        ::= { auxStatEntry 1 }

        auxStatOperStatus OBJECT-TYPE
        SYNTAX          INTEGER {
                up(1),
                down(2),
                init(3),
                called(4),
                calling(5),
                connect(6),
                simwait(7),
                pinwait(8),
                error(9),
                disconnected(10),
                pukwait(11),
                regwait(12),
                apnwait(13)
        }
        MAX-ACCESS      read-only
        STATUS          current
        DESCRIPTION
                "The operational status of the GSM modem. The following
                 states can occur:
                 - up(1)            the device is up - initialization finished
                 - down(2)          the device is down
                 - init(3)          initialization state
                 - called(4)        incoming call received
                 - calling(5)       dialout is performed
                 - connect(6)       connection established
                 - simwait(7)       modem is detected - SIM card not ready
                 - pinwait(8)       modem is waiting for non-empty PIN entry
                 - error(9)         error - for details consult ErrorCode
                 - disconnected(10) the device isn't available (unplugged)
                 - pukwait(11)      waiting for PUK entry after PIN invalidated
                 - regwait(12)      wating for network operator registration
                 - apnwait(13)      waiting for APN entry if APN is empty
                 The initial OperStatus is down(2).
                "
        DEFVAL { down }
        ::= { auxStatEntry 2 }

        auxStatErrorCode OBJECT-TYPE
        SYNTAX          INTEGER {
                none(1),
                unspecified(2),
                pinerror(3),
                pukerror(4),
                apnerror(5),
                simerror(6),
                reg-denied(7)
        }
        MAX-ACCESS      read-only
        STATUS          current
        DESCRIPTION
                "If an error occurs (OperStatus is set to error) this variable
                 shows the reason for the error. Currently the following error
                 codes are possible:
                 - none(1)        no error occured
                 - unspecified(2) error can't be specified any further
                 - pinerror(3)    PIN was wrong PUK needed
                 - pukerror(4)    PUK was wrong
                 - apnerror(5)    APN was wrong
                 - simerror(6)    SIM card not present or damaged
                 - reg-denied(7)  Network registration denied
                 The initial ErrorCode is none(1).
                "
        DEFVAL { none }
        ::= { auxStatEntry 3 }

        auxStatNetwork OBJECT-TYPE
        SYNTAX          DisplayString (SIZE (0..60))
        MAX-ACCESS      read-only
        STATUS          current
        DESCRIPTION
                "The name of the PLMN (Public Land Mobile Network)
                 actually being used.
                "
        ::= { auxStatEntry 4 }

        auxStatCommand OBJECT-TYPE
        SYNTAX          DisplayString (SIZE (0..40))
        MAX-ACCESS      read-only
        STATUS          current
        DESCRIPTION
                "The last Command that was sent to the Modem.
                "
        ::= { auxStatEntry 5 }

        auxStatAnswer OBJECT-TYPE
        SYNTAX          DisplayString (SIZE (0..60))
        MAX-ACCESS      read-only
        STATUS          current
        DESCRIPTION
                "The last Answer gotten from the Modem.
                "
        ::= { auxStatEntry 6 }

        auxStatCSQ OBJECT-TYPE
        SYNTAX          INTEGER
        MAX-ACCESS      read-only
        STATUS          current
        DESCRIPTION
                "The GSM receive signal level in decibel (db).
                 A value below -100 signals a very low signal quality.
                 A value between -100 and -80 means that signal quality is low.
                 If the value is between -80 and -70 the quality is ok. The
                 interval from -70 to -60 signals a good quality and if the
                 value is above -60 the quality is excellent. The default e.g.
                 initial value is -113.
                "
        DEFVAL { -113 }
        ::= { auxStatEntry 7 }

        auxStatControlChannel OBJECT-TYPE
        SYNTAX          INTEGER {
                not-available(1),
                available(2)
        }
        MAX-ACCESS      read-only
        STATUS          obsolete
        DESCRIPTION
                "If the UMTS card provides several channels and one could
                 be used to control the card e.g. get status information
                 from the card like the signal quality a dedicated daemon
                 will do this and the auxStatControlChannel will be set to
                 available. In the other case auxStatControlChannel is set
                 to not_available.
                "
        DEFVAL { not-available }
        ::= { auxStatEntry 8 }

        auxStatAccessType OBJECT-TYPE
        SYNTAX INTEGER {
            unknown(1),
            gsm(2),
            compact-gsm(3),
            umts(4),
            gsm-edge(5),
            umts-hsdpa(6),
            umts-hsupa(7),
            umts-hspa(8)
        }
        MAX-ACCESS      read-only
        STATUS          obsolete
        DESCRIPTION
                "The Access Type the modem actually registers on.
                 Normally the `edge' or `hs*pa' Access Types aren't
                 provided in detail by the operator.
                "
        DEFVAL { unknown }
        ::= { auxStatEntry 9 }

        auxStatInDiscards OBJECT-TYPE
        SYNTAX          INTEGER
        MAX-ACCESS      read-only
        STATUS          current
        DESCRIPTION
                "The number of frames which can't be enqueued upstream.
		"
        ::= { auxStatEntry 10 }

        auxStatHomePLMN OBJECT-TYPE
        SYNTAX          INTEGER
        MAX-ACCESS      read-only
        STATUS          current
        DESCRIPTION
                "The PLMN (Public Land Mobile Network) code of the Home PLMN.
		"
        ::= { auxStatEntry 11 }

        auxStatCurrentPLMN OBJECT-TYPE
        SYNTAX          INTEGER
        MAX-ACCESS      read-only
        STATUS          current
        DESCRIPTION
                "The PLMN (Public Land Mobile Network) code of the Network
                 currently used.
		"
        ::= { auxStatEntry 12 }

        auxStatIMEI OBJECT-TYPE
        SYNTAX      DisplayString (SIZE(0..32))
        MAX-ACCESS  read-only
        STATUS      obsolete
            DESCRIPTION
                "The IMEI (International Mobile Equipment Identity)
                 of the detected GSM/UMTS device.
                "
        ::= { auxStatEntry 13 }

        auxStatIccId OBJECT-TYPE
        SYNTAX      DisplayString (SIZE(0..32))
        MAX-ACCESS  read-only
        STATUS      obsolete
        DESCRIPTION
                "The ICC-ID of the SIM-Card found in the device
                 which is actually enumerated with auxStatIfIndex.

                 Some UMTS modem vendors offer no capability to
                 read this ID before entering a valid PIN :-(
                 In this case the default configuration is choosen.
                "
        ::= { auxStatEntry 14 }

        auxStatLocationAreaCode OBJECT-TYPE
        SYNTAX          DisplayString (SIZE (0..16))
        MAX-ACCESS      read-only
        STATUS          current
        DESCRIPTION
                "The actual Location Area Code the UMTS-Modem is registered.
                 This may differ for GSM/UMTS Access Technology.
                "
        ::= { auxStatEntry 15 }

        auxStatCellId OBJECT-TYPE
        SYNTAX          DisplayString (SIZE (0..16))
        MAX-ACCESS      read-only
        STATUS          current
        DESCRIPTION
                "The actual Cell-ID the UMTS-Modem is registered.
                 This may differ for GSM/UMTS Access Technology.
                "
        ::= { auxStatEntry 16 }

--

--  auxMobileOperatorTable OBJECT-TYPE
--      SYNTAX  SEQUENCE OF AuxMobileOperatorEntry
--      MAX-ACCESS      not-accessible
--      STATUS          current
--      DESCRIPTION
--              "The auxMobileOperatorTable shows the actually available
--               network provider and the registration status.
--              "
--      ::= { aux 13 }

--  auxMobileOperatorEntry OBJECT-TYPE
--      SYNTAX AuxMobileOperatorEntry
--      MAX-ACCESS not-accessible
--      STATUS  current
--      DESCRIPTION
--              "A single auxMobileOperatorTable entry.
--              "
--      INDEX { auxMobileOperatorIfIndex, auxMobileOperatorID, auxMobileOperatorAccessType }
--      ::= { auxMobileOperatorTable 1 }

--  AuxMobileOperatorEntry ::=
--      SEQUENCE {
--              auxMobileOperatorIfIndex           INTEGER,
--              auxMobileOperatorID                INTEGER,
--              auxMobileOperatorAccessType        INTEGER,
--              auxMobileOperatorStatus            INTEGER,
--              auxMobileOperatorName              DisplayString
--      }

--

--  auxPLMNTable OBJECT-TYPE
--      SYNTAX  SEQUENCE OF AuxPLMNEntry
--      MAX-ACCESS  not-accessible
--      STATUS      current
--      DESCRIPTION
--          "The auxPLMNTable holds the PLMN (Public Land Mobile
--           Networks) codes known by the Modem(s).
--          "
--  ::= { aux 16 }

--  auxPLMNEntry OBJECT-TYPE
--      SYNTAX AuxPLMNEntry
--      MAX-ACCESS  not-accessible
--      STATUS      current
--      DESCRIPTION
--          "A single auxPLMNTable entry.
--          "
--      INDEX { auxPLMNOperatorId }
--  ::= { auxPLMNTable 1 }

--  AuxPLMNEntry ::=
--      SEQUENCE {
--          auxPLMNOperatorId       INTEGER,
--          auxPLMNOperatorName     DisplayString
--      }

--

--  auxPreferredPLMNTable OBJECT-TYPE
--      SYNTAX  SEQUENCE OF AuxPreferredPLMNEntry
--      MAX-ACCESS      not-accessible
--      STATUS          current
--      DESCRIPTION
--          "The auxPreferredPLMNTable shows the preferred PLMNs
--           (Public Land Mobile Networks) accessible by the SIM-Card.
--          "
--  ::= { aux 17 }

--  auxPreferredPLMNEntry OBJECT-TYPE
--      SYNTAX AuxPreferredPLMNEntry
--      MAX-ACCESS not-accessible
--      STATUS  current
--      DESCRIPTION
--          "A single auxPreferredPLMNTable entry.
--          "
--      INDEX { auxPreferredPLMNIccId, auxPreferredPLMNOperatorId }
--  ::= { auxPreferredPLMNTable 1 }

--  AuxPreferredPLMNEntry ::=
--      SEQUENCE {
--          auxPreferredPLMNIccId               DisplayString,
--          auxPreferredPLMNOperatorId          INTEGER,
--          auxPreferredPLMNOperatorName        DisplayString,
--          auxPreferredPLMNAccessGSM           INTEGER,
--          auxPreferredPLMNAccessUMTS          INTEGER
--      }

END
