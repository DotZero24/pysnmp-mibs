-- This file is corresponding to Release 9.1.10.101 from 2014/08/11 00:00:00


-- (C)opyright 1999-2014 bintec elmeg GmbH, All Rights Reserved
-- $RCSfile: mib-ethphy,v $
-- $Revision: 1.10 $

BIANCA-ETH-PHY-MIB DEFINITIONS ::= BEGIN

        IMPORTS
            MODULE-IDENTITY, OBJECT-TYPE, NOTIFICATION-TYPE,
            Integer32, Unsigned32, Counter32, Gauge32, Counter64,
            IpAddress, TimeTicks, mib-2, enterprises
                FROM SNMPv2-SMI

            DisplayString, TimeStamp, PhysAddress, TruthValue
                FROM SNMPv2-TC

            phy, Date, HexValue
                FROM BINTEC-MIB

            TRAP-TYPE
                FROM RFC-1215;

        exthPhyMIB MODULE-IDENTITY
            LAST-UPDATED "200907240000Z"
            ORGANIZATION
                "bintec elmeg GmbH"
            CONTACT-INFO
                "EMail:   info@bintec-elmeg.com
                 Web:     www.bintec-elmeg.com
                "
            DESCRIPTION
                "MIB module for ethernet (or the like) phy specific
                 definitions."
            REVISION     "200907240000Z"
            DESCRIPTION
                "First version conforming to SMIv2."
            ::= { phy 250 }

    -- Interfaces Group

    -- Management Information for the integrated Ethernet Switches

	ethPhyTable OBJECT-TYPE
	    SYNTAX  SEQUENCE OF EthPhyEntry
	    MAX-ACCESS  not-accessible
	    STATUS  current
	    DESCRIPTION
		"The ethPhyTable contains information relating to the
		 interfaces available on the system. Each entry corresponds
		 to an available ethernet or switch port. Entries cannot be
		 added or deleted by the user.

		 Creating entries: Entries are created by the system
		 automatically during ethernet interface hardware scan
		 and when a managable switch is detected.

		 Deleting entries: Entries can't be deleted."
	::= { phy 1 }

	ethPhyEntry OBJECT-TYPE
	    SYNTAX  EthPhyEntry
	    MAX-ACCESS  not-accessible
	    STATUS  current

	    DESCRIPTION
		"The ethPhyEntry contains configuration and status information
		 of a physical interface associated to one ethernet interface."
	    INDEX   { ethPhyPortIndex }
	::= { ethPhyTable 1 }

	EthPhyEntry ::=
	    SEQUENCE {
		ethPhyPortIndex			INTEGER,

		-- status variables
		ethPhyChipVendor		DisplayString,
		ethPhyChipModel			DisplayString,
		ethPhyPortLinkStatus		INTEGER,
		ethPhyPortMdixStatus		INTEGER,
		ethPhyPortCapabilities		BITS,

		-- configuration
		ethPhyPortMode			INTEGER,
		ethPhyEthAssignedIfIndex	INTEGER,
		ethPhyExtendedDistance		INTEGER,
		ethPhyPortGroup			INTEGER,
		ethPhyPortDescr			DisplayString,
		ethPhyPortFlowControl		INTEGER,
		ethPhyPortFlowControlStatus	INTEGER
	    }

	ethPhyPortIndex OBJECT-TYPE
	    SYNTAX  INTEGER
	    MAX-ACCESS  read-only
	    STATUS  current
	    DESCRIPTION
		"The unique ethernet PHY interface index."
	::= { ethPhyEntry 1 }

    -- status information

	ethPhyChipVendor OBJECT-TYPE
	    SYNTAX  DisplayString (SIZE(1..40))
	    MAX-ACCESS  read-only
	    STATUS  current
	    DESCRIPTION
		"The vendor name or identifier of the PHY or switch
		 detected during hardware scan."
	::= { ethPhyEntry 2 }

	ethPhyChipModel OBJECT-TYPE
	    SYNTAX  DisplayString (SIZE(1..40))
	    MAX-ACCESS  read-only
	    STATUS  current
	    DESCRIPTION
		"The chip modell/revision of the PHY or switch
		 detected during hardware scan."
	::= { ethPhyEntry 3 }

-- obsolete	ethPhyMiiChipIdent OBJECT-TYPE ::= { ethPhyEntry 4 }

-- obsolete	ethPhyMiiAddress OBJECT-TYPE ::= { ethPhyEntry 5 }

	ethPhyPortLinkStatus OBJECT-TYPE
	    SYNTAX  INTEGER {
	       	down(1),
		auto-neg-failed(2),
		auto-neg-unavail(3),
		auto-neg-running(4),
		auto-full-100(5),
		auto-half-100(6),
		auto-full-10(7),
		auto-half-10(8),
		full-100(9),
		half-100(10),
		full-10(11),
		half-10(12),
		admin-down(13),
		full-1000(14)
	    }
	    MAX-ACCESS  read-only
	    STATUS  current
	    DESCRIPTION
		"This variable indicates link status and autonegotiation
		 results:

		 down(1)             -- link down or autonegotiation failed
		 auto-neg-failed(2)  -- autonegotiation failed
		 auto-neg-unavail(3) -- autonegotiation not available
		 auto-neg-running(4) -- autonegotiation running
		 auto-full-100(5)    -- negotiated  100 mbps/full duplex
		 auto-half-100(6)    -- negotiated  100 mbps/half duplex
		 auto-full-10(7)     -- negotiated  10  mbps/full duplex
		 auto-half-10(8)     -- negotiated  10  mbps/half duplex
		 full-100(9)         -- forced mode 100 mbps/full duplex
		 half-100(10)        -- forced mode 100 mbps/half duplex
		 full-10(11)         -- forced mode 10  mbps/full duplex
		 half-10(12)         -- forcde mode 10  mbps/half duplex
		 admin-down(13)      -- link set administrative down
		 full-1000(14)       -- forced mode 1000 mbps/full duplex
		"
	::= { ethPhyEntry 6 }

	ethPhyPortMdixStatus OBJECT-TYPE
	    SYNTAX  INTEGER {
		normal(1),
	       	crossover(2),
		unknown(3)
	    }
	    MAX-ACCESS  read-only
	    STATUS  current
	    DESCRIPTION
		"This variable indicates the cables MDIX status
		 if the link is established."
	::= { ethPhyEntry 7 }

    -- management information

-- obsolete	ethPhyPortCommand OBJECT-TYPE ::= { ethPhyEntry 8 }

	ethPhyPortCapabilities OBJECT-TYPE
	    SYNTAX  BITS {
	    	    half-10(0),
	    	    full-10(1),
	    	    half-100(2),
	    	    full-100(3),
	    	    half-1000(4),
	    	    full-1000(5),
		    autoneg(6)
            }
	    MAX-ACCESS  read-only
	    STATUS  current
	    DESCRIPTION
		"This bitfield describes what modes the port supports:
		 	half-10		: 10Mbit/s half duplex
		 	full-10		: 10Mbit/s full duplex
		 	half-100	: 100Mbit/s half duplex
		 	full-100	: 100Mbit/s full duplex
		 	half-1000	: 1000Mbit/s half duplex
		 	full-1000	: 1000Mbit/s full duplex
			autoneg         : Autonegotiation supported
		 ."
	::= { ethPhyEntry 9 }

    -- configuration

	ethPhyPortMode OBJECT-TYPE
	    SYNTAX  INTEGER {
	       	disable(1),
		auto(2),
		auto-100(3),
		auto-10(4),
		auto-full-100(5),
		auto-half-100(6),
		auto-full-10(7),
		auto-half-10(8),
		fixed-full-100(9),
		fixed-half-100(10),
		fixed-full-10(11),
		fixed-half-10(12),
		auto-1000(14),
		fixed-full-1000(15)
	    }
	    MAX-ACCESS  read-write
	    STATUS  current
	    DESCRIPTION
		"The initial mode of the ethernet PHY or switch port:

		 disable(1)          -- disconnect from physical line
		 auto(2)             -- use default autonegotiation
		 auto-100(3)         -- use autonegotiation for 100 mbps only
		 auto-10(4)          -- use autonegotiation for 10 mbps only
		 auto-full-100(5)    -- auto-negotiate 100 mbps/full-duplex
		 auto-half-100(6)    -- auto-negotiate 100 mbps/half-duplex
		 auto-full-10(7)     -- auto-negotiate 10  mbps/full-duplex
		 auto-half-10(8)     -- auto-negotiate 10  mbps/half-duplex
		 fixed-full-100(9)   -- use fixed mode 100 mbps/full-duplex
		 fixed-half-100(10)  -- use fixed mode 100 mbps/half-duplex
		 fixed-full-10(11)   -- use fixed mode 10  mbps/full-duplex
		 fixed-half-10(12)   -- use fixed mode 10  mbps/half-duplex
		 auto-1000(14)       -- use autonegotiation for 1000 mbps only
		 fixed-full-1000(15) -- use fixed mode 1000 mbps/full-duplex
		"
	    DEFVAL { auto }
	::= { ethPhyEntry 10 }

-- obsolete	ethPhyEthBaseIfIndex OBJECT-TYPE ::= { ethPhyEntry 11 }

	ethPhyEthAssignedIfIndex OBJECT-TYPE
	    SYNTAX  INTEGER
	    MAX-ACCESS  read-write
	    STATUS  obsolete
	    DESCRIPTION
		"The Ethernet interface index the PHY or switch port
		 is connected/assigned to.
		 The system will create interfaces as needed, but there
		 can't be more ethernet interfaces than switch ports."
	    DEFVAL { -1 }
	::= { ethPhyEntry 12 }

	ethPhyExtendedDistance OBJECT-TYPE
	    SYNTAX  INTEGER {
		default(1),
		short-cable(2),
		long-cable(3)
	    }
	    MAX-ACCESS  read-write
	    STATUS  current
	    DESCRIPTION
		"If the PHY supports different receive thresholds depending
		 on the cable length (long-cable > 100 m) and speed (10BaseT)
		 it could be configured by this variable."
	    DEFVAL { default }
	::= { ethPhyEntry 13 }

-- obsolete	ethPhyMaxFrameSize OBJECT-TYPE ::= { ethPhyEntry 14 }

-- obsolete	ethPhyLed0Function OBJECT-TYPE ::= { ethPhyEntry 15 }

-- obsolete	ethPhyLed1Function OBJECT-TYPE ::= { ethPhyEntry 16 }

-- obsolete	ethPhyLed2Function OBJECT-TYPE ::= { ethPhyEntry 17 }

	ethPhyPortGroup OBJECT-TYPE
	    SYNTAX  INTEGER (0..99)
	    MAX-ACCESS  read-write
	    STATUS  current
	    DESCRIPTION
		"The port group this phy is member of."
	::= { ethPhyEntry 18 }

-- obsolete	ethPhySwitchTableAging OBJECT-TYPE ::= { ethPhyEntry 20 }

	ethPhyPortDescr OBJECT-TYPE
	    SYNTAX  DisplayString
	    MAX-ACCESS  read-write
	    STATUS  current
	    DESCRIPTION
		"This object is available to the user for
		 specifying a user-friendly name or tag."
	::= { ethPhyEntry 21 }

	ethPhyPortFlowControl OBJECT-TYPE
	    SYNTAX  INTEGER {
		disable(1),
		enable(2),
		auto(3)
	    }
	    MAX-ACCESS  read-write
	    STATUS  current
	    DESCRIPTION
		"If the PHY supports flow control according to IEEE 802.3x
		 flow control can be enabled on that port by setting variable
		 to value 'auto'. This will cause 802.3x to be advertised via
		 that port as well as enabled automatically in case flow
		 control gets negotiated.
		 Value 'disable' keeps flow control from being advertised and,
		 hence, from being used at all.
		 With value 'enable' flow control can be forced to be enabled
		 regardless of any auto-negotiation.

		 Default value is disable."
	    DEFVAL { disable }
	::= { ethPhyEntry 22 }

	ethPhyPortFlowControlStatus OBJECT-TYPE
	    SYNTAX  INTEGER {
		disabled(1),
		enabled(2)
	    }
	    MAX-ACCESS  read-only
	    STATUS  current
	    DESCRIPTION
		"This variable indicates whether flow control according to IEEE
		 802.3x is currently active on that port.
		 Possible values are ...
			disabled(1) and
			enabled(2)
		"
	    DEFVAL { disabled }
	::= { ethPhyEntry 23 }

END
