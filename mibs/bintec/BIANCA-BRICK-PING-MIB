-- This file is corresponding to Release 9.1.10.101 from 2014/08/11 00:00:00


-- (C)opyright 2002-2014 bintec elmeg GmbH, All Rights Reserved
-- $RCSfile: mibping,v $
-- $Revision: 1.10 $
-- $Id: mibping,v 1.10 2014-02-07 10:37:50 tsbogend Exp $"

BIANCA-BRICK-PING-MIB DEFINITIONS ::= BEGIN

        IMPORTS
            IpAddress, enterprises
                FROM RFC1155-SMI

            DisplayString
                FROM RFC1158-MIB

            OBJECT-TYPE
                FROM RFC-1212;

    bintec      OBJECT IDENTIFIER ::= { enterprises 272 }
    bibo        OBJECT IDENTIFIER ::= { bintec 4 }
    biboip      OBJECT IDENTIFIER ::= { bibo 5 }
    biboping    OBJECT IDENTIFIER
        ::= { biboip 27 }

        biboPingTable OBJECT-TYPE
            SYNTAX SEQUENCE OF BiboPingEntry
            ACCESS not-accessible
            STATUS mandatory
            DESCRIPTION
                "The biboPingTable contains entries which are used
                to request the router to ping a target host for test
                purposes."
            ::= { biboping 1 }

        biboPingEntry OBJECT-TYPE
            SYNTAX BiboPingEntry
            ACCESS not-accessible
            STATUS mandatory
            DESCRIPTION
                "Contains parameters for the ping and results of the
                 operation.

                 To create a new entry, do an SNMP SET request
                 including a biboPingIndex value which is not in use.

                 To delete an existing entry, do an SNMP SET request
                 including a biboPingStatus value equal to delete (6)."
            INDEX { biboPingIndex }
        ::= { biboPingTable 1 }

        BiboPingEntry ::=
            SEQUENCE {
                biboPingIndex           INTEGER,
                biboPingStatus          INTEGER,
                biboPingCompleted       INTEGER,
                biboPingSourceAddress   IpAddress,
                biboPingAddress         IpAddress,
                biboPingPacketCount     INTEGER,
                biboPingPacketSize      INTEGER,
                biboPingPacketTimeout   INTEGER,
                biboPingReceivedPackets INTEGER,
                biboPingMinRoundTrip    INTEGER,
                biboPingMaxRoundTrip    INTEGER,
                biboPingAvgRoundTrip    INTEGER,
                biboPingTTL		INTEGER,
                biboPingTOS		INTEGER
            }

        biboPingIndex OBJECT-TYPE
            SYNTAX INTEGER (1..2147483647)
            ACCESS read-write
            STATUS mandatory
            DESCRIPTION
                "The unique index of the entry."
            DEFVAL { 1 }
        ::= { biboPingEntry 1 }

        biboPingStatus OBJECT-TYPE
            SYNTAX INTEGER {
                active(1),
                notinservice(2),
                notready(3),
                createandgo(4),
                createandwait(5),
                delete(6)
            }
            ACCESS read-write
            STATUS mandatory
            DESCRIPTION
                "The current status of the entry or a request
		to discard it (delete)."
            DEFVAL { createandwait }
        ::= { biboPingEntry 2 }

        biboPingCompleted OBJECT-TYPE
            SYNTAX INTEGER {
                true(1),
                false(2)
            }
            ACCESS read-only
            STATUS mandatory
            DESCRIPTION
                "The completion status of the ping session."
            DEFVAL { false }
        ::= { biboPingEntry 3 }

        biboPingSourceAddress OBJECT-TYPE
            SYNTAX IpAddress
            ACCESS read-write
            STATUS mandatory
            DESCRIPTION
                "The source ip-address for the ping session."
        ::= { biboPingEntry 4 }

        biboPingAddress OBJECT-TYPE
            SYNTAX IpAddress
            ACCESS read-write
            STATUS mandatory
            DESCRIPTION
                "The target ip-address for the ping session."
        ::= { biboPingEntry 5 }

        biboPingPacketCount OBJECT-TYPE
            SYNTAX INTEGER (0..65535)
            ACCESS read-write
            STATUS mandatory
            DESCRIPTION
                "The number of ping packets to send. 0 means
		continuous send."
            DEFVAL { 4 }
        ::= { biboPingEntry 6 }

        biboPingPacketSize OBJECT-TYPE
            SYNTAX INTEGER (8..4096)
            ACCESS read-write
            STATUS mandatory
            DESCRIPTION
                "The size of each ping packet in bytes."
            DEFVAL { 64 }
        ::= { biboPingEntry 7 }

        biboPingPacketTimeout OBJECT-TYPE
            SYNTAX INTEGER (1..65535)
            ACCESS read-write
            STATUS mandatory
            DESCRIPTION
                "The amount of time in milliseconds to wait for
                a reply before deciding the packet is lost."
            DEFVAL { 1000 }
        ::= { biboPingEntry 8 }

        biboPingReceivedPackets OBJECT-TYPE
            SYNTAX INTEGER (0..65535)
            ACCESS read-only
            STATUS mandatory
            DESCRIPTION
                "The number of replies received so far."
            DEFVAL { 0 }
        ::= { biboPingEntry 9 }

        biboPingMinRoundTrip OBJECT-TYPE
            SYNTAX INTEGER (0..65535)
            ACCESS read-only
            STATUS mandatory
            DESCRIPTION
                "The minimum round trip time in milliseconds for
                all the packets which have been replied to."
            DEFVAL { 0 }
        ::= { biboPingEntry 10 }

        biboPingMaxRoundTrip OBJECT-TYPE
            SYNTAX INTEGER (0..65535)
            ACCESS read-only
            STATUS mandatory
            DESCRIPTION
                "The maximum round trip time in milliseconds for
                all the packets which have been replied to."
            DEFVAL { 0 }
        ::= { biboPingEntry 11 }

        biboPingAvgRoundTrip OBJECT-TYPE
            SYNTAX INTEGER (0..65535)
            ACCESS read-only
            STATUS mandatory
            DESCRIPTION
                "The average round trip time in milliseconds for
                all the packets which have been replied to."
            DEFVAL { 0 }
        ::= { biboPingEntry 12 }

        biboPingTTL OBJECT-TYPE
            SYNTAX INTEGER (0..255)
            ACCESS read-write
            STATUS mandatory
            DESCRIPTION
                "The TTL byte value for each packet (0 = IP default)."
            DEFVAL { 0 }
        ::= { biboPingEntry 13 }

        biboPingTOS OBJECT-TYPE
            SYNTAX INTEGER (0..255)
            ACCESS read-write
            STATUS mandatory
            DESCRIPTION
                "The TOS byte value for each packet."
            DEFVAL { 0 }
        ::= { biboPingEntry 14 }

END
