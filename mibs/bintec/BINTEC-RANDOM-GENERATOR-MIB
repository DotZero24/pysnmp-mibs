-- This file is corresponding to Release 9.1.10.101 from 2014/08/11 00:00:00


---------------------------------------------------------------------------
-- (C)opyright 2012-2014 bintec elmeg GmbH, All Rights Reserved
-- $RCSfile: mib-rng,v $
-- $Revision: 1.5 $
-- $Date: 2014-02-07 11:21:02 $
---------------------------------------------------------------------------

BINTEC-RANDOM-GENERATOR-MIB DEFINITIONS ::= BEGIN

IMPORTS
    MODULE-IDENTITY, OBJECT-TYPE, NOTIFICATION-TYPE, enterprises,
    TimeTicks, Counter32, Gauge32, snmpModules, mib-2, Unsigned32, Counter64
        FROM SNMPv2-SMI

    DisplayString, TestAndIncr, TimeStamp
        FROM SNMPv2-TC

    MODULE-COMPLIANCE, OBJECT-GROUP, NOTIFICATION-GROUP
        FROM SNMPv2-CONF

    Date, HexValue, BitValue, sys
        FROM BINTEC-MIB;

---------------------------------------------------------------------------

randomGeneratorMIB MODULE-IDENTITY
    LAST-UPDATED "201203020000Z"
    ORGANIZATION "bintec elmeg GmbH"
    CONTACT-INFO "EMail:   info@bintec-elmeg.com
                  Web:     www.bintec-elmeg.com"
    DESCRIPTION  "Management Information for the Random Generator Subsystem"

    ::= { sys 8 }

randomGeneratorAdmin OBJECT IDENTIFIER
	::= { randomGeneratorMIB 1 }
---------------------------------------------------------------------------
-- Random Generator Administrative variables
	randomGeneratorHwRng OBJECT-TYPE
	    SYNTAX INTEGER {
		enabled (1),
		disabled (2)
	    }
            MAX-ACCESS  read-write
            STATUS  current
            DESCRIPTION
		"Enables/disables usage of HW random generators (if available)."
	    DEFVAL { enabled }
	    ::= { randomGeneratorAdmin 1 }



randomGeneratorStat OBJECT IDENTIFIER
	::= { randomGeneratorMIB 2 }
---------------------------------------------------------------------------
-- Random Generator Statistics Table

	randomGeneratorStatTable OBJECT-TYPE
            SYNTAX  SEQUENCE OF RandomGeneratorStatEntry
            MAX-ACCESS  not-accessible
            STATUS  current
            DESCRIPTION
		"This table contains the statistics for random generators."
	::= { randomGeneratorStat 1 }

	randomGeneratorStatEntry OBJECT-TYPE
            SYNTAX  RandomGeneratorStatEntry
            MAX-ACCESS  not-accessible
            STATUS  current
            DESCRIPTION
		"This object contains a random generator statistics."
	    INDEX   {
		randomGeneratorStatType
	    }
            ::= { randomGeneratorStatTable 1 }

 	RandomGeneratorStatEntry ::=
            SEQUENCE {
		randomGeneratorStatType		 INTEGER,
		randomGeneratorStatCalls	 Counter32,
		randomGeneratorStatBytes	 Counter32,
		randomGeneratorStatLastCallSince TimeTicks
            }


	randomGeneratorStatType OBJECT-TYPE
	    SYNTAX  INTEGER {
	    	software(1),
		hardware(2)
	    }
	    MAX-ACCESS  read-only
	    STATUS      current
	    DESCRIPTION
		"This speficies the type of the random number generator."
	    ::= { randomGeneratorStatEntry 1 }


	randomGeneratorStatCalls OBJECT-TYPE
	    SYNTAX      Counter32
	    MAX-ACCESS  read-only
	    STATUS      current
	    DESCRIPTION
		"The number of calls to get random data from this random number
		 generator."
	    ::= { randomGeneratorStatEntry 2 }

	randomGeneratorStatBytes OBJECT-TYPE
	    SYNTAX      Counter32
	    MAX-ACCESS  read-only
	    STATUS      current
	    DESCRIPTION
		"The number of random bytes drawn from this random number
		 generator."
	    ::= { randomGeneratorStatEntry 3 }

	randomGeneratorStatLastCallSince OBJECT-TYPE
	    SYNTAX TimeTicks
            MAX-ACCESS  read-only
            STATUS  current
            DESCRIPTION
		 "The time passed since the last random number was drawn."
	::= { randomGeneratorStatEntry 4 }

-- End Random Generator Statistics Table

END
