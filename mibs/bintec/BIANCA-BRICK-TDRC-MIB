-- This file is corresponding to Release 9.1.10.101 from 2014/08/11 00:00:00


-- (C)opyright 2004-2014 bintec elmeg GmbH, All Rights Reserved
-- $RCSfile: mibtdrc,v $
-- $Revision: 1.7 $

BIANCA-BRICK-TDRC-MIB DEFINITIONS ::= BEGIN

        IMPORTS
            Counter, enterprises
                FROM RFC1155-SMI

            DisplayString
                FROM RFC1158-MIB

            OBJECT-TYPE
                FROM RFC-1212;

    bintec      OBJECT IDENTIFIER ::= { enterprises 272 }
    bibo        OBJECT IDENTIFIER ::= { bintec 4 }
    biboip      OBJECT IDENTIFIER
        ::= { bibo 5 }

-- TCP Download Rate Control (TDRC) MIB

	ipTdrcTable OBJECT-TYPE
	    SYNTAX SEQUENCE OF IpTdrcEntry
            ACCESS not-accessible
            STATUS mandatory
            DESCRIPTION
                "The ipTdrcTable enables the TCP Download Rate Control (TDRC)
		 on the interface specified by ipTdrcIfIndex (interface index).

		 Creating entries: Entries are created by assigning an
		 interface index to the ipTdrcIfIndex object.

		 Deleting entries: Entries are removed by setting an
		 entry's ipTdrcMode object to 'delete'."
        ::= { biboip 43 }

        ipTdrcEntry OBJECT-TYPE
            SYNTAX IpTdrcEntry
            ACCESS not-accessible
            STATUS mandatory
            DESCRIPTION
                ""
            INDEX { ipTdrcIfIndex }
        ::= { ipTdrcTable 1 }


	IpTdrcEntry ::=
            SEQUENCE {
	        ipTdrcIfIndex			INTEGER,
		ipTdrcMode			INTEGER,
		ipTdrcMaxRate			INTEGER,
		ipTdrcWindowScaling		INTEGER,
		ipTdrcMss			INTEGER,
		ipTdrcServices			INTEGER
           }


	ipTdrcIfIndex OBJECT-TYPE
	    SYNTAX INTEGER
            ACCESS read-write
            STATUS mandatory
            DESCRIPTION
                "The associated Interface Index."
	    DEFVAL { 0 }
        ::= { ipTdrcEntry 1 }


	ipTdrcMode OBJECT-TYPE
            SYNTAX INTEGER {
	    	disabled(1),
		ack-prioritisation(2),
		static(3),
		dynamic(4),
		delete(5)
	    }
            ACCESS read-write
            STATUS mandatory
            DESCRIPTION
                "The TDRC mode for the associated interface.
		 disabled(1):		no TDRC active
		 ack-prioritisation(2):	preferential transmission of
		 			TCP ACK messages
		 static(3):		static TCP download limitation
		 			determined by ipTdrcMaxRate
		 dynamic(4):		dynamic TCP download limitation
		 			determined by ipTdrcMaxRate less
					amount of high priority traffic send
					via the associated interface
		 delete(5):		this entry will be deleted"
            DEFVAL { static }
        ::= { ipTdrcEntry 2 }


        ipTdrcMaxRate OBJECT-TYPE
	    SYNTAX INTEGER
            ACCESS read-write
            STATUS mandatory
            DESCRIPTION
                "The maximum TCP download rate in bits per second."
            DEFVAL { 1024000 }
        ::= { ipTdrcEntry 3 }


        ipTdrcWindowScaling OBJECT-TYPE
	    SYNTAX INTEGER ( 0..16 )
            ACCESS read-write
            STATUS mandatory
            DESCRIPTION
                "The TCP window scaling used for TDRC."
	    DEFVAL { 2 }
        ::= { ipTdrcEntry 4 }


        ipTdrcMss OBJECT-TYPE
	    SYNTAX INTEGER ( 0..4056 )
            ACCESS read-write
            STATUS mandatory
            DESCRIPTION
                "The TCP MSS used for TDRC."
	    DEFVAL { 1452 }
        ::= { ipTdrcEntry 5 }


        ipTdrcServices OBJECT-TYPE
            SYNTAX INTEGER {
	    	listed-only(1),
		all(2)
	    }
            ACCESS read-write
            STATUS mandatory
            DESCRIPTION
                "Determines the TCP services to be considered for TDRC.
		 If set to listed-only(1), only the predefined and listed
		 services (see ipTdrcServiceTable) will be controlled.
		 If set to all(2) each TCP service will be controlled."
	    DEFVAL { all }
        ::= { ipTdrcEntry 6 }



	ipTdrcServiceTable OBJECT-TYPE
	    SYNTAX SEQUENCE OF IpTdrcServiceEntry
            ACCESS not-accessible
            STATUS mandatory
            DESCRIPTION
                "The ipTdrcServiceTable specifies TCP services to be
		 considered for the TCP Download Rate Control (TDRC)
		 if enabled on the interface specified by ipTdrcServiceIfIndex
		 (interface index).

		 Creating entries: Entries are created by assigning an
		 interface index to the ipTdrcServiceIfIndex object.

		 Deleting entries: Entries are removed by setting an
		 entry's ipTdrcServiceStatus object to 'delete'."
        ::= { biboip 44 }

        ipTdrcServiceEntry OBJECT-TYPE
            SYNTAX IpTdrcServiceEntry
            ACCESS not-accessible
            STATUS mandatory
            DESCRIPTION
                ""
            INDEX { ipTdrcServiceIfIndex }
        ::= { ipTdrcServiceTable 1 }


	IpTdrcServiceEntry ::=
            SEQUENCE {
	        ipTdrcServiceIfIndex		INTEGER,
		ipTdrcServicePort		INTEGER,
		ipTdrcServiceStatus		INTEGER,
		ipTdrcServiceAlias		DisplayString
           }


	ipTdrcServiceIfIndex OBJECT-TYPE
	    SYNTAX INTEGER
            ACCESS read-write
            STATUS mandatory
            DESCRIPTION
                "The associated Interface Index."
	    DEFVAL { 0 }
        ::= { ipTdrcServiceEntry 1 }


	ipTdrcServicePort OBJECT-TYPE
	    SYNTAX INTEGER ( 0..65535 )
            ACCESS read-write
            STATUS mandatory
            DESCRIPTION
                "The associated TCP service/port."
	    DEFVAL { 0 }
        ::= { ipTdrcServiceEntry 2 }


	ipTdrcServiceStatus OBJECT-TYPE
            SYNTAX INTEGER {
	    	enabled(1),
		disabled(2),
		delete(5)
	    }
            ACCESS read-write
            STATUS mandatory
            DESCRIPTION
                "The status of this entry.
		 enabled(1):		service will be TDRC controlled
		 disabled(2):		service will not be TDRC controlled
		 delete(5):		this entry will be deleted.
		"
	    DEFVAL { enabled }
        ::= { ipTdrcServiceEntry 3 }


	ipTdrcServiceAlias OBJECT-TYPE
	    SYNTAX DisplayString
            ACCESS read-write
            STATUS mandatory
            DESCRIPTION
                "Alias Name for the Service Entry"
            DEFVAL { "" }
        ::= { ipTdrcServiceEntry 4 }



END
