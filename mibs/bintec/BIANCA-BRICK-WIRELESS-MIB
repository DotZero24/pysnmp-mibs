-- This file is corresponding to Release 9.1.10.101 from 2014/08/11 00:00:00


---------------------------------------------------------------------------
-- (C)opyright 2006-2014 bintec elmeg GmbH
-- $RCSfile: mib-wlan,v $
-- $Revision: 1.80 $
-- $Date: 2014-05-09 13:07:25 $
-- $Revision: 1.80 $
-- $Date: 2014-05-09 13:07:25 $
---------------------------------------------------------------------------

BIANCA-BRICK-WIRELESS-MIB DEFINITIONS ::= BEGIN

        IMPORTS
	IpAddress, enterprises
                FROM RFC1155-SMI
	MacAddress, DisplayString
		FROM SNMPv2-TC
        bibo, wlan, BitValue, Date, HexValue
		FROM BINTEC-MIB
        MODULE-IDENTITY, OBJECT-TYPE, NOTIFICATION-TYPE, Counter32, Counter64,
	TimeTicks, Unsigned32
		FROM SNMPv2-SMI
	TRAP-TYPE
                FROM RFC-1215
        TruthValue, RowStatus
		FROM SNMPv2-TC

	ifIndex FROM IF-MIB

        OBJECT-TYPE
                FROM RFC-1212
        MODULE-COMPLIANCE, OBJECT-GROUP, NOTIFICATION-GROUP
                FROM SNMPv2-CONF;

wlanMIB MODULE-IDENTITY
    LAST-UPDATED "201405090000Z"
    ORGANIZATION "bintec elmeg GmbH"
    CONTACT-INFO
            "EMail: info@bintec-elmeg.com
             Web: www.bintec-elmeg.com
            "
    DESCRIPTION
            "MIB for wlan subsystem"
    REVISION "200611260000Z"
    DESCRIPTION
            "Wireless LAN MIB."
    REVISION "200901290000Z"
    DESCRIPTION
            "Add 5,8 GHz band support."
    REVISION "201202150000Z"
    DESCRIPTION
            "Change Default SSID from Funkwerk-ec to default."
    REVISION "201209260000Z"
    DESCRIPTION
	    "Introduced wlanVSSAuthTable."
    REVISION "201303040000Z"
    DESCRIPTION
	    "Introduced airtime fairness, band steering and
	     blacklisting."
    REVISION "201308010000Z"
    DESCRIPTION
	    "WLAN bridge link functionality added."
    ::= { bibo 59 }


    -- Interfaces Group

    -- Management Information for the WLAN Subsystem

-- **********************************************************************
-- *  Textual conventions
-- **********************************************************************
    WlanRSSI ::= TEXTUAL-CONVENTION
	STATUS current
	DESCRIPTION
	    "This type is used to represent receiver input levels in dBm."
	SYNTAX INTEGER (-110..0)

    WlanRate ::= TEXTUAL-CONVENTION
	STATUS current
	DESCRIPTION
	    "This type is used to represent WLAN data rates in 500 Kbps units."
	SYNTAX INTEGER (0..600)

-- **********************************************************************
-- *    wlanIfTable  TABLE
-- **********************************************************************
wlanIfTable OBJECT-TYPE
    SYNTAX  SEQUENCE OF WlanIfEntry
    MAX-ACCESS  not-accessible
    STATUS  current
    DESCRIPTION
	"The wlanIfTable contains information relating to the
                interfaces available on the system. Each entry corresponds to
                an available WLAN interface. Entries cannot be added or
	deleted by the user.

                Creating entries: Entries are created by the system
                automatically when a new WLAN module is installed.

                Deleting entries: Entries are removed by the system
                after the appropriate WLAN module is removed."
    ::= { wlan 1 }

    wlanIfEntry OBJECT-TYPE
            SYNTAX  WlanIfEntry
            MAX-ACCESS  not-accessible
            STATUS  current
            DESCRIPTION
	""
	INDEX   { wlanIfIndex }
    ::= { wlanIfTable 1 }

    WlanIfEntry ::=
	SEQUENCE {
	-- configuration
        wlanIfIndex	    INTEGER,
	wlanIfType	    INTEGER,
	wlanIfMode	    INTEGER,
	wlanIfSpeed	    INTEGER,
	wlanIfChannel	    INTEGER,



	wlanIfSkipChannels24Ghz  BITS,
	wlanIfSkipChannels5Ghz 	 BITS,
	wlanIfRtsThreshold  INTEGER,
	wlanIfTxPower	    INTEGER,

	wlanIfAntennaRx	    INTEGER,
	wlanIfAntennaTx	    INTEGER,

	wlanIfBand	    INTEGER,
	wlanIfBurst	    INTEGER,

	wlanIfRxThreshold   INTEGER,
	wlanIfAntennaDiversity	INTEGER,
	wlanIfTimeout	    INTEGER,
	wlanIfCWmin	    INTEGER,
	wlanIfCWmax	    INTEGER,
	wlanIfPerfOptions   BITS,
	wlanIfStaTimeout	Counter32,
	wlanIfWMMParam	    INTEGER,

	wlanIfCountry	    DisplayString,
	wlanIfAddress	    MacAddress,
	wlanIfAckWindow	    INTEGER,
	wlanIfStaMaxPolls	Counter32,
	wlanIfRealChannel   INTEGER,
	-- statistics
	wlanIfRxPackets	    Counter32,
	wlanIfRxBytes	    Counter32,
	wlanIfRxErrors	    Counter32,
	wlanIfRxDecryptionError	Counter32,
	wlanIfRxRejected    Counter32,
	wlanIfTxPackets	    Counter32,
	wlanIfTxBytes	    Counter32,
	wlanIfTxErrors	    Counter32,
	wlanIfTxDropped     Counter32,
	wlanIfMSDUTxErrors  Counter32,
	wlanIfMSDURxErrors  Counter32,
	wlanIfOperState	    TruthValue,
	wlanIfAssociated    Counter32,
	wlanIfNoise	    WlanRSSI,
	wlanIfRadioNumber   INTEGER
            }

    wlanIfIndex OBJECT-TYPE
	SYNTAX  INTEGER
	MAX-ACCESS  read-only
	STATUS  current
	DESCRIPTION
	    "Unique radio index."
    ::= { wlanIfEntry 1 }

    -- configuration

    wlanIfType OBJECT-TYPE
	SYNTAX  INTEGER { off(1), access-point(2), client(3), wds-only(4) }
	MAX-ACCESS  read-write
	STATUS  current
	DESCRIPTION
	    "The WLAN physical interface type
	    off(1)		interface disabled
	    access-point(2)	access point
	    client(3)		client mode
	    wds-only(4)		wireless distribution system
	    "
	DEFVAL { off }
    ::= { wlanIfEntry 2 }

    wlanIfMode OBJECT-TYPE
	SYNTAX  INTEGER {
	    m802-11b(1),
	    m802-11g(2),
	    m802-11mixed(3),
	    m802-11mixed-long(4),
	    m802-11mixed-short(5),
	    m802-11a(6),
	    m802-11bgn(7),
	    m802-11gn(8),
	    m802-11n(10),
	    m802-11an(11),
            m802-11abg(12),
            m802-11abgn(13),
            m802-11agn(14)
	    }
	MAX-ACCESS  read-write
	STATUS  current
	DESCRIPTION
	    "Mixed and compatibility modes between various 802.11 substandards.."
	DEFVAL { m802-11mixed }
    ::= { wlanIfEntry 3 }

    wlanIfSpeed OBJECT-TYPE
	SYNTAX  INTEGER {
	    s1mbit(1),
	    s2mbit(2),
	    s5mbit(3),
	    s6mbit(4),
	    s9mbit(5),
	    s11mbit(6),
	    s12mbit(7),
	    s18mbit(8),
	    s24mbit(9),
	    s36mbit(10),
	    s48mbit(11),
	    s54mbit(12),

	    sMCS0-HT(13),
	    sMCS1-HT(14),
	    sMCS2-HT(15),
	    sMCS3-HT(16),
	    sMCS4-HT(17),
	    sMCS5-HT(18),
	    sMCS6-HT(19),
	    sMCS7-HT(20),
	    sMCS8-HT(21),
	    sMCS9-HT(22),
	    sMCS10-HT(23),
	    sMCS11-HT(24),
	    sMCS12-HT(25),
            sMCS13-HT(26),
            sMCS14-HT(27),
            sMCS15-HT(28),

	    auto(31)
	    }
	MAX-ACCESS  read-write
	STATUS  current
	DESCRIPTION
	    "The value defines the bitrate or the coding scheme to use for data frames.
	     auto(31) enables automatic rate adaption."
	DEFVAL { s54mbit }
    ::= { wlanIfEntry 4 }

    wlanIfChannel OBJECT-TYPE
	SYNTAX  INTEGER (-1..256)
	MAX-ACCESS  read-write
	STATUS  current
	DESCRIPTION
	    "The physical channel "
	DEFVAL { 6 }
    ::= { wlanIfEntry 5 }

    wlanIfRtsThreshold OBJECT-TYPE
	SYNTAX  INTEGER (-1..65535)
	MAX-ACCESS  read-write
	STATUS  current
	DESCRIPTION
	    "This attribute shall indicate the number of octets in an
	    MPDU, below which an RTS/CTS handshake shall not be
	    performed, except as RTS/CTS is used as a cross modulation
	    protection mechanism. An RTS/CTS
	    handshake shall be performed at the beginning of any frame
	    exchange sequence where the MPDU is of type Data or
	    Management, the MPDU has an individual address in the
	    Address1 field, and the length of the MPDU is greater than
	    this threshold. Setting this attribute to be larger than the
	    maximum MSDU size shall have the effect of turning off the
	    RTS/CTS handshake for frames of Data or Management type
	    transmitted by this STA. Setting this attribute to one
	    shall have the effect of turning on the RTS/CTS handshake
	    for all frames of Data or Management type transmitted by
	    this STA. The default value of this attribute shall be
	    2347."
	DEFVAL { 2347 }
    ::= { wlanIfEntry 6 }

    wlanIfRxThreshold OBJECT-TYPE
	SYNTAX  INTEGER (1..255)
	MAX-ACCESS  read-write
	STATUS  current
	DESCRIPTION
	  "
	  "
	DEFVAL { 1 }
    ::= { wlanIfEntry 7 }

    wlanIfTxPower OBJECT-TYPE
	SYNTAX  INTEGER (0..63)
	UNITS "dBm"
	MAX-ACCESS  read-write
	STATUS  current
	DESCRIPTION
	  "Transmitter output power in dBm."
	DEFVAL { 20 }
    ::= { wlanIfEntry 8 }

    wlanIfAntennaRx OBJECT-TYPE
	SYNTAX  INTEGER { right(1), left(2) }
	MAX-ACCESS  read-write
	STATUS  current
	DESCRIPTION
	    "The current antenna being used to receive."
	DEFVAL { right }
    ::= { wlanIfEntry 9 }

    wlanIfAntennaTx OBJECT-TYPE
	SYNTAX  INTEGER { right(1), left(2) }
	MAX-ACCESS  read-write
	STATUS  current
	DESCRIPTION
	    "The current antenna being used to transmit."
	DEFVAL { right }
    ::= { wlanIfEntry 10 }

    wlanIfAntennaDiversity OBJECT-TYPE
	SYNTAX  INTEGER { none(1), rx(2), tx(3), rxtx(4) }
	MAX-ACCESS  read-write
	STATUS  current
	DESCRIPTION
	    " "
	DEFVAL { rx }
    ::= { wlanIfEntry 11 }

    wlanIfTimeout OBJECT-TYPE
	SYNTAX  INTEGER (0..255)
	MAX-ACCESS  read-write
	STATUS  current
	DESCRIPTION
	    "Station Timeout in minutes."
	DEFVAL { 5 }
    ::= { wlanIfEntry 12 }

    wlanIfBurst OBJECT-TYPE
	SYNTAX  INTEGER { off(1), compat(2), ideal(3), max(4) }
	MAX-ACCESS  read-write
	STATUS  current
	DESCRIPTION
	    "Sending wireless frames without backoff time."
	DEFVAL { compat }
    ::= { wlanIfEntry 13 }

-- obsolete    wlanIfMaxSTA OBJECT-TYPE    ::= { wlanIfEntry 14 }
-- obsolete    wlanIfMaxBSS OBJECT-TYPE    ::= { wlanIfEntry 15 }

    wlanIfCountry OBJECT-TYPE
	SYNTAX  DisplayString (SIZE (0..3))
	MAX-ACCESS  read-write
	STATUS  current
	DESCRIPTION
	    "This attribute identifies the country in which the station is operating.
	    The first two octets of this string is the two character country code as
	    described in document ISO/IEC 3166-1. The third octet shall be one of the
	    following:
	    1. an ASCII space character, if the regulations under which the
	    station is operating encompass all environments in the country,
	    2. an ASCII 'O' character, if the regulations under which the
	    station is operating are for an Outdoor environment only, or
	    3. an ASCII 'I' character, if the regulations under which the
	    station is operating are for an Indoor environment only."
	DEFVAL { "DE " }
    ::= { wlanIfEntry 16 }

    wlanIfAddress OBJECT-TYPE
	SYNTAX MacAddress
	MAX-ACCESS  read-only
	STATUS  current
	DESCRIPTION
	    " The MAC Address of the AP "
    ::= { wlanIfEntry 17 }

--  ::= { wlanIfEntry 18 }    this OID is obsolete

    wlanIfBand OBJECT-TYPE
	SYNTAX INTEGER { b24-GHz(1), b5-GHz(2), b58-GHz(3), b24-5-GHz(4) }
	MAX-ACCESS  read-write
	STATUS  current
	DESCRIPTION
	    " Frequency band  "
	DEFVAL { b24-GHz }
    ::= { wlanIfEntry 19 }

    wlanIfAckWindow OBJECT-TYPE
        SYNTAX INTEGER (0..199)
	UNITS "microseconds"
        MAX-ACCESS read-write
        STATUS current
        DESCRIPTION
            "Additional 802.11 ACK timeout in microseconds.
	     This must be set to non-zero value for radio distances
	     larger than about 700m.
	     Recommended setting is about 10 microseconds per kilometer."
        DEFVAL { 0 }
    ::= { wlanIfEntry 20 }

    wlanIfRealChannel OBJECT-TYPE
	SYNTAX  INTEGER (0..256)
	MAX-ACCESS  read-only
	STATUS  current
	DESCRIPTION
	    "The actually selected channel for transmit and receive.
	     In most cases this is the same value as wlanIfChannel,
	     except if automatic channel selection is active. In this
	     case, this variable shows the channel in use."
	DEFVAL { 6 }
    ::= { wlanIfEntry 21 }

    wlanIfCWmin OBJECT-TYPE
        SYNTAX INTEGER (1..65535)
        MAX-ACCESS read-write
        STATUS current
        DESCRIPTION
            "Minimum size of contention window.
             See also 9.2.4 of IEEE 802.11.
             This value must be a power of 2 minus 1."
        DEFVAL { 15 }
    ::= { wlanIfEntry 22 }

    wlanIfCWmax OBJECT-TYPE
        SYNTAX INTEGER (1..65535)
        MAX-ACCESS read-write
        STATUS current
        DESCRIPTION
            "Maximum size of contention window.
             See also 9.2.4 of IEEE 802.11.
             This value must be a power of 2 minus 1."
        DEFVAL { 1023 }
    ::= { wlanIfEntry 23 }

--  ::= { wlanIfEntry 24 }    this OID is obsolete

    wlanIfPerfOptions OBJECT-TYPE
	SYNTAX BITS		{
					nitroXMFrameCompression(0),
					nitroXMFrameConcatenation(1),
					nitroXMPiggybackAck(2),
					nitroXMDirectLink(3)
					}
        MAX-ACCESS read-write
        STATUS current
        DESCRIPTION
            "This attribute holds a collection of radio-dependant,
             proprietary performance enhancement options.
             Currently defined options are:
	     nitroXMFrameCompression(0)
		This option enables software compression of data
		frame contents. This is only available on
		Conexant-based chipsets, and is only effective with
		Conexant-based clients.
	     nitroXMFrameConcatenation(1)
		This option enabled concatenation of short
		data frames into large ones. This is only available
		on Conexant-based chipsets.
	     nitroXMPiggybackAck(2)
		This option allows ACK frames to be transmitted
		piggyback with data frames. This is only available
		on Conexant-based chipsets.
	     nitroXMDirectLink(3)
		This option enables direct data transfer between two
		associated clients. This is only available on
		Conexant-based chipsets, and is only effective with
		Conexant-based clients."
        DEFVAL { { nitroXMDirectLink, nitroXMPiggybackAck, nitroXMFrameConcatenation } }
    ::= { wlanIfEntry 25 }

	wlanIfStaTimeout OBJECT-TYPE
        SYNTAX  Counter32
        UNITS   "s"
        MAX-ACCESS read-write
        STATUS current
        DESCRIPTION
            "Number of seconds without any incoming traffic before
             associated STAs are polled for presence.
             If the STA fails to respond to wlanIfStaMaxPolls
             consecutive polls, it will be forcefully disassociated
             and removed from wlanStationTable."
        DEFVAL { 15 }
	::= { wlanIfEntry 26 }

	wlanIfStaMaxPolls OBJECT-TYPE
        SYNTAX  Counter32
        MAX-ACCESS read-write
        STATUS current
        DESCRIPTION
            "Number of times associated STAs are polled for presence.
             If the STA fails to respond to wlanIfStaMaxPolls
             consecutive polls, it will be forcefully disassociated
             and removed from wlanStationTable."
        DEFVAL { 3 }
	::= { wlanIfEntry 27 }

    wlanIfWMMParam OBJECT-TYPE
	SYNTAX  INTEGER { enabled(1), disabled(2) }
	MAX-ACCESS  read-write
	STATUS  current
	DESCRIPTION
	"WWM status 1=enable, 2=disable, access category parameters
	 could be changed in wLanWMMTable."
	DEFVAL { disabled }
    ::= { wlanIfEntry 28 }

    wlanIfSkipChannels24Ghz OBJECT-TYPE
	SYNTAX BITS {
			channel-1(0),
			channel-2(1),
			channel-3(2),
			channel-4(3),
			channel-5(4),
			channel-6(5),
			channel-7(6),
			channel-8(7),
			channel-9(8),
			channel-10(9),
			channel-11(10),
			channel-12(11),
			channel-13(12),
			channel-14(13)
		    }
	MAX-ACCESS  read-write
	STATUS  current
	DESCRIPTION
	    " If a bit is set the accordingly channel will be skipped from
	      the channel scan list (channel 1-14 for 2.4 GHz).
	      Default is scan all channels.  "
	DEFVAL { { } }
    ::= { wlanIfEntry 29 }

    wlanIfSkipChannels5Ghz OBJECT-TYPE
	SYNTAX BITS {
			channel-36(0),
			channel-40(1),
			channel-44(2),
			channel-48(3),
			channel-52(4),
			channel-56(5),
			channel-60(6),
			channel-64(7),
			channel-100(8),
			channel-104(9),
			channel-108(10),
			channel-112(11),
			channel-116(12),
			channel-120(13),
			channel-124(14),
			channel-128(15),
			channel-132(16),
			channel-136(17),
			channel-140(18),
			channel-149(19),
			channel-153(20),
			channel-157(21),
			channel-161(22),
			channel-165(23),
			channel-169(24),
			channel-173(25)
		    }
	MAX-ACCESS  read-write
	STATUS  current
	DESCRIPTION
	    " If a bit is set the accordingly channel will be skipped from
	      the channel scan list (channel 36-173 for 5 GHz).
	      Default is scan all channels.  "
	DEFVAL { { } }
    ::= { wlanIfEntry 30 }


    -- statistic counter
    wlanIfRxPackets OBJECT-TYPE
	SYNTAX  Counter32
	MAX-ACCESS  read-only
	STATUS  current
	DESCRIPTION
	    ""
    ::= { wlanIfEntry 65 }


    wlanIfRxBytes OBJECT-TYPE
	SYNTAX  Counter32
	MAX-ACCESS  read-only
	STATUS  current
	DESCRIPTION
	    ""
    ::= { wlanIfEntry 66 }

    wlanIfRxErrors OBJECT-TYPE
	SYNTAX  Counter32
	MAX-ACCESS  read-only
	STATUS  current
	DESCRIPTION
	    ""
    ::= { wlanIfEntry 67 }


    wlanIfRxDecryptionError OBJECT-TYPE
	SYNTAX  Counter32
	MAX-ACCESS  read-only
	STATUS  current
	DESCRIPTION
	    ""
    ::= { wlanIfEntry 68 }

    wlanIfRxRejected OBJECT-TYPE
	SYNTAX  Counter32
	MAX-ACCESS  read-only
	STATUS  current
	DESCRIPTION
	    ""
    ::= { wlanIfEntry 69 }

    wlanIfTxPackets OBJECT-TYPE
	SYNTAX  Counter32
	MAX-ACCESS  read-only
	STATUS  current
	DESCRIPTION
	""
    ::= { wlanIfEntry 70 }


    wlanIfTxBytes OBJECT-TYPE
	SYNTAX  Counter32
	MAX-ACCESS  read-only
	STATUS  current
	DESCRIPTION
	""
    ::= { wlanIfEntry 71 }

    wlanIfTxErrors OBJECT-TYPE
	SYNTAX  Counter32
	MAX-ACCESS  read-only
	STATUS  current
	DESCRIPTION
	""
    ::= { wlanIfEntry 72 }


    wlanIfTxDropped OBJECT-TYPE
	SYNTAX  Counter32
	MAX-ACCESS  read-only
	STATUS  current
	DESCRIPTION
	""
    ::= { wlanIfEntry 73 }


    wlanIfMSDUTxErrors OBJECT-TYPE
	SYNTAX  Counter32
	MAX-ACCESS  read-only
	STATUS  current
	DESCRIPTION
	""
    ::= { wlanIfEntry 74 }

    wlanIfMSDURxErrors OBJECT-TYPE
	SYNTAX  Counter32
	MAX-ACCESS  read-only
	STATUS  current
	DESCRIPTION
	""
    ::= { wlanIfEntry 75 }

    wlanIfAssociated OBJECT-TYPE
	SYNTAX  Counter32
	MAX-ACCESS  read-only
	STATUS  current
	DESCRIPTION
	    ""
    ::= { wlanIfEntry 76 }

    wlanIfOperState OBJECT-TYPE
	SYNTAX  TruthValue
	MAX-ACCESS  read-only
	STATUS  current
	DESCRIPTION
	    "This attribute reflects the operational state of
	     the corresponding WLAN card."
	DEFVAL { false }
    ::= { wlanIfEntry 77 }

-- obsolete    wlanIfMaxVSS OBJECT-TYPE    ::= { wlanIfEntry 78 }
-- obsolete    wlanIfMaxWDS OBJECT-TYPE     ::= { wlanIfEntry 79 }
-- obsolete    wlanIfMaxClient OBJECT-TYPE  ::= { wlanIfEntry 80 }

    wlanIfNoise OBJECT-TYPE
	SYNTAX  WlanRSSI
	UNITS "dBm"
	MAX-ACCESS  read-only
	STATUS  current
	DESCRIPTION
	    "This attribute shows the measured noise level in dBm, or
	     0 when this value is not available.
	     It's the value measured during the last reception of data."
	DEFVAL { 0 }
    ::= { wlanIfEntry 81 }

    wlanIfRadioNumber OBJECT-TYPE
	SYNTAX  INTEGER
	MAX-ACCESS  read-only
	STATUS  current
	DESCRIPTION
	    "Radio number used in user interfaces and for labeling."
	DEFVAL { 0 }
    ::= { wlanIfEntry 82 }


-- **********************************************************************
-- *    End of wlanIfTable  TABLE
-- **********************************************************************

-- **********************************************************************
-- *    wlanVSSTable  TABLE
-- **********************************************************************
    wlanVSSTable OBJECT-TYPE
	SYNTAX  SEQUENCE OF WlanVSSEntry
	MAX-ACCESS  not-accessible
	STATUS  current
	DESCRIPTION
	    " Describes a WLAN VSS and the correspondending
	  settings"
    ::= { wlan 2 }

    wlanVSSEntry OBJECT-TYPE
       SYNTAX  WlanVSSEntry
       MAX-ACCESS  not-accessible
       STATUS  current
       DESCRIPTION
	""
       INDEX   { wlanVSSwlanIf }
       ::= { wlanVSSTable 1 }

        WlanVSSEntry ::=
	 SEQUENCE {
	wlanVSSIndex	    INTEGER,
	wlanVSSIfIndex	    INTEGER,
	wlanVSSwlanIf	    INTEGER,
	wlanVSSId	    DisplayString,
	wlanVSSAdminStatus  INTEGER,
	wlanVSSSecurity	    INTEGER,
	wlanVSSDefaultKey   INTEGER,
	wlanVSSKey1	    OCTET STRING,
	wlanVSSKey2	    OCTET STRING,
	wlanVSSKey3	    OCTET STRING,
	wlanVSSKey4	    OCTET STRING,
	wlanVSSTotal	    INTEGER,
	wlanVSSMAC	    INTEGER,
	wlanVSSLocal	    INTEGER,
	wlanVSSHidden	    INTEGER,
	wlanVSSWPAMulticastCipher   BitValue,
	wlanVSSRSNMulticastCipher   BitValue,
	wlanVSSWPAUnicastCipher	    BitValue,
	wlanVSSRSNUnicastCipher	    BitValue,
	wlanVSSRsnPreauthentication INTEGER,
	wlanVSSBSSID	    MacAddress,
	wlanVSSWMMEnabled   TruthValue,
        wlanVSSIgmpSnooping         INTEGER,
	wlanVSSRSNCapabilities	    INTEGER,
	wlanVSSWpaMixedMode	    INTEGER,
	wlanVSSARPProcessing	    TruthValue,
	wlanVSSPolicies	    INTEGER,
	wlanVSSInvoked	    INTEGER,
	wlanVSSExunencrypted    INTEGER,

	-- statistics
	wlanVSSMSDUTx	    Counter32,
	wlanVSSMSDURx	    Counter32,
	wlanVSSBytesTx	    Counter32,
	wlanVSSBytesRx	    Counter32,
	wlanVSSTxMcAirtime  Counter64,
	wlanVSSRxAirtime    Counter64,
	wlanVSSTxUcAirtime  Counter64,
	wlanVSSCurrent	    INTEGER
	 }

    wlanVSSIndex OBJECT-TYPE
	SYNTAX  INTEGER (0..255)
	MAX-ACCESS  read-only
	STATUS  current
	DESCRIPTION
	    "Unique VSS index of an Broadcast VSS."
	DEFVAL { 0 }
    ::= { wlanVSSEntry 1 }

--  ::= { wlanVSSEntry 2 }    this OID is obsolete

    wlanVSSIfIndex OBJECT-TYPE
	SYNTAX  INTEGER
	MAX-ACCESS  read-only
	STATUS  current
	DESCRIPTION
	    "ifIndex for this service set."
	DEFVAL { 0 }
    ::= { wlanVSSEntry 3 }

    wlanVSSwlanIf OBJECT-TYPE
	SYNTAX  INTEGER
	MAX-ACCESS  read-write
	STATUS  current
	DESCRIPTION
	    "Radio index the VSS belongs to."
    ::= { wlanVSSEntry 4 }


    wlanVSSId OBJECT-TYPE
	SYNTAX  DisplayString (SIZE(0..32))
	MAX-ACCESS  read-write
	STATUS  current
	DESCRIPTION
	    "This attribute reflects the Service Set ID used
	    in the DesiredSSID parameter of the most recent
	    MLME_Scan.request."
	DEFVAL { "default" }
    ::= { wlanVSSEntry 5 }


    wlanVSSAdminStatus OBJECT-TYPE
	SYNTAX  INTEGER { enable(1), disable(2), delete(3) }
	MAX-ACCESS  read-write
	STATUS  current
	DESCRIPTION
                "Enable or disable the requested VSS."
	DEFVAL { disable }
    ::= { wlanVSSEntry 6 }


     wlanVSSSecurity OBJECT-TYPE
	SYNTAX  INTEGER { none(1), wep40(2), wep104(3), wpa-psk(4),
			  wpa(5), wpa2(6) }
	MAX-ACCESS  read-write
	STATUS  current
	DESCRIPTION
	    "The Security Option which will be used.
            wep40 and wep104:= WEP-Authentication
            wpa-psk := WPA-Authentication with PSK
            wpa := WPA-Authentication with radius (802.1X)
            wpa2 := OBSOLETE and not used anymore!
            "
	DEFVAL { none }
    ::= { wlanVSSEntry 7 }

    wlanVSSPolicies OBJECT-TYPE
	SYNTAX  INTEGER
	MAX-ACCESS  read-write
	STATUS  current
	DESCRIPTION
	"The Policies of the Broadcast VSS.
	 Applicable:
	    DOT11_MLMEPOLICY_PRIVACYREQUIRED
	    DOT11_MLMEPOLICY_PRIVACYCAPABILITY
	    DOT11_MLMEPOLICY_ALLOWUNENCRYPTEDBCAST
	    DOT11_MLMEPOLICY_PRIVACYCAPDIRECTED
	    DOT11_MLMEPOLICY_UNENCRYPTEDBCAST
	    DOT11_MLMEPOLICY_PRIVACYREFUSED
	"
	DEFVAL { 0 }
     ::= { wlanVSSEntry 10 }

     wlanVSSInvoked OBJECT-TYPE
	SYNTAX  INTEGER { none(1), enable(2) }
	MAX-ACCESS  read-write
	STATUS  current
	DESCRIPTION
	    "The Privacy Invoke Setting"
	DEFVAL { none }
    ::= { wlanVSSEntry 11 }

    wlanVSSExunencrypted OBJECT-TYPE
	SYNTAX  INTEGER { never(1), always(2), dynamic(3) }
	MAX-ACCESS  read-write
	STATUS  current
	DESCRIPTION
	    "The Privacy Invoke Setting"
	DEFVAL { never }
    ::= { wlanVSSEntry 12 }

    wlanVSSDefaultKey OBJECT-TYPE
	SYNTAX  INTEGER { key1(1), key2(2), key3(3), key4(4) }
	MAX-ACCESS  read-write
	STATUS  current
	DESCRIPTION
	    "Default key for WEP encryption."
	DEFVAL { key1 }
    ::= { wlanVSSEntry 13 }

    wlanVSSKey1 OBJECT-TYPE
	SYNTAX  OCTET STRING  (SIZE(0..64))
	MAX-ACCESS  read-write
	STATUS  current
	DESCRIPTION
	    "Key string for WEP key no. 1.
	      Also used for WPA passphrase"
	DEFVAL { "" }
    ::= { wlanVSSEntry 14 }

    wlanVSSKey2 OBJECT-TYPE
	SYNTAX  OCTET STRING  (SIZE(0..33))
	MAX-ACCESS  read-write
	STATUS  current
	DESCRIPTION
	    "Key string for WEP key no. 2."
	DEFVAL { "" }
    ::= { wlanVSSEntry 15 }

    wlanVSSKey3 OBJECT-TYPE
	SYNTAX  OCTET STRING  (SIZE(0..33))
	MAX-ACCESS  read-write
	STATUS  current
	DESCRIPTION
	    "Key string for WEP key no. 3."
	DEFVAL { "" }
    ::= { wlanVSSEntry 16 }

    wlanVSSKey4 OBJECT-TYPE
	SYNTAX  OCTET STRING  (SIZE(0..33))
	MAX-ACCESS  read-write
	STATUS  current
	DESCRIPTION
	    "Key string for WEP key no. 4."
	DEFVAL { "" }
    ::= { wlanVSSEntry 17 }


    wlanVSSTotal OBJECT-TYPE
	SYNTAX  INTEGER (1..256)
	MAX-ACCESS  read-write
	STATUS  current
	DESCRIPTION
	    "The number of allowed clients of the requested VSS."
	DEFVAL { 32 }
    ::= { wlanVSSEntry 18 }

--  ::= { wlanVSSEntry 19 }    this OID is obsolete

    wlanVSSMAC OBJECT-TYPE
	SYNTAX  INTEGER { enable(1), disable(2) }
	MAX-ACCESS  read-write
	STATUS  current
	DESCRIPTION
	    " MAC Media Access Control via MAC Address"
	DEFVAL { disable }
    ::= { wlanVSSEntry 20 }

    wlanVSSLocal OBJECT-TYPE
	SYNTAX  INTEGER { enable(1), disable(2) }
	MAX-ACCESS  read-write
	STATUS  current
	DESCRIPTION
	    " Routing between connected Clients "
	DEFVAL { enable }
    ::= { wlanVSSEntry 21 }

    wlanVSSHidden OBJECT-TYPE
	SYNTAX  INTEGER { no(1), yes(2) }
	MAX-ACCESS  read-create
	STATUS  current
	DESCRIPTION
	    "Define whether SSID is hidden (yes(2)) or not (no(2)).
	     Default value is 'no(1)'."
	DEFVAL { no }
    ::= { wlanVSSEntry 22 }

    -- statistic counters

    wlanVSSCurrent OBJECT-TYPE
	SYNTAX  INTEGER
	MAX-ACCESS  read-only
	STATUS  current
	DESCRIPTION
	"Count of current associated stations"
    ::= { wlanVSSEntry 24 }

    wlanVSSMSDUTx OBJECT-TYPE
	SYNTAX  Counter32
	MAX-ACCESS  read-only
	STATUS  current
	DESCRIPTION
        "This attribute counts the total number of
         packets transmitted on this VSS."
    ::= { wlanVSSEntry 25 }

    wlanVSSMSDURx OBJECT-TYPE
	SYNTAX  Counter32
	MAX-ACCESS  read-only
	STATUS  current
	DESCRIPTION
        "This attribute counts the total number of
         packets received by this VSS."
    ::= { wlanVSSEntry 26 }

    wlanVSSBytesTx OBJECT-TYPE
	SYNTAX  Counter32
	MAX-ACCESS  read-only
	STATUS  current
	DESCRIPTION
	"Transmitted Bytes"
    ::= { wlanVSSEntry 27 }

    wlanVSSBytesRx OBJECT-TYPE
	SYNTAX  Counter32
	MAX-ACCESS  read-only
	STATUS  current
	DESCRIPTION
	"Received Bytes"
    ::= { wlanVSSEntry 28 }

    wlanVSSWPAMulticastCipher OBJECT-TYPE
	SYNTAX  BitValue
	MAX-ACCESS  read-only
	STATUS  current
	DESCRIPTION
	    "The multicast ciphers used for WPA.
	     Only one of the following values is allowed:
	     WPA_CIPHERSUITE_NONE(0)
	     WPA_CIPHERSUITE_WEP_40(1)
	     WPA_CIPHERSUITE_WEP_104(2)
	     WPA_CIPHERSUITE_TKIP(4)
	     WPA_CIPHERSUITE_AES_CCMP(8)
	     Only one of the bits may be set to indicate
	     the WPA group cipher to be used."
	DEFVAL { 4 }
    ::= { wlanVSSEntry 29 }

    wlanVSSRSNMulticastCipher OBJECT-TYPE
	SYNTAX  BitValue
	MAX-ACCESS  read-only
	STATUS  current
	DESCRIPTION
	    "The multicast ciphers used for RSN.
	     Only one of the following values is allowed:
	     WPA_CIPHERSUITE_NONE(0)
	     WPA_CIPHERSUITE_WEP_40(1)
	     WPA_CIPHERSUITE_WEP_104(2)
	     WPA_CIPHERSUITE_TKIP(4)
	     WPA_CIPHERSUITE_AES_CCMP(8)
	     Only one of the bits may be set to indicate
	     the RSN group cipher to be used."
	DEFVAL { 4 }
    ::= { wlanVSSEntry 30 }

    wlanVSSWPAUnicastCipher OBJECT-TYPE
	SYNTAX  BitValue
	MAX-ACCESS  read-write
	STATUS  current
	DESCRIPTION
	    "The set of unicast ciphers used for WPA.
	     set one or more of the following bit values:
	     WPA_CIPHERSUITE_NONE(0)
	     WPA_CIPHERSUITE_WEP_40(1)
	     WPA_CIPHERSUITE_WEP_104(2)
	     WPA_CIPHERSUITE_TKIP(4)
	     WPA_CIPHERSUITE_AES_CCMP(8)
	     One or more bits may be set to indicate the available pairwise ciphers."
	DEFVAL { 8 }
     ::= { wlanVSSEntry 31 }

    wlanVSSRSNUnicastCipher OBJECT-TYPE
	SYNTAX  BitValue
	MAX-ACCESS  read-write
	STATUS  current
	DESCRIPTION
	    "The set of unicast ciphers used for RSN.
	     set one or more of the following bit values:
	     WPA_CIPHERSUITE_NONE(0)
	     WPA_CIPHERSUITE_WEP_40(1)
	     WPA_CIPHERSUITE_WEP_104(2)
	     WPA_CIPHERSUITE_TKIP(4)
	     WPA_CIPHERSUITE_AES_CCMP(8)
	     One or more bits may be set to indicate the available pairwise ciphers."
	DEFVAL { 16 }
     ::= { wlanVSSEntry 32 }

    wlanVSSRSNCapabilities OBJECT-TYPE
	SYNTAX  INTEGER (0..65535)
	MAX-ACCESS  read-only
	STATUS  current
	DESCRIPTION
	    "Acccording to IEEE 802.11-2007 Section 7.3.2.25.3:
	     The RSN Capabilities field indicates requested or advertised capabilities.
	     The value of each of the RSN Capabilities fields
	     shall be taken to be 0 if the RSN Capabilities field
	     is not available in the RSN information element.

	     The length of the RSN Capabilities field is 2 octets.
	     The format of the RSN Capabilities field is illustrated in
	     IEEE 802.11-2007 Figure 7-74"
	DEFVAL { 0 }
    ::= { wlanVSSEntry 34 }

    wlanVSSWpaMixedMode OBJECT-TYPE
	SYNTAX  INTEGER { wpa(1), wpa2(2), wpaandwpa2(3) }
	MAX-ACCESS  read-write
	STATUS  current
	DESCRIPTION
	    "Allowed mixed operation of WPA and WPA2 by value wpaandwpa2(3)
	     (default value).
	     For tightened security, wpa2(2) can be selected.
	     The value wpa(1) is available for some older clients with drivers
	     that are unable to deal with WPA2 information elements."
	DEFVAL { wpaandwpa2 }
    ::= { wlanVSSEntry 35 }

    wlanVSSRsnPreauthentication OBJECT-TYPE
	SYNTAX  INTEGER { enable(1), disable(2) }
	MAX-ACCESS  read-write
	STATUS  current
	DESCRIPTION
	    "When this object is set to TRUE, this shall indicate that RSNA
	    preauthentication is enabled on this entity.
	    This object requires that dot11RSNAEnabled also be set to TRUE."
	DEFVAL { enable }
    ::= { wlanVSSEntry 36 }

    wlanVSSBSSID OBJECT-TYPE
	SYNTAX MacAddress
	MAX-ACCESS  read-only
	STATUS  current
	DESCRIPTION
	    "This object contains the actual current BSSID for the service set."
    ::= { wlanVSSEntry 37 }

    wlanVSSWMMEnabled OBJECT-TYPE
	SYNTAX	TruthValue
        MAX-ACCESS read-write
        STATUS current
        DESCRIPTION
	    "This object defines whether WMM (Wi-Fi Multimedia)
	     is active for this service set.
	     Depending on the WLAN hardware and driver, WMM might
	     only be allowed for one service set, i.e. enabling WMM for one
	     service set disables WMM for all other service sets."
	DEFVAL { true }
    ::= { wlanVSSEntry 38 }

    wlanVSSTxMcAirtime OBJECT-TYPE
	SYNTAX	Counter64
	UNITS  "microseconds"
        MAX-ACCESS read-only
        STATUS current
        DESCRIPTION
	    "Accumulated estimated time in microseconds for all
	     broadcast/multicast frames transmitted."
    ::= { wlanVSSEntry 39 }

    wlanVSSRxAirtime OBJECT-TYPE
	SYNTAX	Counter64
	UNITS  "microseconds"
        MAX-ACCESS read-only
        STATUS current
        DESCRIPTION
	    "Accumulated estimated time in microseconds for all
	     unidirectional frames received from all stations."
    ::= { wlanVSSEntry 40 }

    wlanVSSTxUcAirtime OBJECT-TYPE
	SYNTAX	Counter64
	UNITS  "microseconds"
        MAX-ACCESS read-only
        STATUS current
        DESCRIPTION
	    "Accumulated estimated time in microseconds for all
	     unidirectional frames transmitted to all stations."
    ::= { wlanVSSEntry 41 }

    wlanVSSARPProcessing OBJECT-TYPE
	SYNTAX	TruthValue
        MAX-ACCESS read-write
        STATUS current
        DESCRIPTION
	    "This object defines whether ARP processing
	     is active for this service set or not.
	     ARP processing is a feature to reduce the number
	     of ARP broadcast packets. If the AP finds the
	     requested IP address in the node table it exchanges
	     the broadcast MAC address by the unicast MAC address
	     of the client.
	     Default is false."
	DEFVAL { false }
    ::= { wlanVSSEntry 42 }


    wlanVSSIgmpSnooping OBJECT-TYPE
	SYNTAX INTEGER { disabled(1), enabled(2),
            enabled-no-mac-translation(3) }
        MAX-ACCESS read-write
        STATUS current
        DESCRIPTION
	    "This object defines the mode off IGMP Snooping.
             disabled(1) means that IGMP Snooping is off and therefore
             all multicast is sent out. In mode enabled(2) multicast traffic
             is converted to unicast if a station has joined the traffic's
             multicast group via IGMP and therefor sent out to only this
             station. In mode enabled_no_mac_translation(3) multicast traffic
             is also only sent out if a station has joined the corresponding
             mcast group BUT isn't converted to unicast.
	     Default is disabled(1)."
	DEFVAL { disabled }
    ::= { wlanVSSEntry 43 }

-- **********************************************************************
-- *    End of wlanVSSTable  TABLE
-- **********************************************************************

-- **********************************************************************
-- *    wlanWDSTable  TABLE
-- **********************************************************************
    wlanWDSTable OBJECT-TYPE
	SYNTAX  SEQUENCE OF WlanWDSEntry
	MAX-ACCESS  not-accessible
        STATUS  current
	DESCRIPTION
	    "Describe a WLAN WDS and the corresponding settings."
    ::= { wlan 3 }

    wlanWDSEntry OBJECT-TYPE
	SYNTAX  WlanWDSEntry
	MAX-ACCESS  not-accessible
        STATUS  current
	DESCRIPTION
	  "WDS Link Configuration"
       INDEX   { wlanWDSAddress }
   ::= { wlanWDSTable 1 }

    WlanWDSEntry ::=
	 SEQUENCE {
	wlanWDSIndex		INTEGER,
	wlanWDSIfIndex		INTEGER,
	wlanWDSwlanIf		INTEGER,
	wlanWDSAdminStatus	INTEGER,
	wlanWDSAddress		MacAddress,
	wlanWDSPrivacyMode	INTEGER,
	wlanWDSOperStatus	TruthValue,
	wlanWDSPrivacyAutoKey	INTEGER,
	wlanWDSLinkAliasName	OCTET STRING,
	wlanWDSDefaultKey	INTEGER,
	wlanWDSPassPhrase	OCTET STRING,
	wlanWDSKey1		OCTET STRING,
	wlanWDSKey2		OCTET STRING,
	wlanWDSKey3		OCTET STRING,
	wlanWDSKey4		OCTET STRING,
	wlanWDSTransientKey	OCTET STRING,
	wlanWDSLocalAddress	MacAddress
	,
	-- statistics
	wlanWDSMSDUTx		Counter32,
	wlanWDSMSDURx		Counter32,
	wlanWDSBytesTx		Counter32,
	wlanWDSBytesRx		Counter32,
	wlanWDSCurrentRate	WlanRate,
	wlanWDSCurrentRSSI	WlanRSSI,
	wlanWDSCurrentRSSI1	WlanRSSI,
	wlanWDSCurrentRSSI2	WlanRSSI,
	wlanWDSCurrentRSSI3	WlanRSSI,
	wlanWDSCurrentNoise	WlanRSSI,
	wlanWDSTimeoutCount	Counter32,
	wlanWDSRxFrames54	Counter32,
	wlanWDSRxFrames48	Counter32,
	wlanWDSRxFrames36	Counter32,
	wlanWDSRxFrames24	Counter32,
	wlanWDSRxFrames18	Counter32,
	wlanWDSRxFrames12	Counter32,
	wlanWDSRxFrames11	Counter32,
	wlanWDSRxFrames9	Counter32,
	wlanWDSRxFrames6	Counter32,
	wlanWDSRxFrames5	Counter32,
	wlanWDSRxFrames2	Counter32,
	wlanWDSRxFrames1	Counter32,
	wlanWDSTxFrames54	Counter32,
	wlanWDSTxFrames48	Counter32,
	wlanWDSTxFrames36	Counter32,
	wlanWDSTxFrames24	Counter32,
	wlanWDSTxFrames18	Counter32,
	wlanWDSTxFrames12	Counter32,
	wlanWDSTxFrames11	Counter32,
	wlanWDSTxFrames9	Counter32,
	wlanWDSTxFrames6	Counter32,
	wlanWDSTxFrames5	Counter32,
	wlanWDSTxFrames2	Counter32,
	wlanWDSTxFrames1	Counter32
	}

    wlanWDSIndex OBJECT-TYPE
	SYNTAX  INTEGER (0..31)
	MAX-ACCESS  read-only
	STATUS  current
	DESCRIPTION
	    "Unique index of a WDS link "
	DEFVAL { 0 }
    ::= { wlanWDSEntry 1 }

    wlanWDSIfIndex OBJECT-TYPE
	SYNTAX  INTEGER
	MAX-ACCESS  read-only
	STATUS  current
	DESCRIPTION
	    "IfIndex of the WDS."
	DEFVAL { 0 }
    ::= { wlanWDSEntry 2 }

    wlanWDSwlanIf OBJECT-TYPE
	SYNTAX  INTEGER
	MAX-ACCESS read-create
	STATUS  current
	DESCRIPTION
	    "IfIndex of the  Interface the WDS belongs to."
    ::= { wlanWDSEntry 3 }

    wlanWDSAdminStatus OBJECT-TYPE
	SYNTAX  INTEGER { enable(1), disable(2), delete(3) }
	MAX-ACCESS read-create
	STATUS  current
	DESCRIPTION
	    "Enable or disable the requested WDS."
	DEFVAL { disable }
    ::= { wlanWDSEntry 4 }

    wlanWDSAddress OBJECT-TYPE
	SYNTAX  MacAddress
	MAX-ACCESS read-create
	STATUS  current
	DESCRIPTION
	    "MAC Address of the WDS partner."
    ::= { wlanWDSEntry 5 }

    wlanWDSPrivacyMode OBJECT-TYPE
	SYNTAX  INTEGER {
	    none(1),
--	    wep40default(2),
--	    wep104default(3),
	    wep40(4),
	    wep104(5),
	    tkip(6),
	    aes(7)
	    }
	MAX-ACCESS read-create
	STATUS  current
	DESCRIPTION
            "This attribute selects privacy mode to use for a
             WDS link. Privacy is immediately enabled if anything
             different from 'none' is selected and an appropriate
             key has been set.
             For wep40default(2) or wep104default(3) privacy, the
             default WEP keys are used, which are shared between
             all WDS links on a radio module."
        DEFVAL { none }
    ::= { wlanWDSEntry 6 }

    wlanWDSPrivacyAutoKey OBJECT-TYPE
	SYNTAX INTEGER (0..1)
	MAX-ACCESS read-create
	STATUS current
	DESCRIPTION
	    "Writing any non-zero value to this attribute triggers
	     automatic bridge privacy setup.
	     Depending on wlanWDSPrivacyMode, a pseudo-random
	     WEP key or passphrase is generated.
	     If non-empty keys have previously been set, writing
	     this attribute has no effect.
	     Reading this attribute always retuns 0."
	DEFVAL { 0 }
	::= { wlanWDSEntry 7 }

    wlanWDSLinkAliasName OBJECT-TYPE
        SYNTAX OCTET STRING (SIZE(0..13))
        MAX-ACCESS read-create
        STATUS current
        DESCRIPTION
            "This attribute can be used to set a textual alias
             name for this bridge link. Default is 'wl?_br?',
             where first '?' is radio number and second '?'
             is link number on this radio."
	::= { wlanWDSEntry 8 }

    wlanWDSOperStatus OBJECT-TYPE
	SYNTAX  TruthValue
	MAX-ACCESS  read-only
	STATUS  current
	DESCRIPTION
	"This attribute shows if the bridge link
	 connection is currently operative."
    ::= { wlanWDSEntry 9 }

    wlanWDSDefaultKey OBJECT-TYPE
	SYNTAX  INTEGER { key1(1), key2(2), key3(3), key4(4) }
	MAX-ACCESS read-create
	STATUS  current
	DESCRIPTION
	    "Number of the WEP key to use for
	     encryption of outgoing WDS frames."
	DEFVAL { key1 }
    ::= { wlanWDSEntry 10 }

    wlanWDSKey1 OBJECT-TYPE
	SYNTAX  OCTET STRING  (SIZE(0..13))
	MAX-ACCESS read-create
	STATUS  current
	DESCRIPTION
	    "Key string for WEP key nr. 1.
	     Allowed number of octets are 5 for WEP-40 and 13 for WEP-104."
	DEFVAL { "" }
    ::= { wlanWDSEntry 11 }

    wlanWDSKey2 OBJECT-TYPE
	SYNTAX  OCTET STRING  (SIZE(0..13))
	MAX-ACCESS read-create
	STATUS  current
	DESCRIPTION
	    "Key string for WEP key nr. 2.
	     Allowed number of octets are 5 for WEP-40 and 13 for WEP-104."
	DEFVAL { "" }
    ::= { wlanWDSEntry 12 }

    wlanWDSKey3 OBJECT-TYPE
	SYNTAX  OCTET STRING  (SIZE(0..13))
	MAX-ACCESS read-create
	STATUS  current
	DESCRIPTION
	    "Key string for WEP key nr. 3.
	     Allowed number of octets are 5 for WEP-40 and 13 for WEP-104."
	DEFVAL { "" }
    ::= { wlanWDSEntry 13 }

    wlanWDSKey4 OBJECT-TYPE
	SYNTAX  OCTET STRING  (SIZE(0..13))
	MAX-ACCESS read-create
	STATUS  current
	DESCRIPTION
	    "Key string for WEP key nr. 4.
	     Allowed number of octets are 5 for WEP-40 and 13 for WEP-104."
	DEFVAL { "" }
    ::= { wlanWDSEntry 14 }

    wlanWDSPassPhrase OBJECT-TYPE
	SYNTAX  OCTET STRING  (SIZE(0..64))
	MAX-ACCESS read-create
	STATUS  current
	DESCRIPTION
	    "Passphrase string for WDS encryption type TKIP and AES."
	DEFVAL { "" }
    ::= { wlanWDSEntry 15 }

   wlanWDSMSDUTx OBJECT-TYPE
	SYNTAX  Counter32
	MAX-ACCESS  read-only
	STATUS  current
	DESCRIPTION
        "This attribute counts the total number of
         packets transmitted on this WDS link."
    ::= { wlanWDSEntry 17 }

    wlanWDSMSDURx OBJECT-TYPE
	SYNTAX  Counter32
	MAX-ACCESS  read-only
	STATUS  current
	DESCRIPTION
        "This attribute counts the total number of
         packets received on this WDS link."
    ::= { wlanWDSEntry 18 }

    wlanWDSBytesTx OBJECT-TYPE
	SYNTAX  Counter32
	MAX-ACCESS  read-only
	STATUS  current
	DESCRIPTION
        "This attribute counts the total number of
         octets transmitted on this WDS link."
    ::= { wlanWDSEntry 19 }

    wlanWDSBytesRx OBJECT-TYPE
	SYNTAX  Counter32
	MAX-ACCESS  read-only
	STATUS  current
	DESCRIPTION
        "This attribute counts the total number of
         octets received on this WDS link."
    ::= { wlanWDSEntry 20 }

    wlanWDSCurrentRate OBJECT-TYPE
	SYNTAX  WlanRate
	MAX-ACCESS  read-only
	STATUS  current
	DESCRIPTION
	"This attribute returns the current receive data rate
	 for this link in 500 Kbps units, or 0 if no connection can be established."
    ::= { wlanWDSEntry 21 }

    wlanWDSCurrentRSSI OBJECT-TYPE
	SYNTAX  WlanRSSI
	UNITS "dBm"
	MAX-ACCESS  read-only
	STATUS  current
	DESCRIPTION
	"This attribute returns the current receive signal strength
	 for this link, or 0 if no connection can be established."
    ::= { wlanWDSEntry 22 }

    wlanWDSCurrentNoise OBJECT-TYPE
	SYNTAX  WlanRSSI
	UNITS "dBm"
	MAX-ACCESS  read-only
	STATUS  current
	DESCRIPTION
	"This attribute shows the measured noise level in dBm, or
	 0 if no connection can be established."
    ::= { wlanWDSEntry 23 }

    wlanWDSTransientKey OBJECT-TYPE
	SYNTAX  OCTET STRING  (SIZE(16..32))
	MAX-ACCESS  not-accessible
	STATUS  current
	DESCRIPTION
	    "Transient key generated from Passphrase string for WDS encryption type TKIP and AES."
    ::= { wlanWDSEntry 24 }

    wlanWDSLocalAddress OBJECT-TYPE
	SYNTAX  MacAddress
	MAX-ACCESS read-create
	STATUS  current
	DESCRIPTION
	    "Local MAC Address for the WDS link."
    ::= { wlanWDSEntry 25 }

    wlanWDSTimeoutCount OBJECT-TYPE
	SYNTAX  Counter32
	MAX-ACCESS  not-accessible
	STATUS  current
	DESCRIPTION
	"This counter increments every second if no packets are
	 received from link partner.
	 If a certain threshold is reached, an ArbopAnnounceLinkUp
	 packet is transmitted in order to resynchronize the bridge partners."
    ::= { wlanWDSEntry 26 }

    wlanWDSRxFrames54 OBJECT-TYPE
        SYNTAX Counter32
        MAX-ACCESS read-only
        STATUS current
        DESCRIPTION
            "This attribute shows the number of data
             frames that were received at 54 Mbps."
	::= { wlanWDSEntry 27 }

    wlanWDSRxFrames48 OBJECT-TYPE
        SYNTAX Counter32
        MAX-ACCESS read-only
        STATUS current
        DESCRIPTION
            "This attribute shows the number of data
             frames that were received at 48 Mbps."
	::= { wlanWDSEntry 28 }

    wlanWDSRxFrames36 OBJECT-TYPE
        SYNTAX Counter32
        MAX-ACCESS read-only
        STATUS current
        DESCRIPTION
            "This attribute shows the number of data
             frames that were received at 36 Mbps."
	::= { wlanWDSEntry 29 }

    wlanWDSRxFrames24 OBJECT-TYPE
        SYNTAX Counter32
        MAX-ACCESS read-only
        STATUS current
        DESCRIPTION
            "This attribute shows the number of data
             frames that were received at 24 Mbps."
	::= { wlanWDSEntry 30 }

    wlanWDSRxFrames18 OBJECT-TYPE
        SYNTAX Counter32
        MAX-ACCESS read-only
        STATUS current
        DESCRIPTION
            "This attribute shows the number of data
             frames that were received at 18 Mbps."
	::= { wlanWDSEntry 31 }

    wlanWDSRxFrames12 OBJECT-TYPE
        SYNTAX Counter32
        MAX-ACCESS read-only
        STATUS current
        DESCRIPTION
            "This attribute shows the number of data
             frames that were received at 12 Mbps."
	::= { wlanWDSEntry 32 }

    wlanWDSRxFrames11 OBJECT-TYPE
        SYNTAX Counter32
        MAX-ACCESS read-only
        STATUS current
        DESCRIPTION
            "This attribute shows the number of data
             frames that were received at 11 Mbps."
	::= { wlanWDSEntry 33 }

    wlanWDSRxFrames9 OBJECT-TYPE
        SYNTAX Counter32
        MAX-ACCESS read-only
        STATUS current
        DESCRIPTION
            "This attribute shows the number of data
             frames that were received at 9 Mbps."
	::= { wlanWDSEntry 34 }

    wlanWDSRxFrames6 OBJECT-TYPE
        SYNTAX Counter32
        MAX-ACCESS read-only
        STATUS current
        DESCRIPTION
            "This attribute shows the number of data
             frames that were received at 6 Mbps."
	::= { wlanWDSEntry 35 }

    wlanWDSRxFrames5 OBJECT-TYPE
        SYNTAX Counter32
        MAX-ACCESS read-only
        STATUS current
        DESCRIPTION
            "This attribute shows the number of data
             frames that were received at 5.5 Mbps."
	::= { wlanWDSEntry 36 }

    wlanWDSRxFrames2 OBJECT-TYPE
        SYNTAX Counter32
        MAX-ACCESS read-only
        STATUS current
        DESCRIPTION
            "This attribute shows the number of data
             frames that were received at 2 Mbps."
	::= { wlanWDSEntry 37 }

    wlanWDSRxFrames1 OBJECT-TYPE
        SYNTAX Counter32
        MAX-ACCESS read-only
        STATUS current
        DESCRIPTION
            "This attribute shows the number of data
             frames that were received at 1 Mbps."
	::= { wlanWDSEntry 38 }

    wlanWDSTxFrames54 OBJECT-TYPE
        SYNTAX Counter32
        MAX-ACCESS read-only
        STATUS current
        DESCRIPTION
            "This attribute shows the number of data
             frames that were transmitted at 54 Mbps."
	::= { wlanWDSEntry 39 }

    wlanWDSTxFrames48 OBJECT-TYPE
        SYNTAX Counter32
        MAX-ACCESS read-only
        STATUS current
        DESCRIPTION
            "This attribute shows the number of data
             frames that were transmitted at 48 Mbps."
	::= { wlanWDSEntry 40 }

    wlanWDSTxFrames36 OBJECT-TYPE
        SYNTAX Counter32
        MAX-ACCESS read-only
        STATUS current
        DESCRIPTION
            "This attribute shows the number of data
             frames that were transmitted at 36 Mbps."
	::= { wlanWDSEntry 41 }

    wlanWDSTxFrames24 OBJECT-TYPE
        SYNTAX Counter32
        MAX-ACCESS read-only
        STATUS current
        DESCRIPTION
            "This attribute shows the number of data
             frames that were transmitted at 24 Mbps."
	::= { wlanWDSEntry 42 }

    wlanWDSTxFrames18 OBJECT-TYPE
        SYNTAX Counter32
        MAX-ACCESS read-only
        STATUS current
        DESCRIPTION
            "This attribute shows the number of data
             frames that were transmitted at 18 Mbps."
	::= { wlanWDSEntry 43 }

    wlanWDSTxFrames12 OBJECT-TYPE
        SYNTAX Counter32
        MAX-ACCESS read-only
        STATUS current
        DESCRIPTION
            "This attribute shows the number of data
             frames that were transmitted at 12 Mbps."
	::= { wlanWDSEntry 44 }

    wlanWDSTxFrames11 OBJECT-TYPE
        SYNTAX Counter32
        MAX-ACCESS read-only
        STATUS current
        DESCRIPTION
            "This attribute shows the number of data
             frames that were transmitted at 11 Mbps."
	::= { wlanWDSEntry 45 }

    wlanWDSTxFrames9 OBJECT-TYPE
        SYNTAX Counter32
        MAX-ACCESS read-only
        STATUS current
        DESCRIPTION
            "This attribute shows the number of data
             frames that were transmitted at 9 Mbps."
	::= { wlanWDSEntry 46 }

    wlanWDSTxFrames6 OBJECT-TYPE
        SYNTAX Counter32
        MAX-ACCESS read-only
        STATUS current
        DESCRIPTION
            "This attribute shows the number of data
             frames that were transmitted at 6 Mbps."
	::= { wlanWDSEntry 47 }

    wlanWDSTxFrames5 OBJECT-TYPE
        SYNTAX Counter32
        MAX-ACCESS read-only
        STATUS current
        DESCRIPTION
            "This attribute shows the number of data
             frames that were transmitted at 5.5 Mbps."
	::= { wlanWDSEntry 48 }

    wlanWDSTxFrames2 OBJECT-TYPE
        SYNTAX Counter32
        MAX-ACCESS read-only
        STATUS current
        DESCRIPTION
            "This attribute shows the number of data
             frames that were transmitted at 2 Mbps."
	::= { wlanWDSEntry 49 }

    wlanWDSTxFrames1 OBJECT-TYPE
        SYNTAX Counter32
        MAX-ACCESS read-only
        STATUS current
        DESCRIPTION
            "This attribute shows the number of data
             frames that were transmitted at 1 Mbps."
	::= { wlanWDSEntry 50 }

    wlanWDSCurrentRSSI1 OBJECT-TYPE
	SYNTAX  WlanRSSI
	UNITS "dBm"
	MAX-ACCESS  read-only
	STATUS  current
	DESCRIPTION
	"This attribute returns the current receive signal strength
	 on the first receiver for this link, or 0 if no connection
	 can be established."
    ::= { wlanWDSEntry 51 }

    wlanWDSCurrentRSSI2 OBJECT-TYPE
	SYNTAX  WlanRSSI
	UNITS "dBm"
	MAX-ACCESS  read-only
	STATUS  current
	DESCRIPTION
	"This attribute returns the current receive signal strength
	 on the second receiver for this link, or 0 if no second
	 receiver present or no connection can be established."
    ::= { wlanWDSEntry 52 }

    wlanWDSCurrentRSSI3 OBJECT-TYPE
	SYNTAX  WlanRSSI
	UNITS "dBm"
	MAX-ACCESS  read-only
	STATUS  current
	DESCRIPTION
	"This attribute returns the current receive signal strength
	 on the third receiver for this link, or 0 if no third
	 receiver present or no connection can be established."
    ::= { wlanWDSEntry 53 }

-- **********************************************************************
-- *    End of wlanWDSTable  TABLE
-- **********************************************************************
--  ::= { wlan 4 }        this OID is obsolete

-- **********************************************************************
-- *    wlanStationTable  TABLE
-- **********************************************************************
wlanStationTable OBJECT-TYPE
    SYNTAX  SEQUENCE OF WlanStationEntry
    MAX-ACCESS  not-accessible
    STATUS  current
    DESCRIPTION
            "The wlanStationTable contains information relating to the
             clients currently associated to our access points.
             Each entry corresponds to
             an associated client station (STA).
             Entries cannot be added or deleted by the user.

             Creating entries: Entries are created by the system
             automatically when a new STA ia associated.

             Deleting entries: Entries are removed by the system
             whenever an associated STA is removed."
    ::= { wlan 5 }

    wlanStationEntry OBJECT-TYPE
	SYNTAX  WlanStationEntry
	MAX-ACCESS  not-accessible
	STATUS  current
	DESCRIPTION
	""
	INDEX   { wlanStationAddress }
    ::= { wlanStationTable 1 }

    WlanStationEntry ::=
	SEQUENCE {
                wlanStationIfIndex	INTEGER,
		wlanStationAddress	MacAddress,
		wlanStationVSSIndex	INTEGER,
		wlanStationState	INTEGER,
		wlanStationSecurity	INTEGER,
		wlanStationNode		INTEGER,
		wlanStationMSDUTx	Counter32,
		wlanStationMSDURx	Counter32,
		wlanStationBytesRx	Counter32,
		wlanStationBytesTx	Counter32,
		wlanStationRate         WlanRate,
		wlanStationSignal       WlanRSSI,
		wlanStationRSSI1	WlanRSSI,
		wlanStationRSSI2	WlanRSSI,
		wlanStationRSSI3	WlanRSSI,
		wlanStationNoise	WlanRSSI,
		wlanStationConnectTime	Counter32,
		wlanStationTimeoutTStamp	Counter32,
		wlanStationTimeoutCount		Counter32,
		wlanStationRxFrames54	Counter32,
		wlanStationRxFrames48	Counter32,
		wlanStationRxFrames36	Counter32,
		wlanStationRxFrames24	Counter32,
		wlanStationRxFrames18	Counter32,
		wlanStationRxFrames12	Counter32,
		wlanStationRxFrames11	Counter32,
		wlanStationRxFrames9	Counter32,
		wlanStationRxFrames6	Counter32,
		wlanStationRxFrames5	Counter32,
		wlanStationRxFrames2	Counter32,
		wlanStationRxFrames1	Counter32,
		wlanStationTxFrames54	Counter32,
		wlanStationTxFrames48	Counter32,
		wlanStationTxFrames36	Counter32,
		wlanStationTxFrames24	Counter32,
		wlanStationTxFrames18	Counter32,
		wlanStationTxFrames12	Counter32,
		wlanStationTxFrames11	Counter32,
		wlanStationTxFrames9	Counter32,
		wlanStationTxFrames6	Counter32,
		wlanStationTxFrames5	Counter32,
		wlanStationTxFrames2	Counter32,
		wlanStationTxFrames1	Counter32,

		wlanStationIpAddress	IpAddress,
		wlanStationRxAirtime	Counter64,
		wlanStationTxAirtime    Counter64,
		wlanStationCapabilities BITS,
		wlanStationLastSeen	Date,
		wlanStationRxDiscards   Counter32,
		wlanStationTxDiscards   Counter32
	}

    wlanStationIfIndex OBJECT-TYPE
	SYNTAX  INTEGER
	MAX-ACCESS  read-only
	STATUS  current
	DESCRIPTION
	    "The WLAN radio index."
    ::= { wlanStationEntry 1 }

    wlanStationAddress OBJECT-TYPE
	SYNTAX  MacAddress
	MAX-ACCESS  read-only
	STATUS  current
	DESCRIPTION
	    "MAC Address of the Assigned STA."
    ::= { wlanStationEntry 2 }

    wlanStationVSSIndex OBJECT-TYPE
	SYNTAX  INTEGER
	MAX-ACCESS  read-only
	STATUS  current
	DESCRIPTION
	    "The ifindex of the associated Service Set."
    ::= { wlanStationEntry 3 }


    wlanStationState OBJECT-TYPE
	SYNTAX  INTEGER {
		    none(1),
		    associating(2),
		    associated(3),
		    authenticate(4),
		    authenticated(5),
--		    wds(6),				this OID is obsolete
--		    ibss(7),			this OID is obsolete
		    delete(8)
		    }
	MAX-ACCESS  read-write
	STATUS  current
	DESCRIPTION
	    ""
	DEFVAL { none }
    ::= { wlanStationEntry 4 }

    wlanStationSecurity OBJECT-TYPE
	SYNTAX  INTEGER {
		    none(1),
		    wep40(2),
		    wep104(3),
		    wpa-psk(4),
		    wpa(5),
		    wpa2(6)
		}
	MAX-ACCESS  read-only
	STATUS  current
	DESCRIPTION
	    "The Security Option of the Station."
	DEFVAL { none }
    ::= { wlanStationEntry 5 }

    wlanStationNode OBJECT-TYPE
	SYNTAX  INTEGER { unknown(1), access-point(2), client(3) }
	MAX-ACCESS  read-only
	STATUS  current
	DESCRIPTION
                ""
	DEFVAL { client }
    ::= { wlanStationEntry 6 }

--  ::= { wlanStationEntry 7 }        this OID is obsolete

    wlanStationMSDUTx OBJECT-TYPE
	SYNTAX  Counter32
	MAX-ACCESS  read-only
	STATUS  current
	DESCRIPTION
            "This attribute counts the total number of
             packets transmitted to this station."
	DEFVAL { 0 }
    ::= { wlanStationEntry 8 }

    wlanStationMSDURx OBJECT-TYPE
	SYNTAX  Counter32
	MAX-ACCESS  read-only
	STATUS  current
	DESCRIPTION
            "This attribute counts the total number of
             packets received from this station."
	DEFVAL { 0 }
    ::= { wlanStationEntry 9 }

    wlanStationBytesTx OBJECT-TYPE
	SYNTAX  Counter32
	MAX-ACCESS  read-only
	STATUS  current
	DESCRIPTION
            "This attribute counts the total number of
             octets transmitted to this station."
	DEFVAL { 0 }
    ::= { wlanStationEntry 10 }

    wlanStationBytesRx OBJECT-TYPE
	SYNTAX  Counter32
	MAX-ACCESS  read-only
	STATUS  current
	DESCRIPTION
            "This attribute counts the total number of
             octets received from this station."
	DEFVAL { 0 }
    ::= { wlanStationEntry 11 }

    wlanStationRate OBJECT-TYPE
	SYNTAX  WlanRate
	MAX-ACCESS  read-only
	STATUS  current
	DESCRIPTION
            "This attribute reflects the data rate of the latest
             packet received from this station, in 500 kbps units."
	DEFVAL { 0 }
    ::= { wlanStationEntry 12 }

    wlanStationSignal OBJECT-TYPE
	SYNTAX  WlanRSSI
	UNITS "dBm"
	MAX-ACCESS  read-only
	STATUS  current
	DESCRIPTION
            "This attribute shows the received signal strength in dBm."
	DEFVAL { 0 }
    ::= { wlanStationEntry 13 }

    wlanStationNoise OBJECT-TYPE
	SYNTAX  WlanRSSI
	UNITS "dBm"
	MAX-ACCESS  read-only
	STATUS  current
	DESCRIPTION
	    "This attribute shows the measured noise level in dBm, or
	     0 if no connection can be established."
	DEFVAL { 0 }
    ::= { wlanStationEntry 14 }

    wlanStationConnectTime OBJECT-TYPE
        SYNTAX Counter32
	UNITS "s"
        MAX-ACCESS read-only
        STATUS current
        DESCRIPTION
            "This attribute records the system uptime at the moment
             the client successfully finished association."
	::= { wlanStationEntry 15 }

	wlanStationTimeoutTStamp OBJECT-TYPE
        SYNTAX Counter32
        MAX-ACCESS not-accessible
        STATUS current
        DESCRIPTION
                "Internal time stamp of the most recent STA timeout poll."
	    DEFVAL { 0 }
	::= { wlanStationEntry 16 }

	wlanStationTimeoutCount OBJECT-TYPE
        SYNTAX Counter32
        MAX-ACCESS not-accessible
        STATUS current
        DESCRIPTION
                "Internal counter for number of polls sent to the STA without reply."
	    DEFVAL { 0 }
	::= { wlanStationEntry 17 }

    wlanStationRxFrames54 OBJECT-TYPE
        SYNTAX Counter32
        MAX-ACCESS read-only
        STATUS current
        DESCRIPTION
            "This attribute shows the number of data
             frames that were received at 54 Mbps."
	::= { wlanStationEntry 30 }

    wlanStationRxFrames48 OBJECT-TYPE
        SYNTAX Counter32
        MAX-ACCESS read-only
        STATUS current
        DESCRIPTION
            "This attribute shows the number of data
             frames that were received at 48 Mbps."
	::= { wlanStationEntry 31 }

    wlanStationRxFrames36 OBJECT-TYPE
        SYNTAX Counter32
        MAX-ACCESS read-only
        STATUS current
        DESCRIPTION
            "This attribute shows the number of data
             frames that were received at 36 Mbps."
	::= { wlanStationEntry 32 }

    wlanStationRxFrames24 OBJECT-TYPE
        SYNTAX Counter32
        MAX-ACCESS read-only
        STATUS current
        DESCRIPTION
            "This attribute shows the number of data
             frames that were received at 24 Mbps."
	::= { wlanStationEntry 33 }

    wlanStationRxFrames18 OBJECT-TYPE
        SYNTAX Counter32
        MAX-ACCESS read-only
        STATUS current
        DESCRIPTION
            "This attribute shows the number of data
             frames that were received at 18 Mbps."
	::= { wlanStationEntry 34 }

    wlanStationRxFrames12 OBJECT-TYPE
        SYNTAX Counter32
        MAX-ACCESS read-only
        STATUS current
        DESCRIPTION
            "This attribute shows the number of data
             frames that were received at 12 Mbps."
	::= { wlanStationEntry 35 }

    wlanStationRxFrames11 OBJECT-TYPE
        SYNTAX Counter32
        MAX-ACCESS read-only
        STATUS current
        DESCRIPTION
            "This attribute shows the number of data
             frames that were received at 11 Mbps."
	::= { wlanStationEntry 36 }

    wlanStationRxFrames9 OBJECT-TYPE
        SYNTAX Counter32
        MAX-ACCESS read-only
        STATUS current
        DESCRIPTION
            "This attribute shows the number of data
             frames that were received at 9 Mbps."
	::= { wlanStationEntry 37 }

    wlanStationRxFrames6 OBJECT-TYPE
        SYNTAX Counter32
        MAX-ACCESS read-only
        STATUS current
        DESCRIPTION
            "This attribute shows the number of data
             frames that were received at 6 Mbps."
	::= { wlanStationEntry 38 }

    wlanStationRxFrames5 OBJECT-TYPE
        SYNTAX Counter32
        MAX-ACCESS read-only
        STATUS current
        DESCRIPTION
            "This attribute shows the number of data
             frames that were received at 5.5 Mbps."
	::= { wlanStationEntry 39 }

    wlanStationRxFrames2 OBJECT-TYPE
        SYNTAX Counter32
        MAX-ACCESS read-only
        STATUS current
        DESCRIPTION
            "This attribute shows the number of data
             frames that were received at 2 Mbps."
	::= { wlanStationEntry 40 }

    wlanStationRxFrames1 OBJECT-TYPE
        SYNTAX Counter32
        MAX-ACCESS read-only
        STATUS current
        DESCRIPTION
            "This attribute shows the number of data
             frames that were received at 1 Mbps."
	::= { wlanStationEntry 41 }

    wlanStationTxFrames54 OBJECT-TYPE
        SYNTAX Counter32
        MAX-ACCESS read-only
        STATUS current
        DESCRIPTION
            "This attribute shows the number of data
             frames that were transmitted at 54 Mbps."
	::= { wlanStationEntry 42 }

    wlanStationTxFrames48 OBJECT-TYPE
        SYNTAX Counter32
        MAX-ACCESS read-only
        STATUS current
        DESCRIPTION
            "This attribute shows the number of data
             frames that were transmitted at 48 Mbps."
	::= { wlanStationEntry 43 }

    wlanStationTxFrames36 OBJECT-TYPE
        SYNTAX Counter32
        MAX-ACCESS read-only
        STATUS current
        DESCRIPTION
            "This attribute shows the number of data
             frames that were transmitted at 36 Mbps."
	::= { wlanStationEntry 44 }

    wlanStationTxFrames24 OBJECT-TYPE
        SYNTAX Counter32
        MAX-ACCESS read-only
        STATUS current
        DESCRIPTION
            "This attribute shows the number of data
             frames that were transmitted at 24 Mbps."
	::= { wlanStationEntry 45 }

    wlanStationTxFrames18 OBJECT-TYPE
        SYNTAX Counter32
        MAX-ACCESS read-only
        STATUS current
        DESCRIPTION
            "This attribute shows the number of data
             frames that were transmitted at 18 Mbps."
	::= { wlanStationEntry 46 }

    wlanStationTxFrames12 OBJECT-TYPE
        SYNTAX Counter32
        MAX-ACCESS read-only
        STATUS current
        DESCRIPTION
            "This attribute shows the number of data
             frames that were transmitted at 12 Mbps."
	::= { wlanStationEntry 47 }

    wlanStationTxFrames11 OBJECT-TYPE
        SYNTAX Counter32
        MAX-ACCESS read-only
        STATUS current
        DESCRIPTION
            "This attribute shows the number of data
             frames that were transmitted at 11 Mbps."
	::= { wlanStationEntry 48 }

    wlanStationTxFrames9 OBJECT-TYPE
        SYNTAX Counter32
        MAX-ACCESS read-only
        STATUS current
        DESCRIPTION
            "This attribute shows the number of data
             frames that were transmitted at 9 Mbps."
	::= { wlanStationEntry 49 }

    wlanStationTxFrames6 OBJECT-TYPE
        SYNTAX Counter32
        MAX-ACCESS read-only
        STATUS current
        DESCRIPTION
            "This attribute shows the number of data
             frames that were transmitted at 6 Mbps."
	::= { wlanStationEntry 50 }

    wlanStationTxFrames5 OBJECT-TYPE
        SYNTAX Counter32
        MAX-ACCESS read-only
        STATUS current
        DESCRIPTION
            "This attribute shows the number of data
             frames that were transmitted at 5.5 Mbps."
	::= { wlanStationEntry 51 }

    wlanStationTxFrames2 OBJECT-TYPE
        SYNTAX Counter32
        MAX-ACCESS read-only
        STATUS current
        DESCRIPTION
            "This attribute shows the number of data
             frames that were transmitted at 2 Mbps."
	::= { wlanStationEntry 52 }

    wlanStationTxFrames1 OBJECT-TYPE
        SYNTAX Counter32
        MAX-ACCESS read-only
        STATUS current
        DESCRIPTION
            "This attribute shows the number of data
             frames that were transmitted at 1 Mbps."
	::= { wlanStationEntry 53 }

    wlanStationIpAddress OBJECT-TYPE
        SYNTAX IpAddress
        MAX-ACCESS read-only
        STATUS current
        DESCRIPTION
            "This attribute shows the IP address of the client.
             It is only available if any IP frames have been
             received from the client."
	DEFVAL { '00000000'h }
	::= { wlanStationEntry 54 }

    wlanStationRSSI1 OBJECT-TYPE
	SYNTAX  WlanRSSI
	UNITS "dBm"
	MAX-ACCESS  read-only
	STATUS  current
	DESCRIPTION
            "This attribute shows the received signal strength at the
            first receiver in dBm. The value 0 indicates no connection."
	DEFVAL { 0 }
    ::= { wlanStationEntry 55 }

    wlanStationRSSI2 OBJECT-TYPE
	SYNTAX  WlanRSSI
	UNITS "dBm"
	MAX-ACCESS  read-only
	STATUS  current
	DESCRIPTION
            "This attribute shows the received signal strength at the
            second receiver in dBm. The value 0 indicates no connection
            or no second receiver present."
	DEFVAL { 0 }
    ::= { wlanStationEntry 56 }

    wlanStationRSSI3 OBJECT-TYPE
	SYNTAX  WlanRSSI
	UNITS "dBm"
	MAX-ACCESS  read-only
	STATUS  current
	DESCRIPTION
            "This attribute shows the received signal strength at the
            third receiver in dBm. The value 0 indicates no connection
            or no third receiver present."
	DEFVAL { 0 }
    ::= { wlanStationEntry 57 }

    wlanStationRxAirtime OBJECT-TYPE
        SYNTAX Counter64
	UNITS  "microseconds"
        MAX-ACCESS read-only
        STATUS current
        DESCRIPTION
	    "Accumulated estimated time in microseconds for all
	     unidirectional frames received from this station."
	::= { wlanStationEntry 82 }

    wlanStationTxAirtime OBJECT-TYPE
        SYNTAX Counter64
	UNITS  "microseconds"
        MAX-ACCESS read-only
        STATUS current
        DESCRIPTION
	    "Accumulated estimated time in microseconds for all
	     unidirectional frames transmitted to this station."
	::= { wlanStationEntry 83 }

    wlanStationCapabilities OBJECT-TYPE
        SYNTAX BITS {
		uapsd-vo(0),
		uapsd-vi(1),
		uapsd-bk(2),
		uapsd-be(3)
	    }
        MAX-ACCESS read-only
        STATUS current
        DESCRIPTION
	    "This field contains supported capabilities of a station.
	     uapsd-vo := AC_VO U-APSD Flag enabled
	     uapsd-vi := AC_VI U-APSD Flag enabled
	     uapsd-bk := AC_BK U-APSD Flag enabled
	     uapsd-be := AC_BE U-APSD Flag enabled
	    "
	DEFVAL { { } }
	::= { wlanStationEntry 84 }

    wlanStationLastSeen OBJECT-TYPE
	SYNTAX  Date
	MAX-ACCESS  read-only
	STATUS  current
	DESCRIPTION
	    "Timestamp of the last received frame by this Station"
	DEFVAL { 0 }
    ::= { wlanStationEntry 85 }

    wlanStationRxDiscards OBJECT-TYPE
        SYNTAX Counter32
	UNITS  "bytes"
        MAX-ACCESS read-only
        STATUS current
        DESCRIPTION
	    "Count of discarded bytes due to bandwidth limitation.
             see wlanVSSStationRxShaping"
	DEFVAL { 0 }
	::= { wlanStationEntry 86 }

    wlanStationTxDiscards OBJECT-TYPE
        SYNTAX Counter32
	UNITS  "bytes"
        MAX-ACCESS read-only
        STATUS current
        DESCRIPTION
	    "Count of discarded bytes due to bandwidth limitation.
             see wlanVSSStationTxShaping"
	DEFVAL { 0 }
	::= { wlanStationEntry 87 }

-- **********************************************************************
-- *    End of wlanStationTable  TABLE
-- **********************************************************************

-- **********************************************************************
-- *    wlanMACTable  TABLE
-- **********************************************************************
wlanMACTable OBJECT-TYPE
    SYNTAX  SEQUENCE OF WlanMACEntry
    MAX-ACCESS  not-accessible
    STATUS  current
    DESCRIPTION
	"The wlanStationTable contains information relating to the
                interfaces available on the system. Each entry corresponds to
                an available wlan interface. Entries cannot be added or
	deleted by the user.

                Creating entries: Entries are created by the system
                automatically when a new wlan module is installed.

                Deleting entries: Entries are removed by the system
                after the appropriate wlan module is removed."
    ::= { wlan 6 }

    wlanMACEntry OBJECT-TYPE
	SYNTAX  WlanMACEntry
	MAX-ACCESS  not-accessible
	STATUS  current
	DESCRIPTION
	    ""
	INDEX   { wlanMACAddress }
    ::= { wlanMACTable 1 }

    WlanMACEntry ::=
	SEQUENCE {
	    wlanMACAddress	OCTET STRING,
	    wlanMACIfIndex	INTEGER,
	    wlanMACRule		INTEGER,
	    wlanMACMask		OCTET STRING
	}

    wlanMACAddress OBJECT-TYPE
	SYNTAX  OCTET STRING  (SIZE(0..6))
	MAX-ACCESS  read-write
	STATUS  current
	DESCRIPTION
	    " The Objects MAC Address "
	DEFVAL { "" }
    ::= { wlanMACEntry 1 }

    wlanMACIfIndex OBJECT-TYPE
	SYNTAX  INTEGER
	MAX-ACCESS  read-write
	STATUS  current
	DESCRIPTION
	    " The Objects associated WLAN Hardware "
	DEFVAL { "" }
    ::= { wlanMACEntry 2 }

    wlanMACRule OBJECT-TYPE
	SYNTAX  INTEGER { accept(1), delete(8) }
	MAX-ACCESS  read-write
	STATUS  current
	DESCRIPTION
	    " The Rule of the MAC Object "
	DEFVAL { accept }
    ::= { wlanMACEntry 3 }

    wlanMACMask OBJECT-TYPE
	SYNTAX  OCTET STRING  (SIZE(0..32))
	MAX-ACCESS  read-write
	STATUS  current
	DESCRIPTION
	    " Service Sets associated with this Object max. 256 Bit "
	DEFVAL { "" }
    ::= { wlanMACEntry 4 }

-- **********************************************************************
-- *    End of wlanMACTable  TABLE
-- **********************************************************************

-- **********************************************************************
-- *    wlanACLDeniedTable  TABLE
-- **********************************************************************
wlanACLDeniedTable OBJECT-TYPE
    SYNTAX  SEQUENCE OF WlanACLDeniedEntry
    MAX-ACCESS  not-accessible
    STATUS  current
    DESCRIPTION
	"Contains all MAC Addresses of denied clients"
    ::= { wlan 7 }

    wlanACLDeniedEntry OBJECT-TYPE
	SYNTAX  WlanACLDeniedEntry
	MAX-ACCESS  not-accessible
	STATUS  current
	DESCRIPTION
	""
	INDEX   { wlanACLDeniedAddress, wlanACLDeniedIfIndex }
    ::= { wlanACLDeniedTable 1 }

    WlanACLDeniedEntry ::=
	SEQUENCE {
	    wlanACLDeniedAddress    MacAddress,
	    wlanACLDeniedIfIndex    INTEGER,
	    wlanACLDeniedCount	INTEGER,
	    wlanACLDeniedAge	INTEGER
	}

    wlanACLDeniedAddress OBJECT-TYPE
	SYNTAX       MacAddress
	MAX-ACCESS   read-only
	STATUS	 current
	DESCRIPTION
	    "The MAC Address of the denied Client"
    ::= { wlanACLDeniedEntry 1 }

    wlanACLDeniedIfIndex OBJECT-TYPE
	SYNTAX  INTEGER
	MAX-ACCESS	read-only
	STATUS  current
	DESCRIPTION
	    "The Interface the Deniued Address belongs to"
	DEFVAL { 0 }
    ::= { wlanACLDeniedEntry 2 }

    wlanACLDeniedCount OBJECT-TYPE
	SYNTAX  INTEGER
	MAX-ACCESS  read-only
	STATUS  current
	DESCRIPTION
	    "The count of detected denies to this MAC Address"
	DEFVAL { 0 }
    ::= { wlanACLDeniedEntry 3 }

    wlanACLDeniedAge OBJECT-TYPE
	SYNTAX  INTEGER
	MAX-ACCESS  read-only
	STATUS  current
	DESCRIPTION
	    "The Age of the last MAX-ACCESS"
	DEFVAL { 0 }
    ::= { wlanACLDeniedEntry 4 }
-- **********************************************************************
-- *    End of wlanACLDeniedTable  TABLE
-- **********************************************************************

-- **********************************************************************
-- *    wlanACLTable  TABLE
-- **********************************************************************
wlanACLTable OBJECT-TYPE
	SYNTAX  SEQUENCE OF WlanACLEntry
	MAX-ACCESS  not-accessible
	STATUS  current
	DESCRIPTION
	""
    ::= { wlan 8 }

    wlanACLEntry OBJECT-TYPE
	SYNTAX   WlanACLEntry
	MAX-ACCESS   not-accessible
	STATUS  current
	DESCRIPTION
	"The WLAN Access List based on MAC Addresses"
	INDEX { wlanACLAddress, wlanACLIfIndex }
    ::= { wlanACLTable 1 }

    WlanACLEntry ::=
	SEQUENCE {
	    wlanACLAddress	    MacAddress,
	    wlanACLIfIndex	    INTEGER,
	    wlanACLStatus	    INTEGER
	}

    wlanACLAddress OBJECT-TYPE
	SYNTAX  MacAddress
	MAX-ACCESS  read-write
	STATUS  current
	DESCRIPTION
	    "The MAC Address for the accepted client"
    ::= { wlanACLEntry 1 }

    wlanACLIfIndex OBJECT-TYPE
	SYNTAX  INTEGER
	MAX-ACCESS	read-write
	STATUS  current
	DESCRIPTION
	    "The VSS Interface the MAC Address belongs"
	DEFVAL { 0 }
    ::= { wlanACLEntry 2 }


    wlanACLStatus OBJECT-TYPE
	SYNTAX  INTEGER { enable(1), disable(2), delete(3) }
	MAX-ACCESS  read-write
	STATUS  current
	DESCRIPTION
	    "The Status for the entry (delete)"
	DEFVAL { enable }
    ::= { wlanACLEntry 3 }

-- **********************************************************************
-- *    End of wlanACLTable  TABLE
-- **********************************************************************

-- **********************************************************************
-- *    wlanWDSAutoConfigTable  TABLE
-- **********************************************************************
wlanWDSAutoConfigTable OBJECT-TYPE
	SYNTAX SEQUENCE OF WlanWDSAutoConfigEntry
	MAX-ACCESS not-accessible
	STATUS current
	DESCRIPTION
	    "Attributes for artem bridge link auto-configuration."
    ::= { wlan 9 }

    wlanWDSAutoConfigEntry OBJECT-TYPE
	SYNTAX WlanWDSAutoConfigEntry
	MAX-ACCESS not-accessible
	STATUS current
	DESCRIPTION
	    "An entry in wlanWDSAutoConfigTable."
	INDEX { wlanWDSAutoConfigIfIndex }
	::= { wlanWDSAutoConfigTable 1 }

    WlanWDSAutoConfigEntry ::=
	SEQUENCE {
	    wlanWDSAutoConfigIfIndex	INTEGER,
	    wlanWDSLinkLockState	TruthValue,
	    wlanWDSLinkConfigScanState	INTEGER
	}

    wlanWDSAutoConfigIfIndex OBJECT-TYPE
	SYNTAX INTEGER
	MAX-ACCESS read-only
	STATUS current
	DESCRIPTION
	    "Auxiliary index in wlanWDSAutoConfigTable."
	::= { wlanWDSAutoConfigEntry 99 }

    wlanWDSLinkLockState OBJECT-TYPE
        SYNTAX TruthValue
        MAX-ACCESS read-write
        STATUS current
        DESCRIPTION
            "This attribute defines if the bridge is locked.
             Lock state is common for all bridge links
             using the same radio.
	     If the bridge is locked, it cannot be discovered
	     by auto-configuration scan, and remote changing of any
	     parameters is blocked."
        DEFVAL { false }
	::= { wlanWDSAutoConfigEntry 1 }

    wlanWDSLinkConfigScanState OBJECT-TYPE
	SYNTAX INTEGER { idle(1), scanning(2), busy(3) }
        MAX-ACCESS read-write
        STATUS current
        DESCRIPTION
            "This attribute defines the current auto-configuration
             state.
	     idle(1) - In this state, writing scanning(2) starts an
		    auto-configuration scan for bridge link peers.
		    State will stay at scanning(2) while the scan
		    is in progress. When the scan is finished, the
		    results are available in the artemBidgePeersTable.
	     scanning(2) - An auto-configuration scan for bridge
		    link peers is currently in progress. When scanning
		    has finished, the state will automatically
		    change back to idle(1).
	     busy(3) - An auto-configuration setup is currently in
		    progress on this radio module.
	     Writing this attribute in any state other than
	     idle(1) is silently ignored."
        DEFVAL { idle }
	::= { wlanWDSAutoConfigEntry 2 }

-- **********************************************************************
-- *    End of wlanWDSAutoConfigTable  TABLE
-- **********************************************************************

-- **********************************************************************
-- *    wlanWDSPeersTable  TABLE
-- **********************************************************************
    wlanWDSPeersTable OBJECT-TYPE
	SYNTAX SEQUENCE OF WlanWDSPeersEntry
	MAX-ACCESS not-accessible
	STATUS current
	DESCRIPTION
	    "This table contains the results of bridge link
	     auto-configuration scans. Each line represents
	     a possible link partner."
	::= { wlan 10 }

    wlanWDSPeersEntry OBJECT-TYPE
	SYNTAX WlanWDSPeersEntry
	MAX-ACCESS not-accessible
	STATUS current
	DESCRIPTION
	    "An entry in wlanWDSPeersTable."
	INDEX { wlanWDSPeerIfIndex, wlanWDSPeerIndex }
	::= { wlanWDSPeersTable 1 }

    WlanWDSPeersEntry ::=
	SEQUENCE {
	    wlanWDSPeerIfIndex		    INTEGER,
	    wlanWDSPeerIndex		    INTEGER,
	    wlanWDSPeerLinkAliasName	    OCTET STRING,
	    wlanWDSPeerCompointName	    OCTET STRING,
	    wlanWDSPeerRSSI		    WlanRSSI,
	    wlanWDSPeerRSSI1		    WlanRSSI,
	    wlanWDSPeerRSSI2		    WlanRSSI,
	    wlanWDSPeerRSSI3		    WlanRSSI,
	    wlanWDSPeerLinkAdminStatus	    TruthValue,
	    wlanWDSPeerLockState	    TruthValue,
	    wlanWDSPeerCompointMacAddress   MacAddress,
	    wlanWDSPeerRadioMacAddress	    MacAddress,
	    wlanWDSPeerConfigSetupState	    INTEGER,
	    wlanWDSPeerConfigSetupResult    INTEGER,
	    wlanWDSPeerRemoteIfIndex	    INTEGER
	}

    wlanWDSPeerIfIndex OBJECT-TYPE
	SYNTAX INTEGER
	MAX-ACCESS read-only
	STATUS current
	DESCRIPTION
	    "Auxiliary index in wlanWDSPeersTable."
	::= { wlanWDSPeersEntry 99 }

    wlanWDSPeerIndex OBJECT-TYPE
        SYNTAX INTEGER (1..2147483647)
        MAX-ACCESS read-only
        STATUS current
        DESCRIPTION
            "The auxiliary variable used to identify instances
             of the columnar objects in the wlanWDSPeersTable."
	::= { wlanWDSPeersEntry 1 }

    wlanWDSPeerLinkAliasName OBJECT-TYPE
        SYNTAX OCTET STRING (SIZE(0..13))
        MAX-ACCESS read-only
        STATUS current
        DESCRIPTION
            "This attribute shows the user-defined alias
             name for the peer's bridge link."
	::= { wlanWDSPeersEntry 2 }

    wlanWDSPeerCompointName OBJECT-TYPE
        SYNTAX OCTET STRING (SIZE(0..32))
        MAX-ACCESS read-only
        STATUS current
        DESCRIPTION
            "This attribute displays the given node name of the
             peer ComPoint."
	::= { wlanWDSPeersEntry 3 }

    wlanWDSPeerRSSI OBJECT-TYPE
        SYNTAX WlanRSSI
	UNITS "dBm"
        MAX-ACCESS read-only
        STATUS current
        DESCRIPTION
            "This attribute shows the receive signal
             strength for the signal received from the peer in dBm."
	::= { wlanWDSPeersEntry 4 }

    wlanWDSPeerLinkAdminStatus OBJECT-TYPE
        SYNTAX TruthValue
        MAX-ACCESS read-only
        STATUS current
        DESCRIPTION
            "This attribute shows is the peer's bridge
             link is currently enabled."
	::= { wlanWDSPeersEntry 5 }

    wlanWDSPeerLockState OBJECT-TYPE
        SYNTAX TruthValue
        MAX-ACCESS read-only
        STATUS current
        DESCRIPTION
            "This attribute defines if the peer's bridge is locked.
             Lock state is common for all bridge links
             using the same radio.
	     If the bridge is locked, it cannot be discovered
	     by auto-configuration scan, and changing of any
	     parameters is blocked."
	::= { wlanWDSPeersEntry 6 }

    wlanWDSPeerCompointMacAddress OBJECT-TYPE
        SYNTAX MacAddress
        MAX-ACCESS read-only
        STATUS current
        DESCRIPTION
            "This attribute displays the MAC address
             of the peer ComPoint.
	     This is not the WLAN radio's MAC address, but rather
	     the MAC address of the first ethernet port."
	::= { wlanWDSPeersEntry 7 }

    wlanWDSPeerRadioMacAddress OBJECT-TYPE
        SYNTAX MacAddress
        MAX-ACCESS read-only
        STATUS current
        DESCRIPTION
            "This attribute displays the peer's WLAN radio's MAC address."
	::= { wlanWDSPeersEntry 8 }

    wlanWDSPeerConfigSetupState OBJECT-TYPE
	SYNTAX INTEGER { idle(1), setup(2), busy(3) }
        MAX-ACCESS read-write
        STATUS current
        DESCRIPTION
            "This attribute defines the current auto-configuration
             setup state of the bridge link.
	     idle(1) - No auto-configuration is currently in progress.
		    In this state, writing any value other than idle(1)
		    to this attribute starts auto-configuration of a
		    bridge link to the partner defined by the table row.
		    The state then automatically changes to setup(1) for
		    this peer, and to busy(3) for all other peers.
	     setup(2) - Auto-configuration of this bridge link to
		    connect to this peer is currently in progress.
		    As soon as auto-config setup is finished, the
		    state changes back to idle(0). You can check
		    whether auto-config setup succeeded by reading
		    wlanWDSPeerConfigSetupResult.
	     busy(3) - Either the bridge link is currently scanning
		    for peers, or auto-configuration setup with another
		    peer is currently in progress for this bridge link.
	     Writing this attribute in any state other than idle(0)
	     returns an error."
        DEFVAL { idle }
	::= { wlanWDSPeersEntry 9 }

    wlanWDSPeerConfigSetupResult OBJECT-TYPE
        SYNTAX INTEGER
	    {
	    noError(1),
	    unknownCommand(2),
	    locked(3),
	    invalidPortID(4),
	    deviceError(5),
	    invalidTag(6),
	    timeout(7),
	    outOfBuffers(8),
	    notFound(9),
	    internalError(10),
	    receivedNAK(11)
	    }
        MAX-ACCESS read-only
        STATUS current
        DESCRIPTION
            "This attribute holds the result after a bridge link
             auto-config setup.
             It is reset whenever a new auto-config setup is triggered."
        DEFVAL { noError }
	::= { wlanWDSPeersEntry 10 }

    wlanWDSPeerRemoteIfIndex OBJECT-TYPE
	SYNTAX INTEGER
        MAX-ACCESS read-only
        STATUS current
        DESCRIPTION
	    "This is a unique identifier (port ID or ifIndex) for
	     the bridge link on the remote side."
	::= { wlanWDSPeersEntry 11 }

    wlanWDSPeerRSSI1 OBJECT-TYPE
        SYNTAX WlanRSSI
	UNITS "dBm"
        MAX-ACCESS read-only
        STATUS current
        DESCRIPTION
            "This attribute shows the receive signal
             strength on the first receiver for the signal received
             from the peer in dBm. A value of 0 indicates no
             connection"
	::= { wlanWDSPeersEntry 12 }

    wlanWDSPeerRSSI2 OBJECT-TYPE
        SYNTAX WlanRSSI
	UNITS "dBm"
        MAX-ACCESS read-only
        STATUS current
        DESCRIPTION
            "This attribute shows the receive signal
             strength on the second receiver for the signal received
             from the peer in dBm. A value of 0 indicates no
             connection or no second receiver present."
	::= { wlanWDSPeersEntry 13 }

    wlanWDSPeerRSSI3 OBJECT-TYPE
        SYNTAX WlanRSSI
	UNITS "dBm"
        MAX-ACCESS read-only
        STATUS current
        DESCRIPTION
            "This attribute shows the receive signal
             strength on the third receiver for the signal received
             from the peer in dBm. A value of 0 indicates no
             connection or no third receiver present."
	::= { wlanWDSPeersEntry 14 }

-- **********************************************************************
-- *    End of wlanWDSPeersTable  TABLE
-- **********************************************************************

-- **********************************************************************
-- *    wlanLinkTestTable  TABLE
-- **********************************************************************
wlanLinkTestTable OBJECT-TYPE
	SYNTAX SEQUENCE OF WlanLinkTestEntry
	MAX-ACCESS not-accessible
	STATUS  current
	DESCRIPTION
	    "This table contains the link test results for every
	     bridge link. Writing any value to the wlanLinkTestUpdate
	     attribute triggers transmission of a new link request frame."
	::= { wlan 11 }

    wlanLinkTestEntry OBJECT-TYPE
	SYNTAX WlanLinkTestEntry
	MAX-ACCESS not-accessible
	STATUS current
	DESCRIPTION
	    "An entry in WlanLinkTestEntry."
	INDEX { wlanLinkTestIfIndex }
	::= { wlanLinkTestTable 1 }

    WlanLinkTestEntry ::=
	SEQUENCE {
	    wlanLinkTestIfIndex		    INTEGER,
	    wlanLinkTestSignalLocal	    WlanRSSI,
	    wlanLinkTestSignalRemote	    WlanRSSI,
	    wlanLinkTestNoiseLocal	    WlanRSSI,
	    wlanLinkTestNoiseRemote	    WlanRSSI,
	    wlanLinkTestSNRLocal	    INTEGER,
	    wlanLinkTestSNRRemote	    INTEGER,
	    wlanLinkTestFramesTransmitted   Counter32,
	    wlanLinkTestFramesReceived	    Counter32,
	    wlanLinkTestFramesLost	    Counter32,
	    wlanLinkTestRateLocal	    WlanRate,
	    wlanLinkTestRateRemote	    WlanRate,
	    wlanLinkTestRxFrames54	    Counter32,
	    wlanLinkTestRxFrames48	    Counter32,
	    wlanLinkTestRxFrames36	    Counter32,
	    wlanLinkTestRxFrames24	    Counter32,
	    wlanLinkTestRxFrames18	    Counter32,
	    wlanLinkTestRxFrames12	    Counter32,
	    wlanLinkTestRxFrames11	    Counter32,
	    wlanLinkTestRxFrames9	    Counter32,
	    wlanLinkTestRxFrames6	    Counter32,
	    wlanLinkTestRxFrames5	    Counter32,
	    wlanLinkTestRxFrames2	    Counter32,
	    wlanLinkTestRxFrames1	    Counter32,
	    wlanLinkTestRxFramesRemote54    Counter32,
	    wlanLinkTestRxFramesRemote48    Counter32,
	    wlanLinkTestRxFramesRemote36    Counter32,
	    wlanLinkTestRxFramesRemote24    Counter32,
	    wlanLinkTestRxFramesRemote18    Counter32,
	    wlanLinkTestRxFramesRemote12    Counter32,
	    wlanLinkTestRxFramesRemote11    Counter32,
	    wlanLinkTestRxFramesRemote9	    Counter32,
	    wlanLinkTestRxFramesRemote6	    Counter32,
	    wlanLinkTestRxFramesRemote5	    Counter32,
	    wlanLinkTestRxFramesRemote2	    Counter32,
	    wlanLinkTestRxFramesRemote1	    Counter32,
	    wlanLinkTestUpdate		    INTEGER
	}

    wlanLinkTestIfIndex OBJECT-TYPE
	SYNTAX INTEGER
	MAX-ACCESS read-only
	STATUS current
	DESCRIPTION
	    "Auxiliary index in wlanLinkTestTable."
	::= { wlanLinkTestEntry 99 }

    wlanLinkTestSignalLocal OBJECT-TYPE
        SYNTAX WlanRSSI
	UNITS "dBm"
        MAX-ACCESS read-only
        STATUS current
        DESCRIPTION
            "This attribute shows the received signal strength in dBm."
	::= { wlanLinkTestEntry 1 }

    wlanLinkTestSignalRemote OBJECT-TYPE
        SYNTAX WlanRSSI
	UNITS "dBm"
        MAX-ACCESS read-only
        STATUS current
        DESCRIPTION
            "This attribute shows the received signal in dBm, as
             measured by remote bridge link partner. Reading
             this attribute triggers transmission of a
             new link request frame."
	::= { wlanLinkTestEntry 2 }

    wlanLinkTestNoiseLocal OBJECT-TYPE
        SYNTAX WlanRSSI
	UNITS "dBm"
        MAX-ACCESS read-only
        STATUS current
        DESCRIPTION
            "This attribute shows the measured noise level in dBm."
	::= { wlanLinkTestEntry 3 }

    wlanLinkTestNoiseRemote OBJECT-TYPE
        SYNTAX WlanRSSI
	UNITS "dBm"
        MAX-ACCESS read-only
        STATUS current
        DESCRIPTION
            "This attribute shows the noise level in dBm, as
             measured by remote bridge link partner."
	::= { wlanLinkTestEntry 4 }

    wlanLinkTestSNRLocal OBJECT-TYPE
        SYNTAX INTEGER (0..90)
	    UNITS "dB"
        MAX-ACCESS read-only
        STATUS current
        DESCRIPTION
            "This attribute shows the calculated Signal
             to Noise ratio in dB."
	::= { wlanLinkTestEntry 5 }

    wlanLinkTestSNRRemote OBJECT-TYPE
        SYNTAX INTEGER (0..90)
	    UNITS "dB"
        MAX-ACCESS read-only
        STATUS current
        DESCRIPTION
            "This attribute shows the calculated Signal to Noise
             ratio in dB, as measured by remote bridge link partner."
	::= { wlanLinkTestEntry 6 }

    wlanLinkTestFramesTransmitted OBJECT-TYPE
        SYNTAX Counter32
        MAX-ACCESS read-only
        STATUS current
        DESCRIPTION
            "This attribute shows the number of link test
             frames transmitted."
	::= { wlanLinkTestEntry 7 }

    wlanLinkTestFramesReceived OBJECT-TYPE
        SYNTAX Counter32
        MAX-ACCESS read-only
        STATUS current
        DESCRIPTION
            "This attribute shows the number of link test
             frames successfully received."
	::= { wlanLinkTestEntry 8 }

    wlanLinkTestFramesLost OBJECT-TYPE
        SYNTAX Counter32
        MAX-ACCESS read-only
        STATUS current
        DESCRIPTION
            "This attribute shows the number of link test frames
             for which no reply has been received and
             therefore are considered lost."
	::= { wlanLinkTestEntry 9 }

    wlanLinkTestRateLocal OBJECT-TYPE
        SYNTAX WlanRate
        MAX-ACCESS read-only
        STATUS current
        DESCRIPTION
            "This attribute shows the data rate of the most
             recent received link test frame, in 500 Kbps units."
	::= { wlanLinkTestEntry 10 }

    wlanLinkTestRateRemote OBJECT-TYPE
        SYNTAX WlanRate
        MAX-ACCESS read-only
        STATUS current
        DESCRIPTION
            "This attribute shows the data rate of the most
             recent link test frame received by the link
             partner, in 500 Kbps units."
	::= { wlanLinkTestEntry 11 }

    wlanLinkTestRxFrames54 OBJECT-TYPE
        SYNTAX Counter32
        MAX-ACCESS read-only
        STATUS current
        DESCRIPTION
            "This attribute shows the number of link
             test frames that were received at 54 Mbps."
	::= { wlanLinkTestEntry 32 }

    wlanLinkTestRxFrames48 OBJECT-TYPE
        SYNTAX Counter32
        MAX-ACCESS read-only
        STATUS current
        DESCRIPTION
            "This attribute shows the number of link
             test frames that were received at 48 Mbps."
	::= { wlanLinkTestEntry 33 }

    wlanLinkTestRxFrames36 OBJECT-TYPE
        SYNTAX Counter32
        MAX-ACCESS read-only
        STATUS current
        DESCRIPTION
            "This attribute shows the number of link
             test frames that were received at 36 Mbps."
	::= { wlanLinkTestEntry 34 }

    wlanLinkTestRxFrames24 OBJECT-TYPE
        SYNTAX Counter32
        MAX-ACCESS read-only
        STATUS current
        DESCRIPTION
            "This attribute shows the number of link
             test frames that were received at 24 Mbps."
	::= { wlanLinkTestEntry 35 }

    wlanLinkTestRxFrames18 OBJECT-TYPE
        SYNTAX Counter32
        MAX-ACCESS read-only
        STATUS current
        DESCRIPTION
            "This attribute shows the number of link
             test frames that were received at 18 Mbps."
	::= { wlanLinkTestEntry 36 }

    wlanLinkTestRxFrames12 OBJECT-TYPE
        SYNTAX Counter32
        MAX-ACCESS read-only
        STATUS current
        DESCRIPTION
            "This attribute shows the number of link
             test frames that were received at 12 Mbps."
	::= { wlanLinkTestEntry 37 }

    wlanLinkTestRxFrames11 OBJECT-TYPE
        SYNTAX Counter32
        MAX-ACCESS read-only
        STATUS current
        DESCRIPTION
            "This attribute shows the number of link
             test frames that were received at 11 Mbps."
	::= { wlanLinkTestEntry 38 }

    wlanLinkTestRxFrames9 OBJECT-TYPE
        SYNTAX Counter32
        MAX-ACCESS read-only
        STATUS current
        DESCRIPTION
            "This attribute shows the number of link
             test frames that were received at 9 Mbps."
	::= { wlanLinkTestEntry 39 }

    wlanLinkTestRxFrames6 OBJECT-TYPE
        SYNTAX Counter32
        MAX-ACCESS read-only
        STATUS current
        DESCRIPTION
            "This attribute shows the number of link
             test frames that were received at 6 Mbps."
	::= { wlanLinkTestEntry 40 }

    wlanLinkTestRxFrames5 OBJECT-TYPE
        SYNTAX Counter32
        MAX-ACCESS read-only
        STATUS current
        DESCRIPTION
            "This attribute shows the number of link
             test frames that were received at 5.5 Mbps."
	::= { wlanLinkTestEntry 41 }

    wlanLinkTestRxFrames2 OBJECT-TYPE
        SYNTAX Counter32
        MAX-ACCESS read-only
        STATUS current
        DESCRIPTION
            "This attribute shows the number of link
             test frames that were received at 2 Mbps."
	::= { wlanLinkTestEntry 42 }

    wlanLinkTestRxFrames1 OBJECT-TYPE
        SYNTAX Counter32
        MAX-ACCESS read-only
        STATUS current
        DESCRIPTION
            "This attribute shows the number of link
             test frames that were received at 1 Mbps."
	::= { wlanLinkTestEntry 43 }

    wlanLinkTestUpdate OBJECT-TYPE
        SYNTAX INTEGER
        MAX-ACCESS read-write
        STATUS current
        DESCRIPTION
            "Writing any non-zero value to this attribute
             triggers transmission of a new link request frame.
             Reading this attribute always returns 0."
	::= { wlanLinkTestEntry 50 }

    wlanLinkTestRxFramesRemote54 OBJECT-TYPE
        SYNTAX Counter32
        MAX-ACCESS read-only
        STATUS current
        DESCRIPTION
            "This attribute shows the number of link
             test frames that were received by the remote
             partner at 54 Mbps."
	::= { wlanLinkTestEntry 60 }

    wlanLinkTestRxFramesRemote48 OBJECT-TYPE
        SYNTAX Counter32
        MAX-ACCESS read-only
        STATUS current
        DESCRIPTION
            "This attribute shows the number of link
             test frames that were received by the remote
             partner at 48 Mbps."
	::= { wlanLinkTestEntry 61 }

    wlanLinkTestRxFramesRemote36 OBJECT-TYPE
        SYNTAX Counter32
        MAX-ACCESS read-only
        STATUS current
        DESCRIPTION
            "This attribute shows the number of link
             test frames that were received by the remote
             partner at 36 Mbps."
	::= { wlanLinkTestEntry 62 }

    wlanLinkTestRxFramesRemote24 OBJECT-TYPE
        SYNTAX Counter32
        MAX-ACCESS read-only
        STATUS current
        DESCRIPTION
            "This attribute shows the number of link
             test frames that were received by the remote
             partner at 24 Mbps."
	::= { wlanLinkTestEntry 63 }

    wlanLinkTestRxFramesRemote18 OBJECT-TYPE
        SYNTAX Counter32
        MAX-ACCESS read-only
        STATUS current
        DESCRIPTION
            "This attribute shows the number of link
             test frames that were received by the remote
             partner at 18 Mbps."
	::= { wlanLinkTestEntry 64 }

    wlanLinkTestRxFramesRemote12 OBJECT-TYPE
        SYNTAX Counter32
        MAX-ACCESS read-only
        STATUS current
        DESCRIPTION
            "This attribute shows the number of link
             test frames that were received by the remote
             partner at 12 Mbps."
	::= { wlanLinkTestEntry 65 }

    wlanLinkTestRxFramesRemote11 OBJECT-TYPE
        SYNTAX Counter32
        MAX-ACCESS read-only
        STATUS current
        DESCRIPTION
            "This attribute shows the number of link
             test frames that were received by the remote
             partner at 11 Mbps."
	::= { wlanLinkTestEntry 66 }

    wlanLinkTestRxFramesRemote9 OBJECT-TYPE
        SYNTAX Counter32
        MAX-ACCESS read-only
        STATUS current
        DESCRIPTION
            "This attribute shows the number of link
             test frames that were received by the remote
             partner at 9 Mbps."
	::= { wlanLinkTestEntry 67 }

    wlanLinkTestRxFramesRemote6 OBJECT-TYPE
        SYNTAX Counter32
        MAX-ACCESS read-only
        STATUS current
        DESCRIPTION
            "This attribute shows the number of link
             test frames that were received by the remote
             partner at 6 Mbps."
	::= { wlanLinkTestEntry 68 }

    wlanLinkTestRxFramesRemote5 OBJECT-TYPE
        SYNTAX Counter32
        MAX-ACCESS read-only
        STATUS current
        DESCRIPTION
            "This attribute shows the number of link
             test frames that were received by the remote
             partner at 5.5 Mbps."
	::= { wlanLinkTestEntry 69 }

    wlanLinkTestRxFramesRemote2 OBJECT-TYPE
        SYNTAX Counter32
        MAX-ACCESS read-only
        STATUS current
        DESCRIPTION
            "This attribute shows the number of link
             test frames that were received by the remote
             partner at 2 Mbps."
	::= { wlanLinkTestEntry 70 }

    wlanLinkTestRxFramesRemote1 OBJECT-TYPE
        SYNTAX Counter32
        MAX-ACCESS read-only
        STATUS current
        DESCRIPTION
            "This attribute shows the number of link
             test frames that were received by the remote
             partner at 1 Mbps."
	::= { wlanLinkTestEntry 71 }

-- **********************************************************************
-- *    End of wlanLinkTestTable  TABLE
-- **********************************************************************

-- **********************************************************************
-- *    WLAN WDS common Bridge configuration Objects
-- **********************************************************************
wlanBridge OBJECT IDENTIFIER
--	    wlanBridgeConfigScanTimeout		1
--	    wlanBridgeConfigSetupTimeout	2
::= { wlan 12 }

    wlanBridgeConfigScanTimeout OBJECT-TYPE
        SYNTAX INTEGER (10..600)
	UNITS "seconds"
        MAX-ACCESS read-write
        STATUS current
        DESCRIPTION
            "This attribute defines the maximum time a bridge
             auto-configuration scan may take. After this timeout has
             expired, any auto-configuration scan will be aborted,
             regardless of current state."
        DEFVAL { 120 }
	::= { wlanBridge 1 }

    wlanBridgeConfigSetupTimeout OBJECT-TYPE
        SYNTAX INTEGER (10..600)
	UNITS "seconds"
        MAX-ACCESS read-write
        STATUS current
        DESCRIPTION
            "This attribute defines the maximum time a bridge
             auto-configuration setup may take. After this timeout
             has expired, any auto-configuration setup will be aborted,
             regardless of current state.
             In this case, artemBridgePeerConfigSetupResult
             will be set to 'timeout'."
        DEFVAL { 300 }
	::= { wlanBridge 2 }

-- **********************************************************************
-- *    wlanClientTable  TABLE
-- **********************************************************************
wlanClientTable OBJECT-TYPE
    SYNTAX  SEQUENCE OF WlanClientEntry
    MAX-ACCESS  not-accessible
    STATUS  current
    DESCRIPTION
	" Describe a WLAN Client and the correspondending
	settings"
    ::= { wlan 13 }

    wlanClientEntry OBJECT-TYPE
       SYNTAX  WlanClientEntry
       MAX-ACCESS  not-accessible
       STATUS  current
       DESCRIPTION
	""
       INDEX   { wlanClientwlanIf }
       ::= { wlanClientTable 1 }

        WlanClientEntry ::=
	 SEQUENCE {
	wlanClientIndex			INTEGER,
	wlanClientIfIndex		INTEGER,
	wlanClientwlanIf		INTEGER,
	wlanClientMode			INTEGER,
	wlanClientSSID			DisplayString,
	wlanClient11dConformance	INTEGER,
	wlanClientSecurity		INTEGER,
	wlanClientDefaultKey		INTEGER,
	wlanClientKey1			OCTET STRING,
	wlanClientKey2			OCTET STRING,
	wlanClientKey3			OCTET STRING,
	wlanClientKey4			OCTET STRING,
	wlanClientPassPhrase		OCTET STRING,
	wlanClientRsnPreauthentication	INTEGER,
	wlanClientBand			INTEGER,
	wlanClientRoamingPreference	INTEGER,
	wlanClientScanThreshold		INTEGER,
	wlanClientScanInterval		INTEGER,
	wlanClientChannelSweep		INTEGER,
	wlanClientScanPeriodAMin	INTEGER,
	wlanClientScanPeriodAMax	INTEGER,
	wlanClientScanPeriodMin		INTEGER,
	wlanClientScanPeriodMax		INTEGER,
	wlanClientWeightOfAssocAdv	INTEGER,
	wlanClientWeightOfRSSIAdv	INTEGER,
	wlanClientWeightOfAge		INTEGER,
	wlanClientWeightOfPenalty	INTEGER,
	wlanClientJoinFailedPenalty	INTEGER,
	wlanClientSkipChannels		BITS,
	wlanClientRoamingProfile	INTEGER,
	-- no saves
	wlanClientWPAMulticastCipher	BitValue,
	wlanClientRSNMulticastCipher	BitValue,
	wlanClientWPAUnicastCipher	BitValue,
	wlanClientRSNUnicastCipher	BitValue,
	wlanClientScanState		INTEGER
	,
	wlanClientRSNCapabilities	INTEGER,
	-- statistics
	wlanClientBss			MacAddress,
	wlanClientCurrSSID		DisplayString,
	wlanClientMSDUTx		Counter32,
	wlanClientMSDURx		Counter32,
	wlanClientBytesTx		Counter32,
	wlanClientBytesRx		Counter32,
	wlanClientRate                  WlanRate,
	wlanClientRSSI			WlanRSSI,
	wlanClientRSSI1			WlanRSSI,
	wlanClientRSSI2			WlanRSSI,
	wlanClientRSSI3			WlanRSSI,
	wlanClientNoise			WlanRSSI,
	wlanClientRxFrames54		Counter32,
	wlanClientRxFrames48		Counter32,
	wlanClientRxFrames36		Counter32,
	wlanClientRxFrames24		Counter32,
	wlanClientRxFrames18		Counter32,
	wlanClientRxFrames12		Counter32,
	wlanClientRxFrames11		Counter32,
	wlanClientRxFrames9		Counter32,
	wlanClientRxFrames6		Counter32,
	wlanClientRxFrames5		Counter32,
	wlanClientRxFrames2		Counter32,
	wlanClientRxFrames1		Counter32,
	wlanClientTxFrames54		Counter32,
	wlanClientTxFrames48		Counter32,
	wlanClientTxFrames36		Counter32,
	wlanClientTxFrames24		Counter32,
	wlanClientTxFrames18		Counter32,
	wlanClientTxFrames12		Counter32,
	wlanClientTxFrames11		Counter32,
	wlanClientTxFrames9		Counter32,
	wlanClientTxFrames6		Counter32,
	wlanClientTxFrames5		Counter32,
	wlanClientTxFrames2		Counter32,
	wlanClientTxFrames1		Counter32
	 }

    wlanClientIndex OBJECT-TYPE
	SYNTAX  INTEGER (0..255)
	MAX-ACCESS  read-only
	STATUS  current
	DESCRIPTION
	    "Unique Client index."
	DEFVAL { 0 }
    ::= { wlanClientEntry 1 }

    wlanClientIfIndex OBJECT-TYPE
	SYNTAX  INTEGER
	MAX-ACCESS  read-only
	STATUS  current
	DESCRIPTION
	    "IfIndex of the client interface."
	DEFVAL { 0 }
    ::= { wlanClientEntry 2 }

    wlanClientwlanIf OBJECT-TYPE
	SYNTAX  INTEGER
	MAX-ACCESS  read-write
	STATUS  current
	DESCRIPTION
	    "IfIndex of the wlan Interface the client belongs to."
    ::= { wlanClientEntry 3 }


    wlanClientMode OBJECT-TYPE
	SYNTAX  INTEGER { infra(1), ad-hoc(2), delete(3) }
	MAX-ACCESS  read-write
	STATUS  current
	DESCRIPTION
                "Switch between infrastructure and ad-hoc mode."
	DEFVAL { infra }
    ::= { wlanClientEntry 4 }


    wlanClientSSID OBJECT-TYPE
	SYNTAX  DisplayString
	MAX-ACCESS  read-write
	STATUS  current
	DESCRIPTION
	    "The Service Set Name"
    ::= { wlanClientEntry 5 }

    wlanClient11dConformance OBJECT-TYPE
	SYNTAX  INTEGER { none(1), flexible(2), strict(3) }
	MAX-ACCESS  read-write
	STATUS  current
	DESCRIPTION
	"none     - use own country info
	 flexible - try to get country info from an AP else use own country info
	 strict   - try to get country info from an AP else do nothing"
	DEFVAL { strict }
    ::= { wlanClientEntry 6 }

    wlanClientSecurity OBJECT-TYPE
	SYNTAX  INTEGER {
	    none(1),
	    wep40(2),
	    wep104(3),
	    wpa-psk(4),
	    wpa2-psk(5),
	    wpa(6),
	    wpa2(7),
	    wpa-none(8)
	}
	MAX-ACCESS  read-write
	STATUS  current
	DESCRIPTION
	"The Security Option which will be used. WPA-NONE is a special
	 mode only for Ad-hoc mode. There is no key management that means
	 the key is static (calculated from SSID and passphrase)."
	DEFVAL { none }
    ::= { wlanClientEntry 7 }

    wlanClientDefaultKey OBJECT-TYPE
	SYNTAX  INTEGER { key1(1), key2(2), key3(3), key4(4) }
	MAX-ACCESS  read-write
	STATUS  current
	DESCRIPTION
	    " "
	DEFVAL { key1 }
    ::= { wlanClientEntry 8 }

    wlanClientKey1 OBJECT-TYPE
	SYNTAX  OCTET STRING  (SIZE(0..33))
	MAX-ACCESS  read-write
	STATUS  current
	DESCRIPTION
	    "Key string for WEP key nr. 1."
	DEFVAL { "" }
    ::= { wlanClientEntry 9 }

    wlanClientKey2 OBJECT-TYPE
	SYNTAX  OCTET STRING  (SIZE(0..33))
	MAX-ACCESS  read-write
	STATUS  current
	DESCRIPTION
	    "Key string for WEP key nr. 2."
	DEFVAL { "" }
    ::= { wlanClientEntry 10 }

    wlanClientKey3 OBJECT-TYPE
	SYNTAX  OCTET STRING  (SIZE(0..33))
	MAX-ACCESS  read-write
	STATUS  current
	DESCRIPTION
	    "Key string for WEP key nr. 3."
	DEFVAL { "" }
    ::= { wlanClientEntry 11 }

    wlanClientKey4 OBJECT-TYPE
	SYNTAX  OCTET STRING  (SIZE(0..33))
	MAX-ACCESS  read-write
	STATUS  current
	DESCRIPTION
	    "Key string for WEP key nr. 4."
	DEFVAL { "" }
    ::= { wlanClientEntry 12 }

    wlanClientPassPhrase OBJECT-TYPE
	SYNTAX  OCTET STRING  (SIZE(0..64))
	MAX-ACCESS  read-write
	STATUS  current
	DESCRIPTION
	    "Passphrase string for WPA-PSK and WPA2-PSK."
	DEFVAL { "" }
    ::= { wlanClientEntry 13 }

    wlanClientRsnPreauthentication OBJECT-TYPE
	SYNTAX  INTEGER { enable(1), disable(2) }
	MAX-ACCESS  read-write
	STATUS  current
	DESCRIPTION
	    "When this object is set to TRUE, this shall indicate that RSNA
	    preauthentication is enabled on this entity.
	    This object requires that dot11RSNAEnabled also be set to TRUE."
	DEFVAL { enable }
    ::= { wlanClientEntry 14 }

    wlanClientBand OBJECT-TYPE
	SYNTAX INTEGER { b24-GHz(1), b5-GHz(2), b24-5-GHz(3) }
	MAX-ACCESS  read-write
	STATUS  obsolete
	DESCRIPTION
	    " Frequency band  "
    ::= { wlanClientEntry 15 }

    wlanClientRoamingPreference OBJECT-TYPE
	SYNTAX INTEGER { none(1), b24-GHz(2), b5-GHz(3) }
	MAX-ACCESS  read-write
	STATUS  current
	DESCRIPTION
	    "	Which band is prefered for
		association.
		none   : no preference (default)
		b24-GHz: prefer APs on 2,4 GHz
		b5-GHz : prefer APs on 5 GHz"
	DEFVAL { none }
    ::= { wlanClientEntry 16 }

    wlanClientScanThreshold OBJECT-TYPE
	SYNTAX INTEGER (-90..-10)
	UNITS "dBm"
	MAX-ACCESS  read-write
	STATUS  current
	DESCRIPTION
	    " Threshold in dBm above which the background scan is active.
	      Default is -70dBm."
	DEFVAL { -70 }
    ::= { wlanClientEntry 17 }

    wlanClientScanInterval OBJECT-TYPE
	SYNTAX INTEGER (200..50000)
	MAX-ACCESS  read-write
	STATUS  current
	DESCRIPTION
	    " Scan interval, in ms, between successive sweeps.
	      Default is 5000ms."
	DEFVAL { 5000 }
    ::= { wlanClientEntry 18 }

    wlanClientChannelSweep OBJECT-TYPE
	SYNTAX INTEGER
	MAX-ACCESS  read-write
	STATUS  current
	DESCRIPTION
	    "	Number of frequencies to scan for each background scan.
		Sweep = 0 disables background scanning.
		Sweep = -1 causes the sweep to cover all frequencies available.
		Default is a sweep of 2 channels."
	DEFVAL { 2 }
    ::= { wlanClientEntry 19 }

    wlanClientScanPeriodAMin OBJECT-TYPE
	SYNTAX INTEGER
	MAX-ACCESS  read-write
	STATUS  current
	DESCRIPTION
	    "	Minimum time in ms to spend on a frequency when active
		scanning.
		Default is 10ms."
	DEFVAL { 10 }
    ::= { wlanClientEntry 20 }

    wlanClientScanPeriodAMax OBJECT-TYPE
	SYNTAX INTEGER
	MAX-ACCESS  read-write
	STATUS  current
	DESCRIPTION
	    "	Maximum time in ms to spend on a frequency when active
		scanning.
		Default is 40ms."
	DEFVAL { 40 }
    ::= { wlanClientEntry 21 }

    wlanClientScanPeriodMin OBJECT-TYPE
	SYNTAX INTEGER
	MAX-ACCESS  read-write
	STATUS  current
	DESCRIPTION
	    "	Minimum time in ms to spend on a frequency when passive
		scanning.
		Default is 20ms."
	DEFVAL { 20 }
    ::= { wlanClientEntry 22 }

    wlanClientScanPeriodMax OBJECT-TYPE
	SYNTAX INTEGER
	MAX-ACCESS  read-write
	STATUS  current
	DESCRIPTION
	    "	Maximum time in ms to spend on a frequency when passive
		scanning.
		Default is 120ms."
	DEFVAL { 120 }
    ::= { wlanClientEntry 23 }

    wlanClientWeightOfAssocAdv OBJECT-TYPE
	SYNTAX INTEGER
	MAX-ACCESS  read-write
	STATUS  current
	DESCRIPTION
	    " Advantage of the BSS currently associated with.
	      Default is a weight of 10."
	DEFVAL { 10 }
    ::= { wlanClientEntry 24 }

    wlanClientWeightOfRSSIAdv OBJECT-TYPE
	SYNTAX INTEGER
	MAX-ACCESS  read-write
	STATUS  current
	DESCRIPTION
	    " Weight of the BSS's received signal strength indicator (RSSI).
	      Default is a weight of 10."
	DEFVAL { 10 }
    ::= { wlanClientEntry 25 }

    wlanClientWeightOfAge OBJECT-TYPE
	SYNTAX INTEGER
	MAX-ACCESS  read-write
	STATUS  current
	DESCRIPTION
	    " Weight of the BSS's age.
	      Default is a weight of 5"
	DEFVAL { 5 }
    ::= { wlanClientEntry 26 }

    wlanClientWeightOfPenalty OBJECT-TYPE
	SYNTAX INTEGER
	MAX-ACCESS  read-write
	STATUS  current
	DESCRIPTION
	    " Weight of the BSS's penalty.
	      Default is a weigth of 10."
	DEFVAL { 10 }
    ::= { wlanClientEntry 27 }

    wlanClientJoinFailedPenalty OBJECT-TYPE
	SYNTAX INTEGER
	MAX-ACCESS  read-write
	STATUS  current
	DESCRIPTION
	    " Penalty when joining an AP failed.
	      Default is a penalty value of 50."
	DEFVAL { 50 }
    ::= { wlanClientEntry 28 }

    wlanClientRoamingProfile OBJECT-TYPE
	SYNTAX INTEGER { fast(1), normal(2), slow(3), no(4), custom(5) }
	MAX-ACCESS  read-write
	STATUS  current
	DESCRIPTION
	    " All roaming parameters are summarized to profiles for
	      the most used roaming behaviors.
	      fast  : client roams if signal is not strong enough for higher data rates
	      normal: default roaming parameters
	      slow  : client roams if signal is weak
	      no    : client roams only when it is disassociated
	      custom: user can change roaming parameter "
	DEFVAL { normal }
    ::= { wlanClientEntry 29 }

    wlanClientSkipChannels OBJECT-TYPE
	SYNTAX BITS {
			channel-1(0),
			channel-2(1),
			channel-3(2),
			channel-4(3),
			channel-5(4),
			channel-6(5),
			channel-7(6),
			channel-8(7),
			channel-9(8),
			channel-10(9),
			channel-11(10),
			channel-12(11),
			channel-13(12),
			channel-14(13)
		    }
	MAX-ACCESS  read-write
	STATUS  obsolete
	DESCRIPTION
	    " If a bit is set the accordingly channel will be skipped from
	      the channel scan list (channel 1-14 for 2.4 GHz).
	      Default is scan all channels.  "
	DEFVAL { { } }
    ::= { wlanClientEntry 30 }

    wlanClientWPAMulticastCipher OBJECT-TYPE
	SYNTAX  BitValue
	MAX-ACCESS  read-only
	STATUS  current
	DESCRIPTION
	    "The multicast ciphers used for WPA.
	     For WPA and RSN, only one of the following values is allowed:
	    WPA_CIPHERSUITE_NONE(0)
	    WPA_CIPHERSUITE_WEP_40(1)
	    WPA_CIPHERSUITE_WEP_104(2)
	    WPA_CIPHERSUITE_TKIP(4)
	    WPA_CIPHERSUITE_AES_CCMP(8)
	    WPA_CIPHERSUITE_AES_WRAP(16)
	    Only one of the WPA_ and RSN_ bits may be set."
	DEFVAL { 4 }
    ::= { wlanClientEntry 33 }

    wlanClientRSNMulticastCipher OBJECT-TYPE
	SYNTAX  BitValue
	MAX-ACCESS  read-only
	STATUS  current
	DESCRIPTION
	    "The multicast ciphers used for RSN.
	     For WPA and RSN, only one of the following values is allowed:
	    WPA_CIPHERSUITE_NONE(0)
	    WPA_CIPHERSUITE_WEP_40(1)
	    WPA_CIPHERSUITE_WEP_104(2)
	    WPA_CIPHERSUITE_TKIP(4)
	    WPA_CIPHERSUITE_AES_CCMP(8)
	    WPA_CIPHERSUITE_AES_WRAP(16)
	    Only one of the WPA_ and RSN_ bits may be set."
	DEFVAL { 4 }
    ::= { wlanClientEntry 34 }

    wlanClientWPAUnicastCipher OBJECT-TYPE
	SYNTAX  BitValue
	MAX-ACCESS  read-write
	STATUS  current
	DESCRIPTION
	    "The set of unicast ciphers used for WPA.
	     For WPA and RSN, set one or more of the following bit values:
	    WPA_CIPHERSUITE_NONE(0)
	    WPA_CIPHERSUITE_WEP_40(1)
	    WPA_CIPHERSUITE_WEP_104(2)
	    WPA_CIPHERSUITE_TKIP(4)
	    WPA_CIPHERSUITE_AES_CCMP(8)
	    WPA_CIPHERSUITE_AES_WRAP(16)
	    One or more bits may be set to indicate the available ciphers."
	DEFVAL { 8 }
     ::= { wlanClientEntry 35 }

    wlanClientRSNUnicastCipher OBJECT-TYPE
	SYNTAX  BitValue
	MAX-ACCESS  read-write
	STATUS  current
	DESCRIPTION
	    "The set of unicast ciphers used for RSN.
	     For WPA and RSN, set one or more of the following bit values:
	    WPA_CIPHERSUITE_NONE(0)
	    WPA_CIPHERSUITE_WEP_40(1)
	    WPA_CIPHERSUITE_WEP_104(2)
	    WPA_CIPHERSUITE_TKIP(4)
	    WPA_CIPHERSUITE_AES_CCMP(8)
	    WPA_CIPHERSUITE_AES_WRAP(16)
	    One or more bits may be set to indicate the available ciphers."
	DEFVAL { 16 }
     ::= { wlanClientEntry 36 }

    wlanClientRSNCapabilities OBJECT-TYPE
	SYNTAX  INTEGER (0..65535)
	MAX-ACCESS  read-only
	STATUS  current
	DESCRIPTION
	    "The RSN capabilities bytes, "
	DEFVAL { 0 }
    ::= { wlanClientEntry 37 }

    wlanClientScanState OBJECT-TYPE
	SYNTAX INTEGER { idle(1), scanning(2), update(3) }
	MAX-ACCESS  read-write
	STATUS  current
	DESCRIPTION
	    "This attribute holds the foreground scanning status.
	     Writing scanning(2) in idle state triggers a new
	     foreground scan cycle. All entries for this client
	     interface in the wlanScanResultsTable are removed.
	     When the WLAN client has finished scanning, the attribute
	     changes back to idle(1), and the wlanScanResultsTable is
	     updated automatically.
	     To update wlanScanResultsTable without triggering a new
	     foreground scan, you can write update(3) to this attribute.
	     This causes wlanScanResultsTable to be updated immedieately,
	     reflecting any changes detected by automatic backgound scanning.
	     After wlanScanResultsTable is updated, the value switches back
	     to state idle(1).
	     Any attempt to write different values, or to write values in a
	     state different from idle(1), is ignored."
	DEFVAL { idle }
    ::= { wlanClientEntry 38 }

    -- statistic counters

    wlanClientBss OBJECT-TYPE
	SYNTAX  MacAddress
	MAX-ACCESS  read-only
	STATUS  current
	DESCRIPTION
                "BSS Id the client is associated with. If client is not
                 associated, this attribute reads 00:00:00:00:00:00."
    ::= { wlanClientEntry 64 }

    wlanClientCurrSSID OBJECT-TYPE
	SYNTAX  DisplayString
	MAX-ACCESS  read-only
	STATUS  current
	DESCRIPTION
                "The Service Set Name the client really is associated with.
                 This usually equal to wlanClientSSID, except for empty
                 wlanClientSSID, which means any SSID."
    ::= { wlanClientEntry 65 }

    wlanClientMSDUTx OBJECT-TYPE
	SYNTAX  Counter32
	MAX-ACCESS  read-only
	STATUS  current
	DESCRIPTION
	"Count of transmitted MSDU"
    ::= { wlanClientEntry 66 }

    wlanClientMSDURx OBJECT-TYPE
	SYNTAX  Counter32
	MAX-ACCESS  read-only
	STATUS  current
	DESCRIPTION
	"Count of received MSDU"
    ::= { wlanClientEntry 67 }

    wlanClientBytesTx OBJECT-TYPE
	SYNTAX  Counter32
	MAX-ACCESS  read-only
	STATUS  current
	DESCRIPTION
	"total number of transmitted bytes"
    ::= { wlanClientEntry 68 }

    wlanClientBytesRx OBJECT-TYPE
	SYNTAX  Counter32
	MAX-ACCESS  read-only
	STATUS  current
	DESCRIPTION
	"total number of received bytes"
    ::= { wlanClientEntry 69 }

    wlanClientRate OBJECT-TYPE
	SYNTAX  WlanRate
	MAX-ACCESS  read-only
	STATUS  current
	DESCRIPTION
	    "Data rate of latest received data frame, in 500 kbps units.
	     If client is not associated, this attribute always reads 0."
	DEFVAL { 0 }
    ::= { wlanClientEntry 70 }

    wlanClientRSSI OBJECT-TYPE
	SYNTAX  WlanRSSI
	UNITS "dBm"
	MAX-ACCESS  read-only
	STATUS  current
	DESCRIPTION
	    "Receive signal strength of latest received data frame."
	DEFVAL { 0 }
    ::= { wlanClientEntry 71 }

    wlanClientNoise OBJECT-TYPE
	SYNTAX  WlanRSSI
	UNITS "dBm"
	MAX-ACCESS  read-only
	STATUS  current
	DESCRIPTION
	"This attribute shows the measured noise level in dBm, or
	 0 if no connection can be established."
	DEFVAL { 0 }
    ::= { wlanClientEntry 72 }

    wlanClientRxFrames54 OBJECT-TYPE
        SYNTAX Counter32
        MAX-ACCESS read-only
        STATUS current
        DESCRIPTION
            "This attribute shows the number of data
             frames that were received at 54 Mbps."
	::= { wlanClientEntry 73 }

    wlanClientRxFrames48 OBJECT-TYPE
        SYNTAX Counter32
        MAX-ACCESS read-only
        STATUS current
        DESCRIPTION
            "This attribute shows the number of data
             frames that were received at 48 Mbps."
	::= { wlanClientEntry 74 }

    wlanClientRxFrames36 OBJECT-TYPE
        SYNTAX Counter32
        MAX-ACCESS read-only
        STATUS current
        DESCRIPTION
            "This attribute shows the number of data
             frames that were received at 36 Mbps."
	::= { wlanClientEntry 75 }

    wlanClientRxFrames24 OBJECT-TYPE
        SYNTAX Counter32
        MAX-ACCESS read-only
        STATUS current
        DESCRIPTION
            "This attribute shows the number of data
             frames that were received at 24 Mbps."
	::= { wlanClientEntry 76 }

    wlanClientRxFrames18 OBJECT-TYPE
        SYNTAX Counter32
        MAX-ACCESS read-only
        STATUS current
        DESCRIPTION
            "This attribute shows the number of data
             frames that were received at 18 Mbps."
	::= { wlanClientEntry 77 }

    wlanClientRxFrames12 OBJECT-TYPE
        SYNTAX Counter32
        MAX-ACCESS read-only
        STATUS current
        DESCRIPTION
            "This attribute shows the number of data
             frames that were received at 12 Mbps."
	::= { wlanClientEntry 78 }

    wlanClientRxFrames11 OBJECT-TYPE
        SYNTAX Counter32
        MAX-ACCESS read-only
        STATUS current
        DESCRIPTION
            "This attribute shows the number of data
             frames that were received at 11 Mbps."
	::= { wlanClientEntry 79 }

    wlanClientRxFrames9 OBJECT-TYPE
        SYNTAX Counter32
        MAX-ACCESS read-only
        STATUS current
        DESCRIPTION
            "This attribute shows the number of data
             frames that were received at 9 Mbps."
	::= { wlanClientEntry 80 }

    wlanClientRxFrames6 OBJECT-TYPE
        SYNTAX Counter32
        MAX-ACCESS read-only
        STATUS current
        DESCRIPTION
            "This attribute shows the number of data
             frames that were received at 6 Mbps."
	::= { wlanClientEntry 81 }

    wlanClientRxFrames5 OBJECT-TYPE
        SYNTAX Counter32
        MAX-ACCESS read-only
        STATUS current
        DESCRIPTION
            "This attribute shows the number of data
             frames that were received at 5.5 Mbps."
	::= { wlanClientEntry 82 }

    wlanClientRxFrames2 OBJECT-TYPE
        SYNTAX Counter32
        MAX-ACCESS read-only
        STATUS current
        DESCRIPTION
            "This attribute shows the number of data
             frames that were received at 2 Mbps."
	::= { wlanClientEntry 83 }

    wlanClientRxFrames1 OBJECT-TYPE
        SYNTAX Counter32
        MAX-ACCESS read-only
        STATUS current
        DESCRIPTION
            "This attribute shows the number of data
             frames that were received at 1 Mbps."
	::= { wlanClientEntry 84 }

    wlanClientTxFrames54 OBJECT-TYPE
        SYNTAX Counter32
        MAX-ACCESS read-only
        STATUS current
        DESCRIPTION
            "This attribute shows the number of data
             frames that were transmitted at 54 Mbps."
	::= { wlanClientEntry 85 }

    wlanClientTxFrames48 OBJECT-TYPE
        SYNTAX Counter32
        MAX-ACCESS read-only
        STATUS current
        DESCRIPTION
            "This attribute shows the number of data
             frames that were transmitted at 48 Mbps."
	::= { wlanClientEntry 86 }

    wlanClientTxFrames36 OBJECT-TYPE
        SYNTAX Counter32
        MAX-ACCESS read-only
        STATUS current
        DESCRIPTION
            "This attribute shows the number of data
             frames that were transmitted at 36 Mbps."
	::= { wlanClientEntry 87 }

    wlanClientTxFrames24 OBJECT-TYPE
        SYNTAX Counter32
        MAX-ACCESS read-only
        STATUS current
        DESCRIPTION
            "This attribute shows the number of data
             frames that were transmitted at 24 Mbps."
	::= { wlanClientEntry 88 }

    wlanClientTxFrames18 OBJECT-TYPE
        SYNTAX Counter32
        MAX-ACCESS read-only
        STATUS current
        DESCRIPTION
            "This attribute shows the number of data
             frames that were transmitted at 18 Mbps."
	::= { wlanClientEntry 89 }

    wlanClientTxFrames12 OBJECT-TYPE
        SYNTAX Counter32
        MAX-ACCESS read-only
        STATUS current
        DESCRIPTION
            "This attribute shows the number of data
             frames that were transmitted at 12 Mbps."
	::= { wlanClientEntry 90 }

    wlanClientTxFrames11 OBJECT-TYPE
        SYNTAX Counter32
        MAX-ACCESS read-only
        STATUS current
        DESCRIPTION
            "This attribute shows the number of data
             frames that were transmitted at 11 Mbps."
	::= { wlanClientEntry 91 }

    wlanClientTxFrames9 OBJECT-TYPE
        SYNTAX Counter32
        MAX-ACCESS read-only
        STATUS current
        DESCRIPTION
            "This attribute shows the number of data
             frames that were transmitted at 9 Mbps."
	::= { wlanClientEntry 92 }

    wlanClientTxFrames6 OBJECT-TYPE
        SYNTAX Counter32
        MAX-ACCESS read-only
        STATUS current
        DESCRIPTION
            "This attribute shows the number of data
             frames that were transmitted at 6 Mbps."
	::= { wlanClientEntry 93 }

    wlanClientTxFrames5 OBJECT-TYPE
        SYNTAX Counter32
        MAX-ACCESS read-only
        STATUS current
        DESCRIPTION
            "This attribute shows the number of data
             frames that were transmitted at 5.5 Mbps."
	::= { wlanClientEntry 94 }

    wlanClientTxFrames2 OBJECT-TYPE
        SYNTAX Counter32
        MAX-ACCESS read-only
        STATUS current
        DESCRIPTION
            "This attribute shows the number of data
             frames that were transmitted at 2 Mbps."
	::= { wlanClientEntry 95 }

    wlanClientTxFrames1 OBJECT-TYPE
        SYNTAX Counter32
        MAX-ACCESS read-only
        STATUS current
        DESCRIPTION
            "This attribute shows the number of data
             frames that were transmitted at 1 Mbps."
	::= { wlanClientEntry 96 }

    wlanClientRSSI1 OBJECT-TYPE
	SYNTAX  WlanRSSI
	UNITS "dBm"
	MAX-ACCESS  read-only
	STATUS  current
	DESCRIPTION
	    "Receive signal strength of latest data frame
	     received by first receiver.
	     A value of 0 inidcates no connection."
	DEFVAL { 0 }
    ::= { wlanClientEntry 97 }

    wlanClientRSSI2 OBJECT-TYPE
	SYNTAX  WlanRSSI
	UNITS "dBm"
	MAX-ACCESS  read-only
	STATUS  current
	DESCRIPTION
	    "Receive signal strength of latest data frame
	     received by first receiver.
	     A value of 0 inidcates no second receiver
	     present or no connection."
	DEFVAL { 0 }
    ::= { wlanClientEntry 98 }

    wlanClientRSSI3 OBJECT-TYPE
	SYNTAX  WlanRSSI
	UNITS "dBm"
	MAX-ACCESS  read-only
	STATUS  current
	DESCRIPTION
	    "Receive signal strength of latest data frame
	     received by third receiver.
	     A value of 0 inidcates no third receiver
	     present or no connection."
	DEFVAL { 0 }
    ::= { wlanClientEntry 99 }

-- **********************************************************************
-- *    End of wlanClientTable  TABLE
-- **********************************************************************

-- **********************************************************************
-- *    wlanStatisticsTable  TABLE
-- **********************************************************************
wlanStatisticsTable OBJECT-TYPE
	SYNTAX  SEQUENCE OF WlanStatisticsEntry
	MAX-ACCESS  not-accessible
	STATUS  current
	DESCRIPTION
	    " Describe the WLAN statistics of a wlan card"
    ::= { wlan 14 }

    wlanStatisticsEntry OBJECT-TYPE
       SYNTAX  WlanStatisticsEntry
       MAX-ACCESS  not-accessible
       STATUS  current
       DESCRIPTION
	""
       INDEX   { wlanStatisticsWlanIf }
       ::= { wlanStatisticsTable 1 }

    WlanStatisticsEntry ::=
	SEQUENCE {
	wlanStatisticsWlanIf		INTEGER,
	wlanStatisticsOperation		INTEGER,

	-- statistics
	wlanStatisticsMSDUTxSuccess	Counter32,
	wlanStatisticsMSDUTxMulti	Counter32,
	wlanStatisticsMSDUTxDropped	Counter32,
	wlanStatisticsMSDUTxFailed	Counter32,
	wlanStatisticsMPDUTx		Counter32,
	wlanStatisticsMPDUTxOneRetry	Counter32,
	wlanStatisticsMPDUTxMultiRetry	Counter32,
	wlanStatisticsMPDUTxFailed	Counter32,
	wlanStatisticsMSDURxSuccess	Counter32,
	wlanStatisticsMSDURxMulti	Counter32,
	wlanStatisticsMSDURxDropped	Counter32,
	wlanStatisticsMSDURxFailed	Counter32,
	wlanStatisticsMPDURx		Counter32,
	wlanStatisticsMPDURxDups	Counter32,
	wlanStatisticsACKFailed		Counter32,
	wlanStatisticsFramesRx		Counter32,
	wlanStatisticsFrameRxError	Counter32,
	wlanStatisticsFrameAborts	Counter32,
	wlanStatisticsFrameAbortsPHY	Counter32,
	wlanStatisticsPrivTxRejected	Counter32,
	wlanStatisticsPrivRxPlain	Counter32,
	wlanStatisticsPrivRxFailed	Counter32,
	wlanStatisticsPrivRxNoKey	Counter32,
	wlanStatisticsRTSSuccess	Counter32,
	wlanStatisticsRTSFailed		Counter32
	 }

    wlanStatisticsWlanIf OBJECT-TYPE
	SYNTAX  INTEGER
	MAX-ACCESS  read-only
	STATUS  current
	DESCRIPTION
                "IfIndex of the wlan Interface the statistics belongs to."
    ::= { wlanStatisticsEntry 1 }

    wlanStatisticsOperation OBJECT-TYPE
	SYNTAX INTEGER { none(1), refresh(2) }
	MAX-ACCESS  read-write
	STATUS  current
	DESCRIPTION
	      "Setting this variable to 'refresh' initiates a refresh of the
	       statistic data. After refreshing it is autonomously changed to
	       'none'."
	DEFVAL { none }
    ::= { wlanStatisticsEntry 2 }

    wlanStatisticsMSDUTxSuccess OBJECT-TYPE
	SYNTAX  Counter32
	MAX-ACCESS  read-only
	STATUS  current
	DESCRIPTION
	"The number of successfully transmitted unicast MSDUs."
    ::= { wlanStatisticsEntry 10 }

    wlanStatisticsMSDUTxMulti OBJECT-TYPE
	SYNTAX  Counter32
	MAX-ACCESS  read-only
	STATUS  current
	DESCRIPTION
	"The number of successfully transmitted multicast MSDUs."
    ::= { wlanStatisticsEntry 11 }

    wlanStatisticsMSDUTxDropped OBJECT-TYPE
	SYNTAX  Counter32
	MAX-ACCESS  read-only
	STATUS  current
	DESCRIPTION
	"The number of unicast and multicast MSDUs dropped before
	 a transmission attempt was made."
    ::= { wlanStatisticsEntry 12 }

    wlanStatisticsMSDUTxFailed OBJECT-TYPE
	SYNTAX  Counter32
	MAX-ACCESS  read-only
	STATUS  current
	DESCRIPTION
	"The number of unicast and multicast MSDUs that could not
	 be or were not successfully transmitted by the device."
    ::= { wlanStatisticsEntry 13 }

    wlanStatisticsMPDUTx OBJECT-TYPE
	SYNTAX  Counter32
	MAX-ACCESS  read-only
	STATUS  current
	DESCRIPTION
	"The number of successfully transmitted unicast and
	 multicast MPDUs."
    ::= { wlanStatisticsEntry 14 }

    wlanStatisticsMPDUTxOneRetry OBJECT-TYPE
	SYNTAX  Counter32
	MAX-ACCESS  read-only
	STATUS  current
	DESCRIPTION
	"The number of unicast MPDUs successfully transmitted
	 after one retry."
    ::= { wlanStatisticsEntry 15 }

    wlanStatisticsMPDUTxMultiRetry OBJECT-TYPE
	SYNTAX  Counter32
	MAX-ACCESS  read-only
	STATUS  current
	DESCRIPTION
	"The number of unicast MPDUs successfully transmitted
	 after two or more retries."
    ::= { wlanStatisticsEntry 16 }

    wlanStatisticsMPDUTxFailed OBJECT-TYPE
	SYNTAX  Counter32
	MAX-ACCESS  read-only
	STATUS  current
	DESCRIPTION
	"The number of unicast MPDUs for which the maximum
	 number of retries were exceeded."
    ::= { wlanStatisticsEntry 17 }

    wlanStatisticsMSDURxSuccess OBJECT-TYPE
	SYNTAX  Counter32
	MAX-ACCESS  read-only
	STATUS  current
	DESCRIPTION
	"The number of successfully received unicast MSDUs."
    ::= { wlanStatisticsEntry 18 }

    wlanStatisticsMSDURxMulti OBJECT-TYPE
	SYNTAX  Counter32
	MAX-ACCESS  read-only
	STATUS  current
	DESCRIPTION
	"The number of successfully received multicast MSDUs."
    ::= { wlanStatisticsEntry 19 }

    wlanStatisticsMSDURxDropped OBJECT-TYPE
	SYNTAX  Counter32
	MAX-ACCESS  read-only
	STATUS  current
	DESCRIPTION
	"The number of dropped unicast and multicast MSDUs."
    ::= { wlanStatisticsEntry 20 }

    wlanStatisticsMSDURxFailed OBJECT-TYPE
	SYNTAX  Counter32
	MAX-ACCESS  read-only
	STATUS  current
	DESCRIPTION
	"The number of partially or erroneously received
	 unitcast and multicast MSDUs."
    ::= { wlanStatisticsEntry 21 }

    wlanStatisticsMPDURx OBJECT-TYPE
	SYNTAX  Counter32
	MAX-ACCESS  read-only
	STATUS  current
	DESCRIPTION
	"The number of successfully received unicast MPDUs."
    ::= { wlanStatisticsEntry 22 }

    wlanStatisticsMPDURxDups OBJECT-TYPE
	SYNTAX  Counter32
	MAX-ACCESS  read-only
	STATUS  current
	DESCRIPTION
	"The number of successfully received unicast MPDUs
	 that were a duplicate of earlier frames."
    ::= { wlanStatisticsEntry 23 }

    wlanStatisticsRTSSuccess OBJECT-TYPE
	SYNTAX  Counter32
	MAX-ACCESS  read-only
	STATUS  current
	DESCRIPTION
	"The number of CTS frames received in response to
	 an RTS frame."
    ::= { wlanStatisticsEntry 24 }

    wlanStatisticsRTSFailed OBJECT-TYPE
	SYNTAX  Counter32
	MAX-ACCESS  read-only
	STATUS  current
	DESCRIPTION
	"The number of transmitted RTS frames for which
	 no response CTS frame was received."
    ::= { wlanStatisticsEntry 25 }

    wlanStatisticsACKFailed OBJECT-TYPE
	SYNTAX  Counter32
	MAX-ACCESS  read-only
	STATUS  current
	DESCRIPTION
	"The object counts the number of frame transmissions
	 for which an acknowledgment response frame was expected
	 but not received."
    ::= { wlanStatisticsEntry 26 }

    wlanStatisticsFramesRx OBJECT-TYPE
	SYNTAX  Counter32
	MAX-ACCESS  read-only
	STATUS  current
	DESCRIPTION
	"The number of successfully received frames, before
	 any address and type filtering."
    ::= { wlanStatisticsEntry 27 }

    wlanStatisticsFrameRxError OBJECT-TYPE
	SYNTAX  Counter32
	MAX-ACCESS  read-only
	STATUS  current
	DESCRIPTION
	"The number of unsuccessfully received frames."
    ::= { wlanStatisticsEntry 28 }

    wlanStatisticsFrameAborts OBJECT-TYPE
	SYNTAX  Counter32
	MAX-ACCESS  read-only
	STATUS  current
	DESCRIPTION
	"The number of aborted frames."
    ::= { wlanStatisticsEntry 29 }

    wlanStatisticsFrameAbortsPHY OBJECT-TYPE
	SYNTAX  Counter32
	MAX-ACCESS  read-only
	STATUS  current
	DESCRIPTION
	"The number of PHY aborted frames."
    ::= { wlanStatisticsEntry 30 }

    wlanStatisticsPrivTxRejected OBJECT-TYPE
	SYNTAX  Counter32
	MAX-ACCESS  read-only
	STATUS  current
	DESCRIPTION
	"The number of MPDUs that were not transmitted because
	 no appropriate privacy configuration was available."
    ::= { wlanStatisticsEntry 31 }

    wlanStatisticsPrivRxPlain OBJECT-TYPE
	SYNTAX  Counter32
	MAX-ACCESS  read-only
	STATUS  current
	DESCRIPTION
	"The number of received MPDUs that were rejected because
	 they were unencrypted."
    ::= { wlanStatisticsEntry 32 }

    wlanStatisticsPrivRxFailed OBJECT-TYPE
	SYNTAX  Counter32
	MAX-ACCESS  read-only
	STATUS  current
	DESCRIPTION
	"The number of received crypted MPDUs that were rejected
	 because they could not be successfully decrypted."
    ::= { wlanStatisticsEntry 33 }

    wlanStatisticsPrivRxNoKey OBJECT-TYPE
	SYNTAX  Counter32
	MAX-ACCESS  read-only
	STATUS  current
	DESCRIPTION
	"The number of received crypted MPDUs that could not be
	 decrypted because no key was available for decryption."
    ::= { wlanStatisticsEntry 34 }
-- **********************************************************************
-- *    End of wlanStatisticsTable  TABLE
-- **********************************************************************

-- **********************************************************************
-- *    wlanScanResultsTable  TABLE
-- **********************************************************************
wlanScanResultsTable OBJECT-TYPE
	SYNTAX  SEQUENCE OF WlanScanResultsEntry
	MAX-ACCESS  not-accessible
	STATUS  current
	DESCRIPTION
	    "This table contains the list of BSS entries found by foreground
	     or background scanning in client mode."
    ::= { wlan 15 }

    wlanScanResultsEntry OBJECT-TYPE
       SYNTAX  WlanScanResultsEntry
       MAX-ACCESS  not-accessible
       STATUS  current
       DESCRIPTION
	""
       INDEX   { wlanScanResultsIfIndex, wlanScanResultsIndex }
       ::= { wlanScanResultsTable 1 }

    WlanScanResultsEntry ::=
	SEQUENCE {
	wlanScanResultsIfIndex		INTEGER,
	wlanScanResultsIndex		INTEGER,
	wlanScanResultsBSSID		MacAddress,
	wlanScanResultsAge		INTEGER,
	wlanScanResultsRSSI		WlanRSSI,
	wlanScanResultsRSSI1		WlanRSSI,
	wlanScanResultsRSSI2		WlanRSSI,
	wlanScanResultsRSSI3		WlanRSSI,
	wlanScanResultsSSID		DisplayString,
	wlanScanResultsChannel		INTEGER,
	wlanScanResultsDTIMPeriod	INTEGER,
	wlanScanResultsBeaconPeriod	INTEGER,
	wlanScanResultsCapInfo		INTEGER,
	wlanScanResultsRates		OCTET STRING,
	wlanScanResultsBasicRates	OCTET STRING,
	wlanScanResultsExtendedRates	OCTET STRING,
	wlanScanResultsFrameData	OCTET STRING,
	wlanScanResultsType		INTEGER,
	wlanScanResultsPrivacy		INTEGER,
	wlanScanResultsWPAUnicastCipher	BITS,
	wlanScanResultsRSNUnicastCipher	BITS,
	wlanScanResultsSignal		WlanRSSI
	}

    wlanScanResultsIfIndex OBJECT-TYPE
	SYNTAX  INTEGER
	MAX-ACCESS  read-only
	STATUS  current
	DESCRIPTION
	    "ifIndex of the WLAN Interface the scan results belong to."
    ::= { wlanScanResultsEntry 1 }

    wlanScanResultsIndex OBJECT-TYPE
	SYNTAX  INTEGER
	MAX-ACCESS  read-only
	STATUS  current
	DESCRIPTION
	    "Auxiliary index for different BSS entries."
    ::= { wlanScanResultsEntry 2 }

    wlanScanResultsBSSID OBJECT-TYPE
	SYNTAX  MacAddress
	MAX-ACCESS  read-only
	STATUS  current
	DESCRIPTION
	    "BSSID of this BSS."
    ::= { wlanScanResultsEntry 3 }

    wlanScanResultsAge OBJECT-TYPE
	SYNTAX  INTEGER
	UNITS "TU"
	MAX-ACCESS  read-only
	STATUS  current
	DESCRIPTION
	    "Age of this BSS entry."
    ::= { wlanScanResultsEntry 4 }

    wlanScanResultsRSSI OBJECT-TYPE
	SYNTAX  WlanRSSI
	UNITS "dBm"
	MAX-ACCESS  read-only
	STATUS  current
	DESCRIPTION
                "Receive signal strength of this BSS."
    ::= { wlanScanResultsEntry 5 }

    wlanScanResultsSSID OBJECT-TYPE
	SYNTAX  DisplayString
	MAX-ACCESS  read-only
	STATUS  current
	DESCRIPTION
                "SSID aka network name of this BSS.
                 If broadcasting of SSID is disabled on this
                 BSS, this string may be empty."
    ::= { wlanScanResultsEntry 6 }

    wlanScanResultsChannel OBJECT-TYPE
	SYNTAX  INTEGER (1..256)
	MAX-ACCESS  read-only
	STATUS  current
	DESCRIPTION
                "The channel this BSS was received on."
    ::= { wlanScanResultsEntry 7 }

    wlanScanResultsDTIMPeriod OBJECT-TYPE
	SYNTAX INTEGER (0..255)
	MAX-ACCESS  read-only
	STATUS  current
	DESCRIPTION
            "The number of DTIM intervals between
             the start of CFPs for this BSS."
    ::= { wlanScanResultsEntry 8 }

    wlanScanResultsBeaconPeriod OBJECT-TYPE
	SYNTAX INTEGER (1..65535)
	MAX-ACCESS  read-only
	STATUS  current
	DESCRIPTION
	    "This attribute contains the number of TU that this
	    BSS uses for scheduling Beacon transmissions."
    ::= { wlanScanResultsEntry 9 }

    wlanScanResultsCapInfo OBJECT-TYPE
	SYNTAX INTEGER
	MAX-ACCESS  read-only
	STATUS  current
	DESCRIPTION
            "The number of DTIM intervals between
             the start of CFPs for this BSS."
    ::= { wlanScanResultsEntry 10 }

    wlanScanResultsRates OBJECT-TYPE
	SYNTAX OCTET STRING
	UNITS "TU"
	MAX-ACCESS  read-only
	STATUS  current
	DESCRIPTION
            "This attribute contains one octet for each
             supported rate in this BSS, in 500 Kbps units."
    ::= { wlanScanResultsEntry 11 }

    wlanScanResultsBasicRates OBJECT-TYPE
	SYNTAX OCTET STRING
	MAX-ACCESS  read-only
	STATUS  current
	DESCRIPTION
            "This attribute contains one octet for each required
             basic rate in this BSS, in 500 Kbps units."
    ::= { wlanScanResultsEntry 12 }

    wlanScanResultsExtendedRates OBJECT-TYPE
	SYNTAX OCTET STRING
	MAX-ACCESS  read-only
	STATUS  current
	DESCRIPTION
            "This attribute contains one octet for each supported
             extended rate in this BSS, in 500 Kbps units."
    ::= { wlanScanResultsEntry 13 }

    wlanScanResultsFrameData  OBJECT-TYPE
	SYNTAX OCTET STRING
	MAX-ACCESS  read-only
	STATUS  current
	DESCRIPTION
            "This attribute contains raw data from 802.11 beacon or
             probe response frames, starting with the 802.11 timestamp."
    ::= { wlanScanResultsEntry 14 }

    wlanScanResultsType  OBJECT-TYPE
	SYNTAX INTEGER { access-point(1), ad-hoc(2)}
	MAX-ACCESS  read-only
	STATUS  current
	DESCRIPTION
            "This attribute contains the device type of the
             scanned device."
        DEFVAL { access-point }
    ::= { wlanScanResultsEntry 15 }

    wlanScanResultsPrivacy  OBJECT-TYPE
	SYNTAX INTEGER { none (1),
			 wep(2),
			 wpa-psk(3),
			 wpaandwpa2-psk(4),
			 wpa2-psk(5),
			 wpa-enterprise(6),
			 wpaandwpa2-enterprise(7),
			 wpa2-enterprise(8)}
	MAX-ACCESS  read-only
	STATUS  current
	DESCRIPTION
            "This attribute contains the privacy type of the
             scanned device."
        DEFVAL { none }
    ::= { wlanScanResultsEntry 16 }

    wlanScanResultsWPAUnicastCipher  OBJECT-TYPE
	SYNTAX BITS {
			cipher-none(0),
			cipher-wep40(1),
			cipher-wep104(2),
			cipher-tkip(3),
			cipher-aes(4)
		    }
	MAX-ACCESS  read-only
	STATUS  current
	DESCRIPTION
            "This attribute contains the WPA unicast ciphers of the
             scanned device."
    ::= { wlanScanResultsEntry 17 }

    wlanScanResultsRSNUnicastCipher  OBJECT-TYPE
	SYNTAX BITS {
			cipher-none(0),
			cipher-wep40(1),
			cipher-wep104(2),
			cipher-tkip(3),
			cipher-aes(4)
		    }
	MAX-ACCESS  read-only
	STATUS  current
	DESCRIPTION
            "This attribute contains the RSN unicast ciphers of the
             scanned device."
    ::= { wlanScanResultsEntry 18 }

    wlanScanResultsRSSI1 OBJECT-TYPE
	SYNTAX  WlanRSSI
	UNITS "dBm"
	MAX-ACCESS  read-only
	STATUS  current
	DESCRIPTION
            "Receive signal strength of this BSS at first receiver."
    ::= { wlanScanResultsEntry 19 }

    wlanScanResultsRSSI2 OBJECT-TYPE
	SYNTAX  WlanRSSI
	UNITS "dBm"
	MAX-ACCESS  read-only
	STATUS  current
	DESCRIPTION
            "Receive signal strength of this BSS at second receiver.
             A value of 0 indicates no second receiver present."
    ::= { wlanScanResultsEntry 20 }

    wlanScanResultsRSSI3 OBJECT-TYPE
	SYNTAX  WlanRSSI
	UNITS "dBm"
	MAX-ACCESS  read-only
	STATUS  current
	DESCRIPTION
            "Receive signal strength of this BSS at third receiver.
             A value of 0 indicates no third receiver present."
    ::= { wlanScanResultsEntry 21 }

    wlanScanResultsSignal OBJECT-TYPE
	SYNTAX  WlanRSSI
	UNITS "dBm"
	MAX-ACCESS  read-only
	STATUS  current
	DESCRIPTION
                "Receive signal strength of this BSS."
    ::= { wlanScanResultsEntry 24 }


-- **********************************************************************
-- *    End of wlanScanResultsTable  TABLE
-- **********************************************************************

-- **********************************************************************
-- *    wlanStationHTStatsTable  TABLE
-- **********************************************************************
wlanStationHTStatsTable OBJECT-TYPE
    SYNTAX  SEQUENCE OF WlanStationHTStatsEntry
    MAX-ACCESS  not-accessible
    STATUS  current
    DESCRIPTION
            "The wlanStationHTStatsTable contains additional statistical
             data about 802.11n HT frames related to the clients
             currently associated to our access points.

             Each entry corresponds to an wlanStationTable entry.
             Entries cannot be added or deleted by the user.

             Creating entries: Entries are created by the system
             automatically when a new STA is associated.

             Deleting entries: Entries are removed by the system
             whenever an associated STA is removed."
    ::= { wlan 16 }

    wlanStationHTStatsEntry OBJECT-TYPE
	SYNTAX  WlanStationHTStatsEntry
	MAX-ACCESS  not-accessible
	STATUS  current
	DESCRIPTION
	""
	AUGMENTS   { wlanStationEntry }
    ::= { wlanStationHTStatsTable 1 }

    WlanStationHTStatsEntry ::=
	SEQUENCE {
		wlanStationHTStatsRxFramesMCS0	Counter32,
		wlanStationHTStatsRxFramesMCS1	Counter32,
		wlanStationHTStatsRxFramesMCS2	Counter32,
		wlanStationHTStatsRxFramesMCS3	Counter32,
		wlanStationHTStatsRxFramesMCS4	Counter32,
		wlanStationHTStatsRxFramesMCS5        Counter32,
		wlanStationHTStatsRxFramesMCS6	Counter32,
		wlanStationHTStatsRxFramesMCS7	Counter32,
		wlanStationHTStatsRxFramesMCS8	Counter32,
		wlanStationHTStatsRxFramesMCS9	Counter32,
		wlanStationHTStatsRxFramesMCS10	Counter32,
		wlanStationHTStatsRxFramesMCS11	Counter32,
	        wlanStationHTStatsRxFramesMCS12	Counter32,
                wlanStationHTStatsRxFramesMCS13	Counter32,
                wlanStationHTStatsRxFramesMCS14	Counter32,
                wlanStationHTStatsRxFramesMCS15	Counter32,
		wlanStationHTStatsRxFramesMCS16	Counter32,
		wlanStationHTStatsRxFramesMCS17	Counter32,
		wlanStationHTStatsRxFramesMCS18	Counter32,
		wlanStationHTStatsRxFramesMCS19	Counter32,
		wlanStationHTStatsRxFramesMCS20	Counter32,
		wlanStationHTStatsRxFramesMCS21	Counter32,
		wlanStationHTStatsRxFramesMCS22	Counter32,
		wlanStationHTStatsRxFramesMCS23	Counter32,

		wlanStationHTStatsTxFramesMCS0    Counter32,
		wlanStationHTStatsTxFramesMCS1	Counter32,
		wlanStationHTStatsTxFramesMCS2	Counter32,
		wlanStationHTStatsTxFramesMCS3	Counter32,
		wlanStationHTStatsTxFramesMCS4	Counter32,
		wlanStationHTStatsTxFramesMCS5    Counter32,
		wlanStationHTStatsTxFramesMCS6	Counter32,
		wlanStationHTStatsTxFramesMCS7	Counter32,
		wlanStationHTStatsTxFramesMCS8	Counter32,
		wlanStationHTStatsTxFramesMCS9	Counter32,
		wlanStationHTStatsTxFramesMCS10	Counter32,
		wlanStationHTStatsTxFramesMCS11	Counter32,
                wlanStationHTStatsTxFramesMCS12	Counter32,
                wlanStationHTStatsTxFramesMCS13	Counter32,
                wlanStationHTStatsTxFramesMCS14	Counter32,
                wlanStationHTStatsTxFramesMCS15	Counter32,
		wlanStationHTStatsTxFramesMCS16	Counter32,
		wlanStationHTStatsTxFramesMCS17	Counter32,
		wlanStationHTStatsTxFramesMCS18	Counter32,
		wlanStationHTStatsTxFramesMCS19	Counter32,
		wlanStationHTStatsTxFramesMCS20	Counter32,
		wlanStationHTStatsTxFramesMCS21	Counter32,
		wlanStationHTStatsTxFramesMCS22	Counter32,
		wlanStationHTStatsTxFramesMCS23	Counter32,
                wlanStationHTStatsRxBandwidth     INTEGER,
                wlanStationHTStatsRxGuardInterval INTEGER,
                wlanStationHTStatsTxBandwidth     INTEGER,
                wlanStationHTStatsTxGuardInterval INTEGER
	}

    wlanStationHTStatsRxFramesMCS0 OBJECT-TYPE
        SYNTAX Counter32
        MAX-ACCESS read-only
        STATUS current
        DESCRIPTION
            "This attribute shows the number of HT data
             frames that were received at MCS 0."
	::= { wlanStationHTStatsEntry 1 }

    wlanStationHTStatsRxFramesMCS1 OBJECT-TYPE
        SYNTAX Counter32
        MAX-ACCESS read-only
        STATUS current
        DESCRIPTION
            "This attribute shows the number of HT data
             frames that were received at MCS 1."
	::= { wlanStationHTStatsEntry 2 }

    wlanStationHTStatsRxFramesMCS2 OBJECT-TYPE
        SYNTAX Counter32
        MAX-ACCESS read-only
        STATUS current
        DESCRIPTION
            "This attribute shows the number of HT data
             frames that were received at MCS 2."
	::= { wlanStationHTStatsEntry 3 }

    wlanStationHTStatsRxFramesMCS3 OBJECT-TYPE
        SYNTAX Counter32
        MAX-ACCESS read-only
        STATUS current
        DESCRIPTION
            "This attribute shows the number of HT data
             frames that were received at MCS 3."
	::= { wlanStationHTStatsEntry 4 }

    wlanStationHTStatsRxFramesMCS4 OBJECT-TYPE
        SYNTAX Counter32
        MAX-ACCESS read-only
        STATUS current
        DESCRIPTION
            "This attribute shows the number of HT data
             frames that were received at MCS 4."
	::= { wlanStationHTStatsEntry 5 }

    wlanStationHTStatsRxFramesMCS5 OBJECT-TYPE
        SYNTAX Counter32
        MAX-ACCESS read-only
        STATUS current
        DESCRIPTION
            "This attribute shows the number of HT data
             frames that were received at MCS 5."
	::= { wlanStationHTStatsEntry 6 }

    wlanStationHTStatsRxFramesMCS6 OBJECT-TYPE
        SYNTAX Counter32
        MAX-ACCESS read-only
        STATUS current
        DESCRIPTION
            "This attribute shows the number of HT data
             frames that were received at MCS 6."
	::= { wlanStationHTStatsEntry 7 }

    wlanStationHTStatsRxFramesMCS7 OBJECT-TYPE
        SYNTAX Counter32
        MAX-ACCESS read-only
        STATUS current
        DESCRIPTION
            "This attribute shows the number of HT data
             frames that were received at MCS 7."
	::= { wlanStationHTStatsEntry 8 }

    wlanStationHTStatsRxFramesMCS8 OBJECT-TYPE
        SYNTAX Counter32
        MAX-ACCESS read-only
        STATUS current
        DESCRIPTION
            "This attribute shows the number of data
             frames that were received at MCS 8."
	::= { wlanStationHTStatsEntry 9 }

    wlanStationHTStatsRxFramesMCS9 OBJECT-TYPE
        SYNTAX Counter32
        MAX-ACCESS read-only
        STATUS current
        DESCRIPTION
            "This attribute shows the number of HT data
             frames that were received at MCS 9."
	::= { wlanStationHTStatsEntry 10 }

    wlanStationHTStatsRxFramesMCS10 OBJECT-TYPE
        SYNTAX Counter32
        MAX-ACCESS read-only
        STATUS current
        DESCRIPTION
            "This attribute shows the number of HT data
             frames that were received at MCS 10."
	::= { wlanStationHTStatsEntry 11 }

    wlanStationHTStatsRxFramesMCS11 OBJECT-TYPE
        SYNTAX Counter32
        MAX-ACCESS read-only
        STATUS current
        DESCRIPTION
            "This attribute shows the number of HT data
             frames that were received at MCS 11."
	::= { wlanStationHTStatsEntry 12 }

    wlanStationHTStatsRxFramesMCS12 OBJECT-TYPE
        SYNTAX Counter32
        MAX-ACCESS read-only
        STATUS current
        DESCRIPTION
            "This attribute shows the number of HT data
             frames that were received at MCS 12."
	::= { wlanStationHTStatsEntry 13 }

    wlanStationHTStatsRxFramesMCS13 OBJECT-TYPE
        SYNTAX Counter32
        MAX-ACCESS read-only
        STATUS current
        DESCRIPTION
            "This attribute shows the number of HT data
             frames that were received at MCS 13."
	::= { wlanStationHTStatsEntry 14 }

    wlanStationHTStatsRxFramesMCS14 OBJECT-TYPE
        SYNTAX Counter32
        MAX-ACCESS read-only
        STATUS current
        DESCRIPTION
            "This attribute shows the number of HT data
             frames that were received at MCS 14."
	::= { wlanStationHTStatsEntry 15 }

    wlanStationHTStatsRxFramesMCS15 OBJECT-TYPE
        SYNTAX Counter32
        MAX-ACCESS read-only
        STATUS current
        DESCRIPTION
            "This attribute shows the number of HT data
             frames that were received at MCS 15."
	::= { wlanStationHTStatsEntry 16 }

    wlanStationHTStatsTxFramesMCS0 OBJECT-TYPE
        SYNTAX Counter32
        MAX-ACCESS read-only
        STATUS current
        DESCRIPTION
            "This attribute shows the number of HT data
             frames that were transmitted at MCS 0."
	::= { wlanStationHTStatsEntry 17 }

    wlanStationHTStatsTxFramesMCS1 OBJECT-TYPE
        SYNTAX Counter32
        MAX-ACCESS read-only
        STATUS current
        DESCRIPTION
            "This attribute shows the number of HT data
             frames that were transmitted at MCS 1."
	::= { wlanStationHTStatsEntry 18 }

    wlanStationHTStatsTxFramesMCS2 OBJECT-TYPE
        SYNTAX Counter32
        MAX-ACCESS read-only
        STATUS current
        DESCRIPTION
            "This attribute shows the number of HT data
             frames that were transmitted at MCS 2."
	::= { wlanStationHTStatsEntry 19 }

    wlanStationHTStatsTxFramesMCS3 OBJECT-TYPE
        SYNTAX Counter32
        MAX-ACCESS read-only
        STATUS current
        DESCRIPTION
            "This attribute shows the number of HT data
             frames that were transmitted at MCS 3."
	::= { wlanStationHTStatsEntry 20 }

    wlanStationHTStatsTxFramesMCS4 OBJECT-TYPE
        SYNTAX Counter32
        MAX-ACCESS read-only
        STATUS current
        DESCRIPTION
            "This attribute shows the number of HT data
             frames that were transmitted at MCS 4."
	::= { wlanStationHTStatsEntry 21 }

    wlanStationHTStatsTxFramesMCS5 OBJECT-TYPE
        SYNTAX Counter32
        MAX-ACCESS read-only
        STATUS current
        DESCRIPTION
            "This attribute shows the number of HT data
             frames that were transmitted at MCS 5."
	::= { wlanStationHTStatsEntry 22 }

    wlanStationHTStatsTxFramesMCS6 OBJECT-TYPE
        SYNTAX Counter32
        MAX-ACCESS read-only
        STATUS current
        DESCRIPTION
            "This attribute shows the number of HT data
             frames that were transmitted at MCS 6."
	::= { wlanStationHTStatsEntry 23 }

    wlanStationHTStatsTxFramesMCS7 OBJECT-TYPE
        SYNTAX Counter32
        MAX-ACCESS read-only
        STATUS current
        DESCRIPTION
            "This attribute shows the number of HT data
             frames that were transmitted at MCS 7."
	::= { wlanStationHTStatsEntry 24 }

    wlanStationHTStatsTxFramesMCS8 OBJECT-TYPE
        SYNTAX Counter32
        MAX-ACCESS read-only
        STATUS current
        DESCRIPTION
            "This attribute shows the number of data
             frames that were transmitted at MCS 8."
	::= { wlanStationHTStatsEntry 25 }

    wlanStationHTStatsTxFramesMCS9 OBJECT-TYPE
        SYNTAX Counter32
        MAX-ACCESS read-only
        STATUS current
        DESCRIPTION
            "This attribute shows the number of HT data
             frames that were transmitted at MCS 9."
	::= { wlanStationHTStatsEntry 26 }

    wlanStationHTStatsTxFramesMCS10 OBJECT-TYPE
        SYNTAX Counter32
        MAX-ACCESS read-only
        STATUS current
        DESCRIPTION
            "This attribute shows the number of HT data
             frames that were transmitted at MCS 10."
	::= { wlanStationHTStatsEntry 27 }

    wlanStationHTStatsTxFramesMCS11 OBJECT-TYPE
        SYNTAX Counter32
        MAX-ACCESS read-only
        STATUS current
        DESCRIPTION
            "This attribute shows the number of HT data
             frames that were transmitted at MCS 11."
	::= { wlanStationHTStatsEntry 28 }

    wlanStationHTStatsTxFramesMCS12 OBJECT-TYPE
        SYNTAX Counter32
        MAX-ACCESS read-only
        STATUS current
        DESCRIPTION
            "This attribute shows the number of HT data
             frames that were transmitted at MCS 12."
	::= { wlanStationHTStatsEntry 29 }

    wlanStationHTStatsTxFramesMCS13 OBJECT-TYPE
        SYNTAX Counter32
        MAX-ACCESS read-only
        STATUS current
        DESCRIPTION
            "This attribute shows the number of HT data
             frames that were transmitted at MCS 13."
	::= { wlanStationHTStatsEntry 30 }

    wlanStationHTStatsTxFramesMCS14 OBJECT-TYPE
        SYNTAX Counter32
        MAX-ACCESS read-only
        STATUS current
        DESCRIPTION
            "This attribute shows the number of HT data
             frames that were transmitted at MCS 14."
	::= { wlanStationHTStatsEntry 31 }

    wlanStationHTStatsTxFramesMCS15 OBJECT-TYPE
        SYNTAX Counter32
        MAX-ACCESS read-only
        STATUS current
        DESCRIPTION
            "This attribute shows the number of HT data
             frames that were transmitted at MCS 15."
	::= { wlanStationHTStatsEntry 32 }

    wlanStationHTStatsRxBandwidth OBJECT-TYPE
        SYNTAX INTEGER { b20MHz(1), b40MHz(2) }
        MAX-ACCESS read-only
        STATUS current
        DESCRIPTION
            "This attribute shows the bandwidth the station
             used with the last received frame: 20 MHz (1) or 40 MHz (2)."
        DEFVAL { b20MHz }
	::= { wlanStationHTStatsEntry 33 }

    wlanStationHTStatsRxGuardInterval OBJECT-TYPE
        SYNTAX INTEGER { long(1), short(2) }
        MAX-ACCESS read-only
        STATUS current
        DESCRIPTION
            "This attribute shows the length of the guard interval
             the station used with the last received frame:
             long (1)  or short (2)."
        DEFVAL { long }
	::= { wlanStationHTStatsEntry 34 }

    wlanStationHTStatsTxBandwidth OBJECT-TYPE
        SYNTAX INTEGER { b20MHz(1), b40MHz(2) }
        MAX-ACCESS read-only
        STATUS current
        DESCRIPTION
            "This attribute shows the bandwidth the access point
             used for transmitting the last frame: 20 MHz (1) or 40 MHz (2)."
        DEFVAL { b20MHz }
	::= { wlanStationHTStatsEntry 35 }

    wlanStationHTStatsTxGuardInterval OBJECT-TYPE
        SYNTAX INTEGER { long(1), short(2) }
        MAX-ACCESS read-only
        STATUS current
        DESCRIPTION
            "This attribute shows the length of the guard interval
             the access point used for transmitting the last frame:
             long (1)  or short (2)."
        DEFVAL { long }
	::= { wlanStationHTStatsEntry 36 }

    wlanStationHTStatsRxFramesMCS16 OBJECT-TYPE
        SYNTAX Counter32
        MAX-ACCESS read-only
        STATUS current
        DESCRIPTION
            "This attribute shows the number of HT data
             frames that were received at MCS 16."
	::= { wlanStationHTStatsEntry 37 }

    wlanStationHTStatsRxFramesMCS17 OBJECT-TYPE
        SYNTAX Counter32
        MAX-ACCESS read-only
        STATUS current
        DESCRIPTION
            "This attribute shows the number of HT data
             frames that were received at MCS 17."
	::= { wlanStationHTStatsEntry 38 }

    wlanStationHTStatsRxFramesMCS18 OBJECT-TYPE
        SYNTAX Counter32
        MAX-ACCESS read-only
        STATUS current
        DESCRIPTION
            "This attribute shows the number of HT data
             frames that were received at MCS 18."
	::= { wlanStationHTStatsEntry 39 }

    wlanStationHTStatsRxFramesMCS19 OBJECT-TYPE
        SYNTAX Counter32
        MAX-ACCESS read-only
        STATUS current
        DESCRIPTION
            "This attribute shows the number of HT data
             frames that were received at MCS 19."
	::= { wlanStationHTStatsEntry 40 }

    wlanStationHTStatsRxFramesMCS20 OBJECT-TYPE
        SYNTAX Counter32
        MAX-ACCESS read-only
        STATUS current
        DESCRIPTION
            "This attribute shows the number of HT data
             frames that were received at MCS 20."
	::= { wlanStationHTStatsEntry 41 }

    wlanStationHTStatsRxFramesMCS21 OBJECT-TYPE
        SYNTAX Counter32
        MAX-ACCESS read-only
        STATUS current
        DESCRIPTION
            "This attribute shows the number of HT data
             frames that were received at MCS 21."
	::= { wlanStationHTStatsEntry 42 }

    wlanStationHTStatsRxFramesMCS22 OBJECT-TYPE
        SYNTAX Counter32
        MAX-ACCESS read-only
        STATUS current
        DESCRIPTION
            "This attribute shows the number of HT data
             frames that were received at MCS 22."
	::= { wlanStationHTStatsEntry 43 }

    wlanStationHTStatsRxFramesMCS23 OBJECT-TYPE
        SYNTAX Counter32
        MAX-ACCESS read-only
        STATUS current
        DESCRIPTION
            "This attribute shows the number of HT data
             frames that were received at MCS 23."
	::= { wlanStationHTStatsEntry 44 }

    wlanStationHTStatsTxFramesMCS16 OBJECT-TYPE
        SYNTAX Counter32
        MAX-ACCESS read-only
        STATUS current
        DESCRIPTION
            "This attribute shows the number of HT data
             frames that were transmitted at MCS 16."
	::= { wlanStationHTStatsEntry 45 }

    wlanStationHTStatsTxFramesMCS17 OBJECT-TYPE
        SYNTAX Counter32
        MAX-ACCESS read-only
        STATUS current
        DESCRIPTION
            "This attribute shows the number of HT data
             frames that were transmitted at MCS 17."
	::= { wlanStationHTStatsEntry 46 }

    wlanStationHTStatsTxFramesMCS18 OBJECT-TYPE
        SYNTAX Counter32
        MAX-ACCESS read-only
        STATUS current
        DESCRIPTION
            "This attribute shows the number of HT data
             frames that were transmitted at MCS 18."
	::= { wlanStationHTStatsEntry 47 }

    wlanStationHTStatsTxFramesMCS19 OBJECT-TYPE
        SYNTAX Counter32
        MAX-ACCESS read-only
        STATUS current
        DESCRIPTION
            "This attribute shows the number of HT data
             frames that were transmitted at MCS 19."
	::= { wlanStationHTStatsEntry 48 }

    wlanStationHTStatsTxFramesMCS20 OBJECT-TYPE
        SYNTAX Counter32
        MAX-ACCESS read-only
        STATUS current
        DESCRIPTION
            "This attribute shows the number of HT data
             frames that were transmitted at MCS 20."
	::= { wlanStationHTStatsEntry 49 }

    wlanStationHTStatsTxFramesMCS21 OBJECT-TYPE
        SYNTAX Counter32
        MAX-ACCESS read-only
        STATUS current
        DESCRIPTION
            "This attribute shows the number of HT data
             frames that were transmitted at MCS 21."
	::= { wlanStationHTStatsEntry 50 }

    wlanStationHTStatsTxFramesMCS22 OBJECT-TYPE
        SYNTAX Counter32
        MAX-ACCESS read-only
        STATUS current
        DESCRIPTION
            "This attribute shows the number of HT data
             frames that were transmitted at MCS 22."
	::= { wlanStationHTStatsEntry 51 }

    wlanStationHTStatsTxFramesMCS23 OBJECT-TYPE
        SYNTAX Counter32
        MAX-ACCESS read-only
        STATUS current
        DESCRIPTION
            "This attribute shows the number of HT data
             frames that were transmitted at MCS 23."
	::= { wlanStationHTStatsEntry 52 }

-- **********************************************************************
-- *    End of wlanStationHTStatsTable  TABLE
-- **********************************************************************

-- **********************************************************************
-- *    wlanClientHTStatsTable  TABLE
-- **********************************************************************
wlanClientHTStatsTable OBJECT-TYPE
    SYNTAX  SEQUENCE OF WlanClientHTStatsEntry
    MAX-ACCESS  not-accessible
    STATUS  current
    DESCRIPTION
            "The wlanClientHTStatsTable contains additional statistical
             data about 802.11n HT frames related client mode.

             Each entry corresponds to an wlanClientTable entry.
             Entries cannot be added or deleted by the user.

             Creating entries: Entries are created by the system
             automatically when WLAN is switched to client mode.
	    "
    ::= { wlan 17 }

    wlanClientHTStatsEntry OBJECT-TYPE
	SYNTAX  WlanClientHTStatsEntry
	MAX-ACCESS  not-accessible
	STATUS  current
	DESCRIPTION
	""
	AUGMENTS   { wlanClientEntry }
    ::= { wlanClientHTStatsTable 1 }

    WlanClientHTStatsEntry ::=
	SEQUENCE {
	    wlanClientHTStatsIfIndex                    INTEGER,
	    wlanClientHTStatsRxFramesMCS0		Counter32,
	    wlanClientHTStatsRxFramesMCS1		Counter32,
	    wlanClientHTStatsRxFramesMCS2		Counter32,
	    wlanClientHTStatsRxFramesMCS3		Counter32,
	    wlanClientHTStatsRxFramesMCS4		Counter32,
	    wlanClientHTStatsRxFramesMCS5		Counter32,
	    wlanClientHTStatsRxFramesMCS6		Counter32,
	    wlanClientHTStatsRxFramesMCS7		Counter32,
	    wlanClientHTStatsRxFramesMCS8		Counter32,
	    wlanClientHTStatsRxFramesMCS9	Counter32,
	    wlanClientHTStatsRxFramesMCS10	Counter32,
	    wlanClientHTStatsRxFramesMCS11	Counter32,
            wlanClientHTStatsRxFramesMCS12	Counter32,
            wlanClientHTStatsRxFramesMCS13	Counter32,
            wlanClientHTStatsRxFramesMCS14	Counter32,
            wlanClientHTStatsRxFramesMCS15	Counter32,
	    wlanClientHTStatsRxFramesMCS16	Counter32,
	    wlanClientHTStatsRxFramesMCS17	Counter32,
	    wlanClientHTStatsRxFramesMCS18	Counter32,
	    wlanClientHTStatsRxFramesMCS19	Counter32,
	    wlanClientHTStatsRxFramesMCS20	Counter32,
	    wlanClientHTStatsRxFramesMCS21	Counter32,
	    wlanClientHTStatsRxFramesMCS22	Counter32,
	    wlanClientHTStatsRxFramesMCS23	Counter32,
	    wlanClientHTStatsTxFramesMCS0		Counter32,
	    wlanClientHTStatsTxFramesMCS1		Counter32,
	    wlanClientHTStatsTxFramesMCS2		Counter32,
	    wlanClientHTStatsTxFramesMCS3		Counter32,
	    wlanClientHTStatsTxFramesMCS4		Counter32,
	    wlanClientHTStatsTxFramesMCS5		Counter32,
	    wlanClientHTStatsTxFramesMCS6		Counter32,
	    wlanClientHTStatsTxFramesMCS7		Counter32,
	    wlanClientHTStatsTxFramesMCS8		Counter32,
	    wlanClientHTStatsTxFramesMCS9	Counter32,
	    wlanClientHTStatsTxFramesMCS10	Counter32,
	    wlanClientHTStatsTxFramesMCS11	Counter32,
	    wlanClientHTStatsTxFramesMCS12	Counter32,
	    wlanClientHTStatsTxFramesMCS13	Counter32,
	    wlanClientHTStatsTxFramesMCS14	Counter32,
	    wlanClientHTStatsTxFramesMCS15	Counter32,
	    wlanClientHTStatsTxFramesMCS16	Counter32,
	    wlanClientHTStatsTxFramesMCS17	Counter32,
	    wlanClientHTStatsTxFramesMCS18	Counter32,
	    wlanClientHTStatsTxFramesMCS19	Counter32,
	    wlanClientHTStatsTxFramesMCS20	Counter32,
	    wlanClientHTStatsTxFramesMCS21	Counter32,
	    wlanClientHTStatsTxFramesMCS22	Counter32,
	    wlanClientHTStatsTxFramesMCS23	Counter32,
            wlanClientHTStatsRxBandwidth          INTEGER,
            wlanClientHTStatsRxGuardInterval      INTEGER,
	    wlanClientHTStatsTxBandwidth          INTEGER,
            wlanClientHTStatsTxGuardInterval      INTEGER
	}

    wlanClientHTStatsRxFramesMCS0 OBJECT-TYPE
        SYNTAX Counter32
        MAX-ACCESS read-only
        STATUS current
        DESCRIPTION
            "This attribute shows the number of HT data
             frames that were received at MCS 0."
	::= { wlanClientHTStatsEntry 1 }

    wlanClientHTStatsRxFramesMCS1 OBJECT-TYPE
        SYNTAX Counter32
        MAX-ACCESS read-only
        STATUS current
        DESCRIPTION
            "This attribute shows the number of HT data
             frames that were received at MCS 1."
	::= { wlanClientHTStatsEntry 2 }

    wlanClientHTStatsRxFramesMCS2 OBJECT-TYPE
        SYNTAX Counter32
        MAX-ACCESS read-only
        STATUS current
        DESCRIPTION
            "This attribute shows the number of HT data
             frames that were received at MCS 2."
	::= { wlanClientHTStatsEntry 3 }

    wlanClientHTStatsRxFramesMCS3 OBJECT-TYPE
        SYNTAX Counter32
        MAX-ACCESS read-only
        STATUS current
        DESCRIPTION
            "This attribute shows the number of HT data
             frames that were received at MCS 3."
	::= { wlanClientHTStatsEntry 4 }

    wlanClientHTStatsRxFramesMCS4 OBJECT-TYPE
        SYNTAX Counter32
        MAX-ACCESS read-only
        STATUS current
        DESCRIPTION
            "This attribute shows the number of HT data
             frames that were received at MCS 4."
	::= { wlanClientHTStatsEntry 5 }

    wlanClientHTStatsRxFramesMCS5 OBJECT-TYPE
        SYNTAX Counter32
        MAX-ACCESS read-only
        STATUS current
        DESCRIPTION
            "This attribute shows the number of HT data
             frames that were received at MCS 5."
	::= { wlanClientHTStatsEntry 6 }

    wlanClientHTStatsRxFramesMCS6 OBJECT-TYPE
        SYNTAX Counter32
        MAX-ACCESS read-only
        STATUS current
        DESCRIPTION
            "This attribute shows the number of HT data
             frames that were received at MCS 6."
	::= { wlanClientHTStatsEntry 7 }

    wlanClientHTStatsRxFramesMCS7 OBJECT-TYPE
        SYNTAX Counter32
        MAX-ACCESS read-only
        STATUS current
        DESCRIPTION
            "This attribute shows the number of HT data
             frames that were received at MCS 7."
	::= { wlanClientHTStatsEntry 8 }

    wlanClientHTStatsRxFramesMCS8 OBJECT-TYPE
        SYNTAX Counter32
        MAX-ACCESS read-only
        STATUS current
        DESCRIPTION
            "This attribute shows the number of data
             frames that were received at MCS 8."
	::= { wlanClientHTStatsEntry 9 }

    wlanClientHTStatsRxFramesMCS9 OBJECT-TYPE
        SYNTAX Counter32
        MAX-ACCESS read-only
        STATUS current
        DESCRIPTION
            "This attribute shows the number of HT data
             frames that were received at MCS 9."
	::= { wlanClientHTStatsEntry 10 }

    wlanClientHTStatsRxFramesMCS10 OBJECT-TYPE
        SYNTAX Counter32
        MAX-ACCESS read-only
        STATUS current
        DESCRIPTION
            "This attribute shows the number of HT data
             frames that were received at MCS 10."
	::= { wlanClientHTStatsEntry 11 }

    wlanClientHTStatsRxFramesMCS11 OBJECT-TYPE
        SYNTAX Counter32
        MAX-ACCESS read-only
        STATUS current
        DESCRIPTION
            "This attribute shows the number of HT data
             frames that were received at MCS 11."
	::= { wlanClientHTStatsEntry 12 }

    wlanClientHTStatsRxFramesMCS12 OBJECT-TYPE
        SYNTAX Counter32
        MAX-ACCESS read-only
        STATUS current
        DESCRIPTION
            "This attribute shows the number of HT data
             frames that were received at MCS 12."
	::= { wlanClientHTStatsEntry 13 }

    wlanClientHTStatsRxFramesMCS13 OBJECT-TYPE
        SYNTAX Counter32
        MAX-ACCESS read-only
        STATUS current
        DESCRIPTION
            "This attribute shows the number of HT data
             frames that were received at MCS 13."
	::= { wlanClientHTStatsEntry 14 }

    wlanClientHTStatsRxFramesMCS14 OBJECT-TYPE
        SYNTAX Counter32
        MAX-ACCESS read-only
        STATUS current
        DESCRIPTION
            "This attribute shows the number of HT data
             frames that were received at MCS 14."
	::= { wlanClientHTStatsEntry 15 }

    wlanClientHTStatsRxFramesMCS15 OBJECT-TYPE
        SYNTAX Counter32
        MAX-ACCESS read-only
        STATUS current
        DESCRIPTION
            "This attribute shows the number of HT data
             frames that were received at MCS 15."
	::= { wlanClientHTStatsEntry 16 }

    wlanClientHTStatsTxFramesMCS0 OBJECT-TYPE
        SYNTAX Counter32
        MAX-ACCESS read-only
        STATUS current
        DESCRIPTION
            "This attribute shows the number of HT data
             frames that were transmitted at MCS 0."
	::= { wlanClientHTStatsEntry 17 }

    wlanClientHTStatsTxFramesMCS1 OBJECT-TYPE
        SYNTAX Counter32
        MAX-ACCESS read-only
        STATUS current
        DESCRIPTION
            "This attribute shows the number of HT data
             frames that were transmitted at MCS 1."
	::= { wlanClientHTStatsEntry 18 }

    wlanClientHTStatsTxFramesMCS2 OBJECT-TYPE
        SYNTAX Counter32
        MAX-ACCESS read-only
        STATUS current
        DESCRIPTION
            "This attribute shows the number of HT data
             frames that were transmitted at MCS 2."
	::= { wlanClientHTStatsEntry 19 }

    wlanClientHTStatsTxFramesMCS3 OBJECT-TYPE
        SYNTAX Counter32
        MAX-ACCESS read-only
        STATUS current
        DESCRIPTION
            "This attribute shows the number of HT data
             frames that were transmitted at MCS 3."
	::= { wlanClientHTStatsEntry 20 }

    wlanClientHTStatsTxFramesMCS4 OBJECT-TYPE
        SYNTAX Counter32
        MAX-ACCESS read-only
        STATUS current
        DESCRIPTION
            "This attribute shows the number of HT data
             frames that were transmitted at MCS 4."
	::= { wlanClientHTStatsEntry 21 }

    wlanClientHTStatsTxFramesMCS5 OBJECT-TYPE
        SYNTAX Counter32
        MAX-ACCESS read-only
        STATUS current
        DESCRIPTION
            "This attribute shows the number of HT data
             frames that were transmitted at MCS 5."
	::= { wlanClientHTStatsEntry 22 }

    wlanClientHTStatsTxFramesMCS6 OBJECT-TYPE
        SYNTAX Counter32
        MAX-ACCESS read-only
        STATUS current
        DESCRIPTION
            "This attribute shows the number of HT data
             frames that were transmitted at MCS 6."
	::= { wlanClientHTStatsEntry 23 }

    wlanClientHTStatsTxFramesMCS7 OBJECT-TYPE
        SYNTAX Counter32
        MAX-ACCESS read-only
        STATUS current
        DESCRIPTION
            "This attribute shows the number of HT data
             frames that were transmitted at MCS 7."
	::= { wlanClientHTStatsEntry 24 }

    wlanClientHTStatsTxFramesMCS8 OBJECT-TYPE
        SYNTAX Counter32
        MAX-ACCESS read-only
        STATUS current
        DESCRIPTION
            "This attribute shows the number of data
             frames that were transmitted at MCS 8."
	::= { wlanClientHTStatsEntry 25 }

    wlanClientHTStatsTxFramesMCS9 OBJECT-TYPE
        SYNTAX Counter32
        MAX-ACCESS read-only
        STATUS current
        DESCRIPTION
            "This attribute shows the number of HT data
             frames that were transmitted at MCS 9."
	::= { wlanClientHTStatsEntry 26 }

    wlanClientHTStatsTxFramesMCS10 OBJECT-TYPE
        SYNTAX Counter32
        MAX-ACCESS read-only
        STATUS current
        DESCRIPTION
            "This attribute shows the number of HT data
             frames that were transmitted at MCS 10."
	::= { wlanClientHTStatsEntry 27 }

    wlanClientHTStatsTxFramesMCS11 OBJECT-TYPE
        SYNTAX Counter32
        MAX-ACCESS read-only
        STATUS current
        DESCRIPTION
            "This attribute shows the number of HT data
             frames that were transmitted at MCS 11."
	::= { wlanClientHTStatsEntry 28 }

    wlanClientHTStatsTxFramesMCS12 OBJECT-TYPE
        SYNTAX Counter32
        MAX-ACCESS read-only
        STATUS current
        DESCRIPTION
            "This attribute shows the number of HT data
             frames that were transmitted at MCS 12."
	::= { wlanClientHTStatsEntry 29 }

    wlanClientHTStatsTxFramesMCS13 OBJECT-TYPE
        SYNTAX Counter32
        MAX-ACCESS read-only
        STATUS current
        DESCRIPTION
            "This attribute shows the number of HT data
             frames that were transmitted at MCS 13."
	::= { wlanClientHTStatsEntry 30 }

    wlanClientHTStatsTxFramesMCS14 OBJECT-TYPE
        SYNTAX Counter32
        MAX-ACCESS read-only
        STATUS current
        DESCRIPTION
            "This attribute shows the number of HT data
             frames that were transmitted at MCS 14."
	::= { wlanClientHTStatsEntry 31 }

    wlanClientHTStatsTxFramesMCS15 OBJECT-TYPE
        SYNTAX Counter32
        MAX-ACCESS read-only
        STATUS current
        DESCRIPTION
            "This attribute shows the number of HT data
             frames that were transmitted at MCS 15."
	::= { wlanClientHTStatsEntry 32 }

    wlanClientHTStatsRxBandwidth OBJECT-TYPE
        SYNTAX INTEGER { b20MHz(1), b40MHz(2) }
        MAX-ACCESS read-only
        STATUS current
        DESCRIPTION
            "This attribute shows the bandwidth the access point
             used with the last received frame: 20 MHz (1) or 40 MHz (2)."
        DEFVAL { b20MHz }
	::= { wlanClientHTStatsEntry 33 }

    wlanClientHTStatsRxGuardInterval OBJECT-TYPE
        SYNTAX INTEGER { long(1), short(2) }
        MAX-ACCESS read-only
        STATUS current
        DESCRIPTION
            "This attribute shows the length of the guard interval
             the access point used with last received frame:
             long (1)  or short (2)."
        DEFVAL { long }
	::= { wlanClientHTStatsEntry 34 }

    wlanClientHTStatsTxBandwidth OBJECT-TYPE
        SYNTAX INTEGER { b20MHz(1), b40MHz(2) }
        MAX-ACCESS read-only
        STATUS current
        DESCRIPTION
            "This attribute shows the bandwidth the client
             used for transmitting the last frame: 20 MHz (1) or 40 MHz (2)."
        DEFVAL { b20MHz }
	::= { wlanClientHTStatsEntry 35 }

    wlanClientHTStatsTxGuardInterval OBJECT-TYPE
        SYNTAX INTEGER { long(1), short(2) }
        MAX-ACCESS read-only
        STATUS current
        DESCRIPTION
            "This attribute shows the length of the guard interval
             the client used for transmitting the last frame:
             long (1)  or short (2)."
        DEFVAL { long }
	::= { wlanClientHTStatsEntry 36 }

   wlanClientHTStatsRxFramesMCS16 OBJECT-TYPE
        SYNTAX Counter32
        MAX-ACCESS read-only
        STATUS current
        DESCRIPTION
            "This attribute shows the number of HT data
             frames that were received at MCS 16."
	::= { wlanClientHTStatsEntry 37 }

    wlanClientHTStatsRxFramesMCS17 OBJECT-TYPE
        SYNTAX Counter32
        MAX-ACCESS read-only
        STATUS current
        DESCRIPTION
            "This attribute shows the number of HT data
             frames that were received at MCS 17."
	::= { wlanClientHTStatsEntry 38 }

    wlanClientHTStatsRxFramesMCS18 OBJECT-TYPE
        SYNTAX Counter32
        MAX-ACCESS read-only
        STATUS current
        DESCRIPTION
            "This attribute shows the number of HT data
             frames that were received at MCS 18."
	::= { wlanClientHTStatsEntry 39 }

    wlanClientHTStatsRxFramesMCS19 OBJECT-TYPE
        SYNTAX Counter32
        MAX-ACCESS read-only
        STATUS current
        DESCRIPTION
            "This attribute shows the number of HT data
             frames that were received at MCS 19."
	::= { wlanClientHTStatsEntry 40 }

    wlanClientHTStatsRxFramesMCS20 OBJECT-TYPE
        SYNTAX Counter32
        MAX-ACCESS read-only
        STATUS current
        DESCRIPTION
            "This attribute shows the number of HT data
             frames that were received at MCS 20."
	::= { wlanClientHTStatsEntry 41 }

    wlanClientHTStatsRxFramesMCS21 OBJECT-TYPE
        SYNTAX Counter32
        MAX-ACCESS read-only
        STATUS current
        DESCRIPTION
            "This attribute shows the number of HT data
             frames that were received at MCS 21."
	::= { wlanClientHTStatsEntry 42 }

    wlanClientHTStatsRxFramesMCS22 OBJECT-TYPE
        SYNTAX Counter32
        MAX-ACCESS read-only
        STATUS current
        DESCRIPTION
            "This attribute shows the number of HT data
             frames that were received at MCS 22."
	::= { wlanClientHTStatsEntry 43 }

    wlanClientHTStatsRxFramesMCS23 OBJECT-TYPE
        SYNTAX Counter32
        MAX-ACCESS read-only
        STATUS current
        DESCRIPTION
            "This attribute shows the number of HT data
             frames that were received at MCS 23."
	::= { wlanClientHTStatsEntry 44 }

    wlanClientHTStatsTxFramesMCS16 OBJECT-TYPE
        SYNTAX Counter32
        MAX-ACCESS read-only
        STATUS current
        DESCRIPTION
            "This attribute shows the number of HT data
             frames that were transmitted at MCS 16."
	::= { wlanClientHTStatsEntry 45 }

	wlanClientHTStatsTxFramesMCS17 OBJECT-TYPE
        SYNTAX Counter32
        MAX-ACCESS read-only
        STATUS current
        DESCRIPTION
            "This attribute shows the number of HT data
             frames that were transmitted at MCS 17."
	::= { wlanClientHTStatsEntry 46 }

    wlanClientHTStatsTxFramesMCS18 OBJECT-TYPE
        SYNTAX Counter32
        MAX-ACCESS read-only
        STATUS current
        DESCRIPTION
            "This attribute shows the number of HT data
             frames that were transmitted at MCS 18."
	::= { wlanClientHTStatsEntry 47 }

    wlanClientHTStatsTxFramesMCS19 OBJECT-TYPE
        SYNTAX Counter32
        MAX-ACCESS read-only
        STATUS current
        DESCRIPTION
            "This attribute shows the number of HT data
             frames that were transmitted at MCS 19."
	::= { wlanClientHTStatsEntry 48 }

    wlanClientHTStatsTxFramesMCS20 OBJECT-TYPE
        SYNTAX Counter32
        MAX-ACCESS read-only
        STATUS current
        DESCRIPTION
            "This attribute shows the number of HT data
             frames that were transmitted at MCS 20."
	::= { wlanClientHTStatsEntry 49 }

    wlanClientHTStatsTxFramesMCS21 OBJECT-TYPE
        SYNTAX Counter32
        MAX-ACCESS read-only
        STATUS current
        DESCRIPTION
            "This attribute shows the number of HT data
             frames that were transmitted at MCS 21."
	::= { wlanClientHTStatsEntry 50 }

    wlanClientHTStatsTxFramesMCS22 OBJECT-TYPE
        SYNTAX Counter32
        MAX-ACCESS read-only
        STATUS current
        DESCRIPTION
            "This attribute shows the number of HT data
             frames that were transmitted at MCS 22."
	::= { wlanClientHTStatsEntry 51 }

    wlanClientHTStatsTxFramesMCS23 OBJECT-TYPE
        SYNTAX Counter32
        MAX-ACCESS read-only
        STATUS current
        DESCRIPTION
            "This attribute shows the number of HT data
             frames that were transmitted at MCS 23."
	::= { wlanClientHTStatsEntry 52 }

    wlanClientHTStatsIfIndex OBJECT-TYPE
	SYNTAX  INTEGER
	MAX-ACCESS  read-only
	STATUS  current
	DESCRIPTION
	    "IfIndex of the client interface."
	DEFVAL { 0 }
    	::= { wlanClientHTStatsEntry 53 }

-- **********************************************************************
-- *    End of wlanClientHTStatsTable  TABLE
-- **********************************************************************


-- **********************************************************************
-- *    wlanWDSHTStatsTable  TABLE
-- **********************************************************************
wlanWDSHTStatsTable OBJECT-TYPE
    SYNTAX  SEQUENCE OF WlanWDSHTStatsEntry
    MAX-ACCESS  not-accessible
    STATUS  current
    DESCRIPTION
            "The wlanWDSHTStatsTable contains additional statistical
             data about 802.11n HT frames for WDS links.

             Each entry corresponds to an wlanWDSTable entry.
             Entries cannot be added or deleted by the user.
        "
    ::= { wlan 18 }

    wlanWDSHTStatsEntry OBJECT-TYPE
    SYNTAX  WlanWDSHTStatsEntry
    MAX-ACCESS  not-accessible
    STATUS  current
    DESCRIPTION
    ""
    AUGMENTS   { wlanWDSEntry }
    ::= { wlanWDSHTStatsTable 1 }

    WlanWDSHTStatsEntry ::=
    SEQUENCE {
        wlanWDSHTStatsRxFramesMCS0      Counter32,
        wlanWDSHTStatsRxFramesMCS1      Counter32,
        wlanWDSHTStatsRxFramesMCS2      Counter32,
        wlanWDSHTStatsRxFramesMCS3      Counter32,
        wlanWDSHTStatsRxFramesMCS4      Counter32,
        wlanWDSHTStatsRxFramesMCS5      Counter32,
        wlanWDSHTStatsRxFramesMCS6      Counter32,
        wlanWDSHTStatsRxFramesMCS7      Counter32,
        wlanWDSHTStatsRxFramesMCS8      Counter32,
        wlanWDSHTStatsRxFramesMCS9  Counter32,
        wlanWDSHTStatsRxFramesMCS10 Counter32,
        wlanWDSHTStatsRxFramesMCS11 Counter32,
        wlanWDSHTStatsRxFramesMCS12 Counter32,
        wlanWDSHTStatsRxFramesMCS13 Counter32,
        wlanWDSHTStatsRxFramesMCS14 Counter32,
        wlanWDSHTStatsRxFramesMCS15 Counter32,
	wlanWDSHTStatsRxFramesMCS16 Counter32,
	wlanWDSHTStatsRxFramesMCS17 Counter32,
	wlanWDSHTStatsRxFramesMCS18 Counter32,
	wlanWDSHTStatsRxFramesMCS19 Counter32,
	wlanWDSHTStatsRxFramesMCS20 Counter32,
	wlanWDSHTStatsRxFramesMCS21 Counter32,
	wlanWDSHTStatsRxFramesMCS22 Counter32,
	wlanWDSHTStatsRxFramesMCS23 Counter32,
        wlanWDSHTStatsTxFramesMCS0      Counter32,
        wlanWDSHTStatsTxFramesMCS1      Counter32,
        wlanWDSHTStatsTxFramesMCS2      Counter32,
        wlanWDSHTStatsTxFramesMCS3      Counter32,
        wlanWDSHTStatsTxFramesMCS4      Counter32,
        wlanWDSHTStatsTxFramesMCS5      Counter32,
        wlanWDSHTStatsTxFramesMCS6      Counter32,
        wlanWDSHTStatsTxFramesMCS7      Counter32,
        wlanWDSHTStatsTxFramesMCS8      Counter32,
        wlanWDSHTStatsTxFramesMCS9  Counter32,
        wlanWDSHTStatsTxFramesMCS10 Counter32,
        wlanWDSHTStatsTxFramesMCS11 Counter32,
        wlanWDSHTStatsTxFramesMCS12 Counter32,
        wlanWDSHTStatsTxFramesMCS13 Counter32,
        wlanWDSHTStatsTxFramesMCS14 Counter32,
        wlanWDSHTStatsTxFramesMCS15 Counter32,
	wlanWDSHTStatsTxFramesMCS16 Counter32,
	wlanWDSHTStatsTxFramesMCS17 Counter32,
	wlanWDSHTStatsTxFramesMCS18 Counter32,
	wlanWDSHTStatsTxFramesMCS19 Counter32,
	wlanWDSHTStatsTxFramesMCS20 Counter32,
	wlanWDSHTStatsTxFramesMCS21 Counter32,
	wlanWDSHTStatsTxFramesMCS22 Counter32,
	wlanWDSHTStatsTxFramesMCS23 Counter32,
        wlanWDSHTStatsRxBandwidth     INTEGER,
        wlanWDSHTStatsRxGuardInterval INTEGER,
        wlanWDSHTStatsTxBandwidth     INTEGER,
        wlanWDSHTStatsTxGuardInterval INTEGER

    }

    wlanWDSHTStatsRxFramesMCS0 OBJECT-TYPE
        SYNTAX Counter32
        MAX-ACCESS read-only
        STATUS current
        DESCRIPTION
            "This attribute shows the number of HT data
             frames that were received at MCS 0."
    ::= { wlanWDSHTStatsEntry 1 }

    wlanWDSHTStatsRxFramesMCS1 OBJECT-TYPE
        SYNTAX Counter32
        MAX-ACCESS read-only
        STATUS current
        DESCRIPTION
            "This attribute shows the number of HT data
             frames that were received at MCS 1."
    ::= { wlanWDSHTStatsEntry 2 }

    wlanWDSHTStatsRxFramesMCS2 OBJECT-TYPE
        SYNTAX Counter32
        MAX-ACCESS read-only
        STATUS current
        DESCRIPTION
            "This attribute shows the number of HT data
             frames that were received at MCS 2."
    ::= { wlanWDSHTStatsEntry 3 }

    wlanWDSHTStatsRxFramesMCS3 OBJECT-TYPE
        SYNTAX Counter32
        MAX-ACCESS read-only
        STATUS current
        DESCRIPTION
            "This attribute shows the number of HT data
             frames that were received at MCS 3."
    ::= { wlanWDSHTStatsEntry 4 }

    wlanWDSHTStatsRxFramesMCS4 OBJECT-TYPE
        SYNTAX Counter32
        MAX-ACCESS read-only
        STATUS current
        DESCRIPTION
            "This attribute shows the number of HT data
             frames that were received at MCS 4."
    ::= { wlanWDSHTStatsEntry 5 }

    wlanWDSHTStatsRxFramesMCS5 OBJECT-TYPE
        SYNTAX Counter32
        MAX-ACCESS read-only
        STATUS current
        DESCRIPTION
            "This attribute shows the number of HT data
             frames that were received at MCS 5."
    ::= { wlanWDSHTStatsEntry 6 }

    wlanWDSHTStatsRxFramesMCS6 OBJECT-TYPE
        SYNTAX Counter32
        MAX-ACCESS read-only
        STATUS current
        DESCRIPTION
            "This attribute shows the number of HT data
             frames that were received at MCS 6."
    ::= { wlanWDSHTStatsEntry 7 }

    wlanWDSHTStatsRxFramesMCS7 OBJECT-TYPE
        SYNTAX Counter32
        MAX-ACCESS read-only
        STATUS current
        DESCRIPTION
            "This attribute shows the number of HT data
             frames that were received at MCS 7."
    ::= { wlanWDSHTStatsEntry 8 }

    wlanWDSHTStatsRxFramesMCS8 OBJECT-TYPE
        SYNTAX Counter32
        MAX-ACCESS read-only
        STATUS current
        DESCRIPTION
            "This attribute shows the number of data
             frames that were received at MCS 8."
    ::= { wlanWDSHTStatsEntry 9 }

    wlanWDSHTStatsRxFramesMCS9 OBJECT-TYPE
        SYNTAX Counter32
        MAX-ACCESS read-only
        STATUS current
        DESCRIPTION
            "This attribute shows the number of HT data
             frames that were received at MCS 9."
    ::= { wlanWDSHTStatsEntry 10 }

    wlanWDSHTStatsRxFramesMCS10 OBJECT-TYPE
        SYNTAX Counter32
        MAX-ACCESS read-only
        STATUS current
        DESCRIPTION
            "This attribute shows the number of HT data
             frames that were received at MCS 10."
    ::= { wlanWDSHTStatsEntry 11 }

    wlanWDSHTStatsRxFramesMCS11 OBJECT-TYPE
        SYNTAX Counter32
        MAX-ACCESS read-only
        STATUS current
        DESCRIPTION
            "This attribute shows the number of HT data
             frames that were received at MCS 11."
    ::= { wlanWDSHTStatsEntry 12 }

    wlanWDSHTStatsRxFramesMCS12 OBJECT-TYPE
        SYNTAX Counter32
        MAX-ACCESS read-only
        STATUS current
        DESCRIPTION
            "This attribute shows the number of HT data
             frames that were received at MCS 12."
    ::= { wlanWDSHTStatsEntry 13 }

    wlanWDSHTStatsRxFramesMCS13 OBJECT-TYPE
        SYNTAX Counter32
        MAX-ACCESS read-only
        STATUS current
        DESCRIPTION
            "This attribute shows the number of HT data
             frames that were received at MCS 13."
    ::= { wlanWDSHTStatsEntry 14 }

    wlanWDSHTStatsRxFramesMCS14 OBJECT-TYPE
        SYNTAX Counter32
        MAX-ACCESS read-only
        STATUS current
        DESCRIPTION
            "This attribute shows the number of HT data
             frames that were received at MCS 14."
    ::= { wlanWDSHTStatsEntry 15 }

    wlanWDSHTStatsRxFramesMCS15 OBJECT-TYPE
        SYNTAX Counter32
        MAX-ACCESS read-only
        STATUS current
        DESCRIPTION
            "This attribute shows the number of HT data
             frames that were received at MCS 15."
    ::= { wlanWDSHTStatsEntry 16 }

    wlanWDSHTStatsTxFramesMCS0 OBJECT-TYPE
        SYNTAX Counter32
        MAX-ACCESS read-only
        STATUS current
        DESCRIPTION
            "This attribute shows the number of HT data
             frames that were transmitted at MCS 0."
    ::= { wlanWDSHTStatsEntry 17 }

    wlanWDSHTStatsTxFramesMCS1 OBJECT-TYPE
        SYNTAX Counter32
        MAX-ACCESS read-only
        STATUS current
        DESCRIPTION
            "This attribute shows the number of HT data
             frames that were transmitted at MCS 1."
    ::= { wlanWDSHTStatsEntry 18 }

    wlanWDSHTStatsTxFramesMCS2 OBJECT-TYPE
        SYNTAX Counter32
        MAX-ACCESS read-only
        STATUS current
        DESCRIPTION
            "This attribute shows the number of HT data
             frames that were transmitted at MCS 2."
    ::= { wlanWDSHTStatsEntry 19 }

    wlanWDSHTStatsTxFramesMCS3 OBJECT-TYPE
        SYNTAX Counter32
        MAX-ACCESS read-only
        STATUS current
        DESCRIPTION
            "This attribute shows the number of HT data
             frames that were transmitted at MCS 3."
    ::= { wlanWDSHTStatsEntry 20 }

    wlanWDSHTStatsTxFramesMCS4 OBJECT-TYPE
        SYNTAX Counter32
        MAX-ACCESS read-only
        STATUS current
        DESCRIPTION
            "This attribute shows the number of HT data
             frames that were transmitted at MCS 4."
    ::= { wlanWDSHTStatsEntry 21 }

    wlanWDSHTStatsTxFramesMCS5 OBJECT-TYPE
        SYNTAX Counter32
        MAX-ACCESS read-only
        STATUS current
        DESCRIPTION
            "This attribute shows the number of HT data
             frames that were transmitted at MCS 5."
    ::= { wlanWDSHTStatsEntry 22 }

    wlanWDSHTStatsTxFramesMCS6 OBJECT-TYPE
        SYNTAX Counter32
        MAX-ACCESS read-only
        STATUS current
        DESCRIPTION
            "This attribute shows the number of HT data
             frames that were transmitted at MCS 6."
    ::= { wlanWDSHTStatsEntry 23 }

    wlanWDSHTStatsTxFramesMCS7 OBJECT-TYPE
        SYNTAX Counter32
        MAX-ACCESS read-only
        STATUS current
        DESCRIPTION
            "This attribute shows the number of HT data
             frames that were transmitted at MCS 7."
    ::= { wlanWDSHTStatsEntry 24 }

    wlanWDSHTStatsTxFramesMCS8 OBJECT-TYPE
        SYNTAX Counter32
        MAX-ACCESS read-only
        STATUS current
        DESCRIPTION
            "This attribute shows the number of data
             frames that were transmitted at MCS 8."
    ::= { wlanWDSHTStatsEntry 25 }

    wlanWDSHTStatsTxFramesMCS9 OBJECT-TYPE
        SYNTAX Counter32
        MAX-ACCESS read-only
        STATUS current
        DESCRIPTION
            "This attribute shows the number of HT data
             frames that were transmitted at MCS 9."
    ::= { wlanWDSHTStatsEntry 26 }

    wlanWDSHTStatsTxFramesMCS10 OBJECT-TYPE
        SYNTAX Counter32
        MAX-ACCESS read-only
        STATUS current
        DESCRIPTION
            "This attribute shows the number of HT data
             frames that were transmitted at MCS 10."
    ::= { wlanWDSHTStatsEntry 27 }

    wlanWDSHTStatsTxFramesMCS11 OBJECT-TYPE
        SYNTAX Counter32
        MAX-ACCESS read-only
        STATUS current
        DESCRIPTION
            "This attribute shows the number of HT data
             frames that were transmitted at MCS 11."
    ::= { wlanWDSHTStatsEntry 28 }

    wlanWDSHTStatsTxFramesMCS12 OBJECT-TYPE
        SYNTAX Counter32
        MAX-ACCESS read-only
        STATUS current
        DESCRIPTION
            "This attribute shows the number of HT data
             frames that were transmitted at MCS 12."
    ::= { wlanWDSHTStatsEntry 29 }

    wlanWDSHTStatsTxFramesMCS13 OBJECT-TYPE
        SYNTAX Counter32
        MAX-ACCESS read-only
        STATUS current
        DESCRIPTION
            "This attribute shows the number of HT data
             frames that were transmitted at MCS 13."
    ::= { wlanWDSHTStatsEntry 30 }

    wlanWDSHTStatsTxFramesMCS14 OBJECT-TYPE
        SYNTAX Counter32
        MAX-ACCESS read-only
        STATUS current
        DESCRIPTION
            "This attribute shows the number of HT data
             frames that were transmitted at MCS 14."
    ::= { wlanWDSHTStatsEntry 31 }

    wlanWDSHTStatsTxFramesMCS15 OBJECT-TYPE
        SYNTAX Counter32
        MAX-ACCESS read-only
        STATUS current
        DESCRIPTION
            "This attribute shows the number of HT data
             frames that were transmitted at MCS 15."
    ::= { wlanWDSHTStatsEntry 32 }

    wlanWDSHTStatsRxBandwidth OBJECT-TYPE
        SYNTAX INTEGER { b20MHz(1), b40MHz(2) }
        MAX-ACCESS read-only
        STATUS current
        DESCRIPTION
            "This attribute shows the bandwidth the remote side
             used with the last received frame: 20 MHz (1) or 40 MHz (2)."
        DEFVAL { b20MHz }
	::= { wlanWDSHTStatsEntry 33 }

    wlanWDSHTStatsRxGuardInterval OBJECT-TYPE
        SYNTAX INTEGER { long(1), short(2) }
        MAX-ACCESS read-only
        STATUS current
        DESCRIPTION
            "This attribute shows the length of the guard interval
             the remote side used with the last received frame:
             long (1)  or short (2)."
        DEFVAL { long }
	::= { wlanWDSHTStatsEntry 34 }

    wlanWDSHTStatsTxBandwidth OBJECT-TYPE
        SYNTAX INTEGER { b20MHz(1), b40MHz(2) }
        MAX-ACCESS read-only
        STATUS current
        DESCRIPTION
            "This attribute shows the bandwidth the local side
             used for transmitting the last frame: 20 MHz (1) or 40 MHz (2)."
        DEFVAL { b20MHz }
	::= { wlanWDSHTStatsEntry 35 }

    wlanWDSHTStatsTxGuardInterval OBJECT-TYPE
        SYNTAX INTEGER { long(1), short(2) }
        MAX-ACCESS read-only
        STATUS current
        DESCRIPTION
            "This attribute shows the length of the guard interval
             the local side used for transmitting the last frame:
             long (1)  or short (2)."
        DEFVAL { long }
	::= { wlanWDSHTStatsEntry 36 }

    wlanWDSHTStatsRxFramesMCS16 OBJECT-TYPE
        SYNTAX Counter32
        MAX-ACCESS read-only
        STATUS current
        DESCRIPTION
            "This attribute shows the number of HT data
             frames that were received at MCS 16."
    ::= { wlanWDSHTStatsEntry 37 }

    wlanWDSHTStatsRxFramesMCS17 OBJECT-TYPE
        SYNTAX Counter32
        MAX-ACCESS read-only
        STATUS current
        DESCRIPTION
            "This attribute shows the number of HT data
             frames that were received at MCS 17."
    ::= { wlanWDSHTStatsEntry 38 }

    wlanWDSHTStatsRxFramesMCS18 OBJECT-TYPE
        SYNTAX Counter32
        MAX-ACCESS read-only
        STATUS current
        DESCRIPTION
            "This attribute shows the number of HT data
             frames that were received at MCS 18."
    ::= { wlanWDSHTStatsEntry 39 }

    wlanWDSHTStatsRxFramesMCS19 OBJECT-TYPE
        SYNTAX Counter32
        MAX-ACCESS read-only
        STATUS current
        DESCRIPTION
            "This attribute shows the number of HT data
             frames that were received at MCS 19."
    ::= { wlanWDSHTStatsEntry 40 }

    wlanWDSHTStatsRxFramesMCS20 OBJECT-TYPE
        SYNTAX Counter32
        MAX-ACCESS read-only
        STATUS current
        DESCRIPTION
            "This attribute shows the number of HT data
             frames that were received at MCS 20."
    ::= { wlanWDSHTStatsEntry 41 }

    wlanWDSHTStatsRxFramesMCS21 OBJECT-TYPE
        SYNTAX Counter32
        MAX-ACCESS read-only
        STATUS current
        DESCRIPTION
            "This attribute shows the number of HT data
             frames that were received at MCS 21."
    ::= { wlanWDSHTStatsEntry 42 }

    wlanWDSHTStatsRxFramesMCS22 OBJECT-TYPE
        SYNTAX Counter32
        MAX-ACCESS read-only
        STATUS current
        DESCRIPTION
            "This attribute shows the number of HT data
             frames that were received at MCS 22."
    ::= { wlanWDSHTStatsEntry 43 }

    wlanWDSHTStatsRxFramesMCS23 OBJECT-TYPE
        SYNTAX Counter32
        MAX-ACCESS read-only
        STATUS current
        DESCRIPTION
            "This attribute shows the number of HT data
             frames that were received at MCS 23."
    ::= { wlanWDSHTStatsEntry 44 }

    wlanWDSHTStatsTxFramesMCS16 OBJECT-TYPE
        SYNTAX Counter32
        MAX-ACCESS read-only
        STATUS current
        DESCRIPTION
            "This attribute shows the number of HT data
             frames that were transmitted at MCS 16."
    ::= { wlanWDSHTStatsEntry 45 }

    wlanWDSHTStatsTxFramesMCS17 OBJECT-TYPE
        SYNTAX Counter32
        MAX-ACCESS read-only
        STATUS current
        DESCRIPTION
            "This attribute shows the number of HT data
             frames that were transmitted at MCS 17."
    ::= { wlanWDSHTStatsEntry 46 }

    wlanWDSHTStatsTxFramesMCS18 OBJECT-TYPE
        SYNTAX Counter32
        MAX-ACCESS read-only
        STATUS current
        DESCRIPTION
            "This attribute shows the number of HT data
             frames that were transmitted at MCS 18."
    ::= { wlanWDSHTStatsEntry 47 }

    wlanWDSHTStatsTxFramesMCS19 OBJECT-TYPE
        SYNTAX Counter32
        MAX-ACCESS read-only
        STATUS current
        DESCRIPTION
            "This attribute shows the number of HT data
             frames that were transmitted at MCS 19."
    ::= { wlanWDSHTStatsEntry 48 }

    wlanWDSHTStatsTxFramesMCS20 OBJECT-TYPE
        SYNTAX Counter32
        MAX-ACCESS read-only
        STATUS current
        DESCRIPTION
            "This attribute shows the number of HT data
             frames that were transmitted at MCS 20."
    ::= { wlanWDSHTStatsEntry 49 }

    wlanWDSHTStatsTxFramesMCS21 OBJECT-TYPE
        SYNTAX Counter32
        MAX-ACCESS read-only
        STATUS current
        DESCRIPTION
            "This attribute shows the number of HT data
             frames that were transmitted at MCS 21."
    ::= { wlanWDSHTStatsEntry 50 }

    wlanWDSHTStatsTxFramesMCS22 OBJECT-TYPE
        SYNTAX Counter32
        MAX-ACCESS read-only
        STATUS current
        DESCRIPTION
            "This attribute shows the number of HT data
             frames that were transmitted at MCS 22."
    ::= { wlanWDSHTStatsEntry 51 }

    wlanWDSHTStatsTxFramesMCS23 OBJECT-TYPE
        SYNTAX Counter32
        MAX-ACCESS read-only
        STATUS current
        DESCRIPTION
            "This attribute shows the number of HT data
             frames that were transmitted at MCS 23."
    ::= { wlanWDSHTStatsEntry 52 }

-- **********************************************************************
-- *    End of wlanWDSHTStatsTable  TABLE
-- **********************************************************************

-- **********************************************************************
-- *    wlanLinkTestHTStatsTable  TABLE
-- **********************************************************************
wlanLinkTestHTStatsTable OBJECT-TYPE
    SYNTAX  SEQUENCE OF WlanLinkTestHTStatsEntry
    MAX-ACCESS  not-accessible
    STATUS  current
    DESCRIPTION
            "The wlanLinkTestHTStatsTable contains additional statistical
             data about 802.11n HT frames for WDS links.

             Each entry corresponds to an wlanWDSTable entry.
             Entries cannot be added or deleted by the user.
        "
    ::= { wlan 19 }

    wlanLinkTestHTStatsEntry OBJECT-TYPE
    SYNTAX  WlanLinkTestHTStatsEntry
    MAX-ACCESS  not-accessible
    STATUS  current
    DESCRIPTION
    ""
    INDEX { wlanLinkTestHTStatsIfIndex }
    ::= { wlanLinkTestHTStatsTable 1 }

    WlanLinkTestHTStatsEntry ::=
    SEQUENCE {
        wlanLinkTestHTStatsIfIndex           INTEGER,
        wlanLinkTestHTStatsRxFramesMCS0      Counter32,
        wlanLinkTestHTStatsRxFramesMCS1      Counter32,
        wlanLinkTestHTStatsRxFramesMCS2      Counter32,
        wlanLinkTestHTStatsRxFramesMCS3      Counter32,
        wlanLinkTestHTStatsRxFramesMCS4      Counter32,
        wlanLinkTestHTStatsRxFramesMCS5      Counter32,
        wlanLinkTestHTStatsRxFramesMCS6      Counter32,
        wlanLinkTestHTStatsRxFramesMCS7      Counter32,
        wlanLinkTestHTStatsRxFramesMCS8      Counter32,
        wlanLinkTestHTStatsRxFramesMCS9  Counter32,
        wlanLinkTestHTStatsRxFramesMCS10 Counter32,
        wlanLinkTestHTStatsRxFramesMCS11 Counter32,
        wlanLinkTestHTStatsRxFramesMCS12 Counter32,
        wlanLinkTestHTStatsRxFramesMCS13 Counter32,
        wlanLinkTestHTStatsRxFramesMCS14 Counter32,
        wlanLinkTestHTStatsRxFramesMCS15 Counter32,
	wlanLinkTestHTStatsRxFramesMCS16 Counter32,
        wlanLinkTestHTStatsRxFramesMCS17 Counter32,
        wlanLinkTestHTStatsRxFramesMCS18 Counter32,
        wlanLinkTestHTStatsRxFramesMCS19 Counter32,
        wlanLinkTestHTStatsRxFramesMCS20 Counter32,
        wlanLinkTestHTStatsRxFramesMCS21 Counter32,
        wlanLinkTestHTStatsRxFramesMCS22 Counter32,
	wlanLinkTestHTStatsRxFramesMCS23 Counter32,

        wlanLinkTestHTStatsRxFramesRemoteMCS0      Counter32,
        wlanLinkTestHTStatsRxFramesRemoteMCS1      Counter32,
        wlanLinkTestHTStatsRxFramesRemoteMCS2      Counter32,
        wlanLinkTestHTStatsRxFramesRemoteMCS3      Counter32,
        wlanLinkTestHTStatsRxFramesRemoteMCS4      Counter32,
        wlanLinkTestHTStatsRxFramesRemoteMCS5      Counter32,
        wlanLinkTestHTStatsRxFramesRemoteMCS6      Counter32,
        wlanLinkTestHTStatsRxFramesRemoteMCS7      Counter32,
        wlanLinkTestHTStatsRxFramesRemoteMCS8      Counter32,
        wlanLinkTestHTStatsRxFramesRemoteMCS9  Counter32,
        wlanLinkTestHTStatsRxFramesRemoteMCS10 Counter32,
        wlanLinkTestHTStatsRxFramesRemoteMCS11 Counter32,
        wlanLinkTestHTStatsRxFramesRemoteMCS12 Counter32,
        wlanLinkTestHTStatsRxFramesRemoteMCS13 Counter32,
        wlanLinkTestHTStatsRxFramesRemoteMCS14 Counter32,
        wlanLinkTestHTStatsRxFramesRemoteMCS15 Counter32,
	wlanLinkTestHTStatsRxFramesRemoteMCS16 Counter32,
        wlanLinkTestHTStatsRxFramesRemoteMCS17 Counter32,
        wlanLinkTestHTStatsRxFramesRemoteMCS18 Counter32,
        wlanLinkTestHTStatsRxFramesRemoteMCS19 Counter32,
        wlanLinkTestHTStatsRxFramesRemoteMCS20 Counter32,
        wlanLinkTestHTStatsRxFramesRemoteMCS21 Counter32,
        wlanLinkTestHTStatsRxFramesRemoteMCS22 Counter32,
        wlanLinkTestHTStatsRxFramesRemoteMCS23 Counter32,
        wlanLinkTestHTStatsBandwidthLocal     INTEGER,
        wlanLinkTestHTStatsGuardIntervalLocal INTEGER,
        wlanLinkTestHTStatsRSSI1Local                WlanRSSI,
        wlanLinkTestHTStatsRSSI2Local                WlanRSSI,
        wlanLinkTestHTStatsRSSI3Local                WlanRSSI,
        wlanLinkTestHTStatsBandwidthRemote     INTEGER,
        wlanLinkTestHTStatsGuardIntervalRemote INTEGER,
        wlanLinkTestHTStatsRSSI1Remote          WlanRSSI,
        wlanLinkTestHTStatsRSSI2Remote          WlanRSSI,
        wlanLinkTestHTStatsRSSI3Remote          WlanRSSI
    }

    wlanLinkTestHTStatsIfIndex  OBJECT-TYPE
        SYNTAX INTEGER
        MAX-ACCESS read-only
        STATUS current
        DESCRIPTION
            "The interface index of the corresponding
             bridge interface."
    ::= { wlanLinkTestHTStatsEntry 1 }

    wlanLinkTestHTStatsRxFramesMCS0 OBJECT-TYPE
        SYNTAX Counter32
        MAX-ACCESS read-only
        STATUS current
        DESCRIPTION
            "This attribute shows the number of HT data
             frames that were received at MCS 0."
    ::= { wlanLinkTestHTStatsEntry 2 }

    wlanLinkTestHTStatsRxFramesMCS1 OBJECT-TYPE
        SYNTAX Counter32
        MAX-ACCESS read-only
        STATUS current
        DESCRIPTION
            "This attribute shows the number of HT data
             frames that were received at MCS 1."
    ::= { wlanLinkTestHTStatsEntry 3 }

    wlanLinkTestHTStatsRxFramesMCS2 OBJECT-TYPE
        SYNTAX Counter32
        MAX-ACCESS read-only
        STATUS current
        DESCRIPTION
            "This attribute shows the number of HT data
             frames that were received at MCS 2."
    ::= { wlanLinkTestHTStatsEntry 4 }

    wlanLinkTestHTStatsRxFramesMCS3 OBJECT-TYPE
        SYNTAX Counter32
        MAX-ACCESS read-only
        STATUS current
        DESCRIPTION
            "This attribute shows the number of HT data
             frames that were received at MCS 3."
    ::= { wlanLinkTestHTStatsEntry 5 }

    wlanLinkTestHTStatsRxFramesMCS4 OBJECT-TYPE
        SYNTAX Counter32
        MAX-ACCESS read-only
        STATUS current
        DESCRIPTION
            "This attribute shows the number of HT data
             frames that were received at MCS 4."
    ::= { wlanLinkTestHTStatsEntry 6 }

    wlanLinkTestHTStatsRxFramesMCS5 OBJECT-TYPE
        SYNTAX Counter32
        MAX-ACCESS read-only
        STATUS current
        DESCRIPTION
            "This attribute shows the number of HT data
             frames that were received at MCS 5."
    ::= { wlanLinkTestHTStatsEntry 7 }

    wlanLinkTestHTStatsRxFramesMCS6 OBJECT-TYPE
        SYNTAX Counter32
        MAX-ACCESS read-only
        STATUS current
        DESCRIPTION
            "This attribute shows the number of HT data
             frames that were received at MCS 6."
    ::= { wlanLinkTestHTStatsEntry 8 }

    wlanLinkTestHTStatsRxFramesMCS7 OBJECT-TYPE
        SYNTAX Counter32
        MAX-ACCESS read-only
        STATUS current
        DESCRIPTION
            "This attribute shows the number of HT data
             frames that were received at MCS 7."
    ::= { wlanLinkTestHTStatsEntry 9 }

    wlanLinkTestHTStatsRxFramesMCS8 OBJECT-TYPE
        SYNTAX Counter32
        MAX-ACCESS read-only
        STATUS current
        DESCRIPTION
            "This attribute shows the number of data
             frames that were received at MCS 8."
    ::= { wlanLinkTestHTStatsEntry 10 }

    wlanLinkTestHTStatsRxFramesMCS9 OBJECT-TYPE
        SYNTAX Counter32
        MAX-ACCESS read-only
        STATUS current
        DESCRIPTION
            "This attribute shows the number of HT data
             frames that were received at MCS 9."
    ::= { wlanLinkTestHTStatsEntry 11 }

    wlanLinkTestHTStatsRxFramesMCS10 OBJECT-TYPE
        SYNTAX Counter32
        MAX-ACCESS read-only
        STATUS current
        DESCRIPTION
            "This attribute shows the number of HT data
             frames that were received at MCS 10."
    ::= { wlanLinkTestHTStatsEntry 12 }

    wlanLinkTestHTStatsRxFramesMCS11 OBJECT-TYPE
        SYNTAX Counter32
        MAX-ACCESS read-only
        STATUS current
        DESCRIPTION
            "This attribute shows the number of HT data
             frames that were received at MCS 11."
    ::= { wlanLinkTestHTStatsEntry 13 }

    wlanLinkTestHTStatsRxFramesMCS12 OBJECT-TYPE
        SYNTAX Counter32
        MAX-ACCESS read-only
        STATUS current
        DESCRIPTION
            "This attribute shows the number of HT data
             frames that were received at MCS 12."
    ::= { wlanLinkTestHTStatsEntry 14 }

    wlanLinkTestHTStatsRxFramesMCS13 OBJECT-TYPE
        SYNTAX Counter32
        MAX-ACCESS read-only
        STATUS current
        DESCRIPTION
            "This attribute shows the number of HT data
             frames that were received at MCS 13."
    ::= { wlanLinkTestHTStatsEntry 15 }

    wlanLinkTestHTStatsRxFramesMCS14 OBJECT-TYPE
        SYNTAX Counter32
        MAX-ACCESS read-only
        STATUS current
        DESCRIPTION
            "This attribute shows the number of HT data
             frames that were received at MCS 14."
    ::= { wlanLinkTestHTStatsEntry 16 }

    wlanLinkTestHTStatsRxFramesMCS15 OBJECT-TYPE
        SYNTAX Counter32
        MAX-ACCESS read-only
        STATUS current
        DESCRIPTION
            "This attribute shows the number of HT data
             frames that were received at MCS 15."
    ::= { wlanLinkTestHTStatsEntry 17 }

    wlanLinkTestHTStatsRxFramesRemoteMCS0 OBJECT-TYPE
        SYNTAX Counter32
        MAX-ACCESS read-only
        STATUS current
        DESCRIPTION
            "This attribute shows the number of HT data
             frames that were transmitted at MCS 0."
    ::= { wlanLinkTestHTStatsEntry 18 }

    wlanLinkTestHTStatsRxFramesRemoteMCS1 OBJECT-TYPE
        SYNTAX Counter32
        MAX-ACCESS read-only
        STATUS current
        DESCRIPTION
            "This attribute shows the number of HT data
             frames that were transmitted at MCS 1."
    ::= { wlanLinkTestHTStatsEntry 19 }

    wlanLinkTestHTStatsRxFramesRemoteMCS2 OBJECT-TYPE
        SYNTAX Counter32
        MAX-ACCESS read-only
        STATUS current
        DESCRIPTION
            "This attribute shows the number of HT data
             frames that were transmitted at MCS 2."
    ::= { wlanLinkTestHTStatsEntry 20 }

    wlanLinkTestHTStatsRxFramesRemoteMCS3 OBJECT-TYPE
        SYNTAX Counter32
        MAX-ACCESS read-only
        STATUS current
        DESCRIPTION
            "This attribute shows the number of HT data
             frames that were transmitted at MCS 3."
    ::= { wlanLinkTestHTStatsEntry 21 }

    wlanLinkTestHTStatsRxFramesRemoteMCS4 OBJECT-TYPE
        SYNTAX Counter32
        MAX-ACCESS read-only
        STATUS current
        DESCRIPTION
            "This attribute shows the number of HT data
             frames that were transmitted at MCS 4."
    ::= { wlanLinkTestHTStatsEntry 22 }

    wlanLinkTestHTStatsRxFramesRemoteMCS5 OBJECT-TYPE
        SYNTAX Counter32
        MAX-ACCESS read-only
        STATUS current
        DESCRIPTION
            "This attribute shows the number of HT data
             frames that were transmitted at MCS 5."
    ::= { wlanLinkTestHTStatsEntry 23 }

    wlanLinkTestHTStatsRxFramesRemoteMCS6 OBJECT-TYPE
        SYNTAX Counter32
        MAX-ACCESS read-only
        STATUS current
        DESCRIPTION
            "This attribute shows the number of HT data
             frames that were transmitted at MCS 6."
    ::= { wlanLinkTestHTStatsEntry 24 }

    wlanLinkTestHTStatsRxFramesRemoteMCS7 OBJECT-TYPE
        SYNTAX Counter32
        MAX-ACCESS read-only
        STATUS current
        DESCRIPTION
            "This attribute shows the number of HT data
             frames that were transmitted at MCS 7."
    ::= { wlanLinkTestHTStatsEntry 25 }

    wlanLinkTestHTStatsRxFramesRemoteMCS8 OBJECT-TYPE
        SYNTAX Counter32
        MAX-ACCESS read-only
        STATUS current
        DESCRIPTION
            "This attribute shows the number of data
             frames that were transmitted at MCS 8."
    ::= { wlanLinkTestHTStatsEntry 26 }

    wlanLinkTestHTStatsRxFramesRemoteMCS9 OBJECT-TYPE
        SYNTAX Counter32
        MAX-ACCESS read-only
        STATUS current
        DESCRIPTION
            "This attribute shows the number of HT data
             frames that were transmitted at MCS 9."
    ::= { wlanLinkTestHTStatsEntry 27 }

    wlanLinkTestHTStatsRxFramesRemoteMCS10 OBJECT-TYPE
        SYNTAX Counter32
        MAX-ACCESS read-only
        STATUS current
        DESCRIPTION
            "This attribute shows the number of HT data
             frames that were transmitted at MCS 10."
    ::= { wlanLinkTestHTStatsEntry 28 }

    wlanLinkTestHTStatsRxFramesRemoteMCS11 OBJECT-TYPE
        SYNTAX Counter32
        MAX-ACCESS read-only
        STATUS current
        DESCRIPTION
            "This attribute shows the number of HT data
             frames that were transmitted at MCS 11."
    ::= { wlanLinkTestHTStatsEntry 29 }

    wlanLinkTestHTStatsRxFramesRemoteMCS12 OBJECT-TYPE
        SYNTAX Counter32
        MAX-ACCESS read-only
        STATUS current
        DESCRIPTION
            "This attribute shows the number of HT data
             frames that were transmitted at MCS 12."
    ::= { wlanLinkTestHTStatsEntry 30 }

    wlanLinkTestHTStatsRxFramesRemoteMCS13 OBJECT-TYPE
        SYNTAX Counter32
        MAX-ACCESS read-only
        STATUS current
        DESCRIPTION
            "This attribute shows the number of HT data
             frames that were transmitted at MCS 13."
    ::= { wlanLinkTestHTStatsEntry 31 }

    wlanLinkTestHTStatsRxFramesRemoteMCS14 OBJECT-TYPE
        SYNTAX Counter32
        MAX-ACCESS read-only
        STATUS current
        DESCRIPTION
            "This attribute shows the number of HT data
             frames that were transmitted at MCS 14."
    ::= { wlanLinkTestHTStatsEntry 32 }

    wlanLinkTestHTStatsRxFramesRemoteMCS15 OBJECT-TYPE
        SYNTAX Counter32
        MAX-ACCESS read-only
        STATUS current
        DESCRIPTION
            "This attribute shows the number of HT data
             frames that were transmitted at MCS 15."
    ::= { wlanLinkTestHTStatsEntry 33 }

    wlanLinkTestHTStatsBandwidthLocal OBJECT-TYPE
        SYNTAX INTEGER { b20MHz(1), b40MHz(2) }
        MAX-ACCESS read-only
        STATUS current
        DESCRIPTION
            "This attribute shows the bandwidth the remote side
             used: 20 MHz (1) or 40 MHz (2)."
        DEFVAL { b20MHz }
	::= { wlanLinkTestHTStatsEntry 34 }

    wlanLinkTestHTStatsGuardIntervalLocal OBJECT-TYPE
        SYNTAX INTEGER { long(1), short(2) }
        MAX-ACCESS read-only
        STATUS current
        DESCRIPTION
            "This attribute shows the length of the guard interval
             the remote side used:
             long (1)  or short (2)."
        DEFVAL { long }
	::= { wlanLinkTestHTStatsEntry 35 }

    wlanLinkTestHTStatsRSSI1Local OBJECT-TYPE
        SYNTAX WlanRSSI
        UNITS "dBm"
        MAX-ACCESS read-only
        STATUS current
        DESCRIPTION
            "This attribute shows the received signal strength
             on the first receiver in dBm."
        ::= { wlanLinkTestHTStatsEntry 36 }

    wlanLinkTestHTStatsRSSI2Local OBJECT-TYPE
        SYNTAX WlanRSSI
        UNITS "dBm"
        MAX-ACCESS read-only
        STATUS current
        DESCRIPTION
            "This attribute shows the received signal strength
             on the second receiver in dBm."
        ::= { wlanLinkTestHTStatsEntry 37 }

    wlanLinkTestHTStatsRSSI3Local OBJECT-TYPE
        SYNTAX WlanRSSI
        UNITS "dBm"
        MAX-ACCESS read-only
        STATUS current
        DESCRIPTION
            "This attribute shows the received signal strength
             on the third receiver in dBm."
        ::= { wlanLinkTestHTStatsEntry 38 }

    wlanLinkTestHTStatsBandwidthRemote OBJECT-TYPE
        SYNTAX INTEGER { b20MHz(1), b40MHz(2) }
        MAX-ACCESS read-only
        STATUS current
        DESCRIPTION
            "This attribute shows the bandwidth the local side
             used for transmitting: 20 MHz (1) or 40 MHz (2)."
        DEFVAL { b20MHz }
	::= { wlanLinkTestHTStatsEntry 39 }

    wlanLinkTestHTStatsGuardIntervalRemote OBJECT-TYPE
        SYNTAX INTEGER { long(1), short(2) }
        MAX-ACCESS read-only
        STATUS current
        DESCRIPTION
            "This attribute shows the length of the guard interval
             the local side used for transmitting:
             long (1)  or short (2)."
        DEFVAL { long }
	::= { wlanLinkTestHTStatsEntry 40 }

    wlanLinkTestHTStatsRSSI1Remote OBJECT-TYPE
        SYNTAX WlanRSSI
        UNITS "dBm"
        MAX-ACCESS read-only
        STATUS current
        DESCRIPTION
            "This attribute shows the received signal strength
             on the first receiver on the remote side in dBm."
        ::= { wlanLinkTestHTStatsEntry 41 }

    wlanLinkTestHTStatsRSSI2Remote OBJECT-TYPE
        SYNTAX WlanRSSI
        UNITS "dBm"
        MAX-ACCESS read-only
        STATUS current
        DESCRIPTION
            "This attribute shows the received signal strength
             on the second receiver on the remote side in dBm."
        ::= { wlanLinkTestHTStatsEntry 42 }

    wlanLinkTestHTStatsRSSI3Remote OBJECT-TYPE
        SYNTAX WlanRSSI
        UNITS "dBm"
        MAX-ACCESS read-only
        STATUS current
        DESCRIPTION
            "This attribute shows the received signal strength
             on the third receiver on the remote side in dBm."
        ::= { wlanLinkTestHTStatsEntry 43 }

    wlanLinkTestHTStatsRxFramesMCS16 OBJECT-TYPE
        SYNTAX Counter32
        MAX-ACCESS read-only
        STATUS current
        DESCRIPTION
            "This attribute shows the number of HT data
             frames that were received at MCS 16."
    ::= { wlanLinkTestHTStatsEntry 44 }

    wlanLinkTestHTStatsRxFramesMCS17 OBJECT-TYPE
        SYNTAX Counter32
        MAX-ACCESS read-only
        STATUS current
        DESCRIPTION
            "This attribute shows the number of HT data
             frames that were received at MCS 17."
    ::= { wlanLinkTestHTStatsEntry 45 }

    wlanLinkTestHTStatsRxFramesMCS18 OBJECT-TYPE
        SYNTAX Counter32
        MAX-ACCESS read-only
        STATUS current
        DESCRIPTION
            "This attribute shows the number of HT data
             frames that were received at MCS 18."
    ::= { wlanLinkTestHTStatsEntry 46 }

    wlanLinkTestHTStatsRxFramesMCS19 OBJECT-TYPE
        SYNTAX Counter32
        MAX-ACCESS read-only
        STATUS current
        DESCRIPTION
            "This attribute shows the number of HT data
             frames that were received at MCS 19."
    ::= { wlanLinkTestHTStatsEntry 47 }

    wlanLinkTestHTStatsRxFramesMCS20 OBJECT-TYPE
        SYNTAX Counter32
        MAX-ACCESS read-only
        STATUS current
        DESCRIPTION
            "This attribute shows the number of HT data
             frames that were received at MCS 20."
    ::= { wlanLinkTestHTStatsEntry 48 }

    wlanLinkTestHTStatsRxFramesMCS21 OBJECT-TYPE
        SYNTAX Counter32
        MAX-ACCESS read-only
        STATUS current
        DESCRIPTION
            "This attribute shows the number of HT data
             frames that were received at MCS 21."
    ::= { wlanLinkTestHTStatsEntry 49 }

    wlanLinkTestHTStatsRxFramesMCS22 OBJECT-TYPE
        SYNTAX Counter32
        MAX-ACCESS read-only
        STATUS current
        DESCRIPTION
            "This attribute shows the number of HT data
             frames that were received at MCS 22."
    ::= { wlanLinkTestHTStatsEntry 50 }

    wlanLinkTestHTStatsRxFramesMCS23 OBJECT-TYPE
        SYNTAX Counter32
        MAX-ACCESS read-only
        STATUS current
        DESCRIPTION
            "This attribute shows the number of HT data
             frames that were received at MCS 23."
    ::= { wlanLinkTestHTStatsEntry 51 }

    wlanLinkTestHTStatsRxFramesRemoteMCS16 OBJECT-TYPE
        SYNTAX Counter32
        MAX-ACCESS read-only
        STATUS current
        DESCRIPTION
            "This attribute shows the number of HT data
             frames that were transmitted at MCS 16."
    ::= { wlanLinkTestHTStatsEntry 52 }

    wlanLinkTestHTStatsRxFramesRemoteMCS17 OBJECT-TYPE
        SYNTAX Counter32
        MAX-ACCESS read-only
        STATUS current
        DESCRIPTION
            "This attribute shows the number of HT data
             frames that were transmitted at MCS 17."
    ::= { wlanLinkTestHTStatsEntry 53 }

    wlanLinkTestHTStatsRxFramesRemoteMCS18 OBJECT-TYPE
        SYNTAX Counter32
        MAX-ACCESS read-only
        STATUS current
        DESCRIPTION
            "This attribute shows the number of HT data
             frames that were transmitted at MCS 18."
    ::= { wlanLinkTestHTStatsEntry 54 }

    wlanLinkTestHTStatsRxFramesRemoteMCS19 OBJECT-TYPE
        SYNTAX Counter32
        MAX-ACCESS read-only
        STATUS current
        DESCRIPTION
            "This attribute shows the number of HT data
             frames that were transmitted at MCS 19."
    ::= { wlanLinkTestHTStatsEntry 55 }

    wlanLinkTestHTStatsRxFramesRemoteMCS20 OBJECT-TYPE
        SYNTAX Counter32
        MAX-ACCESS read-only
        STATUS current
        DESCRIPTION
            "This attribute shows the number of HT data
             frames that were transmitted at MCS 20."
    ::= { wlanLinkTestHTStatsEntry 56 }

    wlanLinkTestHTStatsRxFramesRemoteMCS21 OBJECT-TYPE
        SYNTAX Counter32
        MAX-ACCESS read-only
        STATUS current
        DESCRIPTION
            "This attribute shows the number of HT data
             frames that were transmitted at MCS 21."
    ::= { wlanLinkTestHTStatsEntry 57 }

    wlanLinkTestHTStatsRxFramesRemoteMCS22 OBJECT-TYPE
        SYNTAX Counter32
        MAX-ACCESS read-only
        STATUS current
        DESCRIPTION
            "This attribute shows the number of HT data
             frames that were transmitted at MCS 22."
    ::= { wlanLinkTestHTStatsEntry 58 }

    wlanLinkTestHTStatsRxFramesRemoteMCS23 OBJECT-TYPE
        SYNTAX Counter32
        MAX-ACCESS read-only
        STATUS current
        DESCRIPTION
            "This attribute shows the number of HT data
             frames that were transmitted at MCS 23."
    ::= { wlanLinkTestHTStatsEntry 59 }

-- **********************************************************************
-- *    End of wlanLinkTestHTStatsTable  TABLE
-- **********************************************************************

-- **********************************************************************
-- *    WLAN WDS Bridge notification Objects
-- **********************************************************************
    wlanWDSNotification OBJECT IDENTIFIER
	::= { wlan 20 }

    wlanWDSLinkOperState NOTIFICATION-TYPE
	OBJECTS {
	    ifIndex,
	    wlanWDSOperStatus
	    }
	STATUS current
	DESCRIPTION
	    "This notification is triggered whenever the connection state
	     of the bridge link changes, i.e. link connection is lost,
	     or link connection is restored."
	::= { wlanWDSNotification 1 }

    wlanWDSLinkConfigScan NOTIFICATION-TYPE
	OBJECTS {
	    ifIndex,
	    wlanWDSLinkConfigScanState
	    }
	STATUS current
	DESCRIPTION
	    "This notification is thrown whenever the bridge link
	     auto-configuration scanning state changes."
	::= { wlanWDSNotification 2 }

    wlanWDSPeerConfigSetup NOTIFICATION-TYPE
	OBJECTS {
	    ifIndex,
	    wlanWDSPeerConfigSetupState,
	    wlanWDSPeerConfigSetupResult
	    }
	STATUS current
	DESCRIPTION
	    "This notification is thrown whenever the bridge
	     link auto-configuration setup state changes."
	::= { wlanWDSNotification 3 }

    wlanWDSLinkLock NOTIFICATION-TYPE
	OBJECTS {
	    ifIndex,
	    wlanWDSLinkLockState
	    }
	STATUS current
	DESCRIPTION
	    "This notification is triggered whenever the
	     lock state of the bridge link changes."
	::= { wlanWDSNotification 4 }
-- **********************************************************************
-- *    End of WLAN WDS Bridge notification Objects
-- **********************************************************************

-- **********************************************************************
-- *    global WLAN
-- **********************************************************************
    wlanGlobal  OBJECT IDENTIFIER
	::= { wlan 21 }

    wlanGlobalEnable  OBJECT-TYPE
	SYNTAX 		TruthValue
	MAX-ACCESS	read-only
	STATUS		current
	DESCRIPTION
		"This is a global WLAN switch to enable/disable
		 all WLAN cards (can be used for a WLAN button)"
        DEFVAL { true }
	::= { wlanGlobal 1 }

    wlanGlobalDebugType    OBJECT-TYPE
	SYNTAX 	        INTEGER { common(1), authentication(2),
                                  access-point(3), bridge(4), client(5),
                                  lowlevel(6), all(7) }
	MAX-ACCESS	read-write
	STATUS		current
	DESCRIPTION
		"Wireless LAN degugging type. With type common(1) debugging messages
                 of authentication, access_point, bridge and client
                 handling will be shown. With type
                 authentication(2) only messages concerning the authentication
                 handling (mainly WPA) will be shown. With type access_point(3)
                 only messages concerning the access_point handling
                 will be shown. With type bridge(4) only messages concerning
                 the bridge handling will be shown. With type client(5) only
                 messages concerning the client (wlanIfType == client) will be
                 shown. With type lowlevel(6) messages concerning the 802.11 layer
                 and lowlevel driver handling will be shown. With type all(7) all
                 messages of all types will be shown. Default is common(1).
                 Additionally within all types messages concerning generally wlan
                 handling will be shown."
        DEFVAL { common }
	::= { wlanGlobal 2 }

    wlanGlobalDebugLevel    OBJECT-TYPE
	SYNTAX 	        INTEGER { quiet(1), normal(2), verbose(3), very-verbose(4) }
	MAX-ACCESS	read-write
	STATUS		current
	DESCRIPTION
		"Wireless LAN degugging verbosity level. With a higher value
                 more debugging information will be created. Default is normal(2)."
        DEFVAL { normal }
	::= { wlanGlobal 3 }

    wlanGlobalAdminStatus    OBJECT-TYPE
	SYNTAX 	        INTEGER { unmanaged(1), managed(2) }
	MAX-ACCESS	read-write
	STATUS		current
	DESCRIPTION
		"Wireless LAN global AdminStatus. The AP could be used
                unmanaged(1) and must therefore be configured directly
                or managed(2) by a WLAN controller. Default is unmanaged(1)."
        DEFVAL { unmanaged }
	::= { wlanGlobal 4 }

    wlanGlobalOperStatus    OBJECT-TYPE
	SYNTAX 	        INTEGER { undefined(1), managed-waiting(2),
                                managed-controlled(3), unmanaged(4) }
	MAX-ACCESS	read-only
	STATUS		current
	DESCRIPTION
		"Wireless LAN global OperStatus. This variable shows the state of
                the AP where undefined(1) is the initial state when the AP comes up.
                The AP is in the managed_waiting(2) state when he waits for a
                feedback of a WLAN controller. In managed_controlled(3) state the AP
                is connected to and controlled by a WLAN controller. The
                unmanaged(4) state is reached when the AP is set to
                wlanGlobalAdminStatus=unmanaged by the Admin.
                Default is undefined(1)."
        DEFVAL { undefined }
	::= { wlanGlobal 5 }

    wlanGlobalScanResultsMaxAge    OBJECT-TYPE
	SYNTAX 	        INTEGER
	UNITS           "seconds"
	MAX-ACCESS	read-write
	STATUS		current
	DESCRIPTION
		"If a scan result wasn't seen for so many seconds,
		it will be removed from wlanScanResultsTable."
        DEFVAL { 3600 }
	::= { wlanGlobal 6 }

-- **********************************************************************
-- *    wlanWMMTable  TABLE
-- **********************************************************************
    wlanWMMTable OBJECT-TYPE
	SYNTAX  SEQUENCE OF WlanWMMEntry
	MAX-ACCESS  not-accessible
	STATUS  current
	DESCRIPTION
	    " Describes a WLAN WMM Access category settings"
    ::= { wlan 22 }

    wlanWMMEntry OBJECT-TYPE
       SYNTAX  WlanWMMEntry
       MAX-ACCESS  not-accessible
       STATUS  current
       DESCRIPTION
	""
       INDEX   { wlanWMMAccCat, wlanWMMwlanIf, wlanWMMType }
       ::= { wlanWMMTable 1 }

        WlanWMMEntry ::=
	 SEQUENCE {
	wlanWMMAccCat	    INTEGER,
	wlanWMMwlanIf	    INTEGER,
	wlanWMMaCWmin	    INTEGER,
	wlanWMMaCWmax	    INTEGER,
	wlanWMMAifsn	    INTEGER,
	wlanWMMTxopLimitb   INTEGER,
	wlanWMMTxopLimitg   INTEGER,
	wlanWMMAckPolicy    INTEGER,
        wlanWMMACM          INTEGER,
        wlanWMMType         INTEGER
	}

    wlanWMMAccCat OBJECT-TYPE
	SYNTAX  INTEGER	{ besteffort(1), background(2), video(3), voice(4) }
	MAX-ACCESS  read-only
	STATUS  current
	DESCRIPTION
	    "Access category type, each category is mandatory for a wlanIf.

	    An access category (AC) is a label for the common set of enhanced
	    distributed channel access (EDCA) parameters that are used by a
	    quality of service (QoS) station (QSTA) to contend for the channel
	    in order to transmit medium access control (MAC) service data
	    units (MSDUs) with certain priorities.

	    (More info in '802.11E / 3.123 access category (AC)').

	    besteffort(1): standard/default priority
	    background(2): low priority
	    video(3): medium priority (higher than 'besteffort')
	    voice(4): high priority"
	DEFVAL { besteffort }
    ::= { wlanWMMEntry 1 }

    wlanWMMwlanIf OBJECT-TYPE
	SYNTAX  INTEGER
	MAX-ACCESS  read-only
	STATUS  current
	DESCRIPTION
	    "Radio index the AC belongs to."
    ::= { wlanWMMEntry 2 }

    wlanWMMaCWmin OBJECT-TYPE
	SYNTAX  INTEGER
	MAX-ACCESS  read-write
	STATUS  current
	DESCRIPTION
            "Minimum size of contention window.
	    for AC_BK and AC_BE wlanWMMaCWmin = wlanIfCWmin,
	    for AC_VI wlanWMMaCWmin = (wlanIfCWmin-1)/2,
	    for AC_VO wlanWMMaCWmin = (wlanIfCWmin-3)/4."
    ::= { wlanWMMEntry 3 }

    wlanWMMaCWmax OBJECT-TYPE
	SYNTAX  INTEGER
	MAX-ACCESS  read-write
	STATUS  current
	DESCRIPTION
            "Maximum size of contention window.
	    for AC_BK wlanWMMaCWmax = wlanIfCWmax,
	    for AC_BE wlanWMMaCWmax = 4*wlanIfCWmin + 3,
	    for AC_VI wlanWMMaCWmax = wlanIfCWmin,
	    for AC_VO wlanWMMaCWmax = (wlanIfCWmin-1)/2."
    ::= { wlanWMMEntry 4 }

    wlanWMMAifsn OBJECT-TYPE
	SYNTAX  INTEGER (0..99)
	MAX-ACCESS  read-write
	STATUS  current
	DESCRIPTION
            "Arbitration Inter-Frame Space Number (AIFSN)
	    for this Access category."
    ::= { wlanWMMEntry 5 }

    wlanWMMTxopLimitb OBJECT-TYPE
	SYNTAX  INTEGER (0..9999)
	MAX-ACCESS  read-write
	STATUS  current
	DESCRIPTION
                "802.11b mode Transmit Opportunity Limit."
    ::= { wlanWMMEntry 6 }

    wlanWMMTxopLimitg OBJECT-TYPE
	SYNTAX  INTEGER (0..9999)
	MAX-ACCESS  read-write
	STATUS  current
	DESCRIPTION
                "802.11g mode Transmit Opportunity Limit."
    ::= { wlanWMMEntry 7 }

     wlanWMMAckPolicy OBJECT-TYPE
	SYNTAX  INTEGER { ack(1), noAck(2) }
	MAX-ACCESS  read-write
	STATUS  current
	DESCRIPTION
                "Ack policy for this Access category (default value is 'ack(1)')."
	DEFVAL { ack }
    ::= { wlanWMMEntry 8 }

     wlanWMMACM OBJECT-TYPE
	SYNTAX  INTEGER { enabled(1), disabled(2) }
	MAX-ACCESS  read-write
	STATUS  current
	DESCRIPTION
                "ACM (admission control) policy for this Access category i
                (default value is 'disabled(2)')."
	DEFVAL { disabled }
    ::= { wlanWMMEntry 9 }

    wlanWMMType OBJECT-TYPE
	SYNTAX  INTEGER { access-point(1), station(2) }
	MAX-ACCESS  read-only
	STATUS  current
	DESCRIPTION
                "Type to which this wlanWMMEntry corresponds.
                 Type access_point means the own parameters for WMM are changed.
                 The entries with type station will be provided to the connected
                 stations via WMM-IE (default value is 'access_point(1)')."
	DEFVAL { access-point }
    ::= { wlanWMMEntry 10 }

-- **********************************************************************
-- *    End of wlanWMMTable  TABLE
-- **********************************************************************

-- **********************************************************************
-- *    wlanIfFeatureTable  TABLE
-- **********************************************************************
wlanIfFeatureTable OBJECT-TYPE
    SYNTAX	SEQUENCE OF WlanIfFeatureEntry
    MAX-ACCESS  not-accessible
    STATUS	current
    DESCRIPTION
            "This table lists all feature of a wireless card.
             The supported features depends on the vendor and
             wireless chipset."
    ::= { wlan 23 }

    wlanIfFeatureEntry OBJECT-TYPE
	SYNTAX	    WlanIfFeatureEntry
	MAX-ACCESS  not-accessible
	STATUS	    current
	DESCRIPTION
	""
	INDEX   { wlanIfFeatureWlanIf }
    ::= { wlanIfFeatureTable 1 }

    WlanIfFeatureEntry ::=
	SEQUENCE {
	    wlanIfFeatureWlanIf			INTEGER,
	    wlanIfFeatureOperatingBands		BITS,
	    wlanIfFeatureAntennaDiversity	INTEGER,
	    wlanIfFeatureTxPowerMin		INTEGER,
	    wlanIfFeatureTxPowerMax		INTEGER,
	    wlanIfFeatureTxPowerFixedStepsList	DisplayString,
	    wlanIfFeatureFrameCompression	TruthValue,
	    wlanIfFeatureFrameConcatenation	TruthValue,
	    wlanIfFeaturePiggybackAck		TruthValue,
	    wlanIfFeatureDirectLink		TruthValue,
	    wlanIfFeatureLinkDistance		TruthValue,
	    wlanIfFeatureShortRetries		TruthValue,
	    wlanIfFeatureLongRetries		TruthValue,
	    wlanIfFeatureFragThreshold		TruthValue,
	    wlanIfFeatureCCAMode		TruthValue,
	    wlanIfFeatureEdThreshold		TruthValue,
	    wlanIfFeatureCWMin			TruthValue,
	    wlanIfFeatureCWMax			TruthValue,
	    wlanIfFeatureRxLifetime		TruthValue,
	    wlanIfFeatureTxLifetime		TruthValue,
	    wlanIfFeatureSkipModes		BITS,
	    wlanIfFeatureSupportedModes		BITS,
	    wlanIfFeatureSpatialStreams		INTEGER,
	    wlanIfFeatureMaxVSS			INTEGER,
	    wlanIfFeatureMaxWDS			INTEGER,
	    wlanIfFeatureMaxClient		INTEGER,
	    wlanIfFeatureMaxStations		INTEGER
	}

    wlanIfFeatureWlanIf OBJECT-TYPE
        SYNTAX	    INTEGER
        MAX-ACCESS  read-only
        STATUS	    current
        DESCRIPTION
            "Wireless card interface index the table belongs."
	::= { wlanIfFeatureEntry 1 }

    wlanIfFeatureOperatingBands OBJECT-TYPE
        SYNTAX	    BITS { band24(0), band5(1), band58(2) }
        MAX-ACCESS  read-only
        STATUS	    current
        DESCRIPTION
            "This variable says which bands the wireless card supports.
             Default is 2.4 and 5 GHZ."
        DEFVAL { { band24 } }
	::= { wlanIfFeatureEntry 2 }

    wlanIfFeatureAntennaDiversity OBJECT-TYPE
        SYNTAX	    INTEGER {	none	(0),
				rx	(1),
				tx	(2),
				rx-tx	(3) }
        MAX-ACCESS  read-only
        STATUS	    current
        DESCRIPTION
            "This variable says which kind of antenna diversity
             the wireless card supports.
             Default is none."
        DEFVAL { none }
	::= { wlanIfFeatureEntry 3 }

    wlanIfFeatureTxPowerMin OBJECT-TYPE
        SYNTAX	    INTEGER ( 0..30 )
        MAX-ACCESS  read-only
        STATUS	    current
        DESCRIPTION
            "The minimal value of the TX power the wireless card supports."
        DEFVAL { 0 }
	::= { wlanIfFeatureEntry 4 }

    wlanIfFeatureTxPowerMax OBJECT-TYPE
        SYNTAX	    INTEGER ( 0..100 )
        MAX-ACCESS  read-only
        STATUS	    current
        DESCRIPTION
            "The maximal value of the TX power the wireless card supports."
        DEFVAL { 20 }
	::= { wlanIfFeatureEntry 5 }

    wlanIfFeatureTxPowerFixedStepsList OBJECT-TYPE
        SYNTAX	    DisplayString
        MAX-ACCESS  read-only
        STATUS	    current
        DESCRIPTION
            "This variable shows the available TX Power values in dBm
             seperated by commas."
	::= { wlanIfFeatureEntry 6 }

    wlanIfFeatureFrameCompression OBJECT-TYPE
        SYNTAX	    TruthValue
        MAX-ACCESS  read-only
        STATUS	    current
        DESCRIPTION
            "This variable says if the wireless card supports
             frame compression or not.
             Default is false."
        DEFVAL { false }
	::= { wlanIfFeatureEntry 7 }

    wlanIfFeatureFrameConcatenation OBJECT-TYPE
        SYNTAX	    TruthValue
        MAX-ACCESS  read-only
        STATUS	    current
        DESCRIPTION
            "This variable says if the wireless card supports
             frame concatination or not.
             Default is false."
        DEFVAL { false }
	::= { wlanIfFeatureEntry 8 }

    wlanIfFeaturePiggybackAck OBJECT-TYPE
        SYNTAX	    TruthValue
        MAX-ACCESS  read-only
        STATUS	    current
        DESCRIPTION
            "This variable says if the wireless card supports
             piggyback ACKs or not.
             Default is false."
        DEFVAL { false }
	::= { wlanIfFeatureEntry 9 }

    wlanIfFeatureDirectLink OBJECT-TYPE
        SYNTAX	    TruthValue
        MAX-ACCESS  read-only
        STATUS	    current
        DESCRIPTION
            "This variable says if the wireless card supports
             direct links or not.
             Default is false."
        DEFVAL { false }
	::= { wlanIfFeatureEntry 10 }

    wlanIfFeatureLinkDistance OBJECT-TYPE
        SYNTAX	    TruthValue
        MAX-ACCESS  read-only
        STATUS	    current
        DESCRIPTION
            "This variable says if the wireless card supports a
             configurable link distance or not.
             Default is false."
        DEFVAL { false }
	::= { wlanIfFeatureEntry 11 }

    wlanIfFeatureShortRetries OBJECT-TYPE
        SYNTAX	    TruthValue
        MAX-ACCESS  read-only
        STATUS	    current
        DESCRIPTION
            "This variable says if the wireless card supports
             the configuration of the short retry value or not.
             Default is false."
        DEFVAL { false }
	::= { wlanIfFeatureEntry 12 }

    wlanIfFeatureLongRetries OBJECT-TYPE
        SYNTAX	    TruthValue
        MAX-ACCESS  read-only
        STATUS	    current
        DESCRIPTION
            "This variable says if the wireless card supports
             the configuration of the long retry value or not.
             Default is false."
        DEFVAL { false }
	::= { wlanIfFeatureEntry 13 }

    wlanIfFeatureFragThreshold OBJECT-TYPE
        SYNTAX	    TruthValue
        MAX-ACCESS  read-only
        STATUS	    current
        DESCRIPTION
            "This variable says if the wireless card supports
             the configuration of the fragmentation threshold
             value or not.
             Default is false."
        DEFVAL { false }
	::= { wlanIfFeatureEntry 14 }

    wlanIfFeatureCCAMode OBJECT-TYPE
        SYNTAX	    TruthValue
        MAX-ACCESS  read-only
        STATUS	    current
        DESCRIPTION
            "This variable says if the wireless card supports
             the configuration of the CCA mode or not.
             Default is false."
        DEFVAL { false }
	::= { wlanIfFeatureEntry 15 }

    wlanIfFeatureEdThreshold OBJECT-TYPE
        SYNTAX	    TruthValue
        MAX-ACCESS  read-only
        STATUS	    current
        DESCRIPTION
            "This variable says if the wireless card supports
             the configuration of the energy detection threshold
             value or not.
             Default is false."
        DEFVAL { false }
	::= { wlanIfFeatureEntry 16 }

    wlanIfFeatureCWMin OBJECT-TYPE
        SYNTAX	    TruthValue
        MAX-ACCESS  read-only
        STATUS	    current
        DESCRIPTION
            "This variable says if the wireless card supports
             the configuration of the minimal contention window or not.
             Default is false."
        DEFVAL { false }
	::= { wlanIfFeatureEntry 17 }

    wlanIfFeatureCWMax OBJECT-TYPE
        SYNTAX	    TruthValue
        MAX-ACCESS  read-only
        STATUS	    current
        DESCRIPTION
            "This variable says if the wireless card supports
             the configuration of the maximal contention window or not.
             Default is false."
        DEFVAL { false }
	::= { wlanIfFeatureEntry 18 }

    wlanIfFeatureRxLifetime OBJECT-TYPE
        SYNTAX	    TruthValue
        MAX-ACCESS  read-only
        STATUS	    current
        DESCRIPTION
            "This variable says if the wireless card supports
             the configuration of the receive packet lifetime or not.
             Default is false."
        DEFVAL { false }
	::= { wlanIfFeatureEntry 19 }

    wlanIfFeatureTxLifetime OBJECT-TYPE
        SYNTAX	    TruthValue
        MAX-ACCESS  read-only
        STATUS	    current
        DESCRIPTION
            "This variable says if the wireless card supports
             the configuration of the transmit packet lifetime or not.
             Default is false."
        DEFVAL { false }
	::= { wlanIfFeatureEntry 20 }

    wlanIfFeatureSkipModes OBJECT-TYPE
        SYNTAX	    BITS { ap24ghz(0), ap5ghz(1), client24ghz(2), client5ghz(3) }
        MAX-ACCESS  read-only
        STATUS	    current
        DESCRIPTION
	     "This variable says which modes of the WlanIfSkipChannels the wireless card supports.
             Default is client24ghz."
        DEFVAL { { client24ghz } }
	::= { wlanIfFeatureEntry 21 }

    wlanIfFeatureSupportedModes OBJECT-TYPE
        SYNTAX	    BITS { dot11a(0), dot11b(1), dot11g(2), dot11n(3) }
        MAX-ACCESS  read-only
        STATUS	    current
        DESCRIPTION
	     "This variable shows the supported 802.11 modes"
        DEFVAL { { dot11b } }
	::= { wlanIfFeatureEntry 22 }

    wlanIfFeatureSpatialStreams OBJECT-TYPE
        SYNTAX	    INTEGER ( 1..4 )
        MAX-ACCESS  read-only
        STATUS	    current
        DESCRIPTION
            "This variable shows the maximum number
             of supported spatial streams"
        DEFVAL { 1 }
	::= { wlanIfFeatureEntry 23 }


    wlanIfFeatureMaxVSS OBJECT-TYPE
        SYNTAX	    INTEGER (0..40)
        MAX-ACCESS  read-only
        STATUS	    current
        DESCRIPTION
            "This attribute indicates the maximum number of service sets
	     that may be created per radio module.
	    "
        DEFVAL { 0 }
	::= { wlanIfFeatureEntry 30 }

    wlanIfFeatureMaxWDS OBJECT-TYPE
        SYNTAX	    INTEGER (0..40)
        MAX-ACCESS  read-only
        STATUS	    current
        DESCRIPTION
            "This attribute indicates the maximum number of WDS links
	     that may be created per radio module.
	    "
        DEFVAL { 0 }
	::= { wlanIfFeatureEntry 31 }

    wlanIfFeatureMaxClient OBJECT-TYPE
        SYNTAX	    INTEGER (0..10)
        MAX-ACCESS  read-only
        STATUS	    current
        DESCRIPTION
            "This attribute indicates the maximum number of client instances
	     that may be created per radio module.
	    "
        DEFVAL { 0 }
	::= { wlanIfFeatureEntry 32 }

    wlanIfFeatureMaxStations OBJECT-TYPE
	SYNTAX  INTEGER (0..2048)
	MAX-ACCESS  read-only
	STATUS  current
	DESCRIPTION
	    "Maximum number of stations the station database can hold."
	DEFVAL { 128 }
    ::= { wlanIfFeatureEntry 33 }

-- **********************************************************************
-- *    End of wlanIfFeatureTable  TABLE
-- **********************************************************************


-- **********************************************************************
-- *    wlanWDSStatsTable  TABLE
-- **********************************************************************
-- **********************************************************************
-- *    End of wlanWDSStatsTable  TABLE
-- **********************************************************************

-- **********************************************************************
-- *    wlanClientStatsTable  TABLE
-- **********************************************************************
-- **********************************************************************
-- *    End of wlanClientStatsTable  TABLE
-- **********************************************************************


END
