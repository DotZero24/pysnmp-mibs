-- This file is corresponding to Release 9.1.10.101 from 2014/08/11 00:00:00


-- (C)opyright 1991-2014 bintec elmeg GmbH, All Rights Reserved
--  $RCSfile: mibsysx8,v $
-- $Revision: 1.8 $

BIANCA-X8000-MIBSYS-MIB DEFINITIONS ::= BEGIN

        IMPORTS
            Counter, enterprises
                FROM RFC1155-SMI

            DisplayString
                FROM RFC1158-MIB

            TRAP-TYPE
                FROM RFC-1215

            OBJECT-TYPE
                FROM RFC-1212;

    bintec      OBJECT IDENTIFIER ::= { enterprises 272 }
    bibo        OBJECT IDENTIFIER ::= { bintec 4 }
    sys         OBJECT IDENTIFIER ::= { bibo 17 }
    x8		OBJECT IDENTIFIER ::= { sys 3 }
    sysX8Config OBJECT IDENTIFIER
        ::= { x8 1 }

    sysX8Traps  OBJECT IDENTIFIER ::= { x8 2 }

-- System Status and Configuration

	sysX8ConfigPowerSupply1State OBJECT-TYPE
	    SYNTAX  INTEGER { missing(1), off(2), running(3), fail(4) }
	    ACCESS  read-only
  	    STATUS  mandatory

            DESCRIPTION
		"This variable shows the state of the power supply."
      	::= { sysX8Config 1 }

	sysX8ConfigPowerSupply1Temp OBJECT-TYPE
	    SYNTAX  INTEGER (0..250)
	    ACCESS  read-only
  	    STATUS  mandatory

            DESCRIPTION
                "This variable shows the actual power supply temperature
                in the unit Celsius."
      	::= { sysX8Config 2 }

	sysX8ConfigPowerSupply1TempAlarmThreshold OBJECT-TYPE
	    SYNTAX  INTEGER (0..250)
	    ACCESS  read-write
  	    STATUS  mandatory

            DESCRIPTION
                "Power supply 1 temperature threshold."
	    DEFVAL  { 40 }
      	::= { sysX8Config 3 }

	sysX8ConfigPowerSupply1TempAlarmTrap OBJECT-TYPE
	    SYNTAX  INTEGER { normal(1), critical(2) }
	    ACCESS  read-only
  	    STATUS  mandatory

            DESCRIPTION
                "If the power supply temperature raises above the threshold,
                a alarm trap is generated every 60 seconds."
      	::= { sysX8Config 4 }

	sysX8ConfigPowerSupply2State OBJECT-TYPE
	    SYNTAX  INTEGER { missing(1), off(2), running(3), fail(4) }
	    ACCESS  read-only
  	    STATUS  mandatory

            DESCRIPTION
		"This variable show the the state of the power supply."
      	::= { sysX8Config 5 }

	sysX8ConfigPowerSupply2Temp OBJECT-TYPE
	    SYNTAX  INTEGER (0..250)
	    ACCESS  read-only
  	    STATUS  mandatory

            DESCRIPTION
                "This variable shows the actual power supply temperature
                in the unit Celsius."
      	::= { sysX8Config 6 }

	sysX8ConfigPowerSupply2TempAlarmThreshold OBJECT-TYPE
	    SYNTAX  INTEGER (0..250)
	    ACCESS  read-write
  	    STATUS  mandatory

            DESCRIPTION
                "Power supply 2 temperature threshold."
	    DEFVAL  { 40 }
      	::= { sysX8Config 7 }

	sysX8ConfigPowerSupply2TempAlarmTrap OBJECT-TYPE
	    SYNTAX  INTEGER { normal(1), critical(2) }
	    ACCESS  read-only
  	    STATUS  mandatory

            DESCRIPTION
                "If the power supply temperature raises above the threshold,
                a alarm trap is generated every 60 seconds."
      	::= { sysX8Config 8 }

	sysX8ConfigFanControl OBJECT-TYPE
	    SYNTAX  INTEGER { auto(1), high(2) }
	    ACCESS  read-write
  	    STATUS  mandatory
            DESCRIPTION
	        "This variable defines automatic fan control.
	         In mode 'auto' the fans are automatically adjusted
		 depending on the current temperature.
		 In mode 'high' all fans remain at maximum speed."
	    DEFVAL  { high }
      	::= { sysX8Config 9 }

	sysX8ConfigFanVersion OBJECT-TYPE
	    SYNTAX  DisplayString
	    ACCESS  read-only
  	    STATUS  mandatory

            DESCRIPTION
	        "This variable shows the firmware version of
                 the fan unit."
      	::= { sysX8Config 10 }

	sysX8ConfigFan1 OBJECT-TYPE
	    SYNTAX  INTEGER
	    ACCESS  read-only
  	    STATUS  mandatory

            DESCRIPTION
	        "This variable shows the current turning speed."
      	::= { sysX8Config 11 }

	sysX8ConfigFan2 OBJECT-TYPE
	    SYNTAX  INTEGER
	    ACCESS  read-only
  	    STATUS  mandatory

            DESCRIPTION
	        "This variable shows the current turning speed."
      	::= { sysX8Config 12 }

	sysX8ConfigFan3 OBJECT-TYPE
	    SYNTAX  INTEGER
	    ACCESS  read-only
  	    STATUS  mandatory

            DESCRIPTION
	        "This variable shows the current turning speed."
      	::= { sysX8Config 13 }

	sysX8ConfigFan4 OBJECT-TYPE
	    SYNTAX  INTEGER
	    ACCESS  read-only
  	    STATUS  mandatory

            DESCRIPTION
	        "This variable shows the current turning speed."
      	::= { sysX8Config 14 }

---
--- System Status and Configuration Traps
---

  sysX8TrapPowerSupply1Missing TRAP-TYPE
   ENTERPRISE    sysX8Traps
   VARIABLES     {
                  sysDescr,
                  sysName,
	          sysX8ConfigPowerSupply1State,
	          sysX8ConfigPowerSupply1Temp,
	          sysX8ConfigPowerSupply1TempAlarmTrap
                 }
   DESCRIPTION  "This trap signifies that the power supply 1
                 has been removed"
   ::= 1

  sysX8TrapPowerSupply1PowerOff TRAP-TYPE
   ENTERPRISE    sysX8Traps
   VARIABLES     {
                  sysDescr,
                  sysName,
	          sysX8ConfigPowerSupply1State,
	          sysX8ConfigPowerSupply1Temp,
	          sysX8ConfigPowerSupply1TempAlarmTrap
                 }
   DESCRIPTION  "This trap signifies that the power supply 1
                 has no power-good signal (no power input)"
   ::= 2

  sysX8TrapPowerSupply1PowerFail TRAP-TYPE
   ENTERPRISE    sysX8Traps
   VARIABLES     {
                  sysDescr,
                  sysName,
                  sysX8ConfigPowerSupply1State,
                  sysX8ConfigPowerSupply1Temp,
                  sysX8ConfigPowerSupply1TempAlarmTrap
                 }
   DESCRIPTION  "This trap signifies that the power supply 1
                 has been in the failure (bad DC output)"
   ::= 3

  sysX8TrapPowerSupply1PowerGood TRAP-TYPE
   ENTERPRISE    sysX8Traps
   VARIABLES     {
                  sysDescr,
                  sysName,
	          sysX8ConfigPowerSupply1State,
	          sysX8ConfigPowerSupply1Temp,
	          sysX8ConfigPowerSupply1TempAlarmTrap
                 }
   DESCRIPTION  "This trap signifies that the power supply 1
                 is running (supplying power)"
   ::= 4

  sysX8TrapPowerSupply1TempCritical TRAP-TYPE
   ENTERPRISE    sysX8Traps
   VARIABLES     {
                  sysDescr,
                  sysName,
	          sysX8ConfigPowerSupply1State,
	          sysX8ConfigPowerSupply1Temp,
	          sysX8ConfigPowerSupply1TempAlarmThreshold
                 }
   DESCRIPTION   "This trap signifies that the power supply 1 temperature
                  raises above the critical alarm-threshold"
   ::= 5

  sysX8TrapPowerSupply1TempOk TRAP-TYPE
   ENTERPRISE    sysX8Traps
   VARIABLES     {
                  sysDescr,
                  sysName,
	          sysX8ConfigPowerSupply1State,
	          sysX8ConfigPowerSupply1Temp,
	          sysX8ConfigPowerSupply1TempAlarmThreshold
                 }
   DESCRIPTION   "A normal power supply 1 temperature has been restored."
   ::= 6

  sysX8TrapPowerSupply2Missing TRAP-TYPE
   ENTERPRISE    sysX8Traps
   VARIABLES     {
                  sysDescr,
                  sysName,
	          sysX8ConfigPowerSupply2State,
	          sysX8ConfigPowerSupply2Temp,
	          sysX8ConfigPowerSupply2TempAlarmThreshold
                 }
   DESCRIPTION  "This trap signifies that the power supply 2
                 has been removed"
   ::= 7

  sysX8TrapPowerSupply2PowerOff TRAP-TYPE
   ENTERPRISE    sysX8Traps
   VARIABLES     {
                  sysDescr,
                  sysName,
	          sysX8ConfigPowerSupply2State,
	          sysX8ConfigPowerSupply2Temp,
	          sysX8ConfigPowerSupply2TempAlarmThreshold
                 }
   DESCRIPTION  "This trap signifies that the power supply 2
                 has no power-good signal (no power input)"
   ::= 8

  sysX8TrapPowerSupply2PowerFail TRAP-TYPE
   ENTERPRISE    sysX8Traps
   VARIABLES     {
                  sysDescr,
                  sysName,
	          sysX8ConfigPowerSupply2State,
	          sysX8ConfigPowerSupply2Temp,
	          sysX8ConfigPowerSupply2TempAlarmThreshold
                 }
   DESCRIPTION  "This trap signifies that the power supply 2
                 has been in the failure (bad DC output)"
   ::= 9

  sysX8TrapPowerSupply2PowerGood TRAP-TYPE
   ENTERPRISE    sysX8Traps
   VARIABLES     {
                  sysDescr,
                  sysName,
	          sysX8ConfigPowerSupply2State,
	          sysX8ConfigPowerSupply2Temp,
	          sysX8ConfigPowerSupply2TempAlarmThreshold
                 }
   DESCRIPTION  "This trap signifies that the power supply 2
                 is running (supplying power)"
   ::= 10

  sysX8TrapPowerSupply2TempCritical TRAP-TYPE
   ENTERPRISE    sysX8Traps
   VARIABLES     {
                  sysDescr,
                  sysName,
	          sysX8ConfigPowerSupply2State,
	          sysX8ConfigPowerSupply2Temp,
	          sysX8ConfigPowerSupply2TempAlarmThreshold
                 }
   DESCRIPTION   "This trap signifies that the power supply 2 temperature
                  raises above the critical alarm-threshold"
   ::= 11

  sysX8TrapPowerSupply2TempOk TRAP-TYPE
   ENTERPRISE    sysX8Traps
   VARIABLES     {
                  sysDescr,
                  sysName,
	          sysX8ConfigPowerSupply2State,
	          sysX8ConfigPowerSupply2Temp,
	          sysX8ConfigPowerSupply2TempAlarmThreshold
                 }
   DESCRIPTION   "A normal power supply 2 temperature has been restored."
   ::= 12

END
