-- This file is corresponding to Release 9.1.10.101 from 2014/08/11 00:00:00


-- (C)opyright 2000-2014 bintec elmeg GmbH, All Rights Reserved

BIANCA-BRICK-PPPOE-MIB DEFINITIONS ::= BEGIN

        IMPORTS
            IpAddress, Counter, TimeTicks, enterprises
                FROM RFC1155-SMI

            DisplayString
                FROM RFC1158-MIB

	    PhysAddress
		FROM RFC1213-MIB

            OBJECT-TYPE
                FROM RFC-1212;

    bintec 	OBJECT IDENTIFIER ::= { enterprises 272 }
    bibo	OBJECT IDENTIFIER ::= { bintec 4 }
    pppoe	OBJECT IDENTIFIER
	::= { bibo 24 }


    -- PPPoE Group

    -- pppoeCallTable

	pppoeCallTable OBJECT-TYPE
	    SYNTAX  SEQUENCE OF PppoeCallEntry
	    ACCESS  not-accessible
	    STATUS  mandatory
	    DESCRIPTION
		"The pppoeCallTable displays all currently active PPPoE
                calls (incoming and outgoing). Only the system can add
                or remove entries to this table.

                Creating entries: Entries are added when an outgoing
                call is made or when an incoming call is connected.

                Deleting entries: Entries are removed once the
                respective call is disconnected."
	::= { pppoe 1 }

	pppoeCallEntry OBJECT-TYPE
	    SYNTAX  PppoeCallEntry
	    ACCESS  not-accessible
	    STATUS  mandatory
	    DESCRIPTION
		""
	    INDEX   { pppoeCallId }
	::= { pppoeCallTable 1 }

	PppoeCallEntry ::=
	    SEQUENCE {
		pppoeCallId				INTEGER,
		pppoeCallDirection			INTEGER,
		pppoeCallAge				TimeTicks,
		pppoeCallState				INTEGER,
		pppoeCallRemotePhysAddress		PhysAddress,
		pppoeCallLocalPhysAddress		PhysAddress,
		pppoeCallAcName				DisplayString,
		pppoeCallService			DisplayString,
		pppoeCallReceivedPackets		Counter,
		pppoeCallReceivedOctets			Counter,
		pppoeCallReceivedErrors			Counter,
		pppoeCallTransmitPackets		Counter,
		pppoeCallTransmitOctets			Counter,
		pppoeCallTransmitErrors			Counter,
		pppoeCallInfo                           DisplayString,
		pppoeCallSessionId			INTEGER,
		pppoeCallEthIfIndex			INTEGER,
		pppoeCallAssociatedIfIndex		INTEGER
	    }

	pppoeCallId OBJECT-TYPE
	    SYNTAX  INTEGER
	    ACCESS  read-only
	    STATUS  mandatory

	    DESCRIPTION
		"System internal and unique ID for the related PPPoE call."
	::= { pppoeCallEntry 1 }

	pppoeCallDirection OBJECT-TYPE
	    SYNTAX  INTEGER {
		incoming(1),
		outgoing(2)
	    }
	    ACCESS  read-only
	    STATUS  mandatory

	    DESCRIPTION
		"Direction of the PPPoE call, incoming(1) or outgoing(2)."
	    DEFVAL { outgoing }
	::= { pppoeCallEntry 2 }

	pppoeCallAge OBJECT-TYPE
	    SYNTAX  TimeTicks
	    ACCESS  read-only
	    STATUS  mandatory

	    DESCRIPTION
		"The age of the call. For outgoing calls, the time since
                the call began, or for incoming calls, the time since the
                call was received. The format is in hh:mm:ss.00."
	::= { pppoeCallEntry 3 }

	pppoeCallState OBJECT-TYPE
	    SYNTAX  INTEGER {
		idle(1),
		wait-pado(2),
		wait-padr(3),
		wait-pads(4),
		established(5),
		terminated(6),
		close(7),
		delete(8)
	    }
	    ACCESS  read-write
	    STATUS  mandatory

	    DESCRIPTION
		"The state of the PPPoE discovery stage according RFC 2516."
	    DEFVAL { idle }
	::= { pppoeCallEntry 4 }

	pppoeCallRemotePhysAddress OBJECT-TYPE
	    SYNTAX  PhysAddress
	    ACCESS  read-only
	    STATUS  mandatory

	    DESCRIPTION
		"Peer's Ethernet address."
	::= { pppoeCallEntry 5 }

	pppoeCallLocalPhysAddress OBJECT-TYPE
	    SYNTAX  PhysAddress
	    ACCESS  read-only
	    STATUS  mandatory

	    DESCRIPTION
		"Local Ethernet Address."
	::= { pppoeCallEntry 6 }

	pppoeCallAcName OBJECT-TYPE
	    SYNTAX  DisplayString
	    ACCESS  read-only
	    STATUS  mandatory

	    DESCRIPTION
		"The PPPoE access concentrator's name."
	::= { pppoeCallEntry 7 }

	pppoeCallService OBJECT-TYPE
	    SYNTAX  DisplayString
	    ACCESS  read-only
	    STATUS  mandatory

	    DESCRIPTION
		"The PPPoE service name, indicating the service the Host is
		 requesting."
	::= { pppoeCallEntry 8 }

	pppoeCallReceivedPackets OBJECT-TYPE
	    SYNTAX  Counter
	    ACCESS  read-only
	    STATUS  mandatory

	    DESCRIPTION
		"Count of received valid GRE-encapsulated packets."
	::= { pppoeCallEntry 9 }

	pppoeCallReceivedOctets OBJECT-TYPE
	    SYNTAX  Counter
	    ACCESS  read-only
	    STATUS  mandatory

	    DESCRIPTION
		"Count of received valid Octets."
	::= { pppoeCallEntry 10 }

	pppoeCallReceivedErrors OBJECT-TYPE
	    SYNTAX  Counter
	    ACCESS  read-only
	    STATUS  mandatory

	    DESCRIPTION
		"Count of received invalid GRE-encapsulated packets."
	::= { pppoeCallEntry 11 }

	pppoeCallTransmitPackets OBJECT-TYPE
	    SYNTAX  Counter
	    ACCESS  read-only
	    STATUS  mandatory

	    DESCRIPTION
		"Count of transmitted GRE-encapsulated packets."
	::= { pppoeCallEntry 12 }

	pppoeCallTransmitOctets OBJECT-TYPE
	    SYNTAX  Counter
	    ACCESS  read-only
	    STATUS  mandatory

	    DESCRIPTION
		"Count of transmitted Octets."
	::= { pppoeCallEntry 13 }

	pppoeCallTransmitErrors OBJECT-TYPE
	    SYNTAX  Counter
	    ACCESS  read-only
	    STATUS  mandatory

	    DESCRIPTION
		"Count of transmit errors."
	::= { pppoeCallEntry 14 }

        pppoeCallInfo OBJECT-TYPE
            SYNTAX  DisplayString
            ACCESS  read-only
            STATUS  mandatory

            DESCRIPTION
                "Additional information to identify the PPPoE call"
        ::= { pppoeCallEntry 15 }

        pppoeCallSessionId OBJECT-TYPE
            SYNTAX  INTEGER
            ACCESS  read-only
            STATUS  mandatory

            DESCRIPTION
                "The PPPoE session ID, assigned via PPPoE Active Discovery
		Session-Confirmation (PADS)."
        ::= { pppoeCallEntry 16 }

        pppoeCallEthIfIndex OBJECT-TYPE
            SYNTAX  INTEGER
            ACCESS  read-only
            STATUS  mandatory

            DESCRIPTION
                "The interface index (ifIndex) of the associated Ethernet
		device."
        ::= { pppoeCallEntry 17 }

        pppoeCallAssociatedIfIndex OBJECT-TYPE
            SYNTAX  INTEGER
            ACCESS  read-only
            STATUS  mandatory

            DESCRIPTION
                "The index of the associated virtual interface."
        ::= { pppoeCallEntry 18 }


    -- pppoeCreditsTable

	pppoeCreditsTable OBJECT-TYPE
	    SYNTAX  SEQUENCE OF PppoeCreditsEntry
	    ACCESS  not-accessible
	    STATUS  mandatory
	    DESCRIPTION
		"The pppoeCreditsTable contains informations about current
		 used resources and maximum allowed 'PPPoE-Service'-dependent
		 resources.
		 during a specified interval subsystem.

		 Creating entries: Entries are added by the user.

                 Deleting entries: Entries are removed by setting an
                 entry's pppoeCreditsSurveillance object to 'delete'."
	::= { pppoe 2 }

	pppoeCreditsEntry OBJECT-TYPE
	    SYNTAX  PppoeCreditsEntry
	    ACCESS  not-accessible
	    STATUS  mandatory
	    DESCRIPTION
		""
	    INDEX   { pppoeCreditsService }
	::= { pppoeCreditsTable 1 }

	PppoeCreditsEntry ::=
	    SEQUENCE {
		pppoeCreditsService		DisplayString,
		pppoeCreditsSurveillance	INTEGER,
		pppoeCreditsMeasuretime		INTEGER,
		pppoeCreditsMaxInCon		INTEGER,
		pppoeCreditsMaxOutCon		INTEGER,
		pppoeCreditsMaxInDuration	INTEGER,
		pppoeCreditsMaxOutDuration	INTEGER,
		pppoeCreditsTimeleft		INTEGER,
		pppoeCreditsCurrentInCon	INTEGER,
		pppoeCreditsCurrentOutCon	INTEGER,
		pppoeCreditsTotalInCon		INTEGER,
		pppoeCreditsTotalOutCon		INTEGER,
		pppoeCreditsTotalInDuration	INTEGER,
		pppoeCreditsTotalOutDuration	INTEGER,
		pppoeCreditsCurrentAccount	INTEGER
	    }

	pppoeCreditsService OBJECT-TYPE
	    SYNTAX  DisplayString
	    ACCESS  read-write
	    STATUS  mandatory

	    DESCRIPTION
		"The PPPoE service name, indicating the service the Host is
		 requesting."
	::= { pppoeCreditsEntry 1 }

	pppoeCreditsSurveillance OBJECT-TYPE
	    SYNTAX  INTEGER {
	        off(1), on(2), delete(3)
	    }
	    ACCESS  read-write
	    STATUS  mandatory

	    DESCRIPTION
		"Surveillance on or off."
	    DEFVAL { off }
	::= { pppoeCreditsEntry 2 }

	pppoeCreditsMeasuretime OBJECT-TYPE
	    SYNTAX  INTEGER
	    ACCESS  read-write
	    STATUS  mandatory

	    DESCRIPTION
		"Time of one observation interval in seconds."
	    DEFVAL { 86400 }
	::= { pppoeCreditsEntry 3 }

	pppoeCreditsMaxInCon OBJECT-TYPE
	    SYNTAX  INTEGER
	    ACCESS  read-write
	    STATUS  mandatory

	    DESCRIPTION
		"Maximum number of allowed incoming connections during the
		 observation interval. -1 disables this limit."
	    DEFVAL { -1 }
	::= { pppoeCreditsEntry 4 }

	pppoeCreditsMaxOutCon OBJECT-TYPE
	    SYNTAX  INTEGER
	    ACCESS  read-write
	    STATUS  mandatory

	    DESCRIPTION
		"Maximum number of allowed outgoing connections during the
		 observation interval. -1 disables this limit."
	    DEFVAL { 1000 }
	::= { pppoeCreditsEntry 5 }

	pppoeCreditsMaxInDuration OBJECT-TYPE
	    SYNTAX  INTEGER
	    ACCESS  read-write
	    STATUS  mandatory

	    DESCRIPTION
		"Maximum connect time for incoming connections in
		 seconds during the observation interval. -1 disables this
		 limit."
	    DEFVAL { -1 }
	::= { pppoeCreditsEntry 6 }

	pppoeCreditsMaxOutDuration OBJECT-TYPE
	    SYNTAX  INTEGER
	    ACCESS  read-write
	    STATUS  mandatory

	    DESCRIPTION
		"Maximum connect time for outgoing connections in
		 seconds during the observation interval. -1 disables this
		 limit"
		DEFVAL { 28800 }
	::= { pppoeCreditsEntry 7 }

	pppoeCreditsTimeleft OBJECT-TYPE
	    SYNTAX  INTEGER
	    ACCESS  read-write
	    STATUS  mandatory

	    DESCRIPTION
		"Time in seconds left in current interval.
		 Writing to Timeleft will restart the observation
		 interval."
	::= { pppoeCreditsEntry 8 }


	pppoeCreditsCurrentInCon OBJECT-TYPE
	    SYNTAX  INTEGER
	    ACCESS  read-only
	    STATUS  mandatory

	    DESCRIPTION
		"Current number of incoming connections."
	::= { pppoeCreditsEntry 9 }

	pppoeCreditsCurrentOutCon OBJECT-TYPE
	    SYNTAX  INTEGER
	    ACCESS  read-only
	    STATUS  mandatory

	    DESCRIPTION
		"Current number of outgoing connections."
	::= { pppoeCreditsEntry 10 }
	pppoeCreditsTotalInCon OBJECT-TYPE
	    SYNTAX  INTEGER
	    ACCESS  read-only
	    STATUS  mandatory

	    DESCRIPTION
		"Total count of incoming connections during
		 the observation interval."
	::= { pppoeCreditsEntry 11 }

	pppoeCreditsTotalOutCon OBJECT-TYPE
	    SYNTAX  INTEGER
	    ACCESS  read-only
	    STATUS  mandatory

	    DESCRIPTION
		"Total count of outgoing connections during
		 the observation interval."
	::= { pppoeCreditsEntry 12 }

	pppoeCreditsTotalInDuration OBJECT-TYPE
	    SYNTAX  INTEGER
	    ACCESS  read-only
	    STATUS  mandatory

	    DESCRIPTION
		"Total connect time of incoming connections
		 during the observation interval."
	::= { pppoeCreditsEntry 13 }

	pppoeCreditsTotalOutDuration OBJECT-TYPE
	    SYNTAX  INTEGER
	    ACCESS  read-only
	    STATUS  mandatory

	    DESCRIPTION
		"Total connect time of outgoing connections
		during the observation interval."
	::= { pppoeCreditsEntry 14 }

	pppoeCreditsCurrentAccount OBJECT-TYPE
	    SYNTAX  INTEGER (0..100)
	    ACCESS  read-only
	    STATUS  mandatory

	    DESCRIPTION
		"Total connect time of all outgoing connections during
		 the observation interval calculated in percent of
		 'pppoeCreditsMaxOutDuration'."
	::= { pppoeCreditsEntry 15 }


    -- pppoePassThroughTable

	pppoePassThroughTable OBJECT-TYPE
	    SYNTAX  SEQUENCE OF PppoePassThroughEntry
	    ACCESS  not-accessible
	    STATUS  mandatory
	    DESCRIPTION
		"The pppoePassThroughTable is used to enable the PPPoE
		mode between the two specified Ethernet interfaces.

		Creating entries: Entries are added by the user.

                Deleting entries: Entries are removed once the
                respective variable pppoePassThroughStatus is
		set to delete(3)."
	::= { pppoe 5 }

	pppoePassThroughEntry OBJECT-TYPE
	    SYNTAX  PppoePassThroughEntry
	    ACCESS  not-accessible
	    STATUS  mandatory
	    DESCRIPTION
		""
	    INDEX   { pppoePassThroughEthIfIndex1, pppoePassThroughEthIfIndex2 }
	::= { pppoePassThroughTable 1 }

	PppoePassThroughEntry ::=
	    SEQUENCE {
		pppoePassThroughEthIfIndex1		INTEGER,
		pppoePassThroughEthIfIndex2		INTEGER,
		pppoePassThroughStatus			INTEGER
	    }

	pppoePassThroughEthIfIndex1 OBJECT-TYPE
	    SYNTAX  INTEGER
	    ACCESS  read-write
	    STATUS  mandatory

	    DESCRIPTION
                "The interface index (ifIndex) of the first associated
		 Ethernet interface."
	::= { pppoePassThroughEntry 1 }

	pppoePassThroughEthIfIndex2 OBJECT-TYPE
	    SYNTAX  INTEGER
	    ACCESS  read-write
	    STATUS  mandatory

	    DESCRIPTION
                "The interface index (ifIndex) of the secondassociated
		 Ethernet interface."
	::= { pppoePassThroughEntry 2 }

	pppoePassThroughStatus OBJECT-TYPE
	    SYNTAX  INTEGER {
		enabled(1),
		disabled(2),
		delete(3)
	    }
	    ACCESS  read-write
	    STATUS  mandatory

	    DESCRIPTION
		"The administrative status of this entry."
	    DEFVAL { enabled }
	::= { pppoePassThroughEntry 3 }


END
