-- This file is corresponding to Release 9.1.10.101 from 2014/08/11 00:00:00


---------------------------------------------------------------------------
-- (C)opyright 2011-2014 bintec elmeg GmbH
-- $RCSfile: mib-hwaccel,v $
-- $Revision: 1.7 $
-- $Date: 2014-02-07 11:21:02 $
---------------------------------------------------------------------------

FEC-HWACCEL-MIB DEFINITIONS ::= BEGIN

IMPORTS
    MODULE-IDENTITY, OBJECT-TYPE, NOTIFICATION-TYPE, enterprises,
    TimeTicks, Counter32, Gauge32, snmpModules, mib-2, Unsigned32, Counter64
        FROM SNMPv2-SMI
    DisplayString, TestAndIncr, TimeStamp
        FROM SNMPv2-TC
    MODULE-COMPLIANCE, OBJECT-GROUP, NOTIFICATION-GROUP
        FROM SNMPv2-CONF
    Date, HexValue, BitValue, bibo
        FROM BINTEC-MIB;

---------------------------------------------------------------------------

hwAccelMIB MODULE-IDENTITY
    LAST-UPDATED "201101200000Z"
    ORGANIZATION "bintec elmeg GmbH"
    CONTACT-INFO "EMail:   info@bintec-elmeg.com
                  Web:     www.bintec-elmeg.com"
    DESCRIPTION  "Management Information for the Data Encryption Acceleration
    		  Subsystem"

    ::= { bibo 63 }

hwAccelStat OBJECT IDENTIFIER
	::= { hwAccelMIB 1 }
---------------------------------------------------------------------------
-- HW Accelerator Statistics Table

	hwAccelStatTable OBJECT-TYPE
            SYNTAX  SEQUENCE OF HwAccelStatEntry
            MAX-ACCESS  not-accessible
            STATUS  current
            DESCRIPTION
		"This table contains the list of HW accelerators and their statistics."
	::= { hwAccelStat 1 }

	hwAccelStatEntry OBJECT-TYPE
            SYNTAX  HwAccelStatEntry
            MAX-ACCESS  not-accessible
            STATUS  current
            DESCRIPTION
		"This object contains a HW accelerator statistics."
	    INDEX   {
		hwAccelStatSlot,
		hwAccelStatUnit
	    }
            ::= { hwAccelStatTable 1 }

 	HwAccelStatEntry ::=
            SEQUENCE {
	        hwAccelStatSlot			INTEGER,
	        hwAccelStatUnit			INTEGER,
		hwAccelStatErrors		Counter32,
		hwAccelStatLastError		TimeTicks,
		hwAccelStatResets		Counter32,
		hwAccelStatLastReset		TimeTicks
            }

	hwAccelStatSlot OBJECT-TYPE
	    SYNTAX INTEGER
            MAX-ACCESS  read-only
            STATUS  current
            DESCRIPTION
		 "The slot number of this HW accelerator unit."
	::= { hwAccelStatEntry 1 }

	hwAccelStatUnit OBJECT-TYPE
	    SYNTAX INTEGER
            MAX-ACCESS  read-only
            STATUS  current
            DESCRIPTION
		 "The unit number of this HW accelerator unit."
	::= { hwAccelStatEntry 2 }

	hwAccelStatErrors OBJECT-TYPE
	    SYNTAX Counter32
            MAX-ACCESS  read-only
            STATUS  current
            DESCRIPTION
		 "The number of errors for this HW accelerator unit."
	::= { hwAccelStatEntry 3 }

        hwAccelStatLastError OBJECT-TYPE
	    SYNTAX TimeTicks
            MAX-ACCESS  read-only
            STATUS  current
            DESCRIPTION
		 "The time passed since the last error for this HW
		 accelerator unit."
	::= { hwAccelStatEntry 4 }

        hwAccelStatResets OBJECT-TYPE
	    SYNTAX Counter32
            MAX-ACCESS  read-only
            STATUS  current
            DESCRIPTION
		 "The number of resets for this HW accelerator unit."
	::= { hwAccelStatEntry 5 }

    hwAccelStatLastReset OBJECT-TYPE
	    SYNTAX TimeTicks
            MAX-ACCESS  read-only
            STATUS  current
            DESCRIPTION
		 "The time passed since the last HW accelerator unit reset."
	::= { hwAccelStatEntry 6 }


-- HW Accelerator Channel Capability Table

	hwAccelChanCapTable OBJECT-TYPE
            SYNTAX  SEQUENCE OF HwAccelChanCapEntry
            MAX-ACCESS  not-accessible
            STATUS  current
            DESCRIPTION
		"This table contains the list of HW accelerator channels and their capabilities."
	::= { hwAccelStat 2 }

	hwAccelChanCapEntry OBJECT-TYPE
            SYNTAX  HwAccelChanCapEntry
            MAX-ACCESS  not-accessible
            STATUS  current
            DESCRIPTION
		"This object contains a HW accelerator channel capability."
	    INDEX   {
		hwAccelChanCapSlot,
		hwAccelChanCapUnit,
		hwAccelChanCapChan,
		hwAccelChanCapCapability
	    }
            ::= { hwAccelChanCapTable 1 }

 	HwAccelChanCapEntry ::=
            SEQUENCE {
	        hwAccelChanCapSlot			INTEGER,
	        hwAccelChanCapUnit			INTEGER,
	        hwAccelChanCapChan			INTEGER,
		hwAccelChanCapCapability		INTEGER,
		hwAccelChanCapMinKeySize		INTEGER,
		hwAccelChanCapMaxKeySize		INTEGER
            }

	hwAccelChanCapSlot OBJECT-TYPE
	    SYNTAX INTEGER
            MAX-ACCESS  read-only
            STATUS  current
            DESCRIPTION
		 "The slot number of this HW accelerator channel."
	::= { hwAccelChanCapEntry 1 }

	hwAccelChanCapUnit OBJECT-TYPE
	    SYNTAX INTEGER
            MAX-ACCESS  read-only
            STATUS  current
            DESCRIPTION
		 "The unit number of this HW accelerator channel."
	::= { hwAccelChanCapEntry 2 }


	hwAccelChanCapChan OBJECT-TYPE
	    SYNTAX INTEGER
            MAX-ACCESS  read-only
            STATUS  current
            DESCRIPTION
		 "The channel number of this HW accelerator channel."
	::= { hwAccelChanCapEntry 3 }

	hwAccelChanCapCapability OBJECT-TYPE
	    SYNTAX INTEGER {
	         des-cbc(1),
		 des3-cbc(2),
		 aes-cbc(3),
		 rc4(4),
		 md5(5),
		 sha1(6),
		 rsa(7),
		 rng(8)
	    }
            MAX-ACCESS  read-only
            STATUS  current
            DESCRIPTION
		 "The supported capability of this HW accelerator."
	::= { hwAccelChanCapEntry 4}

        hwAccelChanCapMinKeySize OBJECT-TYPE
	    SYNTAX INTEGER (0..2560)
	    UNITS  "bits"
            MAX-ACCESS  read-only
            STATUS  current
	    DESCRIPTION
		"This object specifies the minimum key or field size used with this capability.
		 A key size of 0 means that a explicity key size is not applicable."
	::= { hwAccelChanCapEntry 5}

        hwAccelChanCapMaxKeySize OBJECT-TYPE
	    SYNTAX INTEGER (0..2560)
	    UNITS  "bits"
            MAX-ACCESS  read-only
            STATUS  current
	    DESCRIPTION
		"This object specifies the maximum key or field size used with this capability.
		 A key size of 0 means that a explicity key size is not applicable."
	::= { hwAccelChanCapEntry 6}

-- End HW Accelerator Channel Capability Table


-- HW Accelerator Channel Statistics Table

	hwAccelChanStatTable OBJECT-TYPE
            SYNTAX  SEQUENCE OF HwAccelChanStatEntry
            MAX-ACCESS  not-accessible
            STATUS  current
            DESCRIPTION
		"This table contains statistic info for a HW accelerator channel."
	::= { hwAccelStat 3 }

	hwAccelChanStatEntry OBJECT-TYPE
            SYNTAX  HwAccelChanStatEntry
            MAX-ACCESS  not-accessible
            STATUS  current
            DESCRIPTION
		"This object contains the statistic info for a HW accelerator channel."
	    INDEX   {
		hwAccelChanStatSlot,
		hwAccelChanStatUnit,
		hwAccelChanStatChan
	    }
	    ::= { hwAccelChanStatTable 1 }

        HwAccelChanStatEntry ::=
            SEQUENCE {
		hwAccelChanStatSlot		INTEGER,
		hwAccelChanStatUnit		INTEGER,
		hwAccelChanStatChan		INTEGER,
		hwAccelChanStatCurrSessions	Counter32,
		hwAccelChanStatMaxSessions	Counter32,
		hwAccelChanStatErrors		Counter32,
		hwAccelChanStatLastError	TimeTicks,
		hwAccelChanStatResets		Counter32,
		hwAccelChanStatLastReset	TimeTicks,
		hwAccelChanStatDoneOverflows	Counter32,
		hwAccelChanStatLastDoneOverflow	TimeTicks
	    }

	hwAccelChanStatSlot OBJECT-TYPE
	    SYNTAX INTEGER
            MAX-ACCESS  read-only
            STATUS  current
            DESCRIPTION
		 "The slot number of this HW accelerator entry."
	::= { hwAccelChanStatEntry 1 }

	hwAccelChanStatUnit OBJECT-TYPE
	    SYNTAX INTEGER
            MAX-ACCESS  read-only
            STATUS  current
            DESCRIPTION
		 "The unit number of this HW accelerator entry."
	::= { hwAccelChanStatEntry 2 }

	hwAccelChanStatChan OBJECT-TYPE
	    SYNTAX INTEGER
            MAX-ACCESS  read-only
            STATUS  current
            DESCRIPTION
		 "The channel number of this HW accelerator entry."
	::= { hwAccelChanStatEntry 3 }

    hwAccelChanStatCurrSessions OBJECT-TYPE
	    SYNTAX Counter32
            MAX-ACCESS  read-only
            STATUS  current
            DESCRIPTION
		 "The current number of sessions handled by this HW accelerator
		  channel."
	::= { hwAccelChanStatEntry 4 }

    hwAccelChanStatMaxSessions OBJECT-TYPE
	    SYNTAX Counter32
            MAX-ACCESS  read-only
            STATUS  current
            DESCRIPTION
		 "The maximum number of sessions handled by this HW accelerator
		  channel."
	::= { hwAccelChanStatEntry 5 }

    hwAccelChanStatErrors OBJECT-TYPE
	    SYNTAX Counter32
            MAX-ACCESS  read-only
            STATUS  current
            DESCRIPTION
		 "The number of errors for this HW accelerator channel."
	::= { hwAccelChanStatEntry 9 }

        hwAccelChanStatLastError OBJECT-TYPE
	    SYNTAX TimeTicks
            MAX-ACCESS  read-only
            STATUS  current
            DESCRIPTION
		 "The time passed since the last error for this HW
		 accelerator channel."
	::= { hwAccelChanStatEntry 10 }

        hwAccelChanStatResets OBJECT-TYPE
	    SYNTAX Counter32
            MAX-ACCESS  read-only
            STATUS  current
            DESCRIPTION
		 "The number of HW accelerator channel resets."
	::= { hwAccelChanStatEntry 11 }

    hwAccelChanStatLastReset OBJECT-TYPE
	    SYNTAX TimeTicks
            MAX-ACCESS  read-only
            STATUS  current
            DESCRIPTION
		 "The time passed since the last HW accelerator channel reset."
	::= { hwAccelChanStatEntry 12 }

    hwAccelChanStatDoneOverflows OBJECT-TYPE
	    SYNTAX Counter32
            MAX-ACCESS  read-only
            STATUS  current
            DESCRIPTION
		 "The number of done overflow conditions for this HW accelerator channel."
	::= { hwAccelChanStatEntry 13 }

        hwAccelChanStatLastDoneOverflow OBJECT-TYPE
	    SYNTAX TimeTicks
            MAX-ACCESS  read-only
            STATUS  current
            DESCRIPTION
		 "The time passed since the last done overflow condition for this HW
		 accelerator channel."
	::= { hwAccelChanStatEntry 14 }

-- End HW Accelerator Channel Statistics Table

-- HW Accelerator Channel Directional Statistics Table

	hwAccelChanDirStatTable OBJECT-TYPE
            SYNTAX  SEQUENCE OF HwAccelChanDirStatEntry
            MAX-ACCESS  not-accessible
            STATUS  current
            DESCRIPTION
		"This table contains directional statistic info for a HW accelerator
		 channel."
	::= { hwAccelStat 4 }

	hwAccelChanDirStatEntry OBJECT-TYPE
            SYNTAX  HwAccelChanDirStatEntry
            MAX-ACCESS  not-accessible
            STATUS  current
            DESCRIPTION
		"This object contains the directional statistic info for a
		 HW accelerator channel."
	    INDEX   {
		hwAccelChanDirStatSlot,
		hwAccelChanDirStatUnit,
		hwAccelChanDirStatChan,
		hwAccelChanDirStatDirection
	    }
	    ::= { hwAccelChanDirStatTable 1 }

        HwAccelChanDirStatEntry ::=
            SEQUENCE {
		hwAccelChanDirStatSlot			INTEGER,
		hwAccelChanDirStatUnit			INTEGER,
		hwAccelChanDirStatChan			INTEGER,
		hwAccelChanDirStatDirection		INTEGER,
		hwAccelChanDirStatPkts			Counter32,
		hwAccelChanDirStatPath1Pkts		Counter32,
		hwAccelChanDirStatPath2Pkts		Counter32,
		hwAccelChanDirStatDiscardedPkts		Counter32,
		hwAccelChanDirStatLastDiscarded		TimeTicks,
		hwAccelChanDirStatErrorPkts		Counter32,
		hwAccelChanDirStatLastError		TimeTicks,
		hwAccelChanDirStatDescrs		INTEGER,
		hwAccelChanDirStatCurrBusyDescrs	Gauge32,
		hwAccelChanDirStatMaxBusyDescrs		Counter32,
		hwAccelChanDirStatOverflows		Counter32,
		hwAccelChanDirStatLastOverflow		TimeTicks
	    }

	hwAccelChanDirStatSlot OBJECT-TYPE
	    SYNTAX INTEGER
            MAX-ACCESS  read-only
            STATUS  current
            DESCRIPTION
		 "The slot number of this HW accelerator direction entry."
	::= { hwAccelChanDirStatEntry 1 }

	hwAccelChanDirStatUnit OBJECT-TYPE
	    SYNTAX INTEGER
            MAX-ACCESS  read-only
            STATUS  current
            DESCRIPTION
		 "The unit number of this HW accelerator direction entry."
	::= { hwAccelChanDirStatEntry 2 }

	hwAccelChanDirStatChan OBJECT-TYPE
	    SYNTAX INTEGER
            MAX-ACCESS  read-only
            STATUS  current
            DESCRIPTION
		 "The channel number of this HW accelerator direction entry."
	::= { hwAccelChanDirStatEntry 3 }

	hwAccelChanDirStatDirection OBJECT-TYPE
	    SYNTAX INTEGER { decryption(1), encryption(2) }
            MAX-ACCESS  read-only
            STATUS  current
            DESCRIPTION
		 "The encryption direction of this HW accelerator channel
		  direction entry."
	::= { hwAccelChanDirStatEntry 4 }

    hwAccelChanDirStatPkts OBJECT-TYPE
	    SYNTAX Counter32
            MAX-ACCESS  read-only
            STATUS  current
            DESCRIPTION
		 "The total number of packets for this HW accelerator channel
		   direction."
	::= { hwAccelChanDirStatEntry 5 }

    hwAccelChanDirStatPath1Pkts OBJECT-TYPE
	    SYNTAX Counter32
            MAX-ACCESS  read-only
            STATUS  current
            DESCRIPTION
		 "The total number of packets for this HW accelerator
		  channel direction seen for path 1."
	::= { hwAccelChanDirStatEntry 6 }

    hwAccelChanDirStatPath2Pkts OBJECT-TYPE
	    SYNTAX Counter32
            MAX-ACCESS  read-only
            STATUS  current
            DESCRIPTION
		 "The total number of packets for this HW accelerator
		  channel direction seen for path 2."
	::= { hwAccelChanDirStatEntry 7 }

        hwAccelChanDirStatDiscardedPkts OBJECT-TYPE
	    SYNTAX Counter32
            MAX-ACCESS  read-only
            STATUS  current
            DESCRIPTION
		 "The total number of packets discarded due to resource
		  problems for this HW accelerator channel direction."
	::= { hwAccelChanDirStatEntry 12 }

    hwAccelChanDirStatLastDiscarded OBJECT-TYPE
	    SYNTAX TimeTicks
            MAX-ACCESS  read-only
            STATUS  current
            DESCRIPTION
		 "The time passed since the last packet was discarded for
		  this HW accelerator channel direction."
	::= { hwAccelChanDirStatEntry 13 }

        hwAccelChanDirStatErrorPkts OBJECT-TYPE
	    SYNTAX Counter32
            MAX-ACCESS  read-only
            STATUS  current
            DESCRIPTION
		 "The number of packets which caused errors on this
		  HW accelerator channel direction."
	::= { hwAccelChanDirStatEntry 14 }

    hwAccelChanDirStatLastError OBJECT-TYPE
	    SYNTAX TimeTicks
            MAX-ACCESS  read-only
            STATUS  current
            DESCRIPTION
		 "The time passed since the last erroneous packet on
		  this HW accelerator channel direction."
	::= { hwAccelChanDirStatEntry 15 }


    hwAccelChanDirStatDescrs OBJECT-TYPE
	    SYNTAX INTEGER
            MAX-ACCESS  read-only
            STATUS  current
            DESCRIPTION
		 "The number of descriptors for this HW accelerator channel
		  direction."
	::= { hwAccelChanDirStatEntry 16 }

    hwAccelChanDirStatCurrBusyDescrs OBJECT-TYPE
	    SYNTAX Gauge32
            MAX-ACCESS  read-only
            STATUS  current
            DESCRIPTION
		 "The number of descriptors currently in use for this
		  HW accelerator channel direction."
	::= { hwAccelChanDirStatEntry 17 }

    hwAccelChanDirStatMaxBusyDescrs OBJECT-TYPE
	    SYNTAX Counter32
            MAX-ACCESS  read-only
            STATUS  current
            DESCRIPTION
		 "The maximum number of descriptors in use for this
		  HW accelerator channel direction."
	::= { hwAccelChanDirStatEntry 18 }

    hwAccelChanDirStatOverflows OBJECT-TYPE
	    SYNTAX Counter32
            MAX-ACCESS  read-only
            STATUS  current
            DESCRIPTION
		 "The number of times packets were discarded because no
		  free descriptor was found for this HW accelerator
		  channel direction."
	::= { hwAccelChanDirStatEntry 19 }

    hwAccelChanDirStatLastOverflow OBJECT-TYPE
	    SYNTAX TimeTicks
            MAX-ACCESS  read-only
            STATUS  current
            DESCRIPTION
		 "The time passed since the last descriptor overflow occured for
		  this HW accelerator channel direction."
	::= { hwAccelChanDirStatEntry 20 }

-- End HW Accelerator Channel Directional Statistics Table

END
