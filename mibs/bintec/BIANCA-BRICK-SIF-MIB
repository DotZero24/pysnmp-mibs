-- This file is corresponding to Release 9.1.10.101 from 2014/08/11 00:00:00


-- (C)opyright 1991-2014 bintec elmeg GmbH, All Rights Reserved
-- $RCSfile: mibsif,v $
-- $Revision: 1.33 $

BIANCA-BRICK-SIF-MIB DEFINITIONS ::= BEGIN

        IMPORTS
            IpAddress, Counter, enterprises
                FROM RFC1155-SMI

            DisplayString
                FROM RFC1158-MIB

            OBJECT-TYPE
                FROM RFC-1212;

    bintec      OBJECT IDENTIFIER ::= { enterprises 272 }
    bibo        OBJECT IDENTIFIER ::= { bintec 4 }
    biboip      OBJECT IDENTIFIER
        ::= { bibo 5 }

-- Stateful Inspection MIB

	ipSifAliasAddressTable OBJECT-TYPE
	    SYNTAX SEQUENCE OF IpSifAliasAddressEntry
            ACCESS not-accessible
            STATUS mandatory
            DESCRIPTION
                "Contains a alias Address Entry Index,Ip,Mask,Interface "
        ::= { biboip 28 }

        ipSifAliasAddressEntry OBJECT-TYPE
            SYNTAX IpSifAliasAddressEntry
            ACCESS not-accessible
            STATUS mandatory
            DESCRIPTION
                "Contents a Stateful inspection Firewall description for a
		alias Name"
            INDEX { ipSifAliasAddressAlias }
        ::= { ipSifAliasAddressTable 1 }


	IpSifAliasAddressEntry ::=
            SEQUENCE {
	        ipSifAliasAddressIndex		INTEGER,
                ipSifAliasAddressAlias		DisplayString,
		ipSifAliasAddressAddress   	IpAddress,
		ipSifAliasAddressMask		IpAddress,
		ipSifAliasAddressRange          INTEGER,
		ipSifAliasAddressInterface	INTEGER,
		ipSifAliasAddressMode           INTEGER,
		ipSifAliasAddressGroup          INTEGER
           }


	ipSifAliasAddressIndex OBJECT-TYPE
	    SYNTAX INTEGER
            ACCESS read-only
            STATUS mandatory
            DESCRIPTION
                "The Index for the address alias"
	    DEFVAL { 0 }
        ::= { ipSifAliasAddressEntry 1 }


        ipSifAliasAddressAlias OBJECT-TYPE
            SYNTAX DisplayString
            ACCESS read-write
            STATUS mandatory
            DESCRIPTION
                "Alias Name for the Address Entry"
            DEFVAL { "" }
        ::= { ipSifAliasAddressEntry 2 }

        ipSifAliasAddressAddress OBJECT-TYPE
            SYNTAX IpAddress
            ACCESS read-write
            STATUS mandatory
            DESCRIPTION
                "The ip-address for the Alias"
        ::= { ipSifAliasAddressEntry 3 }

        ipSifAliasAddressMask OBJECT-TYPE
            SYNTAX IpAddress
            ACCESS read-write
            STATUS mandatory
            DESCRIPTION
                "The ip Mask for the Alias"
        ::= { ipSifAliasAddressEntry 4 }


        ipSifAliasAddressInterface OBJECT-TYPE
            SYNTAX INTEGER
            ACCESS read-write
            STATUS mandatory
            DESCRIPTION
                "The interface index for the alias"
	    DEFVAL { 0 }
        ::= { ipSifAliasAddressEntry 5 }


        ipSifAliasAddressMode OBJECT-TYPE
            SYNTAX INTEGER {
	    	interface(1),
		address(2),
		range(3),
		delete(4)
	    }
            ACCESS read-write
            STATUS mandatory
            DESCRIPTION
                "Address or Interface Mode"
	    DEFVAL { 1 }
        ::= { ipSifAliasAddressEntry 6 }


        ipSifAliasAddressRange OBJECT-TYPE
            SYNTAX INTEGER (0..65535)
            ACCESS read-write
            STATUS mandatory
            DESCRIPTION
                "The ip Range for the Alias"
	    DEFVAL { 1 }
        ::= { ipSifAliasAddressEntry 7 }


        ipSifAliasAddressGroup OBJECT-TYPE
            SYNTAX INTEGER
            ACCESS read-write
            STATUS mandatory
            DESCRIPTION
                "For values greater than zero this entry determines the
		 IP address group this entry belongs to, see also
		 ipSifAliasAddressGroupId"
        ::= { ipSifAliasAddressEntry 8 }


	ipSifAliasServiceTable OBJECT-TYPE
	    SYNTAX SEQUENCE OF IpSifAliasServiceEntry
            ACCESS not-accessible
            STATUS mandatory
            DESCRIPTION
                "Contains a alias Service Entry Protocol,Port,Range "
        ::= { biboip 29 }


	ipSifAliasServiceEntry OBJECT-TYPE
	    SYNTAX IpSifAliasServiceEntry
            ACCESS not-accessible
            STATUS mandatory
            DESCRIPTION
                "Contains a alias Service Entry Protocol,Port,Range "
            INDEX { ipSifAliasServiceAlias }
        ::= { ipSifAliasServiceTable 1 }


	IpSifAliasServiceEntry ::=
            SEQUENCE {
	        ipSifAliasServiceIndex          INTEGER,
                ipSifAliasServiceAlias		DisplayString,
		ipSifAliasServiceProtocol   	INTEGER,
		ipSifAliasServicePort		INTEGER,
		ipSifAliasServiceRange		INTEGER,
		ipSifAliasServiceType		INTEGER,
		ipSifAliasServiceGroup		INTEGER,
		ipSifAliasServiceSourcePort	INTEGER,
		ipSifAliasServiceSourceRange	INTEGER,
		ipSifAliasServiceIcmpType	INTEGER,
		ipSifAliasServiceIcmpCode	INTEGER
           }

	ipSifAliasServiceIndex OBJECT-TYPE
	    SYNTAX INTEGER
            ACCESS read-only
            STATUS mandatory
            DESCRIPTION
                "The Index for the address alias"
	    DEFVAL { 0 }
        ::= { ipSifAliasServiceEntry 1 }


	ipSifAliasServiceAlias OBJECT-TYPE
	    SYNTAX DisplayString
            ACCESS read-write
            STATUS mandatory
            DESCRIPTION
                "Alias Name for the Service Entry"
            DEFVAL { "" }
        ::= { ipSifAliasServiceEntry 2 }


	ipSifAliasServiceProtocol OBJECT-TYPE
	    SYNTAX INTEGER {
		icmp(1),
		igmp(2),
		ggp(3),
		ip(4),
		tcp(6),
		egp(8),
		igp(9),
		pup(12),
		chaos(16),
		udp(17),
		hmp(20),
		xns-idp(22),
		rdp(27),
		ipv6(41),
		rsvp(46),
		gre(47),
		esp(50),
		ah(51),
		tlsp(56),
		skip(57),
		kryptolan(65),
		iso-ip(80),
		igrp(88),
		ospf(89),
		ipip(94),
		pim(103),
		ipx-in-ip(111),
		vrrp(112),
		l2tp(115),
		local(250),
		internet(251),
		netmeeting(252),
		udptcp(253),
		any(254),
		delete(255),
		dont-verify(256)
    	    }
	    ACCESS read-write
	    STATUS mandatory
	    DESCRIPTION
	    	"The protocol for the Service alias"
	    DEFVAL { any }
	    ::= { ipSifAliasServiceEntry 3 }


	ipSifAliasServicePort OBJECT-TYPE
	    SYNTAX INTEGER ( -1..65535 )
	    ACCESS read-write
	    STATUS mandatory
	    DESCRIPTION
	    	"The Port for the Service Alias."
	    DEFVAL { -1 }
	::= { ipSifAliasServiceEntry 4 }

	ipSifAliasServiceRange OBJECT-TYPE
	    SYNTAX INTEGER ( 1..65536 )
	    ACCESS read-write
	    STATUS mandatory
	    DESCRIPTION
	    	"The Port Range for the Service Alias."
	    DEFVAL { 1 }
	::= { ipSifAliasServiceEntry 5 }

	ipSifAliasServiceType OBJECT-TYPE
	    SYNTAX INTEGER {
		predefined(1), 	-- entry predifined by IP/SIF subsystem
		custom(2)	-- entry created/modified by administrator
	    }
	    ACCESS read-only
	    STATUS mandatory
	    DESCRIPTION
	    	"Specifies wether created by the IP/SIF subsystem itself or
		 created/modified by the administrator."
	    DEFVAL { custom }
	::= { ipSifAliasServiceEntry 6 }

	ipSifAliasServiceGroup OBJECT-TYPE
            SYNTAX INTEGER
	    ACCESS read-write
	    STATUS mandatory
	    DESCRIPTION
                "For values greater than zero this entry determines the
		 IP service group this entry belongs to, see also
		 ipSifAliasServiceGroupId"
	::= { ipSifAliasServiceEntry 7 }

	ipSifAliasServiceSourcePort OBJECT-TYPE
	    SYNTAX INTEGER ( 0..65535 )
	    ACCESS read-write
	    STATUS mandatory
	    DESCRIPTION
	    	"The Source Port for the Service Alias."
	::= { ipSifAliasServiceEntry 8 }

	ipSifAliasServiceSourceRange OBJECT-TYPE
	    SYNTAX INTEGER ( 1..65536 )
	    ACCESS read-write
	    STATUS mandatory
	    DESCRIPTION
	    	"The Source Port Range for the Service Alias."
            DEFVAL { 1 }
	::= { ipSifAliasServiceEntry 9 }

	ipSifAliasServiceIcmpType OBJECT-TYPE
	    SYNTAX INTEGER ( -1..255 )
	    ACCESS read-write
	    STATUS mandatory
	    DESCRIPTION
	    	"The ICMP Type for the Service Alias."
	::= { ipSifAliasServiceEntry 10 }

	ipSifAliasServiceIcmpCode OBJECT-TYPE
	    SYNTAX INTEGER ( -1..255 )
	    ACCESS read-write
	    STATUS mandatory
	    DESCRIPTION
	    	"The ICMP Code for the Service Alias."
	::= { ipSifAliasServiceEntry 11 }



        ipSifAliasTable OBJECT-TYPE
            SYNTAX SEQUENCE OF IpSifAliasEntry
            ACCESS not-accessible
            STATUS mandatory
            DESCRIPTION
                "Contains a Stateful Inspection Firewall (SIF) policy."
        ::= { biboip 30 }

        ipSifAliasEntry OBJECT-TYPE
            SYNTAX IpSifAliasEntry
            ACCESS not-accessible
            STATUS mandatory
            DESCRIPTION
                ""
            INDEX { ipSifAliasOrder }
        ::= { ipSifAliasTable 1 }

        IpSifAliasEntry ::=
            SEQUENCE {
                ipSifAliasOrder		INTEGER,
		ipSifAliasSource   	INTEGER,
		ipSifAliasDestination	INTEGER,
		ipSifAliasService	INTEGER,
		ipSifAliasAction   	INTEGER,
		ipSifAliasStatus   	INTEGER,
		ipSifAliasPriority   	INTEGER,
		ipSifAliasClassId   	INTEGER
           }


	ipSifAliasOrder OBJECT-TYPE
	    SYNTAX INTEGER
	    ACCESS read-write
	    STATUS mandatory
            DESCRIPTION
		"The Order for the Stateful Inspection Entry rule"
	::= { ipSifAliasEntry 1 }


	ipSifAliasSource OBJECT-TYPE
		SYNTAX	INTEGER
		ACCESS	read-write
		STATUS  mandatory
		DESCRIPTION
		   "The alias Source Index for the Entry"
	::= { ipSifAliasEntry 2 }


	ipSifAliasDestination OBJECT-TYPE
		SYNTAX	INTEGER
		ACCESS	read-write
		STATUS  mandatory
		DESCRIPTION
		   "The alias Destination Index for the Entry"
	::= { ipSifAliasEntry 3 }

	ipSifAliasService OBJECT-TYPE
		SYNTAX	INTEGER
		ACCESS	read-write
		STATUS  mandatory
		DESCRIPTION
		   "The alias Protocol/service Index for Entry"
	::= { ipSifAliasEntry 4 }


	ipSifAliasAction OBJECT-TYPE
	    SYNTAX INTEGER {
		    access(1),
		    deny(2),
		    reject(3),
		    delete(255)
	    }
	    ACCESS  read-write
	    STATUS  mandatory
	    DESCRIPTION
		   "The Rule for the Filter"
	    DEFVAL { access }
	::= { ipSifAliasEntry 5 }


	ipSifAliasStatus OBJECT-TYPE
	    SYNTAX INTEGER {
		    enabled(1),
		    disabled(2)
	    }
	    ACCESS  read-write
	    STATUS  mandatory
	    DESCRIPTION
		   "Defines the administrative status of this policy"
	    DEFVAL { enabled }
	::= { ipSifAliasEntry 6 }


	ipSifAliasPriority OBJECT-TYPE
	    SYNTAX INTEGER {
		    default(1),
		    low-latency(2),
		    high(3),
		    medium(4),
		    low(5)
	    }
	    ACCESS  read-write
	    STATUS  mandatory
	    DESCRIPTION
		   "Defines the QoS priority of this policy"
	    DEFVAL { default }
	::= { ipSifAliasEntry 7 }


	ipSifAliasClassId OBJECT-TYPE
	    SYNTAX  INTEGER  (0..255)
	    ACCESS  read-write
	    STATUS  mandatory
	    DESCRIPTION
		   "Internal ID for SIF policy to QoS policy mapping"
	::= { ipSifAliasEntry 8 }


        ipSifRejectTable OBJECT-TYPE
            SYNTAX SEQUENCE OF IpSifRejectEntry
            ACCESS not-accessible
            STATUS mandatory
            DESCRIPTION
                "Contains actually rejected Frames with Source Destination "
        ::= { biboip 31 }

	ipSifRejectEntry OBJECT-TYPE
	    SYNTAX IpSifRejectEntry
	    ACCESS not-accessible
	    STATUS  mandatory
	    DESCRIPTION
	       ""
	    INDEX   { ipSifRejectIndex }
	::= { ipSifRejectTable 1 }

	IpSifRejectEntry ::=
            SEQUENCE {
                ipSifRejectIndex	INTEGER,
		ipSifRejectSource   	IpAddress,
		ipSifRejectDestination	IpAddress,
		ipSifRejectRejects      INTEGER,
		ipSifRejectSilence      INTEGER,
		ipSifRejectProtocol	INTEGER,
		ipSifRejectPortLo  	INTEGER,
		ipSifRejectPortHigh     INTEGER
           }

	ipSifRejectIndex OBJECT-TYPE
	    SYNTAX INTEGER
	    ACCESS read-only
	    STATUS mandatory
            DESCRIPTION
		"The Index for the Reject Entry"
	::= { ipSifRejectEntry 1 }


	ipSifRejectSource OBJECT-TYPE
	    SYNTAX IpAddress
	    ACCESS read-only
	    STATUS  mandatory
	    DESCRIPTION
	    	"The Reject Source for the Entry"
	    ::= { ipSifRejectEntry 2 }


	ipSifRejectDestination OBJECT-TYPE
	    SYNTAX IpAddress
	    ACCESS read-only
	    STATUS mandatory
	    DESCRIPTION
		"The Reject Destination Index for the Entry"
	    ::= { ipSifRejectEntry 3 }


	ipSifRejectRejects OBJECT-TYPE
	    SYNTAX INTEGER
	    ACCESS read-only

	    STATUS mandatory
	    DESCRIPTION
		"Count of rejected frames"
	    ::= { ipSifRejectEntry 4 }


	ipSifRejectSilence OBJECT-TYPE
	    SYNTAX INTEGER
	    ACCESS read-only
	    STATUS mandatory
	    DESCRIPTION
		"Last reject in seconds"
	    ::= { ipSifRejectEntry 5 }


	ipSifRejectProtocol OBJECT-TYPE
	    SYNTAX INTEGER
	    ACCESS read-only
	    STATUS mandatory
	    DESCRIPTION
		   "The protocol of the rejected Packet"
	    DEFVAL { 0 }
	::= { ipSifRejectEntry 6 }


	ipSifRejectPortLo OBJECT-TYPE
	    SYNTAX INTEGER
	    ACCESS  read-only
	    STATUS  mandatory
	    DESCRIPTION
		   "The lowest Port rejected"
	    DEFVAL { 0 }
	::= { ipSifRejectEntry 7 }

	ipSifRejectPortHigh OBJECT-TYPE
	    SYNTAX INTEGER
	    ACCESS  read-only
	    STATUS  mandatory
	    DESCRIPTION
		   "The highest port rejected"
	    DEFVAL { 0 }
	::= { ipSifRejectEntry 8 }

	ipSifExpectTable OBJECT-TYPE
            SYNTAX SEQUENCE OF IpSifExpectEntry
            ACCESS not-accessible
            STATUS mandatory
            DESCRIPTION
                "Contains expected Sessions with  Source Destination "
        ::= { biboip 35 }

	ipSifExpectEntry OBJECT-TYPE
	    SYNTAX IpSifExpectEntry
	    ACCESS not-accessible
	    STATUS  mandatory
	    DESCRIPTION
	       ""
	    INDEX   { ipSifExpectIndex }
	::= { ipSifExpectTable 1 }

	IpSifExpectEntry ::=
            SEQUENCE {
                ipSifExpectIndex	INTEGER,
		ipSifExpectSource   	IpAddress,
		ipSifExpectDestination	IpAddress,
		ipSifExpectProtocol	INTEGER,
		ipSifExpectSourcePort  	INTEGER,
		ipSifExpectDestPort     INTEGER,
		ipSifExpectPriority   	INTEGER,
		ipSifExpectClassId      INTEGER,
                ipSifExpectIfIndex      INTEGER
           }

	ipSifExpectIndex OBJECT-TYPE
	    SYNTAX INTEGER
	    ACCESS read-only
	    STATUS mandatory
            DESCRIPTION
		"This field is used for SIF-internal signalling and stores the
		 index for the expected session for later matching."
	::= { ipSifExpectEntry 1 }

	ipSifExpectSource OBJECT-TYPE
	    SYNTAX IpAddress
	    ACCESS read-only
	    STATUS mandatory
	    DESCRIPTION
	    	"The source-IP-address for the expected session.
	    	 A value of 0 means ANY source-address."
	    ::= { ipSifExpectEntry 2 }

	ipSifExpectDestination OBJECT-TYPE
	    SYNTAX IpAddress
	    ACCESS read-only
	    STATUS mandatory
	    DESCRIPTION
		"The destination-IP-address for the expected session.
		 A value of 0 means ANY destination-address."
	    ::= { ipSifExpectEntry 3 }

	ipSifExpectProtocol OBJECT-TYPE
	    SYNTAX INTEGER {
		igmp(2),
		ip(4),
		tcp(6),
		udp(17),
		delete(255)
	    }
	    ACCESS read-write
	    STATUS mandatory
	    DESCRIPTION
		   "The protocol of the expected session."
	    DEFVAL { udp }
	::= { ipSifExpectEntry 4 }

	ipSifExpectSourcePort OBJECT-TYPE
	    SYNTAX INTEGER
	    ACCESS  read-only
	    STATUS  mandatory
	    DESCRIPTION
		   "The source-port-number of the expected session.
		    A value of 0 means ANY source-port-number."
	    DEFVAL { 0 }
	::= { ipSifExpectEntry 5 }

	ipSifExpectDestPort OBJECT-TYPE
	    SYNTAX INTEGER
	    ACCESS  read-only
	    STATUS  mandatory
	    DESCRIPTION
		   "The destination-port-number of the expected session.
		    A value of 0 means ANY destination-port-number."
	    DEFVAL { 0 }
	::= { ipSifExpectEntry 6 }

	ipSifExpectPriority OBJECT-TYPE
	    SYNTAX INTEGER {
		    default(1),
		    low-latency(2),
		    high(3),
		    medium(4),
		    low(5)
	    }
	    ACCESS  read-only
	    STATUS  mandatory
	    DESCRIPTION
		   "Defines the QoS-priority/policy to be used for the
		    expected SIF-session."
	    DEFVAL { default }
	::= { ipSifExpectEntry 7 }

	ipSifExpectClassId OBJECT-TYPE
	    SYNTAX  INTEGER  (1..255)
	    ACCESS  read-only
	    STATUS  mandatory
	    DESCRIPTION
		   "Internal ID for mapping SIF-policy to QoS-policy.
		    Default-value of 0 means NOT SPECIFIED."
	::= { ipSifExpectEntry 8 }

	ipSifExpectIfIndex OBJECT-TYPE
	    SYNTAX  INTEGER
	    ACCESS  read-only
	    STATUS  mandatory
	    DESCRIPTION
		   "Interface-index for which the session is expected.
		    A value of 0 means ANY interface-index."
	    DEFVAL { 0 }
	::= { ipSifExpectEntry 9 }


	ipSifAliasAddressGroupTable OBJECT-TYPE
	    SYNTAX SEQUENCE OF IpSifAliasAddressGroupEntry
            ACCESS not-accessible
            STATUS mandatory
            DESCRIPTION
                "Defines IP address or interface group alias"
        ::= { biboip 47 }


	ipSifAliasAddressGroupEntry OBJECT-TYPE
	    SYNTAX IpSifAliasAddressGroupEntry
            ACCESS not-accessible
            STATUS mandatory
            DESCRIPTION
                "Defines IP address or interface group alias"
            INDEX { ipSifAliasAddressGroupId }
        ::= { ipSifAliasAddressGroupTable 1 }


	IpSifAliasAddressGroupEntry ::=
            SEQUENCE {
	        ipSifAliasAddressGroupId	INTEGER,
                ipSifAliasAddressGroupAlias	DisplayString,
	        ipSifAliasAddressGroupIndex	INTEGER,
		ipSifAliasAddressGroupMode	INTEGER
           }


	ipSifAliasAddressGroupId OBJECT-TYPE
	    SYNTAX INTEGER
            ACCESS read-write
            STATUS mandatory
            DESCRIPTION
                "The unique address group entry ID"
        ::= { ipSifAliasAddressGroupEntry 1 }


        ipSifAliasAddressGroupAlias OBJECT-TYPE
            SYNTAX DisplayString
            ACCESS read-write
            STATUS mandatory
            DESCRIPTION
                "Alias name for the address group entry"
        ::= { ipSifAliasAddressGroupEntry 2 }


	ipSifAliasAddressGroupIndex OBJECT-TYPE
	    SYNTAX INTEGER
            ACCESS read-only
            STATUS mandatory
            DESCRIPTION
                "The index for the address group entry to be referred by an
		 ipSifAlias entry"
        ::= { ipSifAliasAddressGroupEntry 3 }


	ipSifAliasAddressGroupMode OBJECT-TYPE
            SYNTAX INTEGER {
	    	interface(1),
		address(2),
		delete(3)
	    }
            ACCESS read-write
            STATUS mandatory
            DESCRIPTION
                "Specifies wether this entry defines an interface or address
		 group"
	    DEFVAL { interface }
        ::= { ipSifAliasAddressGroupEntry 4 }


	ipSifAliasServiceGroupTable OBJECT-TYPE
	    SYNTAX SEQUENCE OF IpSifAliasServiceGroupEntry
            ACCESS not-accessible
            STATUS mandatory
            DESCRIPTION
                "Defines IP service group alias"
        ::= { biboip 48 }


	ipSifAliasServiceGroupEntry OBJECT-TYPE
	    SYNTAX IpSifAliasServiceGroupEntry
            ACCESS not-accessible
            STATUS mandatory
            DESCRIPTION
                "Defines IP service group alias"
            INDEX { ipSifAliasServiceGroupId }
        ::= { ipSifAliasServiceGroupTable 1 }


	IpSifAliasServiceGroupEntry ::=
            SEQUENCE {
	        ipSifAliasServiceGroupId	INTEGER,
                ipSifAliasServiceGroupAlias	DisplayString,
	        ipSifAliasServiceGroupIndex	INTEGER,
		ipSifAliasServiceGroupMode	INTEGER
           }


	ipSifAliasServiceGroupId OBJECT-TYPE
	    SYNTAX INTEGER
            ACCESS read-write
            STATUS mandatory
            DESCRIPTION
                "The unique IP service group entry ID"
        ::= { ipSifAliasServiceGroupEntry 1 }


        ipSifAliasServiceGroupAlias OBJECT-TYPE
            SYNTAX DisplayString
            ACCESS read-write
            STATUS mandatory
            DESCRIPTION
                "Alias name for the IP service group entry"
        ::= { ipSifAliasServiceGroupEntry 2 }


	ipSifAliasServiceGroupIndex OBJECT-TYPE
	    SYNTAX INTEGER
            ACCESS read-only
            STATUS mandatory
            DESCRIPTION
                "The index for the Ip service group entry to be referred by an
		 ipSifAlias entry"
        ::= { ipSifAliasServiceGroupEntry 3 }


	ipSifAliasServiceGroupMode OBJECT-TYPE
            SYNTAX INTEGER {
	    	service(1),
		delete(2)
	    }
            ACCESS read-write
            STATUS mandatory
            DESCRIPTION
                "Specifies wether this entry defines an IP service group or
		 should be deleted"
	    DEFVAL { service }
        ::= { ipSifAliasServiceGroupEntry 4 }


	ipSifPolicyChkTable OBJECT-TYPE
            SYNTAX SEQUENCE OF IpSifPolicyChkEntry
            ACCESS not-accessible
            STATUS mandatory
            DESCRIPTION
                "MIB interface in order to check the configured SIF polices:
		  - for debugging purposes
		  - for test applications
		  - for configuration frontends
		 NOTE: it's a stateless check, not based on a real IP session
		       context
		"
        ::= { biboip 49 }

	ipSifPolicyChkEntry OBJECT-TYPE
	    SYNTAX IpSifPolicyChkEntry
	    ACCESS not-accessible
	    STATUS  mandatory
	    DESCRIPTION
	       ""
	    INDEX { ipSifPolicyChkProtocol, ipSifPolicyChkDestPort }
	::= { ipSifPolicyChkTable 1 }

	IpSifPolicyChkEntry ::=
            SEQUENCE {
		ipSifPolicyChkSourceIfIndex	INTEGER,
		ipSifPolicyChkDestIfIndex	INTEGER,
		ipSifPolicyChkSource		IpAddress,
		ipSifPolicyChkDestination	IpAddress,
		ipSifPolicyChkProtocol		INTEGER,
		ipSifPolicyChkDestPort		INTEGER,
		ipSifPolicyChkRule	   	INTEGER,
		ipSifPolicyChkRuleOrder	   	INTEGER,
		ipSifPolicyChkResult	   	INTEGER,
		ipSifPolicyChkState	   	INTEGER,
		ipSifPolicyChkAdminStatus   	INTEGER,
		ipSifPolicyChkOperStatus   	INTEGER,
		ipSifPolicyChkCurrOperStatus   	INTEGER
           }

	ipSifPolicyChkSourceIfIndex OBJECT-TYPE
	    SYNTAX INTEGER
	    ACCESS read-write
	    STATUS mandatory
            DESCRIPTION
		"The source interface index, for example '1' addresses
		 the 'local' interface whereas '0' means 'don't check."
	::= { ipSifPolicyChkEntry 1 }

	ipSifPolicyChkDestIfIndex OBJECT-TYPE
	    SYNTAX INTEGER
	    ACCESS read-write
	    STATUS mandatory
	    DESCRIPTION
		"The destination interface index, for example '1' addresses
		 the 'local' interface whereas '0' means 'don't check.'"
	::= { ipSifPolicyChkEntry 2 }

	ipSifPolicyChkSource OBJECT-TYPE
	    SYNTAX IpAddress
	    ACCESS read-write
	    STATUS mandatory
            DESCRIPTION
		"The source IP address, 0.0.0.0 means 'don't check'."
	::= { ipSifPolicyChkEntry 3 }

	ipSifPolicyChkDestination OBJECT-TYPE
	    SYNTAX IpAddress
	    ACCESS read-write
	    STATUS mandatory
	    DESCRIPTION
		"The destination IP address, 0.0.0.0 means 'don't check'."
	::= { ipSifPolicyChkEntry 4 }

	ipSifPolicyChkProtocol OBJECT-TYPE
	    SYNTAX INTEGER
	    ACCESS read-write
	    STATUS mandatory
            DESCRIPTION
		"The IP protocol number to checked, '0' means 'don't check."
	::= { ipSifPolicyChkEntry 5 }

	ipSifPolicyChkDestPort OBJECT-TYPE
	    SYNTAX INTEGER
	    ACCESS read-write
	    STATUS mandatory
            DESCRIPTION
		"The destination port number (UDP/TCP service) to checked,
		 '0' means 'don't check."
	::= { ipSifPolicyChkEntry 6 }

	ipSifPolicyChkRule OBJECT-TYPE
            SYNTAX INTEGER {
		access(1),
		deny(2),
		reject(3),
		unknown(4)
	    }
	    ACCESS read-only
	    STATUS mandatory
            DESCRIPTION
		"Returns the associated policy, depending on:
		 - ipSifAliasAction
		 - ipSifAliasOrder
		 - ipSifAliasStatus"
	    DEFVAL { unknown }
	::= { ipSifPolicyChkEntry 7 }

	ipSifPolicyChkRuleOrder OBJECT-TYPE
            SYNTAX INTEGER
	    ACCESS read-only
	    STATUS mandatory
            DESCRIPTION
		"Returns the associated policy order (see ipSifAliasOrder)."
	::= { ipSifPolicyChkEntry 8 }

	ipSifPolicyChkResult OBJECT-TYPE
            SYNTAX INTEGER {
		access(1),
		deny(2),
		unknown(3)
	    }
	    ACCESS read-only
	    STATUS mandatory
            DESCRIPTION
		"Returns the result depending on:
		 - ipSifPolicyChkRule
		 - administrative status (ipSifAdminStatus)
		 - operational status of the SIF engine"
	    DEFVAL { unknown }
	::= { ipSifPolicyChkEntry 9 }

	ipSifPolicyChkState OBJECT-TYPE
            SYNTAX INTEGER {
		initial(1),
		trigger(2),
		running(3),
		done(4)
	    }
	    ACCESS read-write
	    STATUS mandatory
            DESCRIPTION
		"Displays the current status of the policy check, when setting
		 to trigger(2) a new check will be initiated."
	    DEFVAL { initial }
	::= { ipSifPolicyChkEntry 10 }

	ipSifPolicyChkAdminStatus OBJECT-TYPE
            SYNTAX INTEGER {
	    	check(1),
		ignore(2)
	    }
	    ACCESS read-write
	    STATUS mandatory
            DESCRIPTION
		"Determines wether the ipSifAdminStatus should be considered
		 for the policy (check (1)) or not (ingnore (2))."
	    DEFVAL { check }
	::= { ipSifPolicyChkEntry 11 }

	ipSifPolicyChkOperStatus OBJECT-TYPE
            SYNTAX INTEGER {
	    	check(1),
		ignore(2)
	    }
	    ACCESS read-write
	    STATUS mandatory
            DESCRIPTION
		"Determines wether the SIF operational status should be
		 considered for the policy (check (1)) or not (ingnore (2))."
	    DEFVAL { check }
	::= { ipSifPolicyChkEntry 12 }

	ipSifPolicyChkCurrOperStatus OBJECT-TYPE
            SYNTAX INTEGER {
	    	up(1),
		down(2)
	    }
	    ACCESS read-only
	    STATUS mandatory
            DESCRIPTION
		"The current SIF operational status."
	    DEFVAL { down }
	::= { ipSifPolicyChkEntry 13 }



	ipSif OBJECT IDENTIFIER
	::= { biboip 37 }


	ipSifAdminStatus  OBJECT-TYPE
	   SYNTAX  INTEGER {
	   	enable(1),
		disable(2)
	    }
	    ACCESS  read-write
	    STATUS  mandatory
	    DESCRIPTION
	    	"Enable or disable Stateful Inspection Firewall."
	    DEFVAL { enable }
	::= { ipSif 1}

	ipSifLocalFilter  OBJECT-TYPE
	   SYNTAX  INTEGER {
	   	enable(1),
		disable(2)
	    }
	    ACCESS  read-write
	    STATUS  mandatory
	    DESCRIPTION
	    	"Enable or disable filtering on local requests"
	    DEFVAL { disable }
	::= { ipSif 2}

	ipSifInterfaceFilter  OBJECT-TYPE
	   SYNTAX  INTEGER {
	   	enable(1),
		disable(2)
	    }
	    ACCESS  read-write
	    STATUS  mandatory
	    DESCRIPTION
	    	"Enable or disable filtering on same Interface packets"
	    DEFVAL { enable }
	::= { ipSif 3}

	ipSifSysloglevel OBJECT-TYPE
	    SYNTAX  INTEGER {
		deny(1),
		accept(2),
		verbose(3),
		none(4)
	    }
	    ACCESS  read-write
	    STATUS  mandatory
	    DESCRIPTION
	    	"Levels for less or more Informations in the Syslog,
		    verbose : display all Sif Activity
		    deny    : display only rejects, ignore
		    accept  : display only accpts
		    none    : disable Syslogs"
	    DEFVAL { verbose }
	::= { ipSif 4 }

	ipSifUdpTimeout OBJECT-TYPE
	    SYNTAX  INTEGER (30..86400)
	    ACCESS  read-write
	    STATUS  mandatory
	    DESCRIPTION
	    	"Timeout on inactive UDP Session"
	    DEFVAL { 180 }
	::= { ipSif 5 }

	ipSifTcpTimeout OBJECT-TYPE
	    SYNTAX  INTEGER (30..86400)
	    ACCESS  read-write
	    STATUS  mandatory
	    DESCRIPTION
	    	"Timeout on inactive TCP Session"
	    DEFVAL { 3600 }
	::= { ipSif 6 }

	ipSifPPTPTimeout OBJECT-TYPE
	    SYNTAX  INTEGER (30..86400)
	    ACCESS  read-write
	    STATUS  mandatory
	    DESCRIPTION
	    	"Timeout on inactive PPTP Session"
	    DEFVAL { 86400 }
	::= { ipSif 7 }

	ipSifDefaultTimeout OBJECT-TYPE
	    SYNTAX  INTEGER (30..86400)
	    ACCESS  read-write
	    STATUS  mandatory
	    DESCRIPTION
	    	"Timeout on all other ip Sessions"
	    DEFVAL { 30 }
	::= { ipSif 8 }

	ipSifMaxSessions OBJECT-TYPE
	    SYNTAX  INTEGER (0..1000000)
	    ACCESS  read-write
	    STATUS  mandatory
	    DESCRIPTION
	    	"Maximum number of monitored sessions"
	::= { ipSif 9 }

	ipSifMaxRejectEntries OBJECT-TYPE
	    SYNTAX  INTEGER (0..10000)
	    ACCESS  read-write
	    STATUS  mandatory
	    DESCRIPTION
	    	"Maximum number of ipSifRejectTable entries"
	    DEFVAL { 1000 }
	::= { ipSif 14 }

	ipSifMaxRejectTtl OBJECT-TYPE
	    SYNTAX  INTEGER (5..86400)
	    ACCESS  read-write
	    STATUS  mandatory
	    DESCRIPTION
	    	"Maximum time to live of the ipSifRejectTable entries
		 in seconds"
	    DEFVAL { 3600 }
	::= { ipSif 15 }

	ipSifInterfaceAliasAutoCreate OBJECT-TYPE
	   SYNTAX  INTEGER {
	   	enable(1),
		disable(2)
	    }
	    ACCESS  read-write
	    STATUS  mandatory
	    DESCRIPTION
	    	"Enable or disable automatic creation of interface aliases
		 (see ipSifAliasAddressTable) due to created MPR interfaces
		 visible in ifTable."
	    DEFVAL { enable }
	::= { ipSif 16 }


	ipSifStat OBJECT IDENTIFIER
	::= { biboip 46 }

	ipSifStatCurrSessions OBJECT-TYPE
	    SYNTAX  Counter
	    ACCESS  read-only
	    STATUS  mandatory
	    DESCRIPTION
	    	"Current number of all monitored sessions"
	::= { ipSifStat 1 }

	ipSifStatCurrUdpSessions OBJECT-TYPE
	    SYNTAX  Counter
	    ACCESS  read-only
	    STATUS  mandatory
	    DESCRIPTION
	    	"Current number of monitored UDP sessions"
	::= { ipSifStat 2 }

	ipSifStatCurrTcpSessions OBJECT-TYPE
	    SYNTAX  Counter
	    ACCESS  read-only
	    STATUS  mandatory
	    DESCRIPTION
	    	"Current number of monitored TCP sessions"
	::= { ipSifStat 3 }

	ipSifStatCurrOtherSessions OBJECT-TYPE
	    SYNTAX  Counter
	    ACCESS  read-only
	    STATUS  mandatory
	    DESCRIPTION
	    	"Current number of monitored non-TCP/UDP sessions"
	::= { ipSifStat 4 }

	ipSifStatCurrExpectedSessions OBJECT-TYPE
	    SYNTAX  Counter
	    ACCESS  read-only
	    STATUS  mandatory
	    DESCRIPTION
	    	"Current number of created expected sessions"
	::= { ipSifStat 5 }

	ipSifStatTotalUdpSessions OBJECT-TYPE
	    SYNTAX  Counter
	    ACCESS  read-only
	    STATUS  mandatory
	    DESCRIPTION
	    	"Total number of monitored UDP sessions"
	::= { ipSifStat 6 }

	ipSifStatTotalTcpSessions OBJECT-TYPE
	    SYNTAX  Counter
	    ACCESS  read-only
	    STATUS  mandatory
	    DESCRIPTION
	    	"Total number of monitored TCP sessions"
	::= { ipSifStat 7 }

	ipSifStatTotalOtherSessions OBJECT-TYPE
	    SYNTAX  Counter
	    ACCESS  read-only
	    STATUS  mandatory
	    DESCRIPTION
	    	"Total number of monitored non-TCP/UDP sessions"
	::= { ipSifStat 8 }

	ipSifStatTotalExpectedSessions OBJECT-TYPE
	    SYNTAX  Counter
	    ACCESS  read-only
	    STATUS  mandatory
	    DESCRIPTION
	    	"Total number of monitored non-TCP/UDP sessions"
	::= { ipSifStat 9 }


END
