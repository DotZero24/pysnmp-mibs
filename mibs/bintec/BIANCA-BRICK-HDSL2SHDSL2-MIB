-- This file is corresponding to Release 9.1.10.101 from 2014/08/11 00:00:00


-- $RCSfile: mibhdsl2shdsl2,v $
-- $Revision: 1.19 $

-- (C)opyright 2002-2014 bintec elmeg GmbH, All Rights Reserved

BIANCA-BRICK-HDSL2SHDSL2-MIB DEFINITIONS ::= BEGIN

        IMPORTS
            Counter, enterprises
                FROM RFC1155-SMI
            DisplayString
                FROM RFC1158-MIB
            TRAP-TYPE
                FROM RFC-1215
            OBJECT-TYPE
                FROM RFC-1212;

    bintec      OBJECT IDENTIFIER ::= { enterprises 272 }
    bibo        OBJECT IDENTIFIER ::= { bintec 4 }
    hdsl2shdsl  OBJECT IDENTIFIER
        ::= { bibo 35 }


	-- hdsl2shdsl Group

	-- hdsl2shdsl

--	DESCRIPTION
--	     "This MIB module defines a collection of objects for managing
--	      HDSL2/SHDSL lines.  An agent may reside at either end of the
--	      line, however the MIB is designed to require no management
--	      communication between the modems beyond that inherent in the
--	      low-level EOC line protocol as defined in ANSI T1E1.4/2000-006
--	      (for HDSL2 lines), or in ITU G.991.2 (for SHDSL lines)."
--	 REVISION "200205090000Z" - May 9, 2002
--	 DESCRIPTION "Initial version, published as RFC 3276."

    hdsl2ShdslLineMib OBJECT IDENTIFIER ::= { hdsl2shdsl 1 }
    hdsl2ShdslMibObjects OBJECT IDENTIFIER ::= { hdsl2ShdslLineMib 1 }


-- 	Span Configuration Group
--

--	hdsl2ShdslSpanConfTable OBJECT-TYPE
--   	    SYNTAX	SEQUENCE OF Hdsl2ShdslSpanConfEntry
--	    ACCESS	not-accessible
--   	    STATUS	mandatory
--   	    DESCRIPTION
--	    	"This table supports overall configuration of HDSL2/SHDSL
--     	     	 Spans.  Entries in this table MUST be maintained in a
--     	     	 persistent manner. Entries in this table are created by the
--		 system only."
--   	    ::= { hdsl2ShdslMibObjects 1 }
--
--
--	hdsl2ShdslSpanConfEntry OBJECT-TYPE
--  	    SYNTAX      Hdsl2ShdslSpanConfEntry
--   	    ACCESS  	not-accessible
--  	    STATUS      mandatory
-- bintec   NODEL
--   	    DESCRIPTION
--     		"An entry in the hdsl2ShdslSpanConfTable.  Each entry
--     		 represents the complete Span in a single HDSL2/SHDSL line.
--     		 It is indexed by the ifIndex of the associated HDSL2/SHDSL
--     		 line."
--   	    INDEX { hdsl2ShdslSpanLineIfIndex }
--   	    ::= { hdsl2ShdslSpanConfTable 1 }
--
--	Hdsl2ShdslSpanConfEntry ::= SEQUENCE {
--	    hdsl2ShdslSpanLineIfIndex	    INTEGER,
--  	    hdsl2ShdslSpanNumRepeaters      INTEGER,
--   	    hdsl2ShdslSpanProfile           DisplayString,
--   	    hdsl2ShdslSpanAlarmProfile      DisplayString
--   	}
--
--      hdsl2ShdslSpanLineIfIndex OBJECT-TYPE
--          SYNTAX      INTEGER
--          ACCESS      read-only
--          STATUS      mandatory
-- bintec     NOSAVE
--          DESCRIPTION
--              "This object specifies the associated interface index of
--               this HDSL2/SHDSL line."
--          ::= { hdsl2ShdslSpanConfEntry 1 }
--
--   	hdsl2ShdslSpanNumRepeaters OBJECT-TYPE
--   	    SYNTAX      INTEGER  (0..8)
--   	    ACCESS  	read-write
--   	    STATUS      mandatory
--   	    DESCRIPTION
--     		"This object provisions the number of repeaters/regenerators
--     		 in this HDSL2/SHDSL Span."
--   	    ::= { hdsl2ShdslSpanConfEntry 2 }
--
--	hdsl2ShdslSpanProfile OBJECT-TYPE
--   	    SYNTAX      DisplayString (SIZE(0..32))
--   	    ACCESS  	read-write
--   	    STATUS      mandatory
--   	    DESCRIPTION
--     		"This object is a pointer to a span configuration profile in
--     		 the hdsl2ShdslSpanConfProfileTable, which applies to this span.
--     		 The value of this object is the index of the referenced profile
--     		 in the hdsl2ShdslSpanConfProfileTable.  Note that span
--     		 configuration profiles are only applicable to SHDSL lines.
--
--     		 HDSL2 lines MUST reference the default profile, 'DEFVAL'.
--     		 By default, this object will have the value 'DEFVAL' (the index
--     		 of the default profile).
--
--     		 Any attempt to set this object to a value that is not the value
--     		 of the index for an active entry in the profile table,
--     		 hdsl2ShdslSpanConfProfileTable, MUST be rejected."
--   	    ::= { hdsl2ShdslSpanConfEntry 3 }
--
--	hdsl2ShdslSpanAlarmProfile OBJECT-TYPE
--   	    SYNTAX      DisplayString (SIZE(0..32))
--   	    ACCESS  	read-write
--   	    STATUS      mandatory
--   	    DESCRIPTION
--     		"This object is a pointer to an Alarm configuration profile in
--     		 the hdsl2ShdslEndpointAlarmConfProfileTable.  The value of this
--     		 object is the index of the referenced profile in the
--     		 hdsl2ShdslEndpointAlarmConfProfileTable.  The alarm threshold
--     		 configuration in the referenced profile will be used by default
--     		 for all segment endpoints in this span.  Individual endpoints
--     		 may override this profile by explicitly specifying some other
--     		 profile in the hdsl2ShdslEndpointConfTable.  By default, this
--     		 object will have the value 'DEFVAL' (the index of the default
--     		 profile).
--
--     		 Any attempt to set this object to a value that is not the value
--     		 of the index for an active entry in the profile table,
--     		 hdsl2ShdslEndpointAlarmConfProfileTable, MUST be rejected."
--  	    ::= { hdsl2ShdslSpanConfEntry 4 }

-- 	Span Status Group
--

--	hdsl2ShdslSpanStatusTable OBJECT-TYPE
--   	    SYNTAX	SEQUENCE OF Hdsl2ShdslSpanStatusEntry
--   	    ACCESS	not-accessible
--   	    STATUS	mandatory
--   	    DESCRIPTION
--   		"This table provides overall status information of
--     		 HDSL2/SHDSL spans.  This table contains live data from
--     		 equipment.  As such, it is NOT persistent."
--   	    ::= { hdsl2ShdslMibObjects 2 }
--
--	hdsl2ShdslSpanStatusEntry OBJECT-TYPE
--   	    SYNTAX      Hdsl2ShdslSpanStatusEntry
--   	    ACCESS	not-accessible
--   	    STATUS      mandatory
--   	    DESCRIPTION
--     		"An entry in the hdsl2ShdslSpanStatusTable.  Each entry
--     		 represents the complete span in a single HDSL2/SHDSL line.
--     		 It is indexed by the ifIndex of the associated HDSL2/SHDSL
--     		 line."
--   	INDEX { hdsl2ShdslSpanStatusIfIndex }
--   	::= { hdsl2ShdslSpanStatusTable 1 }
--
--	Hdsl2ShdslSpanStatusEntry ::= SEQUENCE {
--	    hdsl2ShdslSpanStatusIfIndex		    	INTEGER,
--   	    hdsl2ShdslSpanStatusNumAvailRepeaters       INTEGER,
--   	    hdsl2ShdslSpanStatusMaxAttainableLineRate   INTEGER,
--   	    hdsl2ShdslSpanStatusActualLineRate          INTEGER,
--   	    hdsl2ShdslSpanStatusTransmissionModeCurrent INTEGER
--
--   	}
--
--      hdsl2ShdslSpanStatusIfIndex OBJECT-TYPE
--          SYNTAX      INTEGER
--          ACCESS      read-only
--          STATUS      mandatory
-- bintec     NOSAVE
--          DESCRIPTION
--              "This object specifies the associated interface index of
--               this HDSL2/SHDSL line."
--          ::= { hdsl2ShdslSpanStatusEntry 1 }
--
--	hdsl2ShdslSpanStatusNumAvailRepeaters OBJECT-TYPE
--   	    SYNTAX      INTEGER (0..8)
--   	    ACCESS  	read-only
--   	    STATUS      mandatory
-- bintec     NOSAVE
--   	    DESCRIPTION
--     		"Contains the actual number of repeaters/regenerators
--     		 discovered in this HDSL2/SHDSL span."
--   	    ::= { hdsl2ShdslSpanStatusEntry 2 }
--
--	not supported by GlobeSpan !
--
--	hdsl2ShdslSpanStatusMaxAttainableLineRate OBJECT-TYPE
--   	    SYNTAX      INTEGER (0..4112000)
--   	    ACCESS	read-only
--   	    STATUS      mandatory
--	    DESCRIPTION
--    		"Contains the maximum attainable line rate (bits per second)
--		 in this HDSL2/SHDSL span. This object provides the maximum
--		 rate the line is capable of achieving. This is based upon
--		 measurements made during line probing."
--   	    ::= { hdsl2ShdslSpanStatusEntry 3 }
--
--	hdsl2ShdslSpanStatusActualLineRate OBJECT-TYPE
--   	    SYNTAX      INTEGER (0..22784000)
--	    ACCESS  	read-only
--   	    STATUS      mandatory
-- bintec     NOSAVE
--   	    DESCRIPTION
--		"Contains the actual line rate (bits per second) in this
--		 HDSL2/SHDSL span. This should equal ifSpeed."
--   	    ::= { hdsl2ShdslSpanStatusEntry 4 }
--
--	hdsl2ShdslSpanStatusTransmissionModeCurrent OBJECT-TYPE
--          SYNTAX      INTEGER {
--              region1(1),
--              region2(2)
--          }
-- 	    ACCESS  	read-only
--   	    STATUS      mandatory
-- bintec     NOSAVE
--   	    DESCRIPTION
--     		"Contains the current Power Spectral Density (PSD) regional
--     		 setting of the HDSL2/SHDSL span:
--               region1   - ITU-T G.991.2 Annex A
--               region2   - ITU-T G.991.2 Annex B"
-- 	    ::= { hdsl2ShdslSpanStatusEntry 5 }

-- 	Unit Inventory Group
--

	hdsl2ShdslInventoryTable OBJECT-TYPE
   	    SYNTAX	SEQUENCE OF Hdsl2ShdslInventoryEntry
   	    ACCESS	not-accessible
   	    STATUS	mandatory
   	    DESCRIPTION
     		"This table supports retrieval of unit inventory information
      		 available via the EOC from units in a HDSL2/SHDSL line.

      		 Entries in this table are dynamically created during the
      		 line discovery process.  The life cycle for these entries
      		 is as follows:

         	 - xtu discovers a device, either a far-end xtu or an xru
         	 - an inventory table entry is created for the device
         	 - the line goes down for whatever reason
         	 - inventory table entries for unreachable devices are
           	   destroyed.

      		 As these entries are created/destroyed dynamically, they
      		 are NOT persistent."
   	    ::= { hdsl2ShdslMibObjects 3 }

	hdsl2ShdslInventoryEntry OBJECT-TYPE
   	    SYNTAX	Hdsl2ShdslInventoryEntry
   	    ACCESS	not-accessible
   	    STATUS	mandatory
  	    DESCRIPTION
     		"An entry in the hdsl2ShdslInventoryTable.  Each entry
		 represents inventory information for a single unit in a
      		 HDSL2/SHDSL line.  It is indexed by the ifIndex of the
      		 HDSL2/SHDSL line."
   	    INDEX { hdsl2ShdslInvIfIndex }
   	    ::= { hdsl2ShdslInventoryTable 1 }

	Hdsl2ShdslInventoryEntry ::= SEQUENCE {
	    hdsl2ShdslInvIfIndex		    INTEGER,
	    hdsl2ShdslInvIndex                      INTEGER,
   	    hdsl2ShdslInvVendorID                   OCTET STRING,
	    hdsl2ShdslInvVendorModelNumber          OCTET STRING,
	    hdsl2ShdslInvVendorSerialNumber         OCTET STRING,
	    hdsl2ShdslInvVendorEOCSoftwareVersion   INTEGER,
	    hdsl2ShdslInvStandardVersion            INTEGER,
	    hdsl2ShdslInvVendorListNumber           OCTET STRING,
	    hdsl2ShdslInvVendorIssueNumber          OCTET STRING,
	    hdsl2ShdslInvVendorSoftwareVersion      OCTET STRING,
	    hdsl2ShdslInvEquipmentCode              OCTET STRING,
	    hdsl2ShdslInvVendorOther                OCTET STRING,
	    hdsl2ShdslInvTransmissionModeCapability INTEGER
   	}

        hdsl2ShdslInvIfIndex OBJECT-TYPE
            SYNTAX      INTEGER
            ACCESS      read-only
            STATUS      mandatory
            DESCRIPTION
                "This object specifies the associated interface index of
                 this HDSL2/SHDSL line."
            ::= { hdsl2ShdslInventoryEntry 1 }

	hdsl2ShdslInvIndex OBJECT-TYPE
            SYNTAX    INTEGER {
                xtuC(1),
                xtuR(2),
                xru1(3),
                xru2(4),
                xru3(5),
                xru4(6),
                xru5(7),
                xru6(8),
                xru7(9),
                xru8(10)
            }
   	    ACCESS  	read-only
   	    STATUS      mandatory
   	    DESCRIPTION
      		"Each entry in this table corresponds to a physical element
      		 in a HDSL2/SHDSL Span.  It is based on the EOC unit addressing
      		 scheme with reference to the xtuC."
   	    ::= { hdsl2ShdslInventoryEntry 2 }

	hdsl2ShdslInvVendorID OBJECT-TYPE
   	    SYNTAX      OCTET STRING (SIZE(8))
   	    ACCESS  	read-only
   	    STATUS      mandatory
   	    DESCRIPTION
     		"Vendor ID as reported in an Inventory Response message."
   	    ::= { hdsl2ShdslInventoryEntry 3 }

	hdsl2ShdslInvVendorModelNumber OBJECT-TYPE
   	    SYNTAX      OCTET STRING (SIZE(12))
   	    ACCESS  	read-only
   	    STATUS      mandatory
   	    DESCRIPTION
     		"Vendor model number as reported in an Inventory Response
      		 message."
   	    ::= { hdsl2ShdslInventoryEntry 4 }

	hdsl2ShdslInvVendorSerialNumber OBJECT-TYPE
   	    SYNTAX      OCTET STRING (SIZE(12))
   	    ACCESS  	read-only
   	    STATUS      mandatory
   	    DESCRIPTION
     		"Vendor serial number as reported in an Inventory Response
      		 message."
   	    ::= { hdsl2ShdslInventoryEntry 5 }

	hdsl2ShdslInvVendorEOCSoftwareVersion OBJECT-TYPE
   	    SYNTAX      INTEGER
   	    ACCESS  	read-only
   	    STATUS      mandatory
   	    DESCRIPTION
     		"Vendor EOC version as reported in a Discovery Response
      		 message."
   	    ::= { hdsl2ShdslInventoryEntry 6 }

	hdsl2ShdslInvStandardVersion OBJECT-TYPE
   	    SYNTAX      INTEGER
   	    ACCESS  	read-only
   	    STATUS      mandatory
   	    DESCRIPTION
     		"Version of the HDSL2/SHDSL standard implemented, as reported
      		 in an Inventory Response message."
   	    ::= { hdsl2ShdslInventoryEntry 7 }

	hdsl2ShdslInvVendorListNumber OBJECT-TYPE
   	    SYNTAX      OCTET STRING (SIZE(3))
   	    ACCESS  	read-only
   	    STATUS      mandatory
   	    DESCRIPTION
     		"Vendor list number as reported in an Inventory Response
      		 message."
   	    ::= { hdsl2ShdslInventoryEntry 8 }

	hdsl2ShdslInvVendorIssueNumber OBJECT-TYPE
   	    SYNTAX      OCTET STRING (SIZE(2))
   	    ACCESS  	read-only
   	    STATUS      mandatory
   	    DESCRIPTION
     		"Vendor issue number as reported in an Inventory Response
      		 message."
   	    ::= { hdsl2ShdslInventoryEntry 9 }

	hdsl2ShdslInvVendorSoftwareVersion OBJECT-TYPE
   	    SYNTAX      OCTET STRING (SIZE(6))
   	    ACCESS  	read-only
   	    STATUS      mandatory
   	    DESCRIPTION
     		"Vendor software version as reported in an Inventory Response
      		 message."
   	    ::= { hdsl2ShdslInventoryEntry 10 }

	hdsl2ShdslInvEquipmentCode OBJECT-TYPE
   	    SYNTAX      OCTET STRING (SIZE(10))
   	    ACCESS  	read-only
   	    STATUS      mandatory
   	    DESCRIPTION
     		"Equipment code conforming to ANSI T1.213, Coded Identification
      		 of Equipment Entities."
   	    ::= { hdsl2ShdslInventoryEntry 11 }

	hdsl2ShdslInvVendorOther OBJECT-TYPE
   	    SYNTAX      OCTET STRING (SIZE(12))
   	    ACCESS  	read-only
   	    STATUS      mandatory
   	    DESCRIPTION
     		"Other vendor information as reported in an Inventory Response
      		 message."
   	    ::= { hdsl2ShdslInventoryEntry 12 }

	hdsl2ShdslInvTransmissionModeCapability OBJECT-TYPE
            SYNTAX      INTEGER {
                region1(1),
                region2(2)
            }
   	    ACCESS  	read-only
   	    STATUS      mandatory
   	    DESCRIPTION
     		"Contains the transmission mode capability of the SHDSL unit:
                 region1   - ITU-T G.991.2 Annex A
                 region2   - ITU-T G.991.2 Annex B"
   	    ::= { hdsl2ShdslInventoryEntry 13 }

-- 	Segment Endpoint Configuration Group
--

	hdsl2ShdslEndpointConfTable OBJECT-TYPE
   	    SYNTAX      SEQUENCE OF Hdsl2ShdslEndpointConfEntry
   	    ACCESS  	not-accessible
   	    STATUS      mandatory
   	    DESCRIPTION
     		"This table supports configuration parameters for segment
      		 endpoints in a HDSL2/SHDSL line.  As this table is indexed
      		 by ifIndex, it MUST be maintained in a persistent manner.
		 Entries in this table are created by the system only."
   	    ::= { hdsl2ShdslMibObjects 4 }

	hdsl2ShdslEndpointConfEntry OBJECT-TYPE
   	    SYNTAX      Hdsl2ShdslEndpointConfEntry
   	    ACCESS  	not-accessible
   	    STATUS      mandatory
   	    DESCRIPTION
     		"An entry in the hdsl2ShdslEndpointConfTable.  Each entry
      		 represents a single segment endpoint in a HDSL2/SHDSL line.
      		 It is indexed by the ifIndex of the HDSL2/SHDSL line."
   	    INDEX { hdsl2ShdslEndpointConfIfIndex }
   	    ::= { hdsl2ShdslEndpointConfTable 1 }

	Hdsl2ShdslEndpointConfEntry ::= SEQUENCE {
	    hdsl2ShdslEndpointConfIfIndex			INTEGER,
   	    hdsl2ShdslEndpointConfSide          		INTEGER,
--   	    hdsl2ShdslEndpointConfWirePair      		INTEGER,
--   	    hdsl2ShdslEndpointConfAlarmProfile			DisplayString,
	    hdsl2ShdslEndpointConfWireInterface 		INTEGER,
	    hdsl2ShdslEndpointConfMinLineRate			INTEGER,
	    hdsl2ShdslEndpointConfMaxLineRate			INTEGER,
	    hdsl2ShdslEndpointConfTransmissionMode		INTEGER,
	    hdsl2ShdslEndpointConfWorstCaseTargetMarginDown	INTEGER,
	    hdsl2ShdslEndpointConfWorstCaseTargetMarginUp	INTEGER,
	    hdsl2ShdslEndpointConfGroupId			INTEGER,
	    hdsl2ShdslEndpointConfLineProbeEnable		INTEGER,
	    hdsl2ShdslEndpointConfLicenseUsage			INTEGER,
	    hdsl2ShdslEndpointConfPamMode			INTEGER,
	    hdsl2ShdslEndpointConfTotalMinLineRate		INTEGER,
	    hdsl2ShdslEndpointConfMinWirePairs			INTEGER,
	    hdsl2ShdslEndpointConfCapListStyle			INTEGER
   	}

        hdsl2ShdslEndpointConfIfIndex OBJECT-TYPE
            SYNTAX	INTEGER
            ACCESS      read-only
            STATUS      mandatory
            DESCRIPTION
                "This object specifies the associated interface index of
                 this HDSL2/SHDSL line."
            ::= { hdsl2ShdslEndpointConfEntry 1 }

	hdsl2ShdslEndpointConfSide OBJECT-TYPE
   	    SYNTAX      INTEGER {
	           networkSide(1),
        	   customerSide(2)
	    }
   	    ACCESS  	read-write
   	    STATUS      mandatory
   	    DESCRIPTION
     		"The side of the unit associated with this segment endpoint -
      		 Network/Customer side - as per the Hdsl2ShdslUnitSide textual
      		 convention."
            DEFVAL      { customerSide }
   	    ::= { hdsl2ShdslEndpointConfEntry 2 }

--	hdsl2ShdslEndpointConfWirePair OBJECT-TYPE
--   	    SYNTAX      INTEGER {
--           	wirePair1(1),
--           	wirePair2(2)
--	    }
--   	    ACCESS  	read-only
--   	    STATUS      mandatory
-- bintec     NOSAVE
--   	    DESCRIPTION
--     		"The wire-pair of the modem associated with this segment
--     		 endpoint as per the Hdsl2ShdslWirePair textual convention."
--   	    ::= { hdsl2ShdslEndpointConfEntry 3 }
--
--	hdsl2ShdslEndpointConfAlarmProfile OBJECT-TYPE
--  	    SYNTAX      DisplayString (SIZE(0..32))
--  	    ACCESS  	read-write
--  	    STATUS      mandatory
--  	    DESCRIPTION
--    		"This object configures the alarm threshold values to be used
--     		 for this segment endpoint.  The values are obtained from the
--     		 alarm configuration profile referenced by this object.  The
--    		 value of this object is the index of the referenced profile in
--     		 the hdsl2ShdslEndpointAlarmConfProfileTable, or NULL (a zero-
--     		 length DisplayString).  If the value is a zero-length
--     		 DisplayString, the endpoint uses the default Alarm
--     		 Configuration Profile for the associated span as per the
--     		 hdsl2ShdslSpanConfAlarmProfile object in the
--     		 hdsl2ShdslSpanConfTable.  The default value of this object is
--    		 a zero-length DisplayString.
--
--     		 Any attempt to set this object to a value that is not the value
--     		 of the index for an active entry in the profile table,
--     		 hdsl2ShdslEndpointAlarmConfProfileTable, MUST be rejected."
--  	    ::= { hdsl2ShdslEndpointConfEntry 4 }
--

	hdsl2ShdslEndpointConfWireInterface OBJECT-TYPE
 	    SYNTAX      INTEGER {
            	twoWire(1),
            	fourWire(2),
            	fourWireStandard(3),
            	fourWireIMA(4),
            	sixWire(5),
            	sixWireIMA(6),
            	eightWire(7),
            	eightWireIMA(8),
            	not-used(9),
            	groupMember(10),
            	twoWireEFM(11),
            	fourWireEFM(12),
            	sixWireEFM(13),
            	eightWireEFM(14)
	    }
   	    ACCESS	read-write
   	    STATUS      mandatory
   	    DESCRIPTION
     		"This object configures the bonding mode of
		the SHDSL Line.
		twoWire(1)          : no bonding is used
		fourWire(2)         : four-wire mode
		fourWireStandard(3) : four-wire mode, disable globespan enhanced mode
		fourWireIMA(4)      : 2 wire pairs bonded with IMA
		sixWire(5)          : 3 wire pairs in m-pair mode
		sixWireIMA(6)       : 3 wire pairs bonded with IMA
		eightWire(7)        : 4 wire pairs in m-pair mode
		eightWireIMA(8)     : 4 wire pairs bonded with IMA
		not-used(9)         : wire pair inactive
		groupMember(10)     : wire pair belongs to a bonding group
            	twoWireEFM(11)      : 2 wire EFM mode
            	fourWireEFM(12)     : 2 wire pairs in EFM mode with PAF bonding
            	sixWireEFM(13)      : 3 wire pairs in EFM mode with PAF bonding
            	eightWireEFM(14)    : 4 wire pairs in EFM mode with PAF bonding"
   	    DEFVAL      { twoWire }
  	    ::= { hdsl2ShdslEndpointConfEntry 5 }

	hdsl2ShdslEndpointConfMinLineRate OBJECT-TYPE
   	    SYNTAX      INTEGER (0..22784000)
--	    UNITS       "bps"
   	    ACCESS  	read-write
   	    STATUS      mandatory
   	    DESCRIPTION
     		"This object configures the minimum transmission rate for
      		 the associated SHDSL Line in bits-per-second (bps).  If
      		 the minimum line rate equals the maximum line rate
      		 (hdsl2ShdslSpanMaxLineRate), the line rate is considered
      		 'fixed'.  If the minimum line rate is less than the maximum
      		 line rate, the line rate is considered 'rate-adaptive'."
   	    DEFVAL      { 1552000 }
  	    ::= { hdsl2ShdslEndpointConfEntry 6 }

	hdsl2ShdslEndpointConfMaxLineRate OBJECT-TYPE
   	    SYNTAX      INTEGER (0..22784000)
--	    UNITS       "bps"
   	    ACCESS  	read-write
   	    STATUS      mandatory
   	    DESCRIPTION
     		"This object configures the maximum transmission rate for
      		 the associated SHDSL Line in bits-per-second (bps).  If
      		 the minimum line rate equals the maximum line rate
      		 (hdsl2ShdslSpanMaxLineRate), the line rate is considered
      		 'fixed'.  If the minimum line rate is less than the maximum
      		 line rate, the line rate is considered 'rate-adaptive'."
   	    DEFVAL      { 1552000 }
  	    ::= { hdsl2ShdslEndpointConfEntry 7 }

	hdsl2ShdslEndpointConfTransmissionMode OBJECT-TYPE
   	    SYNTAX 	INTEGER {
	    	region1(1),
		region2(2),
		region1or2(3)
	    }
   	    ACCESS  	read-write
   	    STATUS      mandatory
   	    DESCRIPTION
     		"This object specifies the regional setting for the SHDSL
      		 line:
   		 region1   - ITU-T G.991.2 Annex A
   		 region2   - ITU-T G.991.2 Annex B"
   	    DEFVAL      { region1 }
  	    ::= { hdsl2ShdslEndpointConfEntry 8 }

	hdsl2ShdslEndpointConfWorstCaseTargetMarginDown OBJECT-TYPE
   	    SYNTAX      INTEGER	(0..65535)
--	    UNITS       "dB"
   	    ACCESS	read-write
   	    STATUS      mandatory
   	    DESCRIPTION
     		"This object specifies the downstream worst case target SNR
      		 margin for a SHDSL line.  The SNR margin is the difference
      		 between the desired SNR and the actual SNR.  Target SNR
      		 margin is the desired SNR margin for a unit."
   	    DEFVAL      { 0 }
  	    ::= { hdsl2ShdslEndpointConfEntry 11 }

	hdsl2ShdslEndpointConfWorstCaseTargetMarginUp OBJECT-TYPE
   	    SYNTAX      INTEGER (-10..21)
--	    UNITS       "dB"
   	    ACCESS	read-write
   	    STATUS      mandatory
   	    DESCRIPTION
     		"This object specifies the upstream worst case target SNR
      		 margin for a SHDSL line.  The SNR margin is the difference
      		 between the desired SNR and the actual SNR.  Target SNR margin
      		 is the desired SNR margin for a unit."
   	    DEFVAL      { 0 }
  	    ::= { hdsl2ShdslEndpointConfEntry 13 }

	hdsl2ShdslEndpointConfGroupId OBJECT-TYPE
   	    SYNTAX      INTEGER (0..255)
   	    ACCESS  	read-write
   	    STATUS      mandatory
   	    DESCRIPTION
     		"This object defines which wire-pairs belong to the same
		 M-pair group or IMA group. Members of the same group have
		 the same entry."
   	    DEFVAL      { 0 }
  	    ::= { hdsl2ShdslEndpointConfEntry 14 }

	hdsl2ShdslEndpointConfLineProbeEnable OBJECT-TYPE
   	    SYNTAX 	INTEGER {
	    	auto(1),
		disable(2),
		enable(3),
		enable-std(4)
	    }
   	    ACCESS  	read-write
   	    STATUS      mandatory
   	    DESCRIPTION
     		"This object specifies the configuration of the PMMS
		 behavior:
   		 auto		- Line Probe is enabled if hdsl2ShdslEndpointConfMinLineRate
		 			< hdsl2ShdslEndpointConfMaxLineRate.
		 disable	- Line Probe is disabled.
		 enable		- Line Probe is enabled.
		 enable_std     - Line Probe is enabled and standard
		                  compliant behaviour is enforced."
   	    DEFVAL      { auto }
  	    ::= { hdsl2ShdslEndpointConfEntry 15 }

	hdsl2ShdslEndpointConfLicenseUsage OBJECT-TYPE
   	    SYNTAX 	INTEGER {
	    	none(1),
		missing(2),
		shdsl(3)
	    }
   	    ACCESS  	read-only
   	    STATUS      mandatory
   	    DESCRIPTION
		"Shows which license type is currently used for this
		 SHDSL interface."
   	    DEFVAL      { none }
  	    ::= { hdsl2ShdslEndpointConfEntry 16 }

	hdsl2ShdslEndpointConfPamMode OBJECT-TYPE
   	    SYNTAX 	INTEGER (4..252)
   	    ACCESS  	read-write
   	    STATUS      mandatory
   	    DESCRIPTION
     		"This object specifies which modulation modes are allowed
		 for this wire pair.
   		 16             - 16-TCPAM, used for Annex A,B and F,G.
		 32		- 32-TCPAM, used for Annex F,G only.
		 4, 8, 64, 128  - non standard proprietary modes.
		 On CPE site more than one mode can be allowed by adding
		 the values.
		 On CO site only the highest mode is used if several
		 values are added."
   	    DEFVAL      { 48 }
  	    ::= { hdsl2ShdslEndpointConfEntry 17 }

	hdsl2ShdslEndpointConfTotalMinLineRate OBJECT-TYPE
   	    SYNTAX      INTEGER (1..50000000)
--	    UNITS       "bps"
   	    ACCESS  	read-write
   	    STATUS      mandatory
   	    DESCRIPTION
     		"This object configures the minimum transmission rate
		 in bits-per-second (bps) for the associated SHDSL bundle.
		 The associated interfaces go up only when the sum of the
		 data rates of the associated wire pairs in state Showtime
		 reaches or exceeds the specified value.
		 This variable has no effect with single pair modes."
   	    DEFVAL      { 1 }
  	    ::= { hdsl2ShdslEndpointConfEntry 18 }

	hdsl2ShdslEndpointConfMinWirePairs OBJECT-TYPE
   	    SYNTAX      INTEGER (1..4)
   	    ACCESS  	read-write
   	    STATUS      mandatory
   	    DESCRIPTION
     		"This object configures the minimum number of wire pairs
		 for the associated SHDSL bundle. The associated interfaces
		 go up only when at least the specified number of wire pairs
		 is connected and in Showtime.
		 This variable has no effect with single pair modes."
   	    DEFVAL      { 1 }
  	    ::= { hdsl2ShdslEndpointConfEntry 19 }

	hdsl2ShdslEndpointConfCapListStyle OBJECT-TYPE
   	    SYNTAX 	INTEGER {
	    	auto(1),
		old(2),
		new(3)
	    }
   	    ACCESS  	read-write
   	    STATUS      mandatory
   	    DESCRIPTION
     		"This object specifies the data format of the capability list,
		 that is exchanged during the G.994.1 handshake:
   		 auto	- automatic detection of the used capability list style.
		 old	- only ATM modes till 2312 kbps can be negotiated.
		 new	- all modes can be negotiated."
   	    DEFVAL      { auto }
  	    ::= { hdsl2ShdslEndpointConfEntry 20 }


-- 	Segment Endpoint Current Status/Performance Group
--

	hdsl2ShdslEndpointCurrTable OBJECT-TYPE
   	    SYNTAX      SEQUENCE OF Hdsl2ShdslEndpointCurrEntry
   	    ACCESS  	not-accessible
   	    STATUS      mandatory
   	    DESCRIPTION
     		"This table contains current status and performance information
      		 for segment endpoints in HDSL2/SHDSL Lines.  As with other
      		 tables in this MIB indexed by ifIndex, entries in this table
      		 MUST be maintained in a persistent manner. Entries in this
		 table are created by the system only."
   	    ::= { hdsl2ShdslMibObjects 5 }

	hdsl2ShdslEndpointCurrEntry OBJECT-TYPE
   	    SYNTAX      Hdsl2ShdslEndpointCurrEntry
   	    ACCESS  	not-accessible
   	    STATUS      mandatory
   	    DESCRIPTION
     		"An entry in the hdsl2ShdslEndpointCurrTable.  Each entry
     		 contains status and performance information relating to a
     		 single segment endpoint.  It is indexed by the ifIndex of the
     		 HDSL2/SHDSL line."
   	    INDEX { hdsl2ShdslEndpointCurrIfIndex }
   	    ::= { hdsl2ShdslEndpointCurrTable 1 }

	Hdsl2ShdslEndpointCurrEntry ::= SEQUENCE {
	    hdsl2ShdslEndpointCurrIfIndex		INTEGER,
	    hdsl2ShdslEndpointCurrReceivedBlks		INTEGER,
	    hdsl2ShdslEndpointCurrTransmittedBlks	INTEGER,
	    hdsl2ShdslEndpointCurrCorrectedBlks		INTEGER,
	    hdsl2ShdslEndpointCurrUncorrectBlks		INTEGER,
   	    hdsl2ShdslEndpointCurrAtn			INTEGER,
   	    hdsl2ShdslEndpointCurrSnrMgn		INTEGER,
  	    hdsl2ShdslEndpointCurrStatus		INTEGER,
   	    hdsl2ShdslEndpointES			Counter,
   	    hdsl2ShdslEndpointSES			Counter,
   	    hdsl2ShdslEndpointCRCanomalies		Counter,
   	    hdsl2ShdslEndpointLOSWS			Counter,
   	    hdsl2ShdslEndpointUAS			Counter,
            hdsl2ShdslEndpointCurr15MinReceivedBlks	INTEGER,
            hdsl2ShdslEndpointCurr15MinTransmittedBlks	INTEGER,
            hdsl2ShdslEndpointCurr15MinCorrectedBlks	INTEGER,
            hdsl2ShdslEndpointCurr15MinUncorrectBlks	INTEGER,
   	    hdsl2ShdslEndpointCurr15MinTimeElapsed	INTEGER,
   	    hdsl2ShdslEndpointCurr15MinES		INTEGER,
   	    hdsl2ShdslEndpointCurr15MinSES		INTEGER,
   	    hdsl2ShdslEndpointCurr15MinCRCanomalies	INTEGER,
   	    hdsl2ShdslEndpointCurr15MinLOSWS		INTEGER,
   	    hdsl2ShdslEndpointCurr15MinUAS		INTEGER,
            hdsl2ShdslEndpointCurr1DayReceivedBlks	INTEGER,
            hdsl2ShdslEndpointCurr1DayTransmittedBlks	INTEGER,
            hdsl2ShdslEndpointCurr1DayCorrectedBlks	INTEGER,
            hdsl2ShdslEndpointCurr1DayUncorrectBlks	INTEGER,
   	    hdsl2ShdslEndpointCurr1DayTimeElapsed	INTEGER,
   	    hdsl2ShdslEndpointCurr1DayES		INTEGER,
   	    hdsl2ShdslEndpointCurr1DaySES		INTEGER,
   	    hdsl2ShdslEndpointCurr1DayCRCanomalies	INTEGER,
   	    hdsl2ShdslEndpointCurr1DayLOSWS		INTEGER,
   	    hdsl2ShdslEndpointCurr1DayUAS		INTEGER
   	}

        hdsl2ShdslEndpointCurrIfIndex OBJECT-TYPE
            SYNTAX      INTEGER
            ACCESS      read-only
            STATUS      mandatory
            DESCRIPTION
                "This object specifies the associated interface index of
                 this HDSL2/SHDSL line."
            ::= { hdsl2ShdslEndpointCurrEntry 1 }

        hdsl2ShdslEndpointCurrReceivedBlks OBJECT-TYPE
            SYNTAX      INTEGER
            ACCESS      read-only
            STATUS      mandatory
            DESCRIPTION
            	"Count of all encoded blocks received on this channel
             	 since agent reset."
            ::= { hdsl2ShdslEndpointCurrEntry 2 }

        hdsl2ShdslEndpointCurrTransmittedBlks OBJECT-TYPE
            SYNTAX      INTEGER
            ACCESS      read-only
            STATUS      mandatory
            DESCRIPTION
                "Count of all encoded blocks transmitted on this channel
                 since agent reset."
            ::= { hdsl2ShdslEndpointCurrEntry 3 }

        hdsl2ShdslEndpointCurrCorrectedBlks OBJECT-TYPE
            SYNTAX      INTEGER
            ACCESS      read-only
            STATUS      mandatory
            DESCRIPTION
                "Count of all blocks received with errors that were
		 corrected since agent reset. These blocks are passed
		 on as good data."
            ::= { hdsl2ShdslEndpointCurrEntry 4 }

        hdsl2ShdslEndpointCurrUncorrectBlks OBJECT-TYPE
            SYNTAX      INTEGER
            ACCESS      read-only
            STATUS      mandatory
            DESCRIPTION
                "Count of all blocks received with uncorrectable errors
                 since agent reset."
            ::= { hdsl2ShdslEndpointCurrEntry 5 }

        hdsl2ShdslEndpointCurrAtn OBJECT-TYPE
   	    SYNTAX      INTEGER (-127..128)
--   	    UNITS       "dB"
   	    ACCESS  	read-only
   	    STATUS      mandatory
   	    DESCRIPTION
     		"The current loop attenuation for this endpoint as reported in
      		 a Network or Customer Side Performance Status message."
--   	    REFERENCE   "HDSL2 Section 7.5.3.7; SHDSL Section 9.5.5.7"
   	    ::= { hdsl2ShdslEndpointCurrEntry 6 }

	hdsl2ShdslEndpointCurrSnrMgn OBJECT-TYPE
   	    SYNTAX      INTEGER (-127..128)
--	    UNITS       "dB"
   	    ACCESS  	read-only
   	    STATUS      mandatory
   	    DESCRIPTION
     		"The current SNR margin for this endpoint as reported in a
      		 Status Response/SNR message."
--   	    REFERENCE   "HDSL2 Section 7.5.3.7; SHDSL Section 9.5.5.7"
   	    ::= { hdsl2ShdslEndpointCurrEntry 7 }

	hdsl2ShdslEndpointCurrStatus OBJECT-TYPE
   	    SYNTAX      INTEGER {
            	noDefect(1),
            	powerBackoff(2),
            	deviceFault(3),
            	dcContinuityFault(4),
            	snrMarginAlarm(5),
--            	loopAttenuationAlarm(6),
            	loswFailureAlarm(7),
            	configInitFailure(8),
            	protocolInitFailure(9),
            	noNeighborPresent(10),
            	loopbackActive(11)
	    }
   	    ACCESS  read-only
   	    STATUS  mandatory
   	    DESCRIPTION
     		"Contains the current state of the endpoint.  This is a
     		 bitmap of possible conditions. The various bit positions
     		 are:

     		 noDefect               There no defects on the line.

     		 powerBackoff           Indicates enhanced Power Backoff.

     		 deviceFault            Indicates a vendor-dependent
                 	                diagnostic or self-test fault
                            		has been detected.

     		 dcContinuityFault      Indicates vendor-dependent
                 	                conditions that interfere with
                            		span powering such as short and
                            		open circuits.

     		 snrMarginAlarm         Indicates that the SNR margin
                 	                has dropped below the alarm threshold.

     		 loopAttenuationAlarm   Indicates that the loop attenuation
                 	                exceeds the alarm threshold.
				        (not supported by GlobeSpan !)

     		 loswFailureAlarm       Indicates a forward LOSW alarm.

     		 configInitFailure      Endpoint failure during initialization
                  	                due to paired endpoint not able to
                            		support requested configuration.

     		 protocolInitFailure    Endpoint failure during initialization
                 	                due to incompatible protocol used by
                            		the paired endpoint.

     		 noNeighborPresent      Endpoint failure during initialization
                 	                due to no activation sequence detected
                            		from paired endpoint.

     		 loopbackActive         A loopback is currently active at this
                 	                Segment Endpoint.

     		 This is intended to supplement ifOperStatus.  Note that there
     		 is a 1-1 relationship between the status bits defined in this
     		 object and the notification thresholds defined elsewhere in
     		 this MIB."
--   	    REFERENCE   "HDSL2 Section 7.5.3.7; SHDSL Section 9.5.5.7"
   	    ::= { hdsl2ShdslEndpointCurrEntry 8 }

	hdsl2ShdslEndpointES OBJECT-TYPE
   	    SYNTAX      Counter
--	    UNITS       "seconds"
   	    ACCESS  	read-only
   	    STATUS      mandatory
   	    DESCRIPTION
     		"Count of Errored Seconds (ES) on this endpoint since the xU
      		 was last restarted."
--   	    REFERENCE   "HDSL2 Section 7.5.3.7; SHDSL Section 9.5.5.7"
   	    ::= { hdsl2ShdslEndpointCurrEntry 9 }

   	hdsl2ShdslEndpointSES OBJECT-TYPE
   	    SYNTAX       Counter
--	    UNITS        "seconds"
   	    ACCESS   	 read-only
   	    STATUS       mandatory
   	    DESCRIPTION
     		"Count of Severely Errored Seconds (SES) on this endpoint
      		 since the xU was last restarted."
--	    REFERENCE   "HDSL2 Section 7.5.3.7; SHDSL Section 9.5.5.7"
   	    ::= { hdsl2ShdslEndpointCurrEntry 10 }

	hdsl2ShdslEndpointCRCanomalies OBJECT-TYPE
   	    SYNTAX       Counter
--	    UNITS        "detected CRC Anomalies"
   	    ACCESS	 read-only
   	    STATUS       mandatory
   	    DESCRIPTION
     		"Count of CRC anomalies on this endpoint since the xU was
      		 last restarted."
--	    REFERENCE   "HDSL2 Section 7.5.3.7; SHDSL Section 9.5.5.7"
   	    ::= { hdsl2ShdslEndpointCurrEntry 11 }

	hdsl2ShdslEndpointLOSWS OBJECT-TYPE
   	    SYNTAX       Counter
--	    UNITS        "seconds"
   	    ACCESS	 read-only
   	    STATUS       mandatory
   	    DESCRIPTION
     		"Count of Loss of Sync Word (LOSW) Seconds on this endpoint
      		 since the xU was last restarted."
--     	    REFERENCE   "HDSL2 Section 7.5.3.7; SHDSL Section 9.5.5.7"
   	    ::= { hdsl2ShdslEndpointCurrEntry 12 }

	hdsl2ShdslEndpointUAS OBJECT-TYPE
   	    SYNTAX       Counter
--	    UNITS        "seconds"
   	    ACCESS	 read-only
   	    STATUS       mandatory
   	    DESCRIPTION
     		"Count of Unavailable Seconds (UAS) on this endpoint since
      		 the xU was last restarted."
--	    REFERENCE   "HDSL2 Section 7.5.3.7; SHDSL Section 9.5.5.7"
   	    ::= { hdsl2ShdslEndpointCurrEntry 13 }

        hdsl2ShdslEndpointCurr15MinReceivedBlks OBJECT-TYPE
            SYNTAX      INTEGER
            ACCESS      read-only
            STATUS      mandatory
            DESCRIPTION
                "Count of all encoded blocks received on this channel
                 within the mandatory 15 minute interval."
            ::= { hdsl2ShdslEndpointCurrEntry 14 }

        hdsl2ShdslEndpointCurr15MinTransmittedBlks OBJECT-TYPE
            SYNTAX      INTEGER
            ACCESS      read-only
            STATUS      mandatory
            DESCRIPTION
                "Count of all encoded blocks transmitted on this channel
                 within the mandatory 15 minute interval."
            ::= { hdsl2ShdslEndpointCurrEntry 15 }

        hdsl2ShdslEndpointCurr15MinCorrectedBlks OBJECT-TYPE
            SYNTAX      INTEGER
            ACCESS      read-only
            STATUS      mandatory
            DESCRIPTION
                "Count of all blocks received with errors that were
                 corrected on this channel within the mandatory 15 minute
		 interval."
            ::= { hdsl2ShdslEndpointCurrEntry 16 }

        hdsl2ShdslEndpointCurr15MinUncorrectBlks OBJECT-TYPE
            SYNTAX      INTEGER
            ACCESS      read-only
            STATUS      mandatory
            DESCRIPTION
                "Count of all blocks received with uncorrectable errors
                 on this channel within the mandatory 15 minute interval."
            ::= { hdsl2ShdslEndpointCurrEntry 17 }

	hdsl2ShdslEndpointCurr15MinTimeElapsed OBJECT-TYPE
   	    SYNTAX       INTEGER (0..86399)
--	    UNITS        "seconds"
   	    ACCESS	 read-only
   	    STATUS       mandatory
   	    DESCRIPTION
     		"Total elapsed seconds in the current 15-minute interval."
   	    ::= { hdsl2ShdslEndpointCurrEntry 18 }

	hdsl2ShdslEndpointCurr15MinES OBJECT-TYPE
   	    SYNTAX       INTEGER
--	    UNITS        "seconds"
   	    ACCESS   	 read-only
   	    STATUS       mandatory
   	    DESCRIPTION
     		"Count of Errored Seconds (ES) in the current 15-minute
      		 interval."
--   	    REFERENCE   "HDSL2 Section 7.5.3.7; SHDSL Section 9.5.5.7"
   	    ::= { hdsl2ShdslEndpointCurrEntry 19 }

	hdsl2ShdslEndpointCurr15MinSES OBJECT-TYPE
   	    SYNTAX       INTEGER
--	    UNITS        "seconds"
   	    ACCESS	 read-only
   	    STATUS       mandatory
   	    DESCRIPTION
     		"Count of Severely Errored Seconds (SES) in the current
      		 15-minute interval."
--	    REFERENCE   "HDSL2 Section 7.5.3.7; SHDSL Section 9.5.5.7"
   	    ::= { hdsl2ShdslEndpointCurrEntry 20 }

	hdsl2ShdslEndpointCurr15MinCRCanomalies OBJECT-TYPE
   	    SYNTAX       INTEGER
--	    UNITS        "detected CRC Anomalies"
   	    ACCESS   	 read-only
   	    STATUS       mandatory
   	    DESCRIPTION
     		"Count of CRC anomalies in the current 15-minute interval."
--	    REFERENCE   "HDSL2 Section 7.5.3.7; SHDSL Section 9.5.5.7"
   	    ::= { hdsl2ShdslEndpointCurrEntry 21 }

	hdsl2ShdslEndpointCurr15MinLOSWS OBJECT-TYPE
   	    SYNTAX       INTEGER
--	    UNITS        "seconds"
   	    ACCESS	 read-only
   	    STATUS       mandatory
   	    DESCRIPTION
     		"Count of Loss of Sync Word (LOSW) Seconds in the current
      		 15-minute interval."
--	    REFERENCE   "HDSL2 Section 7.5.3.7; SHDSL Section 9.5.5.7"
   	    ::= { hdsl2ShdslEndpointCurrEntry 22 }

	hdsl2ShdslEndpointCurr15MinUAS OBJECT-TYPE
   	    SYNTAX       INTEGER
--	    UNITS        "seconds"
   	    ACCESS	 read-only
   	    STATUS       mandatory
   	    DESCRIPTION
     		"Count of Unavailable Seconds (UAS) in the current 15-minute
      	 	 interval."
--	    REFERENCE   "HDSL2 Section 7.5.3.7; SHDSL Section 9.5.5.7"
   	    ::= { hdsl2ShdslEndpointCurrEntry 23 }

        hdsl2ShdslEndpointCurr1DayReceivedBlks OBJECT-TYPE
            SYNTAX      INTEGER
            ACCESS      read-only
            STATUS      mandatory
            DESCRIPTION
                "Count of all encoded blocks received on this channel
                 during the mandatory day as measured by
		 hdsl2ShdslEndpointCurr1DayTimeElapsed."
            ::= { hdsl2ShdslEndpointCurrEntry 24 }

        hdsl2ShdslEndpointCurr1DayTransmittedBlks OBJECT-TYPE
            SYNTAX      INTEGER
            ACCESS      read-only
            STATUS      mandatory
            DESCRIPTION
                "Count of all encoded blocks transmitted on this channel
                 during the mandatory day as measured by
		 hdsl2ShdslEndpointCurr1DayTimeElapsed."
            ::= { hdsl2ShdslEndpointCurrEntry 25 }

        hdsl2ShdslEndpointCurr1DayCorrectedBlks OBJECT-TYPE
            SYNTAX      INTEGER
            ACCESS      read-only
            STATUS      mandatory
            DESCRIPTION
                "Count of all blocks received with errors that were
                 corrected on this channel during the mandatory day as
		 measured by hdsl2ShdslEndpointCurr1DayTimeElapsed."
            ::= { hdsl2ShdslEndpointCurrEntry 26 }

        hdsl2ShdslEndpointCurr1DayUncorrectBlks OBJECT-TYPE
            SYNTAX      INTEGER
            ACCESS      read-only
            STATUS      mandatory
            DESCRIPTION
                "Count of all blocks received with uncorrectable errors
                 on this channel during the mandatory day as measured by
		 hdsl2ShdslEndpointCurr1DayTimeElapsed."
            ::= { hdsl2ShdslEndpointCurrEntry 27 }

	hdsl2ShdslEndpointCurr1DayTimeElapsed OBJECT-TYPE
   	    SYNTAX       INTEGER (0..86399)
--   	    UNITS        "seconds"
   	    ACCESS	 read-only
   	    STATUS       mandatory
   	    DESCRIPTION
     		"Number of seconds that have elapsed since the beginning of
      		 the current 1-day interval."
   	    ::= { hdsl2ShdslEndpointCurrEntry 28 }

	hdsl2ShdslEndpointCurr1DayES OBJECT-TYPE
   	    SYNTAX       INTEGER
--	    UNITS        "seconds"
   	    ACCESS	 read-only
   	    STATUS       mandatory
   	    DESCRIPTION
     		"Count of Errored Seconds (ES) during the current day as
      		 measured by hdsl2ShdslEndpointCurr1DayTimeElapsed."
--	    REFERENCE   "HDSL2 Section 7.5.3.7; SHDSL Section 9.5.5.7"
   	    ::= { hdsl2ShdslEndpointCurrEntry 29 }

	hdsl2ShdslEndpointCurr1DaySES OBJECT-TYPE
   	    SYNTAX       INTEGER
--	    UNITS        "seconds"
   	    ACCESS  	 read-only
   	    STATUS       mandatory
   	    DESCRIPTION
     		"Count of Severely Errored Seconds (SES) during the current
      		 day as measured by hdsl2ShdslEndpointCurr1DayTimeElapsed."
--	    REFERENCE   "HDSL2 Section 7.5.3.7; SHDSL Section 9.5.5.7"
   	    ::= { hdsl2ShdslEndpointCurrEntry 30 }

	hdsl2ShdslEndpointCurr1DayCRCanomalies OBJECT-TYPE
   	    SYNTAX       INTEGER
--   	    UNITS        "detected CRC Anomalies"
   	    ACCESS 	 read-only
   	    STATUS       mandatory
   	    DESCRIPTION
     		"Count of CRC anomalies during the current day as measured
      		 by hdsl2ShdslEndpointCurr1DayTimeElapsed."
--	    REFERENCE   "HDSL2 Section 7.5.3.7; SHDSL Section 9.5.5.7"
   	    ::= { hdsl2ShdslEndpointCurrEntry 31 }

	hdsl2ShdslEndpointCurr1DayLOSWS OBJECT-TYPE
   	    SYNTAX       INTEGER
--	    UNITS        "seconds"
   	    ACCESS  	 read-only
   	    STATUS       mandatory
   	    DESCRIPTION
     		"Count of Loss of Sync Word (LOSW) Seconds during the current
      		 day as measured by hdsl2ShdslEndpointCurr1DayTimeElapsed."
--	    REFERENCE   "HDSL2 Section 7.5.3.7; SHDSL Section 9.5.5.7"
   	    ::= { hdsl2ShdslEndpointCurrEntry 32 }

	hdsl2ShdslEndpointCurr1DayUAS OBJECT-TYPE
   	    SYNTAX       INTEGER
--	    UNITS        "seconds"
   	    ACCESS 	 read-only
   	    STATUS       mandatory
   	    DESCRIPTION
     		"Count of Unavailable Seconds (UAS) during the current day as
      		 measured by hdsl2ShdslEndpointCurr1DayTimeElapsed."
--	    REFERENCE   "HDSL2 Section 7.5.3.7; SHDSL Section 9.5.5.7"
   	    ::= { hdsl2ShdslEndpointCurrEntry 33 }

-- 	Segment Endpoint 15-Minute Interval Status/Performance Group
--

--	hdsl2Shdsl15MinIntervalTable OBJECT-TYPE
--   	    SYNTAX      SEQUENCE OF Hdsl2Shdsl15MinIntervalEntry
--   	    ACCESS  	not-accessible
--  	    STATUS      mandatory
--   	    DESCRIPTION
--     		"This table provides one row for each HDSL2/SHDSL endpoint
--     		 performance data collection interval.  This table contains
--     		 live data from equipment.  As such, it is NOT persistent.
--		 Entries in this table are created by the system only."
--   	    ::= { hdsl2ShdslMibObjects 6 }
--
--	hdsl2Shdsl15MinIntervalEntry OBJECT-TYPE
--   	    SYNTAX	Hdsl2Shdsl15MinIntervalEntry
--   	    ACCESS      not-accessible
--   	    STATUS      mandatory
--   	    DESCRIPTION
--     		"An entry in the hdsl2Shdsl15MinIntervalTable."
--   	    INDEX { hdsl2Shdsl15MinIntervalIfIndex }
--   	    ::= { hdsl2Shdsl15MinIntervalTable 1 }
--
--	Hdsl2Shdsl15MinIntervalEntry ::= SEQUENCE {
--	    hdsl2Shdsl15MinIntervalIfIndex	  INTEGER,
--   	    hdsl2Shdsl15MinIntervalNumber         INTEGER,
--   	    hdsl2Shdsl15MinIntervalES             INTEGER,
--   	    hdsl2Shdsl15MinIntervalSES            INTEGER,
--   	    hdsl2Shdsl15MinIntervalCRCanomalies   INTEGER,
--   	    hdsl2Shdsl15MinIntervalLOSWS          INTEGER,
--   	    hdsl2Shdsl15MinIntervalUAS            INTEGER
--   	}
--
--      hdsl2Shdsl15MinIntervalIfIndex OBJECT-TYPE
--          SYNTAX      INTEGER
--          ACCESS      read-only
--          STATUS      mandatory
-- bintec     NOSAVE
--          DESCRIPTION
--              "This object specifies the associated interface index of
--               this HDSL2/SHDSL line."
-- 	    ::= { hdsl2Shdsl15MinIntervalEntry 1 }
--
--	hdsl2Shdsl15MinIntervalNumber OBJECT-TYPE
--   	    SYNTAX      INTEGER (1..96)
--   	    ACCESS  	read-only
--   	    STATUS      mandatory
-- bintec     NOSAVE
--  	    DESCRIPTION
--     		"Performance Data Interval number. 1 is the the most recent
--     		 previous interval; interval 96 is 24 hours ago. Intervals
--     		 2..96 are optional."
--   	    ::= { hdsl2Shdsl15MinIntervalEntry 2 }
--
--	hdsl2Shdsl15MinIntervalES OBJECT-TYPE
--   	    SYNTAX      INTEGER
--	    UNITS       "seconds"
--   	    ACCESS  	read-only
--   	    STATUS      mandatory
-- bintec     NOSAVE
-- 	    DESCRIPTION
--     		"Count of Errored Seconds (ES) during the interval."
--	    REFERENCE   "HDSL2 Section 7.5.3.7; SHDSL Section 9.5.5.7"
--   	    ::= { hdsl2Shdsl15MinIntervalEntry 3 }
--
--	hdsl2Shdsl15MinIntervalSES OBJECT-TYPE
--   	    SYNTAX      INTEGER
--   	    UNITS       "seconds"
--   	    ACCESS  	read-only
--   	    STATUS      mandatory
-- bintec     NOSAVE
--   	    DESCRIPTION
--     		"Count of Severely Errored Seconds (SES) during the interval."
--	    REFERENCE   "HDSL2 Section 7.5.3.7; SHDSL Section 9.5.5.7"
--   	    ::= { hdsl2Shdsl15MinIntervalEntry 4 }
--
--	hdsl2Shdsl15MinIntervalCRCanomalies OBJECT-TYPE
--   	    SYNTAX      INTEGER
--	    UNITS       "detected CRC Anomalies"
--   	    ACCESS  	read-only
--  	    STATUS      mandatory
-- bintec     NOSAVE
--   	    DESCRIPTION
--     		"Count of CRC anomalies during the interval."
--	    REFERENCE   "HDSL2 Section 7.5.3.7; SHDSL Section 9.5.5.7"
--   	::= { hdsl2Shdsl15MinIntervalEntry 5 }
--
--	hdsl2Shdsl15MinIntervalLOSWS OBJECT-TYPE
--   	    SYNTAX      INTEGER
--	    UNITS       "seconds"
--   	    ACCESS  	read-only
--   	    STATUS      mandatory
-- bintec     NOSAVE
--   	    DESCRIPTION
--     		"Count of Loss of Sync Word (LOSW) Seconds during the
--     	 	 interval."
--	    REFERENCE   "HDSL2 Section 7.5.3.7; SHDSL Section 9.5.5.7"
--   	::= { hdsl2Shdsl15MinIntervalEntry 6 }
--
--	hdsl2Shdsl15MinIntervalUAS OBJECT-TYPE
--   	    SYNTAX      INTEGER
--	    UNITS       "seconds"
--  	    ACCESS  	read-only
--   	    STATUS      mandatory
-- bintec     NOSAVE
-- 	    DESCRIPTION
--     		"Count of Unavailable Seconds (UAS) during the interval."
--	    REFERENCE   "HDSL2 Section 7.5.3.7; SHDSL Section 9.5.5.7"
--   	::= { hdsl2Shdsl15MinIntervalEntry 7 }

-- 	Segment Endpoint 1-Day Interval Status/Performance Group
--

--	hdsl2Shdsl1DayIntervalTable OBJECT-TYPE
--   	    SYNTAX      SEQUENCE OF Hdsl2Shdsl1DayIntervalEntry
--   	    ACCESS      not-accessible
--   	    STATUS      mandatory
--   	    DESCRIPTION
--     		"This table provides one row for each HDSL2/SHDSL endpoint
--     		 performance data collection interval.  This table contains
--     		 live data from equipment.  As such, it is NOT persistent.
--		 Entries in this table are created by the system only."
--   	    ::= { hdsl2ShdslMibObjects 7 }
--
--	hdsl2Shdsl1DayIntervalEntry OBJECT-TYPE
--   	    SYNTAX      Hdsl2Shdsl1DayIntervalEntry
--   	    ACCESS	not-accessible
--   	    STATUS      mandatory
--   	    DESCRIPTION
--     		"An entry in the hdsl2Shdsl1DayIntervalTable."
--   	    INDEX { hdsl2Shdsl1DayIntervalIfIndex }
--   	    ::= { hdsl2Shdsl1DayIntervalTable 1 }
--
--	Hdsl2Shdsl1DayIntervalEntry ::= SEQUENCE {
--	    hdsl2Shdsl1DayIntervalIfIndex	 INTEGER,
--  	    hdsl2Shdsl1DayIntervalNumber         INTEGER,
--   	    hdsl2Shdsl1DayIntervalMoniSecs       INTEGER,
--   	    hdsl2Shdsl1DayIntervalES             INTEGER,
--   	    hdsl2Shdsl1DayIntervalSES            INTEGER,
--   	    hdsl2Shdsl1DayIntervalCRCanomalies   INTEGER,
--   	    hdsl2Shdsl1DayIntervalLOSWS          INTEGER,
--   	    hdsl2Shdsl1DayIntervalUAS            INTEGER
--   	}
--
--      hdsl2Shdsl1DayIntervalIfIndex OBJECT-TYPE
--          SYNTAX      INTEGER
--          ACCESS      read-only
--          STATUS      mandatory
-- bintec     NOSAVE
--          DESCRIPTION
--              "This object specifies the associated interface index of
--               this HDSL2/SHDSL line."
--          ::= { hdsl2Shdsl1DayIntervalEntry 1 }
--
--	hdsl2Shdsl1DayIntervalNumber OBJECT-TYPE
--   	    SYNTAX      INTEGER (1..30)
--   	    ACCESS	read-only
--   	    STATUS      mandatory
-- bintec     NOSAVE
--   	    DESCRIPTION
--     		"History Data Interval number. Interval 1 is the the most
--     		 recent previous day; interval 30 is 30 days ago. Intervals
--     		 2..30 are optional."
--   	    ::= { hdsl2Shdsl1DayIntervalEntry 2 }
--
--	hdsl2Shdsl1DayIntervalMoniSecs OBJECT-TYPE
--   	    SYNTAX       INTEGER (0..86399)
--	    UNITS        "seconds"
--   	    ACCESS   	 read-only
--   	    STATUS       mandatory
-- bintec     NOSAVE
-- 	    DESCRIPTION
--     		"The amount of time in the 1-day interval over which the
--     		 performance monitoring information is actually counted.
--     		 This value will be the same as the interval duration except
--     		 in a situation where performance monitoring data could not
--     		 be collected for any reason."
--  	    ::= { hdsl2Shdsl1DayIntervalEntry 3 }
--
--	hdsl2Shdsl1DayIntervalES OBJECT-TYPE
--   	    SYNTAX       INTEGER
--  	    UNITS        "seconds"
--   	    ACCESS   	 read-only
--   	    STATUS       mandatory
-- bintec     NOSAVE
-- 	    DESCRIPTION
--     		"Count of Errored Seconds (ES) during the 1-day interval as
--     		 measured by hdsl2Shdsl1DayIntervalMoniSecs."
--	    REFERENCE   "HDSL2 Section 7.5.3.7; SHDSL Section 9.5.5.7"
--   	    ::= { hdsl2Shdsl1DayIntervalEntry 4 }
--
--	hdsl2Shdsl1DayIntervalSES OBJECT-TYPE
--   	    SYNTAX       INTEGER
--	    UNITS        "seconds"
--   	    ACCESS   	 read-only
--   	    STATUS       mandatory
-- bintec     NOSAVE
--   	    DESCRIPTION
--     		"Count of Severely Errored Seconds (SES) during the 1-day
--     		 interval as measured by hdsl2Shdsl1DayIntervalMoniSecs."
--	    REFERENCE   "HDSL2 Section 7.5.3.7; SHDSL Section 9.5.5.7"
--   	    ::= { hdsl2Shdsl1DayIntervalEntry 5 }
--
--	hdsl2Shdsl1DayIntervalCRCanomalies OBJECT-TYPE
--   	    SYNTAX       INTEGER
--	    UNITS        "detected CRC Anomalies"
--   	    ACCESS  	 read-only
--   	    STATUS       mandatory
-- bintec     NOSAVE
--   	    DESCRIPTION
--     		"Count of CRC anomalies during the 1-day interval as
--     		 measured by hdsl2Shdsl1DayIntervalMoniSecs."
--	    REFERENCE   "HDSL2 Section 7.5.3.7; SHDSL Section 9.5.5.7"
--   	    ::= { hdsl2Shdsl1DayIntervalEntry 6 }
--
--	hdsl2Shdsl1DayIntervalLOSWS OBJECT-TYPE
--   	    SYNTAX       INTEGER
--	    UNITS        "seconds"
--   	    ACCESS 	 read-only
--   	    STATUS       mandatory
-- bintec     NOSAVE
--   	    DESCRIPTION
--     		"Count of Loss of Sync Word (LOSW) Seconds during the 1-day
--     		 interval as measured by hdsl2Shdsl1DayIntervalMoniSecs."
--	    REFERENCE   "HDSL2 Section 7.5.3.7; SHDSL Section 9.5.5.7"
--   	    ::= { hdsl2Shdsl1DayIntervalEntry 7 }
--
--	hdsl2Shdsl1DayIntervalUAS OBJECT-TYPE
--   	    SYNTAX       INTEGER
--	    UNITS        "seconds"
--   	    ACCESS	 read-only
--   	    STATUS       mandatory
-- bintec     NOSAVE
--   	    DESCRIPTION
--     		"Count of Unavailable Seconds (UAS) during the 1-day interval
--     		 as measured by hdsl2Shdsl1DayIntervalMoniSecs."
--	    REFERENCE   "HDSL2 Section 7.5.3.7; SHDSL Section 9.5.5.7"
--   	::= { hdsl2Shdsl1DayIntervalEntry 8 }

-- 	Maintenance Group
--

--	hdsl2ShdslEndpointMaintTable OBJECT-TYPE
--   	    SYNTAX      SEQUENCE OF Hdsl2ShdslEndpointMaintEntry
--   	    ACCESS  	not-accessible
--   	    STATUS      mandatory
--   	    DESCRIPTION
--     		"This table supports maintenance operations (eg. loopbacks)
--     		 to be performed on HDSL2/SHDSL segment endpoints.  This table
--     		 contains live data from equipment.  As such, it is NOT
--     		 persistent. Entries in this table are created by the system
--		 only."
--   	    ::= { hdsl2ShdslMibObjects 8 }
--
--	hdsl2ShdslEndpointMaintEntry OBJECT-TYPE
--   	    SYNTAX      Hdsl2ShdslEndpointMaintEntry
--   	    ACCESS  	not-accessible
--   	    STATUS      mandatory
--   	    DESCRIPTION
--     		"An entry in the hdsl2ShdslEndpointMaintTable.  Each entry
--     		 corresponds to a single segment endpoint, and is indexed by the
--     		 ifIndex of the HDSL2/SHDSL line, the UnitId of the associated
--     		 unit and the side of the unit."
--   	    INDEX { hdsl2ShdslEndpointMaintIfIndex }
--   	    ::= { hdsl2ShdslEndpointMaintTable 1 }
--
--	Hdsl2ShdslEndpointMaintEntry ::= SEQUENCE {
--	    hdsl2ShdslEndpointMaintIfIndex	INTEGER,
--  	    hdsl2ShdslMaintLoopbackConfig	INTEGER,
--   	    hdsl2ShdslMaintTipRingReversal	INTEGER,
--   	    hdsl2ShdslMaintPowerBackOff		INTEGER,
--   	    hdsl2ShdslMaintSoftRestart		INTEGER
--   	}
--
--      hdsl2ShdslEndpointMaintIfIndex OBJECT-TYPE
--          SYNTAX      INTEGER
--          ACCESS      read-only
--          STATUS      mandatory
-- bintec     NOSAVE
--          DESCRIPTION
--              "This object specifies the associated interface index of
--               this HDSL2/SHDSL line."
-- 	    ::= { hdsl2ShdslEndpointMaintEntry 1 }
--
--	hdsl2ShdslMaintLoopbackConfig OBJECT-TYPE
--   	    SYNTAX      INTEGER {
--            	noLoopback(1),
--            	normalLoopback(2),
--            	specialLoopback(3)
--          }
--   	    ACCESS	read-write
--   	    STATUS	mandatory
--   	    DESCRIPTION
--     		"This object controls configuration of loopbacks for the
--     		 associated segment endpoint.  The status of the loopback
--     		 is obtained via the hdsl2ShdslEndpointCurrStatus object."
--          DEFVAL      { noLoopback }
--   	    ::= { hdsl2ShdslEndpointMaintEntry 2 }
--
--	hdsl2ShdslMaintTipRingReversal OBJECT-TYPE
--   	    SYNTAX      INTEGER {
--            	normal(1),
--            	reversed(2)
--          }
--   	    ACCESS  	read-only
--   	    STATUS      mandatory
-- bintec     NOSAVE
--   	    DESCRIPTION
--    	 	"This object indicates the state of the tip/ring pair at the
--     		 associated segment endpoint."
--   	    ::= { hdsl2ShdslEndpointMaintEntry 3 }
--
--	hdsl2ShdslMaintPowerBackOff OBJECT-TYPE
--   	    SYNTAX      INTEGER {
--            	default(1),
--            	enhanced(2)
--          }
--   	    ACCESS	  read-write
--   	    STATUS 	  mandatory
--   	    DESCRIPTION
--     		"This object configures the receiver at the associated
--     		 segment endpoint to operate in default or enhanced power
--     		 backoff mode."
--          DEFVAL      { default }
--   	    ::= { hdsl2ShdslEndpointMaintEntry 4 }
--
--	hdsl2ShdslMaintSoftRestart OBJECT-TYPE
--   	    SYNTAX      INTEGER {
--            	ready(1),
--            	restart(2)
--          }
--   	    ACCESS	read-write
--   	    STATUS	mandatory
--   	    DESCRIPTION
--     		"This object enables the manager to trigger a soft restart
--     		 of the modem at the associated segment endpoint.  The manager
--     		 may only set this object to the 'restart(2)' value, which
--     		 initiates a restart.  The agent will perform a restart after
--     		 approximately 5 seconds.  Following the 5 second period, the
--     		 agent will restore the object to the 'ready(1)' state."
--          DEFVAL      { ready }
--   	    ::= { hdsl2ShdslEndpointMaintEntry 5 }

--	hdsl2ShdslUnitMaintTable OBJECT-TYPE
--   	    SYNTAX      SEQUENCE OF Hdsl2ShdslUnitMaintEntry
--   	    ACCESS  	not-accessible
--   	    STATUS      mandatory
--   	    DESCRIPTION
--     		"This table supports maintenance operations for units in a
--    		 HDSL2/SHDSL line.  Entries in this table MUST be maintained
--     		 in a persistent manner. Entries in this table are created by
--		 the system only."
--   	    ::= { hdsl2ShdslMibObjects 9 }
--
--	hdsl2ShdslUnitMaintEntry OBJECT-TYPE
--   	    SYNTAX	Hdsl2ShdslUnitMaintEntry
--   	    ACCESS	not-accessible
--   	    STATUS      mandatory
--   	    DESCRIPTION
--     		"An entry in the hdsl2ShdslUnitMaintTable.  Each entry
--     		 corresponds to a single unit, and is indexed by the ifIndex
--     		 of the HDSL2/SHDSL line and the UnitId of the associated
--     		 unit."
--   	    INDEX { hdsl2ShdslUnitMaintIfIndex  }
--   	    ::= { hdsl2ShdslUnitMaintTable 1 }
--
--	Hdsl2ShdslUnitMaintEntry ::= SEQUENCE {
--	    hdsl2ShdslUnitMaintIfIndex		INTEGER,
--   	    hdsl2ShdslMaintLoopbackTimeout	INTEGER
--   	    hdsl2ShdslMaintUnitPowerSource	INTEGER
--   	}
--
--      hdsl2ShdslUnitMaintIfIndex OBJECT-TYPE
--          SYNTAX      INTEGER
--          ACCESS      read-only
--          STATUS      mandatory
-- bintec     NOSAVE
--          DESCRIPTION
--              "This object specifies the associated interface index of
--               this HDSL2/SHDSL line."
--          ::= { hdsl2ShdslUnitMaintEntry 1
--
--	hdsl2ShdslMaintLoopbackTimeout OBJECT-TYPE
--   	    SYNTAX      INTEGER (0..4095)
--	    UNITS       "minutes"
--   	    ACCESS  	read-write
--   	    STATUS      mandatory
--   	    DESCRIPTION
--     		"This object configures the timeout value for loopbacks
--     		 initiated at segments endpoints contained in the associated
--     		 unit.  A value of 0 disables the timeout."
--   	    ::= { hdsl2ShdslUnitMaintEntry 2 }
--
--      not supported by GlobeSpan !
--
--	hdsl2ShdslMaintUnitPowerSource OBJECT-TYPE
--   	    SYNTAX      INTEGER { local(1), span(2) }
--   	    ACCESS	read-only
--   	    STATUS      mandatory
--   	    DESCRIPTION
--     		"This object indicates the DC power source being used by the
--     		 associated unit."
--   	    ::= { hdsl2ShdslUnitMaintEntry 3 }

--	Span Configuration Profile Group
--

	hdsl2ShdslSpanConfProfileTable OBJECT-TYPE
   	    SYNTAX      SEQUENCE OF Hdsl2ShdslSpanConfProfileEntry
   	    ACCESS	not-accessible
   	    STATUS      mandatory
   	    DESCRIPTION
     		"This table supports definitions of span configuration
      		 profiles for SHDSL lines.  HDSL2 does not support these
      		 configuration options.  This table MUST be maintained
      		 in a persistent manner. Entries in this table are created by
		 the system only."
   	    ::= { hdsl2ShdslMibObjects 10 }

	hdsl2ShdslSpanConfProfileEntry OBJECT-TYPE
   	    SYNTAX      Hdsl2ShdslSpanConfProfileEntry
   	    ACCESS	not-accessible
   	    STATUS      mandatory
   	    DESCRIPTION
     		"Each entry corresponds to a single span configuration
      		 profile.  Each profile contains a set of span configuration
      		 parameters.  The configuration parameters in a profile are
      		 applied to those lines referencing that profile (see the
      		 hdsl2ShdslSpanConfProfile object).  Profiles may be
      		 created/deleted only by the system."
	    INDEX { hdsl2ShdslSpanConfProfileName }
   	    ::= { hdsl2ShdslSpanConfProfileTable 1 }

	Hdsl2ShdslSpanConfProfileEntry ::= SEQUENCE {
   	    hdsl2ShdslSpanConfProfileName               DisplayString,
   	    hdsl2ShdslSpanConfWireInterface             INTEGER,
   	    hdsl2ShdslSpanConfMinLineRate               INTEGER,
   	    hdsl2ShdslSpanConfMaxLineRate               INTEGER,
--   	    hdsl2ShdslSpanConfPSD                       INTEGER,
   	    hdsl2ShdslSpanConfTransmissionMode		INTEGER,
--   	    hdsl2ShdslSpanConfRemoteEnabled             INTEGER,
--   	    hdsl2ShdslSpanConfPowerFeeding              INTEGER,
--   	    hdsl2ShdslSpanConfCurrCondTargetMarginDown  INTEGER,
   	    hdsl2ShdslSpanConfWorstCaseTargetMarginDown INTEGER,
--   	    hdsl2ShdslSpanConfCurrCondTargetMarginUp    INTEGER,
   	    hdsl2ShdslSpanConfWorstCaseTargetMarginUp   INTEGER
--   	    hdsl2ShdslSpanConfUsedTargetMargins         INTEGER,
--   	    hdsl2ShdslSpanConfReferenceClock		INTEGER,
--   	    hdsl2ShdslSpanConfLineProbeEnable           INTEGER
--   	    hdsl2ShdslSpanConfProfileRowStatus          RowStatus
   	}

	hdsl2ShdslSpanConfProfileName OBJECT-TYPE
   	    SYNTAX      DisplayString (SIZE(1..32))
   	    ACCESS  	read-only
   	    STATUS      mandatory
   	    DESCRIPTION
    	 	"This object is the unique index associated with this profile.
      		 Entries in this table are referenced via the object
      		 hdsl2ShdslSpanConfProfile in Hdsl2ShdslSpanConfEntry."
   	    ::= { hdsl2ShdslSpanConfProfileEntry 1 }

	hdsl2ShdslSpanConfWireInterface OBJECT-TYPE
 	    SYNTAX      INTEGER {
            	twoWire(1),
            	fourWire(2),
            	fourWireStandard(3),
            	fourWireIMA(4),
            	sixWire(5),
            	sixWireIMA(6),
            	eightWire(7),
            	eightWireIMA(8),
            	not-used(9),
            	groupMember(10),
            	twoWireEFM(11),
            	fourWireEFM(12),
            	sixWireEFM(13),
            	eightWireEFM(14)
	    }
   	    ACCESS	read-write
   	    STATUS      mandatory
   	    DESCRIPTION
     		"This object configures the bonding mode of
		the SHDSL Line.
		twoWire(1)          : no bonding is used
		fourWire(2)         : four-wire mode
		fourWireStandard(3) : four-wire mode, disable globespan enhanced mode
		fourWireIMA(4)      : 2 wire pairs bonded with IMA
		sixWire(5)          : 3 wire pairs in m-pair mode
		sixWireIMA(6)       : 3 wire pairs bonded with IMA
		eightWire(7)        : 4 wire pairs in m-pair mode
		eightWireIMA(8)     : 4 wire pairs bonded with IMA
		not-used(9)         : wire pair inactive
		groupMember(10)     : wire pair belongs to a bonding group
            	twoWireEFM(11)      : 2 wire EFM mode
            	fourWireEFM(12)     : 2 wire pairs in EFM mode with PAF bonding
            	sixWireEFM(13)      : 3 wire pairs in EFM mode with PAF bonding
            	eightWireEFM(14)    : 4 wire pairs in EFM mode with PAF bonding"
   	    DEFVAL      { twoWire }
   	    ::= { hdsl2ShdslSpanConfProfileEntry 2 }

	hdsl2ShdslSpanConfMinLineRate OBJECT-TYPE
   	    SYNTAX      INTEGER (0..22784000)
--	    UNITS       "bps"
   	    ACCESS  	read-write
   	    STATUS      mandatory
   	    DESCRIPTION
     		"This object configures the minimum transmission rate for
      		 the associated SHDSL Line in bits-per-second (bps).  If
      		 the minimum line rate equals the maximum line rate
      		 (hdsl2ShdslSpanMaxLineRate), the line rate is considered
      		 'fixed'.  If the minimum line rate is less than the maximum
      		 line rate, the line rate is considered 'rate-adaptive'."
   	    DEFVAL      { 1552000 }
   	    ::= { hdsl2ShdslSpanConfProfileEntry 3 }

	hdsl2ShdslSpanConfMaxLineRate OBJECT-TYPE
   	    SYNTAX      INTEGER (0..22784000)
--	    UNITS       "bps"
   	    ACCESS  	read-write
   	    STATUS      mandatory
   	    DESCRIPTION
     		"This object configures the maximum transmission rate for
      		 the associated SHDSL Line in bits-per-second (bps).  If
      		 the minimum line rate equals the maximum line rate
      		 (hdsl2ShdslSpanMaxLineRate), the line rate is considered
      		 'fixed'.  If the minimum line rate is less than the maximum
      		 line rate, the line rate is considered 'rate-adaptive'."
   	    DEFVAL      { 1552000 }
   	    ::= { hdsl2ShdslSpanConfProfileEntry 4 }

--	hdsl2ShdslSpanConfPSD OBJECT-TYPE
--   	    SYNTAX      INTEGER {
--            	symmetric(1),
--            	asymmetric(2)
--          }
--   	    ACCESS  	read-write
--   	    STATUS      mandatory
--   	    DESCRIPTION
--     		"This object configures use of symmetric/asymmetric PSD (Power
--     		 Spectral Density) Mask for the associated SHDSL Line.  Support
--     		 for symmetric PSD is mandatory for all supported data rates.
--     		 Support for asymmetric PSD is optional."
--   	    DEFVAL      { symmetric }
--   	    ::= { hdsl2ShdslSpanConfProfileEntry 5 }
--

	hdsl2ShdslSpanConfTransmissionMode OBJECT-TYPE
   	    SYNTAX 	INTEGER { region1(1), region2(2) , region1or2(3)}
   	    ACCESS  	read-write
   	    STATUS      mandatory
   	    DESCRIPTION
     		"This object specifies the regional setting for the SHDSL
      		 line:
   		 region1   - ITU-T G.991.2 Annex A
   		 region2   - ITU-T G.991.2 Annex B"
   	    DEFVAL      { region1 }
   	    ::= { hdsl2ShdslSpanConfProfileEntry 6 }

--	hdsl2ShdslSpanConfRemoteEnabled OBJECT-TYPE
--   	    SYNTAX      INTEGER {
--          	enabled(1),
--        	disabled(2)
--          }
--   	    ACCESS	read-write
--   	    STATUS      mandatory
--   	    DESCRIPTION
--     		"This object enables/disables support for remote management
--     		 of the units in a SHDSL line from the STU-R via the EOC."
--   	    DEFVAL      { enabled }
--   	    ::= { hdsl2ShdslSpanConfProfileEntry 7 }
--
--      not supported by GlobeSpan !
--
--	hdsl2ShdslSpanConfPowerFeeding OBJECT-TYPE
--   	    SYNTAX      INTEGER { noPower(1), powerFeed(2), wettingCurrent(3) }
--   	    ACCESS	read-write
--   	    STATUS      mandatory
--   	    DESCRIPTION
--     		"This object enables/disables support for optional power
--     		 feeding in a SHDSL line."
--   	    DEFVAL      { noPower }
--   	    ::= { hdsl2ShdslSpanConfProfileEntry 8 }

--	hdsl2ShdslSpanConfCurrCondTargetMarginDown OBJECT-TYPE
--   	    SYNTAX      INTEGER (-10..21)
--	    UNITS       "dB"
--   	    ACCESS  	read-write
--   	    STATUS      mandatory
--   	    DESCRIPTION
--     		"This object specifies the downstream current condition target
--     		 SNR margin for a SHDSL line.  The SNR margin is the difference
--     		 between the desired SNR and the actual SNR.  Target SNR margin
--     		 is the desired SNR margin for a unit."
--   	    DEFVAL      { 0 }
--   	    ::= { hdsl2ShdslSpanConfProfileEntry 9 }
--

	hdsl2ShdslSpanConfWorstCaseTargetMarginDown OBJECT-TYPE
   	    SYNTAX      INTEGER	(0..65535)
--	    UNITS       "dB"
   	    ACCESS	read-write
   	    STATUS      mandatory
   	    DESCRIPTION
     		"This object specifies the downstream worst case target SNR
      		 margin for a SHDSL line.  The SNR margin is the difference
      		 between the desired SNR and the actual SNR.  Target SNR
      		 margin is the desired SNR margin for a unit."
   	    DEFVAL      { 0 }
   	    ::= { hdsl2ShdslSpanConfProfileEntry 10 }

--	hdsl2ShdslSpanConfCurrCondTargetMarginUp OBJECT-TYPE
--   	    SYNTAX      INTEGER (-10..21)
--	    UNITS       "dB"
--  	    ACCESS  	read-write
--   	    STATUS      mandatory
--   	    DESCRIPTION
--     		"This object specifies the upstream current condition target
--     		 SNR margin for a SHDSL line.  The SNR margin is the difference
--     		 between the desired SNR and the actual SNR.  Target SNR margin
--     		 is the desired SNR margin for a unit."
--   	    DEFVAL      { 0 }
--   	    ::= { hdsl2ShdslSpanConfProfileEntry 11 }
--

	hdsl2ShdslSpanConfWorstCaseTargetMarginUp OBJECT-TYPE
   	    SYNTAX      INTEGER (-10..21)
--	    UNITS       "dB"
   	    ACCESS	read-write
   	    STATUS      mandatory
   	    DESCRIPTION
     		"This object specifies the upstream worst case target SNR
      		 margin for a SHDSL line.  The SNR margin is the difference
      		 between the desired SNR and the actual SNR.  Target SNR margin
      		 is the desired SNR margin for a unit."
   	    DEFVAL      { 0 }
   	    ::= { hdsl2ShdslSpanConfProfileEntry 12 }

--	hdsl2ShdslSpanConfUsedTargetMargins OBJECT-TYPE
--   	    SYNTAX      INTEGER {
--            	currCondDown(1),
--            	worstCaseDown(2),
--            	currCondUp(3),
--            	worstCaseUp(4)
--          }
--   	    ACCESS	read-write
--   	    STATUS      mandatory
--   	    DESCRIPTION
--     		"Contains indicates whether a target SNR margin is enabled or
--     		 disabled.  This is a bit-map of possible settings.  The
--     		 various bit positions are:
--
--     		 currCondDown     current condition downstream target SNR
--                		  margin enabled
--
--     		 worstCaseDown    worst case downstream target SNR margin
--                	          enabled
--
--     		 currCondUp       current condition upstream target SNR
--                     		  margin enabled
--
--     		 worstCaseUp      worst case upstream target SNR margin
--                	          enabled."
--   	    DEFVAL      { currCondDown }
--   	    ::= { hdsl2ShdslSpanConfProfileEntry 13 }

--	hdsl2ShdslSpanConfReferenceClock OBJECT-TYPE
--   	    SYNTAX      INTEGER { localClk(1), networkClk(2),
--                                dataOrNetworkClk(3), dataClk(4) }
--   	    ACCESS	read-write
--   	    STATUS      mandatory
--   	    DESCRIPTION
--     		"This object configures the clock reference for the STU-C
--     		 in a SHDSL Line.
--          	  localClk(1)        Mode-1 per G991.2
--          	  networkClk(2)      Mode-2 per G991.2
--          	  dataOrNetworkClk   Mode-3a per G991.2
--          	  dataClk            Mode-3b per G991.2
--              "
--   	    DEFVAL      { localClk }
--   	    ::= { hdsl2ShdslSpanConfProfileEntry 14 }
--
--	hdsl2ShdslSpanConfLineProbeEnable OBJECT-TYPE
--   	    SYNTAX      INTEGER {
--            	disable(1),
--            	enable(2)
--          }
--   	    ACCESS	read-write
--   	    STATUS      mandatory
--   	    DESCRIPTION
--     		"This object enables/disables support for Line Probe of
--    		 the units in a SHDSL line.  When Line Probe is enabled, the
--    		 system performs Line Probing to find the best possible
--    		 rate.  If Line probe is disabled, the rate adaptation phase
--    		 is skipped to shorten set up time."
--  	    DEFVAL      { disable }
--   	    ::= { hdsl2ShdslSpanConfProfileEntry 15 }
--
--	hdsl2ShdslSpanConfProfileRowStatus OBJECT-TYPE
--   	    SYNTAX      RowStatus
--   	    MAX-ACCESS  read-create
--   	    STATUS      current
--   	    DESCRIPTION
--     		"This object controls creation/deletion of the associated
--     		 entry in this table per the semantics of RowStatus.  If an
--     		 active entry is referenced in hdsl2ShdslSpanConfProfile, the
--     		 entry MUST remain active until all references are removed."
--   	    ::= { hdsl2ShdslSpanConfProfileEntry 16 }

-- 	Segment Endpoint Alarm Configuration Profile group
--

--	hdsl2ShdslEndpointAlarmConfProfileTable OBJECT-TYPE
--   	    SYNTAX      SEQUENCE OF Hdsl2ShdslEndpointAlarmConfProfileEntry
--   	    ACCESS  	not-accessible
--   	    STATUS      mandatory
--   	    DESCRIPTION
--     		"This table supports definitions of alarm configuration
--     		 profiles for HDSL2/SHDSL segment endpoints.  This table
--     		 MUST be maintained in a persistent manner. Entries in this
--		 table are created by the system only."
--   	    ::= { hdsl2ShdslMibObjects 11 }
--
--	hdsl2ShdslEndpointAlarmConfProfileEntry OBJECT-TYPE
--  	    SYNTAX      Hdsl2ShdslEndpointAlarmConfProfileEntry
--   	    ACCESS	not-accessible
--   	    STATUS      mandatory
-- bintec   NODEL
--   	    DESCRIPTION
--     		"Each entry corresponds to a single alarm configuration profile.
--     		 Each profile contains a set of parameters for setting alarm
--     		 thresholds for various performance attributes monitored at
--     		 HDSL2/SHDSL segment endpoints.  Profiles may be created/deleted
--		 only by the system."
--   	    INDEX { hdsl2ShdslEndpointAlarmIfIndex }
--   	    ::= { hdsl2ShdslEndpointAlarmConfProfileTable 1 }
--
--	Hdsl2ShdslEndpointAlarmConfProfileEntry ::= SEQUENCE {
--   	    hdsl2ShdslEndpointAlarmIfIndex		INTEGER,
--   	    hdsl2ShdslEndpointAlarmConfProfileName      DisplayString,
--   	    hdsl2ShdslEndpointThreshLoopAttenuation     INTEGER,
--   	    hdsl2ShdslEndpointThreshSNRMargin           INTEGER,
--   	    hdsl2ShdslEndpointThreshES			INTEGER,
--   	    hdsl2ShdslEndpointThreshSES			INTEGER,
--   	    hdsl2ShdslEndpointThreshCRCanomalies        INTEGER,
--   	    hdsl2ShdslEndpointThreshLOSWS		INTEGER,
--   	    hdsl2ShdslEndpointThreshUAS			INTEGER
--	    hdsl2ShdslEndpointAlarmConfProfileRowStatus RowStatus
--   	}
--
--	hdsl2ShdslEndpointAlarmIfIndex OBJECT-TYPE
--          SYNTAX      INTEGER
-- 	    ACCESS  	read-only
-- 	    STATUS      mandatory
-- 	    DESCRIPTION
--              "This object specifies the associated interface index of
--               this HDSL2/SHDSL line."
-- 	    ::= { hdsl2ShdslEndpointAlarmConfProfileEntry 10 }
--
--	hdsl2ShdslEndpointAlarmConfProfileName OBJECT-TYPE
--   	    SYNTAX      DisplayString (SIZE(1..32))
--   	    ACCESS  	read-only
--   	    STATUS      mandatory
--   	    DESCRIPTION
--     		"This object is the unique index associated with this profile."
--   	    ::= { hdsl2ShdslEndpointAlarmConfProfileEntry 1 }
--
--      not supported by GlobeSpan !
--
--	hdsl2ShdslEndpointThreshLoopAttenuation OBJECT-TYPE
--   	    SYNTAX      INTEGER (-127..128)
--	    UNITS       "dB"
--   	    ACCESS  	read-write
--  	    STATUS      mandatory
--   	    DESCRIPTION
--     		"This object configures the loop attenuation alarm threshold.
--     		 When the current value of hdsl2ShdslEndpointCurrAtn reaches
--     		 or exceeds this threshold, a hdsl2ShdslLoopAttenCrossing
--     		 MAY be generated."
--  	    DEFVAL      { 0 }
--   	    ::= { hdsl2ShdslEndpointAlarmConfProfileEntry 2 }
--
--	hdsl2ShdslEndpointThreshSNRMargin OBJECT-TYPE
--   	    SYNTAX      INTEGER (-127..128)
--	    UNITS       "dB"
--   	    ACCESS  	read-write
--   	    STATUS      mandatory
--   	DESCRIPTION
--     		"This object configures the SNR margin alarm threshold.
--     		 When the current value of hdsl2ShdslEndpointCurrSnrMgn
--     		 reaches or drops below this threshold, a
--     		 hdsl2ShdslSNRMarginCrossing MAY be generated."
--   	    DEFVAL      { 0 }
--   	    ::= { hdsl2ShdslEndpointAlarmConfProfileEntry 3 }
--
--	hdsl2ShdslEndpointThreshES OBJECT-TYPE
--   	    SYNTAX      INTEGER
--	    UNITS       "seconds"
--   	    ACCESS  	read-write
--   	    STATUS      mandatory
--   	    DESCRIPTION
--     		"This object configures the threshold for the number of
--     		 errored seconds (ES) within any given 15-minute performance
--     		 data collection interval.  If the value of errored seconds
--     		 in a particular 15-minute collection interval reaches/
--     		 exceeds this value, a hdsl2ShdslPerfESThresh MAY be
--     		 generated.  At most one notification will be sent per
--     		 interval per endpoint."
--   	    DEFVAL      { 0 }
--   	    ::= { hdsl2ShdslEndpointAlarmConfProfileEntry 4 }
--
--	hdsl2ShdslEndpointThreshSES OBJECT-TYPE
--   	    SYNTAX      INTEGER
--	    UNITS       "seconds"
--   	    ACCESS	read-write
--   	    STATUS      mandatory
--   	    DESCRIPTION
--     		"This object configures the threshold for the number of
--     		 severely errored seconds (SES) within any given 15-minute
--     		 performance data collection interval.  If the value of
--     		 severely errored seconds in a particular 15-minute collection
--     		 interval reaches/exceeds this value, a hdsl2ShdslPerfSESThresh
--     		 MAY be generated.  At most one notification will be sent per
--     		 interval per endpoint."
--   	    DEFVAL      { 0 }
--   	    ::= { hdsl2ShdslEndpointAlarmConfProfileEntry 5 }
--
--	hdsl2ShdslEndpointThreshCRCanomalies OBJECT-TYPE
--   	    SYNTAX      INTEGER
--	    UNITS       "detected CRC Anomalies"
--   	    ACCESS	read-write
--   	    STATUS      mandatory
--   	    DESCRIPTION
--     		"This object configures the threshold for the number of
--     		 CRC anomalies within any given 15-minute performance data
--     		 collection interval.  If the value of CRC anomalies in a
--     		 particular 15-minute collection interval reaches/exceeds
--     		 this value, a hdsl2ShdslPerfCRCanomaliesThresh MAY be
--     		 generated.  At most one notification will be sent per
--     		 interval per endpoint."
--   	    DEFVAL      { 0 }
--   	    ::= { hdsl2ShdslEndpointAlarmConfProfileEntry 6 }
--
--	hdsl2ShdslEndpointThreshLOSWS OBJECT-TYPE
--   	    SYNTAX      INTEGER
--	    UNITS       "seconds"
--   	    ACCESS	read-write
--   	    STATUS      mandatory
--   	    DESCRIPTION
--     		"This object configures the threshold for the number of
--     		 Loss of Sync Word (LOSW) Seconds within any given 15-minute
--     		 performance data collection interval.  If the value of LOSW
--     		 in a particular 15-minute collection interval reaches/exceeds
--     		 this value, a hdsl2ShdslPerfLOSWSThresh MAY be generated.
--     		 At most one notification will be sent per interval per
--     		 endpoint."
--   	    DEFVAL      { 0 }
--   	    ::= { hdsl2ShdslEndpointAlarmConfProfileEntry 7 }
--
--	hdsl2ShdslEndpointThreshUAS OBJECT-TYPE
--   	    SYNTAX      INTEGER
--	    UNITS       "seconds"
--   	    ACCESS	read-write
--    	    STATUS      mandatory
--   	    DESCRIPTION
--     		"This object configures the threshold for the number of
--     	 	 unavailable seconds (UAS) within any given 15-minute
--     		 performance data collection interval.  If the value of UAS
--     		 in a particular 15-minute collection interval reaches/exceeds
--     		 this value, a hdsl2ShdslPerfUASThresh MAY be generated.
--     		 At most one notification will be sent per interval per
--     		 endpoint."
--   	    DEFVAL      { 0 }
--   	    ::= { hdsl2ShdslEndpointAlarmConfProfileEntry 8 }
--
--	hdsl2ShdslEndpointAlarmConfProfileRowStatus OBJECT-TYPE
--   	    SYNTAX      RowStatus
--   	    MAX-ACCESS  read-create
--   	    STATUS      current
--   	    DESCRIPTION
--     		"This object controls creation/deletion of the associated
--     		 entry in this table as per the semantics of RowStatus.
--     		 If an active entry is referenced in either
--   		 hdsl2ShdslSpanConfAlarmProfile or
--   		 hdsl2ShdslEndpointAlarmConfProfile, the entry MUST remain
--   		 active until all references are removed."
--	    ::= { hdsl2ShdslEndpointAlarmConfProfileEntry 9 }

-- 	Notifications Group
--
--
--	hdsl2ShdslNotifications OBJECT IDENTIFIER ::= { hdsl2ShdslMIB 0 }
--
--	hdsl2ShdslLoopAttenCrossing NOTIFICATION-TYPE OBJECTS {
--   	    hdsl2ShdslEndpointCurrAtn,
--   	    hdsl2ShdslEndpointThreshLoopAttenuation
--   	}
--   	STATUS	mandatory
--   	DESCRIPTION
--     		"This notification indicates that the loop attenuation
--     		 threshold (as per the hdsl2ShdslEndpointThreshLoopAttenuation
--     		 value) has been reached/exceeded for the HDSL2/SHDSL segment
--     		 endpoint."
--   	::= { hdsl2ShdslNotifications 1 }
--
--	hdsl2ShdslSNRMarginCrossing NOTIFICATION-TYPE OBJECTS {
--   	    hdsl2ShdslEndpointCurrSnrMgn,
--  	    hdsl2ShdslEndpointThreshSNRMargin
--   	}
--   	STATUS	mandatory
--   	DESCRIPTION
--     		"This notification indicates that the SNR margin threshold (as
--     		 per the hdsl2ShdslEndpointThreshSNRMargin value) has been
--     		 reached/exceeded for the HDSL2/SHDSL segment endpoint."
--  	::= { hdsl2ShdslNotifications 2 }
--
--	hdsl2ShdslPerfESThresh NOTIFICATION-TYPE OBJECTS {
--   	    hdsl2ShdslEndpointCurr15MinES,
--   	    hdsl2ShdslEndpointThreshES
--   	}
--   	STATUS	mandatory
--   	DESCRIPTION
--     		"This notification indicates that the errored seconds threshold
--     		 (as per the hdsl2ShdslEndpointThreshES value) has been reached/
--     		 exceeded for the HDSL2/SHDSL segment endpoint."
--  	::= { hdsl2ShdslNotifications 3 }
--
--	hdsl2ShdslPerfSESThresh NOTIFICATION-TYPE OBJECTS {
--   	    hdsl2ShdslEndpointCurr15MinSES,
--   	    hdsl2ShdslEndpointThreshSES
--  	}
--   	STATUS	mandatory
--   	DESCRIPTION
--     		"This notification indicates that the severely errored seconds
--     		 threshold (as per the hdsl2ShdslEndpointThreshSES value) has
--     		 been reached/exceeded for the HDSL2/SHDSL Segment Endpoint."
--  	::= { hdsl2ShdslNotifications 4 }
--
--	hdsl2ShdslPerfCRCanomaliesThresh NOTIFICATION-TYPE OBJECTS {
--   	    hdsl2ShdslEndpointCurr15MinCRCanomalies,
--   	    hdsl2ShdslEndpointThreshCRCanomalies
--   	}
--   	STATUS	mandatory
--   	DESCRIPTION
--     		"This notification indicates that the CRC anomalies threshold
--     		 (as per the hdsl2ShdslEndpointThreshCRCanomalies value) has
--     		 been reached/exceeded for the HDSL2/SHDSL Segment Endpoint."
--  	::= { hdsl2ShdslNotifications 5 }
--
--	hdsl2ShdslPerfLOSWSThresh NOTIFICATION-TYPE OBJECTS {
--   	    hdsl2ShdslEndpointCurr15MinLOSWS,
--   	    hdsl2ShdslEndpointThreshLOSWS
--   	}
--   	STATUS	mandatory
--   	DESCRIPTION
--     		"This notification indicates that the LOSW seconds threshold
--     		 (as per the hdsl2ShdslEndpointThreshLOSWS value) has been
--     		 reached/exceeded for the HDSL2/SHDSL segment endpoint."
--   		::= { hdsl2ShdslNotifications 6 }
--
--	hdsl2ShdslPerfUASThresh NOTIFICATION-TYPE OBJECTS {
--  	    hdsl2ShdslEndpointCurr15MinUAS,
--   	    hdsl2ShdslEndpointThreshUAS
--   	}
--   	STATUS	mandatory
--   	DESCRIPTION
--     		"This notification indicates that the unavailable seconds
--     		 threshold (as per the hdsl2ShdslEndpointThreshUAS value) has
--     		 been reached/exceeded for the HDSL2/SHDSL segment endpoint."
--   	::= { hdsl2ShdslNotifications 7 }
--
--	hdsl2ShdslSpanInvalidNumRepeaters NOTIFICATION-TYPE OBJECTS {
--   	    hdsl2ShdslSpanConfNumRepeaters
--   	}
--  	STATUS	mandatory
--   	DESCRIPTION
--     		"This notification indicates that a mismatch has been detected
--     		 between the number of repeater/regenerator units configured
--     		 for a HDSL2/SHDSL line via the hdsl2ShdslSpanConfNumRepeaters
--     		 object and the actual number of repeater/regenerator units
--     		 discovered via the EOC."
--   	::= { hdsl2ShdslNotifications 8 }
--
--	hdsl2ShdslLoopbackFailure NOTIFICATION-TYPE OBJECTS {
--   	    hdsl2ShdslMaintLoopbackConfig
--   	}
--   	STATUS	mandatory
--   	DESCRIPTION
--     		"This notification indicates that an endpoint maintenance
--     		 loopback command failed for an HDSL2/SHDSL segment."
--   	::= { hdsl2ShdslNotifications 9 }
--
--	hdsl2ShdslpowerBackoff NOTIFICATION-TYPE OBJECTS {
--   	    hdsl2ShdslEndpointCurrStatus
--   	}
--   	STATUS	mandatory
--   	DESCRIPTION
--     		"This notification indicates that the bit setting for
--     		 powerBackoff in the hdsl2ShdslEndpointCurrStatus object for
--     		 this endpoint has changed."
--  	::= { hdsl2ShdslNotifications 10 }
--
--	hdsl2ShdsldeviceFault NOTIFICATION-TYPE OBJECTS {
--   	    hdsl2ShdslEndpointCurrStatus
--   	}
--   	STATUS	mandatory
--   	DESCRIPTION
--     		"This notification indicates that the bit setting for
--     		 deviceFault in the hdsl2ShdslEndpointCurrStatus object for
--     		 this endpoint has changed."
--  	::= { hdsl2ShdslNotifications 11 }
--
--	hdsl2ShdsldcContinuityFault NOTIFICATION-TYPE OBJECTS {
--   	    hdsl2ShdslEndpointCurrStatus
--   	}
--   	STATUS  mandatory
--   	DESCRIPTION
--     		"This notification indicates that the bit setting for
--     		 dcContinuityFault in the hdsl2ShdslEndpointCurrStatus object
--     		 for this endpoint has changed."
--   	::= { hdsl2ShdslNotifications 12 }
--
--	hdsl2ShdslconfigInitFailure NOTIFICATION-TYPE OBJECTS {
--   	    hdsl2ShdslEndpointCurrStatus
--   	}
--   	STATUS  mandatory
--   	DESCRIPTION
--     		"This notification indicates that the bit setting for
--     		 configInitFailure in the hdsl2ShdslEndpointCurrStatus object
--     		 for this endpoint has changed."
--   	::= { hdsl2ShdslNotifications 13 }
--
--	hdsl2ShdslprotocolInitFailure NOTIFICATION-TYPE OBJECTS {
--   	    hdsl2ShdslEndpointCurrStatus
--   	}
--   	STATUS  mandatory
--   	DESCRIPTION
--     		"This notification indicates that the bit setting for
--     		 protocolInitFailure in the hdsl2ShdslEndpointCurrStatus
--     		 object for this endpoint has changed."
--  	::= { hdsl2ShdslNotifications 14 }
--
--	hdsl2ShdslnoNeighborPresent NOTIFICATION-TYPE OBJECTS {
--   	    hdsl2ShdslEndpointCurrStatus
--   	}
--   	STATUS  mandatory
--   	DESCRIPTION
--     		"This notification indicates that the bit setting for
--     		 noNeighborPresent in the hdsl2ShdslEndpointCurrStatus object
--     		 for this endpoint has changed."
--   	::= { hdsl2ShdslNotifications 15 }
--
--	hdsl2ShdslLocalPowerLoss NOTIFICATION-TYPE OBJECTS {
--   	    hdsl2ShdslInvVendorID
--   	}
--   	STATUS  mandatory
--   	DESCRIPTION
--     		"This notification indicates impending unit failure due to
--     		 loss of local power (last gasp)."
--   	::= { hdsl2ShdslNotifications 16 }
--

-- 	conformance information
--
--
--	hdsl2ShdslConformance OBJECT IDENTIFIER ::= { hdsl2ShdslMIB 3 }
--	hdsl2ShdslGroups      OBJECT IDENTIFIER ::=
--        	     { hdsl2ShdslConformance 1 }
--	hdsl2ShdslCompliances OBJECT IDENTIFIER ::=
--        	     { hdsl2ShdslConformance 2 }

-- 	agent compliance statements
--
--	hdsl2ShdslLineMibCompliance MODULE-COMPLIANCE
--   	    STATUS  mandatory
--   	    DESCRIPTION
--     		"The section outlines compliance requirements for this MIB."
--   	    MODULE
--   	    MANDATORY-GROUPS {
--   		hdsl2ShdslSpanConfGroup,
--   		hdsl2ShdslSpanStatusGroup,
--   		hdsl2ShdslInventoryGroup,
--   		hdsl2ShdslEndpointConfGroup,
--   		hdsl2ShdslEndpointCurrGroup,
--   		hdsl2Shdsl15MinIntervalGroup,
--   		hdsl2Shdsl1DayIntervalGroup,
--   		hdsl2ShdslMaintenanceGroup,
--   		hdsl2ShdslEndpointAlarmConfGroup,
--  		hdsl2ShdslNotificationGroup
--   	}
--
--	GROUP  hdsl2ShdslInventoryShdslGroup
--   	    DESCRIPTION
--     		"Support for this group is only required for implementations
--     		 supporting SHDSL lines."
--
--	GROUP  hdsl2ShdslSpanShdslStatusGroup
--   	    DESCRIPTION
--     		"Support for this group is only required for implementations
--     		 supporting SHDSL lines."
--
--	GROUP  hdsl2ShdslSpanConfProfileGroup
--   	    DESCRIPTION
--     		"Support for this group is only required for implementations
--     	 	 supporting SHDSL lines."
--
--   	::= { hdsl2ShdslCompliances 1 }
--
--
--	units of conformance
--
--	hdsl2ShdslSpanConfGroup OBJECT-GROUP OBJECTS {
--   	    hdsl2ShdslSpanConfNumRepeaters,
--   	    hdsl2ShdslSpanConfProfile,
--   	    hdsl2ShdslSpanConfAlarmProfile
--   	}
--   	STATUS  mandatory
--   	DESCRIPTION
--     		"This group supports objects for configuring span related
--     		 parameters for HDSL2/SHDSL lines."
--  	::= { hdsl2ShdslGroups 1 }
--
--	hdsl2ShdslSpanStatusGroup OBJECT-GROUP OBJECTS {
--   	    hdsl2ShdslStatusNumAvailRepeaters
--   	}
--   	STATUS  mandatory
--   	DESCRIPTION
--     		"This group supports objects for retrieving span related
--     		 status for HDSL2/SHDSL lines."
--   	::= { hdsl2ShdslGroups 2 }
--
--	hdsl2ShdslInventoryShdslGroup OBJECT-GROUP OBJECTS {
--   	    hdsl2ShdslInvTransmissionModeCapability
--   	}
--   	STATUS  mandatory
--   	DESCRIPTION
--     		"This group supports objects for retrieving SHDSL-specific
--     		 inventory information."
--   	::= { hdsl2ShdslGroups 3 }
--
--	hdsl2ShdslSpanShdslStatusGroup OBJECT-GROUP OBJECTS {
--  	    hdsl2ShdslStatusMaxAttainableLineRate,
--   	    hdsl2ShdslStatusActualLineRate,
--   	    hdsl2ShdslStatusTransmissionModeCurrent
--   	}
--   	STATUS  mandatory
--   	DESCRIPTION
--     		"This group supports objects for retrieving SHDSL-specific
--    		 span related status."
--   	::= { hdsl2ShdslGroups 4 }
--
--	hdsl2ShdslInventoryGroup OBJECT-GROUP OBJECTS {
--   	    hdsl2ShdslInvVendorID,
--   	    hdsl2ShdslInvVendorModelNumber,
--   	    hdsl2ShdslInvVendorSerialNumber,
--   	    hdsl2ShdslInvVendorEOCSoftwareVersion,
--  	    hdsl2ShdslInvStandardVersion,
--  	    hdsl2ShdslInvVendorListNumber,
--   	    hdsl2ShdslInvVendorIssueNumber,
--   	    hdsl2ShdslInvVendorSoftwareVersion,
--   	    hdsl2ShdslInvEquipmentCode,
--  	    hdsl2ShdslInvVendorOther
--   	}
--   	STATUS  mandatory
--   	DESCRIPTION
--     		"This group supports objects that provide unit inventory
--     		 information about the units in HDSL2/SHDSL lines."
--   	::= { hdsl2ShdslGroups 5 }
--
--	hdsl2ShdslEndpointConfGroup OBJECT-GROUP OBJECTS {
--   	    hdsl2ShdslEndpointCurrAtn
--   	}
--   	STATUS  mandatory
--   	DESCRIPTION
--     		"This group supports objects for configuring parameters for
--     		 segment endpoints in HDSL2/SHDSL lines."
--   	::= { hdsl2ShdslGroups 6 }
--
--	hdsl2ShdslEndpointCurrGroup OBJECT-GROUP OBJECTS {
--   	    hdsl2ShdslEndpointCurrAtn,
--   	    hdsl2ShdslEndpointCurrSnrMgn,
--   	    hdsl2ShdslEndpointCurrStatus,
--   	    hdsl2ShdslEndpointES,
--   	    hdsl2ShdslEndpointSES,
--   	    hdsl2ShdslEndpointCRCanomalies,
--   	    hdsl2ShdslEndpointLOSWS,
--  	    hdsl2ShdslEndpointUAS,
--   	    hdsl2ShdslEndpointCurr15MinTimeElapsed,
--   	    hdsl2ShdslEndpointCurr15MinES,
--   	    hdsl2ShdslEndpointCurr15MinSES,
--    	    hdsl2ShdslEndpointCurr15MinCRCanomalies,
--   	    hdsl2ShdslEndpointCurr15MinLOSWS,
--   	    hdsl2ShdslEndpointCurr15MinUAS,
--   	    hdsl2ShdslEndpointCurr1DayTimeElapsed,
--   	    hdsl2ShdslEndpointCurr1DayES,
--   	    hdsl2ShdslEndpointCurr1DaySES,
--   	    hdsl2ShdslEndpointCurr1DayCRCanomalies,
--  	    hdsl2ShdslEndpointCurr1DayLOSWS,
--   	    hdsl2ShdslEndpointCurr1DayUAS
--   	}
--   	STATUS  mandatory
--   	DESCRIPTION
--     		"This group supports objects which provide current status and
--     		 performance measurements relating to segment endpoints in
--     		 HDSL2/SHDSL lines."
--   	::= { hdsl2ShdslGroups 7 }
--
--	hdsl2Shdsl15MinIntervalGroup OBJECT-GROUP OBJECTS {
--   	    hdsl2Shdsl15MinIntervalES,
--   	    hdsl2Shdsl15MinIntervalSES,
--   	    hdsl2Shdsl15MinIntervalCRCanomalies,
--   	    hdsl2Shdsl15MinIntervalLOSWS,
--  	    hdsl2Shdsl15MinIntervalUAS
--   	}
--   	STATUS  mandatory
--   	DESCRIPTION
--     		"This group supports objects which maintain historic
--     		 performance measurements relating to segment endpoints in
--     		 HDSL2/SHDSL lines in 15-minute intervals."
--   	::= { hdsl2ShdslGroups 8 }
--
--	hdsl2Shdsl1DayIntervalGroup OBJECT-GROUP OBJECTS {
--   	    hdsl2Shdsl1DayIntervalMoniSecs,
--   	    hdsl2Shdsl1DayIntervalES,
--   	    hdsl2Shdsl1DayIntervalSES,
--   	    hdsl2Shdsl1DayIntervalCRCanomalies,
--   	    hdsl2Shdsl1DayIntervalLOSWS,
--   	    hdsl2Shdsl1DayIntervalUAS
--   	}
--   	STATUS  mandatory
--   	DESCRIPTION
--     		"This group supports objects which maintain historic
--     		 performance measurements relating to segment endpoints in
--     		 HDSL2/SHDSL lines in 1-day intervals."
--   	::= { hdsl2ShdslGroups 9 }
--
--	hdsl2ShdslMaintenanceGroup OBJECT-GROUP OBJECTS {
--   	    hdsl2ShdslMaintLoopbackConfig,
--   	    hdsl2ShdslMaintTipRingReversal,
--   	    hdsl2ShdslMaintPowerBackOff,
--   	    hdsl2ShdslMaintSoftRestart,
--   	    hdsl2ShdslMaintLoopbackTimeout,
--  	    hdsl2ShdslMaintUnitPowerSource
--   	}
--   	STATUS  mandatory
--   	DESCRIPTION
--     		"This group supports objects that provide support for
--     		 maintenance actions for HDSL2/SHDSL lines."
--   	::= { hdsl2ShdslGroups 10 }
--
--	hdsl2ShdslEndpointAlarmConfGroup OBJECT-GROUP OBJECTS {
--   	    hdsl2ShdslEndpointAlarmConfProfile,
--   	    hdsl2ShdslEndpointThreshLoopAttenuation,
--   	    hdsl2ShdslEndpointThreshSNRMargin,
--   	    hdsl2ShdslEndpointThreshES,
--  	    hdsl2ShdslEndpointThreshSES,
--   	    hdsl2ShdslEndpointThreshCRCanomalies,
--   	    hdsl2ShdslEndpointThreshLOSWS,
--   	    hdsl2ShdslEndpointThreshUAS,
--   	    hdsl2ShdslEndpointAlarmConfProfileRowStatus
--   	}
--   	STATUS  mandatory
--   	DESCRIPTION
--     		"This group supports objects that allow configuration of alarm
--     		 thresholds for various performance parameters for HDSL2/SHDSL
--     		 lines."
--   	::= { hdsl2ShdslGroups 11 }
--
--	hdsl2ShdslNotificationGroup NOTIFICATION-GROUP NOTIFICATIONS {
--   	    hdsl2ShdslLoopAttenCrossing,
--   	    hdsl2ShdslSNRMarginCrossing,
--   	    hdsl2ShdslPerfESThresh,
--   	    hdsl2ShdslPerfSESThresh,
--   	    hdsl2ShdslPerfCRCanomaliesThresh,
--   	    hdsl2ShdslPerfLOSWSThresh,
--   	    hdsl2ShdslPerfUASThresh,
--  	    hdsl2ShdslSpanInvalidNumRepeaters,
--   	    hdsl2ShdslLoopbackFailure,
--   	    hdsl2ShdslpowerBackoff,
--  	    hdsl2ShdsldeviceFault,
--   	    hdsl2ShdsldcContinuityFault,
--  	    hdsl2ShdslconfigInitFailure,
--   	    hdsl2ShdslprotocolInitFailure,
--   	    hdsl2ShdslnoNeighborPresent,
--   	    hdsl2ShdslLocalPowerLoss
--   	}
--   	STATUS  mandatory
--   	DESCRIPTION
--     		"This group supports notifications of significant conditions
--    		 associated with HDSL2/SHDSL lines."
--   	::= { hdsl2ShdslGroups 12 }
--
--	hdsl2ShdslSpanConfProfileGroup OBJECT-GROUP OBJECTS {
--   	    hdsl2ShdslSpanConfWireInterface,
--  	    hdsl2ShdslSpanConfMinLineRate,
--   	    hdsl2ShdslSpanConfMaxLineRate,
--   	    hdsl2ShdslSpanConfPSD,
--   	    hdsl2ShdslSpanConfTransmissionMode,
--   	    hdsl2ShdslSpanConfRemoteEnabled,
--   	    hdsl2ShdslSpanConfPowerFeeding,
--   	    hdsl2ShdslSpanConfCurrCondTargetMarginDown,
--   	    hdsl2ShdslSpanConfWorstCaseTargetMarginDown,
--   	    hdsl2ShdslSpanConfCurrCondTargetMarginUp,
--   	    hdsl2ShdslSpanConfWorstCaseTargetMarginUp,
--   	    hdsl2ShdslSpanConfUsedTargetMargins,
--   	    hdsl2ShdslSpanConfReferenceClock,
--   	    hdsl2ShdslSpanConfLineProbeEnable,
--  	    hdsl2ShdslSpanConfProfileRowStatus
--   	}
--   	STATUS  mandatory
--   	DESCRIPTION
--     		"This group supports objects that constitute configuration
--     		 profiles for configuring span related parameters in SHDSL
--      		 lines."
--  	::= { hdsl2ShdslGroups 13 }

END
