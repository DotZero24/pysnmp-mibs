-- This file is corresponding to Release 9.1.10.101 from 2014/08/11 00:00:00


-- (C)opyright 1991-2014 bintec elmeg GmbH, All Rights Reserved
--  $RCSfile: mibfr,v $
-- $Revision: 1.15 $

BIANCA-BRICK-FR-MIB DEFINITIONS ::= BEGIN

        IMPORTS
            Counter, enterprises
                FROM RFC1155-SMI

            OBJECT-TYPE
                FROM RFC-1212;

    bintec      OBJECT IDENTIFIER ::= { enterprises 272 }
    bibo        OBJECT IDENTIFIER ::= { bintec 4 }
    fr          OBJECT IDENTIFIER
        ::= { bibo 13 }


	frMprTable OBJECT-TYPE
	    SYNTAX  SEQUENCE OF FrMprEntry
	    ACCESS  not-accessible
	    STATUS  mandatory
	    DESCRIPTION
		"This table contains an entry for each frame relay DCE
		 virtual interface. This interface is called virtual
		 because it does not necessarily reflect to a single
		 hardware interface; it is possible to either narrow
		 (many hardware interfaces looking as a single virtual)
		 or widen (a single hardware interface with several VCs
		 is mapped to several virtual interfaces) the interface.

		 Entries in this table are created manually and will result
		 to the creation of a multiprotocol routing interface in
		 the ifTable. This interface can than be used by higher
		 level protocols like ip, ipx and bridging.

		 The object frMprIfIndex shall be set to 0 for creation
		 of new entries. The BRICK will allocate the next free
		 interface index and assign it to frMprIfIndex.

		 Rows of this table can be deleted by setting the object
		 frMprEncapsulation to the value delete.
		 "
	::= { fr 1 }

	frMprEntry OBJECT-TYPE
	    SYNTAX  FrMprEntry
	    ACCESS  not-accessible
	    STATUS  mandatory
	    DESCRIPTION
		""
	    INDEX   { frMprIfIndex }
	::= { frMprTable 1 }

	FrMprEntry ::=
	    SEQUENCE {
		frMprIfIndex				INTEGER,
		frMprMtu				INTEGER,
		frMprEncapsulation			INTEGER,
		frMprIfcType				INTEGER,
		frMprInverseArp				INTEGER
	    }

	frMprIfIndex OBJECT-TYPE
	    SYNTAX  INTEGER
	    ACCESS  read-write
	    STATUS  mandatory

	    DESCRIPTION
		"This object contains an interface index and assigns the
		 row to an entry in ifTable. When creating new entries
		 in the table, the value of this object shall be set to 0.
		 The next free ifIndex value is than allocated
		 by the BRICK and assigned to the object. At the same
		 time a new interface is created in the IfTable."
	    DEFVAL { 0 }
	::= { frMprEntry 1 }

	frMprMtu OBJECT-TYPE
	    SYNTAX  INTEGER (576..8180)
	    ACCESS  read-write
	    STATUS  mandatory

	    DESCRIPTION
		"The Maximum transfer unit to be used with the interface
		 (see also ifMtu)."
	    DEFVAL { 1500 }
	::= { frMprEntry 2 }

	frMprEncapsulation OBJECT-TYPE
	    SYNTAX  INTEGER {
		mpr(1), delete(7)
	    }
	    ACCESS  read-write
	    STATUS  mandatory

	    DESCRIPTION
		"This object specifies the encapsulation method to be used.

		 If this object is set to mpr, the encapsulation method
		 described in Q933a is used for the protocols IP, IPX
		 and transparent bridging. This encapsulation is also
		 explained in RFC 1490.
		"
	    DEFVAL { mpr }
	::= { frMprEntry 3 }

	frMprIfcType OBJECT-TYPE
	    SYNTAX  INTEGER {
		multipoint(1), point-to-point(2)
	    }
	    ACCESS  read-write
	    STATUS  mandatory

	    DESCRIPTION
		"This object specifies wether the interface is a
		 multipoint(1) or a point-to-point(2) interface."
	    DEFVAL { point-to-point }
	::= { frMprEntry 4 }

	frMprInverseArp OBJECT-TYPE
	    SYNTAX  INTEGER {
		enabled(1), disabled(2)
	    }
	    ACCESS  read-write
	    STATUS  mandatory

	    DESCRIPTION
		"This object specifies the use of Inverse Arp (as
		 described in RFC 1490) to automatically detect
		 upper layer network addresses."
	    DEFVAL { disabled }
	::= { frMprEntry 5 }


END
