-- This file is corresponding to Release 9.1.10.101 from 2014/08/11 00:00:00


-- (C)opyright 1991-2014 bintec elmeg GmbH, All Rights Reserved
--  $RCSfile: mibcapiuser,v $
-- $Revision: 1.7 $

BIANCA-BRICK-CAPIUSER-MIB DEFINITIONS ::= BEGIN

        IMPORTS
            Counter, enterprises
                FROM RFC1155-SMI

            DisplayString
                FROM RFC1158-MIB

            HexValue
                FROM BINTEC-MIB

            OBJECT-TYPE
                FROM RFC-1212;

    bintec 	OBJECT IDENTIFIER ::= { enterprises 272 }
    bibo	OBJECT IDENTIFIER ::= { bintec 4 }
    capi	OBJECT IDENTIFIER
	::= { bibo 7 }


    -- CAPI Group

    -- Management Information for the CAPI Subsystem of the BIANCA/BRICK

        capiUserTable OBJECT-TYPE
            SYNTAX  SEQUENCE OF CapiUserEntry
            ACCESS  not-accessible
            STATUS  mandatory
            DESCRIPTION
		"The capiUserTable contains information about the capi users.
		 CAPI users must authenticate to the system by means
		 of user name and password, before active or passive
		 connections may be established. The default configuration
		 defines a user named <default> with all permissions. This
		 user will also be used by old CAPI applications which are
		 not able to select a user. Please note, that the password
		 for the user <default> must be empty in this case.

		 Entries in this table can be deleted by setting
		 the object capiUserCapi to the value <delete>."
	::= { capi 8 }

	capiUserEntry OBJECT-TYPE
            SYNTAX  CapiUserEntry
            ACCESS  not-accessible
            STATUS  mandatory
            DESCRIPTION
		""
	    INDEX   { capiUserName }
              ::= { capiUserTable 1 }

	CapiUserEntry ::=
            SEQUENCE {
		capiUserName			DisplayString,
		capiUserPassword		DisplayString,
		capiUserCapi			INTEGER
            }

	capiUserName OBJECT-TYPE
	    SYNTAX  DisplayString (SIZE (0..15))
	    ACCESS  read-write
	    STATUS  mandatory
	    DESCRIPTION
		"The name of the user."
	::= { capiUserEntry 1 }

	capiUserPassword OBJECT-TYPE
            SYNTAX  DisplayString (SIZE (0..15))
            ACCESS  read-write
	    STATUS  mandatory
            DESCRIPTION
	    "The password for the user."
	::= { capiUserEntry 2 }

	capiUserCapi OBJECT-TYPE
            SYNTAX  INTEGER {
		enable(1),
		disable(2),
		delete(3)
	    }
            ACCESS  read-write
            STATUS  mandatory
            DESCRIPTION
                "Allow or deny the usage of CAPI."
	    DEFVAL { enable }
	::= { capiUserEntry 6 }

END
