-- This file is corresponding to Release 9.1.10.101 from 2014/08/11 00:00:00


-- (C)opyright 2006-2014 bintec elmeg GmbH
-- $RCSfile: mib-session,v $
-- $Revision: 1.16 $

BIANCA-BRICK-SESSION-MIB DEFINITIONS ::= BEGIN

        IMPORTS
            IpAddress, Counter, enterprises
                FROM RFC1155-SMI

            DisplayString
                FROM RFC1158-MIB

	    HexValue
		FROM BINTEC-MIB

            OBJECT-TYPE
                FROM RFC-1212

	    bibo, biboip
		FROM BINTEC-MIB;

---------------------------------------------------------------------------

ipRTPSessionMIB MODULE-IDENTITY
    LAST-UPDATED "201004190000Z"
    ORGANIZATION "bintec elmeg GmbH"
    CONTACT-INFO "EMail:   info@bintec-elmeg.com
                  Web:     www.bintec-elmeg.com"
    DESCRIPTION  "Management Information for RTP session handling"

    ::= { bibo 66 }

---------------------------------------------------------------------------

    bintec      OBJECT IDENTIFIER ::= { enterprises 272 }
    bibo        OBJECT IDENTIFIER ::= { bintec 4 }
    biboip      OBJECT IDENTIFIER
        ::= { bibo 5 }

   	ipRTPSessionTable OBJECT-TYPE
	    SYNTAX SEQUENCE OF IpRTPSessionEntry
            MAX-ACCESS not-accessible
            STATUS current
            DESCRIPTION
                "Table with all current RTP Sessions"
        ::= { biboip 58 }

        ipRTPSessionEntry OBJECT-TYPE
            SYNTAX IpRTPSessionEntry
            MAX-ACCESS not-accessible
            STATUS current
            DESCRIPTION
		" Contains the description of a RTP Stream Session "
            INDEX { ipRTPIndex }
        ::= { ipRTPSessionTable 1 }


	IpRTPSessionEntry ::=
            SEQUENCE {
		ipRTPIndex		INTEGER,
		ipRTPSourceAddress	IpAddress,
		ipRTPSourcePort		INTEGER,
		ipRTPSourceIf		INTEGER,
		ipRTPDestinationAddress	IpAddress,
		ipRTPDestinationPort	INTEGER,
		ipRTPDestinationIf	INTEGER,
		ipRTPSessionIdent	INTEGER,
		ipRTPSessionState	INTEGER,
		ipRTPSessionPayload	INTEGER,
		ipRTPSessionSSRC	HexValue,
		ipRTPSessionPackets	INTEGER,
		ipRTPSessionManage 	INTEGER
           }


	ipRTPIndex OBJECT-TYPE
	    SYNTAX  INTEGER
	    MAX-ACCESS  read-only
	    STATUS  current
	    DESCRIPTION
		" Index of the RTP Session "
	::= { ipRTPSessionEntry 1 }

	ipRTPSourceAddress OBJECT-TYPE
	    SYNTAX  IpAddress
	    MAX-ACCESS  read-only
	    STATUS  current
	    DESCRIPTION
		" Source Address of the RTP Session"
	::= { ipRTPSessionEntry 2 }


	ipRTPSourcePort OBJECT-TYPE
	    SYNTAX  INTEGER (0..65535)
	    MAX-ACCESS  read-only
	    STATUS  current
	    DESCRIPTION
		" Source Port of the RTP Session"
	::= { ipRTPSessionEntry 3 }


	ipRTPSourceIf OBJECT-TYPE
	    SYNTAX  INTEGER
	    MAX-ACCESS  read-only
	    STATUS  current
	    DESCRIPTION
		" Source Interface of the RTP Session "
	::= { ipRTPSessionEntry 4 }

	ipRTPDestinationAddress OBJECT-TYPE
	    SYNTAX  IpAddress
	    MAX-ACCESS  read-only
	    STATUS  current
	    DESCRIPTION
		" Destination Address of the RTP Session "
	::= { ipRTPSessionEntry 5 }


	ipRTPDestinationPort OBJECT-TYPE
	    SYNTAX  INTEGER (0..65535)
	    MAX-ACCESS  read-only
	    STATUS  current
	    DESCRIPTION
		" Destination Port of the RTP Session "
	::= { ipRTPSessionEntry 6 }


	ipRTPDestinationIf OBJECT-TYPE
	    SYNTAX  INTEGER
	    MAX-ACCESS  read-only
	    STATUS  current
	    DESCRIPTION
		" Destination Interface of the RTP Session "
	::= { ipRTPSessionEntry 7 }


	ipRTPSessionIdent OBJECT-TYPE
	    SYNTAX INTEGER
	    MAX-ACCESS  read-only
	    STATUS  current
	    DESCRIPTION
		" Identifier of the RTP Session "
	::= { ipRTPSessionEntry 8 }


	ipRTPSessionState OBJECT-TYPE
	    SYNTAX INTEGER {
		new(1),
		init(2),
		check(3),
		up(4),
		delete(8)
	    }
	    MAX-ACCESS  read-only
	    STATUS  current
	    DESCRIPTION
		" State of the RTP Session "
	::= { ipRTPSessionEntry 9 }



	ipRTPSessionSSRC OBJECT-TYPE
	    SYNTAX  HexValue
	    MAX-ACCESS  read-only
	    STATUS  current
	    DESCRIPTION
		" Unique RTP Session Identifier (SSRC field in RTP header) "
	::= { ipRTPSessionEntry 10 }


	ipRTPSessionPayload OBJECT-TYPE
	    SYNTAX  INTEGER (0..255)
	    MAX-ACCESS  read-only
	    STATUS  current
	    DESCRIPTION
		" Payload Type of the RTP Stream (alaw, ulaw...) "
	::= { ipRTPSessionEntry 11 }


	ipRTPSessionPackets OBJECT-TYPE
	    SYNTAX  INTEGER
	    MAX-ACCESS  read-only
	    STATUS  current
	    DESCRIPTION
		" Current Packets of the RTP Stream (session_handler only) "
	::= { ipRTPSessionEntry 12 }

	ipRTPSessionManage OBJECT-TYPE
	    SYNTAX  INTEGER {
		session-handler(1),
		media-gateway(2),
		application-gateway(3)
	    }
	    MAX-ACCESS  read-only
	    STATUS  current
	    DESCRIPTION
		" Creator of the RTP entry "
	    DEFVAL { session-handler }
	::= { ipRTPSessionEntry 13 }


END
