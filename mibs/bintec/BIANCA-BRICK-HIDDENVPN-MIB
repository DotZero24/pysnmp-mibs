-- This file is corresponding to Release 9.1.10.101 from 2014/08/11 00:00:00


-- (C)opyright 2004-2014 bintec elmeg GmbH, All Rights Reserved
-- $RCSfile: mibhiddenvpn,v $
-- $Revision: 1.8 $

BIANCA-BRICK-HIDDENVPN-MIB DEFINITIONS ::= BEGIN

	IMPORTS
	    NetworkAddress, IpAddress, Counter, Gauge, TimeTicks, enterprises
		FROM RFC1155-SMI

	    OBJECT-TYPE
		FROM RFC-1212;

	--  This MIB module uses the extended OBJECT-TYPE macro as
	--  defined in [14];


	--  MIB-II (same prefix as MIB-I)
	bintec 		OBJECT IDENTIFIER ::= { enterprises 272 }
	bibo		OBJECT IDENTIFIER ::= { bintec 4 }

	admin		OBJECT IDENTIFIER
	    ::= { bibo 1 }

    biboAdmLed     OBJECT IDENTIFIER
            ::= { bintec 253 }

	biboAdmLedStatus OBJECT-TYPE
	    SYNTAX  INTEGER { off(1), on(2), blink(3), flash(4) }
	    ACCESS  read-only
	    STATUS  mandatory
	    DESCRIPTION
		""
	::= { biboAdmLed 1 }

	biboAdmLedMgmt OBJECT-TYPE
	    SYNTAX  INTEGER { off(1), on(2), blink(3), flash(4) }
	    ACCESS  read-only
	    STATUS  mandatory
	    DESCRIPTION
		""
	::= { biboAdmLed 2 }

	biboAdmLedHA OBJECT-TYPE
	    SYNTAX  INTEGER { off(1), on(2), blink(3), flash(4) }
	    ACCESS  read-only
	    STATUS  mandatory
	    DESCRIPTION
		""
	::= { biboAdmLed 3 }

	biboAdmLedInternet OBJECT-TYPE
	    SYNTAX  INTEGER { off(1), on(2), blink(3), flash(4) }
	    ACCESS  read-only
	    STATUS  mandatory
	    DESCRIPTION
		""
	::= { biboAdmLed 4 }

	biboAdmLedSwitch OBJECT-TYPE
	    SYNTAX  INTEGER { off(1), on(2), blink(3), linkact(4) }
	    ACCESS  read-only
	    STATUS  mandatory
	    DESCRIPTION
		""
	::= { biboAdmLed 5 }

	biboAdmLedMeter OBJECT-TYPE
	    SYNTAX  INTEGER { enabled(1), disabled(2) }
	    ACCESS  read-write
	    STATUS  mandatory
	    DESCRIPTION
		""
	    DEFVAL { disabled }
	::= { biboAdmLed 6 }

END
