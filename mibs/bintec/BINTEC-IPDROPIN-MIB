-- This file is corresponding to Release 9.1.10.101 from 2014/08/11 00:00:00


---------------------------------------------------------------------------
-- (C)opyright 2011-2014 bintec elmeg GmbH, All Rights Reserved
-- $RCSfile: mib-ipdropin,v $
-- $Revision: 1.8 $
-- $Date: 2014-02-07 10:37:49 $
-- Author: awimmer
---------------------------------------------------------------------------

BINTEC-IPDROPIN-MIB DEFINITIONS ::= BEGIN

        IMPORTS
        enterprises
                FROM RFC1155-SMI
        IpAddress, enterprises
                FROM RFC1155-SMI
        MacAddress, DisplayString, TimeStamp, TruthValue
                FROM SNMPv2-TC
        Date, BitValue, biboip
                FROM BINTEC-MIB
        MODULE-IDENTITY, OBJECT-TYPE, NOTIFICATION-TYPE, Counter32, Counter64, TimeTicks
                FROM SNMPv2-SMI
        TRAP-TYPE
                FROM RFC-1215
        TruthValue
                FROM SNMPv2-TC
        ifIndex
                FROM IF-MIB
        OBJECT-TYPE
                FROM RFC-1212
        MODULE-COMPLIANCE, OBJECT-GROUP, NOTIFICATION-GROUP
                FROM SNMPv2-CONF
        InetAddressType, InetAddress
                FROM INET-ADDRESS-MIB;

ipDropinMIB MODULE-IDENTITY
    LAST-UPDATED "201212040000Z"
    ORGANIZATION "bintec elmeg GmbH"
    CONTACT-INFO
            "EMail:   info@bintec-elmeg.com
             Web:     www.bintec-elmeg.com
            "
    DESCRIPTION
            "The MIB module for the IP drop-in mode."
    REVISION      "201101250000Z"
    DESCRIPTION
            "Vendor specific Management Information for the IP subsystem."
    ::= { biboip 249 }


-- **********************************************************************
-- *    ipDropinGroupTable  TABLE
-- **********************************************************************

ipDropinGroupTable OBJECT-TYPE
    SYNTAX  SEQUENCE OF IpDropinGroupEntry
    MAX-ACCESS  not-accessible
    STATUS  current
    DESCRIPTION
            "The ipDropinGroupTable contains information related to
             IP drop-in mode on the system.
	     Entries can only be added or deleted by the administrator."
    ::= { biboip 64 }


        ipDropinGroupEntry OBJECT-TYPE
            SYNTAX  IpDropinGroupEntry
            MAX-ACCESS  not-accessible
            STATUS  current
            DESCRIPTION
                ""
            INDEX   { ipDropinGroupIndex }
              ::= { ipDropinGroupTable 1 }

        IpDropinGroupEntry ::=
           SEQUENCE {
                ipDropinGroupIndex		INTEGER,
		ipDropinGroupDescr		DisplayString,
		ipDropinGroupNetworkAddr	IpAddress,
		ipDropinGroupNetworkMask	IpAddress,
		ipDropinGroupLocalAddr		IpAddress,
                ipDropinGroupAdminStatus	INTEGER,
		ipDropinGroupMode		INTEGER,
		ipDropinGroupNetworkConfig	INTEGER,
		ipDropinGroupDhcpClientIfIndex	INTEGER,
		ipDropinGroupArpLifeTime	INTEGER,
		ipDropinGroupDhcpDnsAssign	INTEGER,
		ipDropinGroupExcludeFromNat	INTEGER,
		ipDropinGroupArpPolicy		INTEGER,
		ipDropinGroupUsedNetworkAddr	IpAddress,
		ipDropinGroupUsedNetworkMask	IpAddress,
		ipDropinGroupUsedLocalAddr	IpAddress
            }

        ipDropinGroupIndex OBJECT-TYPE
            SYNTAX  INTEGER
            MAX-ACCESS  read-write
            STATUS  current
            DESCRIPTION
                "Unique group index."
        ::= { ipDropinGroupEntry 1 }

	ipDropinGroupDescr OBJECT-TYPE
	    SYNTAX  DisplayString (SIZE (0..255))
	    MAX-ACCESS  read-write
	    STATUS  current
	    DESCRIPTION
		"A textual string describing this IP drop-in group."
        ::= { ipDropinGroupEntry 2 }

	ipDropinGroupNetworkAddr OBJECT-TYPE
	    SYNTAX  IpAddress
	    MAX-ACCESS  read-write
	    STATUS  current
	    DESCRIPTION
		"This object describes together with ipDropinGroupNetworkMask
		 the network defined for this IP drop-in group."
        ::= { ipDropinGroupEntry 3 }

	ipDropinGroupNetworkMask OBJECT-TYPE
	    SYNTAX  IpAddress
	    MAX-ACCESS  read-write
	    STATUS  current
	    DESCRIPTION
		"This object describes together with ipDropinGroupNetworkAddr
		 the network defined for this IP drop-in group."
        ::= { ipDropinGroupEntry 4 }

	ipDropinGroupLocalAddr OBJECT-TYPE
	    SYNTAX  IpAddress
	    MAX-ACCESS  read-write
	    STATUS  current
	    DESCRIPTION
		"This object defines the configured local IP address
		 accessible via all interfaces associated with this
		 drop-in-group."
        ::= { ipDropinGroupEntry 5 }

        ipDropinGroupAdminStatus OBJECT-TYPE
            SYNTAX  INTEGER {
                enabled (1),
                disabled (2),
                delete (3)
                }
            MAX-ACCESS  read-write
            STATUS  current
            DESCRIPTION
                "The administrative status of this drop-in group."
            DEFVAL { enabled }
        ::= { ipDropinGroupEntry 6 }

        ipDropinGroupMode OBJECT-TYPE
            SYNTAX  INTEGER {
                transparent (1),
                proxy (2),
                secure-proxy (3)
                }
            MAX-ACCESS  read-write
            STATUS  current
            DESCRIPTION
                "The operational mode of this drop-in group."
            DEFVAL { transparent }
        ::= { ipDropinGroupEntry 7 }

        ipDropinGroupNetworkConfig OBJECT-TYPE
            SYNTAX  INTEGER {
                static (1),
                dhcp (2)
                }
            MAX-ACCESS  read-write
            STATUS  current
            DESCRIPTION
                "Determines the source of the network configuration
		 of this drop-in group. If set to static (1) it's  determined
		 by the configured parameters 'ipDropinGroupNetworkAddr' and
		 'ipDropinGroupNetworkMask', if set to dhcp (2) it's
		 determined by the DHCP servers' DHCP OFFER message."
            DEFVAL { static }
        ::= { ipDropinGroupEntry 8 }

        ipDropinGroupDhcpClientIfIndex OBJECT-TYPE
            SYNTAX  INTEGER
            MAX-ACCESS  read-write
            STATUS  current
            DESCRIPTION
                "In case of ipDropinGroupNetworkConfig_dhcp (2) this variable
		 determines the associated interface running in DHCP client
		 mode. In this case setting this variable is mandatory."
        ::= { ipDropinGroupEntry 9 }

        ipDropinGroupArpLifeTime OBJECT-TYPE
	    SYNTAX  INTEGER (0..86400)
	    UNITS   "seconds"
            MAX-ACCESS  read-write
            STATUS  current
            DESCRIPTION
                "This object defines the minimum lifetime (in seconds) of
		 associated but unused ipNetToMediaTable entries."
	    DEFVAL { 3600 }
        ::= { ipDropinGroupEntry 10 }

        ipDropinGroupDhcpDnsAssign OBJECT-TYPE
	    SYNTAX  INTEGER { passthrough(1), self(2) }
            MAX-ACCESS  read-write
            STATUS  current
            DESCRIPTION
                "This variable determines the DNS server assignment policy,
		 if set to passthrough (1) the DHCP domain server tag(s) will
		 be passed unchanged, if set to self (2) the IP address set in
		 'ipDropinGroupUsedLocalAddr' is provided as first nameserver
		 address."
	    DEFVAL { passthrough }
        ::= { ipDropinGroupEntry 11 }

        ipDropinGroupExcludeFromNat OBJECT-TYPE
	    SYNTAX  INTEGER { disabled(1), enabled(2) }
            MAX-ACCESS  read-write
            STATUS  current
            DESCRIPTION
                "This variable determines, in conjunction with the variable
		 'ipDropinIfExcludeFromNat', whether the NAT procedure is
		 bypassed for IP addresses (source or target) within the
		 drop-in network - with exception of the address
		 'ipDropinGroupUsedLocalAddr' itself. If set to enabled (2)
		 NAT-less communication initiated from or addressed to the
		 drop-in network is possible, needed for non-private
		 DMZ networks for example."
	    DEFVAL { disabled }
        ::= { ipDropinGroupEntry 12 }

        ipDropinGroupArpPolicy OBJECT-TYPE
	    SYNTAX  INTEGER { default(1), static-only(2) }
            MAX-ACCESS  read-write
            STATUS  current
            DESCRIPTION
                "This object enables/disables active and passive ARP
		 processing for the associated drop-in network. If set to
		 static-only (2) only predefined or already existing
		 IP/MAC-address relations (see ipNetToMediaTable) will be
		 considered for packet distribution."
	    DEFVAL { default }
        ::= { ipDropinGroupEntry 13 }

	ipDropinGroupUsedNetworkAddr OBJECT-TYPE
	    SYNTAX  IpAddress
	    MAX-ACCESS  read-only
	    STATUS  current
	    DESCRIPTION
		"This object describes together with 'ipDropinGroupUsedNetworkMask'
		 the network used for the IP drop-in mode."
        ::= { ipDropinGroupEntry 20 }

	ipDropinGroupUsedNetworkMask OBJECT-TYPE
	    SYNTAX  IpAddress
	    MAX-ACCESS  read-only
	    STATUS  current
	    DESCRIPTION
		"This object describes together with 'ipDropinGroupUsedNetworkAddr'
		 the network used for the IP drop-in mode."
        ::= { ipDropinGroupEntry 21 }

	ipDropinGroupUsedLocalAddr OBJECT-TYPE
	    SYNTAX  IpAddress
	    MAX-ACCESS  read-only
	    STATUS  current
	    DESCRIPTION
		"This object defines the local IP address currently used on
		 all interfaces associated with this drop-in group."
        ::= { ipDropinGroupEntry 22 }


-- **********************************************************************
-- *    ipDropinIfTable  TABLE
-- **********************************************************************

ipDropinIfTable OBJECT-TYPE
    SYNTAX  SEQUENCE OF IpDropinIfEntry
    MAX-ACCESS  not-accessible
    STATUS  current
    DESCRIPTION
            "The ipDropinIfTable contains extended information related to
             IP drop-in mode and associated interfaces.
	     Entries can only be added or deleted by the administrator."
    ::= { biboip 65 }


        ipDropinIfEntry OBJECT-TYPE
            SYNTAX  IpDropinIfEntry
            MAX-ACCESS  not-accessible
            STATUS  current
            DESCRIPTION
                "."
            INDEX   { ipDropinIfIndex, ipDropinIfGroup }
              ::= { ipDropinIfTable 1 }

        IpDropinIfEntry ::=
           SEQUENCE {
                ipDropinIfIndex			INTEGER,
		ipDropinIfDescr			DisplayString,
                ipDropinIfGroup			INTEGER,
                ipDropinIfAdminStatus		INTEGER,
		ipDropinIfExcludeFromNat	INTEGER
            }

        ipDropinIfIndex OBJECT-TYPE
            SYNTAX  INTEGER
            MAX-ACCESS  read-write
            STATUS  current
            DESCRIPTION
                "Index of interface to be associated with drop-in group."
        ::= { ipDropinIfEntry 1 }

	ipDropinIfDescr OBJECT-TYPE
	    SYNTAX  DisplayString (SIZE (0..255))
	    MAX-ACCESS  read-write
	    STATUS  current
	    DESCRIPTION
		"A textual string describing this IP drop-in interface."
        ::= { ipDropinIfEntry 2 }

        ipDropinIfGroup OBJECT-TYPE
            SYNTAX  INTEGER
            MAX-ACCESS  read-write
            STATUS  current
            DESCRIPTION
                "Associated drop-in group."
        ::= { ipDropinIfEntry 3 }

        ipDropinIfAdminStatus OBJECT-TYPE
            SYNTAX  INTEGER {
                enabled (1),
                disabled (2),
                delete (3)
                }
            MAX-ACCESS  read-write
            STATUS  current
            DESCRIPTION
                "Administrative status in order to switch on/off the drop-in
		 mode for the interface."
            DEFVAL { enabled }
        ::= { ipDropinIfEntry 4 }

        ipDropinIfExcludeFromNat OBJECT-TYPE
	    SYNTAX  INTEGER { disabled(1), enabled(2) }
            MAX-ACCESS  read-write
            STATUS  current
            DESCRIPTION
                "This variable determines, in conjunction with the variable
		 'ipDropinGroupExcludeFromNat', whether the NAT procedure is
		 bypassed for IP addresses (source or target) within the
		 drop-in network - with exception of the address
		 'ipDropinGroupUsedLocalAddr' itself. If set to enabled (2)
		 NAT-less communication initiated from or addressed to the
		 drop-in network is possible, needed for non-private
		 DMZ networks for example."
            DEFVAL { enabled }
        ::= { ipDropinIfEntry 5 }




END
