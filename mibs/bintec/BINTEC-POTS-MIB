-- This file is corresponding to Release 9.1.10.101 from 2014/08/11 00:00:00


-- (C)opyright 1999-2014 bintec elmeg GmbH
-- All Rights Reserved
-- $RCSfile: mib-pots,v $
-- $Revision: 1.16 $

BINTEC-POTS-MIB DEFINITIONS ::= BEGIN

IMPORTS
    MODULE-IDENTITY, OBJECT-TYPE, NOTIFICATION-TYPE,
    Integer32, Unsigned32, Counter32, Counter64, IpAddress, TimeTicks,
    mib-2, enterprises
        FROM SNMPv2-SMI

    DisplayString, TimeStamp, TruthValue
        FROM SNMPv2-TC

    bibo, Date, BitValue, HexValue
        FROM BINTEC-MIB

    MODULE-COMPLIANCE, OBJECT-GROUP, NOTIFICATION-GROUP
        FROM SNMPv2-CONF;


potsMIB MODULE-IDENTITY
    LAST-UPDATED "201211090000Z"
    ORGANIZATION "bintec elmeg GmbH"
    CONTACT-INFO
            "EMail:   info@bintec-elmeg.com
             Web:     www.bintec-elmeg.com
            "
    DESCRIPTION
            "The MIB module for POTS interface administration entities.
            "
    REVISION      "200904230000Z"
    DESCRIPTION
            "POTS administration used for FXS and FXO interfaces.
            "
    REVISION      "201105090000Z"
    DESCRIPTION
            "POTS administration used for FXS and FXO interfaces.
             Redesign of FXO tone detection part.
            "

        ::= { bibo 14 }

    -- INTERFACES Group

-- ~~~~~~~~~~~~~~~~~~~~~~~~~~~~~~~~~~~~~~~~~~~~~~~~~~~~~~~~~~~~~~~~~~~~~~~~
-- POTS OID groups & all tables
-- ~~~~~~~~~~~~~~~~~~~~~~~~~~~~~~~~~~~~~~~~~~~~~~~~~~~~~~~~~~~~~~~~~~~~~~~~
pots            OBJECT IDENTIFIER ::= { potsMIB 1 }
                -- potsIfTable                          1
                -- potsIfFxoTable                       2
                -- potsIfFxsTable                       3
                -- potsIfToneTable                      4
                -- potsIfToneDefinitionTable            5
                -- potsIfRingTable                      6
                -- potsIfDataLinkTimerTable             7

-- ~~~~~~~~~~~~~~~~~~~~~~~~~~~~~~~~~~~~~~~~~~~~~~~~~~~~~~~~~~~~~~~~~~~~~~~~
-- POTS TYPES
-- ~~~~~~~~~~~~~~~~~~~~~~~~~~~~~~~~~~~~~~~~~~~~~~~~~~~~~~~~~~~~~~~~~~~~~~~~
PotsIfIndex             ::= INTEGER             -- table index
ReceiveLevel            ::= INTEGER (-50..0)    -- for tones in dB
TransmitLevel           ::= INTEGER (-30..0)    -- for tones in dB
RingTabIndex            ::= INTEGER             -- table index
ToneTabIndex            ::= INTEGER             -- table index
ToneDefTabIndex         ::= INTEGER             -- table index
ToneFrequency           ::= INTEGER (300..3400) -- value in Hz
CadenceTimingTolerance  ::= INTEGER (0..100)    -- tolerance in percent
CadenceString           ::= DisplayString (SIZE (0..127))
DataLinkTimerTabIndex   ::= Unsigned32          -- table index

-- ~~~~~~~~~~~~~~~~~~~~~~~~~~~~~~~~~~~~~~~~~~~~~~~~~~~~~~~~~~~~~~~~~~~~~~~~
-- DEFAULT VALUES
-- ~~~~~~~~~~~~~~~~~~~~~~~~~~~~~~~~~~~~~~~~~~~~~~~~~~~~~~~~~~~~~~~~~~~~~~~~
-- All entries which must have a value by default are filled with
-- values commonly used in germany because germany is the default
-- country


-- ~~~~~~~~~~~~~~~~~~~~~~~~~~~~~~~~~~~~~~~~~~~~~~~~~~~~~~~~~~~~~~~~~~~~~~~~
-- 1. potsIfTable:  POTS Interface Table
-- ~~~~~~~~~~~~~~~~~~~~~~~~~~~~~~~~~~~~~~~~~~~~~~~~~~~~~~~~~~~~~~~~~~~~~~~~

    potsIfTable OBJECT-TYPE
        SYNTAX          SEQUENCE OF PotsIfEntry
        MAX-ACCESS      not-accessible
        STATUS          current
        DESCRIPTION
            "The potsIfTable contains configuration information
            for the POTS outlets."
        ::= { pots 1 }

    potsIfEntry         OBJECT-TYPE
        SYNTAX          PotsIfEntry
        MAX-ACCESS      not-accessible
        STATUS          current
        DESCRIPTION
            ""
        INDEX           { potsSlot, potsUnit }
        ::= { potsIfTable 1 }

    PotsIfEntry ::=
        SEQUENCE {
            potsSlot                        INTEGER,
            potsUnit                        INTEGER,
            potsType                        INTEGER,
            potsIfMode                      INTEGER,
            potsIfAdminState                INTEGER,
            potsIfOperState                 INTEGER,
            potsIfIndex                     INTEGER,
            potsIfTtxLevel                  INTEGER,
            potsIfTtxFreq                   INTEGER,
            potsIfCoeffIndex                INTEGER,
            potsIfTxGain                    INTEGER,
            potsIfRxGain                    INTEGER,
            potsIfDialInTimeout             INTEGER
        }

    potsSlot OBJECT-TYPE
        SYNTAX          INTEGER (0..31)
        MAX-ACCESS      read-only
        STATUS          current
        DESCRIPTION
            "Identification number of the used slot."
        ::= { potsIfEntry 1 }

    potsUnit OBJECT-TYPE
        SYNTAX          INTEGER (0..31)
        MAX-ACCESS      read-only
        STATUS          current
        DESCRIPTION
            "Identification number of the used unit."
        ::= { potsIfEntry 2 }

    potsType OBJECT-TYPE
        SYNTAX          INTEGER {
                                  any(1),
                                  fax(2),
                                  telephony(3),
                                  modem(4),
                                  disable(5),
                                  doorintercom(6),
                                  answering(7),
                                  emergency(8),
                                  alarmInput(9)
                                }
        MAX-ACCESS      read-write
        STATUS          current
        DESCRIPTION
            "The type of the connected device on socket a.

             Possible values are:
                       - any(1),       (multifunctional)
                       - fax(2),
                       - telephony(3),
                       - modem(4),
                       - disable(5),
                       - doorintercom(6),
                       - answering(7), (-machine)
                       - emergency(8)  (-telephone)
                       - alarmInput(9) (sensor function)
            "
        DEFVAL          { any }
        ::= { potsIfEntry 3 }

-- NOTE: OIDs potsIfEntry.4-7 were defined before and got replaced by the
--       following OIDs; as only MGCP and old XCentric's BOSS used this table
--       the replacement shouldn't bother

    potsIfMode         OBJECT-TYPE
        SYNTAX          INTEGER { fxo(1), fxs(2) }
        MAX-ACCESS      read-only
        STATUS          current
        DESCRIPTION
            "Type of outlet."
        DEFVAL          { fxs }
        ::= { potsIfEntry 4 }

    potsIfAdminState OBJECT-TYPE
        SYNTAX          INTEGER {
                                  down(1),
                                  up(2),
                                  reconfig(3)
                                }
        MAX-ACCESS      read-write
        STATUS          current
        DESCRIPTION
        "This variable allows for taking an POTS interface out of/in
         service w/o having to touch the configuration.

         Besides, it is possible to initiate a reconfiguration for that
         interface in case a mismatch in configuration parameters
         (hardware vs. software) was detected.

         Inconsistencies with the need of reconfiguration is a differing
         potsIfMode (fxo/fxs).

         In case of mismatch, contents of this variable might be
         wrong and this circumstance is reflected in variable
         potsIfOperState. State reconfig may then be used in order to
         cause an update of these variable as appropriate which ...
           - will be signalled to higher protocol layers, and
           - can result in extensive reconfiguration steps
         The latter may also cover clean-ups undoable by system so this
         decision is left to the user.

         Default value is down."

        DEFVAL          { down }
        ::= { potsIfEntry 5 }

    potsIfOperState OBJECT-TYPE
        SYNTAX          INTEGER {
                                  down(1),
                                  running(2),
                                  fail(3),
                                  not-connected(4),
                                  stopped(5),
                                  stopping(6),
                                  starting(7)
                                }
        MAX-ACCESS      read-only
        STATUS          current

        DESCRIPTION
        "The operational state of an interface is indicated via this
         variable.
         Possible values are:
                - down(1),
                - running(2),
                - fail(3),
                - not-connected(4),
                - stopped(5),
                - stopping(6),
                - starting(7),
         The latter two states being of transitional type, mainly for
         hot-plug type hardware, and won't be normally seen by user.

         State fail is used to reflect inconsistencies between hardware
         state and configuration concerning interface mode (potsIfMode)."
        DEFVAL { down }
        ::= { potsIfEntry 6 }

    potsIfIndex OBJECT-TYPE
        SYNTAX          PotsIfIndex
        MAX-ACCESS      read-only
        STATUS          current
        DESCRIPTION
            "Reference to the FXS or FXO table."
        DEFVAL          { 0 }
        ::= { potsIfEntry 7 }

    potsIfTtxLevel OBJECT-TYPE
        SYNTAX          INTEGER (-50..0)
        MAX-ACCESS      read-write
        STATUS          current
        DESCRIPTION
            "Teletax (metering pulse) level:
                for FXS lines: output level
                for FXO lines: minimum level
            "
        DEFVAL          { -30 }
        ::= { potsIfEntry 8 }

    potsIfTtxFreq OBJECT-TYPE
        SYNTAX          INTEGER { off(1),
                              --  freq50hz(2),    not supported
                                  freq12khz(3),
                                  freq16khz(4)
                                }
        MAX-ACCESS      read-write
        STATUS          current
        DESCRIPTION
            "Teletax (metering pulse) frequency:
                1: no teletax output/reception
                3: 12 kHz
                4: 16 kHz
            "
        DEFVAL          { freq16khz }
        ::= { potsIfEntry 9 }

    potsIfCoeffIndex OBJECT-TYPE
        SYNTAX          INTEGER
        MAX-ACCESS      read-write
        STATUS          current
        DESCRIPTION
            "Selection of the coefficient set provided
             by the FXS or FXO line driver. This allows
             to use specific settings with e.g. resistive or
             complex line impedances. Supported values are:
                 600: 600 ohms (resistive)
                1155: german Zr (complex)
                1170: ETSI (complex)
             "
        DEFVAL          { 1155 }
        ::= { potsIfEntry 10 }

    potsIfTxGain OBJECT-TYPE
        SYNTAX          INTEGER (-30..10)
        UNITS           "dB"
        MAX-ACCESS      read-write
        STATUS          current
        DESCRIPTION     "Amplification or attenuation (negative gain)
                         of outgoing audio in dB."
        DEFVAL          { -7 }
        ::= { potsIfEntry 11 }

    potsIfRxGain OBJECT-TYPE
        SYNTAX          INTEGER (-30..10)
        UNITS           "dB"
        MAX-ACCESS      read-write
        STATUS          current
        DESCRIPTION     "Amplification or attenuation (negative gain)
                         of incoming audio in dB."
        DEFVAL          { 0 }
        ::= { potsIfEntry 12 }

    potsIfDialInTimeout OBJECT-TYPE
        SYNTAX          INTEGER (1..99)
        UNITS           "s"
        MAX-ACCESS      read-write
        STATUS          current
        DESCRIPTION     "Limit for time interval between two consecutive
                         dialling digits."
        DEFVAL          { 41 }
        ::= { potsIfEntry 13 }


-- ~~~~~~~~~~~~~~~~~~~~~~~~~~~~~~~~~~~~~~~~~~~~~~~~~~~~~~~~~~~~~~~~~~~~~~~~
-- 2. potsIfFxoTable:  FXO Interface Table
-- ~~~~~~~~~~~~~~~~~~~~~~~~~~~~~~~~~~~~~~~~~~~~~~~~~~~~~~~~~~~~~~~~~~~~~~~~

    potsIfFxoTable OBJECT-TYPE
        SYNTAX          SEQUENCE OF PotsIfFxoEntry
        MAX-ACCESS      read-write
        STATUS          current
        DESCRIPTION
            "The potsIfFxoTable contains configuration information
            for the FXO outlets."
        ::= { pots 2 }

    potsIfFxoEntry OBJECT-TYPE
        SYNTAX          PotsIfFxoEntry
        MAX-ACCESS      not-accessible
        STATUS          current
        DESCRIPTION
            ""
        INDEX           { potsIfFxoIfIndex }
        ::= { potsIfFxoTable 1 }

    PotsIfFxoEntry ::=
        SEQUENCE {
            potsIfFxoIfIndex                    PotsIfIndex,
            potsIfFxoFlashTime                  INTEGER,
-- "obsolete" from here
            potsIfFxoDialToneDetection          INTEGER,
            potsIfFxoDialToneDetectionTime      INTEGER,
            potsIfFxoDialToneMinLevel           INTEGER,
            potsIfFxoDialToneOrgFreq            ToneFrequency,
            potsIfFxoDialToneOrgCadence         CadenceString,
            potsIfFxoDialToneOrgTolerance       CadenceTimingTolerance,
            potsIfFxoDialToneAltFreq            ToneFrequency,
            potsIfFxoDialToneAltCadence         CadenceString,
            potsIfFxoDialToneAltTolerance       CadenceTimingTolerance,
            potsIfFxoBusyToneDetection          INTEGER,
            potsIfFxoBusyToneDetectionTime      INTEGER,
            potsIfFxoBusyToneMinLevel           INTEGER,
            potsIfFxoBusyToneOrgFreq            ToneFrequency,
            potsIfFxoBusyToneOrgCadence         CadenceString,
            potsIfFxoBusyToneOrgTolerance       CadenceTimingTolerance,
            potsIfFxoBusyToneAltFreq            ToneFrequency,
            potsIfFxoBusyToneAltCadence         CadenceString,
            potsIfFxoBusyToneAltTolerance       CadenceTimingTolerance,
-- up to here
            potsIfFxoDialOutMode                INTEGER,
            potsIfFxoDialOutDelay               INTEGER,
            potsIfFxoDialInMode                 INTEGER,
            potsIfFxoDialInProgressTone         TruthValue,
            potsIfFxoDialInProgressToneDef      ToneDefTabIndex,
            potsIfFxoDialPulsePulseTime         INTEGER,
            potsIfFxoDialPulsePauseTime         INTEGER,
            potsIfFxoDialPulseInterDigitTime    INTEGER,
            potsIfFxoDialDtmfLevel              INTEGER,
            potsIfFxoDialDtmfToneTime           INTEGER,
            potsIfFxoDialDtmfInterDigitTime     INTEGER,
            potsIfFxoDataLinkMinLevel           INTEGER,
            potsIfFxoDataLinkModeOnHook         BITS,
            potsIfFxoDataLinkModeOffHook        INTEGER,
            potsIfFxoFaxToneDetection           BITS,
            potsIfFxoKeyBreakDetection          INTEGER,
            potsIfFxoDialOutToneDetection       TruthValue,
            potsIfFxoNormalDialTone             ToneDefTabIndex,
            potsIfFxoSpecialDialTone            ToneDefTabIndex,
            potsIfFxoConcurrentToneDetection    TruthValue,
            potsIfFxoBusyTone                   ToneDefTabIndex,
            potsIfFxoCongestionTone             ToneDefTabIndex
        }

    potsIfFxoIfIndex OBJECT-TYPE
        SYNTAX          PotsIfIndex
        MAX-ACCESS      read-write
        STATUS          current
        DESCRIPTION
            "Index of the FXO interface."
        DEFVAL          { 0 }
        ::= { potsIfFxoEntry 1 }

    potsIfFxoFlashTime OBJECT-TYPE
        SYNTAX          INTEGER
        UNITS           "ms"
        MAX-ACCESS      read-write
        STATUS          current
        DESCRIPTION
            "Dial out flash time (ms)."
        DEFVAL          { 100 }
        ::= { potsIfFxoEntry 2 }

    potsIfFxoDialToneDetection OBJECT-TYPE
        SYNTAX          INTEGER { off(1), single(2), dual(3) }
        MAX-ACCESS      read-write
        STATUS          obsolete
        DESCRIPTION
            "Type of tone:
                off(1)      no dial tone detection
                single(2)   detect just one tone rhythm
                dual(3)     detect also an alternative tone rhythm

             Enable dial tone detection. The following entries describes the
             parameters of the expected tone. It consists of time, level,
             frequency, rhythm and tolerance values.

             There are legacy central offices in some countries which
             uses differently sequenced tones. So beside the original
             tone description an alternative description can be used to
             detect those tones also.

             Another aspect is the allowed deviation from the expected
             tone rhythm which is quite different in the national telephone
             networks. To take this fact into account the tolerance entries
             determines how precise the given rhythms should be proven."
        DEFVAL          { off }
        ::= { potsIfFxoEntry 3 }

    potsIfFxoDialToneDetectionTime OBJECT-TYPE
        SYNTAX          INTEGER
        UNITS           "s"
        MAX-ACCESS      read-write
        STATUS          obsolete
        DESCRIPTION
            "Activation time for dial tone detection in seconds. When this
             time is reached dial tone detection will be switched off.
             A zero value keeps dial tone detection endlessly active."
        DEFVAL          { 10 }
        ::= { potsIfFxoEntry 4 }

    potsIfFxoDialToneMinLevel OBJECT-TYPE
        SYNTAX          ReceiveLevel
        UNITS           "dB"
        MAX-ACCESS      read-write
        STATUS          obsolete
        DESCRIPTION
            "minimum dial tone level."
        DEFVAL          { -47 }
        ::= { potsIfFxoEntry 5 }

    potsIfFxoDialToneOrgFreq OBJECT-TYPE
        SYNTAX          ToneFrequency
        UNITS           "Hz"
        MAX-ACCESS      read-write
        STATUS          obsolete
        DESCRIPTION
            "Frequency of the expected dial tone (Hz)."
        DEFVAL          { 425 }
        ::= { potsIfFxoEntry 6 }

    potsIfFxoDialToneOrgCadence OBJECT-TYPE
        SYNTAX          CadenceString
        MAX-ACCESS      read-write
        STATUS          obsolete
        DESCRIPTION
            "Cadence of the expected dial tone.

             The cadence definition consists of times of activity, times
             of no activity and some control information. All information
             is concatenated to one string and all times are given in
             milliseconds.

             Synopsis:
                 [:] active time [:] [passive time] [:]...

             Arguments:
                 active time    a<time value in ms>
                 passive time   p<time value in ms>
                 :              start or end of loop interval
                 ,|-|blank      allowed delimiters for better reading
                                before and behind the timing arguments

             Examples:
                 1) a200,p200,a200
                    => two tones with 200ms pause in between

                 2) a1000 p500 : a200 p200 :
                    => a long pulse at the beginning followed by a
                       continous interval of short pulses

                 3) p2000-a1000
                    => a pulse of one second after two second pause

                 4) :a1000:
                    => definition for an endless active period
            "
        DEFVAL          { ":a1000:" }
        ::= { potsIfFxoEntry 7 }

    potsIfFxoDialToneOrgTolerance OBJECT-TYPE
        SYNTAX          CadenceTimingTolerance
        UNITS           "%"
        MAX-ACCESS      read-write
        STATUS          obsolete
        DESCRIPTION
            "Dial tone timing tolerance (%)."
        DEFVAL          { 0 }
        ::= { potsIfFxoEntry 8 }

    potsIfFxoDialToneAltFreq OBJECT-TYPE
        SYNTAX          ToneFrequency
        UNITS           "Hz"
        MAX-ACCESS      read-write
        STATUS          obsolete
        DESCRIPTION
            "Alternative dial tone frequncy (Hz)."
        ::= { potsIfFxoEntry 9 }

    potsIfFxoDialToneAltCadence OBJECT-TYPE
        SYNTAX          CadenceString
        MAX-ACCESS      read-write
        STATUS          obsolete
        DESCRIPTION
            "Alternative dial tone cadence. For a description of
             allowed format refer to potsIfFxoDialToneOrgCadence."
        ::= { potsIfFxoEntry 10 }

    potsIfFxoDialToneAltTolerance OBJECT-TYPE
        SYNTAX          CadenceTimingTolerance
        UNITS           "%"
        MAX-ACCESS      read-write
        STATUS          obsolete
        DESCRIPTION
            "Alternative dial tone timing tolerance (%)."
        DEFVAL          { 0 }
        ::= { potsIfFxoEntry 11 }

    potsIfFxoBusyToneDetection OBJECT-TYPE
        SYNTAX          INTEGER { off(1), single(2), dual(3) }
        MAX-ACCESS      read-write
        STATUS          obsolete
        DESCRIPTION
            "Type of tone:
                off(1)      no busy tone detection
                single(2)   detect just one tone rhythm
                dual(3)     detect also an alternative tone rhythm

             Enable busy tone detection."
        DEFVAL          { off }
        ::= { potsIfFxoEntry 12 }

    potsIfFxoBusyToneDetectionTime OBJECT-TYPE
        SYNTAX          INTEGER
        UNITS           "s"
        MAX-ACCESS      read-write
        STATUS          obsolete
        DESCRIPTION
            "Activation time for busy tone detection in seconds. When this
             time is reached busy tone detection will be switched off.
             A zero value keeps busy tone detection endlessly active."
        DEFVAL          { 15 }
        ::= { potsIfFxoEntry 13 }

    potsIfFxoBusyToneMinLevel OBJECT-TYPE
        SYNTAX          ReceiveLevel
        UNITS           "dB"
        MAX-ACCESS      read-write
        STATUS          obsolete
        DESCRIPTION
            "Minimum busy tone level (dB)."
        DEFVAL          { -47 }
        ::= { potsIfFxoEntry 14 }

    potsIfFxoBusyToneOrgFreq OBJECT-TYPE
        SYNTAX          ToneFrequency
        UNITS           "Hz"
        MAX-ACCESS      read-write
        STATUS          obsolete
        DESCRIPTION
            "Busy tone frequncy (Hz)."
        DEFVAL          { 425 }
        ::= { potsIfFxoEntry 15 }

    potsIfFxoBusyToneOrgCadence OBJECT-TYPE
        SYNTAX          CadenceString
        MAX-ACCESS      read-write
        STATUS          obsolete
        DESCRIPTION
            "Busy tone cadence. For a description of allowed
             format refer to potsIfFxoDialToneOrgCadence."
        DEFVAL          { ":200,400:" }
        ::= { potsIfFxoEntry 16 }

    potsIfFxoBusyToneOrgTolerance OBJECT-TYPE
        SYNTAX          CadenceTimingTolerance
        UNITS           "%"
        MAX-ACCESS      read-write
        STATUS          obsolete
        DESCRIPTION
            "Busy tone timing tolerance (%)."
        DEFVAL          { 20 }
        ::= { potsIfFxoEntry 17 }

    potsIfFxoBusyToneAltFreq OBJECT-TYPE
        SYNTAX          ToneFrequency
        MAX-ACCESS      read-write
        STATUS          obsolete
        DESCRIPTION
            "Alternative busy tone frequncy."
        ::= { potsIfFxoEntry 18 }

    potsIfFxoBusyToneAltCadence OBJECT-TYPE
        SYNTAX          CadenceString
        MAX-ACCESS      read-write
        STATUS          obsolete
        DESCRIPTION
            "Alternative busy tone cadence. For a description of
             allowed format refer to potsIfFxoDialToneOrgCadence."
        ::= { potsIfFxoEntry 19 }

    potsIfFxoBusyToneAltTolerance OBJECT-TYPE
        SYNTAX          CadenceTimingTolerance
        UNITS           "%"
        MAX-ACCESS      read-write
        STATUS          obsolete
        DESCRIPTION
            "Alternative busy tone timing tolerance (%)."
        ::= { potsIfFxoEntry 20 }

    potsIfFxoDialOutMode OBJECT-TYPE
        SYNTAX          INTEGER { pulse(1), dtmf(2) }
        MAX-ACCESS      read-write
        STATUS          current
        DESCRIPTION
            "Dial-out mode (1: pulse, 2: DTMF)."
        DEFVAL          { dtmf }
        ::= { potsIfFxoEntry 21 }

    potsIfFxoDialOutDelay OBJECT-TYPE
        SYNTAX          INTEGER
        UNITS           "ms"
        MAX-ACCESS      read-write
        STATUS          current
        DESCRIPTION
            "Waiting time before dialout starts (ms)."
        DEFVAL          { 200 }
        ::= { potsIfFxoEntry 22 }

    potsIfFxoDialInMode OBJECT-TYPE
        SYNTAX          INTEGER { off(1), dtmf(2), uefs(3) }
        MAX-ACCESS      read-write
        STATUS          current
        DESCRIPTION
            "Dial-in mode (1: off, 2: DTMF, 3: UEFS)."
        DEFVAL          { off }
        ::= { potsIfFxoEntry 23 }

    potsIfFxoDialInProgressTone OBJECT-TYPE
        SYNTAX          TruthValue
        MAX-ACCESS      read-write
        STATUS          current
        DESCRIPTION
            "The progress tone is used for dial in mode 'DTMF' only.
             Other dial in modes will ignore this entry. The progress tone
             will signal the caller when to start to dial the subscriber
             number. After reception of the first digit this tone will
             disappear like any other dial tone."
        DEFVAL          { false }
        ::= { potsIfFxoEntry 24 }

    potsIfFxoDialInProgressToneDef OBJECT-TYPE
        SYNTAX          ToneTabIndex
        MAX-ACCESS      read-write
        STATUS          current
        DESCRIPTION
            "Index of the progress tone definition in phoneIfToneTable."
        DEFVAL          { -1 }
        ::= { potsIfFxoEntry 25 }

    potsIfFxoDialPulsePulseTime OBJECT-TYPE
        SYNTAX          INTEGER (30..200)
        UNITS           "ms"
        MAX-ACCESS      read-write
        STATUS          current
        DESCRIPTION
            "Pulse dialling break time (ms)."
        DEFVAL          { 60 }
        ::= { potsIfFxoEntry 26 }

    potsIfFxoDialPulsePauseTime OBJECT-TYPE
        SYNTAX          INTEGER (30..200)
        UNITS           "ms"
        MAX-ACCESS      read-write
        STATUS          current
        DESCRIPTION
            "Pulse dialling make time (ms)."
        DEFVAL          { 40 }
        ::= { potsIfFxoEntry 27 }

    potsIfFxoDialPulseInterDigitTime OBJECT-TYPE
        SYNTAX          INTEGER (100..500)
        UNITS           "ms"
        MAX-ACCESS      read-write
        STATUS          current
        DESCRIPTION
            "DTMF dialling interdigit time (ms)."
        DEFVAL          { 200 }
        ::= { potsIfFxoEntry 28 }

    potsIfFxoDialDtmfLevel OBJECT-TYPE
        SYNTAX          TransmitLevel
        UNITS           "dB"
        MAX-ACCESS      read-write
        STATUS          current
        DESCRIPTION
            "DTMF tone level (dB)."
        DEFVAL          { -10 }
        ::= { potsIfFxoEntry 29 }

    potsIfFxoDialDtmfToneTime OBJECT-TYPE
        SYNTAX          INTEGER (50..250)
        UNITS           "ms"
        MAX-ACCESS      read-write
        STATUS          current
        DESCRIPTION
            "DTMF tone duration (ms)."
        DEFVAL          { 120 }
        ::= { potsIfFxoEntry 30 }

    potsIfFxoDialDtmfInterDigitTime OBJECT-TYPE
        SYNTAX          INTEGER (50..250)
        UNITS           "ms"
        MAX-ACCESS      read-write
        STATUS          current
        DESCRIPTION
            "DTMF dialling interdigit time (ms)."
        DEFVAL          { 120 }
        ::= { potsIfFxoEntry 31 }

    potsIfFxoDataLinkMinLevel OBJECT-TYPE
        SYNTAX          TransmitLevel
        UNITS           "dB"
        MAX-ACCESS      read-write
        STATUS          current
        DESCRIPTION
            "Minimum data transmission level (dB)."
        DEFVAL          { -20 }
        ::= { potsIfFxoEntry 32 }

    potsIfFxoDataLinkModeOnHook OBJECT-TYPE
        SYNTAX          BITS {
                               dt-as(0),
                               dt-as-pol-rev(1),
                               rp-as(2),
                               during-ringing(3),
                               dtmf(4)
                             }
        MAX-ACCESS      read-write
        STATUS          current
        DESCRIPTION
            "Allowed on-hook data transmission modes:
                dt-as:          data transmission prior to ringing with DT-AS
                dt-as-pol-rev:  data transmission prior to ringing with DT-AS
                                and polarity reversal
                rp-as:          data transmission prior to ringing with RP-AS
                during-ringing: data transmission during ringing (after first ring)
                dtmf:           data transmission using DTMF

             With no bit activated on-hook data transmission is disabled."
        DEFVAL          { { } }
        ::= { potsIfFxoEntry 33 }

    potsIfFxoDataLinkModeOffHook OBJECT-TYPE
        SYNTAX          INTEGER {
                                  off(1),
                                  dt-as(2)
                                }
        MAX-ACCESS      read-write
        STATUS          current
        DESCRIPTION
            "Selection of off-hook data transmission mode:
                1: no off-hook data transmission
                2: data transmission prior using DT-AS
            "
        DEFVAL          { off }
        ::= { potsIfFxoEntry 34 }

    potsIfFxoFaxToneDetection OBJECT-TYPE
        SYNTAX          BITS {
                               cng(0),
                               ced(1),
                               dis(2)
                             }
        MAX-ACCESS      read-write
        STATUS          current
        DESCRIPTION
            "Fax tone detection. Tones to detect according to ITU T.30:
                cng: fax announce tone 1100 Hz
                ced: fax answer tone 2100 Hz
                dis: digital identification signal V.21
            "
        DEFVAL          { { } }
        ::= { potsIfFxoEntry 35 }

    potsIfFxoKeyBreakDetection OBJECT-TYPE
        SYNTAX          TruthValue
        MAX-ACCESS      read-write
        STATUS          current
        DESCRIPTION
            "Detection of key break as a release condition."
        DEFVAL          { false }
        ::= { potsIfFxoEntry 36 }

    potsIfFxoDialOutToneDetection OBJECT-TYPE
        SYNTAX          TruthValue
        MAX-ACCESS      read-write
        STATUS          current
        DESCRIPTION
            "Detection of dial tones as a trigger for outgoing dial."
        DEFVAL          { true }
        ::= { potsIfFxoEntry 37 }

    potsIfFxoNormalDialTone OBJECT-TYPE
        SYNTAX          ToneDefTabIndex
        MAX-ACCESS      read-write
        STATUS          current
        DESCRIPTION
            "Index of the normal dial tone definition in
             phoneIfToneTable used by dial out tone detection."
        DEFVAL          { -1 }
        ::= { potsIfFxoEntry 38 }

    potsIfFxoSpecialDialTone OBJECT-TYPE
        SYNTAX          ToneDefTabIndex
        MAX-ACCESS      read-write
        STATUS          current
        DESCRIPTION
            "Index of the special dial tone definition in
             phoneIfToneTable used by dial out tone detection."
        DEFVAL          { -1 }
        ::= { potsIfFxoEntry 39 }

    potsIfFxoConcurrentToneDetection OBJECT-TYPE
        SYNTAX          TruthValue
        MAX-ACCESS      read-write
        STATUS          current
        DESCRIPTION
            "Detection of tones after dialling and during a connection
             to catch a release condition."
        DEFVAL          { true }
        ::= { potsIfFxoEntry 40 }

    potsIfFxoBusyTone OBJECT-TYPE
        SYNTAX          ToneDefTabIndex
        MAX-ACCESS      read-write
        STATUS          current
        DESCRIPTION
            "Index of the busy tone definition in phoneIfToneTable
             used by concurrent tone detection."
        DEFVAL          { -1 }
        ::= { potsIfFxoEntry 41 }

    potsIfFxoCongestionTone OBJECT-TYPE
        SYNTAX          ToneDefTabIndex
        MAX-ACCESS      read-write
        STATUS          current
        DESCRIPTION
            "Index of the congestion tone definition in phoneIfToneTable
             used by concurrent tone detection."
        DEFVAL          { -1 }
        ::= { potsIfFxoEntry 42 }

-- ~~~~~~~~~~~~~~~~~~~~~~~~~~~~~~~~~~~~~~~~~~~~~~~~~~~~~~~~~~~~~~~~~~~~~~~~
-- 3. potsIfFxsTable:  FXS Interface Table
-- ~~~~~~~~~~~~~~~~~~~~~~~~~~~~~~~~~~~~~~~~~~~~~~~~~~~~~~~~~~~~~~~~~~~~~~~~

    potsIfFxsTable OBJECT-TYPE
        SYNTAX          SEQUENCE OF PotsIfFxsEntry
        MAX-ACCESS      read-write
        STATUS          current
        DESCRIPTION
            "The potsIfFxsTable contains configuration information
            for the FXS outlets."
        ::= { pots 3 }

    potsIfFxsEntry OBJECT-TYPE
        SYNTAX          PotsIfFxsEntry
        MAX-ACCESS      not-accessible
        STATUS          current
        DESCRIPTION
            ""
        INDEX           { potsIfFxsIfIndex }
        ::= { potsIfFxsTable 1 }

    PotsIfFxsEntry ::=
        SEQUENCE {
            potsIfFxsIfIndex                PotsIfIndex,
            potsIfFxsFlashMinTime           INTEGER,
            potsIfFxsFlashMaxTime           INTEGER,
            potsIfFxsRingLevel              INTEGER,
            potsIfFxsRingFreq               INTEGER,
            potsIfFxsRingTableIndex         RingTabIndex,
            potsIfFxsToneTableIndex         ToneTabIndex,
            potsIfFxsDataLinkType           BITS,
            potsIfFxsDataLinkElem           BITS,
            potsIfFxsDataLinkLevel          INTEGER,
            potsIfFxsDataLinkTiming         DataLinkTimerTabIndex,
            potsIfFxsDataLinkModeOnHook     INTEGER,
            potsIfFxsDataLinkModeOffHook    INTEGER,
            potsIfFxsDialPulseMinTimePulse  INTEGER,
            potsIfFxsDialPulseMaxTimePulse  INTEGER,
            potsIfFxsDialPulseMinTimePause  INTEGER,
            potsIfFxsDialPulseMaxTimePause  INTEGER
        }

    potsIfFxsIfIndex OBJECT-TYPE
        SYNTAX          PotsIfIndex
        MAX-ACCESS      read-write
        STATUS          current
        DESCRIPTION
            "Index of the FXS interface."
        DEFVAL          { 0 }
        ::= { potsIfFxsEntry 1 }

    potsIfFxsFlashMinTime OBJECT-TYPE
        SYNTAX          INTEGER
        UNITS           "ms"
        MAX-ACCESS      read-write
        STATUS          current
        DESCRIPTION
            "Minimum flash duration (ms). Flash pulses below this
             value will be ignored."
        DEFVAL          { 40 }
        ::= { potsIfFxsEntry 2 }

    potsIfFxsFlashMaxTime OBJECT-TYPE
        SYNTAX          INTEGER
        UNITS           "ms"
        MAX-ACCESS      read-write
        STATUS          current
        DESCRIPTION
            "Maximum flash duration (ms). Flash pulses above this
             value will be interpreted as hook-on."
        DEFVAL          { 250 }
        ::= { potsIfFxsEntry 3 }

    potsIfFxsRingLevel OBJECT-TYPE
        SYNTAX          INTEGER (0..150)
        UNITS           "Vpeak"
        MAX-ACCESS      read-write
        STATUS          current
        DESCRIPTION
            "Peak value of sinusoidal ringing voltage."
        DEFVAL          { 60 }
        ::= { potsIfFxsEntry 4 }

    potsIfFxsRingFreq OBJECT-TYPE
        SYNTAX          INTEGER { freq25hz(1), freq50hz(2) }
        MAX-ACCESS      read-write
        STATUS          current
        DESCRIPTION
            "Frequency of sinusoidal ringing voltage."
        DEFVAL          { freq25hz }
        ::= { potsIfFxsEntry 5 }

    potsIfFxsRingTableIndex OBJECT-TYPE
        SYNTAX          RingTabIndex
        MAX-ACCESS      read-write
        STATUS          current
        DESCRIPTION
            "The ringing table index is the reference to
             all ringing cadences used for this extension.
             Definitions are in phoneIfRingTable."
        DEFVAL          { 0 }
        ::= { potsIfFxsEntry 6 }

    potsIfFxsToneTableIndex OBJECT-TYPE
        SYNTAX          ToneTabIndex
        MAX-ACCESS      read-write
        STATUS          current
        DESCRIPTION
            "The tone table index refers to the tones
             used for this extension. Definitions are
             in phoneIfToneTable"
        DEFVAL          { 0 }
        ::= { potsIfFxsEntry 7 }

    potsIfFxsDataLinkType OBJECT-TYPE
        SYNTAX          BITS {
                               setup(0),
                               mwi(1),
                               aoc(2),
                               sms(3)
                             }
        MAX-ACCESS      read-write
        STATUS          current
        DESCRIPTION
            "Allowed data transmission message types:
                setup - call setup message
                mwi   - message waiting indicator message
                aoc   - advice of charge message
                sms   - short message service message
            "
        DEFVAL          { { setup, mwi, aoc, sms } }
        ::= { potsIfFxsEntry 8 }

    potsIfFxsDataLinkElem OBJECT-TYPE
        SYNTAX          BITS {
                               date-time(0),
                               calling-line-id(1),
                               called-line-id(2),
                               reason-for-absence-of-cli(3),
                               calling-party-name(4),
                               reason-for-absence-of-cpn(5),
                               visual-indicator(6),
                               message-identification(7),
                               last-message-cli(8),
                               complementary-date-time(9),
                               complementary-cli(10),
                               call-type(11),
                               first-cli(12),
                               no-of-messages(13),
                               charge(14),
                               additional-charge(15),
                               duration-of-call(16),
                               network-provider-id(17),
                               carrier-id(18),
                               select-terminal-function(19),
                               display-information(20),
                               service-information(21)
                             }
        MAX-ACCESS      read-write
        STATUS          current
        DESCRIPTION
            "Allowed data transmission parameters (see ETSI EN 300 659-3).
             Not selected elements will be filtered out and not sent to
             the subscriber."
        DEFVAL          { { date-time, calling-line-id, calling-party-name, display-information } }
        ::= { potsIfFxsEntry 9 }

    potsIfFxsDataLinkLevel OBJECT-TYPE
        SYNTAX          TransmitLevel
        UNITS           "dB"
        MAX-ACCESS      read-write
        STATUS          current
        DESCRIPTION
            "Level of the data transmission signal (dB)."
        DEFVAL          { -15 }
        ::= { potsIfFxsEntry 10 }

    potsIfFxsDataLinkTiming OBJECT-TYPE
        SYNTAX          DataLinkTimerTabIndex
        MAX-ACCESS      read-write
        STATUS          current
        DESCRIPTION
            "Index of the timer set to be used for on-hook and off-hook
            data transmission."
        DEFVAL          { 0 }
        ::= { potsIfFxsEntry 11 }

    potsIfFxsDataLinkModeOnHook OBJECT-TYPE
        SYNTAX          INTEGER {
                                  off(1),
                                  dt-as(2),
                                  dt-as-pol-rev(3),
                                  rp-as(4),
                                  during-ringing(5),
                                  dtmf(6)
                                }
        MAX-ACCESS      read-write
        STATUS          current
        DESCRIPTION
            "Selection of on-hook data transmission mode:
                1: no on-hook data transmission
                2: data transmission prior to ringing with DT-AS
                3: data transmission prior to ringing with DT-AS
                        and polarity reversal
                4: data transmission prior to ringing with RP-AS
                5: data transmission during ringing (after first ring)
                6: data transmission using DTMF
            "
        DEFVAL          { 1 }
        ::= { potsIfFxsEntry 12 }

    potsIfFxsDataLinkModeOffHook OBJECT-TYPE
        SYNTAX          INTEGER {
                                  off(1),
                                  dt-as(2)
                                }
        MAX-ACCESS      read-write
        STATUS          current
        DESCRIPTION
            "Selection of off-hook data transmission mode:
                1: no off-hook data transmission
                2: data transmission prior using DT-AS
            "
        DEFVAL          { 1 }
        ::= { potsIfFxsEntry 13 }

    potsIfFxsDialPulseMinTimePulse OBJECT-TYPE
        SYNTAX          INTEGER (10..100)
        UNITS           "ms"
        MAX-ACCESS      read-write
        STATUS          current
        DESCRIPTION
            "Pulse dialling break time minimum (ms). Break pulses below
             this limit will be ignored."
        DEFVAL          { 20 }
        ::= { potsIfFxsEntry 14 }

    potsIfFxsDialPulseMaxTimePulse OBJECT-TYPE
        SYNTAX          INTEGER (50..200)
        UNITS           "ms"
        MAX-ACCESS      read-write
        STATUS          current
        DESCRIPTION
            "Pulse dialling break time maximum (ms). A pause time above
             this limit is regarded as on-hook signal."
        DEFVAL          { 120 }
        ::= { potsIfFxsEntry 15 }

    potsIfFxsDialPulseMinTimePause OBJECT-TYPE
        SYNTAX          INTEGER (10..100)
        UNITS           "ms"
        MAX-ACCESS      read-write
        STATUS          current
        DESCRIPTION
            "Pulse dialling make time minimum (ms). Make pulses below
             this limit will be ignored."
        DEFVAL          { 20 }
        ::= { potsIfFxsEntry 16 }

    potsIfFxsDialPulseMaxTimePause OBJECT-TYPE
        SYNTAX          INTEGER (10..300)
        UNITS           "ms"
        MAX-ACCESS      read-write
        STATUS          current
        DESCRIPTION
            "Pulse dialling make time maximum (ms). A pause time above
             this limit finishes the pulse counting and this digit is
             regarded as complete."
        DEFVAL          { 200 }
        ::= { potsIfFxsEntry 17 }


-- ~~~~~~~~~~~~~~~~~~~~~~~~~~~~~~~~~~~~~~~~~~~~~~~~~~~~~~~~~~~~~~~~~~~~~~~~
-- 4. potsIfDataLinkTimerTable
-- ~~~~~~~~~~~~~~~~~~~~~~~~~~~~~~~~~~~~~~~~~~~~~~~~~~~~~~~~~~~~~~~~~~~~~~~~

    potsIfDataLinkTimerTable OBJECT-TYPE
        SYNTAX          SEQUENCE OF PotsIfDataLinkTimerEntry
        MAX-ACCESS      read-write
        STATUS          current
        DESCRIPTION
            "The potsIfDataLinkTimerTable the contains timer values (in ms)
            controlling on-hook and off-hook data transmission service
            according to ETSI EN 300 659. The reception of data is
            controlled with timers according to the minimum and maximum
            values given in the ETSI standard."
        ::= { pots 4 }

    potsIfDataLinkTimerEntry OBJECT-TYPE
        SYNTAX          PotsIfDataLinkTimerEntry
        MAX-ACCESS      read-write
        STATUS          current
        DESCRIPTION
            ""
        INDEX           { potsIfDataLinkTimerIndex }
        ::= { potsIfDataLinkTimerTable 1 }

    PotsIfDataLinkTimerEntry ::=
        SEQUENCE {
            potsIfDataLinkTimerIndex    DataLinkTimerTabIndex,
            potsIfDataLinkTimer0        INTEGER,
            potsIfDataLinkTimer1        INTEGER,
            potsIfDataLinkTimer2        INTEGER,
            potsIfDataLinkTimer3        INTEGER,
            potsIfDataLinkTimer4        INTEGER,
            potsIfDataLinkTimer5        INTEGER,
            potsIfDataLinkTimer6        INTEGER,
            potsIfDataLinkTimer7        INTEGER,
            potsIfDataLinkTimer8        INTEGER,
            potsIfDataLinkTimer9        INTEGER,
            potsIfDataLinkTimer10       INTEGER,
            potsIfDataLinkTimer11       INTEGER,
            potsIfDataLinkTimer12       INTEGER,
            potsIfDataLinkTimer13       INTEGER,
            potsIfDataLinkTimer14       INTEGER,
            potsIfDataLinkTimerRpAs     INTEGER,
            potsIfDataLinkTimerDtAsOnH  INTEGER,
            potsIfDataLinkTimerDtAsOffH INTEGER
        }

    potsIfDataLinkTimerIndex OBJECT-TYPE
        SYNTAX          DataLinkTimerTabIndex
        MAX-ACCESS      read-write
        STATUS          current
        DESCRIPTION
            "Index of the set of timers which is following up."
        DEFVAL          { 0 }
        ::= { potsIfDataLinkTimerEntry 1 }

    potsIfDataLinkTimer0 OBJECT-TYPE
        SYNTAX          INTEGER (100..550)
        MAX-ACCESS      read-write
        STATUS          current
        DESCRIPTION     "Timer T0 according to ETSI EN 300 659."
        DEFVAL          { 150 }
        ::= { potsIfDataLinkTimerEntry 2 }

    potsIfDataLinkTimer1 OBJECT-TYPE
        SYNTAX          INTEGER (45..500)
        MAX-ACCESS      read-write
        STATUS          current
        DESCRIPTION     "Timer T1 according to ETSI EN 300 659."
        DEFVAL          { 80 }
        ::= { potsIfDataLinkTimerEntry 3 }

    potsIfDataLinkTimer2 OBJECT-TYPE
        SYNTAX          INTEGER (200..500)
        MAX-ACCESS      read-write
        STATUS          current
        DESCRIPTION     "Timer T2 according to ETSI EN 300 659."
        DEFVAL          { 250 }
        ::= { potsIfDataLinkTimerEntry 4 }

    potsIfDataLinkTimer3 OBJECT-TYPE
        SYNTAX          INTEGER (500..800)
        MAX-ACCESS      read-write
        STATUS          current
        DESCRIPTION     "Timer T3 according to ETSI EN 300 659."
        DEFVAL          { 550 }
        ::= { potsIfDataLinkTimerEntry 5 }

    potsIfDataLinkTimer4 OBJECT-TYPE
        SYNTAX          INTEGER (45..500)
        MAX-ACCESS      read-write
        STATUS          current
        DESCRIPTION     "Timer T4 according to ETSI EN 300 659."
        DEFVAL          { 80 }
        ::= { potsIfDataLinkTimerEntry 6 }

    potsIfDataLinkTimer5 OBJECT-TYPE
        SYNTAX          INTEGER (500..2000)
        MAX-ACCESS      read-write
        STATUS          current
        DESCRIPTION     "Timer T5 according to ETSI EN 300 659."
        DEFVAL          { 550 }
        ::= { potsIfDataLinkTimerEntry 7 }

    potsIfDataLinkTimer6 OBJECT-TYPE
        SYNTAX          INTEGER (200..3000)
        MAX-ACCESS      read-write
        STATUS          current
        DESCRIPTION     "Timer T6 according to ETSI EN 300 659."
        DEFVAL          { 250 }
        ::= { potsIfDataLinkTimerEntry 8 }

    potsIfDataLinkTimer7 OBJECT-TYPE
        SYNTAX          INTEGER (250..700)
        MAX-ACCESS      read-write
        STATUS          current
        DESCRIPTION     "Timer T7 according to ETSI EN 300 659."
        DEFVAL          { 700 }
        ::= { potsIfDataLinkTimerEntry 9 }

    potsIfDataLinkTimer8 OBJECT-TYPE
        SYNTAX          INTEGER (200..500)
        MAX-ACCESS      read-write
        STATUS          current
        DESCRIPTION     "Timer T8 according to ETSI EN 300 659."
        DEFVAL          { 300 }
        ::= { potsIfDataLinkTimerEntry 10 }

    potsIfDataLinkTimer9 OBJECT-TYPE
        SYNTAX          INTEGER (0..150)
        MAX-ACCESS      read-write
        STATUS          current
        DESCRIPTION     "Timer T9 according to ETSI EN 300 659."
        DEFVAL          { 0 }
        ::= { potsIfDataLinkTimerEntry 11 }

    potsIfDataLinkTimer10 OBJECT-TYPE
        SYNTAX          INTEGER (0..150)
        MAX-ACCESS      read-write
        STATUS          current
        DESCRIPTION     "Timer T10 according to ETSI EN 300 659."
        DEFVAL          { 20 }
        ::= { potsIfDataLinkTimerEntry 12 }

    potsIfDataLinkTimer11 OBJECT-TYPE
        SYNTAX          INTEGER (40..55)
        MAX-ACCESS      read-write
        STATUS          current
        DESCRIPTION     "Timer T11 according to ETSI EN 300 659."
        DEFVAL          { 50 }
        ::= { potsIfDataLinkTimerEntry 13 }

    potsIfDataLinkTimer12 OBJECT-TYPE
        SYNTAX          INTEGER (55..200)
        MAX-ACCESS      read-write
        STATUS          current
        DESCRIPTION     "Timer T12 according to ETSI EN 300 659."
        DEFVAL          { 80 }
        ::= { potsIfDataLinkTimerEntry 14 }

    potsIfDataLinkTimer13 OBJECT-TYPE
        SYNTAX          INTEGER (40..120)
        MAX-ACCESS      read-write
        STATUS          current
        DESCRIPTION     "Timer T13 according to ETSI EN 300 659."
        DEFVAL          { 50 }
        ::= { potsIfDataLinkTimerEntry 15 }

    potsIfDataLinkTimer14 OBJECT-TYPE
        SYNTAX          INTEGER (155..165)
        MAX-ACCESS      read-write
        STATUS          current
        DESCRIPTION     "Timer T14 according to ETSI EN 300 659."
        DEFVAL          { 160 }
        ::= { potsIfDataLinkTimerEntry 16 }

    potsIfDataLinkTimerRpAs OBJECT-TYPE
        SYNTAX          INTEGER (200..300)
        MAX-ACCESS      read-write
        STATUS          current
        DESCRIPTION     "Timer RP-AS according to ETSI EN 300 659."
        DEFVAL          { 250 }
        ::= { potsIfDataLinkTimerEntry 17 }

    potsIfDataLinkTimerDtAsOnH OBJECT-TYPE
        SYNTAX          INTEGER (90..110)
        MAX-ACCESS      read-write
        STATUS          current
        DESCRIPTION     "Timer DT-AS on-hook according to ETSI EN 300 659."
        DEFVAL          { 100 }
        ::= { potsIfDataLinkTimerEntry 18 }

    potsIfDataLinkTimerDtAsOffH OBJECT-TYPE
        SYNTAX          INTEGER (75..85)
        MAX-ACCESS      read-write
        STATUS          current
        DESCRIPTION     "Timer DT-AS off-hook according to ETSI EN 300 659."
        DEFVAL          { 80 }
        ::= { potsIfDataLinkTimerEntry 19 }


END
