-- This file is corresponding to Release 9.1.10.101 from 2014/08/11 00:00:00


-- (C)opyright 1991-20124 bintec elmeg GmbH, All Rights Reserved
--  $RCSfile: mibx25totcp,v $
-- $Revision: 1.10 $

BIANCA-BRICK-X25TOTCP-MIB DEFINITIONS ::= BEGIN

        IMPORTS
            Counter, TimeTicks, IpAddress, enterprises
                FROM RFC1155-SMI

	    DisplayString
		FROM RFC1158-MIB

            Date, HexValue
                FROM BINTEC-MIB

            OBJECT-TYPE
                FROM RFC-1212;

    bintec 	OBJECT IDENTIFIER ::= { enterprises 272 }
    bibo	OBJECT IDENTIFIER ::= { bintec 4 }
    x25		OBJECT IDENTIFIER
	::= { bibo 6 }


    -- Management Information for the X.25 to TCP Gateway of the BIANCA/BRICK

	x25ToTcpTable OBJECT-TYPE
	    SYNTAX  SEQUENCE OF X25ToTcpEntry
	    ACCESS  not-accessible
	    STATUS  mandatory
	    DESCRIPTION
		""
	::= { x25 9 }

	x25ToTcpEntry OBJECT-TYPE
	    SYNTAX  X25ToTcpEntry
	    ACCESS  not-accessible
	    STATUS  mandatory
	    DESCRIPTION
		"Entries can only be created and deleted manually."
	    INDEX   { x25ToTcpIndex }
	::= { x25ToTcpTable 1 }

	X25ToTcpEntry ::=
	    SEQUENCE {
		x25ToTcpIndex				INTEGER,
		x25ToTcpDescr				DisplayString,
		x25ToTcpState				INTEGER,

		x25ToTcpX25LocAddr			DisplayString,
		x25ToTcpX25LocNSAP			DisplayString,
		x25ToTcpX25RemAddr			DisplayString,
		x25ToTcpX25RemNSAP			DisplayString,
		x25ToTcpX25ProtocolId			INTEGER,
		x25ToTcpX25CallUserData			OCTET STRING,
		x25ToTcpX25Cug                          INTEGER,
		x25ToTcpX25CugOutgoing                  INTEGER,
		x25ToTcpX25CugBilateral                 INTEGER,

		x25ToTcpIpLocAddr			IpAddress,
		x25ToTcpIpLocPort			INTEGER,
		x25ToTcpIpRemAddr			IpAddress,
		x25ToTcpIpRemMask			IpAddress,
		x25ToTcpIpRemPort			INTEGER,
		x25ToTcpIpRemPortRange			INTEGER,
		x25ToTcpClass				INTEGER,

		x25ToTcpMetric				INTEGER,
		x25ToTcpDirection			INTEGER,
		x25ToTcpPacketizing			INTEGER,
		x25ToTcpReset				INTEGER,
		x25ToTcpIntr				INTEGER,

		x25ToTcpMonitor				INTEGER,
		x25ToTcpMonState			INTEGER,

		x25ToTcpX25CUDMode			INTEGER
	}

	x25ToTcpIndex OBJECT-TYPE
	    SYNTAX  INTEGER
	    ACCESS  read-write
	    STATUS  mandatory

	    DESCRIPTION
		"The unique number of the MIB row."
	::= { x25ToTcpEntry 1 }

	x25ToTcpDescr OBJECT-TYPE
	    SYNTAX  DisplayString
	    ACCESS  read-write
	    STATUS  mandatory

	    DESCRIPTION
		"This object contains a textual description of the row."
	::= { x25ToTcpEntry 2 }


	x25ToTcpState OBJECT-TYPE
	    SYNTAX  INTEGER {
			valid(1), invalid(2), delete(3)
	    }
	    ACCESS  read-write
	    STATUS  mandatory

	    DESCRIPTION
		"The State of the MIB row."
	    DEFVAL  { valid }
	::= { x25ToTcpEntry 3 }

        x25ToTcpX25LocAddr OBJECT-TYPE
            SYNTAX  DisplayString
            ACCESS  read-write
            STATUS  mandatory

            DESCRIPTION
                "The local X.121 address in the X25 call. If empty, the
                 local address will not be matched. Extended Adresses are
                 indicated by a leading '@'. The wildcards '*', '?', '[',
                 ']', '{', '}' may be used."
        ::= { x25ToTcpEntry 4 }

        x25ToTcpX25LocNSAP OBJECT-TYPE
            SYNTAX  DisplayString
            ACCESS  read-write
            STATUS  mandatory

            DESCRIPTION
                "The local NSAP in the X25 call. If empty, the
                 local NSAP will not be matched. The NSAP is preceeded
                 by an 'X' if it is an OSI compatible NSAP or by a 'N' if
                 the NSAP is in a not OSI compatible format. The wildcards
                 '*', '?', '[', ']', '{', '}' may be used."
        ::= { x25ToTcpEntry 5 }

        x25ToTcpX25RemAddr OBJECT-TYPE
            SYNTAX  DisplayString
            ACCESS  read-write
            STATUS  mandatory

            DESCRIPTION
                "The remote X.121 address in the X25 call. If empty, the
                 remote address will not be matched. Extended Adresses are
                 indicated by a leading '@'. The wildcards '*', '?', '[',
                 ']', '{', '}' may be used."
        ::= { x25ToTcpEntry 6 }

        x25ToTcpX25RemNSAP OBJECT-TYPE
            SYNTAX  DisplayString
            ACCESS  read-write
            STATUS  mandatory

            DESCRIPTION
                "The remote NSAP in the X25 call. If empty, the
                 local NSAP will not be matched. The NSAP is preceeded
                 by an 'X' if it is an OSI compatible NSAP or by a 'N' if
                 the NSAP is in a not OSI compatible format. The wildcards
                 '*', '?', '[', ']', '{', '}' may be used."

        ::= { x25ToTcpEntry 7 }

        x25ToTcpX25ProtocolId OBJECT-TYPE
            SYNTAX  INTEGER
            ACCESS  read-write
            STATUS  mandatory

            DESCRIPTION
                "The protocol id of the X25 call. The protocol id
                 will not be used for the matching process, when this
                 object is set to -1"
            DEFVAL { -1 }
        ::= { x25ToTcpEntry 8 }

        x25ToTcpX25CallUserData OBJECT-TYPE
            SYNTAX  OCTET STRING
            ACCESS  read-write
            STATUS  mandatory

            DESCRIPTION
                "For outgoing calls, this field contains the Call User Data
                 field of the outgoing X.25 Call Request packet.
                 For incoming X.25 calls, the field will be compared against
                 the first or the last part of the Call User Data field of
                 the incoming X.25 call packet. Direction for matching is
                 defined in x25ToTcpX25CUDMode. If empty, the call user data
                 field will not be used for matching."
        ::= { x25ToTcpEntry 9 }

	x25ToTcpX25Cug OBJECT-TYPE
	    SYNTAX  INTEGER  (-1..9999)
	    ACCESS  read-write
	    STATUS  mandatory

	    DESCRIPTION
		"If this object has a value other than -1, a Closed User Group
		 facility will be generated for outgoing X.25 calls. The value
		 will be the value of the object."
	    DEFVAL { -1 }
	::= { x25ToTcpEntry 10 }

	x25ToTcpX25CugOutgoing OBJECT-TYPE
	    SYNTAX  INTEGER  (-1..9999)
	    ACCESS  read-write
	    STATUS  mandatory

	    DESCRIPTION
		"If this object has a value other than -1, a Closed User Group
		 Outgoing facility will be generated for outgoing X.25 calls.
		 The value will be the value of the object."
	    DEFVAL { -1 }
	::= { x25ToTcpEntry 11 }

	x25ToTcpX25CugBilateral OBJECT-TYPE
	    SYNTAX  INTEGER  (-1..9999)
	    ACCESS  read-write
	    STATUS  mandatory

	    DESCRIPTION
		"If this object has a value other than -1, a Closed User Group
		 Bilateral facility will be generated for outgoing X.25 calls.
		 The value will be the value of the object."
	    DEFVAL { -1 }
	::= { x25ToTcpEntry 12 }


        x25ToTcpIpLocAddr OBJECT-TYPE
            SYNTAX  IpAddress
            ACCESS  read-write
            STATUS  mandatory

            DESCRIPTION
                "This object describes the the Local address of the
		 IP-datagrams belonging
                 to the set. If both objects are set to 0.0.0.0 the local
                 addresses for the datagrams in the set is not specified
                 and can take any value."
        ::= { x25ToTcpEntry 15 }

        x25ToTcpIpLocPort OBJECT-TYPE
            SYNTAX  INTEGER (-1..65535)
            ACCESS  read-write
            STATUS  mandatory

            DESCRIPTION
                "This object is used for incoming TCP calls. A value
                 other than -1 specifies the local port number that
                 is used for matching.
                 Multiple local ports can be defined to extend the
                 address space for TCP calls."
            DEFVAL { -1 }
        ::= { x25ToTcpEntry 17 }

        x25ToTcpIpRemAddr OBJECT-TYPE
            SYNTAX  IpAddress
            ACCESS  read-write
            STATUS  mandatory

            DESCRIPTION
                "This object describes together with x25ToTcpIpRemMask the
                 range of the Remote addresses of the IP-datagrams belonging
                 to the set. If both objects are set to 0.0.0.0 the local
                 addresses for the datagrams in the set is not specified
                 and can take any value."
        ::= { x25ToTcpEntry 19 }

        x25ToTcpIpRemMask OBJECT-TYPE
            SYNTAX  IpAddress
            ACCESS  read-write
            STATUS  mandatory

            DESCRIPTION
                "This object describes together with x25ToTcpIpRemAddr the
                 range of the Remote addresses of the IP-datagrams belonging
                 to the set. If both objects are set to 0.0.0.0 the local
                 addresses for the datagrams in the set is not specified
                 and can take any value."
        ::= { x25ToTcpEntry 20 }

        x25ToTcpIpRemPort OBJECT-TYPE
            SYNTAX  INTEGER (-1..65535)
            ACCESS  read-write
            STATUS  mandatory

            DESCRIPTION
                "This object describes together with x25ToTcpIpRemPortRange the
                 range of local portnumbers of the IP-datagrams belonging to
                 the set. All portnumbers between and including the two
                 objects are within the range.

                 If both objects are set to -1, the value of the source
                 portnumber is not specified and can take any value."
            DEFVAL { -1 }
        ::= { x25ToTcpEntry 21 }

        x25ToTcpIpRemPortRange OBJECT-TYPE
            SYNTAX  INTEGER (-1..65535)
            ACCESS  read-write
            STATUS  mandatory

            DESCRIPTION
                "This object describes together with x25ToTcpIpRemPort the
                 range of local portnumbers of the IP-datagrams belonging to
                 the set. All portnumbers between and including the two
                 objects are within the range.

                 If both objects are set to -1, the value of the source
                 portnumber is not specified and can take any value."
            DEFVAL { -1 }
        ::= { x25ToTcpEntry 22 }

	x25ToTcpClass OBJECT-TYPE
	    SYNTAX  INTEGER {
			normal(1),
			master-plus1(2),
			master-plus2(3),
			master-plus3(4),
			subrule1(5),
			subrule2(6),
			subrule3(7)
	    }
	    ACCESS  read-write
	    STATUS  mandatory

	    DESCRIPTION
		""
	    DEFVAL  { normal }
	::= { x25ToTcpEntry 23 }

	x25ToTcpMetric OBJECT-TYPE
	    SYNTAX  INTEGER
	    ACCESS  read-write
	    STATUS  mandatory

	    DESCRIPTION
		"Metric to put order on table entries"
	    DEFVAL  { 1 }
	::= { x25ToTcpEntry 25 }

	x25ToTcpDirection OBJECT-TYPE
	    SYNTAX  INTEGER {
			t2x(1), x2t(2), both(3)
	    }
	    ACCESS  read-write
	    STATUS  mandatory

	    DESCRIPTION
		"This object describes, if the row its belongs to is
		 valid in the direction from tcp to x25, x25 to tcp or
		 both direction."
	    DEFVAL  { both }
	::= { x25ToTcpEntry 26 }

	x25ToTcpPacketizing OBJECT-TYPE
	    SYNTAX  INTEGER {
			none(1), atos(2), rfc1006(3)
	    }
	    ACCESS  read-write
	    STATUS  mandatory

	    DESCRIPTION
		"This object describes, how x25 packets are encoded on
		 the IP stream:
			none:    no packetizing. Packetizing information
				 is lost.

			pos:     packetization according to the ATOS
				 specification for POS terminals

			rfc1006: packetization according to rfc1006
		 "
	    DEFVAL  { none }
	::= { x25ToTcpEntry 27 }

	x25ToTcpReset OBJECT-TYPE
	    SYNTAX  INTEGER {
			clear(1), accept(2)
	    }
	    ACCESS  read-write
	    STATUS  mandatory

	    DESCRIPTION
		"This object describes, how the reception of a reset
		 packet on the X.25 link shall be handled:
			clear:   the connection will be cleared
			accept:	 the reset will be confirmed and
				 the data transfer continues
		"
	    DEFVAL  { accept }
	::= { x25ToTcpEntry 28 }

	x25ToTcpIntr OBJECT-TYPE
	    SYNTAX  INTEGER {
			clear(1), ignore(2), pass(3)
	    }
	    ACCESS  read-write
	    STATUS  mandatory

	    DESCRIPTION
		"Not supported yet!
		 (This object describes, how the reception of an interrupt
		 packet on the X.25 link shall be handled:
			clear:   the connection will be cleared
			ignore:	 the intr will be ignored and
				 the data transfer continues
			pass:	 the data part will be sent to TCP
				 like data and the data transfer continues)
		"
	    DEFVAL  { ignore }
	::= { x25ToTcpEntry 29 }

	x25ToTcpMonitor OBJECT-TYPE
	    SYNTAX  INTEGER {
			off(1), on(2)
	    }
	    ACCESS  read-write
	    STATUS  mandatory

	    DESCRIPTION
		"If this object is set to on, the row will only be valid
		 for the direction x25 to tcp, when the IpRemoteAddr is
		 reachable by ICMP echo packets. Otherwise it is not
		 used and an alternate entry to a different Ip Address
		 can be used for redundant scenarios.
		"
	    DEFVAL  { off }
	::= { x25ToTcpEntry 30 }

	x25ToTcpMonState OBJECT-TYPE
	    SYNTAX  INTEGER {
			not-monitored(1), unreachable(2), ready(3)
	    }
	    ACCESS  read-only
	    STATUS  mandatory

	    DESCRIPTION
		"This object describes the reachability of the Remote IP
		 Adress:
			not_monitored: the address is not monitored
			unreachable:   the address is monitored, but does
				       not reply to ICMP Echo Requests
			ready:	       the address is answering for
				       ICMP Echo Requests and ready
				       to accept TCP calls.
		"
	::= { x25ToTcpEntry 31 }


	x25ToTcpX25CUDMode OBJECT-TYPE
	    SYNTAX  INTEGER {
		right-to-left(1), left-to-right(2)
	    }
	    ACCESS  read-write
	    STATUS  mandatory

	    DESCRIPTION
		"This object specifies the matching direction for the call
		 user data field. When set to right-to-left, the rightmost
                 digits of the call user data field are compared against
		 the x25TcpX25CallUserData. When set to left-to-right, the
                 leftmost digits of the Call User Data field are compared
                 against x25TcpX25CallUserData. "

	    DEFVAL { left-to-right }
	::= { x25ToTcpEntry 32 }

END
