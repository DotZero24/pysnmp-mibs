-- ****************************************************************************
--  COLUBRIS-TCP-SERIAL-MIB definitions
--
--  Copyright (c) 2008, Hewlett-Packard Development Company, L.P.
--  The information contained herein is subject to change without notice.
--  All Rights Reserved.
--
--  Colubris TCP Serial MIB file.
--
-- ****************************************************************************


COLUBRIS-TCP-SERIAL-MIB DEFINITIONS ::= BEGIN

IMPORTS
    MODULE-IDENTITY, OBJECT-TYPE, Unsigned32, Counter32, IpAddress
        FROM    SNMPv2-SMI
    MODULE-COMPLIANCE, OBJECT-GROUP
        FROM    SNMPv2-CONF
    colubrisMgmtV2
        FROM    COLUBRIS-SMI
;


colubrisTCPSerialMIB MODULE-IDENTITY
    LAST-UPDATED    "200808210000Z"
    ORGANIZATION    "Colubris Networks, Inc."
    CONTACT-INFO    "Colubris Networks
                     Postal: 200 West Street Ste 300
                             Waltham, Massachusetts 02451-1121
                             UNITED STATES
                     Phone:  +1 781 684 0001
                     Fax:    +1 781 684 0009

                     E-mail: cn-snmp@colubris.com"
    DESCRIPTION     "Colubris TCP Serial MIB."

    ::= { colubrisMgmtV2 37 }


-- colubrisTCPSerialMIB definition
colubrisTCPSerialMIBObjects OBJECT IDENTIFIER ::= { colubrisTCPSerialMIB 1 }

-- colubris TCP Serial groups
coTCPSerialStatusGroup      OBJECT IDENTIFIER ::= { colubrisTCPSerialMIBObjects 1 }

-- The TCP Serial Status Group

coTCPSerialConnectionStatus OBJECT-TYPE
    SYNTAX      INTEGER
                {
                    closed(1),
                    listen(2),
                    active(3),
                    idle(4),
                    connect(5)
                }
    MAX-ACCESS  read-only
    STATUS      current
    DESCRIPTION "TCP connection status."
    ::= { coTCPSerialStatusGroup 1 }

coTCPSerialRemoteIPAddress OBJECT-TYPE
    SYNTAX      IpAddress
    MAX-ACCESS  read-only
    STATUS      current
    DESCRIPTION "IP address of the remote TCP end point."
    ::= { coTCPSerialStatusGroup 2 }

coTCPSerialRemoteTCPPort OBJECT-TYPE
    SYNTAX      Unsigned32
    MAX-ACCESS  read-only
    STATUS      current
    DESCRIPTION "TCP port of the remote TCP end point."
    ::= { coTCPSerialStatusGroup 3 }

coTCPSerialConnectTime OBJECT-TYPE
    SYNTAX      Counter32
    UNITS       "seconds"
    MAX-ACCESS  read-only
    STATUS      current
    DESCRIPTION "Elapsed time."
    ::= { coTCPSerialStatusGroup 4 }

coTCPSerialTxBytes OBJECT-TYPE
    SYNTAX      Counter32
    UNITS       "bytes"
    MAX-ACCESS  read-only
    STATUS      current
    DESCRIPTION "Number of bytes transmitted to the serial device."
    ::= { coTCPSerialStatusGroup 5 }

coTCPSerialRxBytes OBJECT-TYPE
    SYNTAX      Counter32
    UNITS       "bytes"
    MAX-ACCESS  read-only
    STATUS      current
    DESCRIPTION "Number of bytes received from the serial device."
    ::= { coTCPSerialStatusGroup 6 }


-- TCP Serial notifications
colubrisTCPSerialMIBNotificationPrefix OBJECT IDENTIFIER ::= { colubrisTCPSerialMIB 2 }
colubrisTCPSerialMIBNotifications OBJECT IDENTIFIER ::= { colubrisTCPSerialMIBNotificationPrefix 0 }

-- conformance information
colubrisTCPSerialMIBConformance OBJECT IDENTIFIER ::= { colubrisTCPSerialMIB 3 }
colubrisTCPSerialMIBCompliances OBJECT IDENTIFIER ::= { colubrisTCPSerialMIBConformance 1 }
colubrisTCPSerialMIBGroups      OBJECT IDENTIFIER ::= { colubrisTCPSerialMIBConformance 2 }


-- compliance statements
colubrisTCPSerialMIBCompliance MODULE-COMPLIANCE
    STATUS      current
    DESCRIPTION "The compliance statement for the TCP Serial MIB."
    MODULE      MANDATORY-GROUPS
                    {
                        colubrisTCPSerialConfigMIBGroup
                    }
    ::= { colubrisTCPSerialMIBCompliances 1 }

-- units of conformance
colubrisTCPSerialConfigMIBGroup OBJECT-GROUP
    OBJECTS     {
                    coTCPSerialConnectionStatus,
                    coTCPSerialRemoteIPAddress,
                    coTCPSerialRemoteTCPPort,
                    coTCPSerialConnectTime,
                    coTCPSerialTxBytes,
                    coTCPSerialRxBytes
                }
    STATUS      current
    DESCRIPTION "A collection of objects for the TCP Serial
                 status information."
    ::= { colubrisTCPSerialMIBGroups 1 }

END
