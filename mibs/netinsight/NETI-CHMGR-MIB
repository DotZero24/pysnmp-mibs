NETI-CHMGR-MIB DEFINITIONS ::= BEGIN

IMPORTS

    MODULE-IDENTITY, OBJECT-TYPE, Counter32, Gauge32,
    Unsigned32, Counter64
        FROM SNMPv2-SMI

    RowPointer, RowStatus, TEXTUAL-CONVENTION, TimeStamp,
    TruthValue, MacAddress
        FROM SNMPv2-TC

    SnmpAdminString
        FROM SNMP-FRAMEWORK-MIB

    netiExperimentalGeneric
        FROM NETI-COMMON-MIB

    DtmAddress
        FROM NETI-DTM-MIB
    ;

netiChmgrMIB MODULE-IDENTITY
    LAST-UPDATED
        "201501081500Z"
    ORGANIZATION
        "Net Insight AB"
    CONTACT-INFO
        "Net Insight AB
         Box 42093
         SE-126 14 Stockholm
         Sweden
         Tel +46-8-685 0400
         info@netinsight.se"
    DESCRIPTION
        "MIB for the Channel Manager. The Channel Manager is a
         function that manages connections and their channels in a
         consistent manner, independently of the service that uses the
         connection. The Channel Manager provides a common method to
         configure the connections, and to present data about the
         connections and channels that exist."

    REVISION
        "201501081500Z"
    DESCRIPTION
        "Added object for Spare Capacity Utilization, a function that
         allows a channel to utilize otherwise unused link capacity:
         chmgrODescrOneHopSpareCapUtilization."

    REVISION
        "201405051200Z"
    DESCRIPTION
        "Updated textual convention Dst with DST for updated JPEG2000
         mapping of audio into MXF: `j2kHdSdi2(24)', `j2k3gSdi2(25)',
         `j2kSdSdi2(26)'."

    REVISION
        "201402061500Z"
    DESCRIPTION
        "Added objects for describing DCP version:
        chmgrODescrRequestedDcpVersion, chmgrOConnDcpVersion and
        chmgrTConnDcpVersion."

    REVISION
        "201309021600Z"
    DESCRIPTION
        "- Added chmgrOConnForceSourceRoute to allow re-establishing
           a channels using a specified source route.

         - Removed unnecessary range limit on Unsinged32 when full
           range is used."

    REVISION
        "201203190900Z"
    DESCRIPTION
        "- Added chmgrODescrAcceptableMbps and
           chmgrODescrRequestedMbps to allow setting of capacity
           larger than 4,294,967,295 bits per second.

         - Removed range limiter on chmgrODescrAcceptableSlots and
           chmgrODescrRequestedSlots to allow presentation of higher
           capacity."

    REVISION
        "201201261500Z"
    DESCRIPTION
        "Updated textual convention Dst with DSTs for JPEG 2000:
         `j2kSdSdi(21)', `j2kHdSdi(22)', and `j2k3gSdi(23)'. "

    REVISION
        "201004060800Z"
    DESCRIPTION
        "Corrected description of chmgrOChanSourceRouteIndex."

    REVISION
        "200909251100Z"
    DESCRIPTION
        "Removed range limiter (0..4294967295) for
         chmgrODescrRequestedBps, chmgrODescrAcceptableBps and
         chmgrODescrChanSourceRoute.

         Added chmgrODescrSuppressAlarms."

    REVISION
        "200812121400Z"
    DESCRIPTION
        "Changed label `dlt(1)' to `ets(1)', and `dit(2)' to `its(2)'
         for enumeration in chmgrODescrType."

    REVISION
        "200801281400Z"
    DESCRIPTION
        "Added chmgrODescrDestAdminStatus that will allow enabling and
         disabling of destinations for multicast connections.

         Added chmgrChanDestDsti and slightly modified
         chmgrChanDestOutgoingIfPort."
    REVISION
        "200801031600Z"
    DESCRIPTION
        "Added allowAlternative and allowZeroCapacity to
         chmgrODescrCapabilities.

         Added DST for Time Transfer Channel Protocol, and AES/EBU."

    REVISION
        "200706291200Z"
    DESCRIPTION
        "Added chmgrChanCapacity.
         Changed label `dlt(8)' to `ets(8)' for textual convention Dst."

    REVISION
        "200609200800Z"
    DESCRIPTION
        "Updated Dsti textual convention to use range 0..32769, and to
         use display hint.

         Added textual convention DisplayId, and using this instead of
         using Unsigned32.

         Added textual convention Dst, and using this instead of
         Integer32.

         Added channel list support by adding chmgrChannelGroup.

         Corrected spelling errors in descriptions."

    REVISION
        "200604200900Z"
    DESCRIPTION
        "Added precedence object chmgrODescrPrecedence.
         Added allowAlternative to chmgrODescrCapabilities.

         Added objects for channel re-establishment
         chmgrOConnReestablish and chmgrOChanReestablish.

         Added statistical objects, 64-bit values for bitrate
         chmgrOStatDcap1Bitrate and chmgrTStatDcap1Bitrate, and per
         cent indicator objects chmgrOStatDcap1Load and
         chmgrTStatDcap1Load.

         Added dle as connection type to chmgrODescrType.

         Changed some formatting and typing errors in descriptions."

    REVISION
        "200509270000Z"
    DESCRIPTION
        "Updated descriptions.
         The chmgrTStatPMReferenceTable is deprecated."

    REVISION
        "200411180000Z"
    DESCRIPTION
        "The value that indicates that no source route shall be
         used is changed from 0 to max value. Changes only made in
         descriptions."

    REVISION
        "200304240000Z"
    DESCRIPTION
        "Added operational state `dormant' for originating and
         terminating connections."
    ::= { netiExperimentalGeneric 14 }

--
-- Textual Conventions
--

Dst ::= TEXTUAL-CONVENTION
    STATUS  current
    DESCRIPTION
        "The DST (DTM Service Type). The DST denotes a class of data
         for which a channel is used."
    SYNTAX  INTEGER {
                ctrl(0),
                dleCrtlAndData(1),
                pdh(4),
                dleInterServer(5),
                ets(8),
                ping(12),
                e1(13),
                ds1(14),
                sdi(15),
                dvb(16),
                sdh(18),
                ttcp(19),
                aesebu(20),
                j2kSdSdi(21),
                j2kHdSdi(22),
                j2k3gSdi(23),
                j2kHdSdi2(24),
                j2k3gSdi2(25),
                j2kSdSdi2(26) }


Dsti ::= TEXTUAL-CONVENTION
    DISPLAY-HINT "d"
    STATUS  current
    DESCRIPTION
        "The DSTI (DTM Service Type Instance) is a number to identify
         an instance of a service within a service type. The number is
         used by the application to address the individual instance of
         the service between nodes."
    SYNTAX  Unsigned32 (0..32769)


ChannelId ::= TEXTUAL-CONVENTION
    DISPLAY-HINT "x"
    STATUS  current
    DESCRIPTION
        "The identity of the a channel. This value is unique within
         the node where the channel originates. Together with the
         address (typically the MAC address) of the originating node,
         the channel's identity is unique within the entire DTM
         network."
    SYNTAX  Unsigned32


DcapType ::= TEXTUAL-CONVENTION
    STATUS  current
    DESCRIPTION
        "The DCAP (DTM Channel Adaptation Protocol) type for the
         connection.

         dcap0(1)
         DCAP-0 that provides an asynchronous streaming service.

         dcap1(2)
         DCAP-1 that provides an asynchronous packet service."
    SYNTAX  INTEGER {
                dcap0(1),
                dcap1(2) }


DtmNode ::= TEXTUAL-CONVENTION
    STATUS  current
    DESCRIPTION
        "The DTM node is either the DTM address of a node, or the
         node's name. If the DtmNode is on the format of a DTM
         address, is assumed that it is the DTM address. If not, it
         is assumed that it is the name of the node.

         A DTM address has the format of eight groups of two characters
         each, separated by dots. Each group represents one octet in
         hexadecimal notation, e.g. '00.00.00.00.00.00.00.00'

         A node's name has the format of a string with printable,
         non-white space characters."
    SYNTAX  OCTET STRING (SIZE (0..64))

DcpVersion ::= TEXTUAL-CONVENTION
    STATUS  current
    DESCRIPTION
        "The DCP version."
    SYNTAX  INTEGER {
                auto(1),
                dcp2(2),
                dcp3(3) }

--
-- Objects in the NETI-CHMGR-MIB
--

chmgrObjects       OBJECT IDENTIFIER ::= { netiChmgrMIB 1 }
chmgrNotifications OBJECT IDENTIFIER ::= { netiChmgrMIB 2 }
chmgrConformance   OBJECT IDENTIFIER ::= { netiChmgrMIB 3 }


--
-- Groups in the NETI-CHMGR-MIB.
-- The group chmgrTDescriptionGroup is a placeholder for future
-- objects for descriptions on the termination side of a connection.
--

chmgrODescriptionGroup OBJECT IDENTIFIER ::= { chmgrObjects 1 }
chmgrTDescriptionGroup OBJECT IDENTIFIER ::= { chmgrObjects 2 }
chmgrSourceRouteGroup  OBJECT IDENTIFIER ::= { chmgrObjects 3 }
chmgrOConnectionGroup  OBJECT IDENTIFIER ::= { chmgrObjects 4 }
chmgrTConnectionGroup  OBJECT IDENTIFIER ::= { chmgrObjects 5 }
chmgrStatisticsGroup   OBJECT IDENTIFIER ::= { chmgrObjects 6 }
chmgrChannelGroup      OBJECT IDENTIFIER ::= { chmgrObjects 7 }


--
-- the Originating Description Group
--

chmgrODescriptionTimeStamp OBJECT-TYPE
    SYNTAX      TimeStamp
    MAX-ACCESS  read-only
    STATUS      current
    DESCRIPTION
        "Time stamp when any data in any of the tables in this group
         were last updated."
    ::= { chmgrODescriptionGroup 1 }

-- Description Table

chmgrODescriptionTable OBJECT-TYPE
    SYNTAX      SEQUENCE OF ChmgrODescriptionEntry
    MAX-ACCESS  not-accessible
    STATUS      current
    DESCRIPTION
        "Descriptions on originating connections. The creation and
         deletion of rows in the table is done by the application that
         provides the service on the connection. When a row is
         deleted, the associated rows in the destination table
         chmgrODescrDestinationTable and channel table
         chmgrODescrChannelTable are also deleted.

         The table contains information about the capabilities of the
         connections as well as the actual configuration of the
         connections. As the capabilities depends on the type of
         service, it is the service's application that is responsible
         for defining these.

         Changes made on a row in the table will take immediate
         effect. This could result in a re-establishment of the
         channel(s) using the new parameters."
    ::= { chmgrODescriptionGroup 2 }

chmgrODescriptionEntry OBJECT-TYPE
    SYNTAX      ChmgrODescriptionEntry
    MAX-ACCESS  not-accessible
    STATUS      current
    DESCRIPTION
        "An entry in the table is representing the description and
         configuration of one connection."
    INDEX { chmgrODescrIndex }
    ::= { chmgrODescriptionTable 1 }

ChmgrODescriptionEntry ::= SEQUENCE {
    chmgrODescrIndex                Unsigned32,
    chmgrODescrType                 INTEGER,
    chmgrODescrCapabilities         BITS,
    chmgrODescrCustomerId           Unsigned32,
    chmgrODescrServiceReference     RowPointer,
    chmgrODescrAcceptableBps        Gauge32,
    chmgrODescrAcceptableSlots      Gauge32,
    chmgrODescrRequestedBps         Gauge32,
    chmgrODescrRequestedSlots       Gauge32,
    chmgrODescrReestablishMethod    INTEGER,
    chmgrODescrMinInterval          Gauge32,
    chmgrODescrMaxInterval          Gauge32,
    chmgrODescrEstablish            TruthValue,
    chmgrODescrNextDestTableIndex   Unsigned32,
    chmgrODescrPrecedence           TruthValue,
    chmgrODescrSuppressAlarms       BITS,
    chmgrODescrAcceptableMbps       Gauge32,
    chmgrODescrRequestedMbps        Gauge32,
    chmgrODescrRequestedDcpVersion  DcpVersion,
    chmgrODescrOneHopSpareCapUtilization TruthValue }

chmgrODescrIndex OBJECT-TYPE
    SYNTAX      Unsigned32
    MAX-ACCESS  not-accessible
    STATUS      current
    DESCRIPTION
        "Index for this entry."
    ::= { chmgrODescriptionEntry 1 }

chmgrODescrType OBJECT-TYPE
    SYNTAX      INTEGER {
                    ets(1),
                    its(2),
                    dle(3) }
    MAX-ACCESS  read-only
    STATUS      current
    DESCRIPTION
        "This is the unique connection type identifier that defined
         the type of service that the connection description
         describes.

         ets(1).  Ethernet Transport Service (DTM LAN Transport).

         its(2).  Isochronous Transport Service (DTM Isochronous
         Transport).

         dle(3).  DTM LAN Emulation."
    ::= { chmgrODescriptionEntry 2 }

chmgrODescrCapabilities OBJECT-TYPE
    SYNTAX      BITS {
                    allowCapacityInterval(0),
                    destination(1),
                    allowDynamicCapacity(2),
                    isMulticast(3),
                    allowEstablish(4),
                    allowProtection(5),
                    allowReestablish(6),
                    allowScheduling(7),
                    allowSourceRoute(8),
                    requireCapacity(9),
                    allowAlternative(10),
                    allowZeroCapacity(11) }
    MAX-ACCESS  read-only
    STATUS      current
    DESCRIPTION
        "Connection capabilities that indicate which parameters that
         are possible to configure in this connection description.

         allowCapacityInterval(0)
         Allows the configuration of capacity to have different values
         on requested and accepted capacity.

         destination(1)
         Describes if destinations shall be configured for this
         description. This is the normal case for most connections,
         but is some cases, the destination is decided by the
         application that is responsible for the service on the
         connection.

         allowDynamicCapacity(2)
         Allows the use of dynamic capacity adjustment.

         isMulticast(3)
         Describes if the connection is a multicast connection. This
         value is set by the application that is responsible for the
         service that uses the connection.

         allowEstablish(4)
         Allows the configuration of whether the connection shall be
         established using the capacity configurations of the
         connection or not.

         allowProtection(5)
         Allows the connection to be configured to be 1+1 protected by
         using two channels for the connection.

         allowReestablish(6)
         Allows configuration of the re- establishment algorithm.

         allowScheduling(7)
         Allows an external application, such as a scheduled, to alter
         the capacity and administrative state of the connection.

         allowSourceRoute(8)
         Allows configuration of source routed connections.

         requireCapacity(9)
         Requires the configuration of capacity. This is the normal
         case for most connections, but in some cases, the capacity is
         defaulted by the application.

         allowAlternative(10)
         Allows configuration of several alternative destinations. The
         unicast connection will be established using only one of the
         available destination.

         allowZeroCapacity(11).
         Allows configuration of zero capacity."
    ::= { chmgrODescriptionEntry 3 }

chmgrODescrCustomerId OBJECT-TYPE
    SYNTAX      Unsigned32
    MAX-ACCESS  read-only
    STATUS      current
    DESCRIPTION
        "This is a customer identifications number assigned by the
         application that is providing the service on the
         connection. The object has no functional use except to
         provide the information."
    ::= { chmgrODescriptionEntry 4 }

chmgrODescrServiceReference OBJECT-TYPE
    SYNTAX      RowPointer
    MAX-ACCESS  read-only
    STATUS      current
    DESCRIPTION
        "This is a pointer to the application or service that owns
         this connection description, and that is responsible for the
         capabilities."
    ::= { chmgrODescriptionEntry 5 }

chmgrODescrAcceptableBps OBJECT-TYPE
    SYNTAX      Gauge32
    MAX-ACCESS  read-write
    STATUS      current
    DESCRIPTION
        "The minimum payload capacity in bits per second for the
         service using the channel. If it is not possible to allocate
         this capacity, a channel will not be established.  If the
         acceptable capacity is larger than the maximum value
         (4,294,967,295) bits per second, then the
         `chmgrODescrAcceptableMbps' must be used.  If the capacity is
         greater than the maximum value of this object, then the this
         object should report the maximum value."
    ::= { chmgrODescriptionEntry 6 }

chmgrODescrAcceptableSlots OBJECT-TYPE
    SYNTAX      Gauge32
    MAX-ACCESS  read-only
    STATUS      current
    DESCRIPTION
        "The minimum capacity in number of 512 kbps DTM slots. The
         value is based on the chmgrAcceptableBps and the necessary
         overhead required by the service for delivering the payload
         capacity. The overhead is calculated by the service
         application."
    ::= { chmgrODescriptionEntry 7 }

chmgrODescrRequestedBps OBJECT-TYPE
    SYNTAX      Gauge32
    MAX-ACCESS  read-write
    STATUS      current
    DESCRIPTION
        "The requested payload capacity in bits per second for the
         service using the channel.  If the requested capacity is
         larger than the maximum value (4,294,967,295) bits per
         second, then the `chmgrODescrRequestedMbps' must be used.
         If the capacity is greater than the maximum value of this
         object, then the this object should report the maximum value."
    ::= { chmgrODescriptionEntry 8 }

chmgrODescrRequestedSlots OBJECT-TYPE
    SYNTAX      Gauge32
    MAX-ACCESS  read-only
    STATUS      current
    DESCRIPTION
        "The requested capacity in number of 512 kbps DTM slots. The
         value is based on the chmgrRequestedBps and the necessary
         overhead required by the service for delivering the payload
         capacity. The overhead is calculated by the service
         application."
    ::= { chmgrODescriptionEntry 9 }

chmgrODescrReestablishMethod OBJECT-TYPE
    SYNTAX      INTEGER {
                    exponential(1) }
    MAX-ACCESS  read-write
    STATUS      current
    DESCRIPTION
        "The type of algorithm or method used to re-establish channels
         that for some reason fail to be established or is torn down.
         The methods are:

         exponential(1)
         Establishment attempts are done at time interval that is
         doubled for each attempt, starting at chmgrMinInterval and
         increased to a maximum of chmgrMaxInterval, until a channel
         is successfully established.

         The value is only valid if the allowReestablish(6) bit in
         chmgrODescrCapabililties is set."
    DEFVAL { exponential }
    ::= { chmgrODescriptionEntry 10 }

chmgrODescrMinInterval OBJECT-TYPE
    SYNTAX      Gauge32 (0..3600000)
    MAX-ACCESS  read-write
    STATUS      current
    DESCRIPTION
        "The minimum time in milliseconds between two attempts to
         establish the channel."
    DEFVAL { 500 }
    ::= { chmgrODescriptionEntry 11 }

chmgrODescrMaxInterval OBJECT-TYPE
    SYNTAX      Gauge32 (0..3600000)
    MAX-ACCESS  read-write
    STATUS      current
    DESCRIPTION
        "The maximum time in milliseconds between two attempts to
         establish the channel. This value must be larger than
         chmgrODescrMinInterval."
    DEFVAL { 10000 }
    ::= { chmgrODescriptionEntry 12 }

chmgrODescrEstablish OBJECT-TYPE
    SYNTAX      TruthValue
    MAX-ACCESS  read-write
    STATUS      current
    DESCRIPTION
        "Describes if the connection shall be established with the
         defined parameters. The value is only valid if the
         allowEstablish(4) bit in chmgrODescrCapabilites is set.

         true(1)
         The connection is established.

         false(2)
         The connection is not established. The establishment of the
         connection is controlled by some other function outside the
         scope of this MIB. This could be a scheduler or timer
         specified in other MIB's."

    DEFVAL { true }
    ::= { chmgrODescriptionEntry 13 }

chmgrODescrNextDestTableIndex OBJECT-TYPE
    SYNTAX      Unsigned32 (0..4294967295)
    MAX-ACCESS  read-only
    STATUS      current
    DESCRIPTION
        "The value of the next available index for this connection
         description in the chmgrODescrDestinationTable."
    ::= { chmgrODescriptionEntry 14 }

chmgrODescrPrecedence OBJECT-TYPE
    SYNTAX      TruthValue
    MAX-ACCESS  read-write
    STATUS      current
    DESCRIPTION
        "A channel with precedence is established and torn down before
         any channel without precedence.

         true(1)
         The channel has precedence.

         false(2)
         The channel does not have precedence."
    DEFVAL { false }
    ::= { chmgrODescriptionEntry 15 }

chmgrODescrSuppressAlarms OBJECT-TYPE
    SYNTAX      BITS {
                    route(0) }
    MAX-ACCESS  read-write
    STATUS      current
    DESCRIPTION
        "Suppress generation of some alarms:

         route(0)
         Alarm raised if a service is not using its primary source route."
    ::= { chmgrODescriptionEntry 16 }

chmgrODescrAcceptableMbps OBJECT-TYPE
    SYNTAX      Gauge32
    MAX-ACCESS  read-write
    STATUS      current
    DESCRIPTION
        "The minimum payload capacity in units of 1,000,000 bits per
         second for the service using the channel.  If it is not
         possible to allocate this capacity, a channel will not be
         established.  This object must be used when requesting a
         capacity larger than 4,294,967,295 bits per second.  If a
         lower capacity is requested, then it is possible to use
         `chmgrODescrAcceptableBps'."
    ::= { chmgrODescriptionEntry 17 }

chmgrODescrRequestedMbps OBJECT-TYPE
    SYNTAX      Gauge32
    MAX-ACCESS  read-write
    STATUS      current
    DESCRIPTION
        "The requested payload capacity in units of 1,000,000 bits per
         second for the service using the channel.  This object must
         be used when requesting a capacity larger than 4,294,967,295
         bits per second.  If a lower capacity is requested, then it
         is possible to use `chmgrODescrRequestedBps'."
    ::= { chmgrODescriptionEntry 18 }

chmgrODescrRequestedDcpVersion OBJECT-TYPE
    SYNTAX      DcpVersion
    MAX-ACCESS  read-write
    STATUS      current
    DESCRIPTION
        "The DCP version that should be used for channel established for
         this connection. `any' means try with DCP3 first and revert to
         DCP2 if unsuccessful because of node version mismatch."
    ::= { chmgrODescriptionEntry 19 }

chmgrODescrOneHopSpareCapUtilization OBJECT-TYPE
    SYNTAX      TruthValue
    MAX-ACCESS  read-write
    STATUS      current
    DESCRIPTION
        "Specifies if the the channel shall dynamically allocate spare
         capacity.

         When `true', then the channel is initially established with
         the acceptable capacity specified in chmgrODescrAcceptableBps
         (or chmgrODescrAcceptableMbps).  The channel capacity is then
         monitored and automatically increased with available capacity
         up to the capacity specified in chmgrODescrRequestedBps (or
         chmgrODescrRequestedMbps).  If another channel would request
         capacity, then the capacity of this channel is reduced as
         needed by the other channel, but not below the acceptable
         capacity.

         When set to `false', then spare capacity will not be used.

         This function requires use of DCP3, see
         chmgrODescrRequestedDcpVersion.

         This function requires use of ETS unicast.

         This function requires the channel destination to be a
         neighboring node."
    ::= { chmgrODescriptionEntry 20 }



-- End of Description Table


-- Destination Table

chmgrODescrDestinationTable OBJECT-TYPE
    SYNTAX      SEQUENCE OF ChmgrODescrDestinationEntry
    MAX-ACCESS  not-accessible
    STATUS      current
    DESCRIPTION
        "The table describes destinations for a connection. A unicast
         connection can normally only have one destination, while a
         multicast connection may have several destinations.

         If a unicast connection allows alternative destinations, as
         defined by the allowAlternative(10) bit in
         chmgrODescrCapabilities, it is allowed to define multiple
         destinations. At channel establishment, the destinations will
         be tried in succession until a channel is successfully
         established.

         It is possible to add, change and delete destinations while
         the connection is active. For a unicast connection, a
         changed destination is torn down as soon as it is changed,
         and established as soon as the changed information contains
         valid data. For a multicast connection, it is possible to
         add and delete destinations to an already established
         connection without affecting the connection to the other
         destinations. An added destination will be established as
         soon as it includes valid information, and will be
         re-established as soon as the information is changed.

         Note that a destination address with an empty string can be
         used to disable the destination. For a multicast connection
         a single destination can also be enabled and disabled using
         its administrative status.

         The bits allowAlternative(10), destination(1) and
         allowMulticast(3) in chmgrODescCapabilities describes
         if and how it is allowed to add a destination to a
         connection."
    ::= { chmgrODescriptionGroup 3 }

chmgrODescrDestinationEntry OBJECT-TYPE
    SYNTAX      ChmgrODescrDestinationEntry
    MAX-ACCESS  not-accessible
    STATUS      current
    DESCRIPTION
        "An entry in the table represents one destination."
    INDEX { chmgrODescrIndex, chmgrODescrDestIndex }
    ::= { chmgrODescrDestinationTable 1 }

ChmgrODescrDestinationEntry ::= SEQUENCE {
    chmgrODescrDestIndex        Unsigned32,
    chmgrODescrDestAddress      DtmNode,
    chmgrODescrDestDsti         Dsti,
    chmgrODescrDestRowStatus    RowStatus,
    chmgrODescrDestAdminStatus  INTEGER }

chmgrODescrDestIndex OBJECT-TYPE
    SYNTAX      Unsigned32
    MAX-ACCESS  not-accessible
    STATUS      current
    DESCRIPTION
        "The index for this entry."
    ::= { chmgrODescrDestinationEntry 1 }

chmgrODescrDestAddress OBJECT-TYPE
    SYNTAX      DtmNode
    MAX-ACCESS  read-create
    STATUS      current
    DESCRIPTION
        "The DTM address for a destination termination point of the
         connection. The empty string indicates an unconfigured
         destination. The address should be the last object to
         configure to avoid unnecessary channel establishment while
         configuring the destination."
    DEFVAL { ''H }
    ::= { chmgrODescrDestinationEntry 2 }

chmgrODescrDestDsti OBJECT-TYPE
    SYNTAX      Dsti
    MAX-ACCESS  read-create
    STATUS      current
    DESCRIPTION
        "The DSTI (DTM Service Type Instance) for the destination
         termination point of the connection."
    DEFVAL { 0 }
    ::= { chmgrODescrDestinationEntry 3 }

chmgrODescrDestRowStatus OBJECT-TYPE
    SYNTAX      RowStatus
    MAX-ACCESS  read-create
    STATUS      current
    DESCRIPTION
        "See SNMPv2-TC. The following values are supported:

         active(1)
         The object always reads active(1).

         createAndGo(4)
         A new conceptual row is created representing a new
         destination.

         destroy(6)
         The conceptual row representing the destination is deleted,
         and the connection to the destination is torn
         down. Connections to other destinations are not
         affected. Associated rows in the channel table
         chmgrODescrChannelTable will also be destroyed."
    ::= { chmgrODescrDestinationEntry 4 }

chmgrODescrDestAdminStatus OBJECT-TYPE
    SYNTAX      INTEGER {
                    up(1),
                    down(2) }
    MAX-ACCESS  read-create
    STATUS      current
    DESCRIPTION
        "The administrative state of the destination. The value
         controls the desired state of the multicast connection
         to the destination.

         up(1). The connection shall be established to the
         destination.

         down(2). No connection shall be established to the
         destination."
    ::= { chmgrODescrDestinationEntry 5 }


-- End of Destination Table


-- Channel Table

chmgrODescrChannelTable OBJECT-TYPE
    SYNTAX      SEQUENCE OF ChmgrODescrChannelEntry
    MAX-ACCESS  not-accessible
    STATUS      current
    DESCRIPTION
        "The table describes relationships between destinations
         defined in the chmgrODescrDestinationTable, channels and
         source routes. To make a connection to a destination 1+1
         protected, create two rows representing the two channels in
         the table. Note that this is only allowed if the bit
         allowProtection(5) is set in chmgrODescrCapabilities.

         If no conceptual row exists for a destination, it is assumed
         that there shall be only one channel to the destination and
         that no source route is shall be used.

         A channel to a destination may have its route through the DTM
         networks defined by one or many source routes. If multiple
         source routes are defined, any one of these source routes is
         chosen when the channel is established."
    ::= { chmgrODescriptionGroup 4 }

chmgrODescrChannelEntry OBJECT-TYPE
    SYNTAX      ChmgrODescrChannelEntry
    MAX-ACCESS  not-accessible
    STATUS      current
    DESCRIPTION
        "An entry in this table represents the relationship between
         one channel in the connection (defined in
         chmgrODescrDestinationTable) and one source route (defined in
         chmgrSourceRouteTable)."
    INDEX { chmgrODescrIndex, chmgrODescrDestIndex,
            chmgrODescrChanIndex, chmgrODescrChanSourceRouteIndex }
    ::= { chmgrODescrChannelTable 1 }

ChmgrODescrChannelEntry ::= SEQUENCE {
    chmgrODescrChanIndex             Unsigned32,
    chmgrODescrChanSourceRouteIndex  Unsigned32,
    chmgrODescrChanSourceRoute       Unsigned32,
    chmgrODescrChanRowStatus         RowStatus
}

chmgrODescrChanIndex OBJECT-TYPE
    SYNTAX      Unsigned32 (1..2)
    MAX-ACCESS  not-accessible
    STATUS      current
    DESCRIPTION
        "The index of the channel used by the connection."
    ::= { chmgrODescrChannelEntry 1 }

chmgrODescrChanSourceRouteIndex OBJECT-TYPE
    SYNTAX      Unsigned32
    MAX-ACCESS  not-accessible
    STATUS      current
    DESCRIPTION
        "The index of the row describing the relationship to one
         source route."
    ::= { chmgrODescrChannelEntry 2 }

chmgrODescrChanSourceRoute OBJECT-TYPE
    SYNTAX      Unsigned32
    MAX-ACCESS  read-create
    STATUS      current
    DESCRIPTION
        "The index in the chmgrOSourceRouteTable representing the
         desired source route for the channel to the destination. If
         no source route shall be used by the channel for this
         destination, delete the conceptual row or set the value to
         the max value (4294967295)."
    ::= { chmgrODescrChannelEntry 3 }

chmgrODescrChanRowStatus OBJECT-TYPE
    SYNTAX      RowStatus
    MAX-ACCESS  read-create
    STATUS      current
    DESCRIPTION
        "See SNMPv2-TC. The following values are supported:

         active(1)
         The object always reads active(1).

         createAndGo(4)
         a new conceptual row is created representing a channel is
         added.

         destroy(6)
         The conceptual row representing the channel is deleted."
    ::= { chmgrODescrChannelEntry 4 }

-- End of Channel Table


--
-- Terminating Description Group
--

-- The group is a placeholder for future extensions to the MIB.
-- Possible extensions could be to configuration of connections
-- on the terminating side. Such connections could be to be able
-- to attachment to an existing multicast tree.


--
-- Source Route Group
--

chmgrSourceRouteTimeStamp OBJECT-TYPE
    SYNTAX      TimeStamp
    MAX-ACCESS  read-only
    STATUS      current
    DESCRIPTION
        "Value of sysUpTime when any of the tables in this group were last
         updated."
    ::= { chmgrSourceRouteGroup 1 }


-- Source Route Table

chmgrSourceRouteTable OBJECT-TYPE
    SYNTAX      SEQUENCE OF ChmgrSourceRouteEntry
    MAX-ACCESS  not-accessible
    STATUS      current
    DESCRIPTION
        "Table listing source routes. A source route is a route
         through the DTM net that is defined at the source of the
         channel. The source routes may be used by many connections,
         making the connections using the same route through the DTM
         network. A source route may only be updated or deleted when
         it is not used by any established connection.

         Note that a source route set up as loose, with no
         intermediate nodes, and set up to use any outgoing interface
         is equivalent to a shortest path routing."
    ::= { chmgrSourceRouteGroup 2 }

chmgrSourceRouteEntry OBJECT-TYPE
    SYNTAX      ChmgrSourceRouteEntry
    MAX-ACCESS  not-accessible
    STATUS      current
    DESCRIPTION
        "An entry representing one source route."
    INDEX { chmgrSourceRouteIndex }
    ::= { chmgrSourceRouteTable 1 }

ChmgrSourceRouteEntry ::= SEQUENCE {
    chmgrSourceRouteIndex           Unsigned32,
    chmgrSourceRouteName            SnmpAdminString,
    chmgrSourceRouteTypeOfRoute     INTEGER,
    chmgrSourceRouteFirstIfBoard    Unsigned32,
    chmgrSourceRouteFirstIfPort     Unsigned32,
    chmgrSourceRouteRowStatus       RowStatus
}

chmgrSourceRouteIndex OBJECT-TYPE
    SYNTAX      Unsigned32
    MAX-ACCESS  not-accessible
    STATUS      current
    DESCRIPTION
        "The index for this entry."
    ::= { chmgrSourceRouteEntry 1 }

chmgrSourceRouteName OBJECT-TYPE
    SYNTAX      SnmpAdminString
    MAX-ACCESS  read-write
    STATUS      current
    DESCRIPTION
        "A string for administrative use that identifies or describes
         the source route. The string does not have to be unique."
    ::= { chmgrSourceRouteEntry 2 }

chmgrSourceRouteTypeOfRoute OBJECT-TYPE
    SYNTAX      INTEGER {
                    strict(1),
                    loose(2) }
    MAX-ACCESS  read-create
    STATUS      current
    DESCRIPTION
        "The type of source route that shall be used.

         strict(1)
         The channel must only pass the hops defined in the source
         route.

         loose(2)
         The channel must pass all the hops defined in the source
         route."
    DEFVAL { strict }
    ::= { chmgrSourceRouteEntry 3 }

chmgrSourceRouteFirstIfBoard OBJECT-TYPE
    SYNTAX      Unsigned32
    MAX-ACCESS  read-create
    STATUS      current
    DESCRIPTION
        "The identity of the board where the DTM interface is located
         that shall be used for leaving the node. A value of zero (0)
         means that any board may be used. A DTM interface is
         identified by a board and a port on that board."
    DEFVAL { 0 }
    ::= { chmgrSourceRouteEntry 4 }

chmgrSourceRouteFirstIfPort OBJECT-TYPE
    SYNTAX      Unsigned32
    MAX-ACCESS  read-create
    STATUS      current
    DESCRIPTION
        "The identity of the port on the board specified in
         chmgrSourceRouteFirstIfBoard that shall be used for leaving
         the node. A value of zero (0) means that any port may be
         used. A DTM interface is identified by a board and a port on
         that board."
    DEFVAL { 0 }
    ::= { chmgrSourceRouteEntry 5 }

chmgrSourceRouteRowStatus OBJECT-TYPE
    SYNTAX      RowStatus
    MAX-ACCESS  read-create
    STATUS      current
    DESCRIPTION
        "Se SNMPv2-TC. Supports createAndGo(4) and destroy(6).

         createAndGo(4)
         A new row is created representing a new
         source route.

         destroy(6)
         A row is deleted. All rows in the chmgrSourceRouteHopTable
         that describes the route are also deleted. It is not possible
         to change or delete a source route that is in use by an
         established channel."

    ::= { chmgrSourceRouteEntry 6 }

-- End of Source Route Table


-- Source Route Hop Table

chmgrSourceRouteHopTable OBJECT-TYPE
    SYNTAX      SEQUENCE OF ChmgrSourceRouteHopEntry
    MAX-ACCESS  not-accessible
    STATUS      current
    DESCRIPTION
        "Table describing the nodes and interfaces for intermediate nodes
         that a source route shall be using."
    ::= { chmgrSourceRouteGroup 3 }

chmgrSourceRouteHopEntry OBJECT-TYPE
    SYNTAX      ChmgrSourceRouteHopEntry
    MAX-ACCESS  not-accessible
    STATUS      current
    DESCRIPTION
        "An entry describes one hop for a source route."
    INDEX { chmgrSourceRouteIndex, chmgrSourceRouteHopIndex }
    ::= { chmgrSourceRouteHopTable 1 }

ChmgrSourceRouteHopEntry ::= SEQUENCE {
    chmgrSourceRouteHopIndex        Unsigned32,
    chmgrSourceRouteHopAddress      DtmNode,
    chmgrSourceRouteHopNextIfBoard  Unsigned32,
    chmgrSourceRouteHopNextIfPort   Unsigned32,
    chmgrSourceRouteHopRowStatus    RowStatus
}

chmgrSourceRouteHopIndex OBJECT-TYPE
    SYNTAX      Unsigned32
    MAX-ACCESS  not-accessible
    STATUS      current
    DESCRIPTION
        "The index for this conceptual row."
    ::= { chmgrSourceRouteHopEntry 1 }

chmgrSourceRouteHopAddress OBJECT-TYPE
    SYNTAX      DtmNode
    MAX-ACCESS  read-create
    STATUS      current
    DESCRIPTION
        "The DTM address of the node."
    ::= { chmgrSourceRouteHopEntry 2 }

chmgrSourceRouteHopNextIfBoard OBJECT-TYPE
    SYNTAX      Unsigned32
    MAX-ACCESS  read-create
    STATUS      current
    DESCRIPTION
        "The identity of the  board where the DTM interface is located
         that shall be used for leaving the node. A value of zero (0)
         means that any board may be used. A DTM interface is
         identified by a card and a port on that board."
    DEFVAL { 0 }
    ::= { chmgrSourceRouteHopEntry 3 }

chmgrSourceRouteHopNextIfPort OBJECT-TYPE
    SYNTAX      Unsigned32
    MAX-ACCESS  read-create
    STATUS      current
    DESCRIPTION
        "The identity of the port on the board specified in
         chmgrSourceRouteFirstIfCard that shall be used for leaving
         the node. A value of zero (0) means that any port may be
         used. A DTM interface is identified by a board and a port on
         that board."
    DEFVAL { 0 }
    ::= { chmgrSourceRouteHopEntry 4 }

chmgrSourceRouteHopRowStatus OBJECT-TYPE
    SYNTAX      RowStatus
    MAX-ACCESS  read-create
    STATUS      current
    DESCRIPTION
        "See SNMPv2-TC. The following values are supported:

         active(1)
         The object always reads active(1).

         createAndGo(4)
         A new conceptual row is created.

         destroy(6)
         The conceptual row representing is deleted."
    ::= { chmgrSourceRouteHopEntry 5 }

-- End of Source Route Hop Table


--
-- Originating Connection Group
--

chmgrOConnectionTimeStamp OBJECT-TYPE
    SYNTAX      TimeStamp
    MAX-ACCESS  read-only
    STATUS      current
    DESCRIPTION
        "The value of sysUpTime when any of the tables in the group
         were last changed."
    ::= { chmgrOConnectionGroup 1 }

-- Originating Connection Table

chmgrOConnectionTable OBJECT-TYPE
    SYNTAX      SEQUENCE OF ChmgrOConnectionEntry
    MAX-ACCESS  not-accessible
    STATUS      current
    DESCRIPTION
        "The table lists all the originating connections. The
         connections are configured in the chmgrODescriptionTable."
    ::= { chmgrOConnectionGroup 2 }

chmgrOConnectionEntry OBJECT-TYPE
    SYNTAX      ChmgrOConnectionEntry
    MAX-ACCESS  not-accessible
    STATUS      current
    DESCRIPTION
        "An entry in the table representing one originating connection."
    INDEX { chmgrOConnIndex }
    ::= { chmgrOConnectionTable 1 }

ChmgrOConnectionEntry ::= SEQUENCE {
    chmgrOConnIndex                  Unsigned32,
    chmgrOConnCustomerId             Unsigned32,
    chmgrOConnODescrIndex            Unsigned32,
    chmgrOConnServiceReference       RowPointer,
    chmgrOConnAllocatedSlots         Gauge32,
    chmgrOConnAllocatedSlotsChanged  TimeStamp,
    chmgrOConnDcapType               DcapType,
    chmgrOConnDst                    Dst,
    chmgrOConnSourceAddress          DtmNode,
    chmgrOConnSourceDsti             Dsti,
    chmgrOConnStatusLastChanged      TimeStamp,
    chmgrOConnAdminStatus            INTEGER,
    chmgrOConnOperStatus             INTEGER,
    chmgrOConnReestablish            INTEGER,
    chmgrOConnForceSourceRoute       Unsigned32,
    chmgrOConnDcpVersion             DcpVersion
}

chmgrOConnIndex OBJECT-TYPE
    SYNTAX      Unsigned32
    MAX-ACCESS  not-accessible
    STATUS      current
    DESCRIPTION
        "The index of the connection in the table."
    ::= { chmgrOConnectionEntry 1 }

chmgrOConnCustomerId OBJECT-TYPE
    SYNTAX      Unsigned32
    MAX-ACCESS  read-only
    STATUS      current
    DESCRIPTION
        "This is a customer identification number assigned by the
         application that is providing the service on the
         connection. The object has no functional use except to
         provide the information. This is the same value as
         chmgrODescrCustomerId."
    ::= { chmgrOConnectionEntry 2 }

chmgrOConnODescrIndex OBJECT-TYPE
    SYNTAX      Unsigned32 (0..4294967295)
    MAX-ACCESS  read-only
    STATUS      current
    DESCRIPTION
        "A reference to the chmgrODescriptionTable. It is the index in
         the chmgrODescriptionTable for the description that describes
         the configuration of this connection."
    ::= { chmgrOConnectionEntry 3 }

chmgrOConnServiceReference OBJECT-TYPE
    SYNTAX      RowPointer
    MAX-ACCESS  read-only
    STATUS      current
    DESCRIPTION
        "A reference to the service responsible for this connection.
         The object points to the instance of the service in the
         service's MIB. Its MIB shall have a table representing all
         the instances of the service."
    ::= { chmgrOConnectionEntry 4 }

chmgrOConnAllocatedSlots OBJECT-TYPE
    SYNTAX      Gauge32 (0..8389)
    MAX-ACCESS  read-only
    STATUS      current
    DESCRIPTION
        "The number of 512 kbps DTM slots that is allocated by the
         connection. Note that for a connection with multiple
         channels, e.g. 1+1 protected connection, all the channels
         have the same capacity.

         To know how much capacity that is used by the connection,
         multiply the value with the number of active channels. The
         channels are listed in chmgrOChannelTable."
    ::= { chmgrOConnectionEntry 5 }

chmgrOConnAllocatedSlotsChanged OBJECT-TYPE
    SYNTAX      TimeStamp
    MAX-ACCESS  read-only
    STATUS      current
    DESCRIPTION
        "The value of sysUpTime when the allocated capacity for the
         connection was last changed."
    ::= { chmgrOConnectionEntry 6 }

chmgrOConnDcapType OBJECT-TYPE
    SYNTAX      DcapType
    MAX-ACCESS  read-only
    STATUS      current
    DESCRIPTION
        "The DCAP (DTM Channel Adaptation Protocol) type for the
         connection."
    ::= { chmgrOConnectionEntry 7 }

chmgrOConnDst OBJECT-TYPE
    SYNTAX      Dst
    MAX-ACCESS  read-only
    STATUS      current
    DESCRIPTION
        "The DST (DTM Service Type) of the service that uses the
         connection."
    ::= { chmgrOConnectionEntry 8 }

chmgrOConnSourceAddress OBJECT-TYPE
    SYNTAX      DtmNode
    MAX-ACCESS  read-only
    STATUS      current
    DESCRIPTION
        "The DTM address of the originating node for the connection."
    ::= { chmgrOConnectionEntry 9 }

chmgrOConnSourceDsti OBJECT-TYPE
    SYNTAX      Dsti
    MAX-ACCESS  read-only
    STATUS      current
    DESCRIPTION
        "The DSTI (DTM Service Type Instance) of the service at the
         originating node of the connection."
    ::= { chmgrOConnectionEntry 10 }

chmgrOConnStatusLastChanged OBJECT-TYPE
    SYNTAX      TimeStamp
    MAX-ACCESS  read-only
    STATUS      current
    DESCRIPTION
        "The value of sysUpTime when the operational status of the
         connection was last changed."
    ::= { chmgrOConnectionEntry 11 }

chmgrOConnAdminStatus OBJECT-TYPE
    SYNTAX      INTEGER {
                    up(1),
                    down(2) }
    MAX-ACCESS  read-only
    STATUS      current
    DESCRIPTION
        "Information about the administrative state of the
         connection. The administrative state is controlled by the
         application that provides the service transported on the
         connection. The application sets the administrative state to
         up(1) when a connection shall be established, and down(2)
         when the connection shall be torn down."
    ::= { chmgrOConnectionEntry 12 }

chmgrOConnOperStatus OBJECT-TYPE
    SYNTAX      INTEGER {
                    up(1),
                    down(2),
                    partial(3),
                    dormant(5) }
    MAX-ACCESS  read-only
    STATUS      current
    DESCRIPTION
        "The operational state of the connection. In general, the
         operational state should follow the administrative state,
         chmgrOConnAdminStatus.

         up(1)
         The connection is up to all its destination on all its
         channels. For a unicast connection, this is the one configured
         destination. For a multicast connection, this is all the
         configured connections. For a 1+1 protected connection, this
         is both the channels.

         down(2)
         No channels are established for the connection.

         partial(3)
         The connection is partly established. The connection is not
         established to at least one of its configured destination on
         at least one of its channels.

         dormant(5)
         The establishment of the connection is pending an action
         from some other entity, e.g. a scheduler. This is not an
         error state."
    ::= { chmgrOConnectionEntry 13 }

chmgrOConnReestablish OBJECT-TYPE
    SYNTAX      INTEGER {
                    notApplicable(0),
                    reestablish(1) }
    MAX-ACCESS  read-write
    STATUS      current
    DESCRIPTION
        "Writing to this object immediately starts to re-establish the
         connection to all its destinations.  The establishment of the
         connection will be done according to the current network
         topology and availability.  If source routes are defined, the
         first source route will be tried first.

         notApplicable(0) Always reads this value. This value cannot
         be written.

         reestablish(1) Writing this value reestablishes the
         connection.  "
    ::= { chmgrOConnectionEntry 14 }

chmgrOConnForceSourceRoute OBJECT-TYPE
    SYNTAX      Unsigned32
    MAX-ACCESS  read-write
    STATUS      current
    DESCRIPTION
        "Writing to this object immediately starts to re-establish the
         connection to the destinations and channels using the source
         route specified with the written value.  The value written
         controls which source route to first try when re-establishing
         the channel.  For each destination and channel for the
         connection, the written value is used as value for the index
         chmgrODescrChanSourceRouteIndex in the the
         chmgrODescrChannelTable.  If the entry does not exist, or if
         the source route is already the one that used by the
         destination and channel, then no action is taken.  Otherwise
         if the entry exists, then the channel for the destination is
         re-established, where the given source route is first
         attempted.

         Reading this always returns the value 0."
    ::= { chmgrOConnectionEntry 15 }

chmgrOConnDcpVersion OBJECT-TYPE
    SYNTAX      DcpVersion
    MAX-ACCESS  read-only
    STATUS      current
    DESCRIPTION
        "Version of DCP that is used for this connection. `any(0)'
         means that a channel is not established."
    ::= { chmgrOConnectionEntry 16 }


-- End of Originating Connection Table


-- Originating Destination Table

chmgrODestinationTable OBJECT-TYPE
    SYNTAX      SEQUENCE OF ChmgrODestinationEntry
    MAX-ACCESS  not-accessible
    STATUS      current
    DESCRIPTION
        "List of destinations per origination connection."
    ::= { chmgrOConnectionGroup 3 }

chmgrODestinationEntry OBJECT-TYPE
    SYNTAX      ChmgrODestinationEntry
    MAX-ACCESS  not-accessible
    STATUS      current
    DESCRIPTION
        "An entry represents one destination for a connection."
    INDEX { chmgrOConnIndex, chmgrODescrDestIndex }
    ::= { chmgrODestinationTable 1 }

ChmgrODestinationEntry ::= SEQUENCE {
    chmgrODestDestinationAddress   DtmNode,
    chmgrODestDestinationDsti      Dsti
}

chmgrODestDestinationAddress OBJECT-TYPE
    SYNTAX      DtmNode
    MAX-ACCESS  read-only
    STATUS      current
    DESCRIPTION
        "The DTM address of a destination node."
    ::= { chmgrODestinationEntry 1 }

chmgrODestDestinationDsti OBJECT-TYPE
    SYNTAX      Dsti
    MAX-ACCESS  read-only
    STATUS      current
    DESCRIPTION
        "The DSTI (DTM Service Type Instance) of the service at the
         destination node."
    ::= { chmgrODestinationEntry 2 }

-- End of Origination Destination Table


-- Origination Destination Channel Table

chmgrOChannelTable OBJECT-TYPE
    SYNTAX      SEQUENCE OF ChmgrOChannelEntry
    MAX-ACCESS  not-accessible
    STATUS      current
    DESCRIPTION
        "Table that shows the status for all the originating channels,
         listed per connection and destination."
    ::= { chmgrOConnectionGroup 4 }

chmgrOChannelEntry OBJECT-TYPE
    SYNTAX      ChmgrOChannelEntry
    MAX-ACCESS  not-accessible
    STATUS      current
    DESCRIPTION
        "An entry per channel."
    INDEX { chmgrOConnIndex, chmgrODescrDestIndex, chmgrODescrChanIndex }
    ::= { chmgrOChannelTable 1 }

ChmgrOChannelEntry ::= SEQUENCE {
    chmgrOChanSourceRouteIndex   Unsigned32,
    chmgrOChanChannelId          ChannelId,
    chmgrOChanErrorMessage       SnmpAdminString,
    chmgrOChanErrorAddress       DtmNode,
    chmgrOChanOperStatus         INTEGER,
    chmgrOChanStatusChanged      TimeStamp,
    chmgrOChanReestablish        INTEGER
}

chmgrOChanSourceRouteIndex OBJECT-TYPE
    SYNTAX      Unsigned32
    MAX-ACCESS  read-only
    STATUS      current
    DESCRIPTION
        "The source route index that is referring to the source route
         currently used by the the channel.  This is the value of the
         index chmgrODescrChanSourceRouteIndex in
         chmgrODescrChannelTable.  A value of '0' would mean the 1st
         configured source route is used, '1' the 2nd, and so on.  If
         no source route is used by the channel, then the value is
         4294967295."
    ::= { chmgrOChannelEntry 1 }

chmgrOChanChannelId OBJECT-TYPE
    SYNTAX      ChannelId
    MAX-ACCESS  read-only
    STATUS      current
    DESCRIPTION
        "The identity of the DTM channel. If no channel is
         established, the value is zero (0)."
    ::= { chmgrOChannelEntry 2 }

chmgrOChanErrorMessage OBJECT-TYPE
    SYNTAX      SnmpAdminString
    MAX-ACCESS  read-only
    STATUS      current
    DESCRIPTION
        "Contains a message describing the error if the channel is
         down due to an error. If there are no error, the objects
         returns an empty string."
    ::= { chmgrOChannelEntry 3 }

chmgrOChanErrorAddress OBJECT-TYPE
    SYNTAX      DtmNode
    MAX-ACCESS  read-only
    STATUS      current
    DESCRIPTION
        "Contains the DTM address if the node that is reporting an
         error, described in chmgrOChanErrorMessage. If there are no
         error, the object returns the address
         00.00.00.00.00.00.00.00."
    ::= { chmgrOChannelEntry 4 }

chmgrOChanOperStatus OBJECT-TYPE
    SYNTAX      INTEGER {
                    up(1),
                    down(2) }
    MAX-ACCESS  read-only
    STATUS      current
    DESCRIPTION
        "The operational status of the channel. If the operational
         status of the connection is up, indicated in
         chmgrOConnOperStatus, a value of up(1) indicates that the
         channel is operational, and a value of down(2) indicates that
         the channel is not operational due to an error. The object
         chmgrOChanErrorMessage describes the problem.

         If the operational status of the connection is down, the
         value of the object is always down."
    ::= { chmgrOChannelEntry 5 }

chmgrOChanStatusChanged OBJECT-TYPE
    SYNTAX      TimeStamp
    MAX-ACCESS  read-only
    STATUS      current
    DESCRIPTION
        "The sysUpTime when the status of the channel to the
         destination was last established or torn down."
    ::= { chmgrOChannelEntry 6 }

chmgrOChanReestablish OBJECT-TYPE
    SYNTAX      INTEGER {
                    notApplicable(0),
                    reestablish(1) }
    MAX-ACCESS  read-write
    STATUS      current
    DESCRIPTION
        "Writing to this object re-establishes the channel to its
         destination without affecting other channels or destinations
         configured for this connection. The establishment of the
         channel will be done according to the current network
         topology and availability. If source routes are defined, the
         first source route will be tried first.

         notApplicable(0)
         Always reads this value. This value cannot be written.

         reestablish(1)
         Writing this value reestablishes the channel."
    ::= { chmgrOChannelEntry 7 }



-- End of Originating Channel Table


--
-- Terminating Connection Group
--

chmgrTConnectionTimeStamp OBJECT-TYPE
    SYNTAX      TimeStamp
    MAX-ACCESS  read-only
    STATUS      current
    DESCRIPTION
        "Time stamp, i.e. the value of sysUpTime when any for the
         tables in the group was last changed."
    ::= { chmgrTConnectionGroup 1 }

-- Terminating Connection Table

chmgrTConnectionTable OBJECT-TYPE
    SYNTAX      SEQUENCE OF ChmgrTConnectionEntry
    MAX-ACCESS  not-accessible
    STATUS      current
    DESCRIPTION
        "Table with termination connections. The table is managed by
         the applications that provide services transported on the
         connections."
    ::= { chmgrTConnectionGroup 2 }

chmgrTConnectionEntry OBJECT-TYPE
    SYNTAX      ChmgrTConnectionEntry
    MAX-ACCESS  not-accessible
    STATUS      current
    DESCRIPTION
        "An entry represents one connection."
    INDEX { chmgrTConnIndex }
    ::= { chmgrTConnectionTable 1 }

ChmgrTConnectionEntry ::= SEQUENCE {
    chmgrTConnIndex                  Unsigned32,
    chmgrTConnCustomerId             Unsigned32,
    chmgrTConnNumberOfChannels       Unsigned32,
    chmgrTConnActiveChannel          Unsigned32,
    chmgrTConnServiceReference       RowPointer,
    chmgrTConnAllocatedSlots         Gauge32,
    chmgrTConnAllocatedSlotsChanged  TimeStamp,
    chmgrTConnDcapType               DcapType,
    chmgrTConnDst                    Dst,
    chmgrTConnSourceDsti             Dsti,
    chmgrTConnSourceAddress          DtmNode,
    chmgrTConnDestinationDsti        Dsti,
    chmgrTConnDestinationAddress     DtmNode,
    chmgrTConnStatusLastChanged      TimeStamp,
    chmgrTConnAdminStatus            INTEGER,
    chmgrTConnOperStatus             INTEGER,
    chmgrTConnDcpVersion             DcpVersion
}

chmgrTConnIndex OBJECT-TYPE
    SYNTAX      Unsigned32
    MAX-ACCESS  not-accessible
    STATUS      current
    DESCRIPTION
        "Index for this entry."
    ::= { chmgrTConnectionEntry 1 }

chmgrTConnCustomerId OBJECT-TYPE
    SYNTAX      Unsigned32
    MAX-ACCESS  read-only
    STATUS      current
    DESCRIPTION
        "This is a customer identification number assigned by the
         application that is providing the service on the
         connection. The object has no functional use except to
         provide the information."
    ::= { chmgrTConnectionEntry 2 }

chmgrTConnNumberOfChannels OBJECT-TYPE
    SYNTAX      Unsigned32 (1..2)
    MAX-ACCESS  read-only
    STATUS      current
    DESCRIPTION
        "The number of channels this connection uses. A 1+1 protected
         connection uses two channels."
    ::= { chmgrTConnectionEntry 3 }

chmgrTConnActiveChannel OBJECT-TYPE
    SYNTAX      Unsigned32 (0..2)
    MAX-ACCESS  read-only
    STATUS      current
    DESCRIPTION
        "The channel that is currently active. This is the index of
         the channel in the chmgrTChannelTable. If there is no active
         channel for the connection, the value is zero (0)."
    ::= { chmgrTConnectionEntry 4 }

chmgrTConnServiceReference OBJECT-TYPE
    SYNTAX      RowPointer
    MAX-ACCESS  read-only
    STATUS      current
    DESCRIPTION
        "A reference to the service responsible for this connection.
         The object points to the instance of the service in the
         service's MIB. Its MIB shall have a table representing all
         the instances of the service."
    ::= { chmgrTConnectionEntry 5 }

chmgrTConnAllocatedSlots OBJECT-TYPE
    SYNTAX      Gauge32 (0..8389)
    MAX-ACCESS  read-only
    STATUS      current
    DESCRIPTION
        "The number of 512 kbps DTM slots that is allocated by the
         connection. Note that for a connection with multiple
         channels, e.g. 1+1 protected connection, all the channels
         have the same capacity.

         To know how much capacity that is used by the connection,
         multiply the value with the number of active channels. The
         channels are listed in chmgrTChannelTable."
    ::= { chmgrTConnectionEntry 6 }

chmgrTConnAllocatedSlotsChanged OBJECT-TYPE
    SYNTAX      TimeStamp
    MAX-ACCESS  read-only
    STATUS      current
    DESCRIPTION
        "The value of sysUpTime when the capacity for the connection
         was last changed."
    ::= { chmgrTConnectionEntry 7 }

chmgrTConnDcapType OBJECT-TYPE
    SYNTAX      DcapType
    MAX-ACCESS  read-only
    STATUS      current
    DESCRIPTION
        "The DCAP (DTM Channel Adaptation Protocol) type for the
        connection."
    ::= { chmgrTConnectionEntry 8 }

chmgrTConnDst OBJECT-TYPE
    SYNTAX      Dst
    MAX-ACCESS  read-only
    STATUS      current
    DESCRIPTION
        "The DST (DTM Service Type) of the service that uses the
         connection."
    ::= { chmgrTConnectionEntry 9 }

chmgrTConnSourceDsti OBJECT-TYPE
    SYNTAX      Dsti
    MAX-ACCESS  read-only
    STATUS      current
    DESCRIPTION
        "The DSTI (DTM Service Type Instance) of the service at the
         originating node of the connection."
    ::= { chmgrTConnectionEntry 10 }

chmgrTConnSourceAddress OBJECT-TYPE
    SYNTAX      DtmNode
    MAX-ACCESS  read-only
    STATUS      current
    DESCRIPTION
        "The DTM address of the connection's originating node."
    ::= { chmgrTConnectionEntry 11 }

chmgrTConnDestinationDsti OBJECT-TYPE
    SYNTAX      Dsti
    MAX-ACCESS  read-only
    STATUS      current
    DESCRIPTION
        "The DSTI (DTM Service Type Instance) of the service at the
         terminating node of the connection."
    ::= { chmgrTConnectionEntry 12 }

chmgrTConnDestinationAddress OBJECT-TYPE
    SYNTAX      DtmNode
    MAX-ACCESS  read-only
    STATUS      current
    DESCRIPTION
        "The DTM address of the connection's terminating node."
    ::= { chmgrTConnectionEntry 13 }

chmgrTConnStatusLastChanged OBJECT-TYPE
    SYNTAX      TimeStamp
    MAX-ACCESS  read-only
    STATUS      current
    DESCRIPTION
        "The value of sysUpTime when the operational status of the
         connection was last changed."
    ::= { chmgrTConnectionEntry 14 }

chmgrTConnAdminStatus OBJECT-TYPE
    SYNTAX      INTEGER {
                    up(1),
                    down(2) }
    MAX-ACCESS  read-only
    STATUS      current
    DESCRIPTION
        "The administrative state of the connection. The
         administrative state is controlled by the application that
         provides a service on the connection. It may be accessed in
         the service's MIB, where the instance is described by
         chmgrTConnServiceReference."
    ::= { chmgrTConnectionEntry 15 }

chmgrTConnOperStatus OBJECT-TYPE
    SYNTAX      INTEGER {
                    up(1),
                    down(2),
                    dormant(5) }
    MAX-ACCESS  read-only
    STATUS      current
    DESCRIPTION
        "The operational state of the connection. It should follow the
         administrative state described in chmgrTConnAdminStatus.

         up(1)
         A channel has been established.

         down(2)
         No channels are established, and the connection's
         administrative state is down.

         dormant(5)
         No channels have been established. The connection's
         administrative state is up and the connection is pending a
         terminating channel."
    ::= { chmgrTConnectionEntry 16 }

chmgrTConnDcpVersion OBJECT-TYPE
    SYNTAX      DcpVersion
    MAX-ACCESS  read-only
    STATUS      current
    DESCRIPTION
        "Version of DCP that is used for this connection. `any(0)'
         means that a channel is not established."
    ::= { chmgrTConnectionEntry 17 }


-- End of Terminating Connection Table


-- Terminating Channel Table

chmgrTChannelTable OBJECT-TYPE
    SYNTAX      SEQUENCE OF ChmgrTChannelEntry
    MAX-ACCESS  not-accessible
    STATUS      current
    DESCRIPTION
        "The channels that exists on a terminating connection.  The
         table is managed by the application that provides the service
         on the connection. A row is inserted when a new channel is
         established and is removed when a channel is torn down. For a
         1+1 protected connection, there are two channels in a
         connection."
    ::= { chmgrTConnectionGroup 3 }

chmgrTChannelEntry OBJECT-TYPE
    SYNTAX      ChmgrTChannelEntry
    MAX-ACCESS  not-accessible
    STATUS      current
    DESCRIPTION
        "An entry in the table represents a channel on a connection."
    INDEX { chmgrTConnIndex, chmgrTChanIndex }
    ::= { chmgrTChannelTable 1 }

ChmgrTChannelEntry ::= SEQUENCE {
    chmgrTChanIndex       Unsigned32,
    chmgrTChanChannelId   ChannelId,
    chmgrTChanCreated     TimeStamp
}

chmgrTChanIndex OBJECT-TYPE
    SYNTAX      Unsigned32 (1..2)
    MAX-ACCESS  not-accessible
    STATUS      current
    DESCRIPTION
        "The index for the channel within the connection. If a
         connection is 1+1 protected, is consists of two channels."
    ::= { chmgrTChannelEntry 1 }

chmgrTChanChannelId OBJECT-TYPE
    SYNTAX      ChannelId
    MAX-ACCESS  read-only
    STATUS      current
    DESCRIPTION
        "The identity of the DTM channel. If no channel is
         established, the value is zero (0)."
    ::= { chmgrTChannelEntry 2 }

chmgrTChanCreated OBJECT-TYPE
    SYNTAX      TimeStamp
    MAX-ACCESS  read-only
    STATUS      current
    DESCRIPTION
        "The sysUpTime when the channel was created."
    ::= { chmgrTChannelEntry 3 }

-- End of Termination Channel Table

--
--  Statistics Group
--

-- Originating Connection DCAP-1 Statistics Table

chmgrOStatDcap1Table OBJECT-TYPE
    SYNTAX      SEQUENCE OF ChmgrOStatDcap1Entry
    MAX-ACCESS  not-accessible
    STATUS      current
    DESCRIPTION
        "The table shows statistics for originating DCAP-1
         connections.  It uses the same index as the
         chmgrOConnectionTable. Note that all connections are not of
         the type DCAP-1, and are hence not represented in this
         table."
    ::= { chmgrStatisticsGroup 1 }

chmgrOStatDcap1Entry OBJECT-TYPE
    SYNTAX      ChmgrOStatDcap1Entry
    MAX-ACCESS  not-accessible
    STATUS      current
    DESCRIPTION
        "An entry represents statistics for one originating
         connection."
    INDEX { chmgrOConnIndex }
    ::= { chmgrOStatDcap1Table 1 }

ChmgrOStatDcap1Entry ::= SEQUENCE {
    chmgrOStatDcap1Octets           Counter32,
    chmgrOStatDcap1Packets          Counter32,
    chmgrOStatDcap1UtilizedBps      Gauge32,
    chmgrOStatDcap1DiscardOctets    Counter32,
    chmgrOStatDcap1DiscardPackets   Counter32,
    chmgrOStatDcap1Bitrate          Counter64,
    chmgrOStatDcap1Load             Unsigned32
}

chmgrOStatDcap1Octets OBJECT-TYPE
    SYNTAX      Counter32
    MAX-ACCESS  read-only
    STATUS      current
    DESCRIPTION
        "The total number of out-bound octets (bytes) on the
         connection."
    ::= { chmgrOStatDcap1Entry 1 }

chmgrOStatDcap1Packets OBJECT-TYPE
    SYNTAX      Counter32
    MAX-ACCESS  read-only
    STATUS      current
    DESCRIPTION
        "The total number of out-bound packets on the connection."
    ::= { chmgrOStatDcap1Entry 2 }

chmgrOStatDcap1UtilizedBps OBJECT-TYPE
    SYNTAX      Gauge32
    MAX-ACCESS  read-only
    STATUS      current
    DESCRIPTION
        "The utilization in bits per second on the connection as mean
         value during the last 30 seconds"
    ::= { chmgrOStatDcap1Entry 3 }

chmgrOStatDcap1DiscardOctets OBJECT-TYPE
    SYNTAX      Counter32
    MAX-ACCESS  read-only
    STATUS      current
    DESCRIPTION
        "The number of out-bound octets which were chosen to be
         discarded even though no errors had been detected to prevent
         their being transmitted. One possible reason for discarding
         such a packet could be to free up buffer space."
    ::= { chmgrOStatDcap1Entry 4 }

chmgrOStatDcap1DiscardPackets OBJECT-TYPE
    SYNTAX      Counter32
    MAX-ACCESS  read-only
    STATUS      current
    DESCRIPTION
        "The number of out-bound packets which were chosen to be
         discarded even though no errors had been detected to prevent
         their being transmitted. One possible reason for discarding
         such a packet could be to free up buffer space."
    ::= { chmgrOStatDcap1Entry 5 }

chmgrOStatDcap1Bitrate OBJECT-TYPE
    SYNTAX      Counter64
    MAX-ACCESS  read-only
    STATUS      current
    DESCRIPTION
        "The utilization in bits per second on the connection as mean
         value measured during the last 30 seconds. This value is a
         64-bit equivalent to chmgrOStatDcap1UtilizedBps."
    ::= { chmgrOStatDcap1Entry 6 }

chmgrOStatDcap1Load OBJECT-TYPE
    SYNTAX      Unsigned32 (0..100)
    MAX-ACCESS  read-only
    STATUS      current
    DESCRIPTION
        "The utilization (load) in percent on the connection as mean
         value measured during the last 30 seconds."
    ::= { chmgrOStatDcap1Entry 7 }

-- End of Originating Connection DCAP-1 Statistics Table


-- Terminating Connection DCAP-1 Statistics Table

chmgrTStatDcap1Table OBJECT-TYPE
    SYNTAX      SEQUENCE OF ChmgrTStatDcap1Entry
    MAX-ACCESS  not-accessible
    STATUS      current
    DESCRIPTION
        "The table shows statistics for terminating DCAP-1
         connections.  It uses the same index as the
         chmgrTConnectionTable. Note that all connections are not of
         the type DCAP-1, and are hence not represented in this
         table."
    ::= { chmgrStatisticsGroup 2 }

chmgrTStatDcap1Entry OBJECT-TYPE
    SYNTAX      ChmgrTStatDcap1Entry
    MAX-ACCESS  not-accessible
    STATUS      current
    DESCRIPTION
        "An entry representing statistics for one terminating
         connection."
    INDEX { chmgrTConnIndex }
    ::= { chmgrTStatDcap1Table 1 }

ChmgrTStatDcap1Entry ::= SEQUENCE {
    chmgrTStatDcap1Octets            Counter32,
    chmgrTStatDcap1Packets           Counter32,
    chmgrTStatDcap1UtilizedBps       Gauge32,
    chmgrTStatDcap1DiscardOctets     Counter32,
    chmgrTStatDcap1DiscardPackets    Counter32,
    chmgrTStatDcap1ErrorCRC          Counter32,
    chmgrTStatDcap1ErrorLods         Counter32,
    chmgrTStatDcap1Bitrate          Counter64,
    chmgrTStatDcap1Load             Unsigned32
}

chmgrTStatDcap1Octets OBJECT-TYPE
    SYNTAX      Counter32
    MAX-ACCESS  read-only
    STATUS      current
    DESCRIPTION
        "The total number of in-bound octets (bytes) on the
         connection."
    ::= { chmgrTStatDcap1Entry 1 }

chmgrTStatDcap1Packets OBJECT-TYPE
    SYNTAX      Counter32
    MAX-ACCESS  read-only
    STATUS      current
    DESCRIPTION
        "The total number of in-bound packets on the connection."
    ::= { chmgrTStatDcap1Entry 2 }

chmgrTStatDcap1UtilizedBps OBJECT-TYPE
    SYNTAX      Gauge32
    MAX-ACCESS  read-only
    STATUS      current
    DESCRIPTION
        "The utilization in bits per second on the connection as a
         mean value during the last 30 seconds."
    ::= { chmgrTStatDcap1Entry 3 }

chmgrTStatDcap1DiscardOctets OBJECT-TYPE
    SYNTAX      Counter32
    MAX-ACCESS  read-only
    STATUS      current
    DESCRIPTION
        "The number of in-bound octets which were chosen to be
         discarded even though no errors had been detected to prevent
         their being transmitted. One possible reason for discarding
         such a packet could be to free up buffer space."
    ::= { chmgrTStatDcap1Entry 4 }

chmgrTStatDcap1DiscardPackets OBJECT-TYPE
    SYNTAX      Counter32
    MAX-ACCESS  read-only
    STATUS      current
    DESCRIPTION
        "The number of in-bound packets which were chosen to be
         discarded even though no errors had been detected to prevent
         their being transmitted. One possible reason for discarding
         such a packet could be to free up buffer space."
    ::= { chmgrTStatDcap1Entry 5 }

chmgrTStatDcap1ErrorCRC OBJECT-TYPE
    SYNTAX      Counter32
    MAX-ACCESS  read-only
    STATUS      current
    DESCRIPTION
        "The number of CRC32 errors detected on in-bound packets for
         the connection."
    ::= { chmgrTStatDcap1Entry 6 }

chmgrTStatDcap1ErrorLods OBJECT-TYPE
    SYNTAX      Counter32
    MAX-ACCESS  read-only
    STATUS      current
    DESCRIPTION
        "The number of LODS errors detected on in-bound data."
    ::= { chmgrTStatDcap1Entry 7 }

chmgrTStatDcap1Bitrate OBJECT-TYPE
    SYNTAX      Counter64
    MAX-ACCESS  read-only
    STATUS      current
    DESCRIPTION
        "The utilization in bits per second on the connection as mean
         value measured during the last 30 seconds. This value is a
         64-bit equivalent to chmgrTStatDcap1UtilizedBps."
    ::= { chmgrTStatDcap1Entry 8 }

chmgrTStatDcap1Load OBJECT-TYPE
    SYNTAX      Unsigned32 (0..100)
    MAX-ACCESS  read-only
    STATUS      current
    DESCRIPTION
        "The utilization (load) in percent on the connection as mean
         value measured during the last 30 seconds."
    ::= { chmgrTStatDcap1Entry 9 }

-- End of Terminating Connection DCAP-1 Statistics Table

-- Terminating Performance Monitoring Data Reference Table

chmgrTStatPMReferenceTable OBJECT-TYPE
    SYNTAX      SEQUENCE OF ChmgrTStatPMReferenceEntry
    MAX-ACCESS  not-accessible
    STATUS      deprecated
    DESCRIPTION
        "Table with reference to Performance Monitoring Data for the
         connections. It uses the same index as the
         chmgrOConnectionTable. Note that all connections are not
         represented in this table."
    ::= { chmgrStatisticsGroup 3 }

chmgrTStatPMReferenceEntry OBJECT-TYPE
    SYNTAX      ChmgrTStatPMReferenceEntry
    MAX-ACCESS  not-accessible
    STATUS      deprecated
    DESCRIPTION
        "An entry in the table."
    INDEX { chmgrTConnIndex }
    ::= { chmgrTStatPMReferenceTable 1 }

ChmgrTStatPMReferenceEntry ::= SEQUENCE {
    chmgrTStatPMReference   RowPointer
}

chmgrTStatPMReference OBJECT-TYPE
    SYNTAX      RowPointer
    MAX-ACCESS  read-only
    STATUS      deprecated
    DESCRIPTION
        "A reference to a row in a table that shows performance data
         for the connection. The table is not part of this MIB."
    ::= { chmgrTStatPMReferenceEntry 1 }

-- End of Terminating Performance Monitoring Data Reference Table

-- Channel Table

chmgrChannelTable OBJECT-TYPE
    SYNTAX      SEQUENCE OF ChmgrChannelEntry
    MAX-ACCESS  not-accessible
    STATUS      current
    DESCRIPTION
        "Table with all channels, that is originating, transiting or
         terminating channels."
    ::= { chmgrChannelGroup 1 }

chmgrChannelEntry OBJECT-TYPE
    SYNTAX      ChmgrChannelEntry
    MAX-ACCESS  not-accessible
    STATUS      current
    DESCRIPTION
        "An entry represents one branch of the channel. There table
         has on entry for each channel branch that is transiting and
         terminating in the node."
    INDEX { chmgrChanSourceMacAddress, chmgrChanChannelId, chmgrChanOutgoingIfBoard, chmgrChanOutgoingIfPort }
    ::= { chmgrChannelTable 1 }

ChmgrChannelEntry ::= SEQUENCE {
    chmgrChanSourceMacAddress       MacAddress,
    chmgrChanChannelId              ChannelId,
    chmgrChanOutgoingIfBoard        Unsigned32,
    chmgrChanOutgoingIfPort         Unsigned32,
    chmgrChanOutgoingIfMacAddress   MacAddress,
    chmgrChanNextHopMacAddress      MacAddress,
    chmgrChanNextHopDtmAddress      DtmAddress,
    chmgrChanIncomingIfBoard        Unsigned32,
    chmgrChanIncomingIfPort         Unsigned32,
    chmgrChanSourceDtmAddress       DtmAddress,
    chmgrChanDst                    Dst,
    chmgrChanSourceDsti             Dsti,
    chmgrChanIsMulticast            TruthValue,
    chmgrChanCapacity               Unsigned32,
    chmgrChanDestDsti               Dsti
}

chmgrChanSourceMacAddress OBJECT-TYPE
    SYNTAX      MacAddress
    MAX-ACCESS  not-accessible
    STATUS      current
    DESCRIPTION
        "The MAC address of the node where the channel originates."
    ::= { chmgrChannelEntry 1 }

chmgrChanChannelId OBJECT-TYPE
    SYNTAX      ChannelId
    MAX-ACCESS  not-accessible
    STATUS      current
    DESCRIPTION
        "The identity of the DTM channel."
    ::= { chmgrChannelEntry 2 }

chmgrChanOutgoingIfBoard OBJECT-TYPE
    SYNTAX      Unsigned32
    MAX-ACCESS  not-accessible
    STATUS      current
    DESCRIPTION
        "The identity of the board where the DTM interface is located
         on which this branch of the channel leaves this node. If the
         channel branch does not leave this node, then the value is 0."
    ::= { chmgrChannelEntry 3 }

chmgrChanOutgoingIfPort OBJECT-TYPE
    SYNTAX      Unsigned32
    MAX-ACCESS  not-accessible
    STATUS      current
    DESCRIPTION
        "The identity of the port on the board specified in
         chmgrChanOutgoingIfBoard for the DTM interface, on which this
         branch of the channel leaves the this node. If the channel
         branch does not leave this node, then the value is the same
         as the value of chmgrChanDestDsti."
    ::= { chmgrChannelEntry 4 }

chmgrChanOutgoingIfMacAddress OBJECT-TYPE
    SYNTAX      MacAddress
    MAX-ACCESS  read-only
    STATUS      current
    DESCRIPTION
        "The MAC address of the DTM interface on which this branch of
         the channel leaves this node."
    ::= { chmgrChannelEntry 5 }

chmgrChanNextHopMacAddress OBJECT-TYPE
    SYNTAX      MacAddress
    MAX-ACCESS  read-only
    STATUS      current
    DESCRIPTION
        "The MAC address for the next-hop DTM node."
    ::= { chmgrChannelEntry 6 }

chmgrChanNextHopDtmAddress OBJECT-TYPE
    SYNTAX      DtmAddress
    MAX-ACCESS  read-only
    STATUS      current
    DESCRIPTION
        "The DTM address for the next-hop DTM node."
    ::= { chmgrChannelEntry 7 }

chmgrChanIncomingIfBoard OBJECT-TYPE
    SYNTAX      Unsigned32
    MAX-ACCESS  read-only
    STATUS      current
    DESCRIPTION
        "The identity of the board where the DTM interface is located
         on which this channel is entering this node. If the channel
         originates in this node, then the value is 0."
    ::= { chmgrChannelEntry 8 }

chmgrChanIncomingIfPort OBJECT-TYPE
    SYNTAX      Unsigned32
    MAX-ACCESS  read-only
    STATUS      current
    DESCRIPTION
        "The identity of the port on the board specified in
         chmgrChanIncomingIfBoard for the DTM interface, on which this
         channels is entering this node. If the channel originates in
         this node, then the value is 0."
    ::= { chmgrChannelEntry 9 }

chmgrChanSourceDtmAddress OBJECT-TYPE
    SYNTAX      DtmAddress
    MAX-ACCESS  read-only
    STATUS      current
    DESCRIPTION
        "The DTM address of the node where the channel originates."
    ::= { chmgrChannelEntry 10 }

chmgrChanDst OBJECT-TYPE
    SYNTAX      Dst
    MAX-ACCESS  read-only
    STATUS      current
    DESCRIPTION
        "The DST (DTM Service Type) of the service that uses the
         channel."
  ::= { chmgrChannelEntry 11 }

chmgrChanSourceDsti OBJECT-TYPE
    SYNTAX      Dsti
    MAX-ACCESS  read-only
    STATUS      current
    DESCRIPTION
        "The DSTI (DTM Service Type Instance) of the service at the
         originating node of the channel."
    ::= { chmgrChannelEntry 12 }

chmgrChanIsMulticast OBJECT-TYPE
    SYNTAX      TruthValue
    MAX-ACCESS  read-only
    STATUS      current
    DESCRIPTION
        "Describes if the channel is a multicast or unicast type.

         true(1)
         The channel is a multicast channel.

         false(2)
         The channel is a unicast channel.
        "
    ::= { chmgrChannelEntry 13 }

chmgrChanCapacity OBJECT-TYPE
    SYNTAX      Unsigned32
    MAX-ACCESS  read-only
    STATUS      current
    DESCRIPTION
        "The capacity of the channel in 512 kbps slots."
    ::= { chmgrChannelEntry 14 }

chmgrChanDestDsti OBJECT-TYPE
    SYNTAX      Dsti
    MAX-ACCESS  read-only
    STATUS      current
    DESCRIPTION
        "The DSTI (DTM Service Type Instance) of the terminating part
         of the service. This value is only valid for an entry
         describing a channel branch that is terminating on the
         node. Its value is 0 for an entry describing a channel
         branch that is continuing to another node."
    ::= { chmgrChannelEntry 15 }

-- End of Channel table

END
