NETI-ITS-MIB DEFINITIONS ::= BEGIN

IMPORTS
    MODULE-IDENTITY, OBJECT-TYPE, Integer32, Unsigned32, Gauge32
        FROM SNMPv2-SMI

    RowPointer, RowStatus, TimeStamp, TruthValue, TEXTUAL-CONVENTION
        FROM SNMPv2-TC

    SnmpAdminString
        FROM SNMP-FRAMEWORK-MIB

    netiExperimentalGeneric
        FROM NETI-COMMON-MIB

    Dsti
        FROM NETI-CHMGR-MIB;


netiItsMIB MODULE-IDENTITY
    LAST-UPDATED
        "201409111300Z"
    ORGANIZATION
        "Net Insight AB"
    CONTACT-INFO
        "Net Insight AB
         Box 42093
         SE-126 14 Stockholm
         Sweden
         Tel +46-8-685 0400
         info@netinsight.se"
   DESCRIPTION
        "Reference: NID757.

         MIB for Isochronous Transport Services (ITS).  ITS provides
         transport of isochronous (time sensitive) traffic across the
         DTM network in a transparent way.  All the bits are
         transported unmodified with preserved timing information.
         The following services are all regarded as ITS:

         - PDH primary rates

         - Video (DVB/SD-SDI/HD-SDI)

         - Audio (AES-EBU)

         - SDH transport

         The MIB includes three primary conceptual tables; for
         configuring the trail termination points on the originating
         (source) and terminating (sink) side of the connection, and
         for configuring the interfaces.

         The table itsSrcTtpTable defines the trail termination points
         for the originating (source) side.

         The table itsSnkTtpTable defines the trail termination points
         for the terminating (sink) side.

         The table itsIfTable defines the interfaces.  In addition to
         the itsIfTable, there are dedicated tables for technology
         specific configuration objects.

         The interconnection between the trail termination points
         shall be done through configuration in the Channel Manager
         MIB (NETI-CHMGR-MIB).

         A bi-directional connections are handled by creating two
         uni-directional connections, one in each direction, between
         the trail termination points."

    REVISION
        "201409111300Z"
    DESCRIPTION
        "- Added object for setting maximum expected differential delay
           on 1+1 protected transport, itsIfPs3MaxExpDifferentialDelay.

         - Added setting to freeze output: freeze(3) to object
           itsIfTxMuteOnFault."

    REVISION
        "201402211500Z"
    DESCRIPTION
        "- Objects for managing SDI timing delay has been changed:
           itsIfSdiFsVDelay and itsIfSdiFsHDelay have been obsoleted,
           and are replaced with itsIfSdiFsDealy.

         - Added object for controlling audio transport on JPEG 2000
           enabled interface, itsIfJ2kReduceAudioTransportBitrate."

    REVISION
        "201309300700Z"
    DESCRIPTION
        "- Added objects for managing SDI timing providers:
           itsIfSdiIsTimingProvider, itsIfSdiFsVDelay and
           itsIfSdiFsHDelay. Also added bits to itsIfCapabilities:
           fs(15), avrs(16), dvrs(25).

         - Updated itsIfJ2kSignalFormat. Renamed sdSdiPAL(1) to
           sdSdi(1), and removed sdSdiNTSC(2). There is no
           differentiation between PAL and NTSC."

    REVISION
        "201212031100Z"
    DESCRIPTION
        "- Added references from interface to TTPs, itsIfMembersSrc,
           itsIfMembersSnk.
         - Added objects for protection type 3 and hitless protection,
           itsIfPs3Table."

    REVISION
        "201209041400Z"
    DESCRIPTION
        "- Added table for SDI interfaces, itsIfSdiTable. This table
           contains objects for controlling autosense and presenting
           video format.
         - Corrected VBI index range to 1..46, itsIfSdiVbiIndex."

    REVISION
        "201201201600Z"
    DESCRIPTION
        "Clarified some object descriptions and the relation to JPEG 2000."

    REVISION
        "201112010900Z"
    DESCRIPTION
        "- Added new JPEG 2000 signal formats to itsIfJ2kSignalFormat.
         - Added objects for presenting VBI, ANC and audio rate on
           JPEG 2000 capable interfaces, itsIfJ2kRateVBI,
           itsIfJ2kRateAnc, itsIfJ2kRateAudio.
         - Added audio sample size to JPEG 2000 capable interfaces,
           itsIfJ2kAudioSampleSize.
         - Added table for VBI lines for SDI interfaces,
           itsIfSdiVbiTable.
         - Added table for ANC data for SDI interfaces,
           itsIfSdiAncTable."

    REVISION
        "201110101300Z"
    DESCRIPTION
        "Extended support for JPEG 2000 interfaces, added:
         - Added object to set signal format, itsIfJ2kSignalFormat.
         - Added objects for presentation of video rate,
           itsIfJ2kRateVideo, itsIfJ2kRateVideoMax.
         - Added table to configure audio groups, itsIfSdiAudioTable."

    REVISION
        "201104270900Z"
    DESCRIPTION
        "This version of the MIB contains functionality that has not
         yet been incorporated into the MAIN branch of NimOS.

         This version of the MIB is a merge of:
         - JPEG 2000 functionality
         - AES (MADI) functionality."

    REVISION
        "201104270800Z"
    DESCRIPTION
        "Added basic support for JPEG 2000:
         - Added table for JPEG 2000 interfaces, itsIfJ2kTable.
         - Added j2kEnc(21) and j2kDec(22) to itsIfCapabilities."

    REVISION
        "201102041200Z"
    DESCRIPTION
        "Added table for AES interfaces, itsIfAesTable.

         Added madi(19) and ref(20) to itsIfCapabilities."

    REVISION
        "201102030900Z"
    DESCRIPTION
        "The itsIfLoopTime is deprecated."

    REVISION
        "201008190900Z"
    DESCRIPTION
        "Added object itsSnkTtpPSAllow to itsSnkTtpTable.

         Removed default value for object itsIfProperites."

    REVISION
        "201001190900Z"
    DESCRIPTION
        "Added object itsIfInterfaceType to itsIfTable.

         Added table itsIfPdhTable dedicated for PDH interface
         related configuration objects.

         Added table itsIfMonTable dedicated for monitor interface
         related configuration objects.

         Added table itsIfSdhTable dedicated for SDH interface related
         configuration objects.

         Added table itsIfDvbTable dedicated for DVB interface related
         configuration objects."

    REVISION
        "200901221500Z"
    DESCRIPTION
        "Added sdi2967(13) and sdi2970(14) to itsIfCapabilities.
         Updated some descriptions.

         Changed labels to sdi1483, sdi1485, sdi288 and sdi270 in
         itsIfCapabilities to conform to SMIv2 (RFC2578).

         Added itsSnkTtpTConnection2 for support of 1+1 protection
         where two connections from two different trail termination
         points (TTPs) are used, as opposed to two channels in the
         same connection from a single TTP."

    REVISION
        "200804171030Z"
    DESCRIPTION
        "Added ttp(5), loopl(7), loopd(8), sdi-1483(9), sdi-1485(10),
         sdi-288(11) and sdi-270(12) to itsIfCapabilities."

    REVISION
        "200801181500Z"
    DESCRIPTION
        "Added tables to lookup index for a TTP based on the DSTI:
         itsSrcIndexLookupTable and itsSnkIndexLookupTable."

    REVISION
        "200712041600Z"
    DESCRIPTION
        "Added itsIfPurpose."

    REVISION
        "200706291400Z"
    DESCRIPTION
        "Changed label ais(2) to warning(2) for itsIfSuppressAlarm
         and itsSnkTtpSuppressAlarm.
         Added interfacePM(4) to itsIfCapabilities.
         Added lod(4), rdi(5), lol(6) to itsIfDefects.
         Added columnar object itsIfTxMuteOnFault.
         Added notSupported(0) to itsIfLoopMode, itsIfSuppressAlarm
         and itsSnkTtpSuppressAlarm.
         Importing Gauge32.
         Corrected typos."
    ::= { netiExperimentalGeneric 16 }


ItsTtpIndexList ::= TEXTUAL-CONVENTION
    STATUS  current
    DESCRIPTION
        "A list of Integer32 values, where each 4 octets
         represents one Integer32 value.  Each value represents
         an index into a table."
    SYNTAX   OCTET STRING (SIZE(0|4|8))


ItsProtectionStatus ::= TEXTUAL-CONVENTION
     STATUS  current
     DESCRIPTION
         "Describes the protection status of a protected service.

          unavailable(1).  means that neither channel is up.

          unprotected(2).  means that one of the channels is up.

          standbyProtected(3).  means that both channels are up and if
          the active channel detects AIS, a failover will occur while
          incurring a hit.

          hitlessCapable(4).  means that the differential delay is
          within limit, but a buffer reset is required to reach
          hitless protected state. This can be achieved by writing the
          forceHit parameter.

          hitlessProtected(5).  means that either channel can go down
          without incurring a data loss."

     SYNTAX  INTEGER {
                 unavailable(1),
                 unprotected(2),
                 standbyProtected(3),
                 hitlessCapable(4),
                 hitlessProtected(5) }



--
-- Objects in the NETI-ITS-MIB
--

itsObjects OBJECT IDENTIFIER ::= { netiItsMIB 1 }


--
-- Groups in the NETI-ITS-MIB
--


itsIfGroup     OBJECT IDENTIFIER ::= { itsObjects 1 }
itsSourceGroup OBJECT IDENTIFIER ::= { itsObjects 2 }
itsSinkGroup   OBJECT IDENTIFIER ::= { itsObjects 3 }


--
-- The ITS interface group
--

itsIfLastChange OBJECT-TYPE
    SYNTAX      TimeStamp
    MAX-ACCESS  read-only
    STATUS      current
    DESCRIPTION
        "The value of sysUpTime of the last change of any object in
         the itsIfTable."
    ::= { itsIfGroup 1 }


-- Table with all interfaces

itsIfTable OBJECT-TYPE
    SYNTAX      SEQUENCE OF ItsIfEntry
    MAX-ACCESS  not-accessible
    STATUS      current
    DESCRIPTION
        "Table with all service interfaces that is detected by the
         device.  The table contains configuration objects common to
         all types of interfaces."
    ::= { itsIfGroup 2 }

itsIfEntry OBJECT-TYPE
    SYNTAX      ItsIfEntry
    MAX-ACCESS  not-accessible
    STATUS      current
    DESCRIPTION
        "One interface is represented by one conceptual row in the table.
         Rx and Tx is always relative the application domain."
    INDEX { itsIfIndex }
    ::= { itsIfTable 1 }

ItsIfEntry ::= SEQUENCE {
    itsIfIndex            Unsigned32,
    itsIfIfIndex          Integer32,         -- same as ifIndex
    itsIfName             SnmpAdminString,   -- same as ifName
    itsIfDescr            SnmpAdminString,   -- same as ifDescr
    itsIfSpeed            Gauge32,           -- same as ifSpeed
    itsIfSuppressAlarm    INTEGER,
    itsIfLoopMode         INTEGER,
    itsIfLoopTime         Gauge32,           -- deprecated
    itsIfCapabilities     BITS,
    itsIfProperties       BITS,
    itsIfDefects          BITS,
    itsIfFailure          SnmpAdminString,
    itsIfPMReference      RowPointer,
    itsIfOperStatus       INTEGER,           -- same as ifOperStatus
    itsIfTxMuteOnFault    INTEGER,
    itsIfPurpose          SnmpAdminString,
    itsIfInterfaceType    INTEGER,
    itsIfMembersSrc       ItsTtpIndexList,
    itsIfMembersSnk       ItsTtpIndexList
}

itsIfIndex OBJECT-TYPE
    SYNTAX      Unsigned32
    MAX-ACCESS  not-accessible
    STATUS      current
    DESCRIPTION
        "The index in the table. The index is maintained across
         re-boots. The index is a positive integer value."
    ::= { itsIfEntry 1 }

itsIfIfIndex OBJECT-TYPE
    SYNTAX      Integer32
    MAX-ACCESS  read-only
    STATUS      current
    DESCRIPTION
        "A reference to the index in the ifTable in the IF-MIB. If
         this is not known, the value is 0."
    ::= { itsIfEntry 2 }

itsIfName OBJECT-TYPE
    SYNTAX      SnmpAdminString
    MAX-ACCESS  read-only
    STATUS      current
    DESCRIPTION
        "The textual name of the interface. The value of this object
         should be the name of the interface as assigned by the local
         device and should be suitable for use in commands entered at
         the device's console. This might be a text name, such as
         `e1-1:1' or a simple port number. This name would be the same
         as presented by the object ifName in the ifXTable."
    ::= { itsIfEntry 3 }

itsIfDescr OBJECT-TYPE
    SYNTAX      SnmpAdminString
    MAX-ACCESS  read-only
    STATUS      current
    DESCRIPTION
        "A textual string containing information about the interface.
         This string should include the name of the manufacturer, the
         product name and the version of the interface
         hardware/software. This description would be the same as
         presented by the object ifDescr in the ifTable."
    ::= { itsIfEntry 4 }

itsIfSpeed OBJECT-TYPE
    SYNTAX      Gauge32
    MAX-ACCESS  read-only
    STATUS      current
    DESCRIPTION
        "The interface's capacity in bits per second. This value would
         be the same as presented by the object ifSpeed in the
         ifTable."
    ::= { itsIfEntry 5 }

itsIfSuppressAlarm OBJECT-TYPE
    SYNTAX      INTEGER {
                    notSupported(0),
                    none(1),
                    warning(2),
                    all(3) }
    MAX-ACCESS  read-write
    STATUS      current
    DESCRIPTION
        "The alarm suppression mode. When alarms are suppressed, no
         alarms will be generated if a fault situation is detected on
         the interface. Failures will still be shown by the object
         itsIfFailure.

         notSupported(0). Suppress alarms is not supported by the
         interface. This value can not be written.

         none(1). No alarms are suppressed. All alarms are reported.

         warning(2). Suppress alarms of severity warning only.

         all(3). All alarms are suppressed. No alarms will be
         reported."
    DEFVAL { none }
    ::= { itsIfEntry 6 }

itsIfLoopMode OBJECT-TYPE
    SYNTAX      INTEGER {
                    notSupported(0),
                    none(1),
                    line(2),
                    dtm(3) }
    MAX-ACCESS  read-write
    STATUS      current
    DESCRIPTION
        "Loop-back mode of the interface. When the loop-back mode is
         changed to line(2) or dtm(3), a timer is initialized with the
         value of itsIfLoopTime. The loop-back mode is reset to
         none(1) when the timer runs out.

         notSupported(0). Loopback is not supported by the
         interface. This value can not be written.

         none(1). The interface is not in loop-back mode. This is the
         normal operation of the interface.

         line(2). The interface is in loop-back mode on the line
         side. Everything that is received on the Rx line interface is
         looped back to the Tx line interface, and is also transmitted
         to the remote node. Data received from the remote node is
         ignored.

         dtm(3). The interface is in loop-back mode on the DTM link
         side. Everything that is received from the remote node is
         looped back to the remote node, and is also output on the Tx
         line interface. Data received on the Rx line interface is
         ignored."
    DEFVAL { none }
    ::= { itsIfEntry 7 }

itsIfLoopTime  OBJECT-TYPE
    SYNTAX      Gauge32 (0..65535)
    MAX-ACCESS  read-write
    STATUS      deprecated
    DESCRIPTION
        "Timer for the loop-back mode. The loop-back mode is reset to
         its normal mode none(0) after the specified number of
         seconds. A timer value of 0 indicates infinite time, which
         means that the interface stays in loop-back mode until it is
         specifically changed.

         If the value of itsIfLoopTime is set while an interface is in
         loop-back mode, the interface's timer will be reinitialized
         with the new value."
    DEFVAL { 0 }
    ::= { itsIfEntry 8 }

itsIfCapabilities OBJECT-TYPE
    SYNTAX      BITS {
                    multicast(0),
                    allowProtection(1),
                    requireCapacity(2),
                    channelPM(3),
                    interfacePM(4),
                    ttp(5),
                    mon(6),
                    loopl(7),
                    loopd(8),
                    sdi1483(9),
                    sdi1485(10),
                    sdi288(11),
                    sdi270(12),
                    sdi2967(13),
                    sdi2970(14),
                    fs(15),
                    avrs(16),
                    madi(19),
                    ref(20),
                    j2kEnc(21),
                    j2kDec(22),
                    hitps(23),
                    psType3(24),
                    dvrs(25),
                    compatible(31) }
    MAX-ACCESS  read-only
    STATUS      current
    DESCRIPTION
        "Capabilities of the interface. The corresponding bit is set if
         the capability is supported by the interface.

         multicast(0). It is possible to use in multicast connection.

         allowProtection(1). 1+1 protection on originating and
         terminating side is supported.

         requireCapacity(2). Management and setting of the connection
         capacity is required. This is the case for e.g. an DVB
         interface where the capacity may be set between 0.5 Mbps and
         212.5 Mbps, but not for e.g. an SDI interface where the
         capacity is fixed at 270 Mbps.

         channelPM(3). Performance monitoring on the connection that
         terminates on the TTP that uses the interface is supported.

         interfacePM(4). Performance monitoring on the data received
         on the interface is supported.

         ttp(5). Allowed to be bound to a TTP.

         mon(6). Monitoring port support.

         loopl(7). Interface supports line loop-back. See itsIfLoopMode.

         loopd(8). Interface supports DTM loop-back. See itsIfLoopMode.

         sdi1483(9). Interface supports HD-SDI 1.485/1.001 Gbps.

         sdi1485(10). Interface supports HD-SDI 1.485 Gbps.

         sdi288(11). Interface supports 270 Mbps SD-SDI using a 288
         Mbps channel.

         sdi270(12). Interface supports 270 Mbps SD-SDI using a 270
         Mbps channel.

         sdi2967(13). Interface supports HD-SDI 2.970/1.001 Gbps.

         sdi2970(14). Interface supports HD-SDI 2.970 Gbps.

         fs(15).  Interface supports frame synchronization.

         avrs(16).  Interface supports analog video reference signal.

         madi(19). Interface supports MADI - AES10.

         ref(20). Interface supports interface locking.

         j2kEnc(21). Interface supports JPEG 2000 encoding.

         j2kDec(22). Interface supports JPEG 2000 decoding.

         hitps(23). Interface supports hitless 1+1 protection.

         psType3(24). Interface supports protection model where two
         sink trail termination points (TTP) per destination is used.

         dvrs(25).  Interface supports digital video reference signal.

         compatible(31). The interface is compatible with older
         systems, and is able to function in a connection where the
         remote node is of older system release."
    ::= { itsIfEntry 9 }

itsIfProperties OBJECT-TYPE
    SYNTAX      BITS {
                    tbd(0) }
    MAX-ACCESS  read-write
    STATUS      current
    DESCRIPTION
        "Properties on the interface.  A property can only be set if
         the interface supports has the corresponding capability.  The
         capabilities of the interface can be determined by examine
         itsIfCapabilities.

         Currently, no properties are supported.  The object exists
         for support of future interfaces where configuration of the
         interface properties are necessary."
    ::= { itsIfEntry 10 }

itsIfDefects OBJECT-TYPE
    SYNTAX      BITS {
                    los(0),
                    lof(1),
                    ais(2),
                    lop(3),
                    lod(4),
                    rdi(5),
                    lol(6)}
    MAX-ACCESS  read-only
    STATUS      current
    DESCRIPTION
        "Defects indicated on the interface since the last time the
         object was read.

         los(0) Loss of Signal was detected.

         lof(1) Loss of Frame was detected.

         ais(2). Alarm Indication Signal was received from up-stream
         node.

         lop(3). Loss of Pointer was detected. This happens on DVB
         when the connection does not have enough capacity.

         lod(4). Loss of Data (congestion) was detected.

         rdi(5). Remote Defect Indication was detected.

         lol(6). Loss of Lock (frequency outside range) was detected."

    ::= { itsIfEntry 11 }

itsIfFailure OBJECT-TYPE
    SYNTAX      SnmpAdminString
    MAX-ACCESS  read-only
    STATUS      current
    DESCRIPTION
        "A textual string describing a fault status on the
         interface. The object presents an empty string if there are
         no faults on the interface."
    ::= { itsIfEntry 12 }

itsIfPMReference OBJECT-TYPE
    SYNTAX      RowPointer
    MAX-ACCESS  read-only
    STATUS      current
    DESCRIPTION
        "A reference to an object that presents performance data
         for the interface. The object is not part of this MIB."
    ::= { itsIfEntry 13 }

itsIfOperStatus OBJECT-TYPE
    SYNTAX      INTEGER {
                    up(1),
                    down(2),
                    unknown(4),
                    dormant(5),
                    notPresent(6) }
    MAX-ACCESS  read-only
    STATUS      current
    DESCRIPTION
        "The operational state of the interface. This is the same as
         the object ifOperStatus in the ifTable.

         up(1). The interface passes data and is used by a TTP.

         down(2). The interface is down. If the administrative state
         is up, the operational state is down only if there is a fault
         situation that prevents the interface from not being down.

         unknown(4). The state of the interface is unknown, possibly
         due to some internal error.

         dormant(5). The interface is ready, but is not used by any
         TTP.

         notPresent(6). The interface is not present.  If a physical
         port is represented by multiple interfaces (e.g. different
         interfaces for DVB, SDI or monitoring), then if one of the
         interfaces at a port is `up(1)', then the remaining
         interfaces at the same port are unavailable for use and gets
         operational state `notPresent(6)'"
    ::= { itsIfEntry 14 }

itsIfTxMuteOnFault OBJECT-TYPE
    SYNTAX      INTEGER {
                    notSupported(0),
                    enable(1),
                    disable(2),
                    freeze(3) }
    MAX-ACCESS  read-write
    STATUS      current
    DESCRIPTION
        "Controls the interface output in case of a fault.

         notSupported(0). The interface does not support control of
         transmitter on fault. This value can only be read, and can
         never be written.

         enable(1). Will turn off (mute) transmitter power on fault.

         disable(2). Will output default signal on fault.

         freeze(3). Freezes the output on signal fail.  This is mainly
         intended to be used with through timing mode.  In aligned
         mode, output is always freezed anyway regardless if this
         value is set or not.  Valid if `fs' bit is set in
         itsIfCapabilities."
    ::= { itsIfEntry 15 }

itsIfPurpose OBJECT-TYPE
    SYNTAX      SnmpAdminString
    MAX-ACCESS  read-only
    STATUS      current
    DESCRIPTION
        "A string presenting the purpose of the TTP that is actively
         (trying) to use the interface.  If no TTP is using the
         interface, then the purpose is empty.  If an interface can be
         used as input and output interface at the same time (e.g. the
         interface has two physical ports), then this object presents
         the purpose of the TTP that originates in this interface."
    DEFVAL { ''H }
    ::= { itsIfEntry 16 }

itsIfInterfaceType OBJECT-TYPE
    SYNTAX      INTEGER {
                    pdh(1),
                    sdh(2),
                    sdi(3),
                    dvb(4),
                    aes(5),
                    mon(6) }
    MAX-ACCESS  read-only
    STATUS      current
    DESCRIPTION
        "Denotes the type of interface."
    ::= { itsIfEntry 17 }

itsIfMembersSrc OBJECT-TYPE
    SYNTAX      ItsTtpIndexList
    MAX-ACCESS  read-only
    STATUS      current
    DESCRIPTION
        "A list of values of the itsSrcTtpIndex for the source trail
         termination points (TTPs) that are actively connected to
         this interface.  A TTP can only be connected to an
         interface if its administrative state is `up'."
    ::= { itsIfEntry 18 }

itsIfMembersSnk OBJECT-TYPE
    SYNTAX      ItsTtpIndexList
    MAX-ACCESS  read-only
    STATUS      current
    DESCRIPTION
        "A list of values of the itsSnkTtpIndex for the sink trail
         termination points (TTPs) that are actively connected to
         this interface.  A TTP can only be connected to an
         interface if its administrative state is `up'."
    ::= { itsIfEntry 19 }



-- Table with PDH interfaces

itsIfPdhTable OBJECT-TYPE
    SYNTAX      SEQUENCE OF ItsIfPdhEntry
    MAX-ACCESS  not-accessible
    STATUS      current
    DESCRIPTION
        "Table with PDH interfaces.  The table contains configuration
         objects specific for PDH interfaces.  The table is indexed using
         the same index as the itsIfTable."
    ::= { itsIfGroup 3 }

itsIfPdhEntry OBJECT-TYPE
    SYNTAX      ItsIfPdhEntry
    MAX-ACCESS  not-accessible
    STATUS      current
    DESCRIPTION
        "One PDH interface is represented by one conceptual row in the
         table.  The interface is also represented in the itsIfTable
         using the same index."
    INDEX { itsIfIndex }
    ::= { itsIfPdhTable 1 }

ItsIfPdhEntry ::= SEQUENCE {
     itsIfPdhSignal     INTEGER,
     itsIfPdhFraming    INTEGER
}

itsIfPdhSignal OBJECT-TYPE
    SYNTAX      INTEGER {
                    e3(1),
                    ds3(2) }
    MAX-ACCESS  read-write
    STATUS      current
    DESCRIPTION
        "Selects type of signal to transport, E3 or DS3."
    DEFVAL { e3 }
    ::= { itsIfPdhEntry 1 }

itsIfPdhFraming OBJECT-TYPE
    SYNTAX      INTEGER {
                    none(1),
                    g751(2),
                    g832(3),
                    cbit(4),
                    m13(5) }
    MAX-ACCESS  read-write
    STATUS      current
    DESCRIPTION
        "Selects the type of framing to use. The valid values depend on
         selection of type on `itsIfPdhType'.

         none(1).  No framing.

         g751(2).  Only valid for E3.

         g832(3).  Only valid for E3.

         cbit(4).  Only valid for DS3.

         m13(5).  Only valid for DS3."
    DEFVAL { none }
    ::= { itsIfPdhEntry 2 }


-- Table with SDH interfaces

itsIfSdhTable OBJECT-TYPE
    SYNTAX      SEQUENCE OF ItsIfSdhEntry
    MAX-ACCESS  not-accessible
    STATUS      current
    DESCRIPTION
        "Table with SDH interfaces.  The table contains configuration
         objects specific for SDH interfaces.  The table is indexed using
         the same index as the itsIfTable."
    ::= { itsIfGroup 4 }

itsIfSdhEntry OBJECT-TYPE
    SYNTAX      ItsIfSdhEntry
    MAX-ACCESS  not-accessible
    STATUS      current
    DESCRIPTION
        "One SDH interface is represented by one conceptual row in the
         table.  The interface is also represented in the itsIfTable
         using the same index."
    INDEX { itsIfIndex }
    ::= { itsIfSdhTable 1 }

ItsIfSdhEntry ::= SEQUENCE {
     itsIfSdhTiming  INTEGER ,
     itsIfSdhMode    INTEGER,
     itsIfSdhSs      Unsigned32,
     itsIfSdhS1      Unsigned32,
     itsIfSdhSoh     SnmpAdminString,
     itsIfSdhPoh     SnmpAdminString,
     itsIfSdhJc      SnmpAdminString
}

itsIfSdhTiming OBJECT-TYPE
    SYNTAX      INTEGER {
                    loop(1),
                    internal(2) }
    MAX-ACCESS  read-write
    STATUS      current
    DESCRIPTION
        "Selects timing mode for the interface, i.e. clock source in
         transmission path."
    DEFVAL { loop }
    ::= { itsIfSdhEntry 1 }

itsIfSdhMode OBJECT-TYPE
    SYNTAX      INTEGER {
                    sdh(1),
                    sonet(2) }
    MAX-ACCESS  read-write
    STATUS      current
    DESCRIPTION
        "Sets SDH or SONET interface mode."
    DEFVAL { sdh }
    ::= { itsIfSdhEntry 2 }


itsIfSdhSs OBJECT-TYPE
    SYNTAX      Unsigned32 (0..3)
    MAX-ACCESS  read-write
    STATUS      current
    DESCRIPTION
        "Payload mapping type."
    DEFVAL { 2 }
    ::= { itsIfSdhEntry 3 }

itsIfSdhS1 OBJECT-TYPE
    SYNTAX      Unsigned32 (0..15)
    MAX-ACCESS  read-write
    STATUS      current
    DESCRIPTION
        "Synchronization message to send to external equipment in
         transmission path.  This defines the quality level of the
         clock used to transmit data."
    DEFVAL { 15 }
    ::= { itsIfSdhEntry 4 }

itsIfSdhSoh OBJECT-TYPE
    SYNTAX      SnmpAdminString
    MAX-ACCESS  read-only
    STATUS      current
    DESCRIPTION
        "A string containing the values of some section overhead
         bytes.  The byte values are on the format byte name, equal
         sign, byte value.  The values are then separated by a single
         space character.  I.e. the format is `S1=n SS=n M1=n B1=n
         B2=n'."
    ::= { itsIfSdhEntry 5 }

itsIfSdhPoh OBJECT-TYPE
    SYNTAX      SnmpAdminString
    MAX-ACCESS  read-only
    STATUS      current
    DESCRIPTION
        "A string containing the values of some path overhead bytes.
         The byte values are on the format byte name, equal sign, byte
         value.  The values are then separated by a single space
         character.  I.e. the format is `B3=n G1=n G2=n'."
    ::= { itsIfSdhEntry 6 }

itsIfSdhJc OBJECT-TYPE
    SYNTAX      SnmpAdminString
    MAX-ACCESS  read-only
    STATUS      current
    DESCRIPTION
        "A string containing the values of some justification
         counters.  The byte values are on the format counter name,
         equal sign, byte value.  The values are then separated by a
         single space character.  I.e. the format is `RPJE+=n RJE-=n
         TPJE+= TPJE-=n FJE+=n FJE-=n'."
    ::= { itsIfSdhEntry 7 }


-- Table with DVB interfaces

itsIfDvbTable OBJECT-TYPE
    SYNTAX      SEQUENCE OF ItsIfDvbEntry
    MAX-ACCESS  not-accessible
    STATUS      current
    DESCRIPTION
        "Table with DVB interfaces.  The table contains configuration
         objects specific for DVB interfaces.  The table is indexed using
         the same index as the itsIfTable."
    ::= { itsIfGroup 5 }

itsIfDvbEntry OBJECT-TYPE
    SYNTAX      ItsIfDvbEntry
    MAX-ACCESS  not-accessible
    STATUS      current
    DESCRIPTION
        "One DVB interface is represented by one conceptual row in the
         table.  The interface is also represented in the itsIfTable
         using the same index."
    INDEX { itsIfIndex }
    ::= { itsIfDvbTable 1 }

ItsIfDvbEntry ::= SEQUENCE {
     itsIfDvbFormat       SnmpAdminString,
     itsIfDvbOutputMode   INTEGER
}

itsIfDvbFormat OBJECT-TYPE
    SYNTAX      SnmpAdminString
    MAX-ACCESS  read-only
    STATUS      current
    DESCRIPTION
        "A textual string in a non-formal format describing the format
         of the data."
    ::= { itsIfDvbEntry 1 }

itsIfDvbOutputMode OBJECT-TYPE
    SYNTAX      INTEGER {
                    auto(1),
                    burst(2),
                    spread(3) }
    MAX-ACCESS  read-write
    STATUS      current
    DESCRIPTION
        "Selects output mode."
    DEFVAL { auto }
    ::= { itsIfDvbEntry 2 }


-- Table with AES/EBU interfaces

itsIfAesTable OBJECT-TYPE
    SYNTAX      SEQUENCE OF ItsIfAesEntry
    MAX-ACCESS  not-accessible
    STATUS      current
    DESCRIPTION
        "Table with AES interfaces.  The table contains configuration
         objects specific for AES interfaces.  The table is indexed
         using the same index as the itsIfTable."
    ::= { itsIfGroup 6 }

itsIfAesEntry OBJECT-TYPE
    SYNTAX      ItsIfAesEntry
    MAX-ACCESS  not-accessible
    STATUS      current
    DESCRIPTION
        "One AES interface is represented by one conceptual row in the
         table."
    INDEX { itsIfIndex }
    ::= { itsIfAesTable 1 }

ItsIfAesEntry ::= SEQUENCE {
     itsIfAesIsTimingProvider   INTEGER,
     itsIfAesReference          Integer32
}

itsIfAesIsTimingProvider OBJECT-TYPE
    SYNTAX      INTEGER {
                    no(0),
                    wordClock(1) }
    MAX-ACCESS  read-write
    STATUS      current
    DESCRIPTION
        "Selects whether the interface will be used primarily as as
         timing provider for other interfaces on the same board.  This
         object is applicable only if the interface supports reference
         locking, i.e. if the `ref' bit is set in itsIfCapabilities.

         no(0). Used primarily as normal transport interface and
         secondarily as digital timing provider.  Operational state is
         non-dormant and alarms are raised only when ingress or egress
         connection exists.

         wordClock(1). Used primarily as 48 kHz word clock timing
         provider.  Neither ingress nor egress connections are
         allowed.  Operational state is non-dormant and alarms can be
         raised if needed. "
    DEFVAL { no }
    ::= { itsIfAesEntry 1 }

itsIfAesReference OBJECT-TYPE
    SYNTAX      Integer32
    MAX-ACCESS  read-write
    STATUS      current
    DESCRIPTION
        "Selects the source interface to use as timing reference for
         output alignment.  The source can be any other interface on
         the same board except itself.  The value is the relative
         interface number on the board, where the first interface on
         the board is number 1, the second is number 2 and so on.

         This object is applicable only if the interface supports
         reference locking, i.e. if the `ref' bit is set in
         itsIfCapabilities."
    ::= { itsIfAesEntry 2 }



-- Table with SDI interfaces

itsIfSdiTable OBJECT-TYPE
    SYNTAX      SEQUENCE OF ItsIfSdiEntry
    MAX-ACCESS  not-accessible
    STATUS      current
    DESCRIPTION
        "Table with SDI video interfaces.  The table contains configuration
         objects specific to SDI interfaces.  The table is indexed using the
         same index as the itsIfTable."
    ::= { itsIfGroup 7 }

itsIfSdiEntry OBJECT-TYPE
    SYNTAX      ItsIfSdiEntry
    MAX-ACCESS  not-accessible
    STATUS      current
    DESCRIPTION
        "One SDI interface is represented by one conceptual row in the
         table.  The interface is also represented in the itsIfTable
         using the same index."
    INDEX { itsIfIndex }
    ::= { itsIfSdiTable 1 }

ItsIfSdiEntry ::= SEQUENCE {
    itsIfSdiFormat            SnmpAdminString,
    itsIfSdiAutoSense         INTEGER,
    itsIfSdiIsTimingProvider  INTEGER,
    itsIfSdiReference         Integer32,
    itsIfSdiFsVDelay          Integer32,  -- obsolete, use itsIfSdiFsDelay instead.
    itsIfSdiFsHDelay          Integer32,  -- obsolete, use itsIfSdiFsDelay instead.
    itsIfSdiFsDelay           Integer32
}

itsIfSdiFormat OBJECT-TYPE
    SYNTAX      SnmpAdminString
    MAX-ACCESS  read-only
    STATUS      current
    DESCRIPTION
        "Video source format.  The format is presented as

         `<pixels-per-line>x<lines-per-frame><i/p> @ <freq> Hz'

         E.g. `1920x1080p @ 30 Hz'

         The string is empty if no format is detected."
     ::= { itsIfSdiEntry 1 }

itsIfSdiAutoSense OBJECT-TYPE
    SYNTAX      INTEGER {
                    notSupported(0),
                    enable(1),
                    disable(2)
                }
    MAX-ACCESS  read-write
    STATUS      current
    DESCRIPTION
        "Controls whether autosense of the input/output signal shall
         be enabled or not.

         notSupported(0).  The interface does not support autosense.

         enable(1).  Autosense is enabled.  Input or output speed is
         automatically detected and the interface speed will
         automatically be configured to this detected speed regardless
         of the configured capacity of the transport channel.

         disable(2).  Autosense is disabled.  The interface is configured
         to a speed in accordance with the capacity of the transported
         channel."
    ::= { itsIfSdiEntry 2 }

itsIfSdiIsTimingProvider OBJECT-TYPE
    SYNTAX      INTEGER {
                    no(0),
                    analog(1),
                    digital(2) }
    MAX-ACCESS  read-write
    STATUS      current
    DESCRIPTION
        "Selects whether the interface will be used primarily as as
         timing provider for other interfaces on the same board.  This
         object is applicable only if the interface supports analog
         video reference signal, or digital video reference signal, i.e.
         if any of the bits `avrs' or `dvrs' is set in
         itsIfCapabilities.

         no(0). Used primarily as normal transport interface and
         secondarily as digital timing provider.  Operational state is
         non-dormant and alarms are raised only when ingress or egress
         connection exists.

         analog(1). Used primarily as analog timing provider.  Neither
         ingress nor egress connections are allowed.  Operational
         state is non-dormant and alarms can be raised as needed.
         This value can only be set if the interface supports analog
         video reference signal, i.e. the `avrs' bit is set in
         itsIfCapabilities.

         digital(1). Used primarily as digital timing provider and
         secondarily as transport interface.  Operational state is
         non-dormant and alarms can be raised as needed regardless
         if any ingress or egress connection exists.  This value can
         only be set if the interface supports digital video reference
         signal, i.e. the `dvrs' bit is set in itsIfCapabilities."
    DEFVAL { no }
    ::= { itsIfSdiEntry 3 }

itsIfSdiReference OBJECT-TYPE
    SYNTAX      Integer32
    MAX-ACCESS  read-write
    STATUS      current
    DESCRIPTION
        "Selects the source interface to use as timing reference for
         output alignment.  The source can be any interface on the
         same board.  The value is the relative interface number on
         the board, where the first interface on the board is number
         1, the second is number 2 and so on.  A value of `0' (zero)
         indicates the node sync.  The default is itself, which equals
         to through timing.  As through timing is not available on
         JPEG 2000 decoder, selection of the interface itself means
         node sync.

         This object is applicable only if the interface supports
         reference locking, i.e. if the `ref' bit is set in
         itsIfCapabilities."
    ::= { itsIfSdiEntry 4 }

itsIfSdiFsVDelay OBJECT-TYPE
    SYNTAX      Integer32 (-3..1124)
    MAX-ACCESS  read-write
    STATUS      obsolete -- use itsIfSdiFsDelay instead.
    DESCRIPTION
        "Adjusts the vertical output delay in number of lines.

         This object is applicable only if the interface supports
         reference locking, i.e. if the `ref' bit is set in
         itsIfCapabilities."
    ::= { itsIfSdiEntry 5 }

itsIfSdiFsHDelay OBJECT-TYPE
    SYNTAX      Integer32 (-3865..259)
    MAX-ACCESS  read-write
    STATUS      obsolete -- use itsIfSdiFsDelay instead.
    DESCRIPTION
        "Adjusts the horizontal output delay in number of pixels.

         This object is applicable only if the interface supports
         reference locking, i.e. if the `ref' bit is set in
         itsIfCapabilities."
    ::= { itsIfSdiEntry 6 }

itsIfSdiFsDelay OBJECT-TYPE
    SYNTAX      Integer32 (-20854167..20854167)
    MAX-ACCESS  read-write
    STATUS      current
    DESCRIPTION
        "Adjusts the output delay in number of nanoseconds.

         This object is applicable only if the interface supports
         reference locking, i.e. if the `ref' bit is set in
         itsIfCapabilities."
    ::= { itsIfSdiEntry 7 }

-- Table with monitor interfaces

itsIfMonTable OBJECT-TYPE
    SYNTAX      SEQUENCE OF ItsIfMonEntry
    MAX-ACCESS  not-accessible
    STATUS      current
    DESCRIPTION
        "Table with monitor interfaces.  The table contains
         configuration objects specific for monitor interfaces.  A
         monitor interface is used for monitoring data on another
         interface.  It outputs the same data as the in- or output of
         the interface that it is monitoring.

         The table is indexed using the same index as the itsIfTable."
    ::= { itsIfGroup 9 }

itsIfMonEntry OBJECT-TYPE
    SYNTAX      ItsIfMonEntry
    MAX-ACCESS  not-accessible
    STATUS      current
    DESCRIPTION
        "One monitor port is represented by one conceptual row in the
         table.  The interface is also represented in the itsIfTable
         using the same index."
    INDEX { itsIfIndex }
    ::= { itsIfMonTable 1 }

ItsIfMonEntry ::= SEQUENCE {
     itsIfMonMonitoredInterface  Integer32,
     itsIfMonDirection           INTEGER,
     itsIfEnableButton           TruthValue
}

itsIfMonMonitoredInterface OBJECT-TYPE
    SYNTAX      Integer32
    MAX-ACCESS  read-write
    STATUS      current
    DESCRIPTION
        "The relative number of the interface on the board that this
         interface is selected to monitor.  The first interface on the
         board is number 1, the second is number 2 and so on.  A value
         of 0 denotes that no interface shall be monitored."
    DEFVAL { 0 }
    ::= { itsIfMonEntry 1 }

itsIfMonDirection OBJECT-TYPE
    SYNTAX      INTEGER {
                    in(1),
                    out(2) }
    MAX-ACCESS  read-write
    STATUS      current
    DESCRIPTION
        "The direction of the monitored interface.

         in(1).  Monitors the input data of the monitored interface.

         out(2).  Monitors the output data of the monitored interface."
    DEFVAL { in }
    ::= { itsIfMonEntry 2 }

itsIfEnableButton OBJECT-TYPE
    SYNTAX      TruthValue
    MAX-ACCESS  read-write
    STATUS      current
    DESCRIPTION
        "Controls if a `monitor' push button on the device front panel
         is enabled for selection of interface to monitor.  This
         object is only applicable for boards supporting this
         function."
    DEFVAL { false }
    ::= { itsIfMonEntry 3 }


-- Table with JPEG 2000 interfaces

itsIfJ2kTable OBJECT-TYPE
    SYNTAX      SEQUENCE OF ItsIfJ2kEntry
    MAX-ACCESS  not-accessible
    STATUS      current
    DESCRIPTION
        "Table with JPEG 2000 interfaces.  The table contains
         configuration objects specific for JPEG 2000 encoding and
         decoding capable interfaces, i.e. when any of the bits
         `j2kEnc' or `j2kDec' are set in `itsIfCapabilities'.

         The table is indexed using the same index as the itsIfTable."
    ::= { itsIfGroup 10 }

itsIfJ2kEntry OBJECT-TYPE
    SYNTAX      ItsIfJ2kEntry
    MAX-ACCESS  not-accessible
    STATUS      current
    DESCRIPTION
        "One JPEG 2000 capable interface is represented by one
         conceptual row in the table.  The interface is also
         represented in the itsIfTable using the same index."
    INDEX { itsIfIndex }
    ::= { itsIfJ2kTable 1 }

ItsIfJ2kEntry ::= SEQUENCE {
     itsIfJ2kEncoderEnable                TruthValue,
     itsIfJ2kDecoderActive                TruthValue,
     itsIfJ2kSignalFormat                 INTEGER,
     itsIfJ2kRateVideo                    Unsigned32,
     itsIfJ2kRateVideoMax                 Unsigned32,
     itsIfJ2kRateVbi                      Unsigned32,
     itsIfJ2kRateAnc                      Unsigned32,
     itsIfJ2kRateAudio                    Unsigned32,
     itsIfJ2kAudioSampleSize              Unsigned32,
     itsIfJ2kReduceAudioTransportBitrate  TruthValue
}

itsIfJ2kEncoderEnable OBJECT-TYPE
    SYNTAX      TruthValue
    MAX-ACCESS  read-write
    STATUS      current
    DESCRIPTION
        "Selects whether the JPEG 2000 encoder functionality is
         enabled of not for the interface.  The rate of the JPEG 2000
         stream is calculated from the channel capacity set in the
         channel manager (NETI-CHMGR-MIB).  This object cannot be
         changed while there is an active connection on the interface.
         Only an ingress interface can act as encoder."
    DEFVAL { false }
    ::= { itsIfJ2kEntry 1 }

itsIfJ2kDecoderActive OBJECT-TYPE
    SYNTAX      TruthValue
    MAX-ACCESS  read-only
    STATUS      current
    DESCRIPTION
        "Indicates whether the JPEG 2000 decoder functionality is
         active or not.  The interface acting as JPEG 2000 decoder is
         automatic.  Only an egress interface can act as decoder."
    ::= { itsIfJ2kEntry 2 }

itsIfJ2kSignalFormat OBJECT-TYPE
    SYNTAX      INTEGER {
                    notApplicable(0),
                    sdSdi(1),
                    hdSdiEu(3),
                    hdSdiUs(4),
                    hd3gSdiEu(5),
                    hd3gSdiUs(6) }
    MAX-ACCESS  read-write
    STATUS      current
    DESCRIPTION
        "Indicates for which format JPEG 2000 is configured. The
         choice of format affects the available VBI configuration, the
         number of audio groups, and the configurable bandwidth range.

         notApplicable(0). If the interface does not support JPEG 2000
         encoding.

         sdSdi(1).    SD-SDI PAL/NTSC format.

         hdSdiEu(3).  HD-SDI European format.

         hdSdiUs(4).  HD-SDI American format.

         hd3gSdiEu(5).  3G-SDI European format.

         hd3gSdiUs(6).  3G-SDI American format."
    ::= { itsIfJ2kEntry 3 }

itsIfJ2kRateVideo OBJECT-TYPE
    SYNTAX      Unsigned32
    MAX-ACCESS  read-only
    STATUS      current
    DESCRIPTION
        "The actual JPEG 2000 code stream bit rate. Applicable for
         both encoder and decoder interfaces."
    ::= { itsIfJ2kEntry 4 }

itsIfJ2kRateVideoMax OBJECT-TYPE
    SYNTAX      Unsigned32
    MAX-ACCESS  read-only
    STATUS      current
    DESCRIPTION
        "The maximum JPEG 2000 code stream bit rate, calculated from
         the channel capacity, ANC, audio and VBI configurations."
    ::= { itsIfJ2kEntry 5 }

itsIfJ2kRateVbi OBJECT-TYPE
    SYNTAX      Unsigned32
    MAX-ACCESS  read-only
    STATUS      current
    DESCRIPTION
        "The VBI service bit rate detected and forwarded."
    ::= { itsIfJ2kEntry 6 }

itsIfJ2kRateAnc OBJECT-TYPE
    SYNTAX      Unsigned32
    MAX-ACCESS  read-only
    STATUS      current
    DESCRIPTION
        "The ancillary data bit rate detected and forwarded."
    ::= { itsIfJ2kEntry 7 }

itsIfJ2kRateAudio OBJECT-TYPE
    SYNTAX      Unsigned32
    MAX-ACCESS  read-only
    STATUS      current
    DESCRIPTION
        "The audio bit rate detected and forwarded."
    ::= { itsIfJ2kEntry 8 }

itsIfJ2kAudioSampleSize OBJECT-TYPE
    SYNTAX      Unsigned32 (0|20|24)
    MAX-ACCESS  read-write
    STATUS      current
    DESCRIPTION
        "The number of bits used for the audio samples: default 20-bit
         audio or extended 24-bit audio.  This value is applicable
         only for SD-SDI signal format (PAL/NTSC), and only on source
         interfaces.  The value zero (0) indicates that it is not
         applicable."
    DEFVAL { 20 }
    ::= { itsIfJ2kEntry 9 }

itsIfJ2kReduceAudioTransportBitrate OBJECT-TYPE
    SYNTAX      TruthValue
    MAX-ACCESS  read-write
    STATUS      current
    DESCRIPTION
        "Enables or disables enhanced audio transport, using a reduced
         transport bitrate for the audio.  This is only applicable for
         HD and 3G format, and only when the JPEG 2000 encodes is
         enabled (`itsIfJ2KEncodedEnable')."
    DEFVAL { false }
    ::= { itsIfJ2kEntry 10 }



-- Table with SDI audio groups

itsIfSdiAudioTable OBJECT-TYPE
    SYNTAX      SEQUENCE OF ItsIfSdiAudioEntry
    MAX-ACCESS  not-accessible
    STATUS      current
    DESCRIPTION
        "Table with audio groups.  The table contains configuration
         objects specific for audio groups in SDI streams.  Each audio
         group consists of 4 audio channels.  Audio group 5-8 is
         available only for 3G-SDI.  The table is indexed per
         interface and per audio group."
    ::= { itsIfGroup 11 }

itsIfSdiAudioEntry OBJECT-TYPE
    SYNTAX      ItsIfSdiAudioEntry
    MAX-ACCESS  not-accessible
    STATUS      current
    DESCRIPTION
        "One audio group is represented by one conceptual row in the
         table.  An entry may only exist for an interface that is
         capable of JPEG 2000, i.e. when any of the bits `j2kEnc' or
         `j2kDec' are set in `itsIfCapabilities'. The data is valid
         only if the interface is enabled for JPEG 2000."
    INDEX { itsIfIndex, itsIfSdiAudioIndex }
    ::= { itsIfSdiAudioTable 1 }

ItsIfSdiAudioEntry ::= SEQUENCE {
     itsIfSdiAudioIndex         Unsigned32,
     itsIfSdiAudioForward       TruthValue
}

itsIfSdiAudioIndex OBJECT-TYPE
    SYNTAX      Unsigned32 (1..8)
    MAX-ACCESS  not-accessible
    STATUS      current
    DESCRIPTION
        "Index in the table. The index specifies the audio group
         number.  Index 5-8 is only available for 3G-SDI."
    ::= { itsIfSdiAudioEntry 1 }

itsIfSdiAudioForward OBJECT-TYPE
    SYNTAX      TruthValue
    MAX-ACCESS  read-write
    STATUS      current
    DESCRIPTION
        "Indicates whether the audio group is enabled for transmission
         or not.  Only applicable for source end interfaces."
    DEFVAL { false }
    ::= { itsIfSdiAudioEntry 2 }


-- Table with VBI (Vertical Blanking Interval)

itsIfSdiVbiTable OBJECT-TYPE
    SYNTAX      SEQUENCE OF ItsIfSdiVbiEntry
    MAX-ACCESS  not-accessible
    STATUS      current
    DESCRIPTION
        "Table with Vertical Blanking Interval (VBI); lines outside
         the actual picture that are used to forward data.  The number
         of lines in the VBI depends on the format of the SDI signal.
         VBI is only used in SD signals (PAL/NTSC)."
    ::= { itsIfGroup 12 }

itsIfSdiVbiEntry OBJECT-TYPE
    SYNTAX      ItsIfSdiVbiEntry
    MAX-ACCESS  not-accessible
    STATUS      current
    DESCRIPTION
        "One entry per VBI line.  An entry may only exist for an
         interface that is capable of JPEG 2000, i.e. when any of the
         bits `j2kEnc' or `j2kDec' are set in `itsIfCapabilities'.
         The data is valid only if the interface is enabled for JPEG
         2000."
    INDEX { itsIfIndex, itsIfSdiVbiIndex }
    ::= { itsIfSdiVbiTable 1 }

ItsIfSdiVbiEntry ::= SEQUENCE {
     itsIfSdiVbiIndex       Integer32,
     itsIfSdiVbiLineNumber  Integer32,
     itsIfSdiVbiForward     INTEGER
}

itsIfSdiVbiIndex OBJECT-TYPE
    SYNTAX      Integer32 (1..46)
    MAX-ACCESS  not-accessible
    STATUS      current
    DESCRIPTION
        "The index in the table for the VBI line.  This is not the
         same as the line number."
    ::= { itsIfSdiVbiEntry 1 }

itsIfSdiVbiLineNumber OBJECT-TYPE
    SYNTAX      Integer32
    MAX-ACCESS  read-only
    STATUS      current
    DESCRIPTION
        "The line number."
    ::= { itsIfSdiVbiEntry 2 }

itsIfSdiVbiForward OBJECT-TYPE
    SYNTAX      INTEGER {
                    notApplicable(0),
                    yes(1),
                    no(2) }
    MAX-ACCESS  read-write
    STATUS      current
    DESCRIPTION
        "Indicates whether the VBI line number is enabled for
         forwarding or not.  The value is applicable only for source
         interfaces."
    DEFVAL { yes }
    ::= { itsIfSdiVbiEntry 3 }


-- Table with ANC data (Ancillary data)

itsIfSdiAncTable OBJECT-TYPE
    SYNTAX      SEQUENCE OF ItsIfSdiAncEntry
    MAX-ACCESS  not-accessible
    STATUS      current
    DESCRIPTION
        "Table with ancillary data.  This is embedded into the SDI
         signal but is not video."
    ::= { itsIfGroup 13 }

itsIfSdiAncEntry OBJECT-TYPE
    SYNTAX      ItsIfSdiAncEntry
    MAX-ACCESS  not-accessible
    STATUS      current
    DESCRIPTION
        "One DID/SDID combination is represented by one conceptual row
         in the table.  An entry may only exist for an interface that
         is capable of JPEG 2000, i.e. when any of the bits `j2kEnc'
         or `j2kDec' are set in `itsIfCapabilities'.  The data is
         valid only if the interface is enabled for JPEG 2000."
    INDEX { itsIfIndex, itsIfSdiAncIndex }
    ::= { itsIfSdiAncTable 1 }

ItsIfSdiAncEntry ::= SEQUENCE {
     itsIfSdiAncIndex        Integer32,
     itsIfSdiAncDescription  SnmpAdminString,
     itsIfSdiAncDid          Unsigned32,
     itsIfSdiAncSdid         Unsigned32,
     itsIfSdiAncForward      INTEGER
}

itsIfSdiAncIndex OBJECT-TYPE
    SYNTAX      Integer32 (1..32)
    MAX-ACCESS  not-accessible
    STATUS      current
    DESCRIPTION
        "An index in the table, with one row per DID/SDID combination."
    ::= { itsIfSdiAncEntry 1 }

itsIfSdiAncDescription OBJECT-TYPE
    SYNTAX      SnmpAdminString
    MAX-ACCESS  read-only
    STATUS      current
    DESCRIPTION
        "A string that identifies or describes the service
         corresponding to the DID/SDID combination."
    ::= { itsIfSdiAncEntry 2 }

itsIfSdiAncDid OBJECT-TYPE
    SYNTAX      Unsigned32
    MAX-ACCESS  read-only
    STATUS      current
    DESCRIPTION
        "The Data ID.  Identifies the type of ANC.  If the value is
         less than 0x08 then the ancillary data is of type 2, which
         means that the SDID is also present and should be used."
    ::= { itsIfSdiAncEntry 3 }

itsIfSdiAncSdid OBJECT-TYPE
    SYNTAX      Unsigned32
    MAX-ACCESS  read-only
    STATUS      current
    DESCRIPTION
        "The Secondary Data ID.  This has the value of 0 if the
         ancillary data is of type 1."
    ::= { itsIfSdiAncEntry 4 }

itsIfSdiAncForward OBJECT-TYPE
    SYNTAX      INTEGER {
                    notApplicable(0),
                    yes(1),
                    no(2) }
    MAX-ACCESS  read-write
    STATUS      current
    DESCRIPTION
        "Indicates if the DID/SDID combination is enabled for
         forwarding or not.  The value is applicable only for source
         interfaces."
    DEFVAL { yes }
    ::= { itsIfSdiAncEntry 5 }


-- Table with protection type 3 settings

itsIfPs3Table OBJECT-TYPE
    SYNTAX      SEQUENCE OF ItsIfPs3Entry
    MAX-ACCESS  not-accessible
    STATUS      current
    DESCRIPTION
        "Table with settings for hitless 1+1 protection."
    ::= { itsIfGroup 14 }

itsIfPs3Entry OBJECT-TYPE
    SYNTAX      ItsIfPs3Entry
    MAX-ACCESS  not-accessible
    STATUS      current
    DESCRIPTION
        "One interface that is capable of hitless 1+1 protection is
         represented by one row in this table.  An entry may only
         exist for an interface that is capable of switch type 3,
         i.e. when the bits `hitps' or `psType3' is set in
         `itsIfCapabilites'."
    INDEX { itsIfIndex }
    ::= { itsIfPs3Table 1 }

ItsIfPs3Entry ::= SEQUENCE {
     itsIfPs3DifferentialDelay        Unsigned32,
     itsIfPs3DifferentialDelayValid   TruthValue,
     itsIfPs3AheadInterface           Integer32,
     itsIfPs3HitlessProtection        TruthValue,
     itsIfPs3ProtectionStatus         ItsProtectionStatus,
     itsIfPs3ExpectedProtectionStatus ItsProtectionStatus,
     itsIfPs3ForceHit                 Unsigned32,
     itsIfPs3ActiveInterface          Integer32,
     itsIfPs3MaxExpDifferentialDelay  Unsigned32
}

itsIfPs3DifferentialDelay OBJECT-TYPE
    SYNTAX      Unsigned32
    MAX-ACCESS  read-only
    STATUS      current
    DESCRIPTION
        "Measured differential delay in microseconds between the two
         paths.  Zero (0) indicates that standby protection is used."
    ::= { itsIfPs3Entry 1 }

itsIfPs3DifferentialDelayValid OBJECT-TYPE
    SYNTAX      TruthValue
    MAX-ACCESS  read-only
    STATUS      current
    DESCRIPTION
        "Specifies if the value of itsIfPs3DifferentialDelay is valid
         or not."
    ::= { itsIfPs3Entry 2 }

itsIfPs3AheadInterface OBJECT-TYPE
    SYNTAX      Integer32
    MAX-ACCESS  read-only
    STATUS      current
    DESCRIPTION
        "The index of the sink trail termination point (TTP) that is
         ahead.  Minus one indicates either that information is not
         available or is invalid."
    ::= { itsIfPs3Entry 3 }

itsIfPs3HitlessProtection OBJECT-TYPE
    SYNTAX      TruthValue
    MAX-ACCESS  read-write
    STATUS      current
    DESCRIPTION
        "Specifies if hitless protection shall be attempted or not.

         true(1).  Will attempt to reach a hitless protection state.

         false(2).  Will only attempt to reach a standby protection
         state."
    ::= { itsIfPs3Entry 4 }

itsIfPs3ProtectionStatus OBJECT-TYPE
    SYNTAX      ItsProtectionStatus
    MAX-ACCESS  read-only
    STATUS      current
    DESCRIPTION
        "The current protection state."
    ::= { itsIfPs3Entry 5 }

itsIfPs3ExpectedProtectionStatus OBJECT-TYPE
    SYNTAX      ItsProtectionStatus
    MAX-ACCESS  read-write
    STATUS      current
    DESCRIPTION
        "The expected protection state.  When the current protection
         state (see itsIfPs3ProtectionStatus) is lower than the expected
         protection state, an alarm is raised.  The alarm is cleared
         when the expected protection state is equal or higher than
         the current protection state."
    DEFVAL { unprotected }
    ::= { itsIfPs3Entry 6 }

itsIfPs3ForceHit OBJECT-TYPE
    SYNTAX      Unsigned32(0)
    MAX-ACCESS  read-write
    STATUS      current
    DESCRIPTION
        "A write of zero (0) resets the buffers, and will therefore
         minimize the the latency penalty incurred by the 1+1
         buffering."
    ::= { itsIfPs3Entry 7 }

itsIfPs3ActiveInterface OBJECT-TYPE
    SYNTAX      Integer32
    MAX-ACCESS  read-write
    STATUS      current
    DESCRIPTION
        "The index of the sink trail termination point (TTP) that is
         is selected as source.  Minus one indicates either that
         information is not available or is invalid."
    ::= { itsIfPs3Entry 8 }

itsIfPs3MaxExpDifferentialDelay OBJECT-TYPE
    SYNTAX      Unsigned32
    MAX-ACCESS  read-write
    STATUS      current
    DESCRIPTION
        "Maximum expected differential delay in milliseconds where 0
         (zero) implies largest possible value for channel capacity
         and service type.  If measured differential delay is above
         this, hitless protected status can not be guaranteed.

         Maximum assignable value is bit rate and service type
         dependent.  The higher the bit rate, the lower the value. For
         largest bit rate however, up to 100 ms is guaranteed to work
         for all service types.

         Note also that the larger the value, the greater the latency.
         Therefore, for latency sensitive signals as small non-zero
         value as possible shall be used."
    ::= { itsIfPs3Entry 9 }


--
-- The source group
--

itsSrcTtpLastChange OBJECT-TYPE
    SYNTAX      TimeStamp
    MAX-ACCESS  read-only
    STATUS      current
    DESCRIPTION
        "The value of sysUpTime of the last change of any object in
         the itsSrcTtpTable."
    ::= { itsSourceGroup 1 }

itsSrcTtpNextIndex OBJECT-TYPE
    SYNTAX      Unsigned32
    MAX-ACCESS  read-only
    STATUS      current
    DESCRIPTION
        "The value of the next available index for an entry in the
         itsSrcTtpTable."
    ::= { itsSourceGroup 2 }


-- The Source TTP Table

itsSrcTtpTable OBJECT-TYPE
    SYNTAX      SEQUENCE OF ItsSrcTtpEntry
    MAX-ACCESS  not-accessible
    STATUS      current
    DESCRIPTION
        "Table with source trail termination points."
    ::= { itsSourceGroup 3 }

itsSrcTtpEntry OBJECT-TYPE
    SYNTAX      ItsSrcTtpEntry
    MAX-ACCESS  not-accessible
    STATUS      current
    DESCRIPTION
        "One conceptual row represents one source trail termination point."
    INDEX { itsSrcTtpIndex }
    ::= { itsSrcTtpTable 1 }

ItsSrcTtpEntry ::= SEQUENCE {
    itsSrcTtpIndex         Unsigned32,
    itsSrcTtpName          SnmpAdminString,
    itsSrcTtpCustomerId    Unsigned32,
    itsSrcTtpPurpose       SnmpAdminString,
    itsSrcTtpLocalIf       Unsigned32,
    itsSrcTtpLocalDsti     Dsti,
    itsSrcTtpMode          INTEGER,
    itsSrcTtpODescription  Unsigned32,
    itsSrcTtpOConnection   Unsigned32,
    itsSrcTtpFailure       SnmpAdminString,
    itsSrcTtpAdminStatus   INTEGER,
    itsSrcTtpOperStatus    INTEGER,
    itsSrcTtpRowStatus     RowStatus
}

itsSrcTtpIndex OBJECT-TYPE
    SYNTAX      Unsigned32
    MAX-ACCESS  not-accessible
    STATUS      current
    DESCRIPTION
        "The index in the table. The index is persistent cross reboots."
    ::= { itsSrcTtpEntry 1 }

itsSrcTtpName OBJECT-TYPE
    SYNTAX      SnmpAdminString
    MAX-ACCESS  read-only
    STATUS      current
    DESCRIPTION
        "The textual name of the trail termination point (TTP). The
         value of this object should be the name of the TTP as
         assigned by the local device and should be suitable for use
         in commands entered at the device's console. This might be
         a text name, such as `itso-1' or a simple port number."
    ::= { itsSrcTtpEntry 2 }

itsSrcTtpCustomerId OBJECT-TYPE
    SYNTAX      Unsigned32
    MAX-ACCESS  read-write
    STATUS      current
    DESCRIPTION
        "A customer identification number that represents the customer
         or user of the trail termination point (TTP). The value could
         be used e.g. for identifying the customer in Charge Data
         Records. The value zero (0) represents that no customer is
         associated with the TTP."
    DEFVAL { 0 }
    ::= { itsSrcTtpEntry 3 }

itsSrcTtpPurpose OBJECT-TYPE
    SYNTAX      SnmpAdminString
    MAX-ACCESS  read-write
    STATUS      current
    DESCRIPTION
        "A string describing the purpose of the TTP. The string is for
         administrative use."
    DEFVAL { ''H }
    ::= { itsSrcTtpEntry 4 }

itsSrcTtpLocalIf OBJECT-TYPE
    SYNTAX      Unsigned32
    MAX-ACCESS  read-write
    STATUS      current
    DESCRIPTION
        "A reference to the local interface that shall be used by the
         trail termination point (TTP). The value is representing the
         index in the itsIfTable. The value must refers to an existing
         entry in itsIfTable. When a TTP is created, the value of this
         object points to an arbitrary interface in itsIfTable."
    ::= { itsSrcTtpEntry 5 }

itsSrcTtpLocalDsti OBJECT-TYPE
    SYNTAX      Dsti
    MAX-ACCESS  read-write
    STATUS      current
    DESCRIPTION
        "The DSTI (DTM Service Type Instance) for the source trail
        termination point. The value is used by the connection to
        refer to this trail termination point. The DSTI must be unique
        among the ITS source trail termination points."
    ::= { itsSrcTtpEntry 6 }

itsSrcTtpMode OBJECT-TYPE
    SYNTAX      INTEGER {
                    unicast(1),
                    multicast(2),
                    compatible(3) }
    MAX-ACCESS  read-create
    STATUS      current
    DESCRIPTION
        "The TTP mode. The associated interface, itsSrcTtpLocalIf,
         must have the capability to support the property when the
         administrative state of the TTP is set to up.

         unicast(1). The trail termination point shall establish a
         unicast connection.

         multicast(2). The trail termination point shall established a
         multicast connection. It will set the corresponding
         capability in chmgrODescrCapabilites.

         compatible(3). The trail termination point shall be
         compatible with early systems releases, and is acting as to
         connect to a remote system with an earlier system release."
    DEFVAL { unicast }
    ::= { itsSrcTtpEntry 7 }

itsSrcTtpODescription OBJECT-TYPE
    SYNTAX      Unsigned32 (1..4294967295)
    MAX-ACCESS  read-only
    STATUS      current
    DESCRIPTION
        "A reference to the corresponding description of the
         connection in the chmgrODescriptionTable in the Channel
         Manager MIB (NETI-CHMGR-MIB). The value is the index into the
         table, i.e. the value of chmgrODescrIndex. When a row
         is created in or deleted from this table, the corresponding
         row is created in or deleted from the table
         chmgrODescriptionTable."
    ::= { itsSrcTtpEntry 8 }

itsSrcTtpOConnection OBJECT-TYPE
    SYNTAX      Unsigned32
    MAX-ACCESS  read-only
    STATUS      current
    DESCRIPTION
        "A reference to the corresponding originating connection in
         the table chmgrOConnectionTable in the Channel Manager MIB
         (NETI-CHMGR-MIB). When an originating connection is
         established from this trail termination point, an entry is
         created in the table. The value is the index into that table,
         i.e. the value of chmgrOConnIndex. If no connection is
         established or associated with this connection, this is
         indicated by a value of zero (0)."
    ::= { itsSrcTtpEntry 9 }

itsSrcTtpFailure OBJECT-TYPE
    SYNTAX      SnmpAdminString
    MAX-ACCESS  read-only
    STATUS      current
    DESCRIPTION
        "A textual string describing a fault status on the trail
         termination point (TTP). A configuration error is regarded as
         a fault state, which is indicated when the administrative
         state is down. A network related fault can only occur when
         the administrative state is up. The object presents an empty
         string if there are no faults on the TTP."
    ::= { itsSrcTtpEntry 10 }

itsSrcTtpAdminStatus OBJECT-TYPE
    SYNTAX      INTEGER {
                    up(1),
                    down(2) }
    MAX-ACCESS  read-write
    STATUS      current
    DESCRIPTION
        "The administrative state of the connection. The value
         controls the desired state of the connection from the trail
         termination point (TTP). Note that the associated interface
         must have capabilities that matches the properties of the
         TTP to be able to successfully change the administrative
         state to up(1).

         up(1). The connection shall be active.

         down(2). The connection shall be in-active. The active
         connection is torn down and alarms are cleared."
    DEFVAL { down }
    ::= { itsSrcTtpEntry 11 }

itsSrcTtpOperStatus OBJECT-TYPE
    SYNTAX      INTEGER {
                    up(1),
                    down(2),
                    unknown(4),
                    dormant(5),
                    partial(9) }
    MAX-ACCESS  read-only
    STATUS      current
    DESCRIPTION
        "The operational state of the trail termination point (TTP).

         up(1). The TTP is up and a connection is established to all
         destinations. If the connection is 1+1 protected, both the
         channels are established to all the destinations.

         down(2). The connection is down to all destinations. The
         itsSrcTtpFailure describes the fault.

         unknown(4). The TTP is in an unknown state due to some
         internal error.

         dormant(5). The TTP is ready and is waiting for a connection
         to be established.

         partial(9). The connection is established to some but not all
         the destinations. Or, if the connection is 1+1 protected,
         only one of the channels are established."
    ::= { itsSrcTtpEntry 12 }

itsSrcTtpRowStatus OBJECT-TYPE
    SYNTAX      RowStatus
    MAX-ACCESS  read-create
    STATUS      current
    DESCRIPTION
        "See SNMPv2-TC. Use itsSrcTtpAdminStatus to activate and
         de-activate a connection. The following values are supported:

         active(1). The object always reads active.

         createAndGo(4). A new conceptual row is created representing
         a new trail termination point (TTP). To activate the TTP, set
         the administrative status to up(1), after all columnar
         objects have been updated. It is only possible to create
         a TTP if at least one interface exists.

         destroy(6). The connection is terminated and the TTP is
         deleted."
    ::= { itsSrcTtpEntry 13 }

-- End of the Source TTP Table


-- The DSTI to Index Lookup Table for Source TTP's

itsSrcIndexLookupTable OBJECT-TYPE
    SYNTAX      SEQUENCE OF ItsSrcIndexLookupEntry
    MAX-ACCESS  not-accessible
    STATUS      current
    DESCRIPTION
        "Table to lookup a DSTI to an index in the itsSrcTtpTable."
    ::= { itsSourceGroup 4 }

itsSrcIndexLookupEntry OBJECT-TYPE
    SYNTAX      ItsSrcIndexLookupEntry
    MAX-ACCESS  not-accessible
    STATUS      current
    DESCRIPTION
        "One conceptual row represents one lookup entry."
    INDEX { itsSrcTtpLocalDsti }
    ::= { itsSrcIndexLookupTable 1 }

ItsSrcIndexLookupEntry ::= SEQUENCE {
    itsSrcIndexLookupIndex       Unsigned32
}

itsSrcIndexLookupIndex OBJECT-TYPE
    SYNTAX      Unsigned32
    MAX-ACCESS  read-only
    STATUS      current
    DESCRIPTION
        "The value refers to the index in table itsSrcTtpTable."
    ::= { itsSrcIndexLookupEntry 1 }

-- End of the DSTI to Index Lookup Table for Source TTP's


--
-- The sink group
--

itsSnkTtpLastChange OBJECT-TYPE
    SYNTAX      TimeStamp
    MAX-ACCESS  read-only
    STATUS      current
    DESCRIPTION
        "The value of sysUpTime of the last change of any object in
         the itsSnkTtpTable."
    ::= { itsSinkGroup 1 }

itsSnkTtpNextIndex OBJECT-TYPE
    SYNTAX      Unsigned32
    MAX-ACCESS  read-only
    STATUS      current
    DESCRIPTION
        "The value of the next available index for an entry in the
         itsSnkTtpTable."
    ::= { itsSinkGroup 2 }


-- The Sink TTP Table

itsSnkTtpTable OBJECT-TYPE
    SYNTAX      SEQUENCE OF ItsSnkTtpEntry
    MAX-ACCESS  not-accessible
    STATUS      current
    DESCRIPTION
        "Table with sink trail termination points."
    ::= { itsSinkGroup 3 }

itsSnkTtpEntry OBJECT-TYPE
    SYNTAX      ItsSnkTtpEntry
    MAX-ACCESS  not-accessible
    STATUS      current
    DESCRIPTION
        "One conceptual row represents one sink trail termination point."
    INDEX { itsSnkTtpIndex }
    ::= { itsSnkTtpTable 1 }

ItsSnkTtpEntry ::= SEQUENCE {
    itsSnkTtpIndex           Unsigned32,
    itsSnkTtpName            SnmpAdminString,
    itsSnkTtpCustomerId      Unsigned32,
    itsSnkTtpPurpose         SnmpAdminString,
    itsSnkTtpLocalIf         Unsigned32,
    itsSnkTtpLocalDsti       Dsti,
    itsSnkTtpPSActiveChannel INTEGER,
    itsSnkTtpSuppressAlarm   INTEGER,
    itsSnkTtpTConnection     Unsigned32,
    itsSnkTtpDefects         BITS,
    itsSnkTtpFailure         SnmpAdminString,
    itsSnkTtpPMReference     RowPointer,
    itsSnkTtpAdminStatus     INTEGER,
    itsSnkTtpOperStatus      INTEGER,
    itsSnkTtpRowStatus       RowStatus,
    itsSnkTtpTConnection2    Integer32,
    itsSnkTtpPSAllow         TruthValue
}

itsSnkTtpIndex OBJECT-TYPE
    SYNTAX      Unsigned32
    MAX-ACCESS  not-accessible
    STATUS      current
    DESCRIPTION
        "The index in the table.  The index is persistent across reboots."
    ::= { itsSnkTtpEntry 1 }

itsSnkTtpName OBJECT-TYPE
    SYNTAX      SnmpAdminString
    MAX-ACCESS  read-only
    STATUS      current
    DESCRIPTION
        "The textual name of the trail termination point (TTP). The
         value of this object should be the name of the TTP as
         assigned by the local device and should be suitable for use
         in commands entered at the device's console. This might be
         a text name, such as `itsi-1' or a simple port number."
    ::= { itsSnkTtpEntry 2 }

itsSnkTtpCustomerId OBJECT-TYPE
    SYNTAX      Unsigned32
    MAX-ACCESS  read-write
    STATUS      current
    DESCRIPTION
        "A customer identification number that represents the customer
         or user of the trail termination point (TTP). The value could
         be used e.g. for identifying the customer in Charge Data
         Records. The value zero (0) represents that no customer is
         associated with the TTP."
    DEFVAL { 0 }
    ::= { itsSnkTtpEntry 3 }

itsSnkTtpPurpose OBJECT-TYPE
    SYNTAX      SnmpAdminString
    MAX-ACCESS  read-write
    STATUS      current
    DESCRIPTION
        "A string describing the purpose of the TTP. The object use is
         for administrative purpose."
    DEFVAL { ''H }
    ::= { itsSnkTtpEntry 4 }

itsSnkTtpLocalIf OBJECT-TYPE
    SYNTAX      Unsigned32
    MAX-ACCESS  read-write
    STATUS      current
    DESCRIPTION
        "A reference to the local interface that shall be used by the
         trail termination point (TTP). The value is representing the
         index in the itsIfTable. The value must point to an existing
         interface. When the TTP is created, the object points to an
         arbitrary interface in itsIfTable."
    ::= { itsSnkTtpEntry 5 }

itsSnkTtpLocalDsti OBJECT-TYPE
    SYNTAX      Dsti
    MAX-ACCESS  read-write
    STATUS      current
    DESCRIPTION
        "The DSTI (DTM Service Type Instance) for the sink trail
         termination point. The value is used by the connection to
         refer to this trail termination point. The DSTI must be
         unique among the ITS sink trail termination points."
    ::= { itsSnkTtpEntry 6 }

itsSnkTtpPSActiveChannel OBJECT-TYPE
    SYNTAX      INTEGER {
                    primary(1),
                    secondary(2),
                    none(3) }
    MAX-ACCESS  read-write
    STATUS      current
    DESCRIPTION
        "The channel to use on a 1+1 protected connection. When a
         connection is being established, the first established
         channel will become the active channel. The device will
         switch to the other channel when it detects a fault on the
         active channel.

         The value of this object cannot be changed unless the
         operational state of the trail termination point is up.

         primary(1). The primary channel is used. If 1+1 protection
         switch is not used or supported, the primary channel is the
         only channel, and the object cannot be set to any other
         value.

         secondary(2). The secondary channel is used.

         none(3). The connection is not established, or is not 1+1
         protected. It is not possible to set this value. While the
         value is none(3), it is not possible to set this object."
    ::= { itsSnkTtpEntry 7 }

itsSnkTtpSuppressAlarm OBJECT-TYPE
    SYNTAX      INTEGER {
                    notSupported(0),
                    none(1),
                    warning(2),
                    all(3) }
    MAX-ACCESS  read-write
    STATUS      current
    DESCRIPTION
        "The alarm suppression mode. When alarms are suppressed, no
         alarms will be generated if a fault situation is detected on
         the trail termination point (TTP). Failures will still be
         shown by the object itsSnkTtpFailure.

         notSupported(0). Suppress alarms is not supported by the
         interface. This value can not be written.

         none(1). No alarms are suppressed. All alarms are reported.

         warning(2). Suppress alarms of severity warning only.

         all(3). All transmission alarms are suppressed."
    DEFVAL { none }
    ::= { itsSnkTtpEntry 8 }

itsSnkTtpTConnection OBJECT-TYPE
    SYNTAX      Unsigned32
    MAX-ACCESS  read-only
    STATUS      current
    DESCRIPTION
        "A reference to the corresponding terminating connection in
         the table chmgrTConnectionTable in the Channel Manager MIB
         (NETI-CHMGR-MIB).  The value is the index into that table,
         i.e. the value of chmgrTConnIndex.

         If 1+1 protection is used, then this object refers to the
         first established connection.  If two channels originate from
         the same TTP, then the same connection is used for both
         channels, which are referenced by this object. If two
         channels originate from different TTPs, then two connections
         are used, one for each channel. The second connected
         connection is referenced by itsSnkTtpTConnection2."
    ::= { itsSnkTtpEntry 9 }

itsSnkTtpDefects OBJECT-TYPE
    SYNTAX      BITS {
                    los(0),
                    lof(1),
                    ais(2),
                    lop(3)}
    MAX-ACCESS  read-only
    STATUS      current
    DESCRIPTION
        "Defects indicated on the trail termination point since the
         last time the object was read.

         los(0) Loss of Signal was detected.

         lof(1) Loss of Frame was detected.

         ais(2). Alarm Indication Signal was received from originating
         node.

         lop(3). Loss of Pointer was detected. This happens on DVB
         when the connection does not have enough capacity."
    ::= { itsSnkTtpEntry 10 }

itsSnkTtpFailure OBJECT-TYPE
    SYNTAX      SnmpAdminString
    MAX-ACCESS  read-only
    STATUS      current
    DESCRIPTION
        "A textual string describing a fault status on the trail
         termination point (TTP). A configuration error is regarded as
         a fault state, which is indicated when the administrative
         state is down. A network related fault can only occur when
         the administrative state is up. The object presents an empty
         string if there are no faults on the TTP."
    ::= { itsSnkTtpEntry 11 }

itsSnkTtpPMReference OBJECT-TYPE
    SYNTAX      RowPointer
    MAX-ACCESS  read-only
    STATUS      current
    DESCRIPTION
        "A reference to an object that presents performance data for
         the trail termination point. The object is not part of this
         MIB. If the selected local interface (itsSnkLocalIf) does not
         support performance monitoring for the TTP, it is indicated
         by the value `0.0'."
    ::= { itsSnkTtpEntry 12 }

itsSnkTtpAdminStatus OBJECT-TYPE
    SYNTAX      INTEGER {
                    up(1),
                    down(2) }
    MAX-ACCESS  read-write
    STATUS      current
    DESCRIPTION
        "The administrative state of the connection. The value
         controls the desired state of the connection from the trail
         termination point (TTP).

         up(1). The connection shall be active.

         down(2). The connection shall be in-active; active connection
         are torn down and alarms are cleared. This is the required
         state when changing the configuration of the TTP."
    DEFVAL { down }
    ::= { itsSnkTtpEntry 13 }

itsSnkTtpOperStatus OBJECT-TYPE
    SYNTAX      INTEGER {
                    up(1),
                    down(2),
                    dormant(5) }
    MAX-ACCESS  read-only
    STATUS      current
    DESCRIPTION
        "The operational state of the trail termination point (TTP).

         up(1). The TTP is up and a connection is established to all
         destinations.

         down(2). The connection is down to all destinations.

         dormant(5). The TTP is ready and is waiting for a connection
         to be established."
    ::= { itsSnkTtpEntry 14 }

itsSnkTtpRowStatus OBJECT-TYPE
    SYNTAX      RowStatus
    MAX-ACCESS  read-create
    STATUS      current
    DESCRIPTION
        "See SNMPv2-TC. Use itsSnkTtpAdminStatus to activate and
         de-activate a connection. The following values are supported:

         active(1). The object always reads active.

         createAndGo(4). A new conceptual row is created representing
         a new trail termination point (TTP). To activate the TTP, set
         the administrative status to up(1), after all columnar
         objects have been updated. It is only possible to crate a
         TTP when at least one interface exists.

         destroy(6). The connection is terminated and the TTP is
         deleted."
    ::= { itsSnkTtpEntry 15 }

itsSnkTtpTConnection2 OBJECT-TYPE
    SYNTAX      Integer32 (-1|0..2147483647)
    MAX-ACCESS  read-only
    STATUS      current
    DESCRIPTION
        "A reference to the corresponding terminating connection in
         the table chmgrTConnectionTable in the Channel Manager MIB
         (NETI-CHMGR-MIB) for the second established connection when 1+1
         protection is used where the two channel originate from two
         different trail termination points (TTPs). If the two
         channels originate from the same TTP, then only one entry is
         used in the chmgrTConnectionTable, referenced by
         itsSnkTtpTConnection, and the value of this object is then
         -1.

         The value is the index into the table, i.e. the value of
         chmgrTConnIndex."
    ::= { itsSnkTtpEntry 16 }

itsSnkTtpPSAllow OBJECT-TYPE
    SYNTAX      TruthValue
    MAX-ACCESS  read-write
    STATUS      current
    DESCRIPTION
        "Controls if termination of an 1+1 is allowed:

         true(1).  Allows termination of two channels or connections
         for a 1+1 protected service.

         false(2). Denies termination of a second channel or
         connection. This prevents 1+1 protection."
    DEFVAL { true }
    ::= { itsSnkTtpEntry 17 }

-- End of the Sink TTP Table


-- The DSTI to Index Lookup Table for Sink TTP's

itsSnkIndexLookupTable OBJECT-TYPE
    SYNTAX      SEQUENCE OF ItsSnkIndexLookupEntry
    MAX-ACCESS  not-accessible
    STATUS      current
    DESCRIPTION
        "Table to lookup a DSTI to an index in the itsSnkTtpTable."
    ::= { itsSinkGroup 4 }

itsSnkIndexLookupEntry OBJECT-TYPE
    SYNTAX      ItsSnkIndexLookupEntry
    MAX-ACCESS  not-accessible
    STATUS      current
    DESCRIPTION
        "One conceptual row represents one lookup entry."
    INDEX { itsSnkTtpLocalDsti }
    ::= { itsSnkIndexLookupTable 1 }

ItsSnkIndexLookupEntry ::= SEQUENCE {
    itsSnkIndexLookupIndex       Unsigned32
}

itsSnkIndexLookupIndex OBJECT-TYPE
    SYNTAX      Unsigned32
    MAX-ACCESS  read-only
    STATUS      current
    DESCRIPTION
        "The value refers to the index in table itsSnkTtpTable."
    ::= { itsSnkIndexLookupEntry 1 }

-- End of the DSTI to Index Lookup Table for Sink TTP's


END
