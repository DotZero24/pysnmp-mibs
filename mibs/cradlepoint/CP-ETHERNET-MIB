CP-ETHERNET-MIB DEFINITIONS ::= BEGIN

-- Cradlepoint Ethernet MIB Release 1.1

-- Copyright 2008-2019 by CradlePoint, Inc.  All rights reserved

-- This Specification is supplied "AS IS", CradlePoint makes no warranty,
-- either expressed or implied, as to the use, operation, condition,
-- or performance of the Specification.

IMPORTS
     wipipeEthernet                             FROM WIPIPE-MIB;

ethernetPortTable        OBJECT-TYPE
    SYNTAX     SEQUENCE OF ethernetPortEntry
    MAX-ACCESS not-accessible
    STATUS     current
    DESCRIPTION
        "Ethernet port table. This table contains one entry per physical Ethernet
         port."
            ::= { wipipeEthernet 1 }

ethernetPortTraps      OBJECT IDENTIFIER ::= { wipipeEthernet 2 }


ethernetPortEntry OBJECT-TYPE
    SYNTAX      EthernetPortEntry
    MAX-ACCESS  not-accessible
    STATUS      current
    DESCRIPTION
            "An entry containing management information applicable to a
            particular physical Ethernet port."
    INDEX   { portIndex }
    ::= { ethernetPortTable 1 }


EthernetPortEntry ::=
    SEQUENCE {
        portIndex                 INTEGER,
        portDescr                 DisplayString,
	portOperStatus            INTEGER,
	portAdminStatus           INTEGER,
	portPseDetectionStatus    INTEGER,
	portPseClass              INTEGER,
	portPsePower              INTEGER,
    }

portIndex OBJECT-TYPE
    SYNTAX      INTEGER
    MAX-ACCESS  read-only
    STATUS      current
    DESCRIPTION
            "A unique value, starting at 1, for each physical Ethernet port.
             The value is expected to remain constant for a given port after
                reboot."
    ::= { ethernetPortEntry 1 }

portDescr OBJECT-TYPE
    SYNTAX      DisplayString (SIZE (0..255))
    MAX-ACCESS  read-only
    STATUS      current
    DESCRIPTION
            "A textual string containing information about the
		Ethernet port."
    ::= { ethernetPortEntry 2 }


portAdminStatus OBJECT-TYPE
    SYNTAX  INTEGER {
           up(1),
           down(2),
     }

    MAX-ACCESS  read-only
    STATUS      current
    DESCRIPTION
            "The current administrative status of the port."

    ::= { ethernetPortEntry 3 }


portOperStatus OBJECT-TYPE
    SYNTAX  INTEGER {
           up(1),        -- ready to pass packets
           down(2),
     }

    MAX-ACCESS  read-only
    STATUS      current
    DESCRIPTION
            "The current operational status of the port."

    ::= { ethernetPortEntry 4 }


portPseDetectionStatus OBJECT-TYPE
    SYNTAX INTEGER   {
             normal-device(1),
             legacy-device(2),
             powered-device(3),
             no-device(4),
             error-detected(5)
     }

    MAX-ACCESS read-only
    STATUS current
    DESCRIPTION
        "Describes the operational status of the port PD detection."
    ::= { ethernetPortEntry 5 }


portPseClass OBJECT-TYPE
    SYNTAX INTEGER   {
             CLASS-INVALID(-1),
             CLASS-UNKNOWN(0),
             CLASS-1(1),
             CLASS-2(2),
             CLASS-3(3),
             CLASS-4(4),
             CLASS-5(5),
             CLASS-6(6),
             CLASS-7(7),
             CLASS-8(8)
     }
    MAX-ACCESS read-only
    STATUS current
    DESCRIPTION
        "Describes the PSE class of the device."
    ::= { ethernetPortEntry 6 }

portPsePower OBJECT-TYPE
    SYNTAX INTEGER   {
             on(1),
             off(2)
     }
    MAX-ACCESS read-only
    STATUS current
    DESCRIPTION
        "On-off state of the PoE device."
    ::= { ethernetPortEntry 7 }

portDown NOTIFICATION-TYPE
    OBJECTS { portIndex, portDescr, portOperStatus, portAdminStatus }
    STATUS  current
    DESCRIPTION
            "A portDown trap indicates that the Ethernet port went down
             from the operational stage."
    ::= { ethernetPortTraps 1 }

portUp NOTIFICATION-TYPE
    OBJECTS { portIndex, portDescr, portOperStatus, portAdminStatus }
    STATUS  current
    DESCRIPTION
            "A portUp trap indicates that the Ethernet port came up and
                is in operational stage."
    ::= { ethernetPortTraps 2}

portPsePortStatusChangeNotification NOTIFICATION-TYPE
         OBJECTS     { portIndex, portDescr, portPseDetectionStatus,
                        portPsePower, portPseClass }
         STATUS      current
         DESCRIPTION
             "This trap indicates a change in status of PSE as indicated
                in the portPseDetectionStatus object."
    ::= { ethernetPortTraps 3 }

END
