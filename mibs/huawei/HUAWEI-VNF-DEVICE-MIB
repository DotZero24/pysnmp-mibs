-- ==================================================================
-- Copyright (C) 2021 by  HUAWEI TECHNOLOGIES. All rights reserved.
--
-- Description: HUAWEI-VNF-DEVICE-MIB
-- Reference:
-- Version: V1.08
-- History:
-- <author>,  <date>,  <contents>
-- zhouyun   2017-7-20
-- ==================================================================
-- ==================================================================
--
-- Variables and types are imported
--
-- ==================================================================

	HUAWEI-VNF-DEVICE-MIB DEFINITIONS ::= BEGIN

		IMPORTS
            hwPatchInstallFileName, hwPatchInstallVersion, hwPatchInstallFailReason
 				FROM HUAWEI-SYS-MAN-MIB
			hwDatacomm
				FROM HUAWEI-MIB
			OBJECT-GROUP, MODULE-COMPLIANCE, NOTIFICATION-GROUP
				FROM SNMPv2-CONF
			IpAddress, Integer32, Unsigned32, OBJECT-TYPE, MODULE-IDENTITY,
			NOTIFICATION-TYPE
				FROM SNMPv2-SMI;


		-- 1.3.6.1.4.1.2011.5.25.348
		hwVNFDevice MODULE-IDENTITY
			LAST-UPDATED "202108181139Z"		-- August 18, 2021 at 14:39 GMT
			ORGANIZATION
				"Huawei Technologies Co.,Ltd."
			CONTACT-INFO
				"Huawei Industrial Base
				Bantian, Longgang
				 Shenzhen 518129
				 People's Republic of China
				 Website: http://www.huawei.com
				 Email: support@huawei.com
				"
                        DESCRIPTION
				"V1.08, modify type of hwVMFaultAlarm and hwVMFaultAlarmResume."
			REVISION "202108181139Z"		-- August 18, 2021 at 14:39 GMT

			DESCRIPTION
				"V1.07, modify type of hwPAEDriverVendorID, hwPAEDriverDeviceID and hwPAEDriverCauseInfo."
			REVISION "201801121139Z"		-- January 12, 2018 at 11:39 GMT

			DESCRIPTION
				"V1.06, add hwVMPartitionTable, hwVMDiskPartitionInValidResume, hwVMDiskPartitionSpacinsufficient,hwVMDiskPartitionSpacinsufficientResume,hwVMDiskPartitionUtilizationRising, hwVMDiskPartitionUtilizationResume,."
			REVISION "201711291139Z"		-- November 29, 2017 at 11:39 GMT

			DESCRIPTION
				"V1.05, modify the hwVNFMPort size 0...65535."
			REVISION "201711031139Z"		-- November 03, 2017 at 11:39 GMT
			DESCRIPTION
				"V1.04, add hwSoftwarePackageTable,hwVmFileIntegrityTrap,hwSoftwareIntegrityTrap,hwPatchInstallVmTrap."
			REVISION  "201710251339Z"                     -- Octo 25, 2017 at 13:39 GMT

			DESCRIPTION
				"V1.03, modify the description of hwVMDiskTrap."
			REVISION  "201710231339Z"                     -- Octo 23, 2017 at 16:39 GMT

			DESCRIPTION
				"The MIB is used to define the VNF-related objects and notifications."
			REVISION "201710191339Z"	                  -- Octo 19, 2017 at 16:39 GMT
			DESCRIPTION
				"V1.02, add hwBaseLinkSubHealthyTrap, hwRUCreateTrap."
			REVISION "201709251339Z"	                  -- Sept 25, 2017 at 13:39 GMT
			DESCRIPTION
				"V1.01, add hwVMDiskTrap."
			REVISION "201707201339Z"		-- July 20, 2017 at 13:39 GMT
			DESCRIPTION
				"The initial revision of this MIB module ."


			::= { hwDatacomm 348 }



--
-- Node definitions
--

		-- 1.3.6.1.4.1.2011.5.25.348.1
		hwVNFDeviceMibObjects OBJECT IDENTIFIER ::= { hwVNFDevice 1 }


		-- 1.3.6.1.4.1.2011.5.25.348.1.1
		hwPAEPlaneTable OBJECT-TYPE
			SYNTAX SEQUENCE OF HwPAEPlaneEntry
			MAX-ACCESS not-accessible
			STATUS current
			DESCRIPTION
				"This table describes PAE fabric plane trap parameters."
			::= { hwVNFDeviceMibObjects 1 }


		-- 1.3.6.1.4.1.2011.5.25.348.1.1.1
		hwPAEPlaneEntry OBJECT-TYPE
			SYNTAX HwPAEPlaneEntry
			MAX-ACCESS not-accessible
			STATUS current
			DESCRIPTION
				"PAE fabric plane entry."
			INDEX { hwPAEPlaneVMName, hwPAEPlaneRemoteVMName, hwPAEPlanePlaneID }
			::= { hwPAEPlaneTable 1 }


		HwPAEPlaneEntry ::=
			SEQUENCE {
				hwPAEPlaneVMName
					OCTET STRING,
				hwPAEPlaneRemoteVMName
					OCTET STRING,
				hwPAEPlanePlaneID
					Integer32,
				hwPAEPlaneSubhealthyThreshold
					Integer32
			 }

		-- 1.3.6.1.4.1.2011.5.25.348.1.1.1.1
		hwPAEPlaneVMName OBJECT-TYPE
			SYNTAX OCTET STRING
			MAX-ACCESS accessible-for-notify
			STATUS current
			DESCRIPTION
				"Local VM name."
			::= { hwPAEPlaneEntry 1 }


		-- 1.3.6.1.4.1.2011.5.25.348.1.1.1.2
		hwPAEPlaneRemoteVMName OBJECT-TYPE
			SYNTAX OCTET STRING
			MAX-ACCESS accessible-for-notify
			STATUS current
			DESCRIPTION
				"Remote VM name."
			::= { hwPAEPlaneEntry 2 }


		-- 1.3.6.1.4.1.2011.5.25.348.1.1.1.3
		hwPAEPlanePlaneID OBJECT-TYPE
			SYNTAX Integer32 (0..256)
			MAX-ACCESS accessible-for-notify
			STATUS current
			DESCRIPTION
				"Plane ID."
			::= { hwPAEPlaneEntry 3 }


		-- 1.3.6.1.4.1.2011.5.25.348.1.1.1.4
		hwPAEPlaneSubhealthyThreshold OBJECT-TYPE
			SYNTAX Integer32
			MAX-ACCESS accessible-for-notify
			STATUS current
			DESCRIPTION
				"Threshold."
			::= { hwPAEPlaneEntry 4 }


		-- 1.3.6.1.4.1.2011.5.25.348.1.2
		hwPAEDriverTable OBJECT-TYPE
			SYNTAX SEQUENCE OF HwPAEDriverEntry
			MAX-ACCESS not-accessible
			STATUS current
			DESCRIPTION
				"This table describes PAE driver trap parameters."
			::= { hwVNFDeviceMibObjects 2 }


		-- 1.3.6.1.4.1.2011.5.25.348.1.2.1
		hwPAEDriverEntry OBJECT-TYPE
			SYNTAX HwPAEDriverEntry
			MAX-ACCESS not-accessible
			STATUS current
			DESCRIPTION
				"PAE driver entry."
			INDEX { hwPAEDriverVMName, hwPAEDriverVendorID, hwPAEDriverDeviceID }
			::= { hwPAEDriverTable 1 }


		HwPAEDriverEntry ::=
			SEQUENCE {
				hwPAEDriverVMName
					OCTET STRING,
				hwPAEDriverVendorID
					OCTET STRING,
				hwPAEDriverDeviceID
					OCTET STRING,
				hwPAEDriverCurDrvType
					INTEGER,
				hwPAEDriverCauseInfo
					INTEGER
			 }

		-- 1.3.6.1.4.1.2011.5.25.348.1.2.1.1
		hwPAEDriverVMName OBJECT-TYPE
			SYNTAX OCTET STRING
			MAX-ACCESS accessible-for-notify
			STATUS current
			DESCRIPTION
				"VM name."
			::= { hwPAEDriverEntry 1 }


		-- 1.3.6.1.4.1.2011.5.25.348.1.2.1.2
		hwPAEDriverVendorID OBJECT-TYPE
			SYNTAX OCTET STRING
			MAX-ACCESS accessible-for-notify
			STATUS current
			DESCRIPTION
				"The vNic's Vendor ID."
			::= { hwPAEDriverEntry 2 }


		-- 1.3.6.1.4.1.2011.5.25.348.1.2.1.3
		hwPAEDriverDeviceID OBJECT-TYPE
			SYNTAX OCTET STRING
			MAX-ACCESS accessible-for-notify
			STATUS current
			DESCRIPTION
				"The vNic's Device ID."
			::= { hwPAEDriverEntry 3 }


		-- 1.3.6.1.4.1.2011.5.25.348.1.2.1.4
		hwPAEDriverCurDrvType OBJECT-TYPE
			SYNTAX INTEGER
				{
				netmapService(0),
				pcap(1),
				pmd(2)
				}
			MAX-ACCESS accessible-for-notify
			STATUS current
			DESCRIPTION
				"Current driver type."
			::= { hwPAEDriverEntry 4 }


		-- 1.3.6.1.4.1.2011.5.25.348.1.2.1.5
		hwPAEDriverCauseInfo OBJECT-TYPE
			SYNTAX INTEGER
				{
				loadMultiDriver(1),
				noDefineInXML(2),
				notSupportDriver(3),
				wrongDriverType(4),
				notRecognizedVNic(5),
				invaild(6)
				}
			MAX-ACCESS accessible-for-notify
			STATUS current
			DESCRIPTION
				"Alarm reason."
			::= { hwPAEDriverEntry 5 }


		-- 1.3.6.1.4.1.2011.5.25.348.1.3
		hwVNFMConnectionTable OBJECT-TYPE
			SYNTAX SEQUENCE OF HwVNFMConnectionEntry
			MAX-ACCESS not-accessible
			STATUS current
			DESCRIPTION
				"This table describes the trap parameters of VNFM connections."
			::= { hwVNFDeviceMibObjects 3 }


		-- 1.3.6.1.4.1.2011.5.25.348.1.3.1
		hwVNFMConnectionEntry OBJECT-TYPE
			SYNTAX HwVNFMConnectionEntry
			MAX-ACCESS not-accessible
			STATUS current
			DESCRIPTION
				"VNFM connection entry."
			INDEX { hwVNFMIp, hwVNFMPort }
			::= { hwVNFMConnectionTable 1 }


		HwVNFMConnectionEntry ::=
			SEQUENCE {
				hwVNFMIp
					IpAddress,
				hwVNFMPort
					Unsigned32,
				hwVNFMFaultReason
					INTEGER
			 }

		-- 1.3.6.1.4.1.2011.5.25.348.1.3.1.1
		hwVNFMIp OBJECT-TYPE
			SYNTAX IpAddress
			MAX-ACCESS accessible-for-notify
			STATUS current
			DESCRIPTION
				"VNFM IP address."
			::= { hwVNFMConnectionEntry 1 }


		-- 1.3.6.1.4.1.2011.5.25.348.1.3.1.2
		hwVNFMPort OBJECT-TYPE
			SYNTAX Unsigned32 (0..65535)
			MAX-ACCESS accessible-for-notify
			STATUS current
			DESCRIPTION
				"VNFM interface number."
			::= { hwVNFMConnectionEntry 2 }


		-- 1.3.6.1.4.1.2011.5.25.348.1.3.1.3
		hwVNFMFaultReason OBJECT-TYPE
			SYNTAX INTEGER
				{
				connectionEstablishmentFailed(1),
				authenticationFailed(2)
				}
			MAX-ACCESS accessible-for-notify
			STATUS current
			DESCRIPTION
				"Fault reason."
			::= { hwVNFMConnectionEntry 3 }


		-- 1.3.6.1.4.1.2011.5.25.348.1.4
		hwVNFCTable OBJECT-TYPE
			SYNTAX SEQUENCE OF HwVNFCEntry
			MAX-ACCESS not-accessible
			STATUS current
			DESCRIPTION
				"VNFC information."
			::= { hwVNFDeviceMibObjects 4 }


		-- 1.3.6.1.4.1.2011.5.25.348.1.4.1
		hwVNFCEntry OBJECT-TYPE
			SYNTAX HwVNFCEntry
			MAX-ACCESS not-accessible
			STATUS current
			DESCRIPTION
				"VNFC entry."
			INDEX { hwVNFCName }
			::= { hwVNFCTable 1 }


		HwVNFCEntry ::=
			SEQUENCE {
				hwVNFCName
					OCTET STRING,
				hwVNFCType
					OCTET STRING
			 }

		-- 1.3.6.1.4.1.2011.5.25.348.1.4.1.1
		hwVNFCName OBJECT-TYPE
			SYNTAX OCTET STRING (SIZE (1..31))
			MAX-ACCESS accessible-for-notify
			STATUS current
			DESCRIPTION
				"VNFC name."
			::= { hwVNFCEntry 1 }


		-- 1.3.6.1.4.1.2011.5.25.348.1.4.1.2
		hwVNFCType OBJECT-TYPE
			SYNTAX OCTET STRING (SIZE (1..31))
			MAX-ACCESS accessible-for-notify
			STATUS current
			DESCRIPTION
				"VNFC type."
			::= { hwVNFCEntry 2 }


		-- 1.3.6.1.4.1.2011.5.25.348.1.5
		hwVMTable OBJECT-TYPE
			SYNTAX SEQUENCE OF HwVMEntry
			MAX-ACCESS not-accessible
			STATUS current
			DESCRIPTION
				"This table describes VM trap parameters."
			::= { hwVNFDeviceMibObjects 5 }


		-- 1.3.6.1.4.1.2011.5.25.348.1.5.1
		hwVMEntry OBJECT-TYPE
			SYNTAX HwVMEntry
			MAX-ACCESS not-accessible
			STATUS current
			DESCRIPTION
				"VM entry."
			INDEX { hwVMName }
			::= { hwVMTable 1 }


		HwVMEntry ::=
			SEQUENCE {
				hwVMName
					OCTET STRING,
				hwVMID
					OCTET STRING,
				hwPhyVMID
					OCTET STRING,
				hwVMInconsistFaultReason
					INTEGER,
				hwVMTypeName
					OCTET STRING,
				hwVMCPUUsageValue
					Integer32,
				hwVMCPUUsageThreshold
					Integer32,
				hwVMMemoryUsageValue
					Integer32,
				hwVMMemoryUsageThreshold
					Integer32
			 }

		-- 1.3.6.1.4.1.2011.5.25.348.1.5.1.1
		hwVMName OBJECT-TYPE
			SYNTAX OCTET STRING
			MAX-ACCESS accessible-for-notify
			STATUS current
			DESCRIPTION
				"VM name."
			::= { hwVMEntry 1 }


		-- 1.3.6.1.4.1.2011.5.25.348.1.5.1.2
		hwVMID OBJECT-TYPE
			SYNTAX OCTET STRING
			MAX-ACCESS accessible-for-notify
			STATUS current
			DESCRIPTION
				"MANO-layer VM ID."
			::= { hwVMEntry 2 }


		-- 1.3.6.1.4.1.2011.5.25.348.1.5.1.3
		hwPhyVMID OBJECT-TYPE
			SYNTAX OCTET STRING
			MAX-ACCESS accessible-for-notify
			STATUS current
			DESCRIPTION
				"Physical-layer VM ID."
			::= { hwVMEntry 3 }


		-- 1.3.6.1.4.1.2011.5.25.348.1.5.1.4
		hwVMInconsistFaultReason OBJECT-TYPE
			SYNTAX INTEGER
				{
				vmPowerOff(1),
				vmReset(2),
				iLayerVmFault(3),
				softwareLoseHeartBeat(4),
				registerFailed(5),
				notExistInVnf(2001),
				notExistInMano(2002),
				macAddrInconsistent(2003)
				}
			MAX-ACCESS accessible-for-notify
			STATUS current
			DESCRIPTION
				"Fault reason."
			::= { hwVMEntry 4 }


		-- 1.3.6.1.4.1.2011.5.25.348.1.5.1.5
		hwVMTypeName OBJECT-TYPE
			SYNTAX OCTET STRING
			MAX-ACCESS accessible-for-notify
			STATUS current
			DESCRIPTION
				"VM type."
			::= { hwVMEntry 5 }


		-- 1.3.6.1.4.1.2011.5.25.348.1.5.1.6
		hwVMCPUUsageValue OBJECT-TYPE
			SYNTAX Integer32
			MAX-ACCESS read-only
			STATUS current
			DESCRIPTION
				"The current value that been measured for the CPU."
			::= { hwVMEntry 6 }


		-- 1.3.6.1.4.1.2011.5.25.348.1.5.1.7
		hwVMCPUUsageThreshold OBJECT-TYPE
			SYNTAX Integer32
			MAX-ACCESS read-write
			STATUS current
			DESCRIPTION
				"The threshold of usage for the CPU."
			::= { hwVMEntry 7 }


		-- 1.3.6.1.4.1.2011.5.25.348.1.5.1.8
		hwVMMemoryUsageValue OBJECT-TYPE
			SYNTAX Integer32
			MAX-ACCESS read-only
			STATUS current
			DESCRIPTION
				"The current value that been measured for the memroy."
			::= { hwVMEntry 8 }


		-- 1.3.6.1.4.1.2011.5.25.348.1.5.1.9
		hwVMMemoryUsageThreshold OBJECT-TYPE
			SYNTAX Integer32
			MAX-ACCESS read-write
			STATUS current
			DESCRIPTION
				"The threshold of usage for the memroy."
			::= { hwVMEntry 9 }


		-- 1.3.6.1.4.1.2011.5.25.348.1.6
		hwVirtualPortTable OBJECT-TYPE
			SYNTAX SEQUENCE OF HwVirtualPortEntry
			MAX-ACCESS not-accessible
			STATUS current
			DESCRIPTION
				"This table describes the trap parameters of virtual interfaces."
			::= { hwVNFDeviceMibObjects 6 }


		-- 1.3.6.1.4.1.2011.5.25.348.1.6.1
		hwVirtualPortEntry OBJECT-TYPE
			SYNTAX HwVirtualPortEntry
			MAX-ACCESS not-accessible
			STATUS current
			DESCRIPTION
				"Virtual interface entry."
			INDEX { hwVMName, hwVirtualPortName }
			::= { hwVirtualPortTable 1 }


		HwVirtualPortEntry ::=
			SEQUENCE {
				hwVirtualPortName
					OCTET STRING
			 }

		-- 1.3.6.1.4.1.2011.5.25.348.1.6.1.1
		hwVirtualPortName OBJECT-TYPE
			SYNTAX OCTET STRING
			MAX-ACCESS accessible-for-notify
			STATUS current
			DESCRIPTION
				"Virtual interface name."
			::= { hwVirtualPortEntry 1 }

		-- 1.3.6.1.4.1.2011.5.25.348.1.7
		hwBaseLinkSubHealthyTable OBJECT-TYPE
			SYNTAX SEQUENCE OF HwBaseLinkSubHealthyEntry
			MAX-ACCESS not-accessible
			STATUS current
			DESCRIPTION
				"The table contains variables for base subhealth detection. At least one entry must exist."
			::= { hwVNFDeviceMibObjects 7 }

		-- 1.3.6.1.4.1.2011.5.25.348.1.7.1
		hwBaseLinkSubHealthyEntry OBJECT-TYPE
			SYNTAX HwBaseLinkSubHealthyEntry
			MAX-ACCESS not-accessible
			STATUS current
			DESCRIPTION
				"Information about a base link subhealth entity. Entities may be managed by this agent or other SNMP agents (possibly) in the same chassis."
			INDEX { hwBaseLinkVMName, hwBaseLinkRemoteVMName, hwBaseLinkPlaneID, hwBaseLinkQuality }
			::= { hwBaseLinkSubHealthyTable 1 }

		HwBaseLinkSubHealthyEntry ::=
			SEQUENCE {
				hwBaseLinkVMName
					OCTET STRING,
				hwBaseLinkRemoteVMName
					OCTET STRING,
				hwBaseLinkPlaneID
					Integer32,
				hwBaseLinkQuality
					Integer32
			 }

		-- 1.3.6.1.4.1.2011.5.25.348.1.7.1.1
		hwBaseLinkVMName OBJECT-TYPE
			SYNTAX OCTET STRING
			MAX-ACCESS accessible-for-notify
			STATUS current
			DESCRIPTION
				"This variable indicates the local VM name for the base link."
			::= { hwBaseLinkSubHealthyEntry 1 }

		-- 1.3.6.1.4.1.2011.5.25.348.1.7.1.2
		hwBaseLinkRemoteVMName OBJECT-TYPE
			SYNTAX OCTET STRING
			MAX-ACCESS accessible-for-notify
			STATUS current
			DESCRIPTION
				"This variable indicates the remote VM name for the base link."
			::= { hwBaseLinkSubHealthyEntry 2 }

		-- 1.3.6.1.4.1.2011.5.25.348.1.7.1.3
		hwBaseLinkPlaneID OBJECT-TYPE
			SYNTAX Integer32
			MAX-ACCESS accessible-for-notify
			STATUS current
			DESCRIPTION
				"This variable indicates which plane used in the base link detection."
			::= { hwBaseLinkSubHealthyEntry 3 }

		-- 1.3.6.1.4.1.2011.5.25.348.1.7.1.4
		hwBaseLinkQuality OBJECT-TYPE
			SYNTAX Integer32
			MAX-ACCESS accessible-for-notify
			STATUS current
			DESCRIPTION
				"This variable indicates the base link quality."
			::= { hwBaseLinkSubHealthyEntry 4 }

		-- 1.3.6.1.4.1.2011.5.25.348.1.8
		hwVNFDeviceTrapObjects OBJECT IDENTIFIER ::= { hwVNFDeviceMibObjects 8 }

		-- 1.3.6.1.4.1.2011.5.25.348.1.8.1
		hwRUName OBJECT-TYPE
			SYNTAX OCTET STRING
			MAX-ACCESS accessible-for-notify
			STATUS current
			DESCRIPTION
				"RU Name."
			::= { hwVNFDeviceTrapObjects 1 }

		-- 1.3.6.1.4.1.2011.5.25.348.1.8.2
		hwRUCreateFaultReason OBJECT-TYPE
			SYNTAX INTEGER
				{
				vmApplyforDiskFailed(1),
				vmRequestRpmFilesFailed(2),
				vmCreateVNFCWatchdogFailed(3)
				}
			MAX-ACCESS accessible-for-notify
			STATUS current
			DESCRIPTION
				"This variable indicates the reason for the failure to create RU. It has follow values:
				1. vmApplyforDiskFailed means VM failed to apply for a disk
				2. vmRequestRpmFilesFailed means VM failed to apply for an RPM file
				3. vmCreateVNFCWatchdogFailed means VM failed tp create VNFC watchdog"
			::= { hwVNFDeviceTrapObjects 2 }


		-- 1.3.6.1.4.1.2011.5.25.348.1.9
		hwSoftwarePackageTable OBJECT-TYPE
			SYNTAX SEQUENCE OF HwSoftwarePackageEntry
			MAX-ACCESS not-accessible
			STATUS current
			DESCRIPTION
				"This table describes software package trap parameters."
			::= { hwVNFDeviceMibObjects 9 }


		-- 1.3.6.1.4.1.2011.5.25.348.1.9.1
		hwSoftwarePackageEntry OBJECT-TYPE
			SYNTAX HwSoftwarePackageEntry
			MAX-ACCESS not-accessible
			STATUS current
			DESCRIPTION
				"Software package entry. Each entry consists of information of software package."
			INDEX { hwSoftwarePackageVNFCType, hwSoftwarePackageAppType, hwSoftwarePackageVersionType, hwSoftwarePackageVersionId }
			::= { hwSoftwarePackageTable 1 }


		HwSoftwarePackageEntry ::=
			SEQUENCE {
			    hwSoftwarePackageVNFCType
				    OCTET STRING,
				hwSoftwarePackageAppType
					OCTET STRING,
				hwSoftwarePackageVersionType
					OCTET STRING,
				hwSoftwarePackageVersionId
					OCTET STRING
			 }


		-- 1.3.6.1.4.1.2011.5.25.348.1.9.1.1
		hwSoftwarePackageVNFCType OBJECT-TYPE
			SYNTAX      OCTET STRING
			MAX-ACCESS  accessible-for-notify
			STATUS      current
			DESCRIPTION
			   "This object indicates the VNFC type of software package."
			   ::= { hwSoftwarePackageEntry 1 }


		-- 1.3.6.1.4.1.2011.5.25.348.1.9.1.2
		hwSoftwarePackageAppType OBJECT-TYPE
			SYNTAX      OCTET STRING
			MAX-ACCESS  accessible-for-notify
			STATUS      current
			DESCRIPTION
			   "This object indicates the App type of software package."
			   ::= { hwSoftwarePackageEntry 2 }


		-- 1.3.6.1.4.1.2011.5.25.348.1.9.1.3
		hwSoftwarePackageVersionType OBJECT-TYPE
			SYNTAX      OCTET STRING
			MAX-ACCESS  accessible-for-notify
			STATUS      current
			DESCRIPTION
			   "This object indicates the Version type of software package."
			   ::= { hwSoftwarePackageEntry 3 }

		-- 1.3.6.1.4.1.2011.5.25.348.1.9.1.4
		hwSoftwarePackageVersionId OBJECT-TYPE
			SYNTAX      OCTET STRING
			MAX-ACCESS  accessible-for-notify
			STATUS      current
			DESCRIPTION
			   "This object indicates the Version Id of software package."
			   ::= { hwSoftwarePackageEntry 4 }

		--1.3.6.1.4.1.2011.5.25.348.1.10
		hwVMPartitionTable OBJECT-TYPE
			SYNTAX SEQUENCE OF HwVMPartitionEntry
			MAX-ACCESS not-accessible
			STATUS current
			DESCRIPTION
				"This table describes disk partition information. Currently, it is only used for disk partition-related alarms.
Creation Restriction: No entry can be created in this table.
Modification Restriction: The entries in this table cannot be modified.
Deletion Restriction: The entries in this table cannot be deleted.
Access Restriction: The entries in this table cannot be accessed."
			::= { hwVNFDeviceMibObjects 10 }


		  --1.3.6.1.4.1.2011.5.25.348.1.10.1
		hwVMPartitionEntry OBJECT-TYPE
			SYNTAX HwVMPartitionEntry
			MAX-ACCESS not-accessible
			STATUS current
			DESCRIPTION
				"A device disk partition entry. Each entry consists of information of a device disk partition.
                                                                              hwVMName and hwVMPartitionName exclusively decide a device disk partition."
			INDEX { hwVMName, hwVMPartitionName}
			::= { hwVMPartitionTable 1 }


		HwVMPartitionEntry ::=
			SEQUENCE {
				hwVMPartitionName
					OCTET STRING,
				hwVMPartitionSpaceFree
					Integer32,
				hwVMPartitionSpaceFreeThreshold
					Integer32,
				hwVMPartitionUseage
					Integer32,
				hwVMPartitionUseageThreshold
					Integer32
			 }


			hwVMPartitionName OBJECT-TYPE
			SYNTAX OCTET STRING
			MAX-ACCESS accessible-for-notify
			STATUS current
			DESCRIPTION
				"This object indicates a disk partition name."
			::= { hwVMPartitionEntry 1 }


		hwVMPartitionSpaceFree OBJECT-TYPE
			SYNTAX Integer32
			MAX-ACCESS accessible-for-notify
			STATUS current
			DESCRIPTION
				"This object indicates the remaining disk partition space for the user, in MB."
			::= { hwVMPartitionEntry 2 }

		hwVMPartitionSpaceFreeThreshold OBJECT-TYPE
			SYNTAX Integer32
			MAX-ACCESS accessible-for-notify
			STATUS current
			DESCRIPTION
				"This object indicates the threshold for the remaining disk partition space for the user, in MB."
			::= { hwVMPartitionEntry 3 }

		hwVMPartitionUseage OBJECT-TYPE
			SYNTAX Integer32
			MAX-ACCESS accessible-for-notify
			STATUS current
			DESCRIPTION
				"This object indicates the current disk partition usage, in percentage."
			::= { hwVMPartitionEntry 4 }

		hwVMPartitionUseageThreshold OBJECT-TYPE
			SYNTAX Integer32
			MAX-ACCESS accessible-for-notify
			STATUS current
			DESCRIPTION
				"This object indicates the threshold for the disk partition usage, in percentage."
			::= { hwVMPartitionEntry 5 }

		-- 1.3.6.1.4.1.2011.5.25.348.2
		hwVNFDeviceNotifications OBJECT IDENTIFIER ::= { hwVNFDevice 2 }


		-- 1.3.6.1.4.1.2011.5.25.348.2.1
		hwFabricTrap OBJECT IDENTIFIER ::= { hwVNFDeviceNotifications 1 }


		-- 1.3.6.1.4.1.2011.5.25.348.2.1.1
		hwFabricPlaneDown NOTIFICATION-TYPE
			OBJECTS { hwPAEPlaneVMName, hwPAEPlaneRemoteVMName, hwPAEPlanePlaneID }
			STATUS current
			DESCRIPTION
				"Fabric plane goes Down."
			::= { hwFabricTrap 1 }


		-- 1.3.6.1.4.1.2011.5.25.348.2.1.2
		hwFabricPlaneUp NOTIFICATION-TYPE
			OBJECTS { hwPAEPlaneVMName, hwPAEPlaneRemoteVMName, hwPAEPlanePlaneID }
			STATUS current
			DESCRIPTION
				"Fabric plane down alarm was cleared."
			::= { hwFabricTrap 2 }


		-- 1.3.6.1.4.1.2011.5.25.348.2.1.3
		hwFabricPlaneSubhealthy NOTIFICATION-TYPE
			OBJECTS { hwPAEPlaneVMName, hwPAEPlaneRemoteVMName, hwPAEPlanePlaneID, hwPAEPlaneSubhealthyThreshold }
			STATUS current
			DESCRIPTION
				"Fabric link goes subhealthy."
			::= { hwFabricTrap 3 }


		-- 1.3.6.1.4.1.2011.5.25.348.2.1.4
		hwFabricPlaneSubhealthyResume NOTIFICATION-TYPE
			OBJECTS { hwPAEPlaneVMName, hwPAEPlaneRemoteVMName, hwPAEPlanePlaneID, hwPAEPlaneSubhealthyThreshold }
			STATUS current
			DESCRIPTION
				"Fabric link resume from subhealthy."
			::= { hwFabricTrap 4 }


		-- 1.3.6.1.4.1.2011.5.25.348.2.1.5
		hwFabricPortDriverMismatch NOTIFICATION-TYPE
			OBJECTS { hwPAEDriverVMName, hwPAEDriverVendorID, hwPAEDriverDeviceID, hwPAEDriverCurDrvType, hwPAEDriverCauseInfo
				 }
			STATUS current
			DESCRIPTION
				"Driver Type Mismatch."
			::= { hwFabricTrap 5 }


		-- 1.3.6.1.4.1.2011.5.25.348.2.2
		hwVNFCTrap OBJECT IDENTIFIER ::= { hwVNFDeviceNotifications 2 }


		-- 1.3.6.1.4.1.2011.5.25.348.2.2.1
		hwVnfcConnectionLost NOTIFICATION-TYPE
			OBJECTS { hwVNFCName }
			STATUS current
			DESCRIPTION
				"The connection between the VNFP and VNFC fails."
			::= { hwVNFCTrap 1 }


		-- 1.3.6.1.4.1.2011.5.25.348.2.2.2
		hwVnfcConnectionResume NOTIFICATION-TYPE
			OBJECTS { hwVNFCName }
			STATUS current
			DESCRIPTION
				"The connection between the VNFP and VNFC is restored."
			::= { hwVNFCTrap 2 }


		-- 1.3.6.1.4.1.2011.5.25.348.2.3
		hwVMResTrap OBJECT IDENTIFIER ::= { hwVNFDeviceNotifications 3 }


		-- 1.3.6.1.4.1.2011.5.25.348.2.3.1
		hwVMInconsist NOTIFICATION-TYPE
			OBJECTS { hwVMName, hwVMID, hwPhyVMID, hwVMInconsistFaultReason }
			STATUS current
			DESCRIPTION
				"Local VM resources are inconsistent with VM resources on the MANO."
			::= { hwVMResTrap 1 }


		-- 1.3.6.1.4.1.2011.5.25.348.2.3.2
		hwVMInconsistResume NOTIFICATION-TYPE
			OBJECTS { hwVMName, hwVMID, hwPhyVMID, hwVMInconsistFaultReason }
			STATUS current
			DESCRIPTION
				"Local VM resources are consistent with VM resources on the MANO."
			::= { hwVMResTrap 2 }


		-- 1.3.6.1.4.1.2011.5.25.348.2.3.3
		hwVMAdd NOTIFICATION-TYPE
			OBJECTS { hwVMName, hwVMTypeName }
			STATUS current
			DESCRIPTION
				"The VM was added."
			::= { hwVMResTrap 3 }


		-- 1.3.6.1.4.1.2011.5.25.348.2.3.4
		hwVMDelete NOTIFICATION-TYPE
			OBJECTS { hwVMName, hwVMTypeName }
			STATUS current
			DESCRIPTION
				"The VM was deleted."
			::= { hwVMResTrap 4 }


		-- 1.3.6.1.4.1.2011.5.25.348.2.3.5
		hwVMFaultAlarm NOTIFICATION-TYPE
			OBJECTS { hwVMName, hwVMID, hwPhyVMID, hwVMInconsistFaultReason }
			STATUS current
			DESCRIPTION
				"A fault occurs on a VM."
			::= { hwVMResTrap 5 }


		-- 1.3.6.1.4.1.2011.5.25.348.2.3.6
		hwVMFaultAlarmResume NOTIFICATION-TYPE
			OBJECTS { hwVMName, hwVMID, hwPhyVMID, hwVMInconsistFaultReason }
			STATUS current
			DESCRIPTION
				"The fault on the VM is cleared."
			::= { hwVMResTrap 6 }


		-- 1.3.6.1.4.1.2011.5.25.348.2.4
		hwVirtualPortTrap OBJECT IDENTIFIER ::= { hwVNFDeviceNotifications 4 }


		-- 1.3.6.1.4.1.2011.5.25.348.2.4.1
		hwVirtualPortDown NOTIFICATION-TYPE
			OBJECTS { hwVirtualPortName, hwVMName, hwVMID, hwPhyVMID }
			STATUS current
			DESCRIPTION
				"The virtual interface went Down."
			::= { hwVirtualPortTrap 1 }


		-- 1.3.6.1.4.1.2011.5.25.348.2.4.2
		hwVirtualPortDownResume NOTIFICATION-TYPE
			OBJECTS { hwVirtualPortName, hwVMName, hwVMID, hwPhyVMID }
			STATUS current
			DESCRIPTION
				"The virtual interface Down alarm was cleared."
			::= { hwVirtualPortTrap 2 }


		-- 1.3.6.1.4.1.2011.5.25.348.2.5
		hwVNFMConnectionTrap OBJECT IDENTIFIER ::= { hwVNFDeviceNotifications 5 }


		-- 1.3.6.1.4.1.2011.5.25.348.2.5.1
		hwVNFMConnectionFault NOTIFICATION-TYPE
			OBJECTS { hwVNFMIp, hwVNFMPort, hwVNFMFaultReason }
			STATUS current
			DESCRIPTION
				"The connection between the VNF and VNFM was faulty."
			::= { hwVNFMConnectionTrap 1 }


		-- 1.3.6.1.4.1.2011.5.25.348.2.5.2
		hwVNFMConnectionFaultResume NOTIFICATION-TYPE
			OBJECTS { hwVNFMIp, hwVNFMPort, hwVNFMFaultReason }
			STATUS current
			DESCRIPTION
				"The fault in the connection between the VNF and VNFM was rectified."
			::= { hwVNFMConnectionTrap 2 }


		-- 1.3.6.1.4.1.2011.5.25.348.2.6
		hwVMMemoryTrap OBJECT IDENTIFIER ::= { hwVNFDeviceNotifications 6 }


		-- 1.3.6.1.4.1.2011.5.25.348.2.6.1
		hwVMMemoryUsageRisingAlarm NOTIFICATION-TYPE
			OBJECTS { hwVMName, hwVMMemoryUsageValue, hwVMMemoryUsageThreshold }
			STATUS current
			DESCRIPTION
				"When the Memory usage remains greater than the Memory alarm threshold for a period of time, this alarm is generated."
			::= { hwVMMemoryTrap 1 }


		-- 1.3.6.1.4.1.2011.5.25.348.2.6.2
		hwVMMemoryUsageResume NOTIFICATION-TYPE
			OBJECTS { hwVMName, hwVMMemoryUsageValue, hwVMMemoryUsageThreshold }
			STATUS current
			DESCRIPTION
				"When the Memory usage remains less than the Memory alarm clearance threshold for a period of time, this alarm is cleared."
			::= { hwVMMemoryTrap 2 }


		-- 1.3.6.1.4.1.2011.5.25.348.2.7
		hwVMCPUTrap OBJECT IDENTIFIER ::= { hwVNFDeviceNotifications 7 }


		-- 1.3.6.1.4.1.2011.5.25.348.2.7.1
		hwVMCPUUsageRisingAlarm NOTIFICATION-TYPE
			OBJECTS { hwVMName, hwVMCPUUsageValue, hwVMCPUUsageThreshold }
			STATUS current
			DESCRIPTION
				"When the average CPU usage is greater than the CPU alarm threshold, this alarm is generated."
			::= { hwVMCPUTrap 1 }


		-- 1.3.6.1.4.1.2011.5.25.348.2.7.2
		hwVMCPUUsageResume NOTIFICATION-TYPE
			OBJECTS { hwVMName, hwVMCPUUsageValue, hwVMCPUUsageThreshold }
			STATUS current
			DESCRIPTION
				"When the average CPU usage is less than the CPU alarm clearance threshold, this alarm is cleared."
			::= { hwVMCPUTrap 2 }


		-- 1.3.6.1.4.1.2011.5.25.348.2.8
		hwVMDiskTrap OBJECT IDENTIFIER ::= { hwVNFDeviceNotifications 8 }

		hwVMDiskInvalid   NOTIFICATION-TYPE
			OBJECTS {hwVMName}
			STATUS current
			DESCRIPTION
				"This object indicates that an alarm is generated when a VM disk fails."
			::= { hwVMDiskTrap 1 }

		hwVMDiskInvalidResume   NOTIFICATION-TYPE
			OBJECTS {hwVMName}
			STATUS current
			DESCRIPTION
				"This object indicates that an alarm is cleared when a VM disk fault is rectified."
			::= { hwVMDiskTrap 2 }

		hwVMDiskPartitionInValid NOTIFICATION-TYPE
			OBJECTS {hwVMName, hwVMPartitionName }
			STATUS current
			DESCRIPTION
				"An alarm was generated when a disk partition was unavailable."
			::= { hwVMDiskTrap 3 }



		hwVMDiskPartitionInValidResume  NOTIFICATION-TYPE
			OBJECTS { hwVMName, hwVMPartitionName }
			STATUS current
			DESCRIPTION
				"The alarm was cleared when the disk partition became available."
			::= { hwVMDiskTrap 4 }


		hwVMDiskPartitionSpacinsufficient  NOTIFICATION-TYPE
			OBJECTS { hwVMName, hwVMPartitionName, hwVMPartitionSpaceFree, hwVMPartitionSpaceFreeThreshold }
			STATUS current
			DESCRIPTION
				"An alarm was generated when the disk partition's(except the log partition) available space was below the threshold."
			::= { hwVMDiskTrap 5}


		hwVMDiskPartitionSpacinsufficientResume  NOTIFICATION-TYPE
			OBJECTS {hwVMName, hwVMPartitionName, hwVMPartitionSpaceFree, hwVMPartitionSpaceFreeThreshold }
			STATUS current
			DESCRIPTION
				"The alarm was cleared when the disk partition's(except the log partition) available space was above the threshold."
			::= { hwVMDiskTrap 6 }


		hwVMDiskPartitionUseageRising  NOTIFICATION-TYPE
			OBJECTS {hwVMName, hwVMPartitionName, hwVMPartitionUseage, hwVMPartitionUseageThreshold }
			STATUS current
			DESCRIPTION
				"When the disk partition usage(except the log partition) is greater than the specified overload threshold within a statistical period, the alarm is reported."
			::= { hwVMDiskTrap 7 }


		hwVMDiskPartitionUseageResume   NOTIFICATION-TYPE
			OBJECTS {hwVMName, hwVMPartitionName, hwVMPartitionUseage, hwVMPartitionUseageThreshold }
			STATUS current
			DESCRIPTION
				"When the disk partition usage(except the log partition) fell and remained below 10% of the specified overload threshold within a statistical period, the alarm is cleared."
			::= { hwVMDiskTrap 8}

		-- 1.3.6.1.4.1.2011.5.25.348.2.9
		hwVmFileIntegrityTrap OBJECT IDENTIFIER ::= { hwVNFDeviceNotifications 9 }


		-- 1.3.6.1.4.1.2011.5.25.348.2.9.1
		hwFileIntegrityError NOTIFICATION-TYPE
			OBJECTS {hwVMName}
			STATUS current
			DESCRIPTION
				"Executable files are incomplete."
		   ::= { hwVmFileIntegrityTrap 1}


		-- 1.3.6.1.4.1.2011.5.25.348.2.9.2
		hwFileIntegrityErrorResume NOTIFICATION-TYPE
			OBJECTS {hwVMName}
			STATUS current
			DESCRIPTION
				"The file check success."
		   ::= { hwVmFileIntegrityTrap 2}



		-- 1.3.6.1.4.1.2011.5.25.348.2.10
		hwSoftwareIntegrityTrap OBJECT IDENTIFIER ::= { hwVNFDeviceNotifications 10 }


		-- 1.3.6.1.4.1.2011.5.25.348.2.10.1
		hwSoftwareIntegrityError NOTIFICATION-TYPE
			OBJECTS { hwSoftwarePackageVNFCType, hwSoftwarePackageAppType, hwSoftwarePackageVersionType, hwSoftwarePackageVersionId}
			STATUS current
			DESCRIPTION
				"The software check failed. "
		   ::= { hwSoftwareIntegrityTrap 1}


		-- 1.3.6.1.4.1.2011.5.25.348.2.10.2
		hwSoftwareIntegrityErrorResume NOTIFICATION-TYPE
			OBJECTS { hwSoftwarePackageVNFCType, hwSoftwarePackageAppType, hwSoftwarePackageVersionType, hwSoftwarePackageVersionId}
			STATUS current
			DESCRIPTION
				"The software check success. "
		   ::= { hwSoftwareIntegrityTrap 2}


		-- 1.3.6.1.4.1.2011.5.25.348.2.11
		hwPatchInstallVmTrap OBJECT IDENTIFIER ::= { hwVNFDeviceNotifications 11 }


		-- 1.3.6.1.4.1.2011.5.25.348.2.11.1
		hwPatchInstallFailVm NOTIFICATION-TYPE
		OBJECTS { hwVMName, hwPatchInstallFileName, hwPatchInstallVersion, hwPatchInstallFailReason }
			STATUS current
			DESCRIPTION
		"The patch package install fail notification."
			::= { hwPatchInstallVmTrap 1 }


		-- 1.3.6.1.4.1.2011.5.25.348.2.11.2
		hwPatchInstallFailVmClear NOTIFICATION-TYPE
		OBJECTS { hwVMName, hwPatchInstallFileName, hwPatchInstallVersion, hwPatchInstallFailReason }
			STATUS current
			DESCRIPTION
		"The patch package install fail clear notification."
			::= { hwPatchInstallVmTrap 2 }

		-- 1.3.6.1.4.1.2011.5.25.348.2.12
		hwBaseLinkSubHealthyTrap OBJECT IDENTIFIER ::= { hwVNFDeviceNotifications 12 }

		-- 1.3.6.1.4.1.2011.5.25.348.2.12.1
		hwBaseLinkSubHealthy NOTIFICATION-TYPE
			OBJECTS { hwBaseLinkVMName, hwBaseLinkRemoteVMName, hwBaseLinkPlaneID, hwBaseLinkQuality }
			STATUS current
			DESCRIPTION

				"The base plane link subhealth value was larger than the threshold, Base plane goes subhealth. The problem may cause a high packet loss rate."
			::= { hwBaseLinkSubHealthyTrap 1 }

		-- 1.3.6.1.4.1.2011.5.25.348.2.12.2
		hwBaseLinkSubHealthyResume NOTIFICATION-TYPE
			OBJECTS { hwBaseLinkVMName, hwBaseLinkRemoteVMName, hwBaseLinkPlaneID, hwBaseLinkQuality }
			STATUS current
			DESCRIPTION
				"The base plane link subhealth value was lower than the threshold. Base plane goes health."
			::= { hwBaseLinkSubHealthyTrap 2 }

		-- 1.3.6.1.4.1.2011.5.25.348.2.13
		hwRUCreateTrap OBJECT IDENTIFIER ::= { hwVNFDeviceNotifications 13 }

		-- 1.3.6.1.4.1.2011.5.25.348.2.13.1
		hwRUCreateFailAlarm NOTIFICATION-TYPE
			OBJECTS { hwVMName, hwVNFCName, hwRUName, hwRUCreateFaultReason }
			STATUS current
			DESCRIPTION
				"The VM create RU failed. And the RU can not work normal."
			::= { hwRUCreateTrap 1 }

		-- 1.3.6.1.4.1.2011.5.25.348.2.13.2
		hwRUCreateFailResume NOTIFICATION-TYPE
			OBJECTS { hwVMName, hwVNFCName, hwRUName, hwRUCreateFaultReason }
			STATUS current
			DESCRIPTION
				"The VM has created the RU."
			::= { hwRUCreateTrap 2 }


		-- 1.3.6.1.4.1.2011.5.25.348.3
		hwVNFDeviceConformance OBJECT IDENTIFIER ::= { hwVNFDevice 3 }


		-- 1.3.6.1.4.1.2011.5.25.348.3.1
		hwVNFDeviceCompliances OBJECT IDENTIFIER ::= { hwVNFDeviceConformance 1 }


		-- 1.3.6.1.4.1.2011.5.25.348.3.1.1
		hwVNFDeviceCompliance MODULE-COMPLIANCE
			STATUS current
			DESCRIPTION
				"The compliance statement for systems supporting
				the HUAWEI-VNF-DEVICE-MIB."
			MODULE -- this module
				MANDATORY-GROUPS { hwVNFDeviceNotificationGroup, hwVNFDeviceGroup }
			::= { hwVNFDeviceCompliances 1 }


		-- 1.3.6.1.4.1.2011.5.25.348.3.2
		hwVNFDeviceGroups OBJECT IDENTIFIER ::= { hwVNFDeviceConformance 2 }


		-- 1.3.6.1.4.1.2011.5.25.348.3.2.1
		hwVNFDeviceGroup OBJECT-GROUP
			OBJECTS { hwPAEPlaneVMName, hwPAEPlaneRemoteVMName, hwPAEPlanePlaneID, hwPAEPlaneSubhealthyThreshold, hwPAEDriverVMName,
				hwPAEDriverVendorID, hwPAEDriverDeviceID, hwPAEDriverCurDrvType, hwPAEDriverCauseInfo, hwVNFMIp,
				hwVNFMPort, hwVNFMFaultReason, hwVNFCName, hwVNFCType, hwVMInconsistFaultReason,
				hwVMID, hwVMName, hwPhyVMID, hwVMTypeName, hwVirtualPortName,
				hwVMCPUUsageValue, hwVMCPUUsageThreshold, hwVMMemoryUsageValue, hwVMMemoryUsageThreshold,
				hwBaseLinkVMName, hwBaseLinkRemoteVMName, hwBaseLinkPlaneID, hwBaseLinkQuality, hwRUName, hwRUCreateFaultReason }
			STATUS current
			DESCRIPTION
				"The VM's group."
			::= { hwVNFDeviceGroups 1 }


		-- 1.3.6.1.4.1.2011.5.25.348.3.2.2
		hwVNFDeviceNotificationGroup NOTIFICATION-GROUP
			NOTIFICATIONS { hwFabricPlaneDown, hwFabricPlaneUp, hwFabricPlaneSubhealthy, hwFabricPlaneSubhealthyResume, hwFabricPortDriverMismatch,
				hwVnfcConnectionLost, hwVnfcConnectionResume, hwVMInconsist, hwVMInconsistResume, hwVMAdd,
				hwVMDelete, hwVirtualPortDown, hwVirtualPortDownResume, hwVNFMConnectionFault, hwVNFMConnectionFaultResume,
				hwVMMemoryUsageRisingAlarm, hwVMMemoryUsageResume, hwVMCPUUsageRisingAlarm, hwVMCPUUsageResume,hwVMDiskInvalid,hwVMDiskInvalidResume, hwVMDiskPartitionInValid, hwVMDiskPartitionInValidResume, hwVMDiskPartitionSpacinsufficient,hwVMDiskPartitionSpacinsufficientResume,hwVMDiskPartitionUseageRising, hwVMDiskPartitionUseageResume,
				hwBaseLinkSubHealthy, hwBaseLinkSubHealthyResume, hwRUCreateFailAlarm, hwRUCreateFailResume,hwFileIntegrityError, hwFileIntegrityErrorResume, hwSoftwareIntegrityError, hwSoftwareIntegrityErrorResume, hwPatchInstallFailVm, hwPatchInstallFailVmClear }
			STATUS current
			DESCRIPTION
				"The notification group."
			::= { hwVNFDeviceGroups 2 }



	END

--
-- HUAWEI-VNF-DEVICE-MIB.mib
--
