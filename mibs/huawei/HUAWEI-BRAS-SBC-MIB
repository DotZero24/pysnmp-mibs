-- =================================================================
-- Copyright (C) 2002 by HUAWEI TECHNOLOGIES. All rights reserved
--
-- Description:
-- Reference:
-- Version: V1.00
-- History:
-- zhangyinxi, 2007-11-21, HUAWEI Bras sbc Configuration
-- =================================================================
    HUAWEI-BRAS-SBC-MIB DEFINITIONS ::= BEGIN

        IMPORTS
            entPhysicalIndex
                FROM ENTITY-MIB
            hwBRASMib
                FROM HUAWEI-MIB
            OBJECT-GROUP, MODULE-COMPLIANCE, NOTIFICATION-GROUP
                FROM SNMPv2-CONF
            TimeTicks, IpAddress, Integer32, Unsigned32, Counter32, Counter64,
            OBJECT-TYPE, MODULE-IDENTITY, NOTIFICATION-TYPE
                FROM SNMPv2-SMI
            DisplayString, TruthValue, RowStatus, DateAndTime, TEXTUAL-CONVENTION
                FROM SNMPv2-TC;

        hwBrasSbcMgmt MODULE-IDENTITY
            LAST-UPDATED "200711210900Z"
            ORGANIZATION
                "Huawei Technologies Co., Ltd."
            CONTACT-INFO
                "R&D BeiJing, Huawei Technologies co.,Ltd.
                Huawei Bld.,NO.3 Xinxi Rd.,
                Shang-Di Information Industry Base,
                Hai-Dian District Beijing P.R. China
                Zip:100085
                Http://www.huawei.com
                E-mail:support@huawei.com"
            DESCRIPTION
                "Session Border Controller Data Config."
            REVISION "200708140900Z"        -- August 14, 2007 at 09:00 GMT
            DESCRIPTION
                "Last revision."
            ::= { hwBRASMib 25 }

        HWBrasEnabledStatus ::= TEXTUAL-CONVENTION
            STATUS current
            DESCRIPTION
                "A simple status value for the object.
                1 enabled
                2 disabled"
            SYNTAX INTEGER
                {
                enabled(1),
                disabled(2)
                }

        HWBrasPermitStatus ::= TEXTUAL-CONVENTION
            STATUS current
            DESCRIPTION
                "A simple status value for the object."
            SYNTAX INTEGER
                {
                deny(1),
                permit(2)
                }

        HWBrasSecurityProtocol ::= TEXTUAL-CONVENTION
            STATUS current
            DESCRIPTION
                "Security protocol value for the object.
                1 sip
                2 mgcp
                3 h323
                4 signaling"
            SYNTAX INTEGER
                {
                sip(1),
                mgcp(2),
                h323(3),
                signaling(4)
                }

        HWBrasSbcBaseProtocol ::= TEXTUAL-CONVENTION
            STATUS current
            DESCRIPTION
                "Sbc base protocol value for the object.
                1 sip
                2 mgcp
                3 snmp
                4 ras
                5 upath
                6 h248
                7 ido
                8 q931"
            SYNTAX INTEGER
                {
                sip(1),
                mgcp(2),
                snmp(3),
                ras(4),
                upath(5),
                h248(6),
                ido(7),
                q931(8)
                }
        -- added by zhangyinxi --
        HwBrasAppMode ::= TEXTUAL-CONVENTION
            STATUS current
            DESCRIPTION
                "Sbc application mode.
                1 single domain mode
                2 multi domain mode"
            SYNTAX INTEGER
                {
                singleDomain(1),
                multiDomain(2)
                }
        --end added by zhangyinxi

        -- begin: gaochangbo on 20090202 --
        HwBrasBWLimitType ::= TEXTUAL-CONVENTION
            STATUS current
            DESCRIPTION
                "Sbc bandwidth limit type.
                1 bandwidth-limit type be
                2 bandwidth-limit type qos"
            SYNTAX INTEGER
                {
                be(1),
                qos(2)
                }
        -- end: gaochangbo on 20090202 --

        hwBrasSbcModule OBJECT IDENTIFIER ::= { hwBrasSbcMgmt 2 }

        hwBrasSbcObjects OBJECT IDENTIFIER ::= { hwBrasSbcModule 1 }

        hwBrasSbcGeneral OBJECT IDENTIFIER ::= { hwBrasSbcObjects 1 }

        hwBrasSbcBase OBJECT IDENTIFIER ::= { hwBrasSbcGeneral 1 }

        hwBrasSbcBaseLeaves OBJECT IDENTIFIER ::= { hwBrasSbcBase 1 }

        hwBrasSbcStatisticEnable OBJECT-TYPE
            SYNTAX HWBrasEnabledStatus
            MAX-ACCESS read-write
            STATUS current
            DESCRIPTION
                "Statistic Enable Status.
                Default: enabled"
            DEFVAL { enabled }
            ::= { hwBrasSbcBaseLeaves 1 }

        hwBrasSbcStatisticSyslogEnable OBJECT-TYPE
            SYNTAX HWBrasEnabledStatus
            MAX-ACCESS read-write
            STATUS current
            DESCRIPTION
                "Statistic Syslog Enable Status.
                Default: enabled"
            DEFVAL { enabled }
            ::= { hwBrasSbcBaseLeaves 2 }

        -- added by zhangyinxi --
        hwBrasSbcAppMode OBJECT-TYPE
            SYNTAX HwBrasAppMode
            MAX-ACCESS read-write
            STATUS current
            DESCRIPTION
                "Sbc application mode.
                Default: Multi-domain mode"
            DEFVAL { multi-domain }
            ::= { hwBrasSbcBaseLeaves 3 }
        -- end    added by zhangyinxi--

        -- added by gaochangbo on 2008-10-14 --
        hwBrasSbcMediaDetectValidityEnable OBJECT-TYPE
            SYNTAX HWBrasEnabledStatus
            MAX-ACCESS read-write
            STATUS current
            DESCRIPTION
                "Sbc media flow validity detect enable status.
                Default: disabled(2)"
            DEFVAL { disabled }
            ::= { hwBrasSbcBaseLeaves 4 }

        hwBrasSbcMediaDetectSsrcEnable OBJECT-TYPE
            SYNTAX HWBrasEnabledStatus
            MAX-ACCESS read-write
            STATUS current
            DESCRIPTION
                "Sbc media flow SSRC detect enable status.
                Default: disabled(2)"
            DEFVAL { disabled }
            ::= { hwBrasSbcBaseLeaves 5 }

        hwBrasSbcMediaDetectPacketLength OBJECT-TYPE
            SYNTAX Unsigned32 (28..65535)
            UNITS "byte"
            MAX-ACCESS read-write
            STATUS current
            DESCRIPTION
                "Sbc media packet length detect function.
                Range: 28-65535
                Default: 1500
                Unit: byte"
            DEFVAL { 1500 }
            ::= { hwBrasSbcBaseLeaves 6 }
        -- end of add by gaochangbo --

        hwBrasSbcBaseTables OBJECT IDENTIFIER ::= { hwBrasSbcBase 2 }

        hwBrasSbcSignalAddrMapTable OBJECT-TYPE
            SYNTAX SEQUENCE OF HwBrasSbcSignalAddrMapEntry
            MAX-ACCESS not-accessible
            STATUS current
            DESCRIPTION
                "Signal Address Map Table.
                obsolete"
            ::= { hwBrasSbcBaseTables 1 }

        hwBrasSbcSignalAddrMapEntry OBJECT-TYPE
            SYNTAX HwBrasSbcSignalAddrMapEntry
            MAX-ACCESS not-accessible
            STATUS current
            DESCRIPTION
                "Signal Address Map Table Entry."
            INDEX { hwBrasSbcSignalAddrMapClientAddr, hwBrasSbcSignalAddrMapServerAddr }
            ::= { hwBrasSbcSignalAddrMapTable 1 }

        HwBrasSbcSignalAddrMapEntry ::=
            SEQUENCE {
                hwBrasSbcSignalAddrMapClientAddr
                    IpAddress,
                hwBrasSbcSignalAddrMapServerAddr
                    IpAddress,
                hwBrasSbcSignalAddrMapSoftAddr
                    IpAddress,
                hwBrasSbcSignalAddrMapIadmsAddr
                    IpAddress,
                hwBrasSbcSignalAddrMapRowStatus
                    RowStatus
             }

        hwBrasSbcSignalAddrMapClientAddr OBJECT-TYPE
            SYNTAX IpAddress
            MAX-ACCESS not-accessible
            STATUS current
            DESCRIPTION
                "Signal Address Map Client Side IP Address."
            ::= { hwBrasSbcSignalAddrMapEntry 1 }

        hwBrasSbcSignalAddrMapServerAddr OBJECT-TYPE
            SYNTAX IpAddress
            MAX-ACCESS not-accessible
            STATUS current
            DESCRIPTION
                "Signal Address Map Server Side IP Address."
            ::= { hwBrasSbcSignalAddrMapEntry 2 }

        hwBrasSbcSignalAddrMapSoftAddr OBJECT-TYPE
            SYNTAX IpAddress
            MAX-ACCESS read-create
            STATUS current
            DESCRIPTION
                "Signal Address Map Softx IP Address."
            ::= { hwBrasSbcSignalAddrMapEntry 3 }

        hwBrasSbcSignalAddrMapIadmsAddr OBJECT-TYPE
            SYNTAX IpAddress
            MAX-ACCESS read-create
            STATUS current
            DESCRIPTION
                "Signal Address Map IADMS IP Address."
            ::= { hwBrasSbcSignalAddrMapEntry 4 }

        hwBrasSbcSignalAddrMapRowStatus OBJECT-TYPE
            SYNTAX RowStatus
            MAX-ACCESS read-create
            STATUS current
            DESCRIPTION
                "Signal Address Map Row Status."
            ::= { hwBrasSbcSignalAddrMapEntry 5 }

        hwBrasSbcMediaAddrMapTable OBJECT-TYPE
            SYNTAX SEQUENCE OF HwBrasSbcMediaAddrMapEntry
            MAX-ACCESS not-accessible
            STATUS current
            DESCRIPTION
                "Media Address Map Table.
                obsolete"
            ::= { hwBrasSbcBaseTables 2 }

        hwBrasSbcMediaAddrMapEntry OBJECT-TYPE
            SYNTAX HwBrasSbcMediaAddrMapEntry
            MAX-ACCESS not-accessible
            STATUS current
            DESCRIPTION
                "Media Address Map Table Entry."
            INDEX { hwBrasSbcMediaAddrMapClientAddr }
            ::= { hwBrasSbcMediaAddrMapTable 1 }

        HwBrasSbcMediaAddrMapEntry ::=
            SEQUENCE {
                hwBrasSbcMediaAddrMapClientAddr
                    IpAddress,
                hwBrasSbcMediaAddrMapServerAddr
                    IpAddress,
                hwBrasSbcMediaAddrMapWeight
                    Unsigned32,
                hwBrasSbcMediaAddrMapRowStatus
                    RowStatus
             }

        hwBrasSbcMediaAddrMapClientAddr OBJECT-TYPE
            SYNTAX IpAddress
            MAX-ACCESS not-accessible
            STATUS current
            DESCRIPTION
                "Media Address Map Client Side IP Address."
            ::= { hwBrasSbcMediaAddrMapEntry 1 }

        hwBrasSbcMediaAddrMapServerAddr OBJECT-TYPE
            SYNTAX IpAddress
            MAX-ACCESS read-create
            STATUS current
            DESCRIPTION
                "Media Address Map Server Side IP Address."
            ::= { hwBrasSbcMediaAddrMapEntry 2 }

        hwBrasSbcMediaAddrMapWeight OBJECT-TYPE
            SYNTAX Unsigned32 (10..100)
            MAX-ACCESS read-create
            STATUS current
            DESCRIPTION
                "Media Address Map Weight.
                Range: 10-100
                Default: 50
                Unit: NA"
            DEFVAL { 50 }
            ::= { hwBrasSbcMediaAddrMapEntry 3 }

        hwBrasSbcMediaAddrMapRowStatus OBJECT-TYPE
            SYNTAX RowStatus
            MAX-ACCESS read-create
            STATUS current
            DESCRIPTION
                "Media Address Map Row Status."
            ::= { hwBrasSbcMediaAddrMapEntry 4 }

        hwBrasSbcPortrangeTable OBJECT-TYPE
            SYNTAX SEQUENCE OF HwBrasSbcPortrangeEntry
            MAX-ACCESS not-accessible
            STATUS current
            DESCRIPTION
                "Port Range Table."
            ::= { hwBrasSbcBaseTables 3 }

        hwBrasSbcPortrangeEntry OBJECT-TYPE
            SYNTAX HwBrasSbcPortrangeEntry
            MAX-ACCESS not-accessible
            STATUS current
            DESCRIPTION
                "Port Range Table Entry."
            INDEX { hwBrasSbcPortrangeIndex }
            ::= { hwBrasSbcPortrangeTable 1 }

        HwBrasSbcPortrangeEntry ::=
            SEQUENCE {
                hwBrasSbcPortrangeIndex
                    INTEGER,
                hwBrasSbcPortrangeBegin
                    Unsigned32,
                hwBrasSbcPortrangeEnd
                    Unsigned32,
                hwBrasSbcPortrangeRowStatus
                    RowStatus
             }

        hwBrasSbcPortrangeIndex OBJECT-TYPE
            SYNTAX INTEGER
                {
                signal(1),
                media(2),
                nat(3),
                tcp(4),
                udp(5),
                mediacur(6)
                }
            MAX-ACCESS not-accessible
            STATUS current
            DESCRIPTION
                "Port Range Index.
                1: signal
                2: media
                3: nat
                4: tcp
                5: udp
                6: mediacur"
            ::= { hwBrasSbcPortrangeEntry 1 }

        hwBrasSbcPortrangeBegin OBJECT-TYPE
            SYNTAX Unsigned32 (10001..65535)
            MAX-ACCESS read-write
            STATUS current
            DESCRIPTION
                "Port Range Begin Port.
                Range: 10001-65535
                Default:
                signal and media: 10001
                nat: 50000"
            ::= { hwBrasSbcPortrangeEntry 2 }

        hwBrasSbcPortrangeEnd OBJECT-TYPE
            SYNTAX Unsigned32 (10001..65535)
            MAX-ACCESS read-write
            STATUS current
            DESCRIPTION
                "Port Range End Port.
                Range: 10001-65535
                Default:
                signal and media: 49999
                nat: 65535"
            ::= { hwBrasSbcPortrangeEntry 3 }

        hwBrasSbcPortrangeRowStatus OBJECT-TYPE
            SYNTAX RowStatus
            MAX-ACCESS read-write
            STATUS current
            DESCRIPTION
                "Port Range Row Status."
            ::= { hwBrasSbcPortrangeEntry 4 }

        hwBrasSbcStatMediaPacketTable OBJECT-TYPE
            SYNTAX SEQUENCE OF HwBrasSbcStatMediaPacketEntry
            MAX-ACCESS not-accessible
            STATUS current
            DESCRIPTION
                "Statistic of Media Packet Table."
            ::= { hwBrasSbcBaseTables 4 }

        hwBrasSbcStatMediaPacketEntry OBJECT-TYPE
            SYNTAX HwBrasSbcStatMediaPacketEntry
            MAX-ACCESS not-accessible
            STATUS current
            DESCRIPTION
                "Statistic of Media Packet Table Entry."
            INDEX { hwBrasSbcStatMediaPacketIndex }
            ::= { hwBrasSbcStatMediaPacketTable 1 }

        HwBrasSbcStatMediaPacketEntry ::=
            SEQUENCE {
                hwBrasSbcStatMediaPacketIndex
                    INTEGER,
                hwBrasSbcStatMediaPacketNumber
                    Counter64,
                hwBrasSbcStatMediaPacketOctet
                    Counter64,
                hwBrasSbcStatMediaPacketRowStatus
                    RowStatus
             }

        hwBrasSbcStatMediaPacketIndex OBJECT-TYPE
            SYNTAX INTEGER
                {
                rtp(1),
                rtcp(2)
                }
            MAX-ACCESS not-accessible
            STATUS current
            DESCRIPTION
                "Rtp or Rtcp.
                1: rtp
                2: rtcp"
            ::= { hwBrasSbcStatMediaPacketEntry 1 }

        hwBrasSbcStatMediaPacketNumber OBJECT-TYPE
            SYNTAX Counter64
            MAX-ACCESS read-only
            STATUS current
            DESCRIPTION
                "Packet Number."
            ::= { hwBrasSbcStatMediaPacketEntry 2 }

        hwBrasSbcStatMediaPacketOctet OBJECT-TYPE
            SYNTAX Counter64
            MAX-ACCESS read-only
            STATUS current
            DESCRIPTION
                "Packet Octet."
            ::= { hwBrasSbcStatMediaPacketEntry 3 }

        hwBrasSbcStatMediaPacketRowStatus OBJECT-TYPE
            SYNTAX RowStatus
            MAX-ACCESS read-write
            STATUS current
            DESCRIPTION
                "Row Status."
            ::= { hwBrasSbcStatMediaPacketEntry 4 }

        hwBrasSbcClientPortTable OBJECT-TYPE
            SYNTAX SEQUENCE OF HwBrasSbcClientPortEntry
            MAX-ACCESS not-accessible
            STATUS current
            DESCRIPTION
                "Client wellknown port table."
            ::= { hwBrasSbcBaseTables 5 }

        hwBrasSbcClientPortEntry OBJECT-TYPE
            SYNTAX HwBrasSbcClientPortEntry
            MAX-ACCESS not-accessible
            STATUS current
            DESCRIPTION
                "Client wellknown port entry."
            INDEX { hwBrasSbcClientPortProtocol, hwBrasSbcClientPortVPN, hwBrasSbcClientPortIP }
            ::= { hwBrasSbcClientPortTable 1 }

        HwBrasSbcClientPortEntry ::=
            SEQUENCE {
                hwBrasSbcClientPortProtocol
                    INTEGER,
                hwBrasSbcClientPortVPN
                    Unsigned32,
                hwBrasSbcClientPortIP
                    IpAddress,
                hwBrasSbcClientPortPort01
                    Unsigned32,
                hwBrasSbcClientPortPort02
                    Unsigned32,
                hwBrasSbcClientPortPort03
                    Unsigned32,
                hwBrasSbcClientPortPort04
                    Unsigned32,
                hwBrasSbcClientPortPort05
                    Unsigned32,
                hwBrasSbcClientPortPort06
                    Unsigned32,
                hwBrasSbcClientPortPort07
                    Unsigned32,
                hwBrasSbcClientPortPort08
                    Unsigned32,
                hwBrasSbcClientPortPort09
                    Unsigned32,
                hwBrasSbcClientPortPort10
                    Unsigned32,
                hwBrasSbcClientPortPort11
                    Unsigned32,
                hwBrasSbcClientPortPort12
                    Unsigned32,
                hwBrasSbcClientPortPort13
                    Unsigned32,
                hwBrasSbcClientPortPort14
                    Unsigned32,
                hwBrasSbcClientPortPort15
                    Unsigned32,
                hwBrasSbcClientPortPort16
                    Unsigned32,
                hwBrasSbcClientPortRowStatus
                    RowStatus
             }

        hwBrasSbcClientPortProtocol OBJECT-TYPE
            SYNTAX INTEGER
                {
                sip(1),
                mgcp(2),
                snmp(3),
                ras(4),
                upath(5),
                h248(6),
                ido(7)
                }
            MAX-ACCESS not-accessible
            STATUS current
            DESCRIPTION
                "Protocol.
                Base on HWBrasSbcBaseProtocol."
            ::= { hwBrasSbcClientPortEntry 1 }

        hwBrasSbcClientPortVPN OBJECT-TYPE
            SYNTAX Unsigned32 (0..1023)
            MAX-ACCESS not-accessible
            STATUS current
            DESCRIPTION
                "Vpn-instance Index"
            ::= { hwBrasSbcClientPortEntry 2 }

        hwBrasSbcClientPortIP OBJECT-TYPE
            SYNTAX IpAddress
            MAX-ACCESS not-accessible
            STATUS current
            DESCRIPTION
                "Client Address."
            ::= { hwBrasSbcClientPortEntry 3 }

        hwBrasSbcClientPortPort01 OBJECT-TYPE
            SYNTAX Unsigned32 (0..10000)
            MAX-ACCESS read-create
            STATUS current
            DESCRIPTION
                "Client Wellknown Port."
            ::= { hwBrasSbcClientPortEntry 11 }

        hwBrasSbcClientPortPort02 OBJECT-TYPE
            SYNTAX Unsigned32 (0..10000)
            MAX-ACCESS read-create
            STATUS current
            DESCRIPTION
                "Client Wellknown Port."
            ::= { hwBrasSbcClientPortEntry 12 }

        hwBrasSbcClientPortPort03 OBJECT-TYPE
            SYNTAX Unsigned32 (0..10000)
            MAX-ACCESS read-create
            STATUS current
            DESCRIPTION
                "Client Wellknown Port."
            ::= { hwBrasSbcClientPortEntry 13 }

        hwBrasSbcClientPortPort04 OBJECT-TYPE
            SYNTAX Unsigned32 (0..10000)
            MAX-ACCESS read-create
            STATUS current
            DESCRIPTION
                "Client Wellknown Port."
            ::= { hwBrasSbcClientPortEntry 14 }

        hwBrasSbcClientPortPort05 OBJECT-TYPE
            SYNTAX Unsigned32 (0..10000)
            MAX-ACCESS read-create
            STATUS current
            DESCRIPTION
                "Client Wellknown Port."
            ::= { hwBrasSbcClientPortEntry 15 }

        hwBrasSbcClientPortPort06 OBJECT-TYPE
            SYNTAX Unsigned32 (0..10000)
            MAX-ACCESS read-create
            STATUS current
            DESCRIPTION
                "Client Wellknown Port."
            ::= { hwBrasSbcClientPortEntry 16 }

        hwBrasSbcClientPortPort07 OBJECT-TYPE
            SYNTAX Unsigned32 (0..10000)
            MAX-ACCESS read-create
            STATUS current
            DESCRIPTION
                "Client Wellknown Port."
            ::= { hwBrasSbcClientPortEntry 17 }

        hwBrasSbcClientPortPort08 OBJECT-TYPE
            SYNTAX Unsigned32 (0..10000)
            MAX-ACCESS read-create
            STATUS current
            DESCRIPTION
                "Client Wellknown Port."
            ::= { hwBrasSbcClientPortEntry 18 }

        hwBrasSbcClientPortPort09 OBJECT-TYPE
            SYNTAX Unsigned32 (0..10000)
            MAX-ACCESS read-create
            STATUS current
            DESCRIPTION
                "Client Wellknown Port."
            ::= { hwBrasSbcClientPortEntry 19 }

        hwBrasSbcClientPortPort10 OBJECT-TYPE
            SYNTAX Unsigned32 (0..10000)
            MAX-ACCESS read-create
            STATUS current
            DESCRIPTION
                "Client Wellknown Port."
            ::= { hwBrasSbcClientPortEntry 20 }

        hwBrasSbcClientPortPort11 OBJECT-TYPE
            SYNTAX Unsigned32 (0..10000)
            MAX-ACCESS read-create
            STATUS current
            DESCRIPTION
                "Client Wellknown Port."
            ::= { hwBrasSbcClientPortEntry 21 }

        hwBrasSbcClientPortPort12 OBJECT-TYPE
            SYNTAX Unsigned32 (0..10000)
            MAX-ACCESS read-create
            STATUS current
            DESCRIPTION
                "Client Wellknown Port."
            ::= { hwBrasSbcClientPortEntry 22 }

        hwBrasSbcClientPortPort13 OBJECT-TYPE
            SYNTAX Unsigned32 (0..10000)
            MAX-ACCESS read-create
            STATUS current
            DESCRIPTION
                "Client Wellknown Port."
            ::= { hwBrasSbcClientPortEntry 23 }

        hwBrasSbcClientPortPort14 OBJECT-TYPE
            SYNTAX Unsigned32 (0..10000)
            MAX-ACCESS read-create
            STATUS current
            DESCRIPTION
                "Client Wellknown Port."
            ::= { hwBrasSbcClientPortEntry 24 }

        hwBrasSbcClientPortPort15 OBJECT-TYPE
            SYNTAX Unsigned32 (0..10000)
            MAX-ACCESS read-create
            STATUS current
            DESCRIPTION
                "Client Wellknown Port."
            ::= { hwBrasSbcClientPortEntry 25 }

        hwBrasSbcClientPortPort16 OBJECT-TYPE
            SYNTAX Unsigned32 (0..10000)
            MAX-ACCESS read-create
            STATUS current
            DESCRIPTION
                "Client Wellknown Port."
            ::= { hwBrasSbcClientPortEntry 26 }

        hwBrasSbcClientPortRowStatus OBJECT-TYPE
            SYNTAX RowStatus
            MAX-ACCESS read-create
            STATUS current
            DESCRIPTION
                "Row Status."
            ::= { hwBrasSbcClientPortEntry 51 }

        hwBrasSbcSoftswitchPortTable OBJECT-TYPE
            SYNTAX SEQUENCE OF HwBrasSbcSoftswitchPortEntry
            MAX-ACCESS not-accessible
            STATUS current
            DESCRIPTION
                "Softswitch wellknown port table."
            ::= { hwBrasSbcBaseTables 6 }

        hwBrasSbcSoftswitchPortEntry OBJECT-TYPE
            SYNTAX HwBrasSbcSoftswitchPortEntry
            MAX-ACCESS not-accessible
            STATUS current
            DESCRIPTION
                "Softswitch wellknown port entry."
            INDEX { hwBrasSbcSoftswitchPortProtocol, hwBrasSbcSoftswitchPortVPN, hwBrasSbcSoftswitchPortIP }
            ::= { hwBrasSbcSoftswitchPortTable 1 }

        HwBrasSbcSoftswitchPortEntry ::=
            SEQUENCE {
                hwBrasSbcSoftswitchPortProtocol
                    INTEGER,
                hwBrasSbcSoftswitchPortVPN
                    Unsigned32,
                hwBrasSbcSoftswitchPortIP
                    IpAddress,
                hwBrasSbcSoftswitchPortPort
                    Unsigned32,
                hwBrasSbcSoftswitchPortRowStatus
                    RowStatus
             }

        hwBrasSbcSoftswitchPortProtocol OBJECT-TYPE
            SYNTAX INTEGER
                {
                sip(1),
                mgcp(2),
                ras(4),
                upath(5),
                h248(6),
                ido(7),
                q931(8)
                }
            MAX-ACCESS not-accessible
            STATUS current
            DESCRIPTION
                "Protocol.
                Base on HWBrasSbcBaseProtocol."
            ::= { hwBrasSbcSoftswitchPortEntry 1 }

        hwBrasSbcSoftswitchPortVPN OBJECT-TYPE
            SYNTAX Unsigned32 (0..1023)
            MAX-ACCESS not-accessible
            STATUS current
            DESCRIPTION
                "Vpn-instance Index."
            ::= { hwBrasSbcSoftswitchPortEntry 2 }

        hwBrasSbcSoftswitchPortIP OBJECT-TYPE
            SYNTAX IpAddress
            MAX-ACCESS not-accessible
            STATUS current
            DESCRIPTION
                "Softswitch Address."
            ::= { hwBrasSbcSoftswitchPortEntry 3 }

        hwBrasSbcSoftswitchPortPort OBJECT-TYPE
            SYNTAX Unsigned32 (1..65535)
            MAX-ACCESS read-create
            STATUS current
            DESCRIPTION
                "Softswitch Wellknown Port."
            ::= { hwBrasSbcSoftswitchPortEntry 11 }

        hwBrasSbcSoftswitchPortRowStatus OBJECT-TYPE
            SYNTAX RowStatus
            MAX-ACCESS read-create
            STATUS current
            DESCRIPTION
                "Row Status."
            ::= { hwBrasSbcSoftswitchPortEntry 51 }

        hwBrasSbcIadmsPortTable OBJECT-TYPE
            SYNTAX SEQUENCE OF HwBrasSbcIadmsPortEntry
            MAX-ACCESS not-accessible
            STATUS current
            DESCRIPTION
                "Iadms wellknown port table."
            ::= { hwBrasSbcBaseTables 7 }

        hwBrasSbcIadmsPortEntry OBJECT-TYPE
            SYNTAX HwBrasSbcIadmsPortEntry
            MAX-ACCESS not-accessible
            STATUS current
            DESCRIPTION
                "Iadms wellknown port entry."
            INDEX { hwBrasSbcIadmsPortProtocol, hwBrasSbcIadmsPortVPN, hwBrasSbcIadmsPortIP }
            ::= { hwBrasSbcIadmsPortTable 1 }

        HwBrasSbcIadmsPortEntry ::=
            SEQUENCE {
                hwBrasSbcIadmsPortProtocol
                    INTEGER,
                hwBrasSbcIadmsPortVPN
                    Unsigned32,
                hwBrasSbcIadmsPortIP
                    IpAddress,
                hwBrasSbcIadmsPortPort
                    Unsigned32,
                hwBrasSbcIadmsPortRowStatus
                    RowStatus
             }

        hwBrasSbcIadmsPortProtocol OBJECT-TYPE
            SYNTAX INTEGER { snmp(3) }
            MAX-ACCESS not-accessible
            STATUS current
            DESCRIPTION
                "Protocol.
                Base on HWBrasSbcBaseProtocol."
            ::= { hwBrasSbcIadmsPortEntry 1 }

        hwBrasSbcIadmsPortVPN OBJECT-TYPE
            SYNTAX Unsigned32 (0..1023)
            MAX-ACCESS not-accessible
            STATUS current
            DESCRIPTION
                "Vpn-instance Index."
            ::= { hwBrasSbcIadmsPortEntry 2 }

        hwBrasSbcIadmsPortIP OBJECT-TYPE
            SYNTAX IpAddress
            MAX-ACCESS not-accessible
            STATUS current
            DESCRIPTION
                "Iadms Address."
            ::= { hwBrasSbcIadmsPortEntry 3 }

        hwBrasSbcIadmsPortPort OBJECT-TYPE
            SYNTAX Unsigned32 (1..65535)
            MAX-ACCESS read-create
            STATUS current
            DESCRIPTION
                "Iadms Wellknown Port."
            ::= { hwBrasSbcIadmsPortEntry 11 }

        hwBrasSbcIadmsPortRowStatus OBJECT-TYPE
            SYNTAX RowStatus
            MAX-ACCESS read-create
            STATUS current
            DESCRIPTION
                "Row Status."
            ::= { hwBrasSbcIadmsPortEntry 51 }

    --add zhangyinxi 2008-3-5 for DT SBC II
                hwBrasSbcInstanceTable OBJECT-TYPE
                        SYNTAX SEQUENCE OF HwBrasSbcInstanceEntry
                        MAX-ACCESS not-accessible
                        STATUS current
                        DESCRIPTION
                                "SBC instance table."
                        ::= { hwBrasSbcBaseTables 8 }

                hwBrasSbcInstanceEntry OBJECT-TYPE
                        SYNTAX HwBrasSbcInstanceEntry
                        MAX-ACCESS not-accessible
                        STATUS current
                        DESCRIPTION
                                "SBC instance entry."
                        INDEX { hwBrasSbcInstanceName }
                        ::= { hwBrasSbcInstanceTable 1 }

                HwBrasSbcInstanceEntry ::=
                        SEQUENCE {
                                hwBrasSbcInstanceName
                                        DisplayString,
                                hwBrasSbcInstanceRowStatus
                                        RowStatus
                         }

                hwBrasSbcInstanceName OBJECT-TYPE
                        SYNTAX DisplayString (SIZE (1..32))
                        MAX-ACCESS read-only
                        STATUS current
                        DESCRIPTION
                                "the name of the sbc instance."
                        ::= { hwBrasSbcInstanceEntry 1 }

                hwBrasSbcInstanceRowStatus OBJECT-TYPE
                        SYNTAX RowStatus
                        MAX-ACCESS read-create
                        STATUS current
                        DESCRIPTION
                                "Row Status."
                        ::= { hwBrasSbcInstanceEntry 51 }
    --end add zhangyinxi 2008-3-5 for DT SBC II

        hwBrasSbcMapGroup OBJECT IDENTIFIER ::= { hwBrasSbcBase 3 }

        hwBrasSbcMapGroupLeaves OBJECT IDENTIFIER ::= { hwBrasSbcMapGroup 1 }

        hwBrasSbcMapGroupTables OBJECT IDENTIFIER ::= { hwBrasSbcMapGroup 2 }

        hwBrasSbcMapGroupsTable OBJECT-TYPE
            SYNTAX SEQUENCE OF HwBrasSbcMapGroupsEntry
            MAX-ACCESS not-accessible
            STATUS current
            DESCRIPTION
                "Map Groups.
                This table for create or delete map groups.
                When you create the index, the groups' status must be disabled.
                The groups' type for index:
                  index      type
                   1-1000      1
                1001-2000      2
                2001-2500      3
                2501-2999      4
                If type don't match index, set will be failed!"
            ::= { hwBrasSbcMapGroupTables 1 }

        hwBrasSbcMapGroupsEntry OBJECT-TYPE
            SYNTAX HwBrasSbcMapGroupsEntry
            MAX-ACCESS not-accessible
            STATUS current
            DESCRIPTION
                "Map Groups entry."
            INDEX { hwBrasSbcMapGroupsIndex }
            ::= { hwBrasSbcMapGroupsTable 1 }

        HwBrasSbcMapGroupsEntry ::=
            SEQUENCE {
                hwBrasSbcMapGroupsIndex
                    Unsigned32,
                hwBrasSbcMapGroupsType
                    INTEGER,
                hwBrasSbcMapGroupsStatus
                    HWBrasEnabledStatus,
                hwBrasSbcMapGroupInstanceName
                    DisplayString,
-- add by gaochangbo on 20081013 --
                hwBrasSbcMapGroupSessionLimit
                    Unsigned32,
-- end of add by gaochangbo --
                hwBrasSbcMapGroupsRowStatus
                    RowStatus
             }

        hwBrasSbcMapGroupsIndex OBJECT-TYPE
            SYNTAX Unsigned32 (1..2999)
            MAX-ACCESS not-accessible
            STATUS current
            DESCRIPTION
                "Map Group's Index.
                proxy         : 1...1000
                intercomIP    : 1001...2000
                IntercomPrefix: 2001...2500
                bgf           : 2501...2999"
            ::= { hwBrasSbcMapGroupsEntry 1 }

        hwBrasSbcMapGroupsType OBJECT-TYPE
            SYNTAX INTEGER
                {
                proxy(1),
                intercomIP(2),
                intercomPrefix(3),
                bgf(4)
                }
            MAX-ACCESS read-create
            STATUS current
            DESCRIPTION
                "Map Group's Type.
                proxy         : 1...1000
                intercomIP    : 1001...2000
                IntercomPrefix: 2001...2500
                bgf           : 2501...2999"
            ::= { hwBrasSbcMapGroupsEntry 11 }

        hwBrasSbcMapGroupsStatus OBJECT-TYPE
            SYNTAX HWBrasEnabledStatus
            MAX-ACCESS read-create
            STATUS current
            DESCRIPTION
                "Map Group's Enable Status.
                default: disabled"
            DEFVAL { disabled }
            ::= { hwBrasSbcMapGroupsEntry 12 }

        hwBrasSbcMapGroupInstanceName OBJECT-TYPE
            SYNTAX DisplayString (SIZE (1..32))
            MAX-ACCESS read-create
            STATUS current
            DESCRIPTION
                "SBC instance which the mapgroup belongs to "
            ::= { hwBrasSbcMapGroupsEntry 13 }

-- add by gaochangbo on 20081013 --
        hwBrasSbcMapGroupSessionLimit OBJECT-TYPE
            SYNTAX Unsigned32 (1..40000)
            MAX-ACCESS read-create
            STATUS current
            DESCRIPTION
                "Map Group's maximum session count.
                Range: 1-40000
                Default: 40000"
            DEFVAL { 40000 }
            ::= { hwBrasSbcMapGroupsEntry 14 }
-- end of add by gaochangbo --

        hwBrasSbcMapGroupsRowStatus OBJECT-TYPE
            SYNTAX RowStatus
            MAX-ACCESS read-create
            STATUS current
            DESCRIPTION
                "Row status."
            ::= { hwBrasSbcMapGroupsEntry 51 }

        hwBrasSbcMGCliAddrTable OBJECT-TYPE
            SYNTAX SEQUENCE OF HwBrasSbcMGCliAddrEntry
            MAX-ACCESS not-accessible
            STATUS current
            DESCRIPTION
                "Map Groups' Client Address.
                Support map group index: 1..2000
                "
            ::= { hwBrasSbcMapGroupTables 2 }

        hwBrasSbcMGCliAddrEntry OBJECT-TYPE
            SYNTAX HwBrasSbcMGCliAddrEntry
            MAX-ACCESS not-accessible
            STATUS current
            DESCRIPTION
                "Map Groups' client address entry."
            INDEX { hwBrasSbcMGCliAddrIndex }
            ::= { hwBrasSbcMGCliAddrTable 1 }

        HwBrasSbcMGCliAddrEntry ::=
            SEQUENCE {
                hwBrasSbcMGCliAddrIndex
                    Unsigned32,
                hwBrasSbcMGCliAddrVPN
                    Unsigned32,
                hwBrasSbcMGCliAddrIP
                    IpAddress,
                hwBrasSbcMGCliAddrRowStatus
                    RowStatus
             }

        hwBrasSbcMGCliAddrIndex OBJECT-TYPE
            SYNTAX Unsigned32 (1..2999)
            MAX-ACCESS not-accessible
            STATUS current
            DESCRIPTION
                "Map Group's Index.
                Support map group index: 1..2000"
            ::= { hwBrasSbcMGCliAddrEntry 1 }

        hwBrasSbcMGCliAddrVPN OBJECT-TYPE
            SYNTAX Unsigned32 (0..1023)
            MAX-ACCESS read-create
            STATUS current
            DESCRIPTION
                "VPN Index.
                range:
                SE2200==>0~255
                SE2300==>0~1023"
            DEFVAL { 0 }
            ::= { hwBrasSbcMGCliAddrEntry 11 }

        hwBrasSbcMGCliAddrIP OBJECT-TYPE
            SYNTAX IpAddress
            MAX-ACCESS read-create
            STATUS current
            DESCRIPTION
                "Client Address."
            ::= { hwBrasSbcMGCliAddrEntry 12 }

        hwBrasSbcMGCliAddrRowStatus OBJECT-TYPE
            SYNTAX RowStatus
            MAX-ACCESS read-create
            STATUS current
            DESCRIPTION
                "Row stauts."
            ::= { hwBrasSbcMGCliAddrEntry 51 }

        hwBrasSbcMGServAddrTable OBJECT-TYPE
            SYNTAX SEQUENCE OF HwBrasSbcMGServAddrEntry
            MAX-ACCESS not-accessible
            STATUS current
            DESCRIPTION
                "Map Groups' Server Address.
                Support map group index: 1..2500"
            ::= { hwBrasSbcMapGroupTables 3 }

        hwBrasSbcMGServAddrEntry OBJECT-TYPE
            SYNTAX HwBrasSbcMGServAddrEntry
            MAX-ACCESS not-accessible
            STATUS current
            DESCRIPTION
                "Map Groups' server address entry."
            INDEX { hwBrasSbcMGServAddrIndex }
            ::= { hwBrasSbcMGServAddrTable 1 }

        HwBrasSbcMGServAddrEntry ::=
            SEQUENCE {
                hwBrasSbcMGServAddrIndex
                    Unsigned32,
                hwBrasSbcMGServAddrVPN
                    Unsigned32,
                hwBrasSbcMGServAddrIP1
                    IpAddress,
                hwBrasSbcMGServAddrIP2
                    IpAddress,
                hwBrasSbcMGServAddrIP3
                    IpAddress,
                hwBrasSbcMGServAddrIP4
                    IpAddress,
                hwBrasSbcMGServAddrRowStatus
                    RowStatus
             }

        hwBrasSbcMGServAddrIndex OBJECT-TYPE
            SYNTAX Unsigned32 (1..2999)
            MAX-ACCESS not-accessible
            STATUS current
            DESCRIPTION
                "Map Group's Index.
                Support map group index: 1..2500"
            ::= { hwBrasSbcMGServAddrEntry 1 }

        hwBrasSbcMGServAddrVPN OBJECT-TYPE
            SYNTAX Unsigned32 (0..1023)
            MAX-ACCESS read-create
            STATUS current
            DESCRIPTION
                "VPN Index.
                range:
                SE2200==>0~255
                SE2300==>0~1023"
            ::= { hwBrasSbcMGServAddrEntry 11 }

        hwBrasSbcMGServAddrIP1 OBJECT-TYPE
            SYNTAX IpAddress
            MAX-ACCESS read-create
            STATUS current
            DESCRIPTION
                "Server Address."
            ::= { hwBrasSbcMGServAddrEntry 12 }

        hwBrasSbcMGServAddrIP2 OBJECT-TYPE
            SYNTAX IpAddress
            MAX-ACCESS read-create
            STATUS current
            DESCRIPTION
                "Server Address."
            ::= { hwBrasSbcMGServAddrEntry 13 }

        hwBrasSbcMGServAddrIP3 OBJECT-TYPE
            SYNTAX IpAddress
            MAX-ACCESS read-create
            STATUS current
            DESCRIPTION
                "Server Address."
            ::= { hwBrasSbcMGServAddrEntry 14 }

        hwBrasSbcMGServAddrIP4 OBJECT-TYPE
            SYNTAX IpAddress
            MAX-ACCESS read-create
            STATUS current
            DESCRIPTION
                "Server Address."
            ::= { hwBrasSbcMGServAddrEntry 15 }

        hwBrasSbcMGServAddrRowStatus OBJECT-TYPE
            SYNTAX RowStatus
            MAX-ACCESS read-create
            STATUS current
            DESCRIPTION
                "Row stauts."
            ::= { hwBrasSbcMGServAddrEntry 51 }

        hwBrasSbcMGSofxAddrTable OBJECT-TYPE
            SYNTAX SEQUENCE OF HwBrasSbcMGSofxAddrEntry
            MAX-ACCESS not-accessible
            STATUS current
            DESCRIPTION
                "Map Groups' Soft-switch Address.
                Support map group index: 1..2500"
            ::= { hwBrasSbcMapGroupTables 4 }

        hwBrasSbcMGSofxAddrEntry OBJECT-TYPE
            SYNTAX HwBrasSbcMGSofxAddrEntry
            MAX-ACCESS not-accessible
            STATUS current
            DESCRIPTION
                "Map Groups' soft-switch address entry."
            INDEX { hwBrasSbcMGSofxAddrIndex }
            ::= { hwBrasSbcMGSofxAddrTable 1 }

        HwBrasSbcMGSofxAddrEntry ::=
            SEQUENCE {
                hwBrasSbcMGSofxAddrIndex
                    Unsigned32,
                hwBrasSbcMGSofxAddrVPN
                    Unsigned32,
                hwBrasSbcMGSofxAddrIP1
                    IpAddress,
                hwBrasSbcMGSofxAddrIP2
                    IpAddress,
                hwBrasSbcMGSofxAddrIP3
                    IpAddress,
                hwBrasSbcMGSofxAddrIP4
                    IpAddress,
                hwBrasSbcMGSofxAddrRowStatus
                    RowStatus
             }

        hwBrasSbcMGSofxAddrIndex OBJECT-TYPE
            SYNTAX Unsigned32 (1..2999)
            MAX-ACCESS not-accessible
            STATUS current
            DESCRIPTION
                "Map Group's Index.
                Support map group index: 1..2500"
            ::= { hwBrasSbcMGSofxAddrEntry 1 }

        hwBrasSbcMGSofxAddrVPN OBJECT-TYPE
            SYNTAX Unsigned32 (0..1023)
            MAX-ACCESS read-write
            STATUS current
            DESCRIPTION
                "VPN Index.
                range:
                SE2200==>0~255
                SE2300==>0~1023"
            ::= { hwBrasSbcMGSofxAddrEntry 11 }

        hwBrasSbcMGSofxAddrIP1 OBJECT-TYPE
            SYNTAX IpAddress
            MAX-ACCESS read-create
            STATUS current
            DESCRIPTION
                "Soft-switch Address."
            ::= { hwBrasSbcMGSofxAddrEntry 12 }

        hwBrasSbcMGSofxAddrIP2 OBJECT-TYPE
            SYNTAX IpAddress
            MAX-ACCESS read-create
            STATUS current
            DESCRIPTION
                "Soft-switch Address."
            ::= { hwBrasSbcMGSofxAddrEntry 13 }

        hwBrasSbcMGSofxAddrIP3 OBJECT-TYPE
            SYNTAX IpAddress
            MAX-ACCESS read-create
            STATUS current
            DESCRIPTION
                "Soft-switch Address."
            ::= { hwBrasSbcMGSofxAddrEntry 14 }

        hwBrasSbcMGSofxAddrIP4 OBJECT-TYPE
            SYNTAX IpAddress
            MAX-ACCESS read-create
            STATUS current
            DESCRIPTION
                "Soft-switch Address."
            ::= { hwBrasSbcMGSofxAddrEntry 15 }

        hwBrasSbcMGSofxAddrRowStatus OBJECT-TYPE
            SYNTAX RowStatus
            MAX-ACCESS read-write
            STATUS current
            DESCRIPTION
                "Row stauts."
            ::= { hwBrasSbcMGSofxAddrEntry 51 }

        hwBrasSbcMGIadmsAddrTable OBJECT-TYPE
            SYNTAX SEQUENCE OF HwBrasSbcMGIadmsAddrEntry
            MAX-ACCESS not-accessible
            STATUS current
            DESCRIPTION
                "Map Groups' UMS Address.
                Support map group index: 1..1000"
            ::= { hwBrasSbcMapGroupTables 5 }

        hwBrasSbcMGIadmsAddrEntry OBJECT-TYPE
            SYNTAX HwBrasSbcMGIadmsAddrEntry
            MAX-ACCESS not-accessible
            STATUS current
            DESCRIPTION
                "Map Groups' ums address entry."
            INDEX { hwBrasSbcMGIadmsAddrIndex }
            ::= { hwBrasSbcMGIadmsAddrTable 1 }

        HwBrasSbcMGIadmsAddrEntry ::=
            SEQUENCE {
                hwBrasSbcMGIadmsAddrIndex
                    Unsigned32,
                hwBrasSbcMGIadmsAddrVPN
                    Unsigned32,
                hwBrasSbcMGIadmsAddrIP1
                    IpAddress,
                hwBrasSbcMGIadmsAddrIP2
                    IpAddress,
                hwBrasSbcMGIadmsAddrIP3
                    IpAddress,
                hwBrasSbcMGIadmsAddrIP4
                    IpAddress,
                hwBrasSbcMGIadmsAddrRowStatus
                    RowStatus
             }

        hwBrasSbcMGIadmsAddrIndex OBJECT-TYPE
            SYNTAX Unsigned32 (1..2999)
            MAX-ACCESS not-accessible
            STATUS current
            DESCRIPTION
                "Map Group's Index.
                Support map group index: 1..1000"
            ::= { hwBrasSbcMGIadmsAddrEntry 1 }

        hwBrasSbcMGIadmsAddrVPN OBJECT-TYPE
            SYNTAX Unsigned32 (0..1023)
            MAX-ACCESS read-write
            STATUS current
            DESCRIPTION
                "VPN Index.
                range:
                SE2200==>0~255
                SE2300==>0~1023"
            ::= { hwBrasSbcMGIadmsAddrEntry 11 }

        hwBrasSbcMGIadmsAddrIP1 OBJECT-TYPE
            SYNTAX IpAddress
            MAX-ACCESS read-write
            STATUS current
            DESCRIPTION
                "IADMS Server Address."
            ::= { hwBrasSbcMGIadmsAddrEntry 12 }

        hwBrasSbcMGIadmsAddrIP2 OBJECT-TYPE
            SYNTAX IpAddress
            MAX-ACCESS read-write
            STATUS current
            DESCRIPTION
                "IADMS Server Address."
            ::= { hwBrasSbcMGIadmsAddrEntry 13 }

        hwBrasSbcMGIadmsAddrIP3 OBJECT-TYPE
            SYNTAX IpAddress
            MAX-ACCESS read-write
            STATUS current
            DESCRIPTION
                "IADMS Server Address."
            ::= { hwBrasSbcMGIadmsAddrEntry 14 }

        hwBrasSbcMGIadmsAddrIP4 OBJECT-TYPE
            SYNTAX IpAddress
            MAX-ACCESS read-write
            STATUS current
            DESCRIPTION
                "IADMS Server Address."
            ::= { hwBrasSbcMGIadmsAddrEntry 15 }

        hwBrasSbcMGIadmsAddrRowStatus OBJECT-TYPE
            SYNTAX RowStatus
            MAX-ACCESS read-write
            STATUS current
            DESCRIPTION
                "Row stauts."
            ::= { hwBrasSbcMGIadmsAddrEntry 51 }

        hwBrasSbcMGProtocolTable OBJECT-TYPE
            SYNTAX SEQUENCE OF HwBrasSbcMGProtocolEntry
            MAX-ACCESS not-accessible
            STATUS current
            DESCRIPTION
                "Map Groups' Bellow Protocol.
                Support map group index: 1..1000"
            ::= { hwBrasSbcMapGroupTables 6 }

        hwBrasSbcMGProtocolEntry OBJECT-TYPE
            SYNTAX HwBrasSbcMGProtocolEntry
            MAX-ACCESS not-accessible
            STATUS current
            DESCRIPTION
                "Map Groups' bellow protocol entry."
            INDEX { hwBrasSbcMGProtocolIndex }
            ::= { hwBrasSbcMGProtocolTable 1 }

        HwBrasSbcMGProtocolEntry ::=
            SEQUENCE {
                hwBrasSbcMGProtocolIndex
                    Unsigned32,
                hwBrasSbcMGProtocolSip
                    HWBrasEnabledStatus,
                hwBrasSbcMGProtocolMgcp
                    HWBrasEnabledStatus,
                hwBrasSbcMGProtocolH323
                    HWBrasEnabledStatus,
                hwBrasSbcMGProtocolIadms
                    HWBrasEnabledStatus,
                hwBrasSbcMGProtocolUpath
                    HWBrasEnabledStatus,
                hwBrasSbcMGProtocolH248
                    HWBrasEnabledStatus,
                hwBrasSbcMGProtocolRowStatus
                    RowStatus
             }

        hwBrasSbcMGProtocolIndex OBJECT-TYPE
            SYNTAX Unsigned32 (1..2999)
            MAX-ACCESS not-accessible
            STATUS current
            DESCRIPTION
                "Map Group's Index.
                Support map group index: 1..1000"
            ::= { hwBrasSbcMGProtocolEntry 1 }

        hwBrasSbcMGProtocolSip OBJECT-TYPE
            SYNTAX HWBrasEnabledStatus
            MAX-ACCESS read-write
            STATUS current
            DESCRIPTION
                "SIP Protocol."
            ::= { hwBrasSbcMGProtocolEntry 11 }

        hwBrasSbcMGProtocolMgcp OBJECT-TYPE
            SYNTAX HWBrasEnabledStatus
            MAX-ACCESS read-write
            STATUS current
            DESCRIPTION
                "MGCP Protocol."
            ::= { hwBrasSbcMGProtocolEntry 12 }

        hwBrasSbcMGProtocolH323 OBJECT-TYPE
            SYNTAX HWBrasEnabledStatus
            MAX-ACCESS read-write
            STATUS current
            DESCRIPTION
                "H.323 Protocol."
            ::= { hwBrasSbcMGProtocolEntry 13 }

        hwBrasSbcMGProtocolIadms OBJECT-TYPE
            SYNTAX HWBrasEnabledStatus
            MAX-ACCESS read-write
            STATUS current
            DESCRIPTION
                "IADMS Protocol."
            ::= { hwBrasSbcMGProtocolEntry 14 }

        hwBrasSbcMGProtocolUpath OBJECT-TYPE
            SYNTAX HWBrasEnabledStatus
            MAX-ACCESS read-write
            STATUS current
            DESCRIPTION
                "UPATH Protocol."
            ::= { hwBrasSbcMGProtocolEntry 15 }

        hwBrasSbcMGProtocolH248 OBJECT-TYPE
            SYNTAX HWBrasEnabledStatus
            MAX-ACCESS read-write
            STATUS current
            DESCRIPTION
                "H.248 Protocol."
            ::= { hwBrasSbcMGProtocolEntry 16 }

        hwBrasSbcMGProtocolRowStatus OBJECT-TYPE
            SYNTAX RowStatus
            MAX-ACCESS read-write
            STATUS current
            DESCRIPTION
                "Row stauts."
            ::= { hwBrasSbcMGProtocolEntry 51 }

        hwBrasSbcMGPortTable OBJECT-TYPE
            SYNTAX SEQUENCE OF HwBrasSbcMGPortEntry
            MAX-ACCESS not-accessible
            STATUS current
            DESCRIPTION
                "Map Groups' Port.
                Support map group index: 1..2000"
            ::= { hwBrasSbcMapGroupTables 7 }

        hwBrasSbcMGPortEntry OBJECT-TYPE
            SYNTAX HwBrasSbcMGPortEntry
            MAX-ACCESS not-accessible
            STATUS current
            DESCRIPTION
                "Map Groups' port entry."
            INDEX { hwBrasSbcMGPortIndex }
            ::= { hwBrasSbcMGPortTable 1 }

        HwBrasSbcMGPortEntry ::=
            SEQUENCE {
                hwBrasSbcMGPortIndex
                    Unsigned32,
                hwBrasSbcMGPortNumber
                    Unsigned32,
                hwBrasSbcMGPortRowStatus
                    RowStatus
             }

        hwBrasSbcMGPortIndex OBJECT-TYPE
            SYNTAX Unsigned32 (1..2999)
            MAX-ACCESS not-accessible
            STATUS current
            DESCRIPTION
                "Map Group's Index.
                Support index: 1..2000"
            ::= { hwBrasSbcMGPortEntry 1 }

        hwBrasSbcMGPortNumber OBJECT-TYPE
            SYNTAX Unsigned32 (1..65535)
            MAX-ACCESS read-create
            STATUS current
            DESCRIPTION
                "Port Index.
                Support range :1...65535"
            ::= { hwBrasSbcMGPortEntry 11 }

        hwBrasSbcMGPortRowStatus OBJECT-TYPE
            SYNTAX RowStatus
            MAX-ACCESS read-create
            STATUS current
            DESCRIPTION
                "Row stauts."
            ::= { hwBrasSbcMGPortEntry 51 }

        hwBrasSbcMGPrefixTable OBJECT-TYPE
            SYNTAX SEQUENCE OF HwBrasSbcMGPrefixEntry
            MAX-ACCESS not-accessible
            STATUS current
            DESCRIPTION
                "Map Groups' Prefix.
                Support index: 2001..2500"
            ::= { hwBrasSbcMapGroupTables 8 }

        hwBrasSbcMGPrefixEntry OBJECT-TYPE
            SYNTAX HwBrasSbcMGPrefixEntry
            MAX-ACCESS not-accessible
            STATUS current
            DESCRIPTION
                "Map Groups' prefix entry."
            INDEX { hwBrasSbcMGPrefixIndex }
            ::= { hwBrasSbcMGPrefixTable 1 }

        HwBrasSbcMGPrefixEntry ::=
            SEQUENCE {
                hwBrasSbcMGPrefixIndex
                    Unsigned32,
                hwBrasSbcMGPrefixID
                    DisplayString,
                hwBrasSbcMGPrefixRowStatus
                    RowStatus
             }

        hwBrasSbcMGPrefixIndex OBJECT-TYPE
            SYNTAX Unsigned32 (1..2999)
            MAX-ACCESS not-accessible
            STATUS current
            DESCRIPTION
                "Map Group's Index.
                Support map group index: 2001..2500"
            ::= { hwBrasSbcMGPrefixEntry 1 }

        hwBrasSbcMGPrefixID OBJECT-TYPE
            SYNTAX DisplayString (SIZE (1..63))
            MAX-ACCESS read-create
            STATUS current
            DESCRIPTION
                "Intercom Prefix ID.
                Support length :1...63"
            ::= { hwBrasSbcMGPrefixEntry 11 }

        hwBrasSbcMGPrefixRowStatus OBJECT-TYPE
            SYNTAX RowStatus
            MAX-ACCESS read-create
            STATUS current
            DESCRIPTION
                "Row stauts."
            ::= { hwBrasSbcMGPrefixEntry 51 }

        hwBrasSbcMGMdCliAddrTable OBJECT-TYPE
            SYNTAX SEQUENCE OF HwBrasSbcMGMdCliAddrEntry
            MAX-ACCESS not-accessible
            STATUS current
            DESCRIPTION
                "Map Groups' Media Client Address.
                Support map group index: 1..1000 | 2501..2999"
            ::= { hwBrasSbcMapGroupTables 9 }

        hwBrasSbcMGMdCliAddrEntry OBJECT-TYPE
            SYNTAX HwBrasSbcMGMdCliAddrEntry
            MAX-ACCESS not-accessible
            STATUS current
            DESCRIPTION
                "Map Groups' media client address entry."
            INDEX { hwBrasSbcMGMdCliAddrIndex }
            ::= { hwBrasSbcMGMdCliAddrTable 1 }

        HwBrasSbcMGMdCliAddrEntry ::=
            SEQUENCE {
                hwBrasSbcMGMdCliAddrIndex
                    Unsigned32,
                hwBrasSbcMGMdCliAddrVPN
                    Unsigned32,
                hwBrasSbcMGMdCliAddrIP1
                    IpAddress,
                hwBrasSbcMGMdCliAddrIP2
                    IpAddress,
                hwBrasSbcMGMdCliAddrIP3
                    IpAddress,
                hwBrasSbcMGMdCliAddrIP4
                    IpAddress,
                -- added by zhangyinxi --
                hwBrasSbcMGMdCliAddrVPNName
                    OCTET STRING,
                hwBrasSbcMGMdCliAddrIf1
                    OCTET STRING,
                hwBrasSbcMGMdCliAddrSlotID1
                    Unsigned32,
                hwBrasSbcMGMdCliAddrIf2
                    OCTET STRING,
                hwBrasSbcMGMdCliAddrSlotID2
                    Unsigned32,
                hwBrasSbcMGMdCliAddrIf3
                    OCTET STRING,
                hwBrasSbcMGMdCliAddrSlotID3
                    Unsigned32,
                hwBrasSbcMGMdCliAddrIf4
                    OCTET STRING,
                hwBrasSbcMGMdCliAddrSlotID4
                    Unsigned32,
                -- end added by zhangyinxi --
                hwBrasSbcMGMdCliAddrRowStatus
                    RowStatus
             }

        hwBrasSbcMGMdCliAddrIndex OBJECT-TYPE
            SYNTAX Unsigned32 (1..2999)
            MAX-ACCESS not-accessible
            STATUS current
            DESCRIPTION
                "Map Group's Index.
                Support map group index: 1..1000 | 2501..2999"
            ::= { hwBrasSbcMGMdCliAddrEntry 1 }

        hwBrasSbcMGMdCliAddrVPN OBJECT-TYPE
            SYNTAX Unsigned32 (0..1023)
            MAX-ACCESS read-create
            STATUS current
            DESCRIPTION
                "VPN Index.
                range:
                SE2200==>0~255
                SE2300==>0~1023"
            ::= { hwBrasSbcMGMdCliAddrEntry 11 }

        hwBrasSbcMGMdCliAddrIP1 OBJECT-TYPE
            SYNTAX IpAddress
            MAX-ACCESS read-create
            STATUS current
            DESCRIPTION
                "Media Client Address."
            ::= { hwBrasSbcMGMdCliAddrEntry 12 }

        hwBrasSbcMGMdCliAddrIP2 OBJECT-TYPE
            SYNTAX IpAddress
            MAX-ACCESS read-create
            STATUS current
            DESCRIPTION
                "Media Client Address."
            ::= { hwBrasSbcMGMdCliAddrEntry 13 }

        hwBrasSbcMGMdCliAddrIP3 OBJECT-TYPE
            SYNTAX IpAddress
            MAX-ACCESS read-create
            STATUS current
            DESCRIPTION
                "Media Client Address."
            ::= { hwBrasSbcMGMdCliAddrEntry 14 }

        hwBrasSbcMGMdCliAddrIP4 OBJECT-TYPE
            SYNTAX IpAddress
            MAX-ACCESS read-create
            STATUS current
            DESCRIPTION
                "Media Client Address."
            ::= { hwBrasSbcMGMdCliAddrEntry 15 }
        -- add by zhangyinxi --
        hwBrasSbcMGMdCliAddrVPNName OBJECT-TYPE
            SYNTAX OCTET STRING (SIZE (0..31))
            MAX-ACCESS read-create
            STATUS current
            DESCRIPTION
                "The name of VPN interface."
            ::= { hwBrasSbcMGMdCliAddrEntry 16 }

        hwBrasSbcMGMdCliAddrIf1 OBJECT-TYPE
            SYNTAX OCTET STRING (SIZE (0..47))
            MAX-ACCESS read-create
            STATUS current
            DESCRIPTION
                "Client Interface."
            ::= { hwBrasSbcMGMdCliAddrEntry 17 }

          hwBrasSbcMGMdCliAddrSlotID1 OBJECT-TYPE
            SYNTAX Unsigned32 (0..16)
            MAX-ACCESS read-create
            STATUS current
            DESCRIPTION
                "the working slot."
            ::= { hwBrasSbcMGMdCliAddrEntry 18 }

        hwBrasSbcMGMdCliAddrIf2 OBJECT-TYPE
            SYNTAX OCTET STRING (SIZE (0..47))
            MAX-ACCESS read-create
            STATUS current
            DESCRIPTION
                "Client Interface."
            ::= { hwBrasSbcMGMdCliAddrEntry 19 }

          hwBrasSbcMGMdCliAddrSlotID2 OBJECT-TYPE
            SYNTAX Unsigned32 (0..16)
            MAX-ACCESS read-create
            STATUS current
            DESCRIPTION
                "the working slot."
            ::= { hwBrasSbcMGMdCliAddrEntry 20 }

        hwBrasSbcMGMdCliAddrIf3 OBJECT-TYPE
            SYNTAX OCTET STRING (SIZE (0..47))
            MAX-ACCESS read-create
            STATUS current
            DESCRIPTION
                "Client Interface."
            ::= { hwBrasSbcMGMdCliAddrEntry 21 }

          hwBrasSbcMGMdCliAddrSlotID3 OBJECT-TYPE
            SYNTAX Unsigned32 (0..16)
            MAX-ACCESS read-create
            STATUS current
            DESCRIPTION
                "the working slot."
            ::= { hwBrasSbcMGMdCliAddrEntry 22 }

        hwBrasSbcMGMdCliAddrIf4 OBJECT-TYPE
            SYNTAX OCTET STRING (SIZE (0..47))
            MAX-ACCESS read-create
            STATUS current
            DESCRIPTION
                "Client Interface."
            ::= { hwBrasSbcMGMdCliAddrEntry 23 }

              hwBrasSbcMGMdCliAddrSlotID4 OBJECT-TYPE
            SYNTAX Unsigned32 (0..16)
            MAX-ACCESS read-create
            STATUS current
            DESCRIPTION
                "the working slot."
            ::= { hwBrasSbcMGMdCliAddrEntry 24 }
        -- end add by zhangyinxi --
        hwBrasSbcMGMdCliAddrRowStatus OBJECT-TYPE
            SYNTAX RowStatus
            MAX-ACCESS read-create
            STATUS current
            DESCRIPTION
                "Row stauts."
            ::= { hwBrasSbcMGMdCliAddrEntry 51 }

        hwBrasSbcMGMdServAddrTable OBJECT-TYPE
            SYNTAX SEQUENCE OF HwBrasSbcMGMdServAddrEntry
            MAX-ACCESS not-accessible
            STATUS current
            DESCRIPTION
                "Map Groups' Media Server Address.
                Support map group index: 1..1000 | 2501..2999"
            ::= { hwBrasSbcMapGroupTables 10 }

        hwBrasSbcMGMdServAddrEntry OBJECT-TYPE
            SYNTAX HwBrasSbcMGMdServAddrEntry
            MAX-ACCESS not-accessible
            STATUS current
            DESCRIPTION
                "Map Groups' media server address entry."
            INDEX { hwBrasSbcMGMdServAddrIndex }
            ::= { hwBrasSbcMGMdServAddrTable 1 }

        HwBrasSbcMGMdServAddrEntry ::=
            SEQUENCE {
                hwBrasSbcMGMdServAddrIndex
                    Unsigned32,
                hwBrasSbcMGMdServAddrVPN
                    Unsigned32,
                hwBrasSbcMGMdServAddrIP1
                    IpAddress,
                hwBrasSbcMGMdServAddrIP2
                    IpAddress,
                hwBrasSbcMGMdServAddrIP3
                    IpAddress,
                hwBrasSbcMGMdServAddrIP4
                    IpAddress,
                -- added by zhangyinxi --
                hwBrasSbcMGMdServAddrVPNName
                    OCTET STRING,
                hwBrasSbcMGMdServAddrIf1
                    OCTET STRING,
                hwBrasSbcMGMdServAddrSlotID1
                    Unsigned32,
                hwBrasSbcMGMdServAddrIf2
                    OCTET STRING,
                hwBrasSbcMGMdServAddrSlotID2
                    Unsigned32,
                hwBrasSbcMGMdServAddrIf3
                    OCTET STRING,
                hwBrasSbcMGMdServAddrSlotID3
                    Unsigned32,
                hwBrasSbcMGMdServAddrIf4
                    OCTET STRING,
                hwBrasSbcMGMdServAddrSlotID4
                    Unsigned32,
                -- end added by zhangyinxi --

                hwBrasSbcMGMdServAddrRowStatus
                    RowStatus
             }

        hwBrasSbcMGMdServAddrIndex OBJECT-TYPE
            SYNTAX Unsigned32 (1..2999)
            MAX-ACCESS not-accessible
            STATUS current
            DESCRIPTION
                "Map Group's Index.
                Support map group index: 1..1000 | 2501..2999"
            ::= { hwBrasSbcMGMdServAddrEntry 1 }

        hwBrasSbcMGMdServAddrVPN OBJECT-TYPE
            SYNTAX Unsigned32 (0..1023)
            MAX-ACCESS read-write
            STATUS current
            DESCRIPTION
                "VPN Index.
                range:
                SE2200==>0~255
                SE2300==>0~1023"
            ::= { hwBrasSbcMGMdServAddrEntry 11 }

        hwBrasSbcMGMdServAddrIP1 OBJECT-TYPE
            SYNTAX IpAddress
            MAX-ACCESS read-create
            STATUS current
            DESCRIPTION
                "Media Server Address."
            ::= { hwBrasSbcMGMdServAddrEntry 12 }

        hwBrasSbcMGMdServAddrIP2 OBJECT-TYPE
            SYNTAX IpAddress
            MAX-ACCESS read-create
            STATUS current
            DESCRIPTION
                "Media Server Address."
            ::= { hwBrasSbcMGMdServAddrEntry 13 }

        hwBrasSbcMGMdServAddrIP3 OBJECT-TYPE
            SYNTAX IpAddress
            MAX-ACCESS read-create
            STATUS current
            DESCRIPTION
                "Media Server Address."
            ::= { hwBrasSbcMGMdServAddrEntry 14 }

        hwBrasSbcMGMdServAddrIP4 OBJECT-TYPE
            SYNTAX IpAddress
            MAX-ACCESS read-create
            STATUS current
            DESCRIPTION
                "Media Server Address."
            ::= { hwBrasSbcMGMdServAddrEntry 15 }

        -- add by zhangyinxi --
        hwBrasSbcMGMdServAddrVPNName OBJECT-TYPE
            SYNTAX OCTET STRING (SIZE (0..31))
            MAX-ACCESS read-create
            STATUS current
            DESCRIPTION
                "The name of VPN interface."
            ::= { hwBrasSbcMGMdServAddrEntry 16 }

        hwBrasSbcMGMdServAddrIf1 OBJECT-TYPE
            SYNTAX OCTET STRING (SIZE (0..47))
            MAX-ACCESS read-create
            STATUS current
            DESCRIPTION
                "Server Interface."
            ::= { hwBrasSbcMGMdServAddrEntry 17 }

          hwBrasSbcMGMdServAddrSlotID1 OBJECT-TYPE
            SYNTAX Unsigned32 (0..16)
            MAX-ACCESS read-create
            STATUS current
            DESCRIPTION
                "the working slot."
            ::= { hwBrasSbcMGMdServAddrEntry 18 }

        hwBrasSbcMGMdServAddrIf2 OBJECT-TYPE
            SYNTAX OCTET STRING (SIZE (0..47))
            MAX-ACCESS read-create
            STATUS current
            DESCRIPTION
                "Server Interface."
            ::= { hwBrasSbcMGMdServAddrEntry 19 }

          hwBrasSbcMGMdServAddrSlotID2 OBJECT-TYPE
            SYNTAX Unsigned32 (0..16)
            MAX-ACCESS read-create
            STATUS current
            DESCRIPTION
                "the working slot."
            ::= { hwBrasSbcMGMdServAddrEntry 20 }

        hwBrasSbcMGMdServAddrIf3 OBJECT-TYPE
            SYNTAX OCTET STRING (SIZE (0..47))
            MAX-ACCESS read-create
            STATUS current
            DESCRIPTION
                "Server Interface."
            ::= { hwBrasSbcMGMdServAddrEntry 21 }

          hwBrasSbcMGMdServAddrSlotID3 OBJECT-TYPE
            SYNTAX Unsigned32 (0..16)
            MAX-ACCESS read-create
            STATUS current
            DESCRIPTION
                "the working slot."
            ::= { hwBrasSbcMGMdServAddrEntry 22 }

        hwBrasSbcMGMdServAddrIf4 OBJECT-TYPE
            SYNTAX OCTET STRING (SIZE (0..47))
            MAX-ACCESS read-create
            STATUS current
            DESCRIPTION
                "Server Interface."
            ::= { hwBrasSbcMGMdServAddrEntry 23 }

          hwBrasSbcMGMdServAddrSlotID4 OBJECT-TYPE
            SYNTAX Unsigned32 (0..16)
            MAX-ACCESS read-create
            STATUS current
            DESCRIPTION
                "the working slot."
            ::= { hwBrasSbcMGMdServAddrEntry 24 }

        -- end add by zhangyinxi --
        hwBrasSbcMGMdServAddrRowStatus OBJECT-TYPE
            SYNTAX RowStatus
            MAX-ACCESS read-create
            STATUS current
            DESCRIPTION
                "Row stauts."
            ::= { hwBrasSbcMGMdServAddrEntry 51 }

        hwBrasSbcMGMatchTable OBJECT-TYPE
            SYNTAX SEQUENCE OF HwBrasSbcMGMatchEntry
            MAX-ACCESS not-accessible
            STATUS current
            DESCRIPTION
                "Map Groups' Match Acl Number.
                Support map group index: 1..1000 | 2501..2999"
            ::= { hwBrasSbcMapGroupTables 11 }

        hwBrasSbcMGMatchEntry OBJECT-TYPE
            SYNTAX HwBrasSbcMGMatchEntry
            MAX-ACCESS not-accessible
            STATUS current
            DESCRIPTION
                "Map Groups' match acl number entry."
            INDEX { hwBrasSbcMGMatchIndex }
            ::= { hwBrasSbcMGMatchTable 1 }

        HwBrasSbcMGMatchEntry ::=
            SEQUENCE {
                hwBrasSbcMGMatchIndex
                    Unsigned32,
                hwBrasSbcMGMatchAcl
                    Unsigned32,
                hwBrasSbcMGMatchRowStatus
                    RowStatus
             }

        hwBrasSbcMGMatchIndex OBJECT-TYPE
            SYNTAX Unsigned32 (1..2999)
            MAX-ACCESS not-accessible
            STATUS current
            DESCRIPTION
                "Map Group's Index.
                Support map group index: 1..1000 | 2501..2999"
            ::= { hwBrasSbcMGMatchEntry 1 }

        hwBrasSbcMGMatchAcl OBJECT-TYPE
            SYNTAX Unsigned32 (2000..3999)
            MAX-ACCESS read-create
            STATUS current
            DESCRIPTION
                "ACL Index.
                Support range: 2000...3999"
            ::= { hwBrasSbcMGMatchEntry 11 }

        hwBrasSbcMGMatchRowStatus OBJECT-TYPE
            SYNTAX RowStatus
            MAX-ACCESS read-create
            STATUS current
            DESCRIPTION
                "Row stauts."
            ::= { hwBrasSbcMGMatchEntry 51 }

       --begin: add by zhouqin for ADM MIB --
       hwBrasSbcAdmModuleTable OBJECT IDENTIFIER ::= { hwBrasSbcBase 4 }
       hwBrasSbcBackupGroupsTable OBJECT IDENTIFIER ::= { hwBrasSbcAdmModuleTable 1 }

       hwBrasSbcBackupGroupTable OBJECT-TYPE
            SYNTAX SEQUENCE OF HwBrasSbcBackupGroupEntry
            MAX-ACCESS not-accessible
            STATUS current
            DESCRIPTION
                "Sbc BackupGroup Table.
                obsolete"
            ::= { hwBrasSbcBackupGroupsTable 1 }


      hwBrasSbcBackupGroupEntry OBJECT-TYPE
            SYNTAX HwBrasSbcBackupGroupEntry
            MAX-ACCESS not-accessible
            STATUS current
            DESCRIPTION
                "Sbc BackupGroup Table Entry."
            INDEX { hwBrasSbcBackupGroupID }
            ::= { hwBrasSbcBackupGroupTable 1 }

        HwBrasSbcBackupGroupEntry ::=
            SEQUENCE {
                hwBrasSbcBackupGroupID
                    Integer32,
                hwBrasSbcBackupGroupType
                    INTEGER,
                hwBrasSbcBackupGroupInstanceName
                    DisplayString,
                    hwBrasSbcBackupGroupRowStatus
                    RowStatus
                     }

        hwBrasSbcBackupGroupID OBJECT-TYPE
            SYNTAX Integer32 (0..14)
            MAX-ACCESS not-accessible
            STATUS current
            DESCRIPTION
                "BackupGroup ID."
            ::= { hwBrasSbcBackupGroupEntry 1 }

       hwBrasSbcBackupGroupType OBJECT-TYPE
            -- SYNTAX Integer32 (1..2)
            SYNTAX INTEGER
                {
                signal(1),
                media(2)
                }
            MAX-ACCESS read-create
            STATUS current
            DESCRIPTION
                "BackupGroup type.
                1 signal backup group
                2 media backup group"
            ::= { hwBrasSbcBackupGroupEntry 2 }

     hwBrasSbcBackupGroupInstanceName OBJECT-TYPE
             SYNTAX DisplayString (SIZE (1..32))
            MAX-ACCESS read-create
            STATUS current
            DESCRIPTION
                "Instance Name."
            ::= { hwBrasSbcBackupGroupEntry 3 }

        hwBrasSbcBackupGroupRowStatus OBJECT-TYPE
            SYNTAX RowStatus
            MAX-ACCESS read-create
            STATUS current
            DESCRIPTION
                "Row stauts."
            ::= { hwBrasSbcBackupGroupEntry 51 }

      --  ============== hwBrasSbcBackupGroupTable define endding==============


      --  ============== hwBrasSbcSlotInforTable  define beginning ==============

       hwBrasSbcSlotInforTable OBJECT-TYPE
            SYNTAX SEQUENCE OF HwBrasSbcSlotInforEntry
            MAX-ACCESS not-accessible
            STATUS current
            DESCRIPTION
                "Slot Information Table.
                obsolete"
            ::= { hwBrasSbcBackupGroupsTable 2 }

      hwBrasSbcSlotInforEntry OBJECT-TYPE
            SYNTAX HwBrasSbcSlotInforEntry
            MAX-ACCESS not-accessible
            STATUS current
            DESCRIPTION
                "Slot Information Table Entry."
            INDEX { hwBrasSbcBackupGroupIndex, hwBrasSbcSlotIndex }
            ::= { hwBrasSbcSlotInforTable 1 }

      HwBrasSbcSlotInforEntry ::=
            SEQUENCE {
                hwBrasSbcBackupGroupIndex
                    Integer32,
                hwBrasSbcSlotIndex
                    Integer32,
               hwBrasSbcCurrentSlotID
                    Integer32,
               hwBrasSbcSlotCfgState
                     INTEGER,
              hwBrasSbcSlotInforRowStatus
                    RowStatus
                     }
    hwBrasSbcBackupGroupIndex OBJECT-TYPE
            SYNTAX Integer32 (0..14)
            MAX-ACCESS not-accessible
            STATUS current
            DESCRIPTION
                "BackupGroup index."
            ::= { hwBrasSbcSlotInforEntry 1 }


    hwBrasSbcSlotIndex OBJECT-TYPE
            SYNTAX Integer32 (0..7)
            MAX-ACCESS not-accessible
            STATUS current
            DESCRIPTION
                "Slot Index."
            ::= { hwBrasSbcSlotInforEntry 2 }

    hwBrasSbcCurrentSlotID OBJECT-TYPE
            SYNTAX Integer32 (1..16)
            MAX-ACCESS read-create
            STATUS current
            DESCRIPTION
                "Slot ID."
            ::= { hwBrasSbcSlotInforEntry 3 }

    hwBrasSbcSlotCfgState OBJECT-TYPE
                SYNTAX INTEGER
                {
                master(1),
                slave(2)
                }
            MAX-ACCESS read-create
            STATUS current
            DESCRIPTION
                "Config State.
                1 master
                2 backup"
            ::= { hwBrasSbcSlotInforEntry 4 }

    hwBrasSbcSlotInforRowStatus OBJECT-TYPE
            SYNTAX RowStatus
            MAX-ACCESS read-create
            STATUS current
            DESCRIPTION
                "Row stauts."
            ::= { hwBrasSbcSlotInforEntry 5 }

   --  ============== hwBrasSbcSlotInforTable  define endding ==============
   -- add by zhou qin for ADM MIB --


        hwBrasSbcAdvance OBJECT IDENTIFIER ::= { hwBrasSbcGeneral 2 }

        hwBrasSbcAdvanceLeaves OBJECT IDENTIFIER ::= { hwBrasSbcAdvance 1 }

        hwBrasSbcMediaPassEnable OBJECT-TYPE
            SYNTAX HWBrasEnabledStatus
            MAX-ACCESS read-write
            STATUS current
            DESCRIPTION
                "Mediapass Enable Status.
                Default: disabled"
            DEFVAL { disabled }
            ::= { hwBrasSbcAdvanceLeaves 1 }

        hwBrasSbcMediaPassSyslogEnable OBJECT-TYPE
            SYNTAX HWBrasEnabledStatus
            MAX-ACCESS read-write
            STATUS current
            DESCRIPTION
                "Mediapass Syslog Enable Status.
                Default: enabled"
            DEFVAL { enabled }
            ::= { hwBrasSbcAdvanceLeaves 2 }

        hwBrasSbcIntMediaPassEnable OBJECT-TYPE
            SYNTAX HWBrasEnabledStatus
            MAX-ACCESS read-write
            STATUS current
            DESCRIPTION
                "obsolete
                Internet-mediapass Enable Status.
                Default: disabled"
            DEFVAL { disabled }
            ::= { hwBrasSbcAdvanceLeaves 3 }

        hwBrasSbcRoamlimitEnable OBJECT-TYPE
            SYNTAX HWBrasEnabledStatus
            MAX-ACCESS read-write
            STATUS current
            DESCRIPTION
                "Roamlimit Enable Status.
                Default: disabled"
            DEFVAL { disabled }
            ::= { hwBrasSbcAdvanceLeaves 4 }

        hwBrasSbcRoamlimitDefault OBJECT-TYPE
            SYNTAX HWBrasPermitStatus
            MAX-ACCESS read-write
            STATUS current
            DESCRIPTION
                "Roamlimit Default Rule."
            DEFVAL { deny }
            ::= { hwBrasSbcAdvanceLeaves 5 }

        hwBrasSbcRoamlimitSyslogEnable OBJECT-TYPE
            SYNTAX HWBrasEnabledStatus
            MAX-ACCESS read-write
            STATUS current
            DESCRIPTION
                "Roamlimit Syslog Enable Status.
                Default: enabled"
            DEFVAL { enabled }
            ::= { hwBrasSbcAdvanceLeaves 6 }

        hwBrasSbcRoamlimitExtendEnable OBJECT-TYPE
            SYNTAX HWBrasEnabledStatus
            MAX-ACCESS read-write
            STATUS current
            DESCRIPTION
                "Roamlimit Extend Enable Status.
                Default: disabled"
            DEFVAL { disabled }
            ::= { hwBrasSbcAdvanceLeaves 7 }

        hwBrasSbcHrpSynchronization OBJECT-TYPE
            SYNTAX INTEGER
                {
                reserve(1),
                synchronize(2)
                }
            MAX-ACCESS read-write
            STATUS current
            DESCRIPTION
                "HRP Synchronization:
                Synchronize data in master device to slave device"
            ::= { hwBrasSbcAdvanceLeaves 8 }

        hwBrasSbcAdvanceTables OBJECT IDENTIFIER ::= { hwBrasSbcAdvance 2 }

        hwBrasSbcMediaPassTable OBJECT-TYPE
            SYNTAX SEQUENCE OF HwBrasSbcMediaPassEntry
            MAX-ACCESS not-accessible
            STATUS current
            DESCRIPTION
                "Mediapass Configuration Table."
            ::= { hwBrasSbcAdvanceTables 1 }

        hwBrasSbcMediaPassEntry OBJECT-TYPE
            SYNTAX HwBrasSbcMediaPassEntry
            MAX-ACCESS not-accessible
            STATUS current
            DESCRIPTION
                "MediaPass Configuration Table Entry."
            INDEX { hwBrasSbcMediaPassIndex }
            ::= { hwBrasSbcMediaPassTable 1 }

        HwBrasSbcMediaPassEntry ::=
            SEQUENCE {
                hwBrasSbcMediaPassIndex
                    INTEGER,
                hwBrasSbcMediaPassAclNumber
                    INTEGER,
                hwBrasSbcMediaPassRowStatus
                    RowStatus
             }

        hwBrasSbcMediaPassIndex OBJECT-TYPE
            SYNTAX INTEGER (1..1000)
            MAX-ACCESS not-accessible
            STATUS current
            DESCRIPTION
                "Usergroup Index.
                Range: 1-1000"
            ::= { hwBrasSbcMediaPassEntry 1 }

        hwBrasSbcMediaPassAclNumber OBJECT-TYPE
            SYNTAX INTEGER (0 | 2000..2999)
            MAX-ACCESS read-create
            STATUS current
            DESCRIPTION
                "ACL Index.
                Range: 2000-2999
                0 for no acl bind"
            ::= { hwBrasSbcMediaPassEntry 2 }

        hwBrasSbcMediaPassRowStatus OBJECT-TYPE
            SYNTAX RowStatus
            MAX-ACCESS read-create
            STATUS current
            DESCRIPTION
                "Mediapass Row Status."
            ::= { hwBrasSbcMediaPassEntry 3 }

        hwBrasSbcUsergroupTable OBJECT-TYPE
            SYNTAX SEQUENCE OF HwBrasSbcUsergroupEntry
            MAX-ACCESS not-accessible
            STATUS current
            DESCRIPTION
                "Usergroup for Roamlimit Rule Table."
            ::= { hwBrasSbcAdvanceTables 2 }

        hwBrasSbcUsergroupEntry OBJECT-TYPE
            SYNTAX HwBrasSbcUsergroupEntry
            MAX-ACCESS not-accessible
            STATUS current
            DESCRIPTION
                "Usergroup for Roamlimit Table Entry."
            INDEX { hwBrasSbcUsergroupIndex }
            ::= { hwBrasSbcUsergroupTable 1 }

        HwBrasSbcUsergroupEntry ::=
            SEQUENCE {
                hwBrasSbcUsergroupIndex
                    INTEGER,
                hwBrasSbcUsergroupRowStatus
                    RowStatus
             }

        hwBrasSbcUsergroupIndex OBJECT-TYPE
            SYNTAX INTEGER (1..1000)
            MAX-ACCESS not-accessible
            STATUS current
            DESCRIPTION
                "Usergroup Index.
                Range: 1-1000"
            ::= { hwBrasSbcUsergroupEntry 1 }

        hwBrasSbcUsergroupRowStatus OBJECT-TYPE
            SYNTAX RowStatus
            MAX-ACCESS read-create
            STATUS current
            DESCRIPTION
                "Usergroup Row Status."
            ::= { hwBrasSbcUsergroupEntry 2 }

        hwBrasSbcUsergroupRuleTable OBJECT-TYPE
            SYNTAX SEQUENCE OF HwBrasSbcUsergroupRuleEntry
            MAX-ACCESS not-accessible
            STATUS current
            DESCRIPTION
                "Usergroup for Roamlimit Rule Table."
            ::= { hwBrasSbcAdvanceTables 3 }

        hwBrasSbcUsergroupRuleEntry OBJECT-TYPE
            SYNTAX HwBrasSbcUsergroupRuleEntry
            MAX-ACCESS not-accessible
            STATUS current
            DESCRIPTION
                "Usergroup for Roamlimit Rule Table Entry."
            INDEX { hwBrasSbcUsergroupIndex, hwBrasSbcUsergroupRuleIndex }
            ::= { hwBrasSbcUsergroupRuleTable 1 }

        HwBrasSbcUsergroupRuleEntry ::=
            SEQUENCE {
                hwBrasSbcUsergroupRuleIndex
                    INTEGER,
                hwBrasSbcUsergroupRuleType
                    HWBrasPermitStatus,
                hwBrasSbcUsergroupRuleUserName
                    DisplayString,
                hwBrasSbcUsergroupRuleRowStatus
                    RowStatus
             }

        hwBrasSbcUsergroupRuleIndex OBJECT-TYPE
            SYNTAX INTEGER (1..100)
            MAX-ACCESS not-accessible
            STATUS current
            DESCRIPTION
                "Usergroup Rule Index.
                Range: 1-100"
            ::= { hwBrasSbcUsergroupRuleEntry 1 }

        hwBrasSbcUsergroupRuleType OBJECT-TYPE
            SYNTAX HWBrasPermitStatus
            MAX-ACCESS read-create
            STATUS current
            DESCRIPTION
                "Rule Type."
            ::= { hwBrasSbcUsergroupRuleEntry 2 }

        hwBrasSbcUsergroupRuleUserName OBJECT-TYPE
            SYNTAX DisplayString (SIZE (1..63))
            MAX-ACCESS read-create
            STATUS current
            DESCRIPTION
                "User Infomation."
            ::= { hwBrasSbcUsergroupRuleEntry 3 }

        hwBrasSbcUsergroupRuleRowStatus OBJECT-TYPE
            SYNTAX RowStatus
            MAX-ACCESS read-create
            STATUS current
            DESCRIPTION
                "Usergroup Rule Row Status."
            ::= { hwBrasSbcUsergroupRuleEntry 4 }

        hwBrasSbcRtpSpecialAddrTable OBJECT-TYPE
            SYNTAX SEQUENCE OF HwBrasSbcRtpSpecialAddrEntry
            MAX-ACCESS not-accessible
            STATUS current
            DESCRIPTION
                "Rtp Special Address Table."
            ::= { hwBrasSbcAdvanceTables 4 }

        hwBrasSbcRtpSpecialAddrEntry OBJECT-TYPE
            SYNTAX HwBrasSbcRtpSpecialAddrEntry
            MAX-ACCESS not-accessible
            STATUS current
            DESCRIPTION
                "Rtp Special Address Table Entry."
            INDEX { hwBrasSbcRtpSpecialAddrIndex }
            ::= { hwBrasSbcRtpSpecialAddrTable 1 }

        HwBrasSbcRtpSpecialAddrEntry ::=
            SEQUENCE {
                hwBrasSbcRtpSpecialAddrIndex
                    INTEGER,
                hwBrasSbcRtpSpecialAddrAddr
                    IpAddress,
                hwBrasSbcRtpSpecialAddrRowStatus
                    RowStatus
             }

        hwBrasSbcRtpSpecialAddrIndex OBJECT-TYPE
            SYNTAX INTEGER (1..10)
            MAX-ACCESS not-accessible
            STATUS current
            DESCRIPTION
                "Rtp Special Address Index."
            ::= { hwBrasSbcRtpSpecialAddrEntry 1 }

        hwBrasSbcRtpSpecialAddrAddr OBJECT-TYPE
            SYNTAX IpAddress
            MAX-ACCESS read-create
            STATUS current
            DESCRIPTION
                "Rtp Special Address Address."
            ::= { hwBrasSbcRtpSpecialAddrEntry 2 }

        hwBrasSbcRtpSpecialAddrRowStatus OBJECT-TYPE
            SYNTAX RowStatus
            MAX-ACCESS read-create
            STATUS current
            DESCRIPTION
                "Rtp Special Address Row Status."
            ::= { hwBrasSbcRtpSpecialAddrEntry 3 }

        hwBrasSbcRoamlimitTable OBJECT-TYPE
            SYNTAX SEQUENCE OF HwBrasSbcRoamlimitEntry
            MAX-ACCESS not-accessible
            STATUS current
            DESCRIPTION
                "Roamlimit Table."
            ::= { hwBrasSbcAdvanceTables 5 }

        hwBrasSbcRoamlimitEntry OBJECT-TYPE
            SYNTAX HwBrasSbcRoamlimitEntry
            MAX-ACCESS not-accessible
            STATUS current
            DESCRIPTION
                "Roamlimit Table Entry."
            INDEX { hwBrasSbcRoamlimitIndex }
            ::= { hwBrasSbcRoamlimitTable 1 }

        HwBrasSbcRoamlimitEntry ::=
            SEQUENCE {
                hwBrasSbcRoamlimitIndex
                    Unsigned32,
                hwBrasSbcRoamlimitAclNumber
                    Unsigned32,
                hwBrasSbcRoamlimitRowStatus
                    RowStatus
             }

        hwBrasSbcRoamlimitIndex OBJECT-TYPE
            SYNTAX Unsigned32 (1..1000)
            MAX-ACCESS not-accessible
            STATUS current
            DESCRIPTION
                "Roamlimit Number."
            ::= { hwBrasSbcRoamlimitEntry 1 }

        hwBrasSbcRoamlimitAclNumber OBJECT-TYPE
            SYNTAX Unsigned32 (2000..2999)
            MAX-ACCESS read-create
            STATUS current
            DESCRIPTION
                "Roamlimit Acl Number."
            ::= { hwBrasSbcRoamlimitEntry 2 }

        hwBrasSbcRoamlimitRowStatus OBJECT-TYPE
            SYNTAX RowStatus
            MAX-ACCESS read-create
            STATUS current
            DESCRIPTION
                "Roamlimit Row Status."
            ::= { hwBrasSbcRoamlimitEntry 3 }

        hwBrasSbcMediaUsersTable OBJECT-TYPE
            SYNTAX SEQUENCE OF HwBrasSbcMediaUsersEntry
            MAX-ACCESS not-accessible
            STATUS current
            DESCRIPTION
                "Media QoS Configuration Table."
            ::= { hwBrasSbcAdvanceTables 6 }

        hwBrasSbcMediaUsersEntry OBJECT-TYPE
            SYNTAX HwBrasSbcMediaUsersEntry
            MAX-ACCESS not-accessible
            STATUS current
            DESCRIPTION
                "Media Users Table Entry."
            INDEX { hwBrasSbcMediaUsersIndex }
            ::= { hwBrasSbcMediaUsersTable 1 }

        HwBrasSbcMediaUsersEntry ::=
            SEQUENCE {
                hwBrasSbcMediaUsersIndex
                    INTEGER,
                hwBrasSbcMediaUsersType
                    INTEGER,
                hwBrasSbcMediaUsersCallerID1
                    DisplayString,
                hwBrasSbcMediaUsersCallerID2
                    DisplayString,
                hwBrasSbcMediaUsersCallerID3
                    DisplayString,
                hwBrasSbcMediaUsersCallerID4
                    DisplayString,
                hwBrasSbcMediaUsersCalleeID1
                    DisplayString,
                hwBrasSbcMediaUsersCalleeID2
                    DisplayString,
                hwBrasSbcMediaUsersCalleeID3
                    DisplayString,
                hwBrasSbcMediaUsersCalleeID4
                    DisplayString,
                hwBrasSbcMediaUsersRowStatus
                    RowStatus
             }

        hwBrasSbcMediaUsersIndex OBJECT-TYPE
            SYNTAX INTEGER (1..255)
            MAX-ACCESS not-accessible
            STATUS current
            DESCRIPTION
                "SessionEngine2000 Media Users Index
                read range: 1-255
                set  range: 1-253"
            ::= { hwBrasSbcMediaUsersEntry 1 }

        hwBrasSbcMediaUsersType OBJECT-TYPE
            SYNTAX INTEGER
                {
                media(1),
                audio(2),
                video(3),
                data(4)
                }
            MAX-ACCESS read-create
            STATUS current
            DESCRIPTION
                "Media Users Media Type."
            ::= { hwBrasSbcMediaUsersEntry 2 }

        hwBrasSbcMediaUsersCallerID1 OBJECT-TYPE
            SYNTAX DisplayString (SIZE (0..63))
            MAX-ACCESS read-create
            STATUS current
            DESCRIPTION
                "Media Users Caller ID1
                Range: 0-63"
            ::= { hwBrasSbcMediaUsersEntry 3 }

        hwBrasSbcMediaUsersCallerID2 OBJECT-TYPE
            SYNTAX DisplayString (SIZE (0..63))
            MAX-ACCESS read-create
            STATUS current
            DESCRIPTION
                "Media Users Caller ID2
                Range: 0-63"
            ::= { hwBrasSbcMediaUsersEntry 4 }

        hwBrasSbcMediaUsersCallerID3 OBJECT-TYPE
            SYNTAX DisplayString (SIZE (0..63))
            MAX-ACCESS read-create
            STATUS current
            DESCRIPTION
                "Media Users Caller ID3
                Range: 0-63"
            ::= { hwBrasSbcMediaUsersEntry 5 }

        hwBrasSbcMediaUsersCallerID4 OBJECT-TYPE
            SYNTAX DisplayString (SIZE (0..63))
            MAX-ACCESS read-create
            STATUS current
            DESCRIPTION
                "Media Users Caller ID4
                Range: 0-63"
            ::= { hwBrasSbcMediaUsersEntry 6 }

        hwBrasSbcMediaUsersCalleeID1 OBJECT-TYPE
            SYNTAX DisplayString (SIZE (0..63))
            MAX-ACCESS read-create
            STATUS current
            DESCRIPTION
                "Media Users Callee ID1
                Range: 0-63"
            ::= { hwBrasSbcMediaUsersEntry 7 }

        hwBrasSbcMediaUsersCalleeID2 OBJECT-TYPE
            SYNTAX DisplayString (SIZE (0..63))
            MAX-ACCESS read-create
            STATUS current
            DESCRIPTION
                "Media Users Callee ID2
                Range: 0-63"
            ::= { hwBrasSbcMediaUsersEntry 8 }

        hwBrasSbcMediaUsersCalleeID3 OBJECT-TYPE
            SYNTAX DisplayString (SIZE (0..63))
            MAX-ACCESS read-create
            STATUS current
            DESCRIPTION
                "Media Users Callee ID3
                Range: 0-63"
            ::= { hwBrasSbcMediaUsersEntry 9 }

        hwBrasSbcMediaUsersCalleeID4 OBJECT-TYPE
            SYNTAX DisplayString (SIZE (0..63))
            MAX-ACCESS read-create
            STATUS current
            DESCRIPTION
                "Media Users Callee ID4
                Range: 0-63"
            ::= { hwBrasSbcMediaUsersEntry 10 }

        hwBrasSbcMediaUsersRowStatus OBJECT-TYPE
            SYNTAX RowStatus
            MAX-ACCESS read-create
            STATUS current
            DESCRIPTION
                "Media Users Row Status."
            ::= { hwBrasSbcMediaUsersEntry 11 }

        hwBrasSbcIntercom OBJECT IDENTIFIER ::= { hwBrasSbcAdvance 3 }

        hwBrasSbcIntercomLeaves OBJECT IDENTIFIER ::= { hwBrasSbcIntercom 1 }

        hwBrasSbcIntercomEnable OBJECT-TYPE
            SYNTAX HWBrasEnabledStatus
            MAX-ACCESS read-write
            STATUS current
            DESCRIPTION
                "Intercom Enable Status.
                Default: disabled
                obsolete"
            DEFVAL { disabled }
            ::= { hwBrasSbcIntercomLeaves 1 }

        hwBrasSbcIntercomStatus OBJECT-TYPE
            SYNTAX INTEGER
                {
                disabled(1),
                iproute(2),
                prefixroute(3)
                }
            MAX-ACCESS read-write
            STATUS current
            DESCRIPTION
                "intercom status set
                1:disabled, intercom is closed
                2:ip-route, intercom ip route function is enable
                3:prefix-route, intercom prefix route function is enable"
            DEFVAL { disabled }
            ::= { hwBrasSbcIntercomLeaves 2 }

        hwBrasSbcIntercomTables OBJECT IDENTIFIER ::= { hwBrasSbcIntercom 2 }

        hwBrasSbcIntercomPrefixTable OBJECT-TYPE
            SYNTAX SEQUENCE OF HwBrasSbcIntercomPrefixEntry
            MAX-ACCESS not-accessible
            STATUS current
            DESCRIPTION
                "Intercom Prefix-route Set Table."
            ::= { hwBrasSbcIntercomTables 1 }

        hwBrasSbcIntercomPrefixEntry OBJECT-TYPE
            SYNTAX HwBrasSbcIntercomPrefixEntry
            MAX-ACCESS not-accessible
            STATUS current
            DESCRIPTION
                "Intercom Prefix-route Set Table Entry."
            INDEX { hwBrasSbcIntercomPrefixIndex }
            ::= { hwBrasSbcIntercomPrefixTable 1 }

        HwBrasSbcIntercomPrefixEntry ::=
            SEQUENCE {
                hwBrasSbcIntercomPrefixIndex
                    DisplayString,
                hwBrasSbcIntercomPrefixDestAddr
                    IpAddress,
                hwBrasSbcIntercomPrefixSrcAddr
                    IpAddress,
                hwBrasSbcIntercomPrefixRowStatus
                    RowStatus
             }

        hwBrasSbcIntercomPrefixIndex OBJECT-TYPE
            SYNTAX DisplayString (SIZE (1..63))
            MAX-ACCESS not-accessible
            STATUS current
            DESCRIPTION
                "Intercom Prefix number."
            ::= { hwBrasSbcIntercomPrefixEntry 1 }

        hwBrasSbcIntercomPrefixDestAddr OBJECT-TYPE
            SYNTAX IpAddress
            MAX-ACCESS read-create
            STATUS current
            DESCRIPTION
                "Intercom Prefix Destination IP address."
            ::= { hwBrasSbcIntercomPrefixEntry 2 }

        hwBrasSbcIntercomPrefixSrcAddr OBJECT-TYPE
            SYNTAX IpAddress
            MAX-ACCESS read-create
            STATUS current
            DESCRIPTION
                "Intercom Prefix Local IP address."
            ::= { hwBrasSbcIntercomPrefixEntry 3 }

        hwBrasSbcIntercomPrefixRowStatus OBJECT-TYPE
            SYNTAX RowStatus
            MAX-ACCESS read-create
            STATUS current
            DESCRIPTION
                "Intercom Prefix Row Status."
            ::= { hwBrasSbcIntercomPrefixEntry 4 }

        hwBrasSbcSessionCar OBJECT IDENTIFIER ::= { hwBrasSbcAdvance 4 }

        hwBrasSbcSessionCarLeaves OBJECT IDENTIFIER ::= { hwBrasSbcSessionCar 1 }

        hwBrasSbcSessionCarEnable OBJECT-TYPE
            SYNTAX HWBrasEnabledStatus
            MAX-ACCESS read-write
            STATUS current
            DESCRIPTION
                "Session Car Enable Status.
                Default: disabled"
            DEFVAL { disabled }
            ::= { hwBrasSbcSessionCarLeaves 1 }

        hwBrasSbcSessionCarTables OBJECT IDENTIFIER ::= { hwBrasSbcSessionCar 2 }

        hwBrasSbcSessionCarDegreeTable OBJECT-TYPE
            SYNTAX SEQUENCE OF HwBrasSbcSessionCarDegreeEntry
            MAX-ACCESS not-accessible
            STATUS current
            DESCRIPTION
                "Session Car Degree Table."
            ::= { hwBrasSbcSessionCarTables 1 }

        hwBrasSbcSessionCarDegreeEntry OBJECT-TYPE
            SYNTAX HwBrasSbcSessionCarDegreeEntry
            MAX-ACCESS not-accessible
            STATUS current
            DESCRIPTION
                "Session Car Degree Table Entry."
            INDEX { hwBrasSbcSessionCarDegreeID }
            ::= { hwBrasSbcSessionCarDegreeTable 1 }

        HwBrasSbcSessionCarDegreeEntry ::=
            SEQUENCE {
                hwBrasSbcSessionCarDegreeID
                    INTEGER,
                hwBrasSbcSessionCarDegreeBandWidth
                    Unsigned32,
                hwBrasSbcSessionCarDegreeDscp
                    INTEGER,
                hwBrasSbcSessionCarDegreeRowStatus
                    RowStatus
             }

        hwBrasSbcSessionCarDegreeID OBJECT-TYPE
            SYNTAX INTEGER (1..16)
            MAX-ACCESS not-accessible
            STATUS current
            DESCRIPTION
                "Session Car Degree Table ID."
            ::= { hwBrasSbcSessionCarDegreeEntry 1 }

        hwBrasSbcSessionCarDegreeBandWidth OBJECT-TYPE
            SYNTAX Unsigned32 (8..131071)
            MAX-ACCESS read-write
            STATUS current
            DESCRIPTION
                "Session Car Degree Table Brand Width Information."
            ::= { hwBrasSbcSessionCarDegreeEntry 2 }

        hwBrasSbcSessionCarDegreeDscp OBJECT-TYPE
            SYNTAX INTEGER (0..64)
            MAX-ACCESS read-write
            STATUS current
            DESCRIPTION
                "Session Car Degree Table Dscp Information."
            ::= { hwBrasSbcSessionCarDegreeEntry 3 }

        hwBrasSbcSessionCarDegreeRowStatus OBJECT-TYPE
            SYNTAX RowStatus
            MAX-ACCESS read-create
            STATUS current
            DESCRIPTION
                "Session Car Degree Table Row Status."
            ::= { hwBrasSbcSessionCarDegreeEntry 4 }

        hwBrasSbcSessionCarRuleTable OBJECT-TYPE
            SYNTAX SEQUENCE OF HwBrasSbcSessionCarRuleEntry
            MAX-ACCESS not-accessible
            STATUS current
            DESCRIPTION
                "Session Car Rule Table."
            ::= { hwBrasSbcSessionCarTables 2 }

        hwBrasSbcSessionCarRuleEntry OBJECT-TYPE
            SYNTAX HwBrasSbcSessionCarRuleEntry
            MAX-ACCESS not-accessible
            STATUS current
            DESCRIPTION
                "Session Car Rule Table Entry."
            INDEX { hwBrasSbcSessionCarRuleID }
            ::= { hwBrasSbcSessionCarRuleTable 1 }

        HwBrasSbcSessionCarRuleEntry ::=
            SEQUENCE {
                hwBrasSbcSessionCarRuleID
                    INTEGER,
                hwBrasSbcSessionCarRuleName
                    DisplayString,
                hwBrasSbcSessionCarRuleDegreeID
                    INTEGER,
                hwBrasSbcSessionCarRuleDegreeBandWidth
                    Unsigned32,
                hwBrasSbcSessionCarRuleDegreeDscp
                    INTEGER,
                hwBrasSbcSessionCarRuleRowStatus
                    RowStatus
             }

        hwBrasSbcSessionCarRuleID OBJECT-TYPE
            SYNTAX INTEGER (1..255)
            MAX-ACCESS not-accessible
            STATUS current
            DESCRIPTION
                "Session Car Rule Table ID."
            ::= { hwBrasSbcSessionCarRuleEntry 1 }

        hwBrasSbcSessionCarRuleName OBJECT-TYPE
            SYNTAX DisplayString (SIZE (1..63))
            MAX-ACCESS read-create
            STATUS current
            DESCRIPTION
                "Session Car Rule Table Name."
            ::= { hwBrasSbcSessionCarRuleEntry 2 }

        hwBrasSbcSessionCarRuleDegreeID OBJECT-TYPE
            SYNTAX INTEGER (1..16)
            MAX-ACCESS read-create
            STATUS current
            DESCRIPTION
                "Session Car Rule Table Degree ID."
            ::= { hwBrasSbcSessionCarRuleEntry 3 }

        hwBrasSbcSessionCarRuleDegreeBandWidth OBJECT-TYPE
            SYNTAX Unsigned32 (8..131071)
            MAX-ACCESS read-only
            STATUS current
            DESCRIPTION
                "Session Car Rule Table Degree Band Width."
            ::= { hwBrasSbcSessionCarRuleEntry 4 }

        hwBrasSbcSessionCarRuleDegreeDscp OBJECT-TYPE
            SYNTAX INTEGER (0..64)
            MAX-ACCESS read-only
            STATUS current
            DESCRIPTION
                "Session Car Rule Table Degree Description."
            ::= { hwBrasSbcSessionCarRuleEntry 5 }

        hwBrasSbcSessionCarRuleRowStatus OBJECT-TYPE
            SYNTAX RowStatus
            MAX-ACCESS read-create
            STATUS current
            DESCRIPTION
                "Session Car Rule Table Row Status."
            ::= { hwBrasSbcSessionCarRuleEntry 6 }

        hwBrasSbcSecurity OBJECT IDENTIFIER ::= { hwBrasSbcAdvance 5 }

        hwBrasSbcSecurityLeaves OBJECT IDENTIFIER ::= { hwBrasSbcSecurity 1 }

        hwBrasSbcDefendEnable OBJECT-TYPE
            SYNTAX HWBrasEnabledStatus
            MAX-ACCESS read-write
            STATUS current
            DESCRIPTION
                "Signaling Defend Enable Status.
                Default: enabled"
            DEFVAL { enabled }
            ::= { hwBrasSbcSecurityLeaves 1 }

        hwBrasSbcDefendMode OBJECT-TYPE
            SYNTAX INTEGER
                {
                auto(1),
                manual(2)
                }
            MAX-ACCESS read-write
            STATUS current
            DESCRIPTION
                "Signaling Defend Mode Status.
                1 auto
                2 manual
                Default: auto"
            DEFVAL { auto }
            ::= { hwBrasSbcSecurityLeaves 2 }

        hwBrasSbcDefendActionLogEnable OBJECT-TYPE
            SYNTAX HWBrasEnabledStatus
            MAX-ACCESS read-write
            STATUS current
            DESCRIPTION
                "Signaling Defend Action log Status.
                Default: disabled"
            DEFVAL { disabled }
            ::= { hwBrasSbcSecurityLeaves 3 }

        hwBrasSbcCacEnable OBJECT-TYPE
            SYNTAX HWBrasEnabledStatus
            MAX-ACCESS read-write
            STATUS current
            DESCRIPTION
                "Cac Enable Status.
                Default: enabled"
            DEFVAL { enabled }
            ::= { hwBrasSbcSecurityLeaves 4 }

        hwBrasSbcCacActionLogStatus OBJECT-TYPE
            SYNTAX INTEGER
                {
                denyAndNoLog(1),
                permitAndNoLog(2),
                denyAndLog(3),
                permitAndLog(4)
                }
            MAX-ACCESS read-write
            STATUS current
            DESCRIPTION
                "Cac Action log Status.
                1 deny and no log
                2 permit and no log
                3 deny and log
                4 permit and log
                Default: deny and no log"
            DEFVAL { denyAndNoLog }
            ::= { hwBrasSbcSecurityLeaves 5 }

        hwBrasSbcDefendExtStatus OBJECT-TYPE
            SYNTAX HWBrasEnabledStatus
            MAX-ACCESS read-write
            STATUS current
            DESCRIPTION
                "Description."
            DEFVAL { disabled }
            ::= { hwBrasSbcSecurityLeaves 6 }

        hwBrasSbcSignalingCarStatus OBJECT-TYPE
            SYNTAX HWBrasEnabledStatus
            MAX-ACCESS read-write
            STATUS current
            DESCRIPTION
                "Description."
            DEFVAL { disabled }
            ::= { hwBrasSbcSecurityLeaves 7 }

        hwBrasSbcIPCarStatus OBJECT-TYPE
            SYNTAX HWBrasEnabledStatus
            MAX-ACCESS read-write
            STATUS current
            DESCRIPTION
                "Description."
            DEFVAL { disabled }
            ::= { hwBrasSbcSecurityLeaves 8 }

        hwBrasSbcDynamicStatus OBJECT-TYPE
            SYNTAX HWBrasEnabledStatus
            MAX-ACCESS read-write
            STATUS current
            DESCRIPTION
                "Description."
            DEFVAL { disabled }
            ::= { hwBrasSbcSecurityLeaves 9 }

        hwBrasSbcSecurityTables OBJECT IDENTIFIER ::= { hwBrasSbcSecurity 2 }

        hwBrasSbcDefendConnectRateTable OBJECT-TYPE
            SYNTAX SEQUENCE OF HwBrasSbcDefendConnectRateEntry
            MAX-ACCESS not-accessible
            STATUS current
            DESCRIPTION
                "Signaling Defend Limited Connect Rate Table."
            ::= { hwBrasSbcSecurityTables 1 }

        hwBrasSbcDefendConnectRateEntry OBJECT-TYPE
            SYNTAX HwBrasSbcDefendConnectRateEntry
            MAX-ACCESS not-accessible
            STATUS current
            DESCRIPTION
                "Signaling Defend Connect Rate Table Entry."
            INDEX { hwBrasSbcDefendConnectRateProtocol }
            ::= { hwBrasSbcDefendConnectRateTable 1 }

        HwBrasSbcDefendConnectRateEntry ::=
            SEQUENCE {
                hwBrasSbcDefendConnectRateProtocol
                    HWBrasSecurityProtocol,
                hwBrasSbcDefendConnectRateThreshold
                    Unsigned32,
                hwBrasSbcDefendConnectRatePercent
                    Unsigned32,
                hwBrasSbcDefendConnectRateRowStatus
                    RowStatus
             }

        hwBrasSbcDefendConnectRateProtocol OBJECT-TYPE
            SYNTAX HWBrasSecurityProtocol
            MAX-ACCESS not-accessible
            STATUS current
            DESCRIPTION
                "Protocol."
            ::= { hwBrasSbcDefendConnectRateEntry 1 }

        hwBrasSbcDefendConnectRateThreshold OBJECT-TYPE
            SYNTAX Unsigned32 (6..60000)
            MAX-ACCESS read-write
            STATUS current
            DESCRIPTION
                "Threshold."
            ::= { hwBrasSbcDefendConnectRateEntry 2 }

        hwBrasSbcDefendConnectRatePercent OBJECT-TYPE
            SYNTAX Unsigned32 (60..100)
            MAX-ACCESS read-write
            STATUS current
            DESCRIPTION
                "Percent."
            DEFVAL { 80 }
            ::= { hwBrasSbcDefendConnectRateEntry 3 }

        hwBrasSbcDefendConnectRateRowStatus OBJECT-TYPE
            SYNTAX RowStatus
            MAX-ACCESS read-write
            STATUS current
            DESCRIPTION
                "RowStatus."
            ::= { hwBrasSbcDefendConnectRateEntry 4 }

        hwBrasSbcDefendUserConnectRateTable OBJECT-TYPE
            SYNTAX SEQUENCE OF HwBrasSbcDefendUserConnectRateEntry
            MAX-ACCESS not-accessible
            STATUS current
            DESCRIPTION
                "Signaling Defend Limited Per-user Connect Rate Table."
            ::= { hwBrasSbcSecurityTables 2 }

        hwBrasSbcDefendUserConnectRateEntry OBJECT-TYPE
            SYNTAX HwBrasSbcDefendUserConnectRateEntry
            MAX-ACCESS not-accessible
            STATUS current
            DESCRIPTION
                "Signaling Defend Per-user Connect Rate Table Entry."
            INDEX { hwBrasSbcDefendUserConnectRateProtocol }
            ::= { hwBrasSbcDefendUserConnectRateTable 1 }

        HwBrasSbcDefendUserConnectRateEntry ::=
            SEQUENCE {
                hwBrasSbcDefendUserConnectRateProtocol
                    HWBrasSecurityProtocol,
                hwBrasSbcDefendUserConnectRateThreshold
                    Unsigned32,
                hwBrasSbcDefendUserConnectRatePercent
                    Unsigned32,
                hwBrasSbcDefendUserConnectRateRowStatus
                    RowStatus
             }

        hwBrasSbcDefendUserConnectRateProtocol OBJECT-TYPE
            SYNTAX HWBrasSecurityProtocol
            MAX-ACCESS not-accessible
            STATUS current
            DESCRIPTION
                "Protocol."
            ::= { hwBrasSbcDefendUserConnectRateEntry 1 }

        hwBrasSbcDefendUserConnectRateThreshold OBJECT-TYPE
            SYNTAX Unsigned32 (6..60000)
            MAX-ACCESS read-write
            STATUS current
            DESCRIPTION
                "Threshold."
            ::= { hwBrasSbcDefendUserConnectRateEntry 2 }

        hwBrasSbcDefendUserConnectRatePercent OBJECT-TYPE
            SYNTAX Unsigned32 (60..100)
            MAX-ACCESS read-write
            STATUS current
            DESCRIPTION
                "Percent."
            DEFVAL { 80 }
            ::= { hwBrasSbcDefendUserConnectRateEntry 3 }

        hwBrasSbcDefendUserConnectRateRowStatus OBJECT-TYPE
            SYNTAX RowStatus
            MAX-ACCESS read-write
            STATUS current
            DESCRIPTION
                "RowStatus."
            ::= { hwBrasSbcDefendUserConnectRateEntry 4 }

        hwBrasSbcCacCallTotalTable OBJECT-TYPE
            SYNTAX SEQUENCE OF HwBrasSbcCacCallTotalEntry
            MAX-ACCESS not-accessible
            STATUS current
            DESCRIPTION
                "CAC Limited Simultanous Call Total Table."
            ::= { hwBrasSbcSecurityTables 3 }

        hwBrasSbcCacCallTotalEntry OBJECT-TYPE
            SYNTAX HwBrasSbcCacCallTotalEntry
            MAX-ACCESS not-accessible
            STATUS current
            DESCRIPTION
                "CAC Simultanous Call Total Table Entry."
            INDEX { hwBrasSbcCacCallTotalProtocol }
            ::= { hwBrasSbcCacCallTotalTable 1 }

        HwBrasSbcCacCallTotalEntry ::=
            SEQUENCE {
                hwBrasSbcCacCallTotalProtocol
                    HWBrasSecurityProtocol,
                hwBrasSbcCacCallTotalThreshold
                    Unsigned32,
                hwBrasSbcCacCallTotalPercent
                    Unsigned32,
                hwBrasSbcCacCallTotalRowStatus
                    RowStatus
             }

        hwBrasSbcCacCallTotalProtocol OBJECT-TYPE
            SYNTAX HWBrasSecurityProtocol
            MAX-ACCESS not-accessible
            STATUS current
            DESCRIPTION
                "Protocol."
            ::= { hwBrasSbcCacCallTotalEntry 1 }

        hwBrasSbcCacCallTotalThreshold OBJECT-TYPE
            SYNTAX Unsigned32 (60..60000)
            MAX-ACCESS read-write
            STATUS current
            DESCRIPTION
                "Threshold."
            ::= { hwBrasSbcCacCallTotalEntry 2 }

        hwBrasSbcCacCallTotalPercent OBJECT-TYPE
            SYNTAX Unsigned32 (60..100)
            MAX-ACCESS read-write
            STATUS current
            DESCRIPTION
                "Percent."
            DEFVAL { 80 }
            ::= { hwBrasSbcCacCallTotalEntry 3 }

        hwBrasSbcCacCallTotalRowStatus OBJECT-TYPE
            SYNTAX RowStatus
            MAX-ACCESS read-write
            STATUS current
            DESCRIPTION
                "RowStatus."
            ::= { hwBrasSbcCacCallTotalEntry 4 }

        hwBrasSbcCacCallRateTable OBJECT-TYPE
            SYNTAX SEQUENCE OF HwBrasSbcCacCallRateEntry
            MAX-ACCESS not-accessible
            STATUS current
            DESCRIPTION
                "CAC Limited Per-user Simultanous Call Rate Table."
            ::= { hwBrasSbcSecurityTables 4 }

        hwBrasSbcCacCallRateEntry OBJECT-TYPE
            SYNTAX HwBrasSbcCacCallRateEntry
            MAX-ACCESS not-accessible
            STATUS current
            DESCRIPTION
                "CAC Per-user Simultanous Call Rate Table Entry."
            INDEX { hwBrasSbcCacCallRateProtocol }
            ::= { hwBrasSbcCacCallRateTable 1 }

        HwBrasSbcCacCallRateEntry ::=
            SEQUENCE {
                hwBrasSbcCacCallRateProtocol
                    HWBrasSecurityProtocol,
                hwBrasSbcCacCallRateThreshold
                    Unsigned32,
                hwBrasSbcCacCallRatePercent
                    Unsigned32,
                hwBrasSbcCacCallRateRowStatus
                    RowStatus
             }

        hwBrasSbcCacCallRateProtocol OBJECT-TYPE
            SYNTAX HWBrasSecurityProtocol
            MAX-ACCESS not-accessible
            STATUS current
            DESCRIPTION
                "Protocol."
            ::= { hwBrasSbcCacCallRateEntry 1 }

        hwBrasSbcCacCallRateThreshold OBJECT-TYPE
            SYNTAX Unsigned32 (6..600)
            MAX-ACCESS read-write
            STATUS current
            DESCRIPTION
                "Threshold."
            ::= { hwBrasSbcCacCallRateEntry 2 }

        hwBrasSbcCacCallRatePercent OBJECT-TYPE
            SYNTAX Unsigned32 (60..100)
            MAX-ACCESS read-write
            STATUS current
            DESCRIPTION
                "Percent."
            DEFVAL { 80 }
            ::= { hwBrasSbcCacCallRateEntry 3 }

        hwBrasSbcCacCallRateRowStatus OBJECT-TYPE
            SYNTAX RowStatus
            MAX-ACCESS read-write
            STATUS current
            DESCRIPTION
                "RowStatus."
            ::= { hwBrasSbcCacCallRateEntry 4 }

        hwBrasSbcCacRegTotalTable OBJECT-TYPE
            SYNTAX SEQUENCE OF HwBrasSbcCacRegTotalEntry
            MAX-ACCESS not-accessible
            STATUS current
            DESCRIPTION
                "CAC Limited Register Total Table."
            ::= { hwBrasSbcSecurityTables 5 }

        hwBrasSbcCacRegTotalEntry OBJECT-TYPE
            SYNTAX HwBrasSbcCacRegTotalEntry
            MAX-ACCESS not-accessible
            STATUS current
            DESCRIPTION
                "CAC Register Total Table Entry."
            INDEX { hwBrasSbcCacRegTotalProtocol }
            ::= { hwBrasSbcCacRegTotalTable 1 }

        HwBrasSbcCacRegTotalEntry ::=
            SEQUENCE {
                hwBrasSbcCacRegTotalProtocol
                    HWBrasSecurityProtocol,
                hwBrasSbcCacRegTotalThreshold
                    Unsigned32,
                hwBrasSbcCacRegTotalPercent
                    Unsigned32,
                hwBrasSbcCacRegTotalRowStatus
                    RowStatus
             }

        hwBrasSbcCacRegTotalProtocol OBJECT-TYPE
            SYNTAX HWBrasSecurityProtocol
            MAX-ACCESS not-accessible
            STATUS current
            DESCRIPTION
                "Protocol."
            ::= { hwBrasSbcCacRegTotalEntry 1 }

        hwBrasSbcCacRegTotalThreshold OBJECT-TYPE
            SYNTAX Unsigned32 (100..60000)
            MAX-ACCESS read-write
            STATUS current
            DESCRIPTION
                "Threshold."
            ::= { hwBrasSbcCacRegTotalEntry 2 }

        hwBrasSbcCacRegTotalPercent OBJECT-TYPE
            SYNTAX Unsigned32 (60..100)
            MAX-ACCESS read-write
            STATUS current
            DESCRIPTION
                "Percent."
            DEFVAL { 80 }
            ::= { hwBrasSbcCacRegTotalEntry 3 }

        hwBrasSbcCacRegTotalRowStatus OBJECT-TYPE
            SYNTAX RowStatus
            MAX-ACCESS read-write
            STATUS current
            DESCRIPTION
                "RowStatus."
            ::= { hwBrasSbcCacRegTotalEntry 4 }

        hwBrasSbcCacRegRateTable OBJECT-TYPE
            SYNTAX SEQUENCE OF HwBrasSbcCacRegRateEntry
            MAX-ACCESS not-accessible
            STATUS current
            DESCRIPTION
                "CAC Limited Per-user Register Rate Table."
            ::= { hwBrasSbcSecurityTables 6 }

        hwBrasSbcCacRegRateEntry OBJECT-TYPE
            SYNTAX HwBrasSbcCacRegRateEntry
            MAX-ACCESS not-accessible
            STATUS current
            DESCRIPTION
                "CAC Per-user Register Rate Table Entry."
            INDEX { hwBrasSbcCacRegRateProtocol }
            ::= { hwBrasSbcCacRegRateTable 1 }

        HwBrasSbcCacRegRateEntry ::=
            SEQUENCE {
                hwBrasSbcCacRegRateProtocol
                    HWBrasSecurityProtocol,
                hwBrasSbcCacRegRateThreshold
                    Unsigned32,
                hwBrasSbcCacRegRatePercent
                    Unsigned32,
                hwBrasSbcCacRegRateRowStatus
                    RowStatus
             }

        hwBrasSbcCacRegRateProtocol OBJECT-TYPE
            SYNTAX HWBrasSecurityProtocol
            MAX-ACCESS not-accessible
            STATUS current
            DESCRIPTION
                "Protocol."
            ::= { hwBrasSbcCacRegRateEntry 1 }

        hwBrasSbcCacRegRateThreshold OBJECT-TYPE
            SYNTAX Unsigned32 (6..600)
            MAX-ACCESS read-write
            STATUS current
            DESCRIPTION
                "Threshold."
            ::= { hwBrasSbcCacRegRateEntry 2 }

        hwBrasSbcCacRegRatePercent OBJECT-TYPE
            SYNTAX Unsigned32 (60..100)
            MAX-ACCESS read-write
            STATUS current
            DESCRIPTION
                "Percent."
            DEFVAL { 80 }
            ::= { hwBrasSbcCacRegRateEntry 3 }

        hwBrasSbcCacRegRateRowStatus OBJECT-TYPE
            SYNTAX RowStatus
            MAX-ACCESS read-write
            STATUS current
            DESCRIPTION
                "RowStatus."
            ::= { hwBrasSbcCacRegRateEntry 4 }

        hwBrasSbcIPCarBandwidthTable OBJECT-TYPE
            SYNTAX SEQUENCE OF HwBrasSbcIPCarBandwidthEntry
            MAX-ACCESS not-accessible
            STATUS current
            DESCRIPTION
                "Description."
            ::= { hwBrasSbcSecurityTables 7 }

        hwBrasSbcIPCarBandwidthEntry OBJECT-TYPE
            SYNTAX HwBrasSbcIPCarBandwidthEntry
            MAX-ACCESS not-accessible
            STATUS current
            DESCRIPTION
                "Description."
            INDEX { hwBrasSbcIPCarBWVpn, hwBrasSbcIPCarBWAddress }
            ::= { hwBrasSbcIPCarBandwidthTable 1 }

        HwBrasSbcIPCarBandwidthEntry ::=
            SEQUENCE {
                hwBrasSbcIPCarBWVpn
                    Unsigned32,
                hwBrasSbcIPCarBWAddress
                    IpAddress,
                hwBrasSbcIPCarBWValue
                    Unsigned32,
                hwBrasSbcIPCarBWRowStatus
                    RowStatus
             }

        hwBrasSbcIPCarBWVpn OBJECT-TYPE
            SYNTAX Unsigned32 (0..1023)
            MAX-ACCESS not-accessible
            STATUS current
            DESCRIPTION
                "Description."
            ::= { hwBrasSbcIPCarBandwidthEntry 1 }

        hwBrasSbcIPCarBWAddress OBJECT-TYPE
            SYNTAX IpAddress
            MAX-ACCESS not-accessible
            STATUS current
            DESCRIPTION
                "Description."
            ::= { hwBrasSbcIPCarBandwidthEntry 2 }

        hwBrasSbcIPCarBWValue OBJECT-TYPE
            SYNTAX Unsigned32 (8..1000000000)
            MAX-ACCESS read-create
            STATUS current
            DESCRIPTION
                "Description."
            DEFVAL { 1000000000 }
            ::= { hwBrasSbcIPCarBandwidthEntry 3 }

        hwBrasSbcIPCarBWRowStatus OBJECT-TYPE
            SYNTAX RowStatus
            MAX-ACCESS read-create
            STATUS current
            DESCRIPTION
                "Description."
            ::= { hwBrasSbcIPCarBandwidthEntry 4 }

        hwBrasSbcUdpTunnel OBJECT IDENTIFIER ::= { hwBrasSbcAdvance 6 }

        hwBrasSbcUdpTunnelLeaves OBJECT IDENTIFIER ::= { hwBrasSbcUdpTunnel 1 }

        hwBrasSbcUdpTunnelEnable OBJECT-TYPE
            SYNTAX HWBrasEnabledStatus
            MAX-ACCESS read-write
            STATUS current
            DESCRIPTION
                "UdpTunnelEnable
                Udp Tunnel Status.
                Default: disabled.Value range(disabled[1],server[2],client[3])"
            DEFVAL { disabled }
            ::= { hwBrasSbcUdpTunnelLeaves 1 }

        hwBrasSbcUdpTunnelType OBJECT-TYPE
            SYNTAX INTEGER
                {
                notype(1),
                server(2),
                client(3)
                }
            MAX-ACCESS read-write
            STATUS current
            DESCRIPTION
                "UdpTunnelType
                Udp Tunnel Type.
                1 no type
                2 server
                3 client"
            ::= { hwBrasSbcUdpTunnelLeaves 2 }

        hwBrasSbcUdpTunnelSctpAddr OBJECT-TYPE
            SYNTAX IpAddress
            MAX-ACCESS read-write
            STATUS current
            DESCRIPTION
                "SctpAddress
                Udp Tunnel Sctp Address.
                Default 0.0.0.0 no address."
            ::= { hwBrasSbcUdpTunnelLeaves 3 }

        hwBrasSbcUdpTunnelTunnelTimer OBJECT-TYPE
            SYNTAX Unsigned32 (1..65535)
            UNITS "seconds"
            MAX-ACCESS read-write
            STATUS current
            DESCRIPTION
                "UdpTimerLength
                Udp tunnel tunnel mode node timer length
                Range: 1-65535
                Unit: seconds
                Default: 900"
            DEFVAL { 900 }
            ::= { hwBrasSbcUdpTunnelLeaves 4 }

        hwBrasSbcUdpTunnelTransportTimer OBJECT-TYPE
            SYNTAX Unsigned32 (1..65535)
            UNITS "seconds"
            MAX-ACCESS read-write
            STATUS current
            DESCRIPTION
                "SctpTimerLength
                Udp tunnel sctp node timer length.
                Range: 1-65535
                Unit: seconds
                Default: 900"
            DEFVAL { 900 }
            ::= { hwBrasSbcUdpTunnelLeaves 5 }

        hwBrasSbcUdpTunnelTables OBJECT IDENTIFIER ::= { hwBrasSbcUdpTunnel 2 }

        hwBrasSbcUdpTunnelPoolTable OBJECT-TYPE
            SYNTAX SEQUENCE OF HwBrasSbcUdpTunnelPoolEntry
            MAX-ACCESS not-accessible
            STATUS current
            DESCRIPTION
                "Udp Tunnel Address Pool Table."
            ::= { hwBrasSbcUdpTunnelTables 1 }

        hwBrasSbcUdpTunnelPoolEntry OBJECT-TYPE
            SYNTAX HwBrasSbcUdpTunnelPoolEntry
            MAX-ACCESS not-accessible
            STATUS current
            DESCRIPTION
                "Udp Tunnel Address Pool Table Entry."
            INDEX { hwBrasSbcUdpTunnelPoolIndex }
            ::= { hwBrasSbcUdpTunnelPoolTable 1 }

        HwBrasSbcUdpTunnelPoolEntry ::=
            SEQUENCE {
                hwBrasSbcUdpTunnelPoolIndex
                    Unsigned32,
                hwBrasSbcUdpTunnelPoolStartIP
                    IpAddress,
                hwBrasSbcUdpTunnelPoolEndIP
                    IpAddress,
                hwBrasSbcUdpTunnelPoolRowStatus
                    RowStatus
             }

        hwBrasSbcUdpTunnelPoolIndex OBJECT-TYPE
            SYNTAX Unsigned32 (1)
            MAX-ACCESS not-accessible
            STATUS current
            DESCRIPTION
                "Index for Pool.
                "
            ::= { hwBrasSbcUdpTunnelPoolEntry 1 }

        hwBrasSbcUdpTunnelPoolStartIP OBJECT-TYPE
            SYNTAX IpAddress
            MAX-ACCESS read-write
            STATUS current
            DESCRIPTION
                "Start Address.
                Default: 172.168.181.1"
            DEFVAL { '7FA8B501'h }
            ::= { hwBrasSbcUdpTunnelPoolEntry 2 }

        hwBrasSbcUdpTunnelPoolEndIP OBJECT-TYPE
            SYNTAX IpAddress
            MAX-ACCESS read-write
            STATUS current
            DESCRIPTION
                "End Address.
                Default: 172.168.239.152"
            DEFVAL { '7FA8EF98'h }
            ::= { hwBrasSbcUdpTunnelPoolEntry 3 }

        hwBrasSbcUdpTunnelPoolRowStatus OBJECT-TYPE
            SYNTAX RowStatus
            MAX-ACCESS read-write
            STATUS current
            DESCRIPTION
                "Row Status."
            ::= { hwBrasSbcUdpTunnelPoolEntry 4 }

        hwBrasSbcUdpTunnelPortTable OBJECT-TYPE
            SYNTAX SEQUENCE OF HwBrasSbcUdpTunnelPortEntry
            MAX-ACCESS not-accessible
            STATUS current
            DESCRIPTION
                "Udp Tunnel Port Table."
            ::= { hwBrasSbcUdpTunnelTables 2 }

        hwBrasSbcUdpTunnelPortEntry OBJECT-TYPE
            SYNTAX HwBrasSbcUdpTunnelPortEntry
            MAX-ACCESS not-accessible
            STATUS current
            DESCRIPTION
                "Udp Tunnel Port Table Entry."
            INDEX { hwBrasSbcUdpTunnelPortProtocol, hwBrasSbcUdpTunnelPortPort }
            ::= { hwBrasSbcUdpTunnelPortTable 1 }

        HwBrasSbcUdpTunnelPortEntry ::=
            SEQUENCE {
                hwBrasSbcUdpTunnelPortProtocol
                    INTEGER,
                hwBrasSbcUdpTunnelPortPort
                    Unsigned32,
                hwBrasSbcUdpTunnelPortRowStatus
                    RowStatus
             }

        hwBrasSbcUdpTunnelPortProtocol OBJECT-TYPE
            SYNTAX INTEGER
                {
                udp(1),
                tcp(2)
                }
            MAX-ACCESS not-accessible
            STATUS current
            DESCRIPTION
                "Support Protocol of Udp Tunnel.
                1 udp
                2 tcp"
            ::= { hwBrasSbcUdpTunnelPortEntry 1 }

        hwBrasSbcUdpTunnelPortPort OBJECT-TYPE
            SYNTAX Unsigned32 (1..65535)
            MAX-ACCESS not-accessible
            STATUS current
            DESCRIPTION
                "Port."
            ::= { hwBrasSbcUdpTunnelPortEntry 2 }

        hwBrasSbcUdpTunnelPortRowStatus OBJECT-TYPE
            SYNTAX RowStatus
            MAX-ACCESS read-create
            STATUS current
            DESCRIPTION
                "Row Status."
            ::= { hwBrasSbcUdpTunnelPortEntry 3 }

        hwBrasSbcUdpTunnelIfPortTable OBJECT-TYPE
            SYNTAX SEQUENCE OF HwBrasSbcUdpTunnelIfPortEntry
            MAX-ACCESS not-accessible
            STATUS current
            DESCRIPTION
                "Udp Tunnel Interface Port Table."
            ::= { hwBrasSbcUdpTunnelTables 3 }

        hwBrasSbcUdpTunnelIfPortEntry OBJECT-TYPE
            SYNTAX HwBrasSbcUdpTunnelIfPortEntry
            MAX-ACCESS not-accessible
            STATUS current
            DESCRIPTION
                "Udp Tunnel Interface Port Table Entry."
            INDEX { entPhysicalIndex, hwBrasSbcUdpTunnelIfPortAddr, hwBrasSbcUdpTunnelIfPortPort }
            ::= { hwBrasSbcUdpTunnelIfPortTable 1 }

        HwBrasSbcUdpTunnelIfPortEntry ::=
            SEQUENCE {
                hwBrasSbcUdpTunnelIfPortAddr
                    IpAddress,
                hwBrasSbcUdpTunnelIfPortPort
                    Unsigned32,
                hwBrasSbcUdpTunnelIfPortRowStatus
                    RowStatus
             }

        hwBrasSbcUdpTunnelIfPortAddr OBJECT-TYPE
            SYNTAX IpAddress
            MAX-ACCESS not-accessible
            STATUS current
            DESCRIPTION
                "Address in the interface."
            ::= { hwBrasSbcUdpTunnelIfPortEntry 2 }

        hwBrasSbcUdpTunnelIfPortPort OBJECT-TYPE
            SYNTAX Unsigned32 (1..9999)
            MAX-ACCESS not-accessible
            STATUS current
            DESCRIPTION
                "Port."
            ::= { hwBrasSbcUdpTunnelIfPortEntry 3 }

        hwBrasSbcUdpTunnelIfPortRowStatus OBJECT-TYPE
            SYNTAX RowStatus
            MAX-ACCESS read-create
            STATUS current
            DESCRIPTION
                "Row Status."
            ::= { hwBrasSbcUdpTunnelIfPortEntry 4 }

        hwBrasSbcIms OBJECT IDENTIFIER ::= { hwBrasSbcAdvance 7 }

        hwBrasSbcImsLeaves OBJECT IDENTIFIER ::= { hwBrasSbcIms 1 }

        hwBrasSbcImsQosEnable OBJECT-TYPE
            SYNTAX HWBrasEnabledStatus
            MAX-ACCESS read-write
            STATUS current
            DESCRIPTION
                "Ims QoS Enable Status.
                default: disabled"
            DEFVAL { disabled }
            ::= { hwBrasSbcImsLeaves 1 }

        hwBrasSbcImsMediaProxyEnable OBJECT-TYPE
            SYNTAX HWBrasEnabledStatus
            MAX-ACCESS read-write
            STATUS current
            DESCRIPTION
                "Ims Mediaproxy Enable Status.
                default: disabled"
            DEFVAL { disabled }
            ::= { hwBrasSbcImsLeaves 2 }

        hwBrasSbcImsQosLogEnable OBJECT-TYPE
            SYNTAX HWBrasEnabledStatus
            MAX-ACCESS read-write
            STATUS current
            DESCRIPTION
                "Ims QoS Syslog Enable Status.
                default: enabled"
            DEFVAL { enabled }
            ::= { hwBrasSbcImsLeaves 3 }

        hwBrasSbcImsMediaProxyLogEnable OBJECT-TYPE
            SYNTAX HWBrasEnabledStatus
            MAX-ACCESS read-write
            STATUS current
            DESCRIPTION
                "Ims Mediaproxy Syslog Enable Status.
                default: enabled"
            DEFVAL { enabled }
            ::= { hwBrasSbcImsLeaves 4 }

        hwBrasSbcImsMGStatus OBJECT-TYPE
            SYNTAX HWBrasEnabledStatus
            MAX-ACCESS read-write
            STATUS current
            DESCRIPTION
                "Ims MG Enable Status.
                default: disabled"
            DEFVAL { disabled }
            ::= { hwBrasSbcImsLeaves 5 }

        hwBrasSbcImsMGConnectTimer OBJECT-TYPE
            SYNTAX Unsigned32 (100..3600000)
            UNITS "ms"
            MAX-ACCESS read-write
            STATUS current
            DESCRIPTION
                "MG Connect Aging Time.
                Range: 100-3600000
                Default: 1000
                Unit: millisecond"
            DEFVAL { 1000 }
            ::= { hwBrasSbcImsLeaves 6 }

        hwBrasSbcImsMGAgingTimer OBJECT-TYPE
            SYNTAX Unsigned32 (0..36000)
            UNITS "s"
            MAX-ACCESS read-write
            STATUS current
            DESCRIPTION
                "MG Aging Time.
                Range: 0-36000
                Default: 120
                Unit: second"
            DEFVAL { 120 }
            ::= { hwBrasSbcImsLeaves 7 }

        hwBrasSbcImsMGCallSessionTimer OBJECT-TYPE
            SYNTAX Unsigned32 (1..14400)
            UNITS "m"
            MAX-ACCESS read-write
            STATUS current
            DESCRIPTION
                "MG Call Session Aging Time.
                Range: 1-14400
                Default: 30
                Unit: minute"
            DEFVAL { 30 }
            ::= { hwBrasSbcImsLeaves 8 }

        hwBrasSbcSctpStatus OBJECT-TYPE
            SYNTAX HWBrasEnabledStatus
            MAX-ACCESS read-write
            STATUS current
            DESCRIPTION
                "Sctp Enable Status.
                default: disabled"
            DEFVAL { disabled }
            ::= { hwBrasSbcImsLeaves 9 }

        -- ewei add begin
        hwBrasSbcIdlecutRtcpTimer OBJECT-TYPE
            SYNTAX Unsigned32 (5..3600)
            UNITS "s"
            MAX-ACCESS read-write
            STATUS current
            DESCRIPTION
                "RTCP Media Stream Detect Time.
                Range: 5-3600
                Default: 300
                Unit: second"
            DEFVAL { 300 }
            ::= { hwBrasSbcImsLeaves 10 }

        hwBrasSbcIdlecutRtpTimer OBJECT-TYPE
            SYNTAX Unsigned32 (5..3600)
            UNITS "s"
            MAX-ACCESS read-write
            STATUS current
            DESCRIPTION
                "RTP Media Stream Detect Time.
                Range: 5-3600
                Default: 30
                Unit: second"
            DEFVAL { 30 }
            ::= { hwBrasSbcImsLeaves 11 }

        hwBrasSbcMediaDetectStatus OBJECT-TYPE
            SYNTAX HWBrasEnabledStatus
            MAX-ACCESS read-write
            STATUS current
            DESCRIPTION
                "Media Detect Enable Status.
                default: disabled"
            DEFVAL { disabled }
            ::= { hwBrasSbcImsLeaves 12 }

        hwBrasSbcMediaOnewayStatus OBJECT-TYPE
            SYNTAX HWBrasEnabledStatus
            MAX-ACCESS read-write
            STATUS current
            DESCRIPTION
                "Media Detect One-way Enable Status.
                default: disabled"
            DEFVAL { disabled }
            ::= { hwBrasSbcImsLeaves 13 }

        hwBrasSbcImsMgLogEnable OBJECT-TYPE
            SYNTAX HWBrasEnabledStatus
            MAX-ACCESS read-write
            STATUS current
            DESCRIPTION
                "Ims Mg Syslog Enable Status.
                default: disabled"
            DEFVAL { disabled }
            ::= { hwBrasSbcImsLeaves 14 }

        -- ewei add end

        -- ewei add for for DT SBC II
        hwBrasSbcImsStatisticsEnable OBJECT-TYPE
            SYNTAX HWBrasEnabledStatus
            MAX-ACCESS read-write
            STATUS current
            DESCRIPTION
                "Ims Statistics Enable Status.
                default: disabled"
            DEFVAL { disabled }
            ::= { hwBrasSbcImsLeaves 15 }
        -- ewei add for DT SBC II end

-- add by gaochangbo on 20081013 --
        hwBrasSbcTimerMediaAging OBJECT-TYPE
            SYNTAX Unsigned32 (5..3600)
            UNITS "s"
            MAX-ACCESS read-write
            STATUS current
            DESCRIPTION
                "RTP Media Stream Aging Time.
                Range: 5-3600
                Default: 300
                Unit: second"
            DEFVAL { 300 }
            ::= { hwBrasSbcImsLeaves 16 }
-- end of add by gaochangbo --

        hwBrasSbcImsTables OBJECT IDENTIFIER ::= { hwBrasSbcIms 2 }

        hwBrasSbcImsConnectTable OBJECT-TYPE
            SYNTAX SEQUENCE OF HwBrasSbcImsConnectEntry
            MAX-ACCESS not-accessible
            STATUS current
            DESCRIPTION
                "Set Ims Connection Table"
            ::= { hwBrasSbcImsTables 1 }

        hwBrasSbcImsConnectEntry OBJECT-TYPE
            SYNTAX HwBrasSbcImsConnectEntry
            MAX-ACCESS not-accessible
            STATUS current
            DESCRIPTION
                "Set Ims Connection Table Entry."
            INDEX { hwBrasSbcImsConnectIndex }
            ::= { hwBrasSbcImsConnectTable 1 }

        HwBrasSbcImsConnectEntry ::=
            SEQUENCE {
                hwBrasSbcImsConnectIndex
                    Unsigned32,
                hwBrasSbcImsConnectPepID
                    DisplayString,
                hwBrasSbcImsConnectCliType
                    INTEGER,
                hwBrasSbcImsConnectCliIP
                    IpAddress,
                hwBrasSbcImsConnectCliPort
                    Unsigned32,
                hwBrasSbcImsConnectServIP
                    IpAddress,
                hwBrasSbcImsConnectServPort
                    Unsigned32,
                hwBrasSbcImsConnectRowStatus
                    RowStatus
             }

        hwBrasSbcImsConnectIndex OBJECT-TYPE
            SYNTAX Unsigned32 (0..9)
            MAX-ACCESS not-accessible
            STATUS current
            DESCRIPTION
                "Index of the Connection
                Range : 0-9"
            ::= { hwBrasSbcImsConnectEntry 1 }

        hwBrasSbcImsConnectPepID OBJECT-TYPE
            SYNTAX DisplayString (SIZE (1..32))
            MAX-ACCESS read-create
            STATUS current
            DESCRIPTION
                "Pep Id of Connection.
                Range:1-32."
            ::= { hwBrasSbcImsConnectEntry 11 }

        hwBrasSbcImsConnectCliType OBJECT-TYPE
            SYNTAX INTEGER
                {
                unknown(1),
                brasSbci(2),
                goi(3)
                }
            MAX-ACCESS read-create
            STATUS current
            DESCRIPTION
                "Client Type of Connection."
            ::= { hwBrasSbcImsConnectEntry 12 }

        hwBrasSbcImsConnectCliIP OBJECT-TYPE
            SYNTAX IpAddress
            MAX-ACCESS read-create
            STATUS current
            DESCRIPTION
                "Client Ip Address of Connection."
            ::= { hwBrasSbcImsConnectEntry 13 }

        hwBrasSbcImsConnectCliPort OBJECT-TYPE
            SYNTAX Unsigned32 (1..50000)
            MAX-ACCESS read-create
            STATUS current
            DESCRIPTION
                "Client Port of Connection."
            ::= { hwBrasSbcImsConnectEntry 14 }

        hwBrasSbcImsConnectServIP OBJECT-TYPE
            SYNTAX IpAddress
            MAX-ACCESS read-create
            STATUS current
            DESCRIPTION
                "Server Ip Address of Connection."
            ::= { hwBrasSbcImsConnectEntry 15 }

        hwBrasSbcImsConnectServPort OBJECT-TYPE
            SYNTAX Unsigned32 (1..50000)
            MAX-ACCESS read-create
            STATUS current
            DESCRIPTION
                "Server Port of Connection."
            ::= { hwBrasSbcImsConnectEntry 16 }

        hwBrasSbcImsConnectRowStatus OBJECT-TYPE
            SYNTAX RowStatus
            MAX-ACCESS read-create
            STATUS current
            DESCRIPTION
                "Row Status."
            ::= { hwBrasSbcImsConnectEntry 51 }

        hwBrasSbcImsBandTable OBJECT-TYPE
            SYNTAX SEQUENCE OF HwBrasSbcImsBandEntry
            MAX-ACCESS not-accessible
            STATUS current
            DESCRIPTION
                "Set Ims Band Table."
            ::= { hwBrasSbcImsTables 2 }

        hwBrasSbcImsBandEntry OBJECT-TYPE
            SYNTAX HwBrasSbcImsBandEntry
            MAX-ACCESS not-accessible
            STATUS current
            DESCRIPTION
                "Set Ims Band Table Entry."
            INDEX { hwBrasSbcImsBandIndex }
            ::= { hwBrasSbcImsBandTable 1 }

        HwBrasSbcImsBandEntry ::=
            SEQUENCE {
                hwBrasSbcImsBandIndex
                    Unsigned32,
                hwBrasSbcImsBandIfIndex
                    Unsigned32,
                hwBrasSbcImsBandIfName
                    DisplayString,
                hwBrasSbcImsBandIfType
                    INTEGER,
                hwBrasSbcImsBandValue
                    Unsigned32,
                hwBrasSbcImsBandRowStatus
                    RowStatus
             }

        hwBrasSbcImsBandIndex OBJECT-TYPE
            SYNTAX Unsigned32 (1..64)
            MAX-ACCESS not-accessible
            STATUS current
            DESCRIPTION
                "Interface number.
                Range: 1-64."
            ::= { hwBrasSbcImsBandEntry 1 }

        hwBrasSbcImsBandIfIndex OBJECT-TYPE
            SYNTAX Unsigned32
            MAX-ACCESS read-only
            STATUS current
            DESCRIPTION
                "Index of the Interface."
            ::= { hwBrasSbcImsBandEntry 11 }

        hwBrasSbcImsBandIfName OBJECT-TYPE
            SYNTAX DisplayString
            MAX-ACCESS read-only
            STATUS current
            DESCRIPTION
                "Name of the Interface."
            ::= { hwBrasSbcImsBandEntry 12 }

        hwBrasSbcImsBandIfType OBJECT-TYPE
            SYNTAX INTEGER
                {
                fe(1),
                ge(2)
                }
            MAX-ACCESS read-only
            STATUS current
            DESCRIPTION
                "Type of the Interface:FE,GE."
            ::= { hwBrasSbcImsBandEntry 13 }

        hwBrasSbcImsBandValue OBJECT-TYPE
            SYNTAX Unsigned32 (1..1024)
            MAX-ACCESS read-write
            STATUS current
            DESCRIPTION
                "Bandwidth Value
                Range:1-1024
                Default: FE  100Mbps
                         GE  1024Mbps"
            ::= { hwBrasSbcImsBandEntry 14 }

        hwBrasSbcImsBandRowStatus OBJECT-TYPE
            SYNTAX RowStatus
            MAX-ACCESS read-write
            STATUS current
            DESCRIPTION
                "Row Status."
            ::= { hwBrasSbcImsBandEntry 51 }

        hwBrasSbcImsActiveTable OBJECT-TYPE
            SYNTAX SEQUENCE OF HwBrasSbcImsActiveEntry
            MAX-ACCESS not-accessible
            STATUS current
            DESCRIPTION
                "Active the Ims Connection Table."
            ::= { hwBrasSbcImsTables 3 }

        hwBrasSbcImsActiveEntry OBJECT-TYPE
            SYNTAX HwBrasSbcImsActiveEntry
            MAX-ACCESS not-accessible
            STATUS current
            DESCRIPTION
                "Active the Ims Connection Table Entry."
            INDEX { hwBrasSbcImsActiveConnectId }
            ::= { hwBrasSbcImsActiveTable 1 }

        HwBrasSbcImsActiveEntry ::=
            SEQUENCE {
                hwBrasSbcImsActiveConnectId
                    Unsigned32,
                hwBrasSbcImsActiveStatus
                    INTEGER,
                hwBrasSbcImsActiveRowStatus
                    RowStatus
             }

        hwBrasSbcImsActiveConnectId OBJECT-TYPE
            SYNTAX Unsigned32 (0..9)
            MAX-ACCESS not-accessible
            STATUS current
            DESCRIPTION
                "Index of the Connection
                Range : 0-9"
            ::= { hwBrasSbcImsActiveEntry 1 }

        hwBrasSbcImsActiveStatus OBJECT-TYPE
            SYNTAX INTEGER
                {
                sleep(1),
                active(2),
                online(3)
                }
            MAX-ACCESS read-write
            STATUS current
            DESCRIPTION
                "Connection Status:sleep,active.
                "
            DEFVAL { sleep }
            ::= { hwBrasSbcImsActiveEntry 11 }

        hwBrasSbcImsActiveRowStatus OBJECT-TYPE
            SYNTAX RowStatus
            MAX-ACCESS read-write
            STATUS current
            DESCRIPTION
                "Row Status."
            ::= { hwBrasSbcImsActiveEntry 51 }

        hwBrasSbcImsMGTable OBJECT-TYPE
            SYNTAX SEQUENCE OF HwBrasSbcImsMGEntry
            MAX-ACCESS not-accessible
            STATUS current
            DESCRIPTION
                "Set MG Table."
            ::= { hwBrasSbcImsTables 4 }

        hwBrasSbcImsMGEntry OBJECT-TYPE
            SYNTAX HwBrasSbcImsMGEntry
            MAX-ACCESS not-accessible
            STATUS current
            DESCRIPTION
                "Set MG Table Entry."
            INDEX { hwBrasSbcImsMGIndex }
            ::= { hwBrasSbcImsMGTable 1 }

        HwBrasSbcImsMGEntry ::=
            SEQUENCE {
                hwBrasSbcImsMGIndex
                    Unsigned32,
                hwBrasSbcImsMGDescription
                    DisplayString,
                hwBrasSbcImsMGTableStatus
                    HWBrasEnabledStatus,
                hwBrasSbcImsMGProtocol
                    INTEGER,
                hwBrasSbcImsMGMidString
                    DisplayString,
                -- ewei add for DT stage2
                hwBrasSbcImsMGInstanceName
                    DisplayString,
                -- ewei add for DT stage2 end
                hwBrasSbcImsMGRowStatus
                    RowStatus
             }

        hwBrasSbcImsMGIndex OBJECT-TYPE
            SYNTAX Unsigned32 (0..14)
            MAX-ACCESS not-accessible
            STATUS current
            DESCRIPTION
                "Index of the MG
                Range : 0-14"
            ::= { hwBrasSbcImsMGEntry 1 }

        hwBrasSbcImsMGDescription OBJECT-TYPE
            SYNTAX DisplayString (SIZE (0..63))
            MAX-ACCESS read-create
            STATUS current
            DESCRIPTION
                "Description of the MG."
            ::= { hwBrasSbcImsMGEntry 11 }

        hwBrasSbcImsMGTableStatus OBJECT-TYPE
            SYNTAX HWBrasEnabledStatus
            MAX-ACCESS read-create
            STATUS current
            DESCRIPTION
                "Status of the MG
                Default:disabled"
            DEFVAL { disabled }
            ::= { hwBrasSbcImsMGEntry 12 }

        hwBrasSbcImsMGProtocol OBJECT-TYPE
            SYNTAX INTEGER
                {
                sctp(1),
                udp(2),
                -- add by gaochangbo on 20081014 --
                tcp(3)
                -- end of add by gaochangbo --
                }
            MAX-ACCESS read-create
            STATUS current
            DESCRIPTION
                "Protocol of the MG
                1:SCTP
                2:UDP
                3:TCP
                Default:UDP"
            DEFVAL { udp }
            ::= { hwBrasSbcImsMGEntry 13 }

        hwBrasSbcImsMGMidString OBJECT-TYPE
            SYNTAX DisplayString (SIZE (0..64))
            MAX-ACCESS read-create
            STATUS current
            DESCRIPTION
                "MID of the MG."
            ::= { hwBrasSbcImsMGEntry 14 }

        -- ewei add for DT stage2
        hwBrasSbcImsMGInstanceName OBJECT-TYPE
            SYNTAX DisplayString (SIZE (1..32))
            MAX-ACCESS read-create
            STATUS current
            DESCRIPTION
                "SBC instance which the MG belongs to."
            ::= { hwBrasSbcImsMGEntry 15 }
        -- ewei add for DT stage2 end

        hwBrasSbcImsMGRowStatus OBJECT-TYPE
            SYNTAX RowStatus
            MAX-ACCESS read-create
            STATUS current
            DESCRIPTION
                "Row Status of the MG."
            ::= { hwBrasSbcImsMGEntry 51 }

        hwBrasSbcImsMGIPTable OBJECT-TYPE
            SYNTAX SEQUENCE OF HwBrasSbcImsMGIPEntry
            MAX-ACCESS not-accessible
            STATUS current
            DESCRIPTION
                "Set MG IP Table."
            ::= { hwBrasSbcImsTables 5 }

        hwBrasSbcImsMGIPEntry OBJECT-TYPE
            SYNTAX HwBrasSbcImsMGIPEntry
            MAX-ACCESS not-accessible
            STATUS current
            DESCRIPTION
                "Set MG IP Table Entry."
            INDEX { hwBrasSbcImsMGIndex, hwBrasSbcImsMGIPType, hwBrasSbcImsMGIPSN }
            ::= { hwBrasSbcImsMGIPTable 1 }

        HwBrasSbcImsMGIPEntry ::=
            SEQUENCE {
                hwBrasSbcImsMGIPType
                    INTEGER,
                hwBrasSbcImsMGIPSN
                    Unsigned32,
                hwBrasSbcImsMGIPVersion
                    INTEGER,
                hwBrasSbcImsMGIPAddr
                    DisplayString,
                hwBrasSbcImsMGIPPort
                    Unsigned32,
                hwBrasSbcImsMGIPRowStatus
                    RowStatus,
                hwBrasSbcImsMGIPInterface  -- ewei add
                    OCTET STRING
                }

        hwBrasSbcImsMGIPType OBJECT-TYPE
            SYNTAX INTEGER
                {
                mg(1),
                mgc(2)
                }
            MAX-ACCESS not-accessible
            STATUS current
            DESCRIPTION
                "Type of the IP table
                1:MG
                2:MGC"
            ::= { hwBrasSbcImsMGIPEntry 2 }

        hwBrasSbcImsMGIPSN OBJECT-TYPE
            SYNTAX Unsigned32 (1..4)
            MAX-ACCESS not-accessible
            STATUS current
            DESCRIPTION
                "Index of the IP table
                Range:1-4"
            ::= { hwBrasSbcImsMGIPEntry 3 }

        hwBrasSbcImsMGIPVersion OBJECT-TYPE
            SYNTAX INTEGER
                {
                ipv4(4),
                ipv6(6)
                }
            MAX-ACCESS read-write
            STATUS current
            DESCRIPTION
                "IP version of the IP table
                4:ipv4
                6:ipv6"
            ::= { hwBrasSbcImsMGIPEntry 11 }

        hwBrasSbcImsMGIPAddr OBJECT-TYPE
            SYNTAX DisplayString (SIZE (0..63))
            MAX-ACCESS read-create
            STATUS current
            DESCRIPTION
                "Address of the IP table."
            ::= { hwBrasSbcImsMGIPEntry 12 }

        -- ewei add begin
        hwBrasSbcImsMGIPInterface OBJECT-TYPE
            SYNTAX OCTET STRING (SIZE (1..47))
            MAX-ACCESS read-write
            STATUS current
            DESCRIPTION
                "MG Interface."
            ::= { hwBrasSbcImsMGIPEntry 15 }
        -- ewei add end

        hwBrasSbcImsMGIPPort OBJECT-TYPE
            SYNTAX Unsigned32 (0..10000)
            MAX-ACCESS read-create
            STATUS current
            DESCRIPTION
                "Port of the IP table."
            ::= { hwBrasSbcImsMGIPEntry 13 }

        hwBrasSbcImsMGIPRowStatus OBJECT-TYPE
            SYNTAX RowStatus
            MAX-ACCESS read-create
            STATUS current
            DESCRIPTION
                "Row Status of the IP table."
            ::= { hwBrasSbcImsMGIPEntry 51 }

        hwBrasSbcImsMGDomainTable OBJECT-TYPE
            SYNTAX SEQUENCE OF HwBrasSbcImsMGDomainEntry
            MAX-ACCESS not-accessible
            STATUS current
            DESCRIPTION
                "Set MG Domain Table."
            ::= { hwBrasSbcImsTables 6 }

        hwBrasSbcImsMGDomainEntry OBJECT-TYPE
            SYNTAX HwBrasSbcImsMGDomainEntry
            MAX-ACCESS not-accessible
            STATUS current
            DESCRIPTION
                "Set MG Domain Table Entry."
            INDEX { hwBrasSbcImsMGIndex, hwBrasSbcImsMGDomainType, hwBrasSbcImsMGDomainName }
            ::= { hwBrasSbcImsMGDomainTable 1 }

        HwBrasSbcImsMGDomainEntry ::=
            SEQUENCE {
                hwBrasSbcImsMGDomainType
                    INTEGER,
                hwBrasSbcImsMGDomainName
                    DisplayString,
                hwBrasSbcImsMGDomainMapIndex
                    Unsigned32,
                hwBrasSbcImsMGDomainRowStatus
                    RowStatus
             }

        hwBrasSbcImsMGDomainType OBJECT-TYPE
            SYNTAX INTEGER
                {
                inner(1),
                outter(2)
                }
            MAX-ACCESS not-accessible
            STATUS current
            DESCRIPTION
                "Type of the domain table
                1:inner
                2:outer"
            ::= { hwBrasSbcImsMGDomainEntry 2 }

        hwBrasSbcImsMGDomainName OBJECT-TYPE
            SYNTAX DisplayString (SIZE (1..64))
            MAX-ACCESS not-accessible
            STATUS current
            DESCRIPTION
                "Name of the domain table."
            ::= { hwBrasSbcImsMGDomainEntry 3 }

        hwBrasSbcImsMGDomainMapIndex OBJECT-TYPE
            SYNTAX Unsigned32 (2501..2999)
            MAX-ACCESS read-create
            STATUS current
            DESCRIPTION
                "Mapgroup index of the domain table
                Range:2501-2999"
            ::= { hwBrasSbcImsMGDomainEntry 11 }

        hwBrasSbcImsMGDomainRowStatus OBJECT-TYPE
            SYNTAX RowStatus
            MAX-ACCESS read-create
            STATUS current
            DESCRIPTION
                "Row Status of the domain table."
            ::= { hwBrasSbcImsMGDomainEntry 51 }

        hwBrasSbcDualHoming OBJECT IDENTIFIER ::= { hwBrasSbcAdvance 8 }

        hwBrasSbcDHLeaves OBJECT IDENTIFIER ::= { hwBrasSbcDualHoming 1 }

        hwBrasSbcDHSIPDetectStatus OBJECT-TYPE
            SYNTAX HWBrasEnabledStatus
            MAX-ACCESS read-write
            STATUS current
            DESCRIPTION
                "Softswitch Detect Enable Status.
                Default: disabled
                This leaf for detect SoftSwitch status."
            DEFVAL { disabled }
            ::= { hwBrasSbcDHLeaves 1 }

        hwBrasSbcDHSIPDetectTimer OBJECT-TYPE
            SYNTAX Unsigned32 (1..7200)
            UNITS "seconds"
            MAX-ACCESS read-write
            STATUS current
            DESCRIPTION
                "Detect Time.
                Range: 1-7200
                Default: 10
                Unit: seconds"
            DEFVAL { 10 }
            ::= { hwBrasSbcDHLeaves 2 }

        hwBrasSbcDHSIPDetectSourcePort OBJECT-TYPE
            SYNTAX Unsigned32 (1024..10000)
            MAX-ACCESS read-write
            STATUS current
            DESCRIPTION
                "Detect Source Port.
                Range: 1024-10000
                Default: 5060"
            DEFVAL { 5060 }
            ::= { hwBrasSbcDHLeaves 3 }

        hwBrasSbcDHSIPDetectFailCount OBJECT-TYPE
            SYNTAX Unsigned32 (1..100)
            MAX-ACCESS read-write
            STATUS current
            DESCRIPTION
                "Detect Fail Limit.
                Range: 1-100
                Default: 3"
            DEFVAL { 3 }
            ::= { hwBrasSbcDHLeaves 4 }

        hwBrasSbcQoSReport OBJECT IDENTIFIER ::= { hwBrasSbcAdvance 9 }

        hwBrasSbcQRLeaves OBJECT IDENTIFIER ::= { hwBrasSbcQoSReport 1 }

        hwBrasSbcQRStatus OBJECT-TYPE
            SYNTAX HWBrasEnabledStatus
            MAX-ACCESS read-write
            STATUS current
            DESCRIPTION
                "QoS report enable status.
                Default: disabled"
            DEFVAL { disabled }
            ::= { hwBrasSbcQRLeaves 1 }

        hwBrasSbcQRBandWidth OBJECT-TYPE
            SYNTAX Unsigned32 (0..40960)
            UNITS "packetspersecond"
            MAX-ACCESS read-write
            STATUS current
            DESCRIPTION
                "QoS report RTCP packet bandwidth.
                Range: 0-40960
                Default: 1024
                Unit: packets/second"
            DEFVAL { 1024 }
            ::= { hwBrasSbcQRLeaves 2 }

        hwBrasSbcQRTables OBJECT IDENTIFIER ::= { hwBrasSbcQoSReport 2 }

        hwBrasSbcMediaDefend OBJECT IDENTIFIER ::= { hwBrasSbcAdvance 11 }

        hwBrasSbcMediaDefendLeaves OBJECT IDENTIFIER ::= { hwBrasSbcMediaDefend 1 }

        hwBrasSbcMDStatus OBJECT-TYPE
            SYNTAX HWBrasEnabledStatus
            MAX-ACCESS read-write
            STATUS current
            DESCRIPTION
                "Description."
            DEFVAL { disabled }
            ::= { hwBrasSbcMediaDefendLeaves 1 }

        hwBrasSbcMediaDefendTables OBJECT IDENTIFIER ::= { hwBrasSbcMediaDefend 2 }

        hwBrasSbcMDLengthTable OBJECT-TYPE
            SYNTAX SEQUENCE OF HwBrasSbcMDLengthEntry
            MAX-ACCESS not-accessible
            STATUS current
            DESCRIPTION
                "Description."
            ::= { hwBrasSbcMediaDefendTables 1 }

        hwBrasSbcMDLengthEntry OBJECT-TYPE
            SYNTAX HwBrasSbcMDLengthEntry
            MAX-ACCESS not-accessible
            STATUS current
            DESCRIPTION
                "Description."
            INDEX { hwBrasSbcMDLengthIndex }
            ::= { hwBrasSbcMDLengthTable 1 }

        HwBrasSbcMDLengthEntry ::=
            SEQUENCE {
                hwBrasSbcMDLengthIndex
                    INTEGER,
                hwBrasSbcMDLengthMin
                    Unsigned32,
                hwBrasSbcMDLengthMax
                    Unsigned32,
                hwBrasSbcMDLengthRowStatus
                    RowStatus
             }

        hwBrasSbcMDLengthIndex OBJECT-TYPE
            SYNTAX INTEGER
                {
                rtp(1),
                rtcp(2)
                }
            MAX-ACCESS not-accessible
            STATUS current
            DESCRIPTION
                "Description."
            ::= { hwBrasSbcMDLengthEntry 1 }

        hwBrasSbcMDLengthMin OBJECT-TYPE
            SYNTAX Unsigned32 (28..65535)
            MAX-ACCESS read-write
            STATUS current
            DESCRIPTION
                "Description."
            DEFVAL { 28 }
            ::= { hwBrasSbcMDLengthEntry 11 }

        hwBrasSbcMDLengthMax OBJECT-TYPE
            SYNTAX Unsigned32 (28..65535)
            MAX-ACCESS read-write
            STATUS current
            DESCRIPTION
                "Description."
            DEFVAL { 1500 }
            ::= { hwBrasSbcMDLengthEntry 12 }

        hwBrasSbcMDLengthRowStatus OBJECT-TYPE
            SYNTAX RowStatus
            MAX-ACCESS read-write
            STATUS current
            DESCRIPTION
                "Description."
            ::= { hwBrasSbcMDLengthEntry 51 }

        hwBrasSbcMDStatisticTable OBJECT-TYPE
            SYNTAX SEQUENCE OF HwBrasSbcMDStatisticEntry
            MAX-ACCESS not-accessible
            STATUS current
            DESCRIPTION
                "Description."
            ::= { hwBrasSbcMediaDefendTables 2 }

        hwBrasSbcMDStatisticEntry OBJECT-TYPE
            SYNTAX HwBrasSbcMDStatisticEntry
            MAX-ACCESS not-accessible
            STATUS current
            DESCRIPTION
                "Description."
            INDEX { hwBrasSbcMDStatisticIndex }
            ::= { hwBrasSbcMDStatisticTable 1 }

        HwBrasSbcMDStatisticEntry ::=
            SEQUENCE {
                hwBrasSbcMDStatisticIndex
                    INTEGER,
                hwBrasSbcMDStatisticMinDrop
                    Unsigned32,
                hwBrasSbcMDStatisticMaxDrop
                    Unsigned32,
                hwBrasSbcMDStatisticFragDrop
                    Unsigned32,
                hwBrasSbcMDStatisticFlowDrop
                    Unsigned32,
                hwBrasSbcMDStatisticRowStatus
                    RowStatus
             }

        hwBrasSbcMDStatisticIndex OBJECT-TYPE
            SYNTAX INTEGER
                {
                rtp(1),
                rtcp(2)
                }
            MAX-ACCESS not-accessible
            STATUS current
            DESCRIPTION
                "Description."
            ::= { hwBrasSbcMDStatisticEntry 1 }

        hwBrasSbcMDStatisticMinDrop OBJECT-TYPE
            SYNTAX Unsigned32
            MAX-ACCESS read-only
            STATUS current
            DESCRIPTION
                "Description."
            ::= { hwBrasSbcMDStatisticEntry 11 }

        hwBrasSbcMDStatisticMaxDrop OBJECT-TYPE
            SYNTAX Unsigned32
            MAX-ACCESS read-only
            STATUS current
            DESCRIPTION
                "Description."
            ::= { hwBrasSbcMDStatisticEntry 12 }

        hwBrasSbcMDStatisticFragDrop OBJECT-TYPE
            SYNTAX Unsigned32
            MAX-ACCESS read-only
            STATUS current
            DESCRIPTION
                "Description."
            ::= { hwBrasSbcMDStatisticEntry 13 }

        hwBrasSbcMDStatisticFlowDrop OBJECT-TYPE
            SYNTAX Unsigned32
            MAX-ACCESS read-only
            STATUS current
            DESCRIPTION
                "Description."
            ::= { hwBrasSbcMDStatisticEntry 14 }

        hwBrasSbcMDStatisticRowStatus OBJECT-TYPE
            SYNTAX RowStatus
            MAX-ACCESS read-write
            STATUS current
            DESCRIPTION
                "Description."
            ::= { hwBrasSbcMDStatisticEntry 51 }

        hwBrasSbcSignalingNat OBJECT IDENTIFIER ::= { hwBrasSbcAdvance 12 }

        hwBrasSbcSignalingNatLeaves OBJECT IDENTIFIER ::= { hwBrasSbcSignalingNat 1 }

        hwBrasSbcNatSessionAgingTime OBJECT-TYPE
            SYNTAX Unsigned32 (1..40000)
            MAX-ACCESS read-write
            STATUS current
            DESCRIPTION
                "Sbc signaling nat session aging time (s).
                Range: 1-40000
                Default: 20"
            DEFVAL { 20 }
            ::= { hwBrasSbcSignalingNatLeaves 1 }

        hwBrasSbcSignalingNatTables OBJECT IDENTIFIER ::= { hwBrasSbcSignalingNat 2 }

        hwBrasSbcNatCfgTable OBJECT-TYPE
            SYNTAX SEQUENCE OF HwBrasSbcNatCfgEntry
            MAX-ACCESS not-accessible
            STATUS current
            DESCRIPTION
                "Sbc signaling nat configuration."
            ::= { hwBrasSbcSignalingNatTables 1 }

        hwBrasSbcNatCfgEntry OBJECT-TYPE
            SYNTAX HwBrasSbcNatCfgEntry
            MAX-ACCESS not-accessible
            STATUS current
            DESCRIPTION
                "Sbc signaling nat configuration."
            INDEX { hwBrasSbcNatGroupIndex, hwBrasSbcNatVpnNameIndex }
            ::= { hwBrasSbcNatCfgTable 1 }

        HwBrasSbcNatCfgEntry ::=
            SEQUENCE {
                hwBrasSbcNatGroupIndex
                    Unsigned32,
                hwBrasSbcNatVpnNameIndex
                    DisplayString,
                                hwBrasSbcNatInstanceName
                                        DisplayString,
                hwBrasSbcNatCfgRowStatus
                    RowStatus
             }

        hwBrasSbcNatGroupIndex OBJECT-TYPE
            SYNTAX Unsigned32 (0..127)
            MAX-ACCESS read-only
            STATUS current
            DESCRIPTION
                "Sbc signaling nat group index."
            ::= { hwBrasSbcNatCfgEntry 1 }

        hwBrasSbcNatVpnNameIndex OBJECT-TYPE
            SYNTAX DisplayString (SIZE (1..31))
            MAX-ACCESS read-only
            STATUS current
            DESCRIPTION
                "Sbc signaling nat source vpn name."
            ::= { hwBrasSbcNatCfgEntry 2 }

        hwBrasSbcNatInstanceName OBJECT-TYPE
            SYNTAX DisplayString (SIZE (1..32))
            MAX-ACCESS read-create
            STATUS current
            DESCRIPTION
                "Sbc signaling nat sbc instance name."
            ::= { hwBrasSbcNatCfgEntry 3 }

        hwBrasSbcNatCfgRowStatus OBJECT-TYPE
            SYNTAX RowStatus
            MAX-ACCESS read-create
            STATUS current
            DESCRIPTION
                "Row Status."
            ::= { hwBrasSbcNatCfgEntry 51 }

        hwBrasSbcNatAddressGroupTable OBJECT-TYPE
            SYNTAX SEQUENCE OF HwBrasSbcNatAddressGroupEntry
            MAX-ACCESS not-accessible
            STATUS current
            DESCRIPTION
                "
                NAT address pool information table."
            ::= { hwBrasSbcSignalingNatTables 2 }

        hwBrasSbcNatAddressGroupEntry OBJECT-TYPE
            SYNTAX HwBrasSbcNatAddressGroupEntry
            MAX-ACCESS not-accessible
            STATUS current
            DESCRIPTION
                "
                NAT address pool information table entry.
                "
            INDEX { hwNatAddrGrpIndex }
            ::= { hwBrasSbcNatAddressGroupTable 1 }

        HwBrasSbcNatAddressGroupEntry ::=
            SEQUENCE {
                hwNatAddrGrpIndex
                    Unsigned32,
                hwNatAddrGrpBeginningIpAddr
                    IpAddress,
                hwNatAddrGrpEndingIpAddr
                    IpAddress,
                hwNatAddrGrpRefCount
                    Unsigned32,
                hwNatAddrGrpVpnName
                    OCTET STRING,
                hwNatAddrGrpRowstatus
                    RowStatus
             }

        hwNatAddrGrpIndex OBJECT-TYPE
            SYNTAX Unsigned32 (0..127)
            MAX-ACCESS not-accessible
            STATUS current
            DESCRIPTION
                "
                The index of address pool
                This item is index.
                "
            ::= { hwBrasSbcNatAddressGroupEntry 1 }

        hwNatAddrGrpBeginningIpAddr OBJECT-TYPE
            SYNTAX IpAddress
            MAX-ACCESS read-create
            STATUS current
            DESCRIPTION
                "
                The beginning IP address of address pool
                "
            ::= { hwBrasSbcNatAddressGroupEntry 2 }

        hwNatAddrGrpEndingIpAddr OBJECT-TYPE
            SYNTAX IpAddress
            MAX-ACCESS read-create
            STATUS current
            DESCRIPTION
                "
                The ending IP address of address pool
                "
            ::= { hwBrasSbcNatAddressGroupEntry 3 }

        hwNatAddrGrpRefCount OBJECT-TYPE
            SYNTAX Unsigned32
            MAX-ACCESS read-only
            STATUS current
            DESCRIPTION
                "
                This address pool reference count.
                "
            ::= { hwBrasSbcNatAddressGroupEntry 4 }

        hwNatAddrGrpVpnName OBJECT-TYPE
            SYNTAX OCTET STRING (SIZE (0..31))
        MAX-ACCESS read-create
        STATUS current
            DESCRIPTION
                "
                Vpn-Instance name.
                "
            ::= { hwBrasSbcNatAddressGroupEntry 5 }

        hwNatAddrGrpRowstatus OBJECT-TYPE
            SYNTAX RowStatus
            MAX-ACCESS read-create
            STATUS current
            DESCRIPTION
                "
                Row status
                Only support CreateAndGo and Destroy.
                "
            ::= { hwBrasSbcNatAddressGroupEntry 6 }

        -- begin:gaochangbo 20090202 --
        hwBrasSbcBandwidthLimit OBJECT IDENTIFIER ::= { hwBrasSbcAdvance 13 }

        hwBrasSbcBWLimitLeaves OBJECT IDENTIFIER ::= { hwBrasSbcBandwidthLimit 1 }

        hwBrasSbcBWLimitType OBJECT-TYPE
            SYNTAX HwBrasBWLimitType
            MAX-ACCESS read-write
            STATUS current
            DESCRIPTION
                "SBC bandwidth-limit type.
                Default: qos"
            DEFVAL { qos }
            ::= { hwBrasSbcBWLimitLeaves 1 }

        hwBrasSbcBWLimitValue OBJECT-TYPE
            SYNTAX Unsigned32 (1..10485760)
            MAX-ACCESS read-write
            STATUS current
            DESCRIPTION
                "SBC maximum bandwidth(K Bytes).
                Range: 1-10485760
                Default: 6291456"
            DEFVAL { 6291456 }
            ::= { hwBrasSbcBWLimitLeaves 2 }
        -- end:gaochangbo on 20090202 --

        hwBrasSbcView OBJECT IDENTIFIER ::= { hwBrasSbcGeneral 3 }

        hwBrasSbcViewLeaves OBJECT IDENTIFIER ::= { hwBrasSbcView 1 }

        hwBrasSbcSoftVersion OBJECT-TYPE
            SYNTAX DisplayString (SIZE (1..64))
            MAX-ACCESS read-only
            STATUS current
            DESCRIPTION
                "Software Version Information."
            ::= { hwBrasSbcViewLeaves 1 }

        hwBrasSbcCpuUsage OBJECT-TYPE
            SYNTAX Unsigned32 (0..100)
            MAX-ACCESS read-only
            STATUS current
            DESCRIPTION
                "Cpu Usage Information.
                Range: 0-100
                Default: NA"
            ::= { hwBrasSbcViewLeaves 2 }

        hwBrasSbcUmsVersion OBJECT-TYPE
            SYNTAX DisplayString (SIZE (8..63))
            MAX-ACCESS read-only
            STATUS current
            DESCRIPTION
                "Software version information for UMS."
            ::= { hwBrasSbcViewLeaves 3 }

        hwBrasSbcViewTables OBJECT IDENTIFIER ::= { hwBrasSbcView 2 }

        hwBrasSbcStatisticTable OBJECT-TYPE
            SYNTAX SEQUENCE OF HwBrasSbcStatisticEntry
            MAX-ACCESS not-accessible
            STATUS current
            DESCRIPTION
                "Statistic Table."
            ::= { hwBrasSbcViewTables 1 }

        hwBrasSbcStatisticEntry OBJECT-TYPE
            SYNTAX HwBrasSbcStatisticEntry
            MAX-ACCESS not-accessible
            STATUS current
            DESCRIPTION
                "Statistic Table Entry."
            INDEX { hwBrasSbcStatisticIndex, hwBrasSbcStatisticOffset }
            ::= { hwBrasSbcStatisticTable 1 }

        HwBrasSbcStatisticEntry ::=
            SEQUENCE {
                hwBrasSbcStatisticIndex
                    Unsigned32,
                hwBrasSbcStatisticOffset
                    Unsigned32,
                hwBrasSbcStatisticDesc
                    DisplayString,
                hwBrasSbcStatisticValue
                    Unsigned32,
                hwBrasSbcStatisticTime
                    DateAndTime
             }

        hwBrasSbcStatisticIndex OBJECT-TYPE
            SYNTAX Unsigned32 (1..2147483647)
            MAX-ACCESS not-accessible
            STATUS current
            DESCRIPTION
                "Statistic Index."
            ::= { hwBrasSbcStatisticEntry 1 }

        hwBrasSbcStatisticOffset OBJECT-TYPE
            SYNTAX Unsigned32 (0..143)
            UNITS "hours"
            MAX-ACCESS not-accessible
            STATUS current
            DESCRIPTION
                "Statistic Hours Offset."
            ::= { hwBrasSbcStatisticEntry 2 }

        hwBrasSbcStatisticDesc OBJECT-TYPE
            SYNTAX DisplayString
            MAX-ACCESS read-only
            STATUS current
            DESCRIPTION
                "Statistic Description."
            ::= { hwBrasSbcStatisticEntry 3 }

        hwBrasSbcStatisticValue OBJECT-TYPE
            SYNTAX Unsigned32
            MAX-ACCESS read-only
            STATUS current
            DESCRIPTION
                "Statistic Value."
            ::= { hwBrasSbcStatisticEntry 4 }

        hwBrasSbcStatisticTime OBJECT-TYPE
            SYNTAX DateAndTime (SIZE (8))
            MAX-ACCESS read-only
            STATUS current
            DESCRIPTION
                "Statistic Time."
            ::= { hwBrasSbcStatisticEntry 5 }

        hwBrasSbcSip OBJECT IDENTIFIER ::= { hwBrasSbcObjects 2 }

        hwBrasSbcSipLeaves OBJECT IDENTIFIER ::= { hwBrasSbcSip 1 }

        hwBrasSbcSipEnable OBJECT-TYPE
            SYNTAX HWBrasEnabledStatus
            MAX-ACCESS read-write
            STATUS current
            DESCRIPTION
                "SIP Enable Status.
                Default: enabled"
            DEFVAL { enabled }
            ::= { hwBrasSbcSipLeaves 1 }

        hwBrasSbcSipSyslogEnable OBJECT-TYPE
            SYNTAX HWBrasEnabledStatus
            MAX-ACCESS read-write
            STATUS current
            DESCRIPTION
                "SIP Syslog Enable Status.
                Default: enabled"
            DEFVAL { enabled }
            ::= { hwBrasSbcSipLeaves 2 }

        hwBrasSbcSipAnonymity OBJECT-TYPE
            SYNTAX DisplayString (SIZE (0..63))
            MAX-ACCESS read-write
            STATUS current
            DESCRIPTION
                "SIP Anonymous card."
            ::= { hwBrasSbcSipLeaves 3 }

        hwBrasSbcSipCheckheartEnable OBJECT-TYPE
            SYNTAX HWBrasEnabledStatus
            MAX-ACCESS read-write
            STATUS current
            DESCRIPTION
                "SIP Check SIP Heartbeat Enable Status.
                Default: disabled"
            DEFVAL { disabled }
            ::= { hwBrasSbcSipLeaves 4 }

        hwBrasSbcSipCallsessionTimer OBJECT-TYPE
            SYNTAX Unsigned32 (0..14400)
            UNITS "minutes"
            MAX-ACCESS read-write
            STATUS current
            DESCRIPTION
                "SIP Callsession Aging Time.
                Range: 0-14400
                Default: 720
                Unit: minutes"
            DEFVAL { 720 }
            ::= { hwBrasSbcSipLeaves 5 }

        hwBrasSbcSipPDHCountLimit OBJECT-TYPE
            SYNTAX Unsigned32 (1..100)
            MAX-ACCESS read-write
            STATUS current
            DESCRIPTION
                "SIP Dual-homing Failed Register Count Limit.
                Range: 1-100
                Default: 6"
            DEFVAL { 6 }
            ::= { hwBrasSbcSipLeaves 6 }

        hwBrasSbcSipRegReduceStatus OBJECT-TYPE
            SYNTAX HWBrasEnabledStatus
            MAX-ACCESS read-write
            STATUS current
            DESCRIPTION
                "SIP Register Reduce Enable States.
                Default: disabled"
            DEFVAL { disabled }
            ::= { hwBrasSbcSipLeaves 7 }

        hwBrasSbcSipRegReduceTimer OBJECT-TYPE
            SYNTAX Unsigned32 (1..600)
            UNITS "minutes"
            MAX-ACCESS read-write
            STATUS current
            DESCRIPTION
                "SIP Register Expire Reduced.
                Range: 1-600
                Default: 60
                Unit: minutes"
            DEFVAL { 60 }
            ::= { hwBrasSbcSipLeaves 8 }

        hwBrasSbcSipTables OBJECT IDENTIFIER ::= { hwBrasSbcSip 2 }

        hwBrasSbcSipWellknownPortTable OBJECT-TYPE
            SYNTAX SEQUENCE OF HwBrasSbcSipWellknownPortEntry
            MAX-ACCESS not-accessible
            STATUS current
            DESCRIPTION
                "SIP Wellknown Port Table.
                obsolete"
            ::= { hwBrasSbcSipTables 1 }

        hwBrasSbcSipWellknownPortEntry OBJECT-TYPE
            SYNTAX HwBrasSbcSipWellknownPortEntry
            MAX-ACCESS not-accessible
            STATUS current
            DESCRIPTION
                "SIP Wellknown Port Table Entry."
            INDEX { hwBrasSbcSipWellknownPortIndex, hwBrasSbcSipWellknownPortProtocol, hwBrasSbcSipWellknownPortAddr }
            ::= { hwBrasSbcSipWellknownPortTable 1 }

        HwBrasSbcSipWellknownPortEntry ::=
            SEQUENCE {
                hwBrasSbcSipWellknownPortIndex
                    INTEGER,
                hwBrasSbcSipWellknownPortProtocol
                    INTEGER,
                hwBrasSbcSipWellknownPortAddr
                    IpAddress,
                hwBrasSbcSipWellknownPortPort
                    Unsigned32,
                hwBrasSbcSipWellknownPortRowStatus
                    RowStatus
             }

        hwBrasSbcSipWellknownPortIndex OBJECT-TYPE
            SYNTAX INTEGER
                {
                clientaddr(1),
                softxaddr(2)
                }
            MAX-ACCESS not-accessible
            STATUS current
            DESCRIPTION
                "SIP Wellknown Port Index.
                1: Client Side Ip Address
                2: Softx IP Address
                Default: NA"
            ::= { hwBrasSbcSipWellknownPortEntry 1 }

        hwBrasSbcSipWellknownPortProtocol OBJECT-TYPE
            SYNTAX INTEGER { sip(1) }
            MAX-ACCESS not-accessible
            STATUS current
            DESCRIPTION
                "SIP Wellknown Port Protocol.
                1: sip
                Default: NA"
            ::= { hwBrasSbcSipWellknownPortEntry 2 }

        hwBrasSbcSipWellknownPortAddr OBJECT-TYPE
            SYNTAX IpAddress
            MAX-ACCESS not-accessible
            STATUS current
            DESCRIPTION
                "SIP Wellknown Port IP Address."
            ::= { hwBrasSbcSipWellknownPortEntry 3 }

        hwBrasSbcSipWellknownPortPort OBJECT-TYPE
            SYNTAX Unsigned32 (1..65535)
            MAX-ACCESS read-create
            STATUS current
            DESCRIPTION
                "SIP Wellknown Port Port."
            ::= { hwBrasSbcSipWellknownPortEntry 4 }

        hwBrasSbcSipWellknownPortRowStatus OBJECT-TYPE
            SYNTAX RowStatus
            MAX-ACCESS read-create
            STATUS current
            DESCRIPTION
                "SIP Wellknown Port Row Status."
            ::= { hwBrasSbcSipWellknownPortEntry 5 }

        hwBrasSbcSipSignalMapTable OBJECT-TYPE
            SYNTAX SEQUENCE OF HwBrasSbcSipSignalMapEntry
            MAX-ACCESS not-accessible
            STATUS current
            DESCRIPTION
                "SIP Signal Map Table.
                obsolete"
            ::= { hwBrasSbcSipTables 2 }

        hwBrasSbcSipSignalMapEntry OBJECT-TYPE
            SYNTAX HwBrasSbcSipSignalMapEntry
            MAX-ACCESS not-accessible
            STATUS current
            DESCRIPTION
                "SIP Signal Map Table Entry."
            INDEX { hwBrasSbcSipSignalMapAddr, hwBrasSbcSipSignalMapProtocol }
            ::= { hwBrasSbcSipSignalMapTable 1 }

        HwBrasSbcSipSignalMapEntry ::=
            SEQUENCE {
                hwBrasSbcSipSignalMapAddr
                    IpAddress,
                hwBrasSbcSipSignalMapProtocol
                    INTEGER,
                hwBrasSbcSipSignalMapNumber
                    Unsigned32,
                hwBrasSbcSipSignalMapAddrType
                    INTEGER
             }

        hwBrasSbcSipSignalMapAddr OBJECT-TYPE
            SYNTAX IpAddress
            MAX-ACCESS not-accessible
            STATUS current
            DESCRIPTION
                "SIP Signal Map Table IP Address."
            ::= { hwBrasSbcSipSignalMapEntry 1 }

        hwBrasSbcSipSignalMapProtocol OBJECT-TYPE
            SYNTAX INTEGER { sip(1) }
            MAX-ACCESS not-accessible
            STATUS current
            DESCRIPTION
                "SIP Signal Map Table Protocol."
            ::= { hwBrasSbcSipSignalMapEntry 2 }

        hwBrasSbcSipSignalMapNumber OBJECT-TYPE
            SYNTAX Unsigned32
            MAX-ACCESS read-only
            STATUS current
            DESCRIPTION
                "SIP Signal Map Table Map Number."
            ::= { hwBrasSbcSipSignalMapEntry 3 }

        hwBrasSbcSipSignalMapAddrType OBJECT-TYPE
            SYNTAX INTEGER
                {
                client(1),
                server(2)
                }
            MAX-ACCESS read-only
            STATUS current
            DESCRIPTION
                "SIP Signal Map Table Map Type.
                "
            ::= { hwBrasSbcSipSignalMapEntry 4 }

        hwBrasSbcSipMediaMapTable OBJECT-TYPE
            SYNTAX SEQUENCE OF HwBrasSbcSipMediaMapEntry
            MAX-ACCESS not-accessible
            STATUS current
            DESCRIPTION
                "SIP Media Map Table.
                obsolete"
            ::= { hwBrasSbcSipTables 3 }

        hwBrasSbcSipMediaMapEntry OBJECT-TYPE
            SYNTAX HwBrasSbcSipMediaMapEntry
            MAX-ACCESS not-accessible
            STATUS current
            DESCRIPTION
                "SIP Media Map Table Entry."
            INDEX { hwBrasSbcSipMediaMapAddr, hwBrasSbcSipMediaMapProtocol }
            ::= { hwBrasSbcSipMediaMapTable 1 }

        HwBrasSbcSipMediaMapEntry ::=
            SEQUENCE {
                hwBrasSbcSipMediaMapAddr
                    IpAddress,
                hwBrasSbcSipMediaMapProtocol
                    INTEGER,
                hwBrasSbcSipMediaMapNumber
                    Unsigned32
             }

        hwBrasSbcSipMediaMapAddr OBJECT-TYPE
            SYNTAX IpAddress
            MAX-ACCESS not-accessible
            STATUS current
            DESCRIPTION
                "SIP Media Map Table IP Address."
            ::= { hwBrasSbcSipMediaMapEntry 1 }

        hwBrasSbcSipMediaMapProtocol OBJECT-TYPE
            SYNTAX INTEGER { sip(1) }
            MAX-ACCESS not-accessible
            STATUS current
            DESCRIPTION
                "SIP Media Map Table Protocol."
            ::= { hwBrasSbcSipMediaMapEntry 2 }

        hwBrasSbcSipMediaMapNumber OBJECT-TYPE
            SYNTAX Unsigned32
            MAX-ACCESS read-only
            STATUS current
            DESCRIPTION
                "SIP Media Map Table Media Map Number."
            ::= { hwBrasSbcSipMediaMapEntry 3 }

        hwBrasSbcSipIntercomMapSignalTable OBJECT-TYPE
            SYNTAX SEQUENCE OF HwBrasSbcSipIntercomMapSignalEntry
            MAX-ACCESS not-accessible
            STATUS current
            DESCRIPTION
                "SIP Intercom Map Signal Table.
                obsolete"
            ::= { hwBrasSbcSipTables 4 }

        hwBrasSbcSipIntercomMapSignalEntry OBJECT-TYPE
            SYNTAX HwBrasSbcSipIntercomMapSignalEntry
            MAX-ACCESS not-accessible
            STATUS current
            DESCRIPTION
                "SIP Intercom Map Signal Table Entry."
            INDEX { hwBrasSbcSipIntercomMapSignalAddr, hwBrasSbcSipIntercomMapSignalProtocol }
            ::= { hwBrasSbcSipIntercomMapSignalTable 1 }

        HwBrasSbcSipIntercomMapSignalEntry ::=
            SEQUENCE {
                hwBrasSbcSipIntercomMapSignalAddr
                    IpAddress,
                hwBrasSbcSipIntercomMapSignalProtocol
                    INTEGER,
                hwBrasSbcSipIntercomMapSignalNumber
                    Unsigned32
             }

        hwBrasSbcSipIntercomMapSignalAddr OBJECT-TYPE
            SYNTAX IpAddress
            MAX-ACCESS not-accessible
            STATUS current
            DESCRIPTION
                "Intercom Address Map SIP Signal Map Table IP Address."
            ::= { hwBrasSbcSipIntercomMapSignalEntry 1 }

        hwBrasSbcSipIntercomMapSignalProtocol OBJECT-TYPE
            SYNTAX INTEGER { sip(1) }
            MAX-ACCESS not-accessible
            STATUS current
            DESCRIPTION
                "Intercom Address Map SIP Signal Map Table Protocol."
            ::= { hwBrasSbcSipIntercomMapSignalEntry 2 }

        hwBrasSbcSipIntercomMapSignalNumber OBJECT-TYPE
            SYNTAX Unsigned32
            MAX-ACCESS read-only
            STATUS current
            DESCRIPTION
                "Intercom Address Map SIP Signal Map Table Map Number."
            ::= { hwBrasSbcSipIntercomMapSignalEntry 3 }

        hwBrasSbcSipIntercomMapMediaTable OBJECT-TYPE
            SYNTAX SEQUENCE OF HwBrasSbcSipIntercomMapMediaEntry
            MAX-ACCESS not-accessible
            STATUS current
            DESCRIPTION
                "SIP Intercom Map Media Table.
                obsolete"
            ::= { hwBrasSbcSipTables 5 }

        hwBrasSbcSipIntercomMapMediaEntry OBJECT-TYPE
            SYNTAX HwBrasSbcSipIntercomMapMediaEntry
            MAX-ACCESS not-accessible
            STATUS current
            DESCRIPTION
                "SIP Intercom Map Media Table Entry."
            INDEX { hwBrasSbcSipIntercomMapMediaAddr, hwBrasSbcSipIntercomMapMediaProtocol }
            ::= { hwBrasSbcSipIntercomMapMediaTable 1 }

        HwBrasSbcSipIntercomMapMediaEntry ::=
            SEQUENCE {
                hwBrasSbcSipIntercomMapMediaAddr
                    IpAddress,
                hwBrasSbcSipIntercomMapMediaProtocol
                    INTEGER,
                hwBrasSbcSipIntercomMapMediaNumber
                    Unsigned32
             }

        hwBrasSbcSipIntercomMapMediaAddr OBJECT-TYPE
            SYNTAX IpAddress
            MAX-ACCESS not-accessible
            STATUS current
            DESCRIPTION
                "Intercom Address Map SIP Media Map Table IP Address."
            ::= { hwBrasSbcSipIntercomMapMediaEntry 1 }

        hwBrasSbcSipIntercomMapMediaProtocol OBJECT-TYPE
            SYNTAX INTEGER { sip(1) }
            MAX-ACCESS not-accessible
            STATUS current
            DESCRIPTION
                "Intercom Address Map SIP Media Map Table Protocol."
            ::= { hwBrasSbcSipIntercomMapMediaEntry 2 }

        hwBrasSbcSipIntercomMapMediaNumber OBJECT-TYPE
            SYNTAX Unsigned32
            MAX-ACCESS read-only
            STATUS current
            DESCRIPTION
                "Intercom Address Map SIP Media Map Table Map Number."
            ::= { hwBrasSbcSipIntercomMapMediaEntry 3 }

        hwBrasSbcSipStatSignalPacketTable OBJECT-TYPE
            SYNTAX SEQUENCE OF HwBrasSbcSipStatSignalPacketEntry
            MAX-ACCESS not-accessible
            STATUS current
            DESCRIPTION
                "SIP Statistic of Signaling Packet Table."
            ::= { hwBrasSbcSipTables 6 }

        hwBrasSbcSipStatSignalPacketEntry OBJECT-TYPE
            SYNTAX HwBrasSbcSipStatSignalPacketEntry
            MAX-ACCESS not-accessible
            STATUS current
            DESCRIPTION
                "SIP Statistic of Signaling Packet Table Entry."
            INDEX { hwBrasSbcSipStatSignalPacketIndex }
            ::= { hwBrasSbcSipStatSignalPacketTable 1 }

        HwBrasSbcSipStatSignalPacketEntry ::=
            SEQUENCE {
                hwBrasSbcSipStatSignalPacketIndex
                    INTEGER,
                hwBrasSbcSipStatSignalPacketInNumber
                    Counter64,
                hwBrasSbcSipStatSignalPacketInOctet
                    Counter64,
                hwBrasSbcSipStatSignalPacketOutNumber
                    Counter64,
                hwBrasSbcSipStatSignalPacketOutOctet
                    Counter64,
                hwBrasSbcSipStatSignalPacketRowStatus
                    RowStatus
             }

        hwBrasSbcSipStatSignalPacketIndex OBJECT-TYPE
            SYNTAX INTEGER { sip(1) }
            MAX-ACCESS not-accessible
            STATUS current
            DESCRIPTION
                "Protocol."
            ::= { hwBrasSbcSipStatSignalPacketEntry 1 }

        hwBrasSbcSipStatSignalPacketInNumber OBJECT-TYPE
            SYNTAX Counter64
            MAX-ACCESS read-only
            STATUS current
            DESCRIPTION
                "Input Packet Number."
            ::= { hwBrasSbcSipStatSignalPacketEntry 2 }

        hwBrasSbcSipStatSignalPacketInOctet OBJECT-TYPE
            SYNTAX Counter64
            MAX-ACCESS read-only
            STATUS current
            DESCRIPTION
                "Input Packet Octet."
            ::= { hwBrasSbcSipStatSignalPacketEntry 3 }

        hwBrasSbcSipStatSignalPacketOutNumber OBJECT-TYPE
            SYNTAX Counter64
            MAX-ACCESS read-only
            STATUS current
            DESCRIPTION
                "Output Packet Number."
            ::= { hwBrasSbcSipStatSignalPacketEntry 4 }

        hwBrasSbcSipStatSignalPacketOutOctet OBJECT-TYPE
            SYNTAX Counter64
            MAX-ACCESS read-only
            STATUS current
            DESCRIPTION
                "Output Packet Octet."
            ::= { hwBrasSbcSipStatSignalPacketEntry 5 }

        hwBrasSbcSipStatSignalPacketRowStatus OBJECT-TYPE
            SYNTAX RowStatus
            MAX-ACCESS read-write
            STATUS current
            DESCRIPTION
                "Row Status."
            ::= { hwBrasSbcSipStatSignalPacketEntry 6 }

        hwBrasSbcMgcp OBJECT IDENTIFIER ::= { hwBrasSbcObjects 3 }

        hwBrasSbcMgcpLeaves OBJECT IDENTIFIER ::= { hwBrasSbcMgcp 1 }

        hwBrasSbcMgcpSyslogEnable OBJECT-TYPE
            SYNTAX HWBrasEnabledStatus
            MAX-ACCESS read-write
            STATUS current
            DESCRIPTION
                "MGCP Syslog Enable Status.
                Default: enabled"
            DEFVAL { enabled }
            ::= { hwBrasSbcMgcpLeaves 1 }

        hwBrasSbcMgcpAuepTimer OBJECT-TYPE
            SYNTAX Unsigned32 (0..3600)
            UNITS "seconds"
            MAX-ACCESS read-write
            STATUS current
            DESCRIPTION
                "MGCP MG Aging Time.
                Range: 0-3600
                Default: 600
                Unit: seconds"
            DEFVAL { 600 }
            ::= { hwBrasSbcMgcpLeaves 2 }

        hwBrasSbcMgcpCcbTimer OBJECT-TYPE
            SYNTAX Unsigned32 (10..14400)
            UNITS "minutes"
            MAX-ACCESS read-write
            STATUS current
            DESCRIPTION
                "MGCP CCB Aging Time.
                Range: 10-14400
                Default: 30
                Unit: minutes"
            DEFVAL { 30 }
            ::= { hwBrasSbcMgcpLeaves 3 }

        hwBrasSbcMgcpTxTimer OBJECT-TYPE
            SYNTAX Unsigned32 (6..60)
            UNITS "seconds"
            MAX-ACCESS read-write
            STATUS current
            DESCRIPTION
                "MGCP Transaction Aging Time.
                Range: 6-60
                Default: 6
                Unit: seconds"
            DEFVAL { 6 }
            ::= { hwBrasSbcMgcpLeaves 4 }

        hwBrasSbcMgcpEnable OBJECT-TYPE
            SYNTAX HWBrasEnabledStatus
            MAX-ACCESS read-write
            STATUS current
            DESCRIPTION
                "MGCP Enable Status.
                Default: enabled"
            DEFVAL { enabled }
            ::= { hwBrasSbcMgcpLeaves 5 }

        hwBrasSbcMgcpPDHCountLimit OBJECT-TYPE
            SYNTAX Unsigned32 (1..100)
            MAX-ACCESS read-write
            STATUS current
            DESCRIPTION
                "MGCP Dual-homing Failed Register Count Limit.
                Range: 1-100
                Default: 6"
            DEFVAL { 6 }
            ::= { hwBrasSbcMgcpLeaves 6 }

        hwBrasSbcMgcpTables OBJECT IDENTIFIER ::= { hwBrasSbcMgcp 3 }

        hwBrasSbcMgcpWellknownPortTable OBJECT-TYPE
            SYNTAX SEQUENCE OF HwBrasSbcMgcpWellknownPortEntry
            MAX-ACCESS not-accessible
            STATUS current
            DESCRIPTION
                "MGCP Wellknown Port Table.
                obsolete"
            ::= { hwBrasSbcMgcpTables 1 }

        hwBrasSbcMgcpWellknownPortEntry OBJECT-TYPE
            SYNTAX HwBrasSbcMgcpWellknownPortEntry
            MAX-ACCESS not-accessible
            STATUS current
            DESCRIPTION
                "MGCP Wellknown Port Table Entry."
            INDEX { hwBrasSbcMgcpWellknownPortIndex, hwBrasSbcMgcpWellknownPortProtocol, hwBrasSbcMgcpWellknownPortAddr }
            ::= { hwBrasSbcMgcpWellknownPortTable 1 }

        HwBrasSbcMgcpWellknownPortEntry ::=
            SEQUENCE {
                hwBrasSbcMgcpWellknownPortIndex
                    INTEGER,
                hwBrasSbcMgcpWellknownPortProtocol
                    INTEGER,
                hwBrasSbcMgcpWellknownPortAddr
                    IpAddress,
                hwBrasSbcMgcpWellknownPortPort
                    Unsigned32,
                hwBrasSbcMgcpWellknownPortRowStatus
                    RowStatus
             }

        hwBrasSbcMgcpWellknownPortIndex OBJECT-TYPE
            SYNTAX INTEGER
                {
                clientaddr(1),
                softxaddr(2)
                }
            MAX-ACCESS not-accessible
            STATUS current
            DESCRIPTION
                "MGCP Wellknown Port Index.
                1: Client Side Ip Address
                2: Softx IP Address
                Default: NA"
            ::= { hwBrasSbcMgcpWellknownPortEntry 1 }

        hwBrasSbcMgcpWellknownPortProtocol OBJECT-TYPE
            SYNTAX INTEGER { mgcp(1) }
            MAX-ACCESS not-accessible
            STATUS current
            DESCRIPTION
                "MGCP Wellknown Port Protocol.
                1: mgcp
                Default: NA"
            ::= { hwBrasSbcMgcpWellknownPortEntry 2 }

        hwBrasSbcMgcpWellknownPortAddr OBJECT-TYPE
            SYNTAX IpAddress
            MAX-ACCESS not-accessible
            STATUS current
            DESCRIPTION
                "MGCP Wellknown Port IP Address."
            ::= { hwBrasSbcMgcpWellknownPortEntry 3 }

        hwBrasSbcMgcpWellknownPortPort OBJECT-TYPE
            SYNTAX Unsigned32 (1..65535)
            MAX-ACCESS read-create
            STATUS current
            DESCRIPTION
                "MGCP Wellknown Port Port."
            ::= { hwBrasSbcMgcpWellknownPortEntry 4 }

        hwBrasSbcMgcpWellknownPortRowStatus OBJECT-TYPE
            SYNTAX RowStatus
            MAX-ACCESS read-create
            STATUS current
            DESCRIPTION
                "MGCP Wellknown Port Row Status."
            ::= { hwBrasSbcMgcpWellknownPortEntry 5 }

        hwBrasSbcMgcpSignalMapTable OBJECT-TYPE
            SYNTAX SEQUENCE OF HwBrasSbcMgcpSignalMapEntry
            MAX-ACCESS not-accessible
            STATUS current
            DESCRIPTION
                "MGCP Signal Map Table.
                obsolete"
            ::= { hwBrasSbcMgcpTables 2 }

        hwBrasSbcMgcpSignalMapEntry OBJECT-TYPE
            SYNTAX HwBrasSbcMgcpSignalMapEntry
            MAX-ACCESS not-accessible
            STATUS current
            DESCRIPTION
                "MGCP Signal Map Table Entry."
            INDEX { hwBrasSbcMgcpSignalMapAddr, hwBrasSbcMgcpSignalMapProtocol }
            ::= { hwBrasSbcMgcpSignalMapTable 1 }

        HwBrasSbcMgcpSignalMapEntry ::=
            SEQUENCE {
                hwBrasSbcMgcpSignalMapAddr
                    IpAddress,
                hwBrasSbcMgcpSignalMapProtocol
                    INTEGER,
                hwBrasSbcMgcpSignalMapNumber
                    Unsigned32,
                hwBrasSbcMgcpSignalMapAddrType
                    INTEGER
             }

        hwBrasSbcMgcpSignalMapAddr OBJECT-TYPE
            SYNTAX IpAddress
            MAX-ACCESS not-accessible
            STATUS current
            DESCRIPTION
                "MGCP Signal Map Table IP Address."
            ::= { hwBrasSbcMgcpSignalMapEntry 1 }

        hwBrasSbcMgcpSignalMapProtocol OBJECT-TYPE
            SYNTAX INTEGER { mgcp(1) }
            MAX-ACCESS not-accessible
            STATUS current
            DESCRIPTION
                "MGCP Signal Map Table Protocol."
            ::= { hwBrasSbcMgcpSignalMapEntry 2 }

        hwBrasSbcMgcpSignalMapNumber OBJECT-TYPE
            SYNTAX Unsigned32
            MAX-ACCESS read-only
            STATUS current
            DESCRIPTION
                "MGCP Signal Map Table Map Number."
            ::= { hwBrasSbcMgcpSignalMapEntry 3 }

        hwBrasSbcMgcpSignalMapAddrType OBJECT-TYPE
            SYNTAX INTEGER
                {
                client(1),
                server(2)
                }
            MAX-ACCESS read-only
            STATUS current
            DESCRIPTION
                "MGCP Signal Map Table Map Type."
            ::= { hwBrasSbcMgcpSignalMapEntry 4 }

        hwBrasSbcMgcpMediaMapTable OBJECT-TYPE
            SYNTAX SEQUENCE OF HwBrasSbcMgcpMediaMapEntry
            MAX-ACCESS not-accessible
            STATUS current
            DESCRIPTION
                "MGCP Media Map Table.
                obsolete"
            ::= { hwBrasSbcMgcpTables 3 }

        hwBrasSbcMgcpMediaMapEntry OBJECT-TYPE
            SYNTAX HwBrasSbcMgcpMediaMapEntry
            MAX-ACCESS not-accessible
            STATUS current
            DESCRIPTION
                "MGCP Media Map Table Entry."
            INDEX { hwBrasSbcMgcpMediaMapAddr, hwBrasSbcMgcpMediaMapProtocol }
            ::= { hwBrasSbcMgcpMediaMapTable 1 }

        HwBrasSbcMgcpMediaMapEntry ::=
            SEQUENCE {
                hwBrasSbcMgcpMediaMapAddr
                    IpAddress,
                hwBrasSbcMgcpMediaMapProtocol
                    INTEGER,
                hwBrasSbcMgcpMediaMapNumber
                    Unsigned32
             }

        hwBrasSbcMgcpMediaMapAddr OBJECT-TYPE
            SYNTAX IpAddress
            MAX-ACCESS not-accessible
            STATUS current
            DESCRIPTION
                "MGCP Media Map Table IP Address."
            ::= { hwBrasSbcMgcpMediaMapEntry 1 }

        hwBrasSbcMgcpMediaMapProtocol OBJECT-TYPE
            SYNTAX INTEGER { mgcp(1) }
            MAX-ACCESS not-accessible
            STATUS current
            DESCRIPTION
                "MGCP Media Map Table Protocol."
            ::= { hwBrasSbcMgcpMediaMapEntry 2 }

        hwBrasSbcMgcpMediaMapNumber OBJECT-TYPE
            SYNTAX Unsigned32
            MAX-ACCESS read-only
            STATUS current
            DESCRIPTION
                "MGCP Media Map Table Media Map Number."
            ::= { hwBrasSbcMgcpMediaMapEntry 3 }

        hwBrasSbcMgcpIntercomMapSignalTable OBJECT-TYPE
            SYNTAX SEQUENCE OF HwBrasSbcMgcpIntercomMapSignalEntry
            MAX-ACCESS not-accessible
            STATUS current
            DESCRIPTION
                "MGCP Intercom Map Signal Table.
                obsolete"
            ::= { hwBrasSbcMgcpTables 4 }

        hwBrasSbcMgcpIntercomMapSignalEntry OBJECT-TYPE
            SYNTAX HwBrasSbcMgcpIntercomMapSignalEntry
            MAX-ACCESS not-accessible
            STATUS current
            DESCRIPTION
                "MGCP Intercom Map Signal Table Entry."
            INDEX { hwBrasSbcMgcpIntercomMapSignalAddr, hwBrasSbcMgcpIntercomMapSignalProtocol }
            ::= { hwBrasSbcMgcpIntercomMapSignalTable 1 }

        HwBrasSbcMgcpIntercomMapSignalEntry ::=
            SEQUENCE {
                hwBrasSbcMgcpIntercomMapSignalAddr
                    IpAddress,
                hwBrasSbcMgcpIntercomMapSignalProtocol
                    INTEGER,
                hwBrasSbcMgcpIntercomMapSignalNumber
                    Unsigned32
             }

        hwBrasSbcMgcpIntercomMapSignalAddr OBJECT-TYPE
            SYNTAX IpAddress
            MAX-ACCESS not-accessible
            STATUS current
            DESCRIPTION
                "Intercom Address Map MGCP Signal Map Table IP Address."
            ::= { hwBrasSbcMgcpIntercomMapSignalEntry 1 }

        hwBrasSbcMgcpIntercomMapSignalProtocol OBJECT-TYPE
            SYNTAX INTEGER { mgcp(1) }
            MAX-ACCESS not-accessible
            STATUS current
            DESCRIPTION
                "Intercom Address Map MGCP Signal Map Table Protocol."
            ::= { hwBrasSbcMgcpIntercomMapSignalEntry 2 }

        hwBrasSbcMgcpIntercomMapSignalNumber OBJECT-TYPE
            SYNTAX Unsigned32
            MAX-ACCESS read-only
            STATUS current
            DESCRIPTION
                "Intercom Address Map MGCP Signal Map Table Map Number."
            ::= { hwBrasSbcMgcpIntercomMapSignalEntry 3 }

        hwBrasSbcMgcpIntercomMapMediaTable OBJECT-TYPE
            SYNTAX SEQUENCE OF HwBrasSbcMgcpIntercomMapMediaEntry
            MAX-ACCESS not-accessible
            STATUS current
            DESCRIPTION
                "MGCP Intercom Map Media Table.
                obsolete"
            ::= { hwBrasSbcMgcpTables 5 }

        hwBrasSbcMgcpIntercomMapMediaEntry OBJECT-TYPE
            SYNTAX HwBrasSbcMgcpIntercomMapMediaEntry
            MAX-ACCESS not-accessible
            STATUS current
            DESCRIPTION
                "MGCP Intercom Map Media Table Entry."
            INDEX { hwBrasSbcMgcpIntercomMapMediaAddr, hwBrasSbcMgcpIntercomMapMediaProtocol }
            ::= { hwBrasSbcMgcpIntercomMapMediaTable 1 }

        HwBrasSbcMgcpIntercomMapMediaEntry ::=
            SEQUENCE {
                hwBrasSbcMgcpIntercomMapMediaAddr
                    IpAddress,
                hwBrasSbcMgcpIntercomMapMediaProtocol
                    INTEGER,
                hwBrasSbcMgcpIntercomMapMediaNumber
                    Unsigned32
             }

        hwBrasSbcMgcpIntercomMapMediaAddr OBJECT-TYPE
            SYNTAX IpAddress
            MAX-ACCESS not-accessible
            STATUS current
            DESCRIPTION
                "Intercom Address Map MGCP Media Map Table IP Address."
            ::= { hwBrasSbcMgcpIntercomMapMediaEntry 1 }

        hwBrasSbcMgcpIntercomMapMediaProtocol OBJECT-TYPE
            SYNTAX INTEGER { mgcp(1) }
            MAX-ACCESS not-accessible
            STATUS current
            DESCRIPTION
                "Intercom Address Map MGCP Media Map Table Protocol."
            ::= { hwBrasSbcMgcpIntercomMapMediaEntry 2 }

        hwBrasSbcMgcpIntercomMapMediaNumber OBJECT-TYPE
            SYNTAX Unsigned32
            MAX-ACCESS read-only
            STATUS current
            DESCRIPTION
                "Intercom Address Map MGCP Media Map Table Map Number."
            ::= { hwBrasSbcMgcpIntercomMapMediaEntry 3 }

        hwBrasSbcMgcpStatSignalPacketTable OBJECT-TYPE
            SYNTAX SEQUENCE OF HwBrasSbcMgcpStatSignalPacketEntry
            MAX-ACCESS not-accessible
            STATUS current
            DESCRIPTION
                "MGCP Statistic of Signaling Packet Table."
            ::= { hwBrasSbcMgcpTables 6 }

        hwBrasSbcMgcpStatSignalPacketEntry OBJECT-TYPE
            SYNTAX HwBrasSbcMgcpStatSignalPacketEntry
            MAX-ACCESS not-accessible
            STATUS current
            DESCRIPTION
                "MGCP Statistic of Signaling Packet Table Entry."
            INDEX { hwBrasSbcMgcpStatSignalPacketIndex }
            ::= { hwBrasSbcMgcpStatSignalPacketTable 1 }

        HwBrasSbcMgcpStatSignalPacketEntry ::=
            SEQUENCE {
                hwBrasSbcMgcpStatSignalPacketIndex
                    INTEGER,
                hwBrasSbcMgcpStatSignalPacketInNumber
                    Counter64,
                hwBrasSbcMgcpStatSignalPacketInOctet
                    Counter64,
                hwBrasSbcMgcpStatSignalPacketOutNumber
                    Counter64,
                hwBrasSbcMgcpStatSignalPacketOutOctet
                    Counter64,
                hwBrasSbcMgcpStatSignalPacketRowStatus
                    RowStatus
             }

        hwBrasSbcMgcpStatSignalPacketIndex OBJECT-TYPE
            SYNTAX INTEGER { mgcp(1) }
            MAX-ACCESS not-accessible
            STATUS current
            DESCRIPTION
                "Protocol."
            ::= { hwBrasSbcMgcpStatSignalPacketEntry 1 }

        hwBrasSbcMgcpStatSignalPacketInNumber OBJECT-TYPE
            SYNTAX Counter64
            MAX-ACCESS read-only
            STATUS current
            DESCRIPTION
                "Input Packet Number."
            ::= { hwBrasSbcMgcpStatSignalPacketEntry 2 }

        hwBrasSbcMgcpStatSignalPacketInOctet OBJECT-TYPE
            SYNTAX Counter64
            MAX-ACCESS read-only
            STATUS current
            DESCRIPTION
                "Input Packet Octet."
            ::= { hwBrasSbcMgcpStatSignalPacketEntry 3 }

        hwBrasSbcMgcpStatSignalPacketOutNumber OBJECT-TYPE
            SYNTAX Counter64
            MAX-ACCESS read-only
            STATUS current
            DESCRIPTION
                "Output Packet Number."
            ::= { hwBrasSbcMgcpStatSignalPacketEntry 4 }

        hwBrasSbcMgcpStatSignalPacketOutOctet OBJECT-TYPE
            SYNTAX Counter64
            MAX-ACCESS read-only
            STATUS current
            DESCRIPTION
                "Output Packet Octet."
            ::= { hwBrasSbcMgcpStatSignalPacketEntry 5 }

        hwBrasSbcMgcpStatSignalPacketRowStatus OBJECT-TYPE
            SYNTAX RowStatus
            MAX-ACCESS read-write
            STATUS current
            DESCRIPTION
                "Row Status."
            ::= { hwBrasSbcMgcpStatSignalPacketEntry 6 }

        hwBrasSbcIadms OBJECT IDENTIFIER ::= { hwBrasSbcObjects 4 }

        hwBrasSbcIadmsLeaves OBJECT IDENTIFIER ::= { hwBrasSbcIadms 1 }

        hwBrasSbcIadmsEnable OBJECT-TYPE
            SYNTAX HWBrasEnabledStatus
            MAX-ACCESS read-write
            STATUS current
            DESCRIPTION
                "IADMS Enable Status.
                Default: enabled"
            DEFVAL { enabled }
            ::= { hwBrasSbcIadmsLeaves 1 }

        hwBrasSbcIadmsSyslogEnable OBJECT-TYPE
            SYNTAX HWBrasEnabledStatus
            MAX-ACCESS read-write
            STATUS current
            DESCRIPTION
                "IADMS Syslog Enable Status.
                Default: enabled"
            DEFVAL { enabled }
            ::= { hwBrasSbcIadmsLeaves 2 }

        hwBrasSbcIadmsRegRefreshEnable OBJECT-TYPE
            SYNTAX HWBrasEnabledStatus
            MAX-ACCESS read-write
            STATUS current
            DESCRIPTION
                "IADMS Register Refresh Enable Status.
                Default: disabled"
            DEFVAL { disabled }
            ::= { hwBrasSbcIadmsLeaves 3 }

        hwBrasSbcIadmsTimer OBJECT-TYPE
            SYNTAX Unsigned32 (0..30)
            UNITS "minutes"
            MAX-ACCESS read-write
            STATUS current
            DESCRIPTION
                "IADMS Register-User Aging Time.
                Range: 0-30
                Default: 20
                Unit: minutes"
            DEFVAL { 20 }
            ::= { hwBrasSbcIadmsLeaves 4 }

        hwBrasSbcIadmsTables OBJECT IDENTIFIER ::= { hwBrasSbcIadms 2 }

        hwBrasSbcIadmsWellknownPortTable OBJECT-TYPE
            SYNTAX SEQUENCE OF HwBrasSbcIadmsWellknownPortEntry
            MAX-ACCESS not-accessible
            STATUS current
            DESCRIPTION
                "IADMS Wellknown Port Table.
                obsolete"
            ::= { hwBrasSbcIadmsTables 1 }

        hwBrasSbcIadmsWellknownPortEntry OBJECT-TYPE
            SYNTAX HwBrasSbcIadmsWellknownPortEntry
            MAX-ACCESS not-accessible
            STATUS current
            DESCRIPTION
                "IADMS Wellknown Port Table Entry."
            INDEX { hwBrasSbcIadmsWellknownPortIndex, hwBrasSbcIadmsWellknownPortProtocol, hwBrasSbcIadmsWellknownPortAddr }
            ::= { hwBrasSbcIadmsWellknownPortTable 1 }

        HwBrasSbcIadmsWellknownPortEntry ::=
            SEQUENCE {
                hwBrasSbcIadmsWellknownPortIndex
                    INTEGER,
                hwBrasSbcIadmsWellknownPortProtocol
                    INTEGER,
                hwBrasSbcIadmsWellknownPortAddr
                    IpAddress,
                hwBrasSbcIadmsWellknownPortPort
                    Unsigned32,
                hwBrasSbcIadmsWellknownPortRowStatus
                    RowStatus
             }

        hwBrasSbcIadmsWellknownPortIndex OBJECT-TYPE
            SYNTAX INTEGER
                {
                clientaddr(1),
                iadmsaddr(2)
                }
            MAX-ACCESS not-accessible
            STATUS current
            DESCRIPTION
                "IADMS Wellknown Port Index.
                1: Client Side Ip Address
                2: IADMS IP Address
                Default: NA"
            ::= { hwBrasSbcIadmsWellknownPortEntry 1 }

        hwBrasSbcIadmsWellknownPortProtocol OBJECT-TYPE
            SYNTAX INTEGER { snmp(1) }
            MAX-ACCESS not-accessible
            STATUS current
            DESCRIPTION
                "IADMS Wellknown Port Protocol.
                1: snmp
                Default: NA"
            ::= { hwBrasSbcIadmsWellknownPortEntry 2 }

        hwBrasSbcIadmsWellknownPortAddr OBJECT-TYPE
            SYNTAX IpAddress
            MAX-ACCESS not-accessible
            STATUS current
            DESCRIPTION
                "IADMS Wellknown Port IP Address."
            ::= { hwBrasSbcIadmsWellknownPortEntry 3 }

        hwBrasSbcIadmsWellknownPortPort OBJECT-TYPE
            SYNTAX Unsigned32 (1..65535)
            MAX-ACCESS read-create
            STATUS current
            DESCRIPTION
                "IADMS Wellknown Port Port."
            ::= { hwBrasSbcIadmsWellknownPortEntry 4 }

        hwBrasSbcIadmsWellknownPortRowStatus OBJECT-TYPE
            SYNTAX RowStatus
            MAX-ACCESS read-create
            STATUS current
            DESCRIPTION
                "IADMS Wellknown Port Row Status."
            ::= { hwBrasSbcIadmsWellknownPortEntry 5 }

        hwBrasSbcIadmsMibRegTable OBJECT-TYPE
            SYNTAX SEQUENCE OF HwBrasSbcIadmsMibRegEntry
            MAX-ACCESS not-accessible
            STATUS current
            DESCRIPTION
                "IADMS Support Mib Version Table."
            ::= { hwBrasSbcIadmsTables 2 }

        hwBrasSbcIadmsMibRegEntry OBJECT-TYPE
            SYNTAX HwBrasSbcIadmsMibRegEntry
            MAX-ACCESS not-accessible
            STATUS current
            DESCRIPTION
                "IADMS Support Mib Version Table Entry."
            INDEX { hwBrasSbcIadmsMibRegVersion }
            ::= { hwBrasSbcIadmsMibRegTable 1 }

        HwBrasSbcIadmsMibRegEntry ::=
            SEQUENCE {
                hwBrasSbcIadmsMibRegVersion
                    INTEGER,
                hwBrasSbcIadmsMibRegRegister
                    TruthValue,
                hwBrasSbcIadmsMibRegRowStatus
                    RowStatus
             }

        hwBrasSbcIadmsMibRegVersion OBJECT-TYPE
            SYNTAX INTEGER
                {
                amend(1),
                v150(2),
                v152(3),
                v160(4),
                v210(5)
                }
            MAX-ACCESS not-accessible
            STATUS current
            DESCRIPTION
                "IADMS Support Mib Version.
                1: amend
                2: v150
                3: v152
                4: v160
                5: v210"
            ::= { hwBrasSbcIadmsMibRegEntry 1 }

        hwBrasSbcIadmsMibRegRegister OBJECT-TYPE
            SYNTAX TruthValue
            MAX-ACCESS read-write
            STATUS current
            DESCRIPTION
                "IADMS Support Mib Version Infomation.
                1: true
                2: faulse
                default: true"
            DEFVAL { true }
            ::= { hwBrasSbcIadmsMibRegEntry 2 }

        hwBrasSbcIadmsMibRegRowStatus OBJECT-TYPE
            SYNTAX RowStatus
            MAX-ACCESS read-write
            STATUS current
            DESCRIPTION
                "IADMS Support Mib Version Row Status."
            ::= { hwBrasSbcIadmsMibRegEntry 3 }

        hwBrasSbcIadmsSignalMapTable OBJECT-TYPE
            SYNTAX SEQUENCE OF HwBrasSbcIadmsSignalMapEntry
            MAX-ACCESS not-accessible
            STATUS current
            DESCRIPTION
                "IADMS Signal Map Table.
                obsolete"
            ::= { hwBrasSbcIadmsTables 3 }

        hwBrasSbcIadmsSignalMapEntry OBJECT-TYPE
            SYNTAX HwBrasSbcIadmsSignalMapEntry
            MAX-ACCESS not-accessible
            STATUS current
            DESCRIPTION
                "IADMS Signal Map Table Entry."
            INDEX { hwBrasSbcIadmsSignalMapAddr, hwBrasSbcIadmsSignalMapProtocol }
            ::= { hwBrasSbcIadmsSignalMapTable 1 }

        HwBrasSbcIadmsSignalMapEntry ::=
            SEQUENCE {
                hwBrasSbcIadmsSignalMapAddr
                    IpAddress,
                hwBrasSbcIadmsSignalMapProtocol
                    INTEGER,
                hwBrasSbcIadmsSignalMapNumber
                    Unsigned32,
                hwBrasSbcIadmsSignalMapAddrType
                    INTEGER
             }

        hwBrasSbcIadmsSignalMapAddr OBJECT-TYPE
            SYNTAX IpAddress
            MAX-ACCESS not-accessible
            STATUS current
            DESCRIPTION
                "IADMS Signal Map Table IP Address."
            ::= { hwBrasSbcIadmsSignalMapEntry 1 }

        hwBrasSbcIadmsSignalMapProtocol OBJECT-TYPE
            SYNTAX INTEGER { snmp(1) }
            MAX-ACCESS not-accessible
            STATUS current
            DESCRIPTION
                "IADMS Signal Map Table Protocol."
            ::= { hwBrasSbcIadmsSignalMapEntry 2 }

        hwBrasSbcIadmsSignalMapNumber OBJECT-TYPE
            SYNTAX Unsigned32
            MAX-ACCESS read-only
            STATUS current
            DESCRIPTION
                "IADMS Signal Map Table Map Number."
            ::= { hwBrasSbcIadmsSignalMapEntry 3 }

        hwBrasSbcIadmsSignalMapAddrType OBJECT-TYPE
            SYNTAX INTEGER
                {
                client(1),
                server(2)
                }
            MAX-ACCESS read-only
            STATUS current
            DESCRIPTION
                "IADMS Signal Map Table Map Type."
            ::= { hwBrasSbcIadmsSignalMapEntry 4 }

        hwBrasSbcIadmsMediaMapTable OBJECT-TYPE
            SYNTAX SEQUENCE OF HwBrasSbcIadmsMediaMapEntry
            MAX-ACCESS not-accessible
            STATUS current
            DESCRIPTION
                "IADMS Media Map Table.
                obsolete"
            ::= { hwBrasSbcIadmsTables 4 }

        hwBrasSbcIadmsMediaMapEntry OBJECT-TYPE
            SYNTAX HwBrasSbcIadmsMediaMapEntry
            MAX-ACCESS not-accessible
            STATUS current
            DESCRIPTION
                "IADMS Media Map Table Entry."
            INDEX { hwBrasSbcIadmsMediaMapAddr, hwBrasSbcIadmsMediaMapProtocol }
            ::= { hwBrasSbcIadmsMediaMapTable 1 }

        HwBrasSbcIadmsMediaMapEntry ::=
            SEQUENCE {
                hwBrasSbcIadmsMediaMapAddr
                    IpAddress,
                hwBrasSbcIadmsMediaMapProtocol
                    INTEGER,
                hwBrasSbcIadmsMediaMapNumber
                    Unsigned32
             }

        hwBrasSbcIadmsMediaMapAddr OBJECT-TYPE
            SYNTAX IpAddress
            MAX-ACCESS not-accessible
            STATUS current
            DESCRIPTION
                "IADMS Media Map Table IP Address."
            ::= { hwBrasSbcIadmsMediaMapEntry 1 }

        hwBrasSbcIadmsMediaMapProtocol OBJECT-TYPE
            SYNTAX INTEGER { snmp(1) }
            MAX-ACCESS not-accessible
            STATUS current
            DESCRIPTION
                "IADMS Media Map Table Protocol."
            ::= { hwBrasSbcIadmsMediaMapEntry 2 }

        hwBrasSbcIadmsMediaMapNumber OBJECT-TYPE
            SYNTAX Unsigned32
            MAX-ACCESS read-only
            STATUS current
            DESCRIPTION
                "IADMS Media Map Table Media Map Number."
            ::= { hwBrasSbcIadmsMediaMapEntry 3 }

        hwBrasSbcIadmsIntercomMapSignalTable OBJECT-TYPE
            SYNTAX SEQUENCE OF HwBrasSbcIadmsIntercomMapSignalEntry
            MAX-ACCESS not-accessible
            STATUS current
            DESCRIPTION
                "IADMS Intercom Map Signal Table.
                obsolete"
            ::= { hwBrasSbcIadmsTables 5 }

        hwBrasSbcIadmsIntercomMapSignalEntry OBJECT-TYPE
            SYNTAX HwBrasSbcIadmsIntercomMapSignalEntry
            MAX-ACCESS not-accessible
            STATUS current
            DESCRIPTION
                "IADMS Intercom Map Signal Table Entry."
            INDEX { hwBrasSbcIadmsIntercomMapSignalAddr, hwBrasSbcIadmsIntercomMapSignalProtocol }
            ::= { hwBrasSbcIadmsIntercomMapSignalTable 1 }

        HwBrasSbcIadmsIntercomMapSignalEntry ::=
            SEQUENCE {
                hwBrasSbcIadmsIntercomMapSignalAddr
                    IpAddress,
                hwBrasSbcIadmsIntercomMapSignalProtocol
                    INTEGER,
                hwBrasSbcIadmsIntercomMapSignalNumber
                    Unsigned32
             }

        hwBrasSbcIadmsIntercomMapSignalAddr OBJECT-TYPE
            SYNTAX IpAddress
            MAX-ACCESS not-accessible
            STATUS current
            DESCRIPTION
                "Intercom Address Map IADMS Signal Map Table IP Address."
            ::= { hwBrasSbcIadmsIntercomMapSignalEntry 1 }

        hwBrasSbcIadmsIntercomMapSignalProtocol OBJECT-TYPE
            SYNTAX INTEGER { snmp(1) }
            MAX-ACCESS not-accessible
            STATUS current
            DESCRIPTION
                "Intercom Address Map IADMS Signal Map Table Protocol."
            ::= { hwBrasSbcIadmsIntercomMapSignalEntry 2 }

        hwBrasSbcIadmsIntercomMapSignalNumber OBJECT-TYPE
            SYNTAX Unsigned32
            MAX-ACCESS read-only
            STATUS current
            DESCRIPTION
                "Intercom Address Map IADMS Signal Map Table Map Number."
            ::= { hwBrasSbcIadmsIntercomMapSignalEntry 3 }

        hwBrasSbcIadmsIntercomMapMediaTable OBJECT-TYPE
            SYNTAX SEQUENCE OF HwBrasSbcIadmsIntercomMapMediaEntry
            MAX-ACCESS not-accessible
            STATUS current
            DESCRIPTION
                "IADMS Intercom Map Media Table.
                obsolete"
            ::= { hwBrasSbcIadmsTables 6 }

        hwBrasSbcIadmsIntercomMapMediaEntry OBJECT-TYPE
            SYNTAX HwBrasSbcIadmsIntercomMapMediaEntry
            MAX-ACCESS not-accessible
            STATUS current
            DESCRIPTION
                "IADMS Intercom Map Media Table Entry."
            INDEX { hwBrasSbcIadmsIntercomMapMediaAddr, hwBrasSbcIadmsIntercomMapMediaProtocol }
            ::= { hwBrasSbcIadmsIntercomMapMediaTable 1 }

        HwBrasSbcIadmsIntercomMapMediaEntry ::=
            SEQUENCE {
                hwBrasSbcIadmsIntercomMapMediaAddr
                    IpAddress,
                hwBrasSbcIadmsIntercomMapMediaProtocol
                    INTEGER,
                hwBrasSbcIadmsIntercomMapMediaNumber
                    Unsigned32
             }

        hwBrasSbcIadmsIntercomMapMediaAddr OBJECT-TYPE
            SYNTAX IpAddress
            MAX-ACCESS not-accessible
            STATUS current
            DESCRIPTION
                "Intercom Address Map IADMS Media Map Table IP Address."
            ::= { hwBrasSbcIadmsIntercomMapMediaEntry 1 }

        hwBrasSbcIadmsIntercomMapMediaProtocol OBJECT-TYPE
            SYNTAX INTEGER { snmp(1) }
            MAX-ACCESS not-accessible
            STATUS current
            DESCRIPTION
                "Intercom Address Map IADMS Media Map Table Protocol."
            ::= { hwBrasSbcIadmsIntercomMapMediaEntry 2 }

        hwBrasSbcIadmsIntercomMapMediaNumber OBJECT-TYPE
            SYNTAX Unsigned32
            MAX-ACCESS read-only
            STATUS current
            DESCRIPTION
                "Intercom Address Map IADMS Media Map Table Map Number."
            ::= { hwBrasSbcIadmsIntercomMapMediaEntry 3 }

        hwBrasSbcIadmsStatSignalPacketTable OBJECT-TYPE
            SYNTAX SEQUENCE OF HwBrasSbcIadmsStatSignalPacketEntry
            MAX-ACCESS not-accessible
            STATUS current
            DESCRIPTION
                "IADMS Statistic of Signaling Packet Table."
            ::= { hwBrasSbcIadmsTables 7 }

        hwBrasSbcIadmsStatSignalPacketEntry OBJECT-TYPE
            SYNTAX HwBrasSbcIadmsStatSignalPacketEntry
            MAX-ACCESS not-accessible
            STATUS current
            DESCRIPTION
                "IADMS Statistic of Signaling Packet Table Entry."
            INDEX { hwBrasSbcIadmsStatSignalPacketIndex }
            ::= { hwBrasSbcIadmsStatSignalPacketTable 1 }

        HwBrasSbcIadmsStatSignalPacketEntry ::=
            SEQUENCE {
                hwBrasSbcIadmsStatSignalPacketIndex
                    INTEGER,
                hwBrasSbcIadmsStatSignalPacketInNumber
                    Counter64,
                hwBrasSbcIadmsStatSignalPacketInOctet
                    Counter64,
                hwBrasSbcIadmsStatSignalPacketOutNumber
                    Counter64,
                hwBrasSbcIadmsStatSignalPacketOutOctet
                    Counter64,
                hwBrasSbcIadmsStatSignalPacketRowStatus
                    RowStatus
             }

        hwBrasSbcIadmsStatSignalPacketIndex OBJECT-TYPE
            SYNTAX INTEGER { iadms(1) }
            MAX-ACCESS not-accessible
            STATUS current
            DESCRIPTION
                "Protocol."
            ::= { hwBrasSbcIadmsStatSignalPacketEntry 1 }

        hwBrasSbcIadmsStatSignalPacketInNumber OBJECT-TYPE
            SYNTAX Counter64
            MAX-ACCESS read-only
            STATUS current
            DESCRIPTION
                "Input Packet Number."
            ::= { hwBrasSbcIadmsStatSignalPacketEntry 2 }

        hwBrasSbcIadmsStatSignalPacketInOctet OBJECT-TYPE
            SYNTAX Counter64
            MAX-ACCESS read-only
            STATUS current
            DESCRIPTION
                "Input Packet Octet."
            ::= { hwBrasSbcIadmsStatSignalPacketEntry 3 }

        hwBrasSbcIadmsStatSignalPacketOutNumber OBJECT-TYPE
            SYNTAX Counter64
            MAX-ACCESS read-only
            STATUS current
            DESCRIPTION
                "Output Packet Number."
            ::= { hwBrasSbcIadmsStatSignalPacketEntry 4 }

        hwBrasSbcIadmsStatSignalPacketOutOctet OBJECT-TYPE
            SYNTAX Counter64
            MAX-ACCESS read-only
            STATUS current
            DESCRIPTION
                "Output Packet Octet."
            ::= { hwBrasSbcIadmsStatSignalPacketEntry 5 }

        hwBrasSbcIadmsStatSignalPacketRowStatus OBJECT-TYPE
            SYNTAX RowStatus
            MAX-ACCESS read-write
            STATUS current
            DESCRIPTION
                "Row Status."
            ::= { hwBrasSbcIadmsStatSignalPacketEntry 6 }

        hwBrasSbcH323 OBJECT IDENTIFIER ::= { hwBrasSbcObjects 5 }

        hwBrasSbcH323Leaves OBJECT IDENTIFIER ::= { hwBrasSbcH323 1 }

        hwBrasSbcH323Enable OBJECT-TYPE
            SYNTAX HWBrasEnabledStatus
            MAX-ACCESS read-write
            STATUS current
            DESCRIPTION
                "H.323 Enable Status.
                Default: enabled"
            DEFVAL { enabled }
            ::= { hwBrasSbcH323Leaves 1 }

        hwBrasSbcH323SyslogEnable OBJECT-TYPE
            SYNTAX HWBrasEnabledStatus
            MAX-ACCESS read-write
            STATUS current
            DESCRIPTION
                "H.323 Syslog Enable Status.
                Default: enabled"
            DEFVAL { enabled }
            ::= { hwBrasSbcH323Leaves 2 }

        hwBrasSbcH323CallsessionTimer OBJECT-TYPE
            SYNTAX Unsigned32 (3..24)
            UNITS "hours"
            MAX-ACCESS read-write
            STATUS current
            DESCRIPTION
                "H.323 Callsession Aging Time.
                Range: 3-24
                Default: 24
                Unit: hours"
            DEFVAL { 24 }
            ::= { hwBrasSbcH323Leaves 3 }

        hwBrasSbcH323Q931WellknownPort OBJECT-TYPE
            SYNTAX Unsigned32 (1..49999)
            MAX-ACCESS read-write
            STATUS current
            DESCRIPTION
                "H.323 Q.931 Wellknown Port Number.
                Range: 1-49999
                Default: 1720"
            DEFVAL { 1720 }
            ::= { hwBrasSbcH323Leaves 4 }

        hwBrasSbcH323PDHCountLimit OBJECT-TYPE
            SYNTAX Unsigned32 (1..100)
            MAX-ACCESS read-write
            STATUS current
            DESCRIPTION
                "H.323 Dual-homing Failed Register Count Limit.
                Range: 1-100
                Default: 6"
            DEFVAL { 6 }
            ::= { hwBrasSbcH323Leaves 5 }

        hwBrasSbcH323Tables OBJECT IDENTIFIER ::= { hwBrasSbcH323 2 }

        hwBrasSbcH323WellknownPortTable OBJECT-TYPE
            SYNTAX SEQUENCE OF HwBrasSbcH323WellknownPortEntry
            MAX-ACCESS not-accessible
            STATUS current
            DESCRIPTION
                "H.323 Wellknown Port Table.
                obsolete"
            ::= { hwBrasSbcH323Tables 1 }

        hwBrasSbcH323WellknownPortEntry OBJECT-TYPE
            SYNTAX HwBrasSbcH323WellknownPortEntry
            MAX-ACCESS not-accessible
            STATUS current
            DESCRIPTION
                "H.323 Wellknown Port Table Entry."
            INDEX { hwBrasSbcH323WellknownPortIndex, hwBrasSbcH323WellknownPortProtocol, hwBrasSbcH323WellknownPortAddr }
            ::= { hwBrasSbcH323WellknownPortTable 1 }

        HwBrasSbcH323WellknownPortEntry ::=
            SEQUENCE {
                hwBrasSbcH323WellknownPortIndex
                    INTEGER,
                hwBrasSbcH323WellknownPortProtocol
                    INTEGER,
                hwBrasSbcH323WellknownPortAddr
                    IpAddress,
                hwBrasSbcH323WellknownPortPort
                    Unsigned32,
                hwBrasSbcH323WellknownPortRowStatus
                    RowStatus
             }

        hwBrasSbcH323WellknownPortIndex OBJECT-TYPE
            SYNTAX INTEGER
                {
                clientaddr(1),
                softxaddr(2)
                }
            MAX-ACCESS not-accessible
            STATUS current
            DESCRIPTION
                "H.323 Wellknown Port Index.
                1: Client Side Ip Address
                2: Softx IP Address
                Default: NA"
            ::= { hwBrasSbcH323WellknownPortEntry 1 }

        hwBrasSbcH323WellknownPortProtocol OBJECT-TYPE
            SYNTAX INTEGER
                {
                ras(1),
                q931(2)
                }
            MAX-ACCESS not-accessible
            STATUS current
            DESCRIPTION
                "H.323 Wellknown Port Protocol.
                1: ras
                2: q931
                Default: NA"
            ::= { hwBrasSbcH323WellknownPortEntry 2 }

        hwBrasSbcH323WellknownPortAddr OBJECT-TYPE
            SYNTAX IpAddress
            MAX-ACCESS not-accessible
            STATUS current
            DESCRIPTION
                "H.323 Wellknown Port IP Address."
            ::= { hwBrasSbcH323WellknownPortEntry 3 }

        hwBrasSbcH323WellknownPortPort OBJECT-TYPE
            SYNTAX Unsigned32 (1..65535)
            MAX-ACCESS read-create
            STATUS current
            DESCRIPTION
                "H.323 Wellknown Port Port."
            ::= { hwBrasSbcH323WellknownPortEntry 4 }

        hwBrasSbcH323WellknownPortRowStatus OBJECT-TYPE
            SYNTAX RowStatus
            MAX-ACCESS read-create
            STATUS current
            DESCRIPTION
                "H.323 Wellknown Port Row Status."
            ::= { hwBrasSbcH323WellknownPortEntry 5 }

        hwBrasSbcH323SignalMapTable OBJECT-TYPE
            SYNTAX SEQUENCE OF HwBrasSbcH323SignalMapEntry
            MAX-ACCESS not-accessible
            STATUS current
            DESCRIPTION
                "H.323 Signal Map Table.
                obsolete"
            ::= { hwBrasSbcH323Tables 2 }

        hwBrasSbcH323SignalMapEntry OBJECT-TYPE
            SYNTAX HwBrasSbcH323SignalMapEntry
            MAX-ACCESS not-accessible
            STATUS current
            DESCRIPTION
                "H.323 Signal Map Table Entry."
            INDEX { hwBrasSbcH323SignalMapAddr, hwBrasSbcH323SignalMapProtocol }
            ::= { hwBrasSbcH323SignalMapTable 1 }

        HwBrasSbcH323SignalMapEntry ::=
            SEQUENCE {
                hwBrasSbcH323SignalMapAddr
                    IpAddress,
                hwBrasSbcH323SignalMapProtocol
                    INTEGER,
                hwBrasSbcH323SignalMapNumber
                    Unsigned32,
                hwBrasSbcH323SignalMapAddrType
                    INTEGER
             }

        hwBrasSbcH323SignalMapAddr OBJECT-TYPE
            SYNTAX IpAddress
            MAX-ACCESS not-accessible
            STATUS current
            DESCRIPTION
                "H.323 Signal Map Table IP Address."
            ::= { hwBrasSbcH323SignalMapEntry 1 }

        hwBrasSbcH323SignalMapProtocol OBJECT-TYPE
            SYNTAX INTEGER
                {
                ras(1),
                q931(2),
                h245(3)
                }
            MAX-ACCESS not-accessible
            STATUS current
            DESCRIPTION
                "H.323 Signal Map Table Protocol."
            ::= { hwBrasSbcH323SignalMapEntry 2 }

        hwBrasSbcH323SignalMapNumber OBJECT-TYPE
            SYNTAX Unsigned32
            MAX-ACCESS read-only
            STATUS current
            DESCRIPTION
                "H.323 Signal Map Table Map Number."
            ::= { hwBrasSbcH323SignalMapEntry 3 }

        hwBrasSbcH323SignalMapAddrType OBJECT-TYPE
            SYNTAX INTEGER
                {
                client(1),
                server(2)
                }
            MAX-ACCESS read-only
            STATUS current
            DESCRIPTION
                "H.323 Signal Map Table Map Type."
            ::= { hwBrasSbcH323SignalMapEntry 4 }

        hwBrasSbcH323MediaMapTable OBJECT-TYPE
            SYNTAX SEQUENCE OF HwBrasSbcH323MediaMapEntry
            MAX-ACCESS not-accessible
            STATUS current
            DESCRIPTION
                "H.323 Media Map Table.
                obsolete"
            ::= { hwBrasSbcH323Tables 3 }

        hwBrasSbcH323MediaMapEntry OBJECT-TYPE
            SYNTAX HwBrasSbcH323MediaMapEntry
            MAX-ACCESS not-accessible
            STATUS current
            DESCRIPTION
                "H.323 Media Map Table Entry."
            INDEX { hwBrasSbcH323MediaMapAddr, hwBrasSbcH323MediaMapProtocol }
            ::= { hwBrasSbcH323MediaMapTable 1 }

        HwBrasSbcH323MediaMapEntry ::=
            SEQUENCE {
                hwBrasSbcH323MediaMapAddr
                    IpAddress,
                hwBrasSbcH323MediaMapProtocol
                    INTEGER,
                hwBrasSbcH323MediaMapNumber
                    Unsigned32
             }

        hwBrasSbcH323MediaMapAddr OBJECT-TYPE
            SYNTAX IpAddress
            MAX-ACCESS not-accessible
            STATUS current
            DESCRIPTION
                "H.323 Media Map Table IP Address."
            ::= { hwBrasSbcH323MediaMapEntry 1 }

        hwBrasSbcH323MediaMapProtocol OBJECT-TYPE
            SYNTAX INTEGER { h323(1) }
            MAX-ACCESS not-accessible
            STATUS current
            DESCRIPTION
                "H.323 Media Map Table Protocol."
            ::= { hwBrasSbcH323MediaMapEntry 2 }

        hwBrasSbcH323MediaMapNumber OBJECT-TYPE
            SYNTAX Unsigned32
            MAX-ACCESS read-only
            STATUS current
            DESCRIPTION
                "H.323 Media Map Table Media Map Number."
            ::= { hwBrasSbcH323MediaMapEntry 3 }

        hwBrasSbcH323IntercomMapSignalTable OBJECT-TYPE
            SYNTAX SEQUENCE OF HwBrasSbcH323IntercomMapSignalEntry
            MAX-ACCESS not-accessible
            STATUS current
            DESCRIPTION
                "H.323 Intercom Map Signal Table.
                obsolete"
            ::= { hwBrasSbcH323Tables 4 }

        hwBrasSbcH323IntercomMapSignalEntry OBJECT-TYPE
            SYNTAX HwBrasSbcH323IntercomMapSignalEntry
            MAX-ACCESS not-accessible
            STATUS current
            DESCRIPTION
                "H.323 Intercom Map Signal Table Entry."
            INDEX { hwBrasSbcH323IntercomMapSignalAddr, hwBrasSbcH323IntercomMapSignalProtocol }
            ::= { hwBrasSbcH323IntercomMapSignalTable 1 }

        HwBrasSbcH323IntercomMapSignalEntry ::=
            SEQUENCE {
                hwBrasSbcH323IntercomMapSignalAddr
                    IpAddress,
                hwBrasSbcH323IntercomMapSignalProtocol
                    INTEGER,
                hwBrasSbcH323IntercomMapSignalNumber
                    Unsigned32
             }

        hwBrasSbcH323IntercomMapSignalAddr OBJECT-TYPE
            SYNTAX IpAddress
            MAX-ACCESS not-accessible
            STATUS current
            DESCRIPTION
                "Intercom Address Map H.323 Signal Map Table IP Address."
            ::= { hwBrasSbcH323IntercomMapSignalEntry 1 }

        hwBrasSbcH323IntercomMapSignalProtocol OBJECT-TYPE
            SYNTAX INTEGER
                {
                ras(1),
                q931(2),
                h245(3)
                }
            MAX-ACCESS not-accessible
            STATUS current
            DESCRIPTION
                "Intercom Address Map H.323 Signal Map Table Protocol."
            ::= { hwBrasSbcH323IntercomMapSignalEntry 2 }

        hwBrasSbcH323IntercomMapSignalNumber OBJECT-TYPE
            SYNTAX Unsigned32
            MAX-ACCESS read-only
            STATUS current
            DESCRIPTION
                "Intercom Address Map H.323 Signal Map Table Map Number."
            ::= { hwBrasSbcH323IntercomMapSignalEntry 3 }

        hwBrasSbcH323IntercomMapMediaTable OBJECT-TYPE
            SYNTAX SEQUENCE OF HwBrasSbcH323IntercomMapMediaEntry
            MAX-ACCESS not-accessible
            STATUS current
            DESCRIPTION
                "H.323 Intercom Map Media Table.
                obsolete"
            ::= { hwBrasSbcH323Tables 5 }

        hwBrasSbcH323IntercomMapMediaEntry OBJECT-TYPE
            SYNTAX HwBrasSbcH323IntercomMapMediaEntry
            MAX-ACCESS not-accessible
            STATUS current
            DESCRIPTION
                "H.323 Intercom Map Media Table Entry."
            INDEX { hwBrasSbcH323IntercomMapMediaAddr, hwBrasSbcH323IntercomMapMediaProtocol }
            ::= { hwBrasSbcH323IntercomMapMediaTable 1 }

        HwBrasSbcH323IntercomMapMediaEntry ::=
            SEQUENCE {
                hwBrasSbcH323IntercomMapMediaAddr
                    IpAddress,
                hwBrasSbcH323IntercomMapMediaProtocol
                    INTEGER,
                hwBrasSbcH323IntercomMapMediaNumber
                    Unsigned32
             }

        hwBrasSbcH323IntercomMapMediaAddr OBJECT-TYPE
            SYNTAX IpAddress
            MAX-ACCESS not-accessible
            STATUS current
            DESCRIPTION
                "Intercom Address Map H.323 Media Map Table IP Address."
            ::= { hwBrasSbcH323IntercomMapMediaEntry 1 }

        hwBrasSbcH323IntercomMapMediaProtocol OBJECT-TYPE
            SYNTAX INTEGER { h323(1) }
            MAX-ACCESS not-accessible
            STATUS current
            DESCRIPTION
                "Intercom Address Map H.323 Media Map Table Protocol."
            ::= { hwBrasSbcH323IntercomMapMediaEntry 2 }

        hwBrasSbcH323IntercomMapMediaNumber OBJECT-TYPE
            SYNTAX Unsigned32
            MAX-ACCESS read-only
            STATUS current
            DESCRIPTION
                "Intercom Address Map H.323 Media Map Table Map Number."
            ::= { hwBrasSbcH323IntercomMapMediaEntry 3 }

        hwBrasSbcH323StatSignalPacketTable OBJECT-TYPE
            SYNTAX SEQUENCE OF HwBrasSbcH323StatSignalPacketEntry
            MAX-ACCESS not-accessible
            STATUS current
            DESCRIPTION
                "H.323 Statistic of Signaling Packet Table."
            ::= { hwBrasSbcH323Tables 6 }

        hwBrasSbcH323StatSignalPacketEntry OBJECT-TYPE
            SYNTAX HwBrasSbcH323StatSignalPacketEntry
            MAX-ACCESS not-accessible
            STATUS current
            DESCRIPTION
                "H.323 Statistic of Signaling Packet Table Entry."
            INDEX { hwBrasSbcH323StatSignalPacketIndex }
            ::= { hwBrasSbcH323StatSignalPacketTable 1 }

        HwBrasSbcH323StatSignalPacketEntry ::=
            SEQUENCE {
                hwBrasSbcH323StatSignalPacketIndex
                    INTEGER,
                hwBrasSbcH323StatSignalPacketInNumber
                    Counter64,
                hwBrasSbcH323StatSignalPacketInOctet
                    Counter64,
                hwBrasSbcH323StatSignalPacketOutNumber
                    Counter64,
                hwBrasSbcH323StatSignalPacketOutOctet
                    Counter64,
                hwBrasSbcH323StatSignalPacketRowStatus
                    RowStatus
             }

        hwBrasSbcH323StatSignalPacketIndex OBJECT-TYPE
            SYNTAX INTEGER { h323(1) }
            MAX-ACCESS not-accessible
            STATUS current
            DESCRIPTION
                "Protocol."
            ::= { hwBrasSbcH323StatSignalPacketEntry 1 }

        hwBrasSbcH323StatSignalPacketInNumber OBJECT-TYPE
            SYNTAX Counter64
            MAX-ACCESS read-only
            STATUS current
            DESCRIPTION
                "Input Packet Number."
            ::= { hwBrasSbcH323StatSignalPacketEntry 2 }

        hwBrasSbcH323StatSignalPacketInOctet OBJECT-TYPE
            SYNTAX Counter64
            MAX-ACCESS read-only
            STATUS current
            DESCRIPTION
                "Input Packet Octet."
            ::= { hwBrasSbcH323StatSignalPacketEntry 3 }

        hwBrasSbcH323StatSignalPacketOutNumber OBJECT-TYPE
            SYNTAX Counter64
            MAX-ACCESS read-only
            STATUS current
            DESCRIPTION
                "Output Packet Number."
            ::= { hwBrasSbcH323StatSignalPacketEntry 4 }

        hwBrasSbcH323StatSignalPacketOutOctet OBJECT-TYPE
            SYNTAX Counter64
            MAX-ACCESS read-only
            STATUS current
            DESCRIPTION
                "Output Packet Octet."
            ::= { hwBrasSbcH323StatSignalPacketEntry 5 }

        hwBrasSbcH323StatSignalPacketRowStatus OBJECT-TYPE
            SYNTAX RowStatus
            MAX-ACCESS read-write
            STATUS current
            DESCRIPTION
                "Row Status."
            ::= { hwBrasSbcH323StatSignalPacketEntry 6 }

        hwBrasSbcIdo OBJECT IDENTIFIER ::= { hwBrasSbcObjects 6 }

        hwBrasSbcIdoLeaves OBJECT IDENTIFIER ::= { hwBrasSbcIdo 1 }

        hwBrasSbcIdoEnable OBJECT-TYPE
            SYNTAX HWBrasEnabledStatus
            MAX-ACCESS read-write
            STATUS current
            DESCRIPTION
                "iDo Enable Status.
                Default: enabled"
            DEFVAL { enabled }
            ::= { hwBrasSbcIdoLeaves 1 }

        hwBrasSbcIdoSyslogEnable OBJECT-TYPE
            SYNTAX HWBrasEnabledStatus
            MAX-ACCESS read-write
            STATUS current
            DESCRIPTION
                "iDo Syslog Enable Status.
                Default: enabled"
            DEFVAL { enabled }
            ::= { hwBrasSbcIdoLeaves 2 }

        hwBrasSbcIdoTables OBJECT IDENTIFIER ::= { hwBrasSbcIdo 2 }

        hwBrasSbcIdoWellknownPortTable OBJECT-TYPE
            SYNTAX SEQUENCE OF HwBrasSbcIdoWellknownPortEntry
            MAX-ACCESS not-accessible
            STATUS current
            DESCRIPTION
                "iDo Wellknown Port Table.
                obsolete"
            ::= { hwBrasSbcIdoTables 1 }

        hwBrasSbcIdoWellknownPortEntry OBJECT-TYPE
            SYNTAX HwBrasSbcIdoWellknownPortEntry
            MAX-ACCESS not-accessible
            STATUS current
            DESCRIPTION
                "iDo Wellknown Port Table Entry."
            INDEX { hwBrasSbcIdoWellknownPortIndex, hwBrasSbcIdoWellknownPortProtocol, hwBrasSbcIdoWellknownPortAddr }
            ::= { hwBrasSbcIdoWellknownPortTable 1 }

        HwBrasSbcIdoWellknownPortEntry ::=
            SEQUENCE {
                hwBrasSbcIdoWellknownPortIndex
                    INTEGER,
                hwBrasSbcIdoWellknownPortProtocol
                    INTEGER,
                hwBrasSbcIdoWellknownPortAddr
                    IpAddress,
                hwBrasSbcIdoWellknownPortPort
                    Unsigned32,
                hwBrasSbcIdoWellknownPortRowStatus
                    RowStatus
             }

        hwBrasSbcIdoWellknownPortIndex OBJECT-TYPE
            SYNTAX INTEGER
                {
                clientaddr(1),
                softxaddr(2)
                }
            MAX-ACCESS not-accessible
            STATUS current
            DESCRIPTION
                "iDo Wellknown Port Index.
                1: Client Side Ip Address
                2: Softx IP Address
                Default: NA"
            ::= { hwBrasSbcIdoWellknownPortEntry 1 }

        hwBrasSbcIdoWellknownPortProtocol OBJECT-TYPE
            SYNTAX INTEGER { ido(1) }
            MAX-ACCESS not-accessible
            STATUS current
            DESCRIPTION
                "iDo Wellknown Port Protocol.
                1: ido
                Default: NA"
            ::= { hwBrasSbcIdoWellknownPortEntry 2 }

        hwBrasSbcIdoWellknownPortAddr OBJECT-TYPE
            SYNTAX IpAddress
            MAX-ACCESS not-accessible
            STATUS current
            DESCRIPTION
                "iDo Wellknown Port IP Address."
            ::= { hwBrasSbcIdoWellknownPortEntry 3 }

        hwBrasSbcIdoWellknownPortPort OBJECT-TYPE
            SYNTAX Unsigned32 (1..65535)
            MAX-ACCESS read-create
            STATUS current
            DESCRIPTION
                "iDo Wellknown Port Port."
            ::= { hwBrasSbcIdoWellknownPortEntry 4 }

        hwBrasSbcIdoWellknownPortRowStatus OBJECT-TYPE
            SYNTAX RowStatus
            MAX-ACCESS read-create
            STATUS current
            DESCRIPTION
                "iDo Wellknown Port Row Status."
            ::= { hwBrasSbcIdoWellknownPortEntry 5 }

        hwBrasSbcIdoSignalMapTable OBJECT-TYPE
            SYNTAX SEQUENCE OF HwBrasSbcIdoSignalMapEntry
            MAX-ACCESS not-accessible
            STATUS current
            DESCRIPTION
                "iDo Signal Map Table.
                obsolete"
            ::= { hwBrasSbcIdoTables 2 }

        hwBrasSbcIdoSignalMapEntry OBJECT-TYPE
            SYNTAX HwBrasSbcIdoSignalMapEntry
            MAX-ACCESS not-accessible
            STATUS current
            DESCRIPTION
                "iDo Signal Map Table Entry."
            INDEX { hwBrasSbcIdoSignalMapAddr, hwBrasSbcIdoSignalMapProtocol }
            ::= { hwBrasSbcIdoSignalMapTable 1 }

        HwBrasSbcIdoSignalMapEntry ::=
            SEQUENCE {
                hwBrasSbcIdoSignalMapAddr
                    IpAddress,
                hwBrasSbcIdoSignalMapProtocol
                    INTEGER,
                hwBrasSbcIdoSignalMapNumber
                    Unsigned32,
                hwBrasSbcIdoSignalMapAddrType
                    INTEGER
             }

        hwBrasSbcIdoSignalMapAddr OBJECT-TYPE
            SYNTAX IpAddress
            MAX-ACCESS not-accessible
            STATUS current
            DESCRIPTION
                "iDo Signal Map Table IP Address."
            ::= { hwBrasSbcIdoSignalMapEntry 1 }

        hwBrasSbcIdoSignalMapProtocol OBJECT-TYPE
            SYNTAX INTEGER { ido(1) }
            MAX-ACCESS not-accessible
            STATUS current
            DESCRIPTION
                "iDo Signal Map Table Protocol."
            ::= { hwBrasSbcIdoSignalMapEntry 2 }

        hwBrasSbcIdoSignalMapNumber OBJECT-TYPE
            SYNTAX Unsigned32
            MAX-ACCESS read-only
            STATUS current
            DESCRIPTION
                "iDo Signal Map Table Map Number."
            ::= { hwBrasSbcIdoSignalMapEntry 3 }

        hwBrasSbcIdoSignalMapAddrType OBJECT-TYPE
            SYNTAX INTEGER
                {
                client(1),
                server(2)
                }
            MAX-ACCESS read-only
            STATUS current
            DESCRIPTION
                "iDo Signal Map Table Map Type."
            ::= { hwBrasSbcIdoSignalMapEntry 4 }

        hwBrasSbcIdoIntercomMapSignalTable OBJECT-TYPE
            SYNTAX SEQUENCE OF HwBrasSbcIdoIntercomMapSignalEntry
            MAX-ACCESS not-accessible
            STATUS current
            DESCRIPTION
                "iDo Intercom Map Signal Table.
                obsolete"
            ::= { hwBrasSbcIdoTables 3 }

        hwBrasSbcIdoIntercomMapSignalEntry OBJECT-TYPE
            SYNTAX HwBrasSbcIdoIntercomMapSignalEntry
            MAX-ACCESS not-accessible
            STATUS current
            DESCRIPTION
                "iDo Intercom Map Signal Table Entry."
            INDEX { hwBrasSbcIdoIntercomMapSignalAddr, hwBrasSbcIdoIntercomMapSignalProtocol }
            ::= { hwBrasSbcIdoIntercomMapSignalTable 1 }

        HwBrasSbcIdoIntercomMapSignalEntry ::=
            SEQUENCE {
                hwBrasSbcIdoIntercomMapSignalAddr
                    IpAddress,
                hwBrasSbcIdoIntercomMapSignalProtocol
                    INTEGER,
                hwBrasSbcIdoIntercomMapSignalNumber
                    Unsigned32
             }

        hwBrasSbcIdoIntercomMapSignalAddr OBJECT-TYPE
            SYNTAX IpAddress
            MAX-ACCESS not-accessible
            STATUS current
            DESCRIPTION
                "Intercom Address Map iDo Signal Map Table IP Address."
            ::= { hwBrasSbcIdoIntercomMapSignalEntry 1 }

        hwBrasSbcIdoIntercomMapSignalProtocol OBJECT-TYPE
            SYNTAX INTEGER { ido(1) }
            MAX-ACCESS not-accessible
            STATUS current
            DESCRIPTION
                "Intercom Address Map iDo Signal Map Table Protocol."
            ::= { hwBrasSbcIdoIntercomMapSignalEntry 2 }

        hwBrasSbcIdoIntercomMapSignalNumber OBJECT-TYPE
            SYNTAX Unsigned32
            MAX-ACCESS read-only
            STATUS current
            DESCRIPTION
                "Intercom Address Map iDo Signal Map Table Map Number."
            ::= { hwBrasSbcIdoIntercomMapSignalEntry 3 }

        hwBrasSbcIdoStatSignalPacketTable OBJECT-TYPE
            SYNTAX SEQUENCE OF HwBrasSbcIdoStatSignalPacketEntry
            MAX-ACCESS not-accessible
            STATUS current
            DESCRIPTION
                "iDo Statistic of Signaling Packet Table."
            ::= { hwBrasSbcIdoTables 4 }

        hwBrasSbcIdoStatSignalPacketEntry OBJECT-TYPE
            SYNTAX HwBrasSbcIdoStatSignalPacketEntry
            MAX-ACCESS not-accessible
            STATUS current
            DESCRIPTION
                "iDo Statistic of Signaling Packet Table Entry."
            INDEX { hwBrasSbcIdoStatSignalPacketIndex }
            ::= { hwBrasSbcIdoStatSignalPacketTable 1 }

        HwBrasSbcIdoStatSignalPacketEntry ::=
            SEQUENCE {
                hwBrasSbcIdoStatSignalPacketIndex
                    INTEGER,
                hwBrasSbcIdoStatSignalPacketInNumber
                    Counter64,
                hwBrasSbcIdoStatSignalPacketInOctet
                    Counter64,
                hwBrasSbcIdoStatSignalPacketOutNumber
                    Counter64,
                hwBrasSbcIdoStatSignalPacketOutOctet
                    Counter64,
                hwBrasSbcIdoStatSignalPacketRowStatus
                    RowStatus
             }

        hwBrasSbcIdoStatSignalPacketIndex OBJECT-TYPE
            SYNTAX INTEGER { ido(1) }
            MAX-ACCESS not-accessible
            STATUS current
            DESCRIPTION
                "Protocol."
            ::= { hwBrasSbcIdoStatSignalPacketEntry 1 }

        hwBrasSbcIdoStatSignalPacketInNumber OBJECT-TYPE
            SYNTAX Counter64
            MAX-ACCESS read-only
            STATUS current
            DESCRIPTION
                "Input Packet Number."
            ::= { hwBrasSbcIdoStatSignalPacketEntry 2 }

        hwBrasSbcIdoStatSignalPacketInOctet OBJECT-TYPE
            SYNTAX Counter64
            MAX-ACCESS read-only
            STATUS current
            DESCRIPTION
                "Input Packet Octet."
            ::= { hwBrasSbcIdoStatSignalPacketEntry 3 }

        hwBrasSbcIdoStatSignalPacketOutNumber OBJECT-TYPE
            SYNTAX Counter64
            MAX-ACCESS read-only
            STATUS current
            DESCRIPTION
                "Output Packet Number."
            ::= { hwBrasSbcIdoStatSignalPacketEntry 4 }

        hwBrasSbcIdoStatSignalPacketOutOctet OBJECT-TYPE
            SYNTAX Counter64
            MAX-ACCESS read-only
            STATUS current
            DESCRIPTION
                "Output Packet Octet."
            ::= { hwBrasSbcIdoStatSignalPacketEntry 5 }

        hwBrasSbcIdoStatSignalPacketRowStatus OBJECT-TYPE
            SYNTAX RowStatus
            MAX-ACCESS read-write
            STATUS current
            DESCRIPTION
                "Row Status."
            ::= { hwBrasSbcIdoStatSignalPacketEntry 6 }

        hwBrasSbcH248 OBJECT IDENTIFIER ::= { hwBrasSbcObjects 7 }

        hwBrasSbcH248Leaves OBJECT IDENTIFIER ::= { hwBrasSbcH248 1 }

        hwBrasSbcH248Enable OBJECT-TYPE
            SYNTAX HWBrasEnabledStatus
            MAX-ACCESS read-write
            STATUS current
            DESCRIPTION
                "H.248 Enable Status.
                Default: enabled"
            DEFVAL { enabled }
            ::= { hwBrasSbcH248Leaves 1 }

        hwBrasSbcH248SyslogEnable OBJECT-TYPE
            SYNTAX HWBrasEnabledStatus
            MAX-ACCESS read-write
            STATUS current
            DESCRIPTION
                "H.248 Syslog Enable Status.
                Default: enabled"
            DEFVAL { enabled }
            ::= { hwBrasSbcH248Leaves 2 }

        hwBrasSbcH248CcbTimer OBJECT-TYPE
            SYNTAX Unsigned32 (10..14400)
            UNITS "minutes"
            MAX-ACCESS read-write
            STATUS current
            DESCRIPTION
                "H.248 CCB Aging Time.
                Range: 10-14400
                Default: 30
                Unit: minutes"
            ::= { hwBrasSbcH248Leaves 3 }

        hwBrasSbcH248UserAgeTimer OBJECT-TYPE
            SYNTAX Unsigned32 (0..3600)
            UNITS "seconds"
            MAX-ACCESS read-write
            STATUS current
            DESCRIPTION
                "H.248 Register-User Aging Time.
                Range: 0-3600
                Default: 30
                Unit: seconds"
            ::= { hwBrasSbcH248Leaves 4 }

        hwBrasSbcH248PDHCountLimit OBJECT-TYPE
            SYNTAX Unsigned32 (1..100)
            MAX-ACCESS read-write
            STATUS current
            DESCRIPTION
                "H.248 Dual-homing Failed Register Count Limit.
                Range: 1-100
                Default: 6"
            DEFVAL { 6 }
            ::= { hwBrasSbcH248Leaves 5 }

        hwBrasSbcH248Tables OBJECT IDENTIFIER ::= { hwBrasSbcH248 2 }

        hwBrasSbcH248WellknownPortTable OBJECT-TYPE
            SYNTAX SEQUENCE OF HwBrasSbcH248WellknownPortEntry
            MAX-ACCESS not-accessible
            STATUS current
            DESCRIPTION
                "H.248 Wellknown Port Table.
                obsolete"
            ::= { hwBrasSbcH248Tables 1 }

        hwBrasSbcH248WellknownPortEntry OBJECT-TYPE
            SYNTAX HwBrasSbcH248WellknownPortEntry
            MAX-ACCESS not-accessible
            STATUS current
            DESCRIPTION
                "H.248 Wellknown Port Table Entry."
            INDEX { hwBrasSbcH248WellknownPortIndex, hwBrasSbcH248WellknownPortProtocol, hwBrasSbcH248WellknownPortAddr }
            ::= { hwBrasSbcH248WellknownPortTable 1 }

        HwBrasSbcH248WellknownPortEntry ::=
            SEQUENCE {
                hwBrasSbcH248WellknownPortIndex
                    INTEGER,
                hwBrasSbcH248WellknownPortProtocol
                    INTEGER,
                hwBrasSbcH248WellknownPortAddr
                    IpAddress,
                hwBrasSbcH248WellknownPortPort
                    Unsigned32,
                hwBrasSbcH248WellknownPortRowStatus
                    RowStatus
             }

        hwBrasSbcH248WellknownPortIndex OBJECT-TYPE
            SYNTAX INTEGER
                {
                clientaddr(1),
                softxaddr(2)
                }
            MAX-ACCESS not-accessible
            STATUS current
            DESCRIPTION
                "H.248 Wellknown Port Index.
                1: Client Side Ip Address
                2: Softx IP Address
                Default: NA"
            ::= { hwBrasSbcH248WellknownPortEntry 1 }

        hwBrasSbcH248WellknownPortProtocol OBJECT-TYPE
            SYNTAX INTEGER { h248(1) }
            MAX-ACCESS not-accessible
            STATUS current
            DESCRIPTION
                "H.248 Wellknown Port Protocol.
                1: h248
                Default: NA"
            ::= { hwBrasSbcH248WellknownPortEntry 2 }

        hwBrasSbcH248WellknownPortAddr OBJECT-TYPE
            SYNTAX IpAddress
            MAX-ACCESS not-accessible
            STATUS current
            DESCRIPTION
                "H.248 Wellknown Port IP Address."
            ::= { hwBrasSbcH248WellknownPortEntry 3 }

        hwBrasSbcH248WellknownPortPort OBJECT-TYPE
            SYNTAX Unsigned32 (1..65535)
            MAX-ACCESS read-create
            STATUS current
            DESCRIPTION
                "H.248 Wellknown Port Port."
            ::= { hwBrasSbcH248WellknownPortEntry 4 }

        hwBrasSbcH248WellknownPortRowStatus OBJECT-TYPE
            SYNTAX RowStatus
            MAX-ACCESS read-create
            STATUS current
            DESCRIPTION
                "H.248 Wellknown Port Row Status."
            ::= { hwBrasSbcH248WellknownPortEntry 5 }

        hwBrasSbcH248SignalMapTable OBJECT-TYPE
            SYNTAX SEQUENCE OF HwBrasSbcH248SignalMapEntry
            MAX-ACCESS not-accessible
            STATUS current
            DESCRIPTION
                "H.248 Signal Map Table.
                obsolete"
            ::= { hwBrasSbcH248Tables 2 }

        hwBrasSbcH248SignalMapEntry OBJECT-TYPE
            SYNTAX HwBrasSbcH248SignalMapEntry
            MAX-ACCESS not-accessible
            STATUS current
            DESCRIPTION
                "H.248 Signal Map Table Entry."
            INDEX { hwBrasSbcH248SignalMapAddr, hwBrasSbcH248SignalMapProtocol }
            ::= { hwBrasSbcH248SignalMapTable 1 }

        HwBrasSbcH248SignalMapEntry ::=
            SEQUENCE {
                hwBrasSbcH248SignalMapAddr
                    IpAddress,
                hwBrasSbcH248SignalMapProtocol
                    INTEGER,
                hwBrasSbcH248SignalMapNumber
                    Unsigned32,
                hwBrasSbcH248SignalMapAddrType
                    INTEGER
             }

        hwBrasSbcH248SignalMapAddr OBJECT-TYPE
            SYNTAX IpAddress
            MAX-ACCESS not-accessible
            STATUS current
            DESCRIPTION
                "H.248 Signal Map Table IP Address."
            ::= { hwBrasSbcH248SignalMapEntry 1 }

        hwBrasSbcH248SignalMapProtocol OBJECT-TYPE
            SYNTAX INTEGER { h248(1) }
            MAX-ACCESS not-accessible
            STATUS current
            DESCRIPTION
                "H.248 Signal Map Table Protocol."
            ::= { hwBrasSbcH248SignalMapEntry 2 }

        hwBrasSbcH248SignalMapNumber OBJECT-TYPE
            SYNTAX Unsigned32
            MAX-ACCESS read-only
            STATUS current
            DESCRIPTION
                "H.248 Signal Map Table Map Number."
            ::= { hwBrasSbcH248SignalMapEntry 3 }

        hwBrasSbcH248SignalMapAddrType OBJECT-TYPE
            SYNTAX INTEGER
                {
                client(1),
                server(2)
                }
            MAX-ACCESS read-only
            STATUS current
            DESCRIPTION
                "H.248 Signal Map Table Map Type."
            ::= { hwBrasSbcH248SignalMapEntry 4 }

        hwBrasSbcH248MediaMapTable OBJECT-TYPE
            SYNTAX SEQUENCE OF HwBrasSbcH248MediaMapEntry
            MAX-ACCESS not-accessible
            STATUS current
            DESCRIPTION
                "H.248 Media Map Table.
                obsolete"
            ::= { hwBrasSbcH248Tables 3 }

        hwBrasSbcH248MediaMapEntry OBJECT-TYPE
            SYNTAX HwBrasSbcH248MediaMapEntry
            MAX-ACCESS not-accessible
            STATUS current
            DESCRIPTION
                "H.248 Media Map Table Entry."
            INDEX { hwBrasSbcH248MediaMapAddr, hwBrasSbcH248MediaMapProtocol }
            ::= { hwBrasSbcH248MediaMapTable 1 }

        HwBrasSbcH248MediaMapEntry ::=
            SEQUENCE {
                hwBrasSbcH248MediaMapAddr
                    IpAddress,
                hwBrasSbcH248MediaMapProtocol
                    INTEGER,
                hwBrasSbcH248MediaMapNumber
                    Unsigned32
             }

        hwBrasSbcH248MediaMapAddr OBJECT-TYPE
            SYNTAX IpAddress
            MAX-ACCESS not-accessible
            STATUS current
            DESCRIPTION
                "H.248 Media Map Table IP Address."
            ::= { hwBrasSbcH248MediaMapEntry 1 }

        hwBrasSbcH248MediaMapProtocol OBJECT-TYPE
            SYNTAX INTEGER { h248(1) }
            MAX-ACCESS not-accessible
            STATUS current
            DESCRIPTION
                "H.248 Media Map Table Protocol."
            ::= { hwBrasSbcH248MediaMapEntry 2 }

        hwBrasSbcH248MediaMapNumber OBJECT-TYPE
            SYNTAX Unsigned32
            MAX-ACCESS read-only
            STATUS current
            DESCRIPTION
                "H.248 Media Map Table Media Map Number."
            ::= { hwBrasSbcH248MediaMapEntry 3 }

        hwBrasSbcH248IntercomMapSignalTable OBJECT-TYPE
            SYNTAX SEQUENCE OF HwBrasSbcH248IntercomMapSignalEntry
            MAX-ACCESS not-accessible
            STATUS current
            DESCRIPTION
                "H.248 Intercom Map Signal Table.
                obsolete"
            ::= { hwBrasSbcH248Tables 4 }

        hwBrasSbcH248IntercomMapSignalEntry OBJECT-TYPE
            SYNTAX HwBrasSbcH248IntercomMapSignalEntry
            MAX-ACCESS not-accessible
            STATUS current
            DESCRIPTION
                "H.248 Intercom Map Signal Table Entry."
            INDEX { hwBrasSbcH248IntercomMapSignalAddr, hwBrasSbcH248IntercomMapSignalProtocol }
            ::= { hwBrasSbcH248IntercomMapSignalTable 1 }

        HwBrasSbcH248IntercomMapSignalEntry ::=
            SEQUENCE {
                hwBrasSbcH248IntercomMapSignalAddr
                    IpAddress,
                hwBrasSbcH248IntercomMapSignalProtocol
                    INTEGER,
                hwBrasSbcH248IntercomMapSignalNumber
                    Unsigned32
             }

        hwBrasSbcH248IntercomMapSignalAddr OBJECT-TYPE
            SYNTAX IpAddress
            MAX-ACCESS not-accessible
            STATUS current
            DESCRIPTION
                "Intercom Address Map H.248 Signal Map Table IP Address."
            ::= { hwBrasSbcH248IntercomMapSignalEntry 1 }

        hwBrasSbcH248IntercomMapSignalProtocol OBJECT-TYPE
            SYNTAX INTEGER { h248(1) }
            MAX-ACCESS not-accessible
            STATUS current
            DESCRIPTION
                "Intercom Address Map H.248 Signal Map Table Protocol."
            ::= { hwBrasSbcH248IntercomMapSignalEntry 2 }

        hwBrasSbcH248IntercomMapSignalNumber OBJECT-TYPE
            SYNTAX Unsigned32
            MAX-ACCESS read-only
            STATUS current
            DESCRIPTION
                "Intercom Address Map H.248 Signal Map Table Map Number."
            ::= { hwBrasSbcH248IntercomMapSignalEntry 3 }

        hwBrasSbcH248IntercomMapMediaTable OBJECT-TYPE
            SYNTAX SEQUENCE OF HwBrasSbcH248IntercomMapMediaEntry
            MAX-ACCESS not-accessible
            STATUS current
            DESCRIPTION
                "H.248 Intercom Map Media Table.
                obsolete"
            ::= { hwBrasSbcH248Tables 5 }

        hwBrasSbcH248IntercomMapMediaEntry OBJECT-TYPE
            SYNTAX HwBrasSbcH248IntercomMapMediaEntry
            MAX-ACCESS not-accessible
            STATUS current
            DESCRIPTION
                "H.248 Intercom Map Media Table Entry."
            INDEX { hwBrasSbcH248IntercomMapMediaAddr, hwBrasSbcH248IntercomMapMediaProtocol }
            ::= { hwBrasSbcH248IntercomMapMediaTable 1 }

        HwBrasSbcH248IntercomMapMediaEntry ::=
            SEQUENCE {
                hwBrasSbcH248IntercomMapMediaAddr
                    IpAddress,
                hwBrasSbcH248IntercomMapMediaProtocol
                    INTEGER,
                hwBrasSbcH248IntercomMapMediaNumber
                    Unsigned32
             }

        hwBrasSbcH248IntercomMapMediaAddr OBJECT-TYPE
            SYNTAX IpAddress
            MAX-ACCESS not-accessible
            STATUS current
            DESCRIPTION
                "Intercom Address Map H.248 Media Map Table IP Address."
            ::= { hwBrasSbcH248IntercomMapMediaEntry 1 }

        hwBrasSbcH248IntercomMapMediaProtocol OBJECT-TYPE
            SYNTAX INTEGER { h248(1) }
            MAX-ACCESS not-accessible
            STATUS current
            DESCRIPTION
                "Intercom Address Map H.248 Media Map Table Protocol."
            ::= { hwBrasSbcH248IntercomMapMediaEntry 2 }

        hwBrasSbcH248IntercomMapMediaNumber OBJECT-TYPE
            SYNTAX Unsigned32
            MAX-ACCESS read-only
            STATUS current
            DESCRIPTION
                "Intercom Address Map H.248 Media Map Table Map Number."
            ::= { hwBrasSbcH248IntercomMapMediaEntry 3 }

        hwBrasSbcH248StatSignalPacketTable OBJECT-TYPE
            SYNTAX SEQUENCE OF HwBrasSbcH248StatSignalPacketEntry
            MAX-ACCESS not-accessible
            STATUS current
            DESCRIPTION
                "H.248 Statistic of Signaling Packet Table."
            ::= { hwBrasSbcH248Tables 6 }

        hwBrasSbcH248StatSignalPacketEntry OBJECT-TYPE
            SYNTAX HwBrasSbcH248StatSignalPacketEntry
            MAX-ACCESS not-accessible
            STATUS current
            DESCRIPTION
                "H.248 Statistic of Signaling Packet Table Entry."
            INDEX { hwBrasSbcH248StatSignalPacketIndex }
            ::= { hwBrasSbcH248StatSignalPacketTable 1 }

        HwBrasSbcH248StatSignalPacketEntry ::=
            SEQUENCE {
                hwBrasSbcH248StatSignalPacketIndex
                    INTEGER,
                hwBrasSbcH248StatSignalPacketInNumber
                    Counter64,
                hwBrasSbcH248StatSignalPacketInOctet
                    Counter64,
                hwBrasSbcH248StatSignalPacketOutNumber
                    Counter64,
                hwBrasSbcH248StatSignalPacketOutOctet
                    Counter64,
                hwBrasSbcH248StatSignalPacketRowStatus
                    RowStatus
             }

        hwBrasSbcH248StatSignalPacketIndex OBJECT-TYPE
            SYNTAX INTEGER { h248(1) }
            MAX-ACCESS not-accessible
            STATUS current
            DESCRIPTION
                "Protocol."
            ::= { hwBrasSbcH248StatSignalPacketEntry 1 }

        hwBrasSbcH248StatSignalPacketInNumber OBJECT-TYPE
            SYNTAX Counter64
            MAX-ACCESS read-only
            STATUS current
            DESCRIPTION
                "Input Packet Number."
            ::= { hwBrasSbcH248StatSignalPacketEntry 2 }

        hwBrasSbcH248StatSignalPacketInOctet OBJECT-TYPE
            SYNTAX Counter64
            MAX-ACCESS read-only
            STATUS current
            DESCRIPTION
                "Input Packet Octet."
            ::= { hwBrasSbcH248StatSignalPacketEntry 3 }

        hwBrasSbcH248StatSignalPacketOutNumber OBJECT-TYPE
            SYNTAX Counter64
            MAX-ACCESS read-only
            STATUS current
            DESCRIPTION
                "Output Packet Number."
            ::= { hwBrasSbcH248StatSignalPacketEntry 4 }

        hwBrasSbcH248StatSignalPacketOutOctet OBJECT-TYPE
            SYNTAX Counter64
            MAX-ACCESS read-only
            STATUS current
            DESCRIPTION
                "Output Packet Octet."
            ::= { hwBrasSbcH248StatSignalPacketEntry 5 }

        hwBrasSbcH248StatSignalPacketRowStatus OBJECT-TYPE
            SYNTAX RowStatus
            MAX-ACCESS read-write
            STATUS current
            DESCRIPTION
                "Row Status."
            ::= { hwBrasSbcH248StatSignalPacketEntry 6 }

        hwBrasSbcUpath OBJECT IDENTIFIER ::= { hwBrasSbcObjects 8 }

        hwBrasSbcUpathLeaves OBJECT IDENTIFIER ::= { hwBrasSbcUpath 2 }

        hwBrasSbcUpathEnable OBJECT-TYPE
            SYNTAX HWBrasEnabledStatus
            MAX-ACCESS read-write
            STATUS current
            DESCRIPTION
                "U-Path Enable Status.
                Default: enabled"
            DEFVAL { enabled }
            ::= { hwBrasSbcUpathLeaves 1 }

        hwBrasSbcUpathSyslogEnable OBJECT-TYPE
            SYNTAX HWBrasEnabledStatus
            MAX-ACCESS read-write
            STATUS current
            DESCRIPTION
                "U-Path Syslog Enable Status.
                Default: enabled"
            DEFVAL { enabled }
            ::= { hwBrasSbcUpathLeaves 2 }

        hwBrasSbcUpathCallsessionTimer OBJECT-TYPE
            SYNTAX Unsigned32 (1..24)
            UNITS "hours"
            MAX-ACCESS read-write
            STATUS current
            DESCRIPTION
                "U-Path Callsession Aging Time.
                Range: 1-24
                Default: 12
                Unit: hours"
            DEFVAL { 12 }
            ::= { hwBrasSbcUpathLeaves 3 }

        hwBrasSbcUpathHeartbeatTimer OBJECT-TYPE
            SYNTAX Unsigned32 (10..30)
            UNITS "seconds"
            MAX-ACCESS read-write
            STATUS current
            DESCRIPTION
                "U-Path Heart Beat Aging Time.
                Range: 10-30
                Default: 10
                Unit: seconds"
            DEFVAL { 10 }
            ::= { hwBrasSbcUpathLeaves 4 }

        hwBrasSbcUpathTables OBJECT IDENTIFIER ::= { hwBrasSbcUpath 3 }

        hwBrasSbcUpathWellknownPortTable OBJECT-TYPE
            SYNTAX SEQUENCE OF HwBrasSbcUpathWellknownPortEntry
            MAX-ACCESS not-accessible
            STATUS current
            DESCRIPTION
                "U-Path Wellknown Port Table.
                obsolete"
            ::= { hwBrasSbcUpathTables 1 }

        hwBrasSbcUpathWellknownPortEntry OBJECT-TYPE
            SYNTAX HwBrasSbcUpathWellknownPortEntry
            MAX-ACCESS not-accessible
            STATUS current
            DESCRIPTION
                "U-Path Wellknown Port Table Entry."
            INDEX { hwBrasSbcUpathWellknownPortIndex, hwBrasSbcUpathWellknownPortProtocol, hwBrasSbcUpathWellknownPortAddr }
            ::= { hwBrasSbcUpathWellknownPortTable 1 }

        HwBrasSbcUpathWellknownPortEntry ::=
            SEQUENCE {
                hwBrasSbcUpathWellknownPortIndex
                    INTEGER,
                hwBrasSbcUpathWellknownPortProtocol
                    INTEGER,
                hwBrasSbcUpathWellknownPortAddr
                    IpAddress,
                hwBrasSbcUpathWellknownPortPort
                    Unsigned32,
                hwBrasSbcUpathWellknownPortRowStatus
                    RowStatus
             }

        hwBrasSbcUpathWellknownPortIndex OBJECT-TYPE
            SYNTAX INTEGER
                {
                clientaddr(1),
                softxaddr(2)
                }
            MAX-ACCESS not-accessible
            STATUS current
            DESCRIPTION
                "U-Path Wellknown Port Index.
                1: Client Side Ip Address
                2: Softx IP Address
                Default: NA"
            ::= { hwBrasSbcUpathWellknownPortEntry 1 }

        hwBrasSbcUpathWellknownPortProtocol OBJECT-TYPE
            SYNTAX INTEGER { upath(1) }
            MAX-ACCESS not-accessible
            STATUS current
            DESCRIPTION
                "U-Path Wellknown Port Protocol.
                1: U-Path
                Default: NA"
            ::= { hwBrasSbcUpathWellknownPortEntry 2 }

        hwBrasSbcUpathWellknownPortAddr OBJECT-TYPE
            SYNTAX IpAddress
            MAX-ACCESS not-accessible
            STATUS current
            DESCRIPTION
                "U-Path Wellknown Port IP Address."
            ::= { hwBrasSbcUpathWellknownPortEntry 3 }

        hwBrasSbcUpathWellknownPortPort OBJECT-TYPE
            SYNTAX Unsigned32 (1..65535)
            MAX-ACCESS read-create
            STATUS current
            DESCRIPTION
                "U-Path Wellknown Port Port."
            ::= { hwBrasSbcUpathWellknownPortEntry 4 }

        hwBrasSbcUpathWellknownPortRowStatus OBJECT-TYPE
            SYNTAX RowStatus
            MAX-ACCESS read-create
            STATUS current
            DESCRIPTION
                "U-Path Wellknown Port Row Status."
            ::= { hwBrasSbcUpathWellknownPortEntry 5 }

        hwBrasSbcUpathSignalMapTable OBJECT-TYPE
            SYNTAX SEQUENCE OF HwBrasSbcUpathSignalMapEntry
            MAX-ACCESS not-accessible
            STATUS current
            DESCRIPTION
                "U-Path Signal Map Table.
                obsolete"
            ::= { hwBrasSbcUpathTables 2 }

        hwBrasSbcUpathSignalMapEntry OBJECT-TYPE
            SYNTAX HwBrasSbcUpathSignalMapEntry
            MAX-ACCESS not-accessible
            STATUS current
            DESCRIPTION
                "U-Path Signal Map Table Entry."
            INDEX { hwBrasSbcUpathSignalMapAddr, hwBrasSbcUpathSignalMapProtocol }
            ::= { hwBrasSbcUpathSignalMapTable 1 }

        HwBrasSbcUpathSignalMapEntry ::=
            SEQUENCE {
                hwBrasSbcUpathSignalMapAddr
                    IpAddress,
                hwBrasSbcUpathSignalMapProtocol
                    INTEGER,
                hwBrasSbcUpathSignalMapNumber
                    Unsigned32,
                hwBrasSbcUpathSignalMapAddrType
                    INTEGER
             }

        hwBrasSbcUpathSignalMapAddr OBJECT-TYPE
            SYNTAX IpAddress
            MAX-ACCESS not-accessible
            STATUS current
            DESCRIPTION
                "U-Path Signal Map Table IP Address."
            ::= { hwBrasSbcUpathSignalMapEntry 1 }

        hwBrasSbcUpathSignalMapProtocol OBJECT-TYPE
            SYNTAX INTEGER { upath(1) }
            MAX-ACCESS not-accessible
            STATUS current
            DESCRIPTION
                "U-Path Signal Map Table Protocol."
            ::= { hwBrasSbcUpathSignalMapEntry 2 }

        hwBrasSbcUpathSignalMapNumber OBJECT-TYPE
            SYNTAX Unsigned32
            MAX-ACCESS read-only
            STATUS current
            DESCRIPTION
                "U-Path Signal Map Table Map Number."
            ::= { hwBrasSbcUpathSignalMapEntry 3 }

        hwBrasSbcUpathSignalMapAddrType OBJECT-TYPE
            SYNTAX INTEGER
                {
                client(1),
                server(2)
                }
            MAX-ACCESS read-only
            STATUS current
            DESCRIPTION
                "U-Path Signal Map Table Server Map Number."
            ::= { hwBrasSbcUpathSignalMapEntry 4 }

        hwBrasSbcUpathMediaMapTable OBJECT-TYPE
            SYNTAX SEQUENCE OF HwBrasSbcUpathMediaMapEntry
            MAX-ACCESS not-accessible
            STATUS current
            DESCRIPTION
                "U-Path Media Map Table.
                obsolete"
            ::= { hwBrasSbcUpathTables 3 }

        hwBrasSbcUpathMediaMapEntry OBJECT-TYPE
            SYNTAX HwBrasSbcUpathMediaMapEntry
            MAX-ACCESS not-accessible
            STATUS current
            DESCRIPTION
                "U-Path Media Map Table Entry."
            INDEX { hwBrasSbcUpathMediaMapAddr, hwBrasSbcUpathMediaMapProtocol }
            ::= { hwBrasSbcUpathMediaMapTable 1 }

        HwBrasSbcUpathMediaMapEntry ::=
            SEQUENCE {
                hwBrasSbcUpathMediaMapAddr
                    IpAddress,
                hwBrasSbcUpathMediaMapProtocol
                    INTEGER,
                hwBrasSbcUpathMediaMapNumber
                    Unsigned32
             }

        hwBrasSbcUpathMediaMapAddr OBJECT-TYPE
            SYNTAX IpAddress
            MAX-ACCESS not-accessible
            STATUS current
            DESCRIPTION
                "U-Path Media Map Table IP Address."
            ::= { hwBrasSbcUpathMediaMapEntry 1 }

        hwBrasSbcUpathMediaMapProtocol OBJECT-TYPE
            SYNTAX INTEGER { upath(1) }
            MAX-ACCESS not-accessible
            STATUS current
            DESCRIPTION
                "U-Path Media Map Table Protocol."
            ::= { hwBrasSbcUpathMediaMapEntry 2 }

        hwBrasSbcUpathMediaMapNumber OBJECT-TYPE
            SYNTAX Unsigned32
            MAX-ACCESS read-only
            STATUS current
            DESCRIPTION
                "U-Path Media Map Table Media Map Number."
            ::= { hwBrasSbcUpathMediaMapEntry 3 }

        hwBrasSbcUpathIntercomMapSignalTable OBJECT-TYPE
            SYNTAX SEQUENCE OF HwBrasSbcUpathIntercomMapSignalEntry
            MAX-ACCESS not-accessible
            STATUS current
            DESCRIPTION
                "U-Path Intercom Map Signal Table.
                obsolete"
            ::= { hwBrasSbcUpathTables 4 }

        hwBrasSbcUpathIntercomMapSignalEntry OBJECT-TYPE
            SYNTAX HwBrasSbcUpathIntercomMapSignalEntry
            MAX-ACCESS not-accessible
            STATUS current
            DESCRIPTION
                "U-Path Intercom Map Signal Table Entry."
            INDEX { hwBrasSbcUpathIntercomMapSignalAddr, hwBrasSbcUpathIntercomMapSignalProtocol }
            ::= { hwBrasSbcUpathIntercomMapSignalTable 1 }

        HwBrasSbcUpathIntercomMapSignalEntry ::=
            SEQUENCE {
                hwBrasSbcUpathIntercomMapSignalAddr
                    IpAddress,
                hwBrasSbcUpathIntercomMapSignalProtocol
                    INTEGER,
                hwBrasSbcUpathIntercomMapSignalNumber
                    Unsigned32
             }

        hwBrasSbcUpathIntercomMapSignalAddr OBJECT-TYPE
            SYNTAX IpAddress
            MAX-ACCESS not-accessible
            STATUS current
            DESCRIPTION
                "Intercom Address Map U-Path Signal Map Table IP Address."
            ::= { hwBrasSbcUpathIntercomMapSignalEntry 1 }

        hwBrasSbcUpathIntercomMapSignalProtocol OBJECT-TYPE
            SYNTAX INTEGER { upath(1) }
            MAX-ACCESS not-accessible
            STATUS current
            DESCRIPTION
                "Intercom Address Map U-Path Signal Map Table Protocol."
            ::= { hwBrasSbcUpathIntercomMapSignalEntry 2 }

        hwBrasSbcUpathIntercomMapSignalNumber OBJECT-TYPE
            SYNTAX Unsigned32
            MAX-ACCESS read-only
            STATUS current
            DESCRIPTION
                "Intercom Address Map U-Path Signal Map Table Map Number."
            ::= { hwBrasSbcUpathIntercomMapSignalEntry 3 }

        hwBrasSbcUpathIntercomMapMediaTable OBJECT-TYPE
            SYNTAX SEQUENCE OF HwBrasSbcUpathIntercomMapMediaEntry
            MAX-ACCESS not-accessible
            STATUS current
            DESCRIPTION
                "U-Path Intercom Map Media Table.
                obsolete"
            ::= { hwBrasSbcUpathTables 5 }

        hwBrasSbcUpathIntercomMapMediaEntry OBJECT-TYPE
            SYNTAX HwBrasSbcUpathIntercomMapMediaEntry
            MAX-ACCESS not-accessible
            STATUS current
            DESCRIPTION
                "U-Path Intercom Map Media Table Entry."
            INDEX { hwBrasSbcUpathIntercomMapMediaAddr, hwBrasSbcUpathIntercomMapMediaProtocol }
            ::= { hwBrasSbcUpathIntercomMapMediaTable 1 }

        HwBrasSbcUpathIntercomMapMediaEntry ::=
            SEQUENCE {
                hwBrasSbcUpathIntercomMapMediaAddr
                    IpAddress,
                hwBrasSbcUpathIntercomMapMediaProtocol
                    INTEGER,
                hwBrasSbcUpathIntercomMapMediaNumber
                    Unsigned32
             }

        hwBrasSbcUpathIntercomMapMediaAddr OBJECT-TYPE
            SYNTAX IpAddress
            MAX-ACCESS not-accessible
            STATUS current
            DESCRIPTION
                "Intercom Address Map U-Path Media Map Table IP Address."
            ::= { hwBrasSbcUpathIntercomMapMediaEntry 1 }

        hwBrasSbcUpathIntercomMapMediaProtocol OBJECT-TYPE
            SYNTAX INTEGER { upath(1) }
            MAX-ACCESS not-accessible
            STATUS current
            DESCRIPTION
                "Intercom Address Map U-Path Media Map Table Protocol."
            ::= { hwBrasSbcUpathIntercomMapMediaEntry 2 }

        hwBrasSbcUpathIntercomMapMediaNumber OBJECT-TYPE
            SYNTAX Unsigned32
            MAX-ACCESS read-only
            STATUS current
            DESCRIPTION
                "Intercom Address Map U-Path Media Map Table Map Number."
            ::= { hwBrasSbcUpathIntercomMapMediaEntry 3 }

        hwBrasSbcUpathStatSignalPacketTable OBJECT-TYPE
            SYNTAX SEQUENCE OF HwBrasSbcUpathStatSignalPacketEntry
            MAX-ACCESS not-accessible
            STATUS current
            DESCRIPTION
                "U-Path Statistic of Signaling Packet Table."
            ::= { hwBrasSbcUpathTables 6 }

        hwBrasSbcUpathStatSignalPacketEntry OBJECT-TYPE
            SYNTAX HwBrasSbcUpathStatSignalPacketEntry
            MAX-ACCESS not-accessible
            STATUS current
            DESCRIPTION
                "U-Path Statistic of Signaling Packet Table Entry."
            INDEX { hwBrasSbcUpathStatSignalPacketIndex }
            ::= { hwBrasSbcUpathStatSignalPacketTable 1 }

        HwBrasSbcUpathStatSignalPacketEntry ::=
            SEQUENCE {
                hwBrasSbcUpathStatSignalPacketIndex
                    INTEGER,
                hwBrasSbcUpathStatSignalPacketInNumber
                    Counter64,
                hwBrasSbcUpathStatSignalPacketInOctet
                    Counter64,
                hwBrasSbcUpathStatSignalPacketOutNumber
                    Counter64,
                hwBrasSbcUpathStatSignalPacketOutOctet
                    Counter64,
                hwBrasSbcUpathStatSignalPacketRowStatus
                    RowStatus
             }

        hwBrasSbcUpathStatSignalPacketIndex OBJECT-TYPE
            SYNTAX INTEGER { upath(1) }
            MAX-ACCESS not-accessible
            STATUS current
            DESCRIPTION
                "Protocol."
            ::= { hwBrasSbcUpathStatSignalPacketEntry 1 }

        hwBrasSbcUpathStatSignalPacketInNumber OBJECT-TYPE
            SYNTAX Counter64
            MAX-ACCESS read-only
            STATUS current
            DESCRIPTION
                "Input Packet Number."
            ::= { hwBrasSbcUpathStatSignalPacketEntry 2 }

        hwBrasSbcUpathStatSignalPacketInOctet OBJECT-TYPE
            SYNTAX Counter64
            MAX-ACCESS read-only
            STATUS current
            DESCRIPTION
                "Input Packet Octet."
            ::= { hwBrasSbcUpathStatSignalPacketEntry 3 }

        hwBrasSbcUpathStatSignalPacketOutNumber OBJECT-TYPE
            SYNTAX Counter64
            MAX-ACCESS read-only
            STATUS current
            DESCRIPTION
                "Output Packet Number."
            ::= { hwBrasSbcUpathStatSignalPacketEntry 4 }

        hwBrasSbcUpathStatSignalPacketOutOctet OBJECT-TYPE
            SYNTAX Counter64
            MAX-ACCESS read-only
            STATUS current
            DESCRIPTION
                "Output Packet Octet."
            ::= { hwBrasSbcUpathStatSignalPacketEntry 5 }

        hwBrasSbcUpathStatSignalPacketRowStatus OBJECT-TYPE
            SYNTAX RowStatus
            MAX-ACCESS read-write
            STATUS current
            DESCRIPTION
                "Row Status."
            ::= { hwBrasSbcUpathStatSignalPacketEntry 6 }

        hwBrasSbcOm OBJECT IDENTIFIER ::= { hwBrasSbcObjects 21 }

        hwBrasSbcOmLeaves OBJECT IDENTIFIER ::= { hwBrasSbcOm 1 }

        hwBrasSbcRestartEnable OBJECT-TYPE
            SYNTAX HWBrasEnabledStatus
            MAX-ACCESS read-write
            STATUS current
            DESCRIPTION
                "The switch for allow Sbc restart.
                Attention: enabled for permit restart device from the nexe oid!"
            DEFVAL { disabled }
            ::= { hwBrasSbcOmLeaves 1 }

        hwBrasSbcRestartButton OBJECT-TYPE
            SYNTAX INTEGER
                {
                notready(1),
                restart(101)
                }
            MAX-ACCESS read-write
            STATUS current
            DESCRIPTION
                "The button for restart Sbc.
                Attention:set 101 for restart device!"
            ::= { hwBrasSbcOmLeaves 2 }

        hwBrasSbcPatchLoadStatus OBJECT-TYPE
            SYNTAX INTEGER
                {
                unknown(1),
                loaded(2)
                }
            MAX-ACCESS read-write
            STATUS current
            DESCRIPTION
                "The botton for load Sbc's patch.
                Operation of 'write' will be forbided if there isn't path file in flash."
            DEFVAL { unknown }
            ::= { hwBrasSbcOmLeaves 3 }

        hwBrasSbcLocalizationStatus OBJECT-TYPE
            SYNTAX HWBrasEnabledStatus
            MAX-ACCESS read-write
            STATUS current
            DESCRIPTION
                "Localization enable status
                default: disabled

                notes:can't support modified operation nowdays."
            DEFVAL { disabled }
            ::= { hwBrasSbcOmLeaves 4 }

        hwBrasSbcOmTables OBJECT IDENTIFIER ::= { hwBrasSbcOm 2 }

        hwBrasSbcTrapBind OBJECT IDENTIFIER ::= { hwBrasSbcModule 2 }

        hwBrasSbcTrapBindLeaves OBJECT IDENTIFIER ::= { hwBrasSbcTrapBind 1 }

        hwBrasSbcTrapBindTables OBJECT IDENTIFIER ::= { hwBrasSbcTrapBind 2 }

        hwBrasSbcTrapBindTable OBJECT-TYPE
            SYNTAX SEQUENCE OF HwBrasSbcTrapBindEntry
            MAX-ACCESS not-accessible
            STATUS current
            DESCRIPTION
                "Sbc Bind Parameter Table."
            ::= { hwBrasSbcTrapBindTables 1 }

        hwBrasSbcTrapBindEntry OBJECT-TYPE
            SYNTAX HwBrasSbcTrapBindEntry
            MAX-ACCESS not-accessible
            STATUS current
            DESCRIPTION
                "Sbc Bind Parameter Table Entry."
            INDEX { hwBrasSbcTrapBindIndex }
            ::= { hwBrasSbcTrapBindTable 1 }

        HwBrasSbcTrapBindEntry ::=
            SEQUENCE {
                hwBrasSbcTrapBindIndex
                    INTEGER,
                hwBrasSbcTrapBindID
                    Unsigned32,
                hwBrasSbcTrapBindTime
                    DateAndTime,
                hwBrasSbcTrapBindFluID
                    Unsigned32,
                hwBrasSbcTrapBindReason
                    Unsigned32,
                hwBrasSbcTrapBindType
                    INTEGER
             }

        hwBrasSbcTrapBindIndex OBJECT-TYPE
            SYNTAX INTEGER { trapbind(1) }
            MAX-ACCESS not-accessible
            STATUS current
            DESCRIPTION
                "Index."
            ::= { hwBrasSbcTrapBindEntry 1 }

        hwBrasSbcTrapBindID OBJECT-TYPE
            SYNTAX Unsigned32 (100..299)
            MAX-ACCESS accessible-for-notify
            STATUS current
            DESCRIPTION
                "Trap Bind ID"
            ::= { hwBrasSbcTrapBindEntry 2 }

        hwBrasSbcTrapBindTime OBJECT-TYPE
            SYNTAX DateAndTime
            MAX-ACCESS accessible-for-notify
            STATUS current
            DESCRIPTION
                "Trap Send Time"
            ::= { hwBrasSbcTrapBindEntry 3 }

        hwBrasSbcTrapBindFluID OBJECT-TYPE
            SYNTAX Unsigned32
            MAX-ACCESS accessible-for-notify
            STATUS current
            DESCRIPTION
                "Trap Flu ID"
            ::= { hwBrasSbcTrapBindEntry 4 }

        hwBrasSbcTrapBindReason OBJECT-TYPE
            SYNTAX Unsigned32 (100..299)
            MAX-ACCESS accessible-for-notify
            STATUS current
            DESCRIPTION
                "Trap Reason"
            ::= { hwBrasSbcTrapBindEntry 5 }

        hwBrasSbcTrapBindType OBJECT-TYPE
            SYNTAX INTEGER
                {
                notify(0),
                alarm(1),
                resume(2),
                sync(3)
                }
            MAX-ACCESS accessible-for-notify
            STATUS current
            DESCRIPTION
                "Trap Type"
            ::= { hwBrasSbcTrapBindEntry 6 }

        hwBrasSbcTrapInfoTable OBJECT-TYPE
            SYNTAX SEQUENCE OF HwBrasSbcTrapInfoEntry
            MAX-ACCESS not-accessible
            STATUS current
            DESCRIPTION
                "Sbc Trap Information."
            ::= { hwBrasSbcTrapBindTables 2 }

        hwBrasSbcTrapInfoEntry OBJECT-TYPE
            SYNTAX HwBrasSbcTrapInfoEntry
            MAX-ACCESS not-accessible
            STATUS current
            DESCRIPTION
                "Sbc Trap Information Entry."
            INDEX { hwBrasSbcTrapInfoIndex }
            ::= { hwBrasSbcTrapInfoTable 1 }

        HwBrasSbcTrapInfoEntry ::=
            SEQUENCE {
                hwBrasSbcTrapInfoIndex
                    INTEGER,
                hwBrasSbcTrapInfoCpu
                    Unsigned32,
                hwBrasSbcTrapInfoHrp
                    INTEGER,
                hwBrasSbcTrapInfoSignalingFlood
                    Unsigned32,
                hwBrasSbcTrapInfoCac
                    Unsigned32,
                hwBrasSbcTrapInfoStatistic
                    INTEGER,
                hwBrasSbcTrapInfoPortStatistic
                    Unsigned32,
                hwBrasSbcTrapInfoOldSSIP
                    IpAddress,
                hwBrasSbcTrapInfoImsConID
                    Unsigned32,
                hwBrasSbcTrapInfoImsCcbID
                    Unsigned32
             }

        hwBrasSbcTrapInfoIndex OBJECT-TYPE
            SYNTAX INTEGER { trap(1) }
            MAX-ACCESS not-accessible
            STATUS current
            DESCRIPTION
                "Index."
            ::= { hwBrasSbcTrapInfoEntry 1 }

        hwBrasSbcTrapInfoCpu OBJECT-TYPE
            SYNTAX Unsigned32 (0..100)
            MAX-ACCESS accessible-for-notify
            STATUS current
            DESCRIPTION
                "Cpu Information."
            ::= { hwBrasSbcTrapInfoEntry 2 }

        hwBrasSbcTrapInfoHrp OBJECT-TYPE
            SYNTAX INTEGER { action(1) }
            MAX-ACCESS accessible-for-notify
            STATUS current
            DESCRIPTION
                "Hrp Information."
            ::= { hwBrasSbcTrapInfoEntry 3 }

        hwBrasSbcTrapInfoSignalingFlood OBJECT-TYPE
            SYNTAX Unsigned32
            MAX-ACCESS accessible-for-notify
            STATUS current
            DESCRIPTION
                "Signaling-flood  Information."
            ::= { hwBrasSbcTrapInfoEntry 4 }

        hwBrasSbcTrapInfoCac OBJECT-TYPE
            SYNTAX Unsigned32
            MAX-ACCESS accessible-for-notify
            STATUS current
            DESCRIPTION
                "Cac Information."
            ::= { hwBrasSbcTrapInfoEntry 5 }

        hwBrasSbcTrapInfoStatistic OBJECT-TYPE
            SYNTAX INTEGER { action(1) }
            MAX-ACCESS accessible-for-notify
            STATUS current
            DESCRIPTION
                "Statistic overflow Information."
            ::= { hwBrasSbcTrapInfoEntry 6 }

        hwBrasSbcTrapInfoPortStatistic OBJECT-TYPE
            SYNTAX Unsigned32
            MAX-ACCESS accessible-for-notify
            STATUS current
            DESCRIPTION
                "Port Statistic Information."
            ::= { hwBrasSbcTrapInfoEntry 7 }

        hwBrasSbcTrapInfoOldSSIP OBJECT-TYPE
            SYNTAX IpAddress
            MAX-ACCESS accessible-for-notify
            STATUS current
            DESCRIPTION
                "Old soft-switch IP address."
            ::= { hwBrasSbcTrapInfoEntry 8 }

        hwBrasSbcTrapInfoImsConID OBJECT-TYPE
            SYNTAX Unsigned32
            MAX-ACCESS accessible-for-notify
            STATUS current
            DESCRIPTION
                "Ims connect id."
            ::= { hwBrasSbcTrapInfoEntry 9 }

        hwBrasSbcTrapInfoImsCcbID OBJECT-TYPE
            SYNTAX Unsigned32
            MAX-ACCESS accessible-for-notify
            STATUS current
            DESCRIPTION
                "Ims ccb id."
            ::= { hwBrasSbcTrapInfoEntry 10 }

        hwBrasSbcComformance OBJECT IDENTIFIER ::= { hwBrasSbcModule 3 }

        hwBrasSbcGroups OBJECT IDENTIFIER ::= { hwBrasSbcComformance 1 }

        hwBrasSbcGroup OBJECT-GROUP
            OBJECTS { hwBrasSbcSignalAddrMapRowStatus, hwBrasSbcPortrangeBegin, hwBrasSbcPortrangeEnd, hwBrasSbcPortrangeRowStatus, hwBrasSbcSipEnable,
                hwBrasSbcSipWellknownPortPort, hwBrasSbcSoftVersion, hwBrasSbcCpuUsage, hwBrasSbcIadmsWellknownPortPort, hwBrasSbcIadmsWellknownPortRowStatus,
                hwBrasSbcH323WellknownPortPort, hwBrasSbcH323WellknownPortRowStatus, hwBrasSbcIdoWellknownPortPort, hwBrasSbcIdoWellknownPortRowStatus, hwBrasSbcH248WellknownPortPort,
                hwBrasSbcH248WellknownPortRowStatus, hwBrasSbcIadmsMibRegRegister, hwBrasSbcIadmsMibRegRowStatus, hwBrasSbcSipWellknownPortRowStatus, hwBrasSbcSipSyslogEnable,
                hwBrasSbcSipAnonymity, hwBrasSbcSipCheckheartEnable, hwBrasSbcSipCallsessionTimer, hwBrasSbcMgcpAuepTimer, hwBrasSbcMgcpCcbTimer,
                hwBrasSbcMgcpTxTimer, hwBrasSbcMgcpWellknownPortPort, hwBrasSbcMgcpWellknownPortRowStatus, hwBrasSbcIadmsEnable, hwBrasSbcIadmsRegRefreshEnable,
                hwBrasSbcMgcpSyslogEnable, hwBrasSbcIadmsSyslogEnable, hwBrasSbcStatisticDesc, hwBrasSbcStatisticValue, hwBrasSbcStatisticTime,
                hwBrasSbcH248Enable, hwBrasSbcH248CcbTimer, hwBrasSbcH248UserAgeTimer, hwBrasSbcH323Enable, hwBrasSbcH323CallsessionTimer,
                hwBrasSbcH248SyslogEnable, hwBrasSbcH323SyslogEnable, hwBrasSbcUpathEnable, hwBrasSbcUpathSyslogEnable, hwBrasSbcUpathCallsessionTimer,
                hwBrasSbcUpathHeartbeatTimer, hwBrasSbcIdoEnable, hwBrasSbcIdoSyslogEnable, hwBrasSbcH323Q931WellknownPort, hwBrasSbcIntercomPrefixDestAddr,
                hwBrasSbcIntercomPrefixSrcAddr, hwBrasSbcIntercomPrefixRowStatus, hwBrasSbcStatisticEnable, hwBrasSbcStatisticSyslogEnable, hwBrasSbcAppMode, hwBrasSbcMediaDetectValidityEnable,
                hwBrasSbcMediaDetectSsrcEnable, hwBrasSbcMediaDetectPacketLength, hwBrasSbcInstanceName, hwBrasSbcInstanceRowStatus, hwBrasSbcMapGroupInstanceName,
                hwBrasSbcMapGroupSessionLimit, hwBrasSbcMGMdCliAddrVPNName, hwBrasSbcMGMdCliAddrIf1, hwBrasSbcMGMdCliAddrSlotID1, hwBrasSbcMGMdCliAddrIf2, hwBrasSbcMGMdCliAddrSlotID2,
                hwBrasSbcMGMdCliAddrIf3, hwBrasSbcMGMdCliAddrSlotID3, hwBrasSbcMGMdCliAddrIf4, hwBrasSbcMGMdCliAddrSlotID4,
                hwBrasSbcMGMdServAddrVPNName, hwBrasSbcMGMdServAddrIf1, hwBrasSbcMGMdServAddrSlotID1, hwBrasSbcMGMdServAddrIf2, hwBrasSbcMGMdServAddrSlotID2,
                hwBrasSbcMGMdServAddrIf3, hwBrasSbcMGMdServAddrSlotID3, hwBrasSbcMGMdServAddrIf4, hwBrasSbcMGMdServAddrSlotID4,
                hwBrasSbcBackupGroupType, hwBrasSbcBackupGroupInstanceName, hwBrasSbcBackupGroupRowStatus,
                hwBrasSbcCurrentSlotID, hwBrasSbcSlotCfgState, hwBrasSbcSlotInforRowStatus,
                hwBrasSbcImsMgLogEnable, hwBrasSbcImsStatisticsEnable, hwBrasSbcTimerMediaAging,
                hwBrasSbcImsMGInstanceName, hwBrasSbcNatSessionAgingTime, hwBrasSbcNatGroupIndex, hwBrasSbcNatVpnNameIndex, hwBrasSbcNatInstanceName,
                hwBrasSbcNatCfgRowStatus, hwNatAddrGrpBeginningIpAddr, hwNatAddrGrpEndingIpAddr, hwNatAddrGrpRefCount, hwNatAddrGrpVpnName,
                hwNatAddrGrpRowstatus, hwBrasSbcBWLimitType, hwBrasSbcBWLimitValue, hwBrasSbcSessionCarDegreeBandWidth,
                hwBrasSbcSessionCarDegreeDscp, hwBrasSbcSessionCarDegreeRowStatus, hwBrasSbcSessionCarRuleName, hwBrasSbcSessionCarRuleDegreeID, hwBrasSbcSessionCarRuleRowStatus,
                hwBrasSbcSessionCarEnable, hwBrasSbcSessionCarRuleDegreeBandWidth, hwBrasSbcSessionCarRuleDegreeDscp, hwBrasSbcSipMediaMapNumber, hwBrasSbcMgcpMediaMapNumber,
                hwBrasSbcH323MediaMapNumber, hwBrasSbcIadmsMediaMapNumber, hwBrasSbcUpathMediaMapNumber, hwBrasSbcH248MediaMapNumber, hwBrasSbcMediaUsersType,
                hwBrasSbcMediaUsersCallerID1, hwBrasSbcMediaUsersCallerID2, hwBrasSbcMediaUsersCallerID3, hwBrasSbcMediaUsersCallerID4, hwBrasSbcMediaUsersCalleeID1,
                hwBrasSbcMediaUsersCalleeID2, hwBrasSbcMediaUsersCalleeID3, hwBrasSbcMediaUsersCalleeID4, hwBrasSbcMediaUsersRowStatus, hwBrasSbcMediaPassEnable,
                hwBrasSbcMediaPassRowStatus, hwBrasSbcUsergroupRuleType, hwBrasSbcUsergroupRowStatus, hwBrasSbcMediaPassSyslogEnable, hwBrasSbcIadmsTimer,
                hwBrasSbcMediaAddrMapServerAddr, hwBrasSbcMediaAddrMapWeight, hwBrasSbcMediaAddrMapRowStatus, hwBrasSbcRoamlimitRowStatus, hwBrasSbcRoamlimitEnable,
                hwBrasSbcRoamlimitDefault, hwBrasSbcRoamlimitSyslogEnable, hwBrasSbcMediaPassAclNumber, hwBrasSbcRtpSpecialAddrRowStatus, hwBrasSbcRtpSpecialAddrAddr,
                hwBrasSbcSipSignalMapNumber, hwBrasSbcSipIntercomMapSignalNumber, hwBrasSbcMgcpIntercomMapSignalNumber, hwBrasSbcMgcpIntercomMapMediaNumber, hwBrasSbcIadmsIntercomMapSignalNumber,
                hwBrasSbcIadmsIntercomMapMediaNumber, hwBrasSbcH323IntercomMapSignalNumber, hwBrasSbcH323IntercomMapMediaNumber, hwBrasSbcIdoIntercomMapSignalNumber, hwBrasSbcH248IntercomMapSignalNumber,
                hwBrasSbcH248IntercomMapMediaNumber, hwBrasSbcUpathIntercomMapSignalNumber, hwBrasSbcUpathIntercomMapMediaNumber, hwBrasSbcRoamlimitExtendEnable, hwBrasSbcSipIntercomMapMediaNumber,
                hwBrasSbcSipSignalMapAddrType, hwBrasSbcMgcpSignalMapNumber, hwBrasSbcMgcpSignalMapAddrType, hwBrasSbcIadmsSignalMapNumber, hwBrasSbcIadmsSignalMapAddrType,
                hwBrasSbcH323SignalMapNumber, hwBrasSbcH323SignalMapAddrType, hwBrasSbcIdoSignalMapNumber, hwBrasSbcIdoSignalMapAddrType, hwBrasSbcH248SignalMapNumber,
                hwBrasSbcH248SignalMapAddrType, hwBrasSbcUpathSignalMapNumber, hwBrasSbcRoamlimitAclNumber, hwBrasSbcUpathSignalMapAddrType, hwBrasSbcUpathWellknownPortPort,
                hwBrasSbcUpathStatSignalPacketInNumber, hwBrasSbcUpathStatSignalPacketInOctet, hwBrasSbcUpathStatSignalPacketOutNumber, hwBrasSbcUpathStatSignalPacketOutOctet, hwBrasSbcUpathStatSignalPacketRowStatus,
                hwBrasSbcH248StatSignalPacketInNumber, hwBrasSbcH248StatSignalPacketInOctet, hwBrasSbcH248StatSignalPacketOutNumber, hwBrasSbcH248StatSignalPacketOutOctet, hwBrasSbcH248StatSignalPacketRowStatus,
                hwBrasSbcIdoStatSignalPacketInNumber, hwBrasSbcIdoStatSignalPacketInOctet, hwBrasSbcIdoStatSignalPacketOutNumber, hwBrasSbcIdoStatSignalPacketOutOctet, hwBrasSbcIdoStatSignalPacketRowStatus,
                hwBrasSbcH323StatSignalPacketInNumber, hwBrasSbcH323StatSignalPacketInOctet, hwBrasSbcH323StatSignalPacketOutNumber, hwBrasSbcH323StatSignalPacketOutOctet, hwBrasSbcH323StatSignalPacketRowStatus,
                hwBrasSbcIadmsStatSignalPacketInNumber, hwBrasSbcIadmsStatSignalPacketInOctet, hwBrasSbcIadmsStatSignalPacketOutNumber, hwBrasSbcIadmsStatSignalPacketOutOctet, hwBrasSbcIadmsStatSignalPacketRowStatus,
                hwBrasSbcMgcpStatSignalPacketInNumber, hwBrasSbcMgcpStatSignalPacketInOctet, hwBrasSbcMgcpStatSignalPacketOutNumber, hwBrasSbcMgcpStatSignalPacketOutOctet, hwBrasSbcMgcpStatSignalPacketRowStatus,
                hwBrasSbcSipStatSignalPacketInNumber, hwBrasSbcSipStatSignalPacketInOctet, hwBrasSbcSipStatSignalPacketOutNumber, hwBrasSbcSipStatSignalPacketOutOctet, hwBrasSbcSipStatSignalPacketRowStatus,
                hwBrasSbcStatMediaPacketNumber, hwBrasSbcStatMediaPacketOctet, hwBrasSbcStatMediaPacketRowStatus, hwBrasSbcCacRegRateThreshold, hwBrasSbcCacRegRatePercent,
                hwBrasSbcCacRegRateRowStatus, hwBrasSbcCacRegTotalThreshold, hwBrasSbcCacRegTotalPercent, hwBrasSbcCacRegTotalRowStatus, hwBrasSbcCacCallRateThreshold,
                hwBrasSbcCacCallRatePercent, hwBrasSbcCacCallRateRowStatus, hwBrasSbcCacCallTotalThreshold, hwBrasSbcCacCallTotalPercent, hwBrasSbcCacCallTotalRowStatus,
                hwBrasSbcDefendUserConnectRateThreshold, hwBrasSbcDefendUserConnectRatePercent, hwBrasSbcDefendUserConnectRateRowStatus, hwBrasSbcDefendConnectRateThreshold, hwBrasSbcDefendConnectRatePercent,
                hwBrasSbcDefendConnectRateRowStatus, hwBrasSbcDefendEnable, hwBrasSbcDefendMode, hwBrasSbcDefendActionLogEnable, hwBrasSbcCacEnable,
                hwBrasSbcUpathWellknownPortRowStatus, hwBrasSbcUsergroupRuleUserName, hwBrasSbcUsergroupRuleRowStatus, hwBrasSbcUdpTunnelPortRowStatus, hwBrasSbcUdpTunnelIfPortRowStatus,
                hwBrasSbcUdpTunnelEnable, hwBrasSbcUdpTunnelType, hwBrasSbcUdpTunnelSctpAddr, hwBrasSbcUdpTunnelTunnelTimer, hwBrasSbcUdpTunnelTransportTimer,
                hwBrasSbcUdpTunnelPoolRowStatus, hwBrasSbcMgcpEnable, hwBrasSbcUdpTunnelPoolStartIP, hwBrasSbcUdpTunnelPoolEndIP, hwBrasSbcIntMediaPassEnable,
                hwBrasSbcSignalAddrMapSoftAddr, hwBrasSbcSignalAddrMapIadmsAddr, hwBrasSbcRestartEnable, hwBrasSbcRestartButton, hwBrasSbcUmsVersion,
                hwBrasSbcMapGroupsType, hwBrasSbcMapGroupsStatus, hwBrasSbcMapGroupsRowStatus, hwBrasSbcMGCliAddrVPN, hwBrasSbcMGCliAddrIP,
                hwBrasSbcMGCliAddrRowStatus, hwBrasSbcMGServAddrVPN, hwBrasSbcMGServAddrRowStatus, hwBrasSbcMGSofxAddrVPN, hwBrasSbcMGSofxAddrRowStatus,
                hwBrasSbcMGIadmsAddrVPN, hwBrasSbcMGIadmsAddrRowStatus, hwBrasSbcMGProtocolRowStatus, hwBrasSbcMGPrefixID, hwBrasSbcMGPrefixRowStatus,
                hwBrasSbcMGMdCliAddrVPN, hwBrasSbcMGMdCliAddrRowStatus, hwBrasSbcMGMdServAddrVPN, hwBrasSbcMGMdServAddrRowStatus, hwBrasSbcMGMatchAcl,
                hwBrasSbcMGMatchRowStatus, hwBrasSbcHrpSynchronization, hwBrasSbcMGIadmsAddrIP1, hwBrasSbcMGIadmsAddrIP2, hwBrasSbcMGIadmsAddrIP3,
                hwBrasSbcMGIadmsAddrIP4, hwBrasSbcMGSofxAddrIP1, hwBrasSbcMGSofxAddrIP2, hwBrasSbcMGSofxAddrIP3, hwBrasSbcMGSofxAddrIP4,
                hwBrasSbcMGMdServAddrIP1, hwBrasSbcMGMdServAddrIP2, hwBrasSbcMGMdServAddrIP3, hwBrasSbcMGMdServAddrIP4, hwBrasSbcMGMdCliAddrIP1,
                hwBrasSbcMGMdCliAddrIP2, hwBrasSbcMGMdCliAddrIP3, hwBrasSbcMGMdCliAddrIP4, hwBrasSbcMGServAddrIP1, hwBrasSbcMGServAddrIP2,
                hwBrasSbcMGServAddrIP3, hwBrasSbcMGServAddrIP4, hwBrasSbcMGProtocolSip, hwBrasSbcMGProtocolMgcp, hwBrasSbcMGProtocolH323,
                hwBrasSbcMGProtocolIadms, hwBrasSbcMGProtocolUpath, hwBrasSbcMGProtocolH248, hwBrasSbcPatchLoadStatus, hwBrasSbcImsActiveStatus,
                hwBrasSbcImsActiveRowStatus, hwBrasSbcImsBandIfIndex, hwBrasSbcImsBandIfName, hwBrasSbcImsBandIfType, hwBrasSbcImsBandValue,
                hwBrasSbcImsBandRowStatus, hwBrasSbcImsConnectPepID, hwBrasSbcImsConnectCliType, hwBrasSbcImsConnectServIP, hwBrasSbcImsConnectServPort,
                hwBrasSbcImsConnectRowStatus, hwBrasSbcImsQosEnable, hwBrasSbcImsMediaProxyEnable, hwBrasSbcImsQosLogEnable, hwBrasSbcImsMediaProxyLogEnable,
                hwBrasSbcCacActionLogStatus, hwBrasSbcImsConnectCliIP, hwBrasSbcH248PDHCountLimit, hwBrasSbcH323PDHCountLimit, hwBrasSbcMgcpPDHCountLimit,
                hwBrasSbcSipPDHCountLimit, hwBrasSbcSipRegReduceStatus, hwBrasSbcSipRegReduceTimer, hwBrasSbcDHSIPDetectStatus, hwBrasSbcDHSIPDetectTimer,
                hwBrasSbcDHSIPDetectSourcePort, hwBrasSbcDHSIPDetectFailCount, hwBrasSbcSoftswitchPortPort, hwBrasSbcSoftswitchPortRowStatus, hwBrasSbcIadmsPortPort,
                hwBrasSbcIadmsPortRowStatus, hwBrasSbcClientPortPort01, hwBrasSbcClientPortPort02, hwBrasSbcClientPortPort03, hwBrasSbcClientPortPort04,
                hwBrasSbcClientPortPort05, hwBrasSbcClientPortPort06, hwBrasSbcClientPortPort07, hwBrasSbcClientPortPort08, hwBrasSbcClientPortPort09,
                hwBrasSbcClientPortPort10, hwBrasSbcClientPortPort11, hwBrasSbcClientPortPort12, hwBrasSbcClientPortPort13, hwBrasSbcClientPortPort14,
                hwBrasSbcClientPortPort15, hwBrasSbcClientPortPort16, hwBrasSbcClientPortRowStatus, hwBrasSbcIntercomStatus, hwBrasSbcQRStatus,
                hwBrasSbcQRBandWidth, hwBrasSbcIPCarBWValue, hwBrasSbcIPCarBWRowStatus, hwBrasSbcDynamicStatus, hwBrasSbcSignalingCarStatus,
                hwBrasSbcIPCarStatus, hwBrasSbcImsMGDomainMapIndex, hwBrasSbcImsMGDomainRowStatus, hwBrasSbcImsMGIPVersion, hwBrasSbcImsMGIPAddr, hwBrasSbcImsMGIPInterface,
                hwBrasSbcImsMGIPPort, hwBrasSbcImsMGIPRowStatus, hwBrasSbcImsMGDescription, hwBrasSbcImsMGTableStatus, hwBrasSbcImsMGProtocol,
                hwBrasSbcImsMGMidString, hwBrasSbcImsMGRowStatus, hwBrasSbcImsMGStatus, hwBrasSbcImsMGConnectTimer, hwBrasSbcImsMGAgingTimer,
                hwBrasSbcImsMGCallSessionTimer, hwBrasSbcSctpStatus, hwBrasSbcIdlecutRtcpTimer, hwBrasSbcIdlecutRtpTimer, hwBrasSbcMediaDetectStatus,
                hwBrasSbcMediaOnewayStatus,    hwBrasSbcMDStatisticMinDrop, hwBrasSbcMDStatisticMaxDrop, hwBrasSbcMDStatisticFragDrop,
                hwBrasSbcMDStatisticFlowDrop, hwBrasSbcMDStatisticRowStatus, hwBrasSbcMDLengthMin, hwBrasSbcMDLengthMax, hwBrasSbcMDLengthRowStatus,
                hwBrasSbcMDStatus, hwBrasSbcDefendExtStatus, hwBrasSbcImsConnectCliPort, hwBrasSbcMGPortNumber, hwBrasSbcMGPortRowStatus,
                hwBrasSbcIntercomEnable, hwBrasSbcLocalizationStatus }
            STATUS current
            DESCRIPTION
                "Session Border Controller Objects Group"
            ::= { hwBrasSbcGroups 1 }

        hwBrasSbcTrapGroup OBJECT-GROUP
            OBJECTS { hwBrasSbcTrapBindID, hwBrasSbcTrapBindTime, hwBrasSbcTrapBindFluID, hwBrasSbcTrapBindReason, hwBrasSbcTrapBindType,
                hwBrasSbcTrapInfoCpu, hwBrasSbcTrapInfoHrp, hwBrasSbcTrapInfoSignalingFlood, hwBrasSbcTrapInfoCac, hwBrasSbcTrapInfoStatistic,
                hwBrasSbcTrapInfoPortStatistic, hwBrasSbcTrapInfoImsConID, hwBrasSbcTrapInfoImsCcbID, hwBrasSbcTrapInfoOldSSIP, hwBrasSbcDHSIPDetectFailCount
                 }
            STATUS current
            DESCRIPTION
                "Session Border Controller Trap Group."
            ::= { hwBrasSbcGroups 2 }

        hwBrasSbcCapabilities OBJECT IDENTIFIER ::= { hwBrasSbcComformance 2 }

        -- added by zhangyinxi --
        hwBrasSbcNotification OBJECT IDENTIFIER ::= { hwBrasSbcModule 4 }

        hwBrasSbcCpu NOTIFICATION-TYPE
            OBJECTS { hwBrasSbcTrapInfoCpu, hwBrasSbcTrapBindID, hwBrasSbcTrapBindTime, hwBrasSbcTrapBindFluID, hwBrasSbcTrapBindReason,
                hwBrasSbcTrapBindType }
            STATUS current
            DESCRIPTION
                "Cpu usage more than threshold."
            ::= { hwBrasSbcNotification 1 }

        hwBrasSbcCpuNormal NOTIFICATION-TYPE
            OBJECTS { hwBrasSbcTrapInfoCpu, hwBrasSbcTrapBindID, hwBrasSbcTrapBindTime, hwBrasSbcTrapBindFluID, hwBrasSbcTrapBindReason,
                hwBrasSbcTrapBindType }
            STATUS current
            DESCRIPTION
                "Cpu usage less than threshold."
            ::= { hwBrasSbcNotification 2 }

        hwBrasSbcHrp NOTIFICATION-TYPE
            OBJECTS { hwBrasSbcTrapInfoHrp, hwBrasSbcTrapBindID, hwBrasSbcTrapBindTime, hwBrasSbcTrapBindFluID, hwBrasSbcTrapBindReason,
                hwBrasSbcTrapBindType }
            STATUS current
            DESCRIPTION
                "Hrp Enable."
            ::= { hwBrasSbcNotification 3 }

        hwBrasSbcSignalingFlood NOTIFICATION-TYPE
            OBJECTS { hwBrasSbcTrapInfoSignalingFlood, hwBrasSbcTrapBindID, hwBrasSbcTrapBindTime, hwBrasSbcTrapBindFluID, hwBrasSbcTrapBindReason,
                hwBrasSbcTrapBindType }
            STATUS current
            DESCRIPTION
                "Flu more than signaling-flood threshold."
            ::= { hwBrasSbcNotification 4 }

        hwBrasSbcSignalingFloodNormal NOTIFICATION-TYPE
            OBJECTS { hwBrasSbcTrapInfoSignalingFlood, hwBrasSbcTrapBindID, hwBrasSbcTrapBindTime, hwBrasSbcTrapBindFluID, hwBrasSbcTrapBindReason,
                hwBrasSbcTrapBindType }
            STATUS current
            DESCRIPTION
                "Flu less than signaling-flood threshold."
            ::= { hwBrasSbcNotification 5 }

        hwBrasSbcCac NOTIFICATION-TYPE
            OBJECTS { hwBrasSbcTrapInfoCac, hwBrasSbcTrapBindID, hwBrasSbcTrapBindTime, hwBrasSbcTrapBindFluID, hwBrasSbcTrapBindReason,
                hwBrasSbcTrapBindType }
            STATUS current
            DESCRIPTION
                "Flu more than cac threshold."
            ::= { hwBrasSbcNotification 6 }

        hwBrasSbcCacNormal NOTIFICATION-TYPE
            OBJECTS { hwBrasSbcTrapInfoCac, hwBrasSbcTrapBindID, hwBrasSbcTrapBindTime, hwBrasSbcTrapBindFluID, hwBrasSbcTrapBindReason,
                hwBrasSbcTrapBindType }
            STATUS current
            DESCRIPTION
                "Flu less than cac threshold."
            ::= { hwBrasSbcNotification 7 }

        hwBrasSbcStatistic NOTIFICATION-TYPE
            OBJECTS { hwBrasSbcTrapInfoStatistic, hwBrasSbcTrapBindID, hwBrasSbcTrapBindTime, hwBrasSbcTrapBindFluID, hwBrasSbcTrapBindReason,
                hwBrasSbcTrapBindType }
            STATUS current
            DESCRIPTION
                "Statistic overflow."
            ::= { hwBrasSbcNotification 8 }

        hwBrasSbcPortStatistic NOTIFICATION-TYPE
            OBJECTS { hwBrasSbcTrapInfoPortStatistic, hwBrasSbcTrapBindID, hwBrasSbcTrapBindTime, hwBrasSbcTrapBindFluID, hwBrasSbcTrapBindReason,
                hwBrasSbcTrapBindType }
            STATUS current
            DESCRIPTION
                "Port statistic more than threshold."
            ::= { hwBrasSbcNotification 9 }

        hwBrasSbcPortStatisticNormal NOTIFICATION-TYPE
            OBJECTS { hwBrasSbcTrapInfoPortStatistic, hwBrasSbcTrapBindID, hwBrasSbcTrapBindTime, hwBrasSbcTrapBindFluID, hwBrasSbcTrapBindReason,
                hwBrasSbcTrapBindType }
            STATUS current
            DESCRIPTION
                "Port statistic less than threshold."
            ::= { hwBrasSbcNotification 10 }

        hwBrasSbcDHSwitch NOTIFICATION-TYPE
            OBJECTS { hwBrasSbcDHSIPDetectFailCount, hwBrasSbcTrapInfoOldSSIP, hwBrasSbcTrapBindID, hwBrasSbcTrapBindTime, hwBrasSbcTrapBindFluID,
                hwBrasSbcTrapBindReason, hwBrasSbcTrapBindType }
            STATUS current
            DESCRIPTION
                "Softswitch address changed"
            ::= { hwBrasSbcNotification 11 }

        hwBrasSbcDHSwitchNormal NOTIFICATION-TYPE
            OBJECTS { hwBrasSbcTrapInfoOldSSIP, hwBrasSbcTrapBindID, hwBrasSbcTrapBindTime, hwBrasSbcTrapBindFluID, hwBrasSbcTrapBindReason,
                hwBrasSbcTrapBindType }
            STATUS current
            DESCRIPTION
                "Softswitch states changed to resume"
            ::= { hwBrasSbcNotification 12 }

        hwBrasSbcImsRptFail NOTIFICATION-TYPE
            OBJECTS { hwBrasSbcTrapInfoImsConID, hwBrasSbcTrapBindID, hwBrasSbcTrapBindTime, hwBrasSbcTrapBindFluID, hwBrasSbcTrapBindReason,
                hwBrasSbcTrapBindType }
            STATUS current
            DESCRIPTION
                "Sbc COPS report failed state "
            ::= { hwBrasSbcNotification 13 }

        hwBrasSbcImsRptDrq NOTIFICATION-TYPE
            OBJECTS { hwBrasSbcTrapInfoImsConID, hwBrasSbcTrapBindID, hwBrasSbcTrapBindTime, hwBrasSbcTrapBindFluID, hwBrasSbcTrapBindReason,
                hwBrasSbcTrapBindType }
            STATUS current
            DESCRIPTION
                "Sbc COPS report Delete Request State"
            ::= { hwBrasSbcNotification 14 }

        hwBrasSbcImsTimeOut NOTIFICATION-TYPE
            OBJECTS { hwBrasSbcTrapInfoImsCcbID, hwBrasSbcTrapBindID, hwBrasSbcTrapBindTime, hwBrasSbcTrapBindFluID, hwBrasSbcTrapBindReason,
                hwBrasSbcTrapBindType }
            STATUS current
            DESCRIPTION
                "Sbc IMS session time out"
            ::= { hwBrasSbcNotification 15 }

        hwBrasSbcImsSessCreate NOTIFICATION-TYPE
            OBJECTS { hwBrasSbcTrapInfoImsCcbID, hwBrasSbcTrapBindID, hwBrasSbcTrapBindTime, hwBrasSbcTrapBindFluID, hwBrasSbcTrapBindReason,
                hwBrasSbcTrapBindType }
            STATUS current
            DESCRIPTION
                "Sbc IMS session is created"
            ::= { hwBrasSbcNotification 16 }

        hwBrasSbcImsSessDelete NOTIFICATION-TYPE
            OBJECTS { hwBrasSbcTrapInfoImsCcbID, hwBrasSbcTrapBindID, hwBrasSbcTrapBindTime, hwBrasSbcTrapBindFluID, hwBrasSbcTrapBindReason,
                hwBrasSbcTrapBindType }
            STATUS current
            DESCRIPTION
                "Sbc IMS session is deleted"
            ::= { hwBrasSbcNotification 17 }

        hwBrasSbcCopsLinkUp NOTIFICATION-TYPE
            OBJECTS { hwBrasSbcTrapInfoImsConID, hwBrasSbcTrapBindID, hwBrasSbcTrapBindTime, hwBrasSbcTrapBindFluID, hwBrasSbcTrapBindReason,
                hwBrasSbcTrapBindType }
            STATUS current
            DESCRIPTION
                "Sbc COPS link up"
            ::= { hwBrasSbcNotification 18 }

        hwBrasSbcCopsLinkDown NOTIFICATION-TYPE
            OBJECTS { hwBrasSbcTrapInfoImsConID, hwBrasSbcTrapBindID, hwBrasSbcTrapBindTime, hwBrasSbcTrapBindFluID, hwBrasSbcTrapBindReason,
                hwBrasSbcTrapBindType }
            STATUS current
            DESCRIPTION
                "Sbc COPS link down"
            ::= { hwBrasSbcNotification 19 }

        hwBrasSbcIaLinkUp NOTIFICATION-TYPE
            OBJECTS { hwBrasSbcTrapInfoImsConID, hwBrasSbcTrapBindID, hwBrasSbcTrapBindTime, hwBrasSbcTrapBindFluID, hwBrasSbcTrapBindReason,
                hwBrasSbcTrapBindType }
            STATUS current
            DESCRIPTION
                "Sbc Ia link up"
            ::= { hwBrasSbcNotification 20 }

        hwBrasSbcIaLinkDown NOTIFICATION-TYPE
            OBJECTS { hwBrasSbcTrapInfoImsConID, hwBrasSbcTrapBindID, hwBrasSbcTrapBindTime, hwBrasSbcTrapBindFluID, hwBrasSbcTrapBindReason,
                hwBrasSbcTrapBindType }
            STATUS current
            DESCRIPTION
                "Sbc Ia link down"
            ::= { hwBrasSbcNotification 21 }

        hwBrasSbcNotificationGroups OBJECT IDENTIFIER ::= { hwBrasSbcModule 5 }

        hwBrasSbcNotificationGroup NOTIFICATION-GROUP
            NOTIFICATIONS { hwBrasSbcCpu, hwBrasSbcCpuNormal, hwBrasSbcHrp, hwBrasSbcSignalingFlood, hwBrasSbcSignalingFloodNormal,
                hwBrasSbcCac, hwBrasSbcCacNormal, hwBrasSbcStatistic, hwBrasSbcPortStatistic, hwBrasSbcPortStatisticNormal,
                hwBrasSbcDHSwitch, hwBrasSbcDHSwitchNormal, hwBrasSbcImsRptFail, hwBrasSbcImsRptDrq, hwBrasSbcImsTimeOut,
                hwBrasSbcImsSessCreate, hwBrasSbcImsSessDelete, hwBrasSbcCopsLinkUp, hwBrasSbcCopsLinkDown, hwBrasSbcIaLinkUp,
                hwBrasSbcIaLinkDown }
            STATUS current
            DESCRIPTION
                "Session Border Controller Notification Group."
            ::= { hwBrasSbcNotificationGroups 1 }
        -- end added by zhangyinxi --

    END

--
-- HUAWEI-BrasSbc-MIB.mib
--
