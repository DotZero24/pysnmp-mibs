-- =================================================================
-- Copyright (C) 2018 by  HUAWEI TECHNOLOGIES. All rights reserved
--
-- Description: The HUAWEI-VNE-MIB provides information about DataComm TRAPS
--
-- Reference:
-- Version: V1.19
-- History:
--
-- =================================================================

	HUAWEI-VNE-MIB DEFINITIONS ::= BEGIN

		IMPORTS
			entPhysicalIndex, entPhysicalName
				FROM ENTITY-MIB
			hwDatacomm
				FROM HUAWEI-MIB
			IANAItuProbableCause
				FROM IANA-ITU-ALARM-TC-MIB
			OBJECT-GROUP, MODULE-COMPLIANCE, NOTIFICATION-GROUP
				FROM SNMPv2-CONF
			IpAddress, Integer32, Unsigned32, OBJECT-TYPE, MODULE-IDENTITY, NOTIFICATION-TYPE
				FROM SNMPv2-SMI
            DisplayString
                FROM SNMPv2-TC;


-- December 22, 2015 at 00:00 GMT
-- 1.3.6.1.4.1.2011.5.25.345


		hwVNEMIB MODULE-IDENTITY
			LAST-UPDATED "201806121600Z"		--June 12, 2018 at 16:00 GMT
			ORGANIZATION
				"Huawei Technologies Co.,Ltd."
			CONTACT-INFO
				"Huawei Industrial Base Bantian, Longgang Shenzhen 518129 People's Republic of China Website: http://www.huawei.com Email: support@huawei.com "
			DESCRIPTION
				"This is the VNE mib definition for DataCom."
                        REVISION  "201806121600Z"
                        DESCRIPTION  "update param."
                        REVISION  "201806081600Z"
                        DESCRIPTION  "add hwCuCpRoleConflict  and hwCuCpRoleConflictResume."
                        REVISION  "201805151600Z"
                        DESCRIPTION  "add hwBackupNotEffectiveProfileName hwBackupNotEffectiveReason and hwWarmBackupNotEffectiveAlarm."
                        REVISION  "201805082000Z"
                        DESCRIPTION  "add hwUpSlotid hwCuUpBoardNotSupportBasAlarm and hwCuUpBoardNotSupportBasAlarmResume."
                        REVISION  "201804270000Z"
                        DESCRIPTION  "modify hwUpid."
			REVISION  "201804012000Z"
                        DESCRIPTION  "add hwDatabaseMemoryUsage."
                        REVISION  "201803192000Z"
                        DESCRIPTION  "add hwInstanceId hwDisconnectReason and hwGMDBMemoryUsage."
                        REVISION  "201802082000Z"
                        DESCRIPTION  "add hwNotSupportServiceName hwNotSupportModule and hwCuNotSupportServiceAlarm."
                        REVISION  "201802072000Z"
                        DESCRIPTION  "add hwHeartbeatSignalDisconnectAlarm and hwHeartbeatSignalDisconnectResume."
                        REVISION  "201801032000Z"
                        DESCRIPTION  "add hwULPULicenseReachThreshold and hwULPULicenseReachThresholdResume."
                        REVISION  "201712042000Z"
                        DESCRIPTION  "add hwUpid of hwCuInterfaceVersionNegotiationFail and hwCuInterfaceVersionNegotiationFailResume."
                        REVISION  "201711302000Z"
                        DESCRIPTION  "add hwAntiSplitBrainFuncFailAlarm and hwAntiSplitBrainFuncFailResume. add hwAntiSplitBrainFuncReliabilityDeAlarmand hwAntiSplitBrainFuncReliabilityDeResume"
                        REVISION  "201711162000Z"
                        DESCRIPTION  "add hwCuInterfaceVersionNegotiationFail and hwCuInterfaceVersionNegotiationFailResume. add hwCpConflictIPAlarm and hwUpConflictIPAlarm"
                        REVISION  "201710232000Z"
                        DESCRIPTION "add hwULPULicenseLimit and hwULPULicenseLimitResume."
                        REVISION  "201707202000Z"
                        DESCRIPTION  "add hwVNEDatabaseDisConnected and hwVNEDatabaseConnectionResume and hwVNEDatabaseServiceException and hwVNEDatabaseServiceResume and hwVNEDatabaseServiceCPUOverload and hwVNEDatabaseServiceCPUOverloadResume and hwVNEDatabaseServiceMemoryOverload and hwVNEDatabaseServiceMemoryOverloadResume. "
                        REVISION  "201704262000Z"
                        DESCRIPTION  "add hwVNEGMDBDisConnected and hwVNEGMDBConnectionResume and hwVNEGMDBServiceException and hwVNEGMDBServiceResume and hwVNEGMDBServiceCPUOverload and hwVNEGMDBServiceCPUOverloadResume and hwVNEGMDBServiceMemoryOverload and hwVNEGMDBServiceMemoryOverloadResume. "
                        REVISION  "201611282000Z"
                        DESCRIPTION  "add hwCreateVmFail and hwCreateVmFailResum. "

                        REVISION  "201602242000Z"
                        DESCRIPTION  "add hwVFabPlaneFailResum and hwVFabHealthyFailResum  TO hwVNETrapGroup . "

                        REVISION  "201602222000Z"
                        DESCRIPTION  "add hwVFabPlaneFailResum and hwVFabHealthyFailResum  . "

                        REVISION  "201501222000Z"
                        DESCRIPTION  "The initial revision of this MIB module . "
			::= { hwDatacomm 345 }

-- Node definitions
--
-- 1.3.6.1.4.1.2011.5.25.345.1
		-- 1.3.6.1.4.1.2011.5.25.345.1
		hwVNETrapObject OBJECT IDENTIFIER ::= { hwVNEMIB 1 }


--  1.3.6.1.4.1.2011.5.25.345.1.1
        -- 1.3.6.1.4.1.2011.5.25.345.1.1
        hwPlaneID OBJECT-TYPE
            SYNTAX Integer32
            MAX-ACCESS accessible-for-notify
            STATUS current
            DESCRIPTION
                "The plane id."
            ::= { hwVNETrapObject 1 }

--  1.3.6.1.4.1.2011.5.25.345.1.2
        -- 1.3.6.1.4.1.2011.5.25.345.1.2
        hwPlaneFailReason OBJECT-TYPE
            SYNTAX Integer32
            MAX-ACCESS accessible-for-notify
            STATUS current
            DESCRIPTION
                "The reason id."
            ::= { hwVNETrapObject 2 }

--  1.3.6.1.4.1.2011.5.25.345.1.3
        -- 1.3.6.1.4.1.2011.5.25.345.1.3
        hwSubhealthyRate OBJECT-TYPE
            SYNTAX Integer32
            MAX-ACCESS accessible-for-notify
            STATUS current
            DESCRIPTION
                "The rate of subhealthy."
            ::= { hwVNETrapObject 3 }

--  1.3.6.1.4.1.2011.5.25.345.1.4
        -- 1.3.6.1.4.1.2011.5.25.345.1.4
        hwVmSlotId OBJECT-TYPE
            SYNTAX Integer32
            MAX-ACCESS accessible-for-notify
            STATUS current
            DESCRIPTION
                "The id of vm."
            ::= { hwVNETrapObject 4 }

--  1.3.6.1.4.1.2011.5.25.345.1.5
        -- 1.3.6.1.4.1.2011.5.25.345.1.5
        hwCreateVmFailReason OBJECT-TYPE
            SYNTAX Integer32
            MAX-ACCESS accessible-for-notify
            STATUS current
            DESCRIPTION
                "The reason id."
            ::= { hwVNETrapObject 5 }

--  1.3.6.1.4.1.2011.5.25.345.1.6
        -- 1.3.6.1.4.1.2011.5.25.345.1.6
        hwVNFCID OBJECT-TYPE
            SYNTAX Unsigned32
            MAX-ACCESS accessible-for-notify
            STATUS current
            DESCRIPTION
                "The vnfc id."
            ::= { hwVNETrapObject 6 }

--  1.3.6.1.4.1.2011.5.25.345.1.7
        -- 1.3.6.1.4.1.2011.5.25.345.1.7
        hwPID OBJECT-TYPE
            SYNTAX Unsigned32
            MAX-ACCESS accessible-for-notify
            STATUS current
            DESCRIPTION
                "The component id."
            ::= { hwVNETrapObject 7 }

--  1.3.6.1.4.1.2011.5.25.345.1.8
        -- 1.3.6.1.4.1.2011.5.25.345.1.8
        hwServerLocator OBJECT-TYPE
            SYNTAX DisplayString
            MAX-ACCESS accessible-for-notify
            STATUS current
            DESCRIPTION
                "The server locator."
            ::= { hwVNETrapObject 8 }

--  1.3.6.1.4.1.2011.5.25.345.1.9
        -- 1.3.6.1.4.1.2011.5.25.345.1.9
        hwClusterName OBJECT-TYPE
            SYNTAX DisplayString
            MAX-ACCESS accessible-for-notify
            STATUS current
            DESCRIPTION
                "The cluster name."
            ::= { hwVNETrapObject 9 }

--  1.3.6.1.4.1.2011.5.25.345.1.10
        -- 1.3.6.1.4.1.2011.5.25.345.1.10
        hwLicenseNumbers OBJECT-TYPE
            SYNTAX Integer32
            MAX-ACCESS accessible-for-notify
            STATUS current
            DESCRIPTION
                "The number of the license."
            ::= { hwVNETrapObject 10 }

--  1.3.6.1.4.1.2011.5.25.345.1.11
        -- 1.3.6.1.4.1.2011.5.25.345.1.11
        hwUlpuNumbers OBJECT-TYPE
            SYNTAX Integer32
            MAX-ACCESS accessible-for-notify
            STATUS current
            DESCRIPTION
                "The number of the ULPU."
            ::= { hwVNETrapObject 11 }

-- 1.3.6.1.4.1.2011.5.25.345.1.12
        hwCuInterfaceVersionCp OBJECT-TYPE
            SYNTAX Integer32
            MAX-ACCESS accessible-for-notify
            STATUS current
            DESCRIPTION
                "The interface version of CP."
            ::= { hwVNETrapObject 12 }

-- 1.3.6.1.4.1.2011.5.25.345.1.13
        hwCuInterfaceVersionUp OBJECT-TYPE
            SYNTAX Integer32
            MAX-ACCESS accessible-for-notify
            STATUS current
            DESCRIPTION
                "The interface version of UP."
            ::= { hwVNETrapObject 13 }

-- 1.3.6.1.4.1.2011.5.25.345.1.14
        hwCuInterfaceVersionReason OBJECT-TYPE
            SYNTAX Integer32
            MAX-ACCESS accessible-for-notify
            STATUS current
            DESCRIPTION
                "The fail/success reason of interface version negotiation."
            ::= { hwVNETrapObject 14 }

-- 1.3.6.1.4.1.2011.5.25.345.1.15
        hwCpPoolName OBJECT-TYPE
            SYNTAX DisplayString (SIZE (1..35))
            MAX-ACCESS accessible-for-notify
            STATUS current
            DESCRIPTION
                "The name of the address pool."
            ::= { hwVNETrapObject 15 }

-- 1.3.6.1.4.1.2011.5.25.345.1.16
        hwCpGateway OBJECT-TYPE
            SYNTAX IpAddress
            MAX-ACCESS read-create
            STATUS current
            DESCRIPTION
                "Gateway IP address.
                By default, the mask is 255.255.255.255."
            ::= { hwVNETrapObject 16 }

-- 1.3.6.1.4.1.2011.5.25.345.1.17
        hwCpNetmask OBJECT-TYPE
            SYNTAX IpAddress
            MAX-ACCESS read-create
            STATUS current
            DESCRIPTION
                "Netmask IP address.
                By default, the mask is 255.255.255.255."
            ::= { hwVNETrapObject 17 }

-- 1.3.6.1.4.1.2011.5.25.345.1.18
        hwUpid OBJECT-TYPE
            SYNTAX Unsigned32
            MAX-ACCESS accessible-for-notify
            STATUS current
            DESCRIPTION
                "Netmask IP address.
                By default, the mask is 255.255.255.255."
            ::= { hwVNETrapObject 18 }

-- 1.3.6.1.4.1.2011.5.25.345.1.19
        hwUpInterface OBJECT-TYPE
            SYNTAX DisplayString (SIZE (1..64))
            MAX-ACCESS accessible-for-notify
            STATUS current
            DESCRIPTION
                "Netmask IP address.
                By default, the mask is 255.255.255.255."
            ::= { hwVNETrapObject 19 }

-- 1.3.6.1.4.1.2011.5.25.345.1.20
        hwAntiSplitBrainFuncReason OBJECT-TYPE
            SYNTAX DisplayString (SIZE (1..128))
            MAX-ACCESS accessible-for-notify
            STATUS current
            DESCRIPTION
                "The reason of tanti-split-brain function failed."
            ::= { hwVNETrapObject 20 }

--  1.3.6.1.4.1.2011.5.25.345.1.21
        -- 1.3.6.1.4.1.2011.5.25.345.1.21
        hwULPUThreshold OBJECT-TYPE
            SYNTAX Integer32
            MAX-ACCESS accessible-for-notify
            STATUS current
            DESCRIPTION
                "License usage upper limit threshold of ULPU."
            ::= { hwVNETrapObject 21}

--  1.3.6.1.4.1.2011.5.25.345.1.22
        -- 1.3.6.1.4.1.2011.5.25.345.1.22
        hwSourceIpAddress OBJECT-TYPE
            SYNTAX Unsigned32
            MAX-ACCESS accessible-for-notify
            STATUS current
            DESCRIPTION
                "Heartbeat channel IP address of the local VNE."
            ::= { hwVNETrapObject 22}

--  1.3.6.1.4.1.2011.5.25.345.1.23
        -- 1.3.6.1.4.1.2011.5.25.345.1.23
        hwPeerIpAddress OBJECT-TYPE
            SYNTAX Unsigned32
            MAX-ACCESS accessible-for-notify
            STATUS current
            DESCRIPTION
                "Heartbeat channel IP address of the peer VNE."
            ::= { hwVNETrapObject 23}

--  1.3.6.1.4.1.2011.5.25.345.1.24
        -- 1.3.6.1.4.1.2011.5.25.345.1.24
        hwDisasterRecoveryReason OBJECT-TYPE
            SYNTAX  DisplayString (SIZE (1..128))
            MAX-ACCESS accessible-for-notify
            STATUS current
            DESCRIPTION
                "Disaster-recovery alarm generation or clearance reason."
            ::= { hwVNETrapObject 24}

--  1.3.6.1.4.1.2011.5.25.345.1.25
        hwNotSupportServiceName OBJECT-TYPE
            SYNTAX  DisplayString (SIZE (1..30))
            MAX-ACCESS accessible-for-notify
            STATUS current
            DESCRIPTION
                "This object indicates that a service that does not support CU separation exists on the UP."
            ::= { hwVNETrapObject 25}

--  1.3.6.1.4.1.2011.5.25.345.1.26
        hwNotSupportModule OBJECT-TYPE
            SYNTAX  DisplayString (SIZE (1..30))
            MAX-ACCESS accessible-for-notify
            STATUS current
            DESCRIPTION
                "This object indicates the name of the module of a service that does not support CU separation."
            ::= { hwVNETrapObject 26}

--  1.3.6.1.4.1.2011.5.25.345.1.27
        -- 1.3.6.1.4.1.2011.5.25.345.1.27
        hwInstanceId OBJECT-TYPE
            SYNTAX  Integer32
            MAX-ACCESS accessible-for-notify
            STATUS current
            DESCRIPTION
                "Instance id."
            ::= { hwVNETrapObject 27}

--  1.3.6.1.4.1.2011.5.25.345.1.28
        -- 1.3.6.1.4.1.2011.5.25.345.1.28
        hwDisconnectReason OBJECT-TYPE
            SYNTAX  Integer32
            MAX-ACCESS accessible-for-notify
            STATUS current
            DESCRIPTION
                "Database alarm generation reason."
            ::= { hwVNETrapObject 28}

 --  1.3.6.1.4.1.2011.5.25.345.1.29
        -- 1.3.6.1.4.1.2011.5.25.345.1.29
        hwDatabaseMemoryUsage OBJECT-TYPE
            SYNTAX  Integer32
            MAX-ACCESS accessible-for-notify
            STATUS current
            DESCRIPTION
                "Database alarm generation reason."
            ::= { hwVNETrapObject 29}

--  1.3.6.1.4.1.2011.5.25.345.1.30
       -- 1.3.6.1.4.1.2011.5.25.345.1.30
       hwUpSlotid OBJECT-TYPE
           SYNTAX  Integer32
           MAX-ACCESS accessible-for-notify
           STATUS current
           DESCRIPTION
               "The slotid of up."
           ::= { hwVNETrapObject 30}

--  1.3.6.1.4.1.2011.5.25.345.1.31
        hwBackupNotEffectiveProfileName OBJECT-TYPE
            SYNTAX  DisplayString (SIZE (1..35))
            MAX-ACCESS accessible-for-notify
            STATUS current
            DESCRIPTION
                "This object indicates the name of the up-backup-profile that backup function is not effective."
            ::= { hwVNETrapObject 31}

--  1.3.6.1.4.1.2011.5.25.345.1.32
        hwBackupNotEffectiveReason OBJECT-TYPE
            SYNTAX  DisplayString (SIZE (1..64))
            MAX-ACCESS accessible-for-notify
            STATUS current
            DESCRIPTION
                "This object indicates the reason why the backup function is not effective ."
            ::= { hwVNETrapObject 32}

-- 1.3.6.1.4.1.2011.5.25.345.2
		-- 1.3.6.1.4.1.2011.5.25.345.2
		hwVNETrapMIB OBJECT IDENTIFIER ::= { hwVNEMIB 2 }

--  1.3.6.1.4.1.2011.5.25.345.2.1
		-- 1.3.6.1.4.1.2011.5.25.345.2.1
		hwVFabricTrap OBJECT IDENTIFIER ::= { hwVNETrapMIB 1 }

--  1.3.6.1.4.1.2011.5.25.345.2.1.1
		-- 1.3.6.1.4.1.2011.5.25.345.2.1.1
		hwVFabPlaneFail NOTIFICATION-TYPE
			OBJECTS { entPhysicalIndex, entPhysicalIndex, hwPlaneID, hwPlaneFailReason }
			STATUS current
			DESCRIPTION
				"fabric plane goes down."
			::= { hwVFabricTrap 1 }


--  1.3.6.1.4.1.2011.5.25.345.2.1.2
		-- 1.3.6.1.4.1.2011.5.25.345.2.1.2
		hwVFabPlaneFailResum NOTIFICATION-TYPE
			OBJECTS { entPhysicalIndex, entPhysicalIndex, hwPlaneID, hwPlaneFailReason }
			STATUS current
			DESCRIPTION
				"fabric plane goes up."
			::= { hwVFabricTrap 2 }

--  1.3.6.1.4.1.2011.5.25.345.2.1.3
		-- 1.3.6.1.4.1.2011.5.25.345.2.1.3
		hwVFabHealthyFail NOTIFICATION-TYPE
			OBJECTS { entPhysicalIndex, entPhysicalIndex, hwPlaneID, hwSubhealthyRate }
			STATUS current
			DESCRIPTION
				"fabric link goes fault."
			::= { hwVFabricTrap 3 }


--  1.3.6.1.4.1.2011.5.25.345.2.1.4
		-- 1.3.6.1.4.1.2011.5.25.345.2.1.4
		hwVFabHealthyFailResum NOTIFICATION-TYPE
			OBJECTS { entPhysicalIndex, entPhysicalIndex, hwPlaneID, hwSubhealthyRate }
			STATUS current
			DESCRIPTION
				"fabric link goes normal."
			::= { hwVFabricTrap 4 }

--  1.3.6.1.4.1.2011.5.25.345.2.2
		-- 1.3.6.1.4.1.2011.5.25.345.2.2
		hwCreateVmTrap OBJECT IDENTIFIER ::= { hwVNETrapMIB 2 }

--  1.3.6.1.4.1.2011.5.25.345.2.2.1
		-- 1.3.6.1.4.1.2011.5.25.345.2.2.1
		hwCreateVmFail NOTIFICATION-TYPE
			OBJECTS { entPhysicalIndex, entPhysicalIndex, hwVmSlotId, hwCreateVmFailReason }
			STATUS current
			DESCRIPTION
				"Create vm goes down."
			::= { hwCreateVmTrap 1 }


--  1.3.6.1.4.1.2011.5.25.345.2.2.2
		-- 1.3.6.1.4.1.2011.5.25.345.2.2.2
		hwCreateVmFailResum NOTIFICATION-TYPE
			OBJECTS { entPhysicalIndex, entPhysicalIndex, hwVmSlotId}
			STATUS current
			DESCRIPTION
				"Create vm goes up."
			::= { hwCreateVmTrap 2 }

--  1.3.6.1.4.1.2011.5.25.345.2.3
		-- 1.3.6.1.4.1.2011.5.25.345.2.3
		hwDatabaseTrap OBJECT IDENTIFIER ::= { hwVNETrapMIB 3 }

--  1.3.6.1.4.1.2011.5.25.345.2.3.1
		-- 1.3.6.1.4.1.2011.5.25.345.2.3.1
		hwVNEDatabaseDisConnected NOTIFICATION-TYPE
			OBJECTS { hwInstanceId, hwDisconnectReason}
			STATUS current
			DESCRIPTION
				"The database connection is broken."
			::= { hwDatabaseTrap 1 }

--  1.3.6.1.4.1.2011.5.25.345.2.3.2
		-- 1.3.6.1.4.1.2011.5.25.345.2.3.2
		hwVNEDatabaseConnectionResume NOTIFICATION-TYPE
			OBJECTS { hwInstanceId, hwDisconnectReason}
			STATUS current
			DESCRIPTION
				"The database connection is resumed."
			::= { hwDatabaseTrap 2 }

--  1.3.6.1.4.1.2011.5.25.345.2.3.3
		-- 1.3.6.1.4.1.2011.5.25.345.2.3.3
		hwVNEDatabaseServiceException NOTIFICATION-TYPE
			OBJECTS { hwVNFCID, hwPID, hwServerLocator, hwClusterName}
			STATUS current
			DESCRIPTION
				"An exception occurred in the database service."
			::= { hwDatabaseTrap 3 }

--  1.3.6.1.4.1.2011.5.25.345.2.3.4
		-- 1.3.6.1.4.1.2011.5.25.345.2.3.4
		hwVNEDatabaseServiceResume NOTIFICATION-TYPE
			OBJECTS { hwVNFCID, hwPID, hwServerLocator, hwClusterName}
			STATUS current
			DESCRIPTION
				"The database service is resumed. "
			::= { hwDatabaseTrap 4 }

--  1.3.6.1.4.1.2011.5.25.345.2.3.5
		-- 1.3.6.1.4.1.2011.5.25.345.2.3.5
		hwVNEDatabaseServiceCPUOverload NOTIFICATION-TYPE
			OBJECTS { hwVNFCID, hwPID, hwServerLocator, hwClusterName}
			STATUS current
			DESCRIPTION
				"The database service CPU is overload. "
			::= { hwDatabaseTrap 5 }

--  1.3.6.1.4.1.2011.5.25.345.2.3.6
		-- 1.3.6.1.4.1.2011.5.25.345.2.3.6
		hwVNEDatabaseServiceCPUOverloadResume NOTIFICATION-TYPE
			OBJECTS { hwVNFCID, hwPID, hwServerLocator, hwClusterName}
			STATUS current
			DESCRIPTION
				"The CPU overload of database service is resumed. "
			::= { hwDatabaseTrap 6 }

--  1.3.6.1.4.1.2011.5.25.345.2.3.7
		-- 1.3.6.1.4.1.2011.5.25.345.2.3.7
		hwVNEDatabaseServiceMemoryOverload NOTIFICATION-TYPE
			OBJECTS { hwDatabaseMemoryUsage }
			STATUS current
			DESCRIPTION
				"The database service memory is overload."
			::= { hwDatabaseTrap 7 }

--  1.3.6.1.4.1.2011.5.25.345.2.3.8
		-- 1.3.6.1.4.1.2011.5.25.345.2.3.8
		hwVNEDatabaseServiceMemoryOverloadResume NOTIFICATION-TYPE
			OBJECTS { hwDatabaseMemoryUsage }
			STATUS current
			DESCRIPTION
				"The memory overload of database service is resumed."
			::= { hwDatabaseTrap 8 }

--  1.3.6.1.4.1.2011.5.25.345.2.4
		-- 1.3.6.1.4.1.2011.5.25.345.2.4
		hwCURESTrap OBJECT IDENTIFIER ::= { hwVNETrapMIB 4 }

--  1.3.6.1.4.1.2011.5.25.345.2.4.1
		-- 1.3.6.1.4.1.2011.5.25.345.2.4.1
		hwULPULicenseLimit NOTIFICATION-TYPE
			OBJECTS { hwLicenseNumbers, hwUlpuNumbers}
			STATUS current
			DESCRIPTION
				"The number of ULPU resources on the device reached the license limit."
			::= { hwCURESTrap 1 }

--  1.3.6.1.4.1.2011.5.25.345.2.4.2
		-- 1.3.6.1.4.1.2011.5.25.345.2.4.2
		hwULPULicenseLimitResume NOTIFICATION-TYPE
			OBJECTS { hwLicenseNumbers, hwUlpuNumbers}
			STATUS current
			DESCRIPTION
				"The number of ULPU resources fell below the upper license limit of the device again."
			::= { hwCURESTrap 2 }

--  1.3.6.1.4.1.2011.5.25.345.2.4.3
		-- 1.3.6.1.4.1.2011.5.25.345.2.4.3
		hwULPULicenseReachThreshold NOTIFICATION-TYPE
			OBJECTS { hwLicenseNumbers, hwUlpuNumbers,hwULPUThreshold}
			STATUS current
			DESCRIPTION
				"The number of ULPU resources on the device reached the license threshold."
			::= { hwCURESTrap 3 }

--  1.3.6.1.4.1.2011.5.25.345.2.4.4
		-- 1.3.6.1.4.1.2011.5.25.345.2.4.4
		hwULPULicenseReachThresholdResume NOTIFICATION-TYPE
			OBJECTS { hwLicenseNumbers, hwUlpuNumbers,hwULPUThreshold}
			STATUS current
			DESCRIPTION
				"The number of ULPU resources fell below the upper license threshold of the device again."
			::= { hwCURESTrap 4}


-- 1.3.6.1.4.1.2011.5.25.345.2.5
        hwCuInterfaceVersionTrap OBJECT IDENTIFIER ::= { hwVNETrapMIB 5 }

        -- 1.3.6.1.4.1.2011.5.25.345.2.5.1
        hwCuInterfaceVersionNegotiationFail NOTIFICATION-TYPE
        OBJECTS{ hwCuInterfaceVersionCp, hwUpid, hwCuInterfaceVersionUp, hwCuInterfaceVersionReason }
        STATUS current
        DESCRIPTION
            "Interface version negotiation failed."
        ::= { hwCuInterfaceVersionTrap 1 }

        -- 1.3.6.1.4.1.2011.5.25.345.2.5.2
        hwCuInterfaceVersionNegotiationFailResume NOTIFICATION-TYPE
        OBJECTS{ hwCuInterfaceVersionCp, hwUpid, hwCuInterfaceVersionUp, hwCuInterfaceVersionReason }
        STATUS current
        DESCRIPTION
            "Interface version negotiation failed resume."
        ::= { hwCuInterfaceVersionTrap 2 }

-- 1.3.6.1.4.1.2011.5.25.345.2.6
        hwCuConflictIpTrap OBJECT IDENTIFIER ::= { hwVNETrapMIB 6 }

        -- 1.3.6.1.4.1.2011.5.25.345.2.6.1
        hwCpConflictIPAlarm NOTIFICATION-TYPE
        OBJECTS{ hwCpPoolName, hwCpGateway, hwCpNetmask, hwUpid ,hwUpInterface}
        STATUS current
        DESCRIPTION
            "The gateway of CP address pool is conflict with the IP address of UP interface."
        ::= { hwCuConflictIpTrap 1 }

        -- 1.3.6.1.4.1.2011.5.25.345.2.6.2
        hwUpConflictIPAlarm NOTIFICATION-TYPE
        OBJECTS{ hwCpGateway, hwCpNetmask, hwUpInterface }
        STATUS current
        DESCRIPTION
            "The IP address of UP interface is conflict with the gateway of CP address pool."
        ::= { hwCuConflictIpTrap 2 }

-- 1.3.6.1.4.1.2011.5.25.345.2.7
        hwAntiSplitBrainTrap OBJECT IDENTIFIER ::= { hwVNETrapMIB 7 }

        -- 1.3.6.1.4.1.2011.5.25.345.2.7.1
        hwAntiSplitBrainFuncFailAlarm NOTIFICATION-TYPE
        OBJECTS { hwAntiSplitBrainFuncReason }
        STATUS current
        DESCRIPTION
            "The anti-split-brain function failed to be enabled."
        ::= { hwAntiSplitBrainTrap 1 }

        -- 1.3.6.1.4.1.2011.5.25.345.2.7.2
        hwAntiSplitBrainFuncFailResume NOTIFICATION-TYPE
        OBJECTS { hwAntiSplitBrainFuncReason }
        STATUS current
        DESCRIPTION
            "The anti-split-brain function is enabled."
        ::= { hwAntiSplitBrainTrap 2 }

        -- 1.3.6.1.4.1.2011.5.25.345.2.7.3
        hwAntiSplitBrainFuncReliabilityDeAlarm NOTIFICATION-TYPE
        OBJECTS { hwAntiSplitBrainFuncReason }
        STATUS current
        DESCRIPTION
            "Anti-split-brain function reliability deteriorates."
        ::= { hwAntiSplitBrainTrap 3 }

        -- 1.3.6.1.4.1.2011.5.25.345.2.7.4
        hwAntiSplitBrainFuncReliabilityDeResume NOTIFICATION-TYPE
        OBJECTS { hwAntiSplitBrainFuncReason }
        STATUS current
        DESCRIPTION
            "Anti-split-brain function reliability is resumed."
        ::= { hwAntiSplitBrainTrap 4 }

-- 1.3.6.1.4.1.2011.5.25.345.2.8
        hwDisasterRecoveryTrap OBJECT IDENTIFIER ::= { hwVNETrapMIB 8 }

        -- 1.3.6.1.4.1.2011.5.25.345.2.8.1
        hwHeartbeatSignalDisconnectAlarm NOTIFICATION-TYPE
        OBJECTS { hwSourceIpAddress, hwPeerIpAddress ,hwDisasterRecoveryReason }
        STATUS current
        DESCRIPTION
            "The heartbeat between VNEs is abnormal."
        ::= { hwDisasterRecoveryTrap 1 }

        -- 1.3.6.1.4.1.2011.5.25.345.2.8.2
        hwHeartbeatSignalDisconnectResume NOTIFICATION-TYPE
        OBJECTS { hwSourceIpAddress, hwPeerIpAddress ,hwDisasterRecoveryReason }
        STATUS current
        DESCRIPTION
            "The heartbeat between VNEs recovers."
        ::= { hwDisasterRecoveryTrap 2 }

-- 1.3.6.1.4.1.2011.5.25.345.2.9
        hwCuNotSupportServiceTrap OBJECT IDENTIFIER ::= { hwVNETrapMIB 9 }

        -- 1.3.6.1.4.1.2011.5.25.345.2.9.1
        hwCuNotSupportServiceAlarm NOTIFICATION-TYPE
        OBJECTS { hwNotSupportServiceName, hwNotSupportModule ,hwUpid }
        STATUS current
        DESCRIPTION
            "This object indicates the name of a service that does not support CU separation on the UP."
        ::= { hwCuNotSupportServiceTrap 1 }

        -- 1.3.6.1.4.1.2011.5.25.345.2.9.2
        hwCuUpBoardNotSupportBasAlarm NOTIFICATION-TYPE
        OBJECTS { hwUpid, hwUpSlotid }
        STATUS current
        DESCRIPTION
            "The upboard does not support BAS."
        ::= { hwCuNotSupportServiceTrap 2 }

        -- 1.3.6.1.4.1.2011.5.25.345.2.9.3
        hwCuUpBoardNotSupportBasAlarmResume NOTIFICATION-TYPE
        OBJECTS { hwUpid, hwUpSlotid }
        STATUS current
        DESCRIPTION
            "The upboard does not support BAS Resume."
        ::= { hwCuNotSupportServiceTrap 3 }

-- 1.3.6.1.4.1.2011.5.25.345.2.10
        hwWarmBackupNotEffectiveTrap OBJECT IDENTIFIER ::= { hwVNETrapMIB 10 }

        -- 1.3.6.1.4.1.2011.5.25.345.2.10.1
        hwWarmBackupNotEffectiveAlarm NOTIFICATION-TYPE
        OBJECTS { hwBackupNotEffectiveProfileName, hwBackupNotEffectiveReason }
        STATUS current
        DESCRIPTION
            "The function of warmbackup is not effective."
        ::= { hwWarmBackupNotEffectiveTrap 1 }

-- 1.3.6.1.4.1.2011.5.25.345.2.11
        hwDisasterRecoveryRoleTrap OBJECT IDENTIFIER ::= { hwVNETrapMIB 11 }

        -- 1.3.6.1.4.1.2011.5.25.345.2.11.1
        hwCuCpRoleConflict NOTIFICATION-TYPE
        OBJECTS { hwSourceIpAddress, hwPeerIpAddress }
        STATUS current
        DESCRIPTION
            "The disaster recovery roles of two CPs conflict."
        ::= { hwDisasterRecoveryRoleTrap 1 }

        -- 1.3.6.1.4.1.2011.5.25.345.2.11.2
        hwCuCpRoleConflictResume NOTIFICATION-TYPE
        OBJECTS { hwSourceIpAddress, hwPeerIpAddress }
        STATUS current
        DESCRIPTION
            "The conflict between the disaster recovery roles of two CPs is removed."
        ::= { hwDisasterRecoveryRoleTrap 2 }

-- 1.3.6.1.4.1.2011.5.25.345.3
		hwVNEMIBConformance OBJECT IDENTIFIER ::= { hwVNEMIB 3 }

--  1.3.6.1.4.1.2011.5.25.345.3.1
		-- 1.3.6.1.4.1.2011.5.25.345.3.1
		hwVNEMIBCompliances OBJECT IDENTIFIER ::= { hwVNEMIBConformance 1 }


-- 1.3.6.1.4.1.2011.5.25.345.3.1.1
		-- 1.3.6.1.4.1.2011.5.25.345.3.1.1
		hwVNEMIBCompliance MODULE-COMPLIANCE
			STATUS current
			DESCRIPTION
				"Compliance statement for agents that provide full support for
				hwVNETrapMIB."
			MODULE -- this module
				MANDATORY-GROUPS { hwVNEObjectGroup }
			::= { hwVNEMIBCompliances 1 }

--  1.3.6.1.4.1.2011.5.25.345.3.2
		-- 1.3.6.1.4.1.2011.5.25.345.3.2
		hwVNETrapGroups OBJECT IDENTIFIER ::= { hwVNEMIBConformance 2 }


--  1.3.6.1.4.1.2011.5.25.345.3.2.1
		-- 1.3.6.1.4.1.2011.5.25.345.3.2.1
		hwVNEObjectGroup OBJECT-GROUP
			OBJECTS { hwPlaneID, hwSubhealthyRate, hwPlaneFailReason, hwVmSlotId, hwVNFCID, hwPID, hwServerLocator, hwClusterName,hwLicenseNumbers,hwUlpuNumbers, hwCuInterfaceVersionCp, hwCuInterfaceVersionUp, hwCuInterfaceVersionReason, hwCpPoolName, hwCpGateway, hwCpNetmask, hwUpid ,hwUpInterface, hwUpSlotid}
			STATUS current
			DESCRIPTION
				"Group for VNE mib objects."
			::= { hwVNETrapGroups 1 }

--  1.3.6.1.4.1.2011.5.25.345.3.2.2
		-- 1.3.6.1.4.1.2011.5.25.345.3.2.2
		hwVNETrapGroup NOTIFICATION-GROUP
			NOTIFICATIONS { hwVFabPlaneFail, hwVFabPlaneFailResum, hwVFabHealthyFail, hwVFabHealthyFailResum, hwCreateVmFail, hwCreateVmFailResum, hwVNEDatabaseDisConnected, hwVNEDatabaseConnectionResume, hwVNEDatabaseServiceException, hwVNEDatabaseServiceResume, hwVNEDatabaseServiceCPUOverload, hwVNEDatabaseServiceCPUOverloadResume, hwVNEDatabaseServiceMemoryOverload, hwVNEDatabaseServiceMemoryOverloadResume,hwULPULicenseLimit,hwULPULicenseLimitResume, hwCuInterfaceVersionNegotiationFail, hwCuInterfaceVersionNegotiationFailResume,hwCpConflictIPAlarm,hwUpConflictIPAlarm, hwCuUpBoardNotSupportBasAlarm, hwCuUpBoardNotSupportBasAlarmResume, hwWarmBackupNotEffectiveAlarm,hwCuCpRoleConflict,hwCuCpRoleConflictResume}
			STATUS current
			DESCRIPTION
				"Group for all VNE mibs."
			::= { hwVNETrapGroups 2 }

	END

--
-- HUAWEI-VNE-MIB.my
--
