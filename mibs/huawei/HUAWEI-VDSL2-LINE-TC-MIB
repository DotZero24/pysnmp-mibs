-- ============================================================================
-- Copyright (C) 2013 by  HUAWEI TECHNOLOGIES. All rights reserved.
-- Description: VDSL text conventions and common defination.
-- Reference:
-- Version: V1.10
-- ============================================================================
    HUAWEI-VDSL2-LINE-TC-MIB DEFINITIONS ::= BEGIN
        IMPORTS
            MODULE-IDENTITY,TimeTicks
                FROM SNMPv2-SMI
            huaweiUtility
                FROM HUAWEI-MIB
            TEXTUAL-CONVENTION
                FROM SNMPv2-TC;

        vdslTCMIB MODULE-IDENTITY
            LAST-UPDATED "201307250000Z"
            ORGANIZATION "Fix-Net Dep, Huawei Technologies Co.,Ltd."
            CONTACT-INFO
                         "Huawei Industrial Base
                          Bantian, Longgang
                          Shenzhen 518129
                          People's Republic of China
                          Website: http://www.huawei.com
                          Email: support@huawei.com
                         "
            DESCRIPTION "VDSL text conventions and common defination."

--  Revision history

            REVISION    "201307250000Z"
            DESCRIPTION "V1.10, delete TEXTUAL-CONVENTION."

            REVISION    "201207200000Z"
            DESCRIPTION "V1.09, delete unnecessary en dashes."

            REVISION    "201205250000Z"
            DESCRIPTION "V1.08, added annexB998E17-M2x-A in Vdsl2PSDClassMask."

            REVISION    "201112030000Z"
            DESCRIPTION "V1.07, added g9935(78) in Vdsl2TransmissionModeType."

            REVISION    "201104070000Z"
            DESCRIPTION "V1.06, added annexB998ADE17-M2x-M in Vdsl2PsdLimitMask and Vdsl2PSDClassMask.
                         added annexA998-D-48, annexA998-D-128 in Vdsl2PSDClassMask.
                         modify the description of Vdsl2TIPsdClassMask, Vdsl2PSDClassMask."

            REVISION    "201102120000Z"
            DESCRIPTION "V1.05, modify syntax from annexB997E17-M2x-NUS0 to annexB997E17-M2x-A in Vdsl2PsdLimitMask and Vdsl2PSDClassMask."

            REVISION    "201012190000Z"
            DESCRIPTION "V1.04, added ginpNotSelected in Vdsl2InitResult for G.998.4 retransmission function.
                         added Vdsl2StatusRtxUsed type for G.998.4 retransmission function."

            REVISION    "201008100000Z"
            DESCRIPTION "V1.03, modifed for Mib standard."

            REVISION    "201004150000Z"
            DESCRIPTION "V1.02, added invalidValue(-1) for MIB standard, including Vdsl2ConfPmsForce, Vdsl2LineLdsf, Vdsl2PowerMngState, Vdsl2LastTransmittedState,
                         Vdsl2TIPsdClassMask, Vdsl2Actmode, Vdsl2SubProfiles, Vdsl2PSDClassMask, Vdsl2Profiles, and Vdsl2InitResult."

            REVISION    "201001260000Z"
            DESCRIPTION "V1.01, added tr165Mode in Vdsl2CfgMode."

            REVISION    "200604270000Z"
            DESCRIPTION "V1.00, initial version."
	        ::= { huaweiUtility 115 }



        Vdsl2Unit ::= TEXTUAL-CONVENTION
            STATUS      current
            DESCRIPTION
                "Identifies a transceiver as being either xtuc or
                 xtur.  An VDSL line consists of two transceivers, an xtuc
                 and an xtur.  Attributes with this syntax reference the two
                 sides of a line.  Specified as an INTEGER.
                 Options:
                 1. xtuc(1)  - Central site transceiver
                 2. xtur(2)  - Remote site transceiver
                "
            SYNTAX  INTEGER {
                    xtuc(1),
                    xtur(2)
                    }

        Vdsl2Direction ::= TEXTUAL-CONVENTION
            STATUS current
            DESCRIPTION
                "Identifies the direction of a band as being
                 either upstream or downstream.  Specified as an INTEGER.
                 Options:
                 1. upstream(1)    - Identifies upstream direction
                 2. downstream(2)  - Identifies downstream direction
                "
            SYNTAX INTEGER {
                upstream(1),
                downstream(2)
            }

        Vdsl2TransmissionModeType ::= TEXTUAL-CONVENTION
            STATUS      current
            DESCRIPTION
                 "A set of VDSL2 line transmission modes, with one bit
                  per mode.  The notes (F) and (L) denote Full-Rate
                  and Lite/splitterless respectively:
                  Bit 00 : Regional Std. (ANSI T1.413) (F)
                  Bit 01 : Regional Std. (ETSI DTS/TM06006) (F)
                  Bit 02 : G.992.1 POTS non-overlapped (F)
                  Bit 03 : G.992.1 POTS overlapped (F)
                  Bit 04 : G.992.1 ISDN non-overlapped (F)
                  Bit 05 : G.992.1 ISDN overlapped (F)
                  Bit 06 : G.992.1 TCM-ISDN non-overlapped (F)
                  Bit 07 : G.992.1 TCM-ISDN overlapped (F)
                  Bit 08 : G.992.2 POTS non-overlapped (L)
                  Bit 09 : G.992.2 POTS overlapped (L)
                  Bit 10 : G.992.2 with TCM-ISDN non-overlapped (L)
                  Bit 11 : G.992.2 with TCM-ISDN overlapped (L)
                  Bit 12 : G.992.1 TCM-ISDN symmetric (F) -- not in G.997.1
                  Bit 13-17: Reserved
                  Bit 18 : G.992.3 POTS non-overlapped (F)
                  Bit 19 : G.992.3 POTS overlapped (F)
                  Bit 20 : G.992.3 ISDN non-overlapped (F)
                  Bit 21 : G.992.3 ISDN overlapped (F)
                  Bit 22-23: Reserved
                  Bit 24 : G.992.4 POTS non-overlapped (L)
                  Bit 25 : G.992.4 POTS overlapped (L)
                  Bit 26-27: Reserved
                  Bit 28 : G.992.3 Annex I All-Digital non-overlapped (F)
                  Bit 29 : G.992.3 Annex I All-Digital overlapped (F)
                  Bit 30 : G.992.3 Annex J All-Digital non-overlapped (F)
                  Bit 31 : G.992.3 Annex J All-Digital overlapped (F)
                  Bit 32 : G.992.4 Annex I All-Digital non-overlapped (L)
                  Bit 33 : G.992.4 Annex I All-Digital overlapped (L)
                  Bit 34 : G.992.3 Annex L POTS non-overlapped, mode 1,
                                           wide U/S (F)
                  Bit 35 : G.992.3 Annex L POTS non-overlapped, mode 2,
                                           narrow U/S(F)
                  Bit 36 : G.992.3 Annex L POTS overlapped, mode 3,
                                           wide U/S (F)
                  Bit 37 : G.992.3 Annex L POTS overlapped, mode 4,
                                           narrow U/S (F)
                  Bit 38 : G.992.3 Annex M POTS non-overlapped (F)
                  Bit 39 : G.992.3 Annex M POTS overlapped (F)
                  Bit 40 : G.992.5 POTS non-overlapped (F)
                  Bit 41 : G.992.5 POTS overlapped (F)
                  Bit 42 : G.992.5 ISDN non-overlapped (F)
                  Bit 43 : G.992.5 ISDN overlapped (F)
                  Bit 44-45: Reserved
                  Bit 46 : G.992.5 Annex I All-Digital non-overlapped (F)
                  Bit 47 : G.992.5 Annex I All-Digital overlapped (F)
                  Bit 48 : G.992.5 Annex J All-Digital non-overlapped (F)
                  Bit 49 : G.992.5 Annex J All-Digital overlapped (F)
                  Bit 50 : G.992.5 Annex M POTS non-overlapped (F)
                  Bit 51 : G.992.5 Annex M POTS overlapped (F)
                  Bit 52-63: Reserved
                  Bit 64 : G.993.1
                  Bit 65~71 (vdsl1 reserved)
                  Bit 72 : G.993.2 Annex A POTS (F)
                  Bit 73 : G.993.2 Annex A ISDN (F)
                  Bit 74 : G.993.2 Annex B POTS (F)
                  Bit 75 : G.993.2 Annex B ISDN (F)
                  Bit 76 : G.993.2 Annex C POTS (F)
                  Bit 77 : G.993.2 Annex C ISDN (F)
                  Bit 78 : G.993.5
        	  Bit 79 : G.993.5 friendly Ds
        	  Bit 80 : Full G.993.5-friendly
                  Bit 81-127: Reserved
                 "
            SYNTAX      BITS {
                  ansit1413(0),
                  etsi(1),
                  g9921PotsNonOverlapped(2),
                  g9921PotsOverlapped(3),
                  g9921IsdnNonOverlapped(4),
                  g9921isdnOverlapped(5),
                  g9921tcmIsdnNonOverlapped(6),
                  g9921tcmIsdnOverlapped(7),
                  g9922potsNonOverlapeed(8),
                  g9922potsOverlapped(9),
                  g9922tcmIsdnNonOverlapped(10),
                  g9922tcmIsdnOverlapped(11),
                  g9921tcmIsdnSymmetric(12),
                  reserved1(13),
                  reserved2(14),
                  reserved3(15),
                  reserved4(16),
                  reserved5(17),
                  g9923PotsNonOverlapped(18),
                  g9923PotsOverlapped(19),
                  g9923IsdnNonOverlapped(20),
                  g9923isdnOverlapped(21),
                  reserved6(22),
                  reserved7(23),
                  g9924potsNonOverlapeed(24),
                  g9924potsOverlapped(25),
                  reserved8(26),
                  reserved9(27),
                  g9923AnnexIAllDigNonOverlapped(28),
                  g9923AnnexIAllDigOverlapped(29),
                  g9923AnnexJAllDigNonOverlapped(30),
                  g9923AnnexJAllDigOverlapped(31),
                  g9924AnnexIAllDigNonOverlapped(32),
                  g9924AnnexIAllDigOverlapped(33),
                  g9923AnnexLMode1NonOverlapped(34),
                  g9923AnnexLMode2NonOverlapped(35),
                  g9923AnnexLMode3Overlapped(36),
                  g9923AnnexLMode4Overlapped(37),
                  g9923AnnexMPotsNonOverlapped(38),
                  g9923AnnexMPotsOverlapped(39),
                  g9925PotsNonOverlapped(40),
                  g9925PotsOverlapped(41),
                  g9925IsdnNonOverlapped(42),
                  g9925isdnOverlapped(43),
                  reserved10(44),
                  reserved11(45),
                  g9925AnnexIAllDigNonOverlapped(46),
                  g9925AnnexIAllDigOverlapped(47),
                  g9925AnnexJAllDigNonOverlapped(48),
                  g9925AnnexJAllDigOverlapped(49),
                  g9925AnnexMPotsNonOverlapped(50),
                  g9925AnnexMPotsOverlapped(51),
                  reserved12(52),
                  reserved13(53),
                  reserved14(54),
                  reserved15(55),
                  reserved16(56),
                  reserved17(57),
                  reserved18(58),
                  reserved19(59),
                  reserved20(60),
                  reserved21(61),
                  reserved22(62),
                  reserved23(63),
        	  reserved24(64),
        	  reserved25(65),
        	  reserved26(66),
        	  reserved27(67),
        	  reserved28(68),
        	  reserved29(69),
        	  reserved30(70),
        	  reserved31(71),
        	  g9932AnnexAPots(72),
        	  g9932AnnexAIsdn(73),
        	  g9932AnnexBPots(74),
        	  g9932AnnexBIsdn(75),
        	  g9932AnnexCPots(76),
        	  g9932AnnexCIsdn(77),
        	  g9935(78),
        	  g9935FriendlyDs(79),
        	  g9935FullFriendly(80),
        	  reserved32(81)
            }

        Vdsl2RaMode ::= TEXTUAL-CONVENTION
            STATUS      current
            DESCRIPTION
                "Specifies the rate adaptation behavior for the line.
                 Options:
                 1. manual (1)   - No Rate-Adaptation.  The initialization
                                   process attempts to synchronize to a
                                   specified rate.
                 2. rainit (2)   - Rate-Adaptation during initialization process
                                   only, which attempts to synchronize to a rate
                                   between minimum and maximum specified values.
                 3. dynamic (3)  - Rate-Adaptation during show time
                "
            SYNTAX      INTEGER {
                 manual(1),
                 raInit(2),
                 dynamic(3)
            }

        Vdsl2InitResult ::= TEXTUAL-CONVENTION
            STATUS      current
            DESCRIPTION
                "Specifies the result of full initialization attempt.
                 Options:
                 1. noFail (0)            - Successful initialization
                 2. configError (1)       - Configuration failure
                 3. configNotFeasible (2) - Configuration details not supported
                 4. commFail (3)          - Communication failure
                 5. noPeerXtu (4)         - Peer xTU not detected
                 6. otherCause (5)        - Other initialization failure reason
                 7. ginpNotSelected(6)    - G.998.4 Retransmission mode was not selected
                                            while RTX_MODE = FORCED or with RTX_MODE = RTX_TESTMODE
                 8. invalidValue(-1)      - Invalid value
                "
            SYNTAX      INTEGER {
                noFail(0),
                configError(1),
                configNotFeasible(2),
                commFail(3),
                noPeerXtu(4),
                otherCause(5),
                ginpNotSelected(6),
                invalidValue(-1)
            }

        Vdsl2OperationModes ::= TEXTUAL-CONVENTION
            STATUS      current
            DESCRIPTION
                "The VDSL2 management model specified includes an VDSL Mode
                 attribute which identifies an instance of VDSL Mode-Specific
                 PSD Configuration object in the VDSL Line Profile.  The
                 following classes of VDSL operating mode are defined.
                 Options:
                 1. defMode (1)             - Indicates defMode
                 2. adsl (2)                - Indicates adsl
                 3. adsl2Pots (3)           - Indicates adsl2Pots
                 4. adsl2Isdn (4)           - Indicates adsl2Isdn
                 5. adsl2PlusPots (5)       - Indicates adsl2PlusPots
                 6. adsl2PlusIsdn (6)       - Indicates adsl2PlusIsdn
                 7. adsl2ReachExtended (7)  - Indicates adsl2ReachExtended
                 8. vdsl2Pots (8)           - Indicates vdsl2Pots
                 9. vdsl2Isdn (9)           - Indicates vdsl2Isdn
                "
            SYNTAX      INTEGER {
                defMode (1),
                adsl (2),
                adsl2Pots (3),
                adsl2Isdn (4),
                adsl2PlusPots (5),
                adsl2PlusIsdn (6),
                adsl2ReachExtended (7),
                vdsl2Pots (8),
                vdsl2Isdn (9)
                       }

        Vdsl2PowerMngState ::= TEXTUAL-CONVENTION
            STATUS      current
            DESCRIPTION
                "Attributes with this syntax uniquely identify each power
                 management state defined for the VDSL2 link.
                 Options:
                 1. l0(0)             - Full power management state
                 2. l1(1)             - Low power management state (for G.992.2)
                 3. l2(2)             - Low power management state (for G.992.3,
                                        G.992.4, and G.992.5)
                 4. l3(3)             - Idle power management state
                 5. invalidValue(-1)  - Invalid value
                "
            SYNTAX      INTEGER {
                l0(0),
                l1(1),
                l2(2),
                l3(3),
                invalidValue(-1)
            }

        Vdsl2ConfPmsForce ::= TEXTUAL-CONVENTION
            STATUS      current
            DESCRIPTION
                "Attributes with this syntax are configuration parameters
                 that reference the desired power management state for the
                 VDSL2 link.
                 Options:
                 1. l3toL0(1)         - Perform a transition from L3 to L0
                                        (Full power management state)
                 2. l0toL2(2)         - Perform a transition from L0 to L2
                                        (Low power management state)
                 3. l0orL2toL3(3)     - Perform a transition into L3 (Idle
                                        power management state)
                 4. invalidValue(-1)    Invalid value
                "
            SYNTAX      INTEGER {
                l3toL0 (0),
                l0toL2 (2),
                l0orL2toL3 (3),
                invalidValue(-1)
            }

        Vdsl2LConfProfPmMode ::= TEXTUAL-CONVENTION
            STATUS current
            DESCRIPTION
              "Attributes with this syntax are configuration parameters
               that reference the power modes/states into which the xTU-C or
               xTU-R may autonomously transit.

               It is a BITS structure that allows control of the following
               transit options:
               1. allowTransitionsToIdle(0)      - xTU may autonomously transit
                                                   to idle (L3) state.
               2. allowTransitionsToLowPower(1)  - xTU may autonomously transit
                                                   to low-power (L2) state.
              "
            SYNTAX BITS {
               allowTransitionsToIdle(0),
               allowTransitionsToLowPower(1)
             }

        Vdsl2LineLdsf ::= TEXTUAL-CONVENTION
            STATUS current
            DESCRIPTION
                "Attributes with this syntax are configuration parameters
                 that control the Loop Diagnostic mode for the VDSL2 link.
                 Options:
                 1. inhibit (0)      - Inhibit Loop Diagnostic mode
                 2. force   (1)      - Force/Initiate Loop Diagnostic mode'
                 3. invalidValue(-1) - Invalid value
                "
            SYNTAX INTEGER {
                inhibit(0),
                force(1),
                invalidValue(-1)
            }

        Vdsl2LdsfResult ::= TEXTUAL-CONVENTION
            STATUS current
            DESCRIPTION
                "Possible failure reasons associated with performing
                 Dual Ended Loop Test (DELT) on a DSL line.
                 Options:
                 1. none        (1)    - The default value in case LDSF was never
                                         requested for the associated line.
                 2. success     (2)    - The recent command completed
                                         successfully.
                 3. inProgress  (3)    - The Loop Diagnostics process is in
                                         progress.
                 4. unsupported (4)    - The NE or the line card doesn't support
                                         LDSF.
                 5. cannotRun   (5)    - The NE cannot initiate the command, due
                                         to a non specific reason.
                 6. aborted     (6)    - The Loop Diagnostics process aborted.
                 7. failed      (7)    - The Loop Diagnostics process failed.
                 8. illegalMode (8)    - The NE cannot initiate the command, due
                                         to the specific mode of the relevant
                                         line.
                 9. adminUp     (9)    - The NE cannot initiate the command, as
                                         the relevant line is administratively
                                         'Up'.
                 10. tableFull   (10)  - The NE cannot initiate the command, due
                                         to reaching the maximum number of rows
                                         in the results table.
                 11. noResources (11)  - The NE cannot initiate the command, due
                                         to lack of internal memory resources.
                "
             SYNTAX INTEGER {
                  none (1),
                  success (2),
                  inProgress (3),
                  unsupported (4),
                  cannotRun (5),
                  aborted (6),
                  failed (7),
                  illegalMode (8),
                  adminUp (9),
                  tableFull (10),
                  noResources (11)
             }

        Vdsl2Actmode ::= TEXTUAL-CONVENTION
            STATUS current
            DESCRIPTION
                "Possible actived mode after training between co and cpe.
                 Options:
                 1. adsl        (1)    - Indicates adsl
                 2. adsl2       (2)    - Indicates adsl2
                 3. adsl2plus   (3)    - Indicates adsl2plus
                 4. vdsl        (4)    - Indicates vdsl
                 5. vdsl2       (5)    - Indicates vdsl2
                 6. invalidValue(-1)   - Indicates invalid value
                "
            SYNTAX INTEGER {
                adsl (1),
                adsl2 (2),
                adsl2plus (3),
                vdsl (4),
                vdsl2 (5),
                invalidValue(-1)
            }

        Vdsl2SymbolProtectionDs ::= TEXTUAL-CONVENTION
            STATUS      current
            DESCRIPTION
                "Attributes with this syntax are configuration parameters
                 that reference the minimum length impulse noise protection
                 (INP) in terms of number of symbols.  The possible values are:
                 noProtection (i.e., INP not required), halfSymbol (i.e., INP
                 length is 1/2 symbol), and 1-16 symbols in steps of 1 symbol.
                 Options:
                 1. noProtection (1)         - Indicates that the INP value is 0
                 2. halfSymbol (2)           - Indicates that the INP value is 0.5
                 3. singleSymbol (3)         - Indicates that the INP value is 1
                 4. twoSymbols (4)           - Indicates that the INP value is 2
                 5. threeSymbols (5)         - Indicates that the INP value is 3
                 6. fourSymbols (6)          - Indicates that the INP value is 4
                 7. fiveSymbols (7)          - Indicates that the INP value is 5
                 8. sixSymbols (8)           - Indicates that the INP value is 6
                 9. sevenSymbols (9)         - Indicates that the INP value is 7
                 10. eightSymbols (10)       - Indicates that the INP value is 8
                 11. nineSymbols (11)        - Indicates that the INP value is 9
                 12. tenSymbols (12)         - Indicates that the INP value is 10
                 13. elevenSymbols (13)      - Indicates that the INP value is 11
                 14. twelveSymbols (14)      - Indicates that the INP value is 12
                 15. thirteenSymbols (15)    - Indicates that the INP value is 13
                 16. fourteenSymbols (16)    - Indicates that the INP value is 14
                 17. fifteenSymbols (17)     - Indicates that the INP value is 15
                 18. sixteenSymbols (18)     - Indicates that the INP value is 16
                "
            SYNTAX      INTEGER {
                 noProtection (1),
                 halfSymbol (2),
                 singleSymbol (3),
                 twoSymbols (4),
                 threeSymbols (5),
                 fourSymbols (6),
                 fiveSymbols (7),
                 sixSymbols (8),
                 sevenSymbols (9),
                 eightSymbols (10),
                 nineSymbols (11),
                 tenSymbols (12),
                 elevenSymbols (13),
                 twelveSymbols (14),
                 thirteenSymbols (15),
                 fourteenSymbols (16),
                 fifteenSymbols (17),
                 sixteenSymbols (18)
            }

        Vdsl2SymbolProtectionUs ::= TEXTUAL-CONVENTION
            STATUS      current
            DESCRIPTION
                "Attributes with this syntax are configuration parameters
                 that reference the minimum length impulse noise protection
                 (INP) in terms of number of symbols.  The possible values are:
                 noProtection (i.e., INP not required), halfSymbol (i.e., INP
                 length is 1/2 symbol), and 1-16 symbols in steps of 1 symbol.
                 Options:
                 1. noProtection (1)         - Indicates that the INP value is 0
                 2. halfSymbol (2)           - Indicates that the INP value is 0.5
                 3. singleSymbol (3)         - Indicates that the INP value is 1
                 4. twoSymbols (4)           - Indicates that the INP value is 2
                 5. threeSymbols (5)         - Indicates that the INP value is 3
                 6. fourSymbols (6)          - Indicates that the INP value is 4
                 7. fiveSymbols (7)          - Indicates that the INP value is 5
                 8. sixSymbols (8)           - Indicates that the INP value is 6
                 9. sevenSymbols (9)         - Indicates that the INP value is 7
                 10. eightSymbols (10)       - Indicates that the INP value is 8
                 11. nineSymbols (11)        - Indicates that the INP value is 9
                 12. tenSymbols (12)         - Indicates that the INP value is 10
                 13. elevenSymbols (13)      - Indicates that the INP value is 11
                 14. twelveSymbols (14)      - Indicates that the INP value is 12
                 15. thirteenSymbols (15)    - Indicates that the INP value is 13
                 16. fourteenSymbols (16)    - Indicates that the INP value is 14
                 17. fifteenSymbols (17)     - Indicates that the INP value is 15
                 18. sixteenSymbols (18)     - Indicates that the INP value is 16
                "
            SYNTAX      INTEGER {
                 noProtection (1),
                 halfSymbol (2),
                 singleSymbol (3),
                 twoSymbols (4),
                 threeSymbols (5),
                 fourSymbols (6),
                 fiveSymbols (7),
                 sixSymbols (8),
                 sevenSymbols (9),
                 eightSymbols (10),
                 nineSymbols (11),
                 tenSymbols (12),
                 elevenSymbols (13),
                 twelveSymbols (14),
                 thirteenSymbols (15),
                 fourteenSymbols (16),
                 fifteenSymbols (17),
                 sixteenSymbols (18)
            }

        Vdsl2MaxBer ::= TEXTUAL-CONVENTION
            STATUS      current
            DESCRIPTION
                "Attributes with this syntax are configuration parameters
                 that reference the maximum Bit Error Rate (BER).
                 Options:
                 1. eminus3 (1)  - Maximum BER=E^-3
                 2. eminus5 (2)  - Maximum BER=E^-5
                 3. eminus7 (3)  - Maximum BER=E^-7
                "
            SYNTAX      INTEGER {
                 eminus3(1),
                 eminus5(2),
                 eminus7(3)
            }

        Vdsl2ScMaskDs ::= TEXTUAL-CONVENTION
            STATUS      current
            DESCRIPTION
                "Each one of the 512 bits in this OCTET
                 STRING array represents the corresponding bin
                 in the downstream direction.  A value of one
                 indicates that the bin is not in use.
                "
            SYNTAX      OCTET STRING (SIZE(0..64))

        Vdsl2ScMaskUs ::= TEXTUAL-CONVENTION
            STATUS      current
            DESCRIPTION
                "Each one of the 64 bits in this OCTET
                 STRING array represents the corresponding bin
                 in the downstream direction.  A value of one
                 indicates that the bin is not in use.
                "
            SYNTAX      OCTET STRING (SIZE(0..8))

        Vdsl2Rfi ::= TEXTUAL-CONVENTION
            STATUS      current
            DESCRIPTION
                "Each one of the 4096 bits in this OCTET
                 STRING array represents the corresponding bin
                 in the downstream direction.  A value of one
                 indicates that the bin is part of a notch
                 filter.
                "
            SYNTAX      OCTET STRING (SIZE(0..512))

        Vdsl2vdsltoneblackout ::= TEXTUAL-CONVENTION
            STATUS      current
            DESCRIPTION
                "Each one of the 4096 bits in this OCTET
                 STRING array represents the corresponding bin
                 of the subcarriers.  A value of one
                 indicates that the bin is part of subcarriermask.
                "
            SYNTAX      OCTET STRING (SIZE(0..512))

        Vdsl2PsdMaskDs ::= TEXTUAL-CONVENTION
            STATUS      current
            DESCRIPTION
                "This is a structure that represents up to
                 32 PSD Mask breakpoints.
                 Each breakpoint occupies 3 octets: The first
                 two octets hold the index of the sub-carrier
                 associated with the breakpoint.  The third octet
                 holds the PSD reduction at the breakpoint from 0
                 (0dBm/Hz) to 255 (-127.5 dBm/Hz) using units of
                 0.5dBm/Hz.
                "
            SYNTAX      OCTET STRING (SIZE(0..96))

        Vdsl2PsdMaskUs ::= TEXTUAL-CONVENTION
            STATUS      current
            DESCRIPTION
                "This is a structure that represents up to
                 16 PSD Mask breakpoints.
                 Each breakpoint occupies 3 octets: The first
                 two octets hold the index of the sub-carrier
                 associated with the breakpoint.  The third octet
                 holds the PSD reduction at the breakpoint from 0
                 (0dBm/Hz) to 255 (-127.5 dBm/Hz) using units of
                 0.5dBm/Hz.
                "
            SYNTAX      OCTET STRING (SIZE(0..48))

        Vdsl2SubProfiles ::= TEXTUAL-CONVENTION
            STATUS      current
            DESCRIPTION
                "Attributes with this syntax are configuration parameters
                 that reference the G.993.2 profiles to be allowed by the near-end xTU on this line.
                 Options:
                 1. profile8a(1)     - Profile 8a
                 2. profile8b(2)     - Profile 8b
                 3. profile8c(3)     - Profile 8c
                 4. profile8d(4)     - Profile 8d
                 5. profile12a(5)    - Profile 12a
                 6. profile12b(6)    - Profile 12b
                 7. profile17a(7)    - Profile 17a
                 8. profile30a(8)    - Profile 30a
                 9. invalidValue(-1) - Invalid value
                "
            SYNTAX      INTEGER {
                 profile8a(1),
                 profile8b(2),
                 profile8c(3),
                 profile8d(4),
                 profile12a(5),
                 profile12b(6),
                 profile17a(7),
                 profile30a(8),
                 invalidValue(-1)
            }

        Vdsl2SubProfilesWeight ::= TEXTUAL-CONVENTION
            STATUS      current
            DESCRIPTION
                "Attributes with this syntax are configuration parameters
                 that reference the G.993.2 profiles to be allowed by the near-end xTU on this line.
                 Options:
                 1. priorityWeight1(1)   - Indicates priority-weight1
                 2. priorityWeight2(2)   - Indicates priority-weight2
                 3. priorityWeight3(3)   - Indicates priority-weight3
                "
            SYNTAX      INTEGER {
                 priorityWeight1(1),
                 priorityWeight2(2),
                 priorityWeight3(3)
            }

        Vdsl2Us0PsdMask ::= TEXTUAL-CONVENTION
            STATUS      current
            DESCRIPTION
                "This parameter contains the US0 PSD masks to be allowed by the near-end xTU on the line.
                 This parameter is only defined for G.993.2 Annex A.
                 Options:
                 1. adlu32Eu32(1)    - ADLU-32/EU-32
                 2. adlu36Eu36(2)    - ADLU-36/EU-36
                 3. adlu40Eu40(3)    - ADLU-40/EU-40
                 4. adlu44Eu44(4)    - ADLU-44/EU-44
                 5. adlu48Eu48(5)    - ADLU-48/EU-48
                 6. adlu52Eu52(6)    - ADLU-52/EU-52
                 7. adlu56Eu56(7)    - ADLU-56/EU-56
                 8. adlu60Eu60(8)    - ADLU-60/EU-60
                 9. adlu64Eu64(9)    - ADLU-64/EU-64
                 10.adlu128Eu128(10) - ADLU-128/EU-128
                "
            SYNTAX      INTEGER {
                 adlu32Eu32(1),
                 adlu36Eu36(2),
                 adlu40Eu40(3),
                 adlu44Eu44(4),
                 adlu48Eu48(5),
                 adlu52Eu52(6),
                 adlu56Eu56(7),
                 adlu60Eu60(8),
                 adlu64Eu64(9),
                 adlu128Eu128(10)
            }

        Vdsl2UpsPsdMaskSelection ::= TEXTUAL-CONVENTION
            STATUS      current
            DESCRIPTION
                "This is a structure that represents up to
                 16 PSD Mask breakpoints.
                 Each breakpoint occupies 3 octets: The first
                 two octets hold the index of the sub-carrier
                 associated with the breakpoint.  The third octet
                 holds the PSD reduction at the breakpoint from 0
                 (0dBm/Hz) to 255 (-127.5 dBm/Hz) using units of
                 0.5dBm/Hz.
                 Options:
                 1. adlu32Eu32(1)    - ADLU-32/EU-32
                 2. adlu36Eu36(2)    - ADLU-36/EU-36
                 3. adlu40Eu40(3)    - ADLU-40/EU-40
                 4. adlu44Eu44(4)    - ADLU-44/EU-44
                 5. adlu48Eu48(5)    - ADLU-48/EU-48
                 6. adlu52Eu52(6)    - ADLU-52/EU-52
                 7. adlu56Eu56(7)    - ADLU-56/EU-56
                 8. adlu60Eu60(8)    - ADLU-60/EU-60
                 9. adlu64Eu64(9)    - ADLU-64/EU-64
                "
            SYNTAX      INTEGER {
                 adlu32Eu32(1),
                 adlu36Eu36(2),
                 adlu40Eu40(3),
                 adlu44Eu44(4),
                 adlu48Eu48(5),
                 adlu52Eu52(6),
                 adlu56Eu56(7),
                 adlu60Eu60(8),
                 adlu64Eu64(9)
            }

        Vdsl2TIPsdClassMask ::= TEXTUAL-CONVENTION
            STATUS      current
            DESCRIPTION
                "VDSL2 PSD Mask Class.
                 The limit Power Spectral Density masks are grouped in
                 the following PSD mask classes:
                 Class 998     Annex A: D-32, D-64, D-48, D-128.
                 Class 997-M1c Annex B: 997-M1c-A-7.
                 Class 997-M1x Annex B: 997-M1x-M-8, 997-M1x-M.
                 Class 997-M2x Annex B: 997-M2x-M-8, 997-M2x-A, 997-M2x-M.
                 Class 998-M1x Annex B: 998-M1x-A, 998-M1x-B, 998-M1x-NUS0.
                 Class 998-M2x Annex B: 998-M2x-A, 998-M2x-M, 998-M2x-B,
                                        998-M2x-NUS0.
                 Class 998     Annex C: POTS (C.2.1.1/G.993.2),
                                        TCM-ISDN (C.2.1.2/G.993.2).
                "

            SYNTAX      INTEGER {
                 none(1),
                 a998B997M1cC998(2),
                 b997M1x(3),
                 b997M2x(4),
                 b998M1x(5),
                 b998M2x(6),
                 invalidValue(-1)
            }

        Vdsl2PsdLimitMask ::= TEXTUAL-CONVENTION
            STATUS      current
            DESCRIPTION
                "The G.993.2 limit PSD mask for each class of profile.
                 The profiles are grouped in following profile classes:
                 - Class 8: Profiles 8a, 8b, 8c, 8d
                 - Class 12: Profiles 12a, 12b
                 - Class 17: Profile 17a
                 - Class 30: Profile 30a.
                "

            SYNTAX      INTEGER {
        	annexA998-D-32              (1),
            	annexA998-D-64              (2),
        	annexB997-M1c-A-7           (3),
        	annexB997-M1x-M-8           (4),
            	annexB997-M1x-M             (5),
            	annexB997-M2x-M-8           (6),
            	annexB997-M2x-A             (7),
            	annexB997-M2x-M             (8),
            	annexB998-M1x-A             (9),
            	annexB998-M1x-B             (10),
            	annexB998-M1x-NUS0          (11),
            	annexB998-M2x-A             (12),
            	annexB998-M2x-M             (13),
            	annexB998-M2x-B             (14),
            	annexB998-M2x-NUS0          (15),
            	annexBHPE17-M1-NUS0         (16),
            	annexBHPE30-M1-NUS0         (17),
            	annexB997E17-M2x-A          (18),
            	annexB997E30-M2x-NUS0       (19),
            	annexB998E17-M2x-NUS0       (20),
            	annexB998E17-M2x-NUS0-M     (21),
            	annexB998ADE17-M2x-NUS0-M   (22),
            	annexB998ADE17-M2x-B        (23),
            	annexB998E30-M2x-NUS0       (24),
            	annexB998E30-M2x-NUS0-M     (25),
            	annexB998ADE30-M2x-NUS0-M   (26),
            	annexB998ADE17-M2x-A        (27),
            	annexB998ADE30-M2x-NUS0-A   (28),
            	annexA998-D-48              (29),
            	annexA998-D-128             (30),
            	annexB998ADE17-M2x-M        (31)
            }

        Vdsl2Us0Disable ::= TEXTUAL-CONVENTION
            STATUS      current
            DESCRIPTION
                "For each limit PSD mask enabled in the LIMITMASK parameter,
                 a bit shall indicate if US0 is disabled. The disabling parameter is coded as a bit-map.
                 The bit is set to 1 if US0 is disabled for the associated limit mask.
                 The bit-map has the same structure than the LIMITMASK parameter.
                 Options:
                 1. unused(1)    - Indicates unused
                 2. used(2)      - Indicates used
                "
            SYNTAX      INTEGER {
                 unused(1),
                 used(2)
            }

        Vdsl2DpboEpsd ::= TEXTUAL-CONVENTION
            STATUS      current
            DESCRIPTION
                "This is a structure that represents up to
                 16 PSD Mask breakpoints.
                 Each breakpoint occupies 3 octets: The first
                 two octets hold the index of the sub-carrier
                 associated with the breakpoint.  The third octet
                 holds the PSD reduction at the breakpoint from 0
                 (0dBm/Hz) to 255 (-127.5dBm/Hz) using units of
                 0.5dBm/Hz.Valid values are in the range 0 to
                 190 (0 to -95dBm/Hz).
                "
            SYNTAX      OCTET STRING (SIZE(0..48))

        Vdsl2DpboEscm ::= TEXTUAL-CONVENTION
            STATUS      current
            DESCRIPTION
                "Octets 0+1 DPBOESCMA
                 Octets 2+3 DPBOESCMB
                 Octets 4+5 DPBOESCMC
                 Each scalar value from 0 to 640
                "
            SYNTAX      OCTET STRING (SIZE(0..6))

        Vdsl2UpboPsdBand ::= TEXTUAL-CONVENTION
            STATUS      current
            DESCRIPTION
                "Octets 0+1 -   a[0]
                 Octets 2+3 -   b[0]
                 Octets 4+5 -   a[1]
                 Octets 6+7 -   b[1]
                 Octets 8+9 -   a[2]
                 Octets 10+11 - b[2]
                 Octets 12+13 - a[3]
                 Octets 14+15 - b[3]
                 Octets 16+17 - a[4]
                 Octets 18+19 - b[4]
                "
            SYNTAX      OCTET STRING (SIZE(0..20))

        Vdsl2UpboKl0RefBand ::= TEXTUAL-CONVENTION
            STATUS      current
            DESCRIPTION
               "Octets 0+1 - length[1]
                Octets 2+3 - length[2]
                Octets 4+5 - length[3]
                Octets 6+7 - length[4]
               "
            SYNTAX      OCTET STRING (SIZE(0..8))

        Vdsl2UpboKlf ::= TEXTUAL-CONVENTION
            STATUS current
            DESCRIPTION
                "Options:
                 1.forced(1)      - Indicates UPBOKL is forced by the VTU-O
                 2.auto(2)        - Indicates UPBOKL shall be autonomously selected by the VTU-O
                "
            SYNTAX INTEGER {
                   forced(1),
                   auto(2)}

        Vdsl2BitSwap ::= TEXTUAL-CONVENTION
            STATUS current
            DESCRIPTION
                "Enables or disables the bit swap upstream or downstream of a line.
                 Options:
                 1. disable(1)  - Disables the bit swap upstream or downstream of a line
                 2. enable(2)   - Enables the bit swap upstream or downstream of a line
                "
            SYNTAX INTEGER {
                   disable(1),
                   enable(2)
            }

        Vdsl2UpboBoostMode ::= TEXTUAL-CONVENTION
            STATUS current
            DESCRIPTION
                "Options:
                 1. disable(1)  - The Equalized FEXT UPBO method is not supported
                 2. enable(2)   - The Equalized FEXT UPBO method is supported
            	"
            SYNTAX INTEGER {
                disable(1),
                enable(2)
            }

        Vdsl2ProfSwitchType ::= TEXTUAL-CONVENTION
            STATUS current
            DESCRIPTION
                "Enables or disables the bit swap upstream or downstream of a line.
                 Options:
                 1. enable(1)   - Enables the bit swap upstream or downstream of a line
                 2. disable(2)  - Disables the bit swap upstream or downstream of a line
                "
            SYNTAX INTEGER {
                   enable(1),
                   disable(2)
            }

        Vdsl2VirtualNoise ::= TEXTUAL-CONVENTION
            STATUS current
            DESCRIPTION
                "Enables or disables the Virtual Noise upstream or downstream of a line.
                 Options:
                 1. disable(1) - Disables the Virtual Noise upstream or downstream of a line
                 2. enable(2)  - Enables the Virtual Noise upstream or downstream of a line
                "
            SYNTAX INTEGER {
                   disable(1),
                   enable(2)
            }

        Vdsl2AutoProfile ::= TEXTUAL-CONVENTION
            STATUS current
            DESCRIPTION
                "Enables or disables the auto profile of a line.
                 Options:
                 1. disable(1) - Disables the auto profile of a line
                 2. enable(2)  - Enables the auto profile of a line
                "
            SYNTAX INTEGER {
                disable(1),
                enable(2)
            }

        Vdsl2VirtualNoiseDs ::= TEXTUAL-CONVENTION
            STATUS      current
            DESCRIPTION
                "This is a structure that represents up to
                 32 Virtual Noise breakpoints.
                 Each breakpoint occupies 3 octets: The first
                 two octets hold the index of the sub-carrier
                 associated with the breakpoint.  The third octet
                 holds the PSD reduction at the breakpoint from 0
                 (0dBm/Hz) to 255 (-127.5 dBm/Hz) using units of
                 0.5dBm/Hz.
                "
            SYNTAX      OCTET STRING (SIZE(0..96))

        Vdsl2VirtualNoiseUs ::= TEXTUAL-CONVENTION
            STATUS      current
            DESCRIPTION
                "This is a structure that represents up to
                 16 Virtual Noise breakpoints.
                 Each breakpoint occupies 3 octets: The first
                 two octets hold the index of the sub-carrier
                 associated with the breakpoint.  The third octet
                 holds the PSD reduction at the breakpoint from 0
                 (0dBm/Hz) to 255 (-127.5 dBm/Hz) using units of
                 0.5dBm/Hz.
                "
            SYNTAX      OCTET STRING (SIZE(0..48))


        Vdsl2Tssi ::= TEXTUAL-CONVENTION
            STATUS      current
            DESCRIPTION
                "This is a structure that represents up to
                 32 transmit spectrum shaping (TSSi) breakpoints.
                 Each breakpoint occupies 3 octets: The first
                 two octets hold the index of the sub-carrier
                 associated with the breakpoint.  The third octet
                 holds the shaping parameter at the breakpoint. It
                 is a value from 0 to 127 (units of -0.5dB). The
                 special value 127 indicates that the sub-carrier
                 is not transmitted.
                "
            SYNTAX      OCTET STRING (SIZE(0..96))

        Vdsl2BandPlan ::= TEXTUAL-CONVENTION
            STATUS      current
            DESCRIPTION
                "Huawei defined. Vdsl2 bandplay type."
            SYNTAX      OCTET STRING (SIZE(0..96))

        Vdsl2LastTransmittedState ::= TEXTUAL-CONVENTION
            STATUS current
            DESCRIPTION
                "This parameter represents the last successful
                 transmitted initialization state in the last full
                 initialization performed on the line.
                "
            SYNTAX      INTEGER {
                 xtucG9941(0),
                 xtucQuiet1(1),
                 xtucComb1(2),
                 xtucQuiet2(3),
                 xtucComb2(4),
                 xtucIcomb1(5),
                 xtucLineprob(6),
                 xtucQuiet3(7),
                 xtucComb3(8),
                 xtucIComb2(9),
                 xtucMsgfmt(10),
                 xtucMsgpcb(11),
                 xtucQuiet4(12),
                 xtucReverb1(13),
                 xtucTref1(14),
                 xtucReverb2(15),
                 xtucEct(16),
                 xtucReverb3(17),
                 xtucTref2(18),
                 xtucReverb4(19),
                 xtucSegue1(20),
                 xtucMsg1(21),
                 xtucReverb5(22),
                 xtucSegue2(23),
                 xtucMedley(24),
                 xtucExchmarker(25),
                 xtucMsg2(26),
                 xtucReverb6(27),
                 xtucSegue3(28),
                 xtucParams(29),
                 xtucReverb7(30),
                 xtucSegue4(31),
                 xtucShowtime(32),
                 --
                 xturG9941(100),
                 xturQuiet1(101),
                 xturComb1(102),
                 xturQuiet2(103),
                 xturComb2(104),
                 xturIcomb1(105),
                 xturLineprob(106),
                 xturQuiet3(107),
                 xturComb3(108),
                 xturIcomb2(109),
                 xturMsgfmt(110),
                 xturMsgpcb(111),
                 xturReverb1(112),
                 xturQuiet4(113),
                 xturReverb2(114),
                 xturQuiet5(115),
                 xturReverb3(116),
                 xturEct(117),
                 xturReverb4(118),
                 xturSegue1(119),
                 xturReverb5(120),
                 xturSegue2(121),
                 xturMsg1(122),
                 xturMedley(123),
                 xturExchmarker(124),
                 xturMsg2(125),
                 xturReverb6(126),
                 xturSegue3(127),
                 xturParams(128),
                 xturReverb7(129),
                 xturSegue4(130),
                 xturShowtime(131),
                 invalidValue(-1)
            }

        Vdsl2LineStatus ::= TEXTUAL-CONVENTION
            STATUS current
            DESCRIPTION
                "Attributes with this syntax are status parameters
                 that reflect the failure status for a given endpoint of
                 VDSL2 link.

                 This BITS structure can report the following failures:
                 1. noDefect (0)      - This bit position positively reports
                                        that no defect or failure exist
                 2. lossOfFraming (1) - Loss of frame synchronization
                 3. lossOfSignal (2)  - Loss of signal
                 4. lossOfPower (3)   - Loss of power.  Usually this failure may
                                        be reported for CPE units only
                 5. initFailure (4)   - Recent initialization process failed
                "
            SYNTAX BITS {
                noDefect(0),
                lossOfFraming(1),
                lossOfSignal(2),
                lossOfPower(3),
                initFailure(4)
            }

        Vdsl2ChAtmStatus ::= TEXTUAL-CONVENTION
            STATUS current
            DESCRIPTION
                "Attributes with this syntax are status parameters that
                 reflect the failure status for Transmission Convergence (TC)
                 layer of a given ATM interface (data path over anVDSL2
                 link).

                 This BITS structure can report the following failures:
                 1. noDefect (0)              - This bit position positively
                                                reports that no defect or failure
                                                exist.
                 2. noCellDelineation (1)     - The link was successfully
                                                initialized but cell delineation
                                                was never acquired on the
                                                associated ATM data path.
                 3. lossOfCellDelineation (2) - Loss of cell delineation on the
                                                associated ATM data path
                "
            SYNTAX BITS {
                noDefect(0),
                noCellDelineation(1),
                lossOfCellDelineation(2)
            }

        Vdsl2ChPtmStatus ::= TEXTUAL-CONVENTION
            STATUS current
            DESCRIPTION
                "Attributes with this syntax are status parameters that
                 reflect the failure status for a given PTM interface (packet
                 data path over an  VDSL2 link).

                 This BITS structure can report the following failures:
                 1. noDefect (0)    - This bit position positively
                                      reports that no defect or failure exist.
                 2. outOfSync (1)   - Out of synchronization.
               "
            SYNTAX BITS {
                   noDefect(0),
                   outOfSync(1)
            }

        Vdsl2BandOptUsage ::= TEXTUAL-CONVENTION
            STATUS current
            DESCRIPTION
                "Defines the VDSL2 link use of the optional frequency
                 range [25kHz - 138kHz] (Opt).
                 Options:
                 1. unused(1)        - Indicates Opt is unused
                 2. used(2)          - Indicates Opt is used
                 3. invalidValue(-1) - Invalid value
                "
            SYNTAX INTEGER {
                   unused(1),
                   used(2),
                   invalidValue(-1)
               }

        Vdsl2PSDClassMask ::= TEXTUAL-CONVENTION
            STATUS current
            DESCRIPTION
                "In order to reduce the number of configuration possibilities,
                 the limit PSD masks are grouped in the following PSD mask classes:
                  -	 Class 998 Annex A: D-32, D-64, D-48, D-128.
                  -	 Class 997-M1c Annex B: 997-M1c-A-7.
                  -	 Class 997-M1x Annex B: 997-M1x-M-8, 997-M1x-M.
                  -	 Class 997-M2x Annex B: 997-M2x-M-8, 997-M2x-A, 997-M2x-M.
                  -	 Class 998-M1x Annex B: 998-M1x-A, 998-M1x-B, 998-M1x-NUS0.
                  -	 Class 998-M2x Annex B: 998-M2x-A, 998-M2x-M, 998-M2x-B, 998-M2x-NUS0.
                  -      Class HPE17 Annex B: HPE17-M1-NUS0.
                  -      Class HPE30 Annex B: HPE30-M1-NUS0.
                  -      Class 997E17-M2x Annex B: 997E17-M2x-A.
                  -      Class 997E30-M2x Annex B: 997E30-M2x-NUS0.
                  -      Class 998E17-M2x Annex B: 998E17-M2x-NUS0, 998E17-M2x-NUS0-M, 998E17-M2x-A.
                  -      Class 998ADE17-M2x Annex B: 998ADE17-M2x-NUS0-M, 998ADE17-M2x-A, 998ADE17-M2x-B, 998ADE17-M2x-M.
                  -      Class 998E30-M2x Annex B: 998E30-M2x-NUS0, 998E30-M2x-NUS0-M.
                  -      Class 998ADE30-M2x Annex B: 998ADE30-M2x-NUS0-M, 998ADE30-M2x-NUS0-A.
                "
            SYNTAX INTEGER {
        	     annexA998-D-32              (1),
        	     annexA998-D-64              (2),
        	     annexB997-M1c-A-7           (3),
        	     annexB997-M1x-M-8           (4),
        	     annexB997-M1x-M             (5),
                     annexB997-M2x-M-8           (6),
                     annexB997-M2x-A             (7),
        	     annexB997-M2x-M             (8),
        	     annexB998-M1x-A             (9),
        	     annexB998-M1x-B             (10),
        	     annexB998-M1x-NUS0          (11),
        	     annexB998-M2x-A             (12),
        	     annexB998-M2x-M             (13),
        	     annexB998-M2x-B             (14),
        	     annexB998-M2x-NUS0          (15),
        	     annexBHPE17-M1-NUS0         (16),
        	     annexBHPE30-M1-NUS0         (17),
        	     annexB997E17-M2x-A          (18),
        	     annexB997E30-M2x-NUS0       (19),
        	     annexB998E17-M2x-NUS0       (20),
        	     annexB998E17-M2x-NUS0-M     (21),
        	     annexB998ADE17-M2x-NUS0-M   (22),
        	     annexB998ADE17-M2x-B        (23),
        	     annexB998E30-M2x-NUS0       (24),
        	     annexB998E30-M2x-NUS0-M     (25),
        	     annexB998ADE30-M2x-NUS0-M   (26),
        	     annexB998ADE17-M2x-A        (27),
        	     annexB998ADE30-M2x-NUS0-A   (28),
        	     annexA998-D-48              (29),
            	     annexA998-D-128             (30),
               	     annexB998ADE17-M2x-M        (31),
               	     annexB998E17-M2x-A          (32),
        	     invalidValue                (-1)

            }

        Vdsl2Profiles ::= TEXTUAL-CONVENTION
            STATUS current
            DESCRIPTION
                "This configuration parameter contains the G.993.2
                 profiles to be allowed by the near-end xTU on this line.
                 Options:
                 1. profile8a(1)     - Profile 8a
                 2. profile8b(2)     - Profile 8b
                 3. profile8c(3)     - Profile 8c
                 4. profile8d(4)     - Profile 8d
                 5. profile12a(5)    - Profile 12a
                 6. profile12b(6)    - Profile 12b
                 7. profile17a(7)    - Profile 17a
                 8. profile30a(8)    - Profile 30a
                 9. invalidValue(-1) - Invalid value
        		"
             SYNTAX INTEGER {
        			profile8a (1),
        			profile8b (2),
        			profile8c (3),
        			profile8d (4),
        			profile12a (5),
        			profile12b (6),
        			profile17a (7),
        			profile30a (8),
        			invalidValue(-1)
                 }

        Vdsl2DataPathMode ::= TEXTUAL-CONVENTION
            STATUS current
            DESCRIPTION
                "The channel data path mode.
                 Options:
                 1. atm(1)    - The channel data path mode is atm
                 2. ptm(2)    - The channel data path mode is ptm
                 3. both(3)   - The channel data path mode is both
        	    "
            SYNTAX INTEGER {
                	 atm(1),
                	 ptm(2),
                	 both(3)
                 }

        Xdsl2Band ::= TEXTUAL-CONVENTION
            STATUS current
            DESCRIPTION
                     "Identifies a band in a
                     VDSL2/ADSL/ADSL2/ADSL2+
                     link. For a band in the upstream direction,
                     transmission is from the remote end (xTU-R)
                     towards the central office end (xTU-C).
                     A band in the upstream direction is
                     indicated by upstream(1) for
                     ADSL/ADSL2/ADSL2+ single band, or any of
                     us0(3), us1(5), us2(7), us3(9), or us4(11) for
                     VDSL2 multiple bands.
                     For a band in the downstream direction,
                     transmission is from the xTU-C towards the xTU-R.
                     A band in the downstream direction is
                     indicated by downstream(2) for
                     ADSL/ADSL2/ADSL2+ single band, or any of
                     ds1(4), ds2(6), ds3(8), or ds4(10) for
                     VDSL2 multiple bands.  Specified as an INTEGER.
                     Options:
                     1. upstream(1)   - Transmission from the ATU-R to the ATU-C
                                       - (ADSL/ADSL2/ADSL2+).
                     2. downstream(2) - Transmission from the ATU-C to the ATU-R
                                       -(ADSL/ADSL2/ADSL2+).
                     3. us0(3)        - Upstream band number 0 (US0) (VDSL2)
                     4. ds1(4)        - Downstream band number 1 (DS1) (VDSL2)
                     5. us1(5)        - Upstream band number 1 (US1) (VDSL2)
                     6. ds2(6)        - Downstream band number 2 (DS2) (VDSL2)
                     7. us2(7)        - Upstream band number 2 (US2) (VDSL2)
                     8. ds3(8)        - Downstream band number 3 (DS3) (VDSL2)
                     9. us3(9)        - Upstream band number 3 (US3) (VDSL2)
                     10.ds4(10)       - Downstream band number 4 (DS4) (VDSL2)
                     11.us4(11)        - Upstream band number 4 (US4) (VDSL2)
                    "
             SYNTAX INTEGER {
                     upstream(1),
                     downstream(2),
                     us0(3),
                     ds1(4),
                     us1(5),
                     ds2(6),
                     us2(7),
                     ds3(8),
                     us3(9),
                     ds4(10),
                     us4(11)
                     }

        Vdsl2ForceINP ::= TEXTUAL-CONVENTION
            STATUS current
            DESCRIPTION
                "Force the INP greater than or equal to the minimal INP.
                 Options:
                 1. forced(1)     - Force the INP greater
                 2. auto(2)       - Auto the INP greater
                "
            SYNTAX INTEGER {
                 force(1),
                 auto(2)
            }

        Vdsl2PhyRControl ::= TEXTUAL-CONVENTION
            STATUS current
            DESCRIPTION
                "To enable or disable the retransmission function.
                 Options:
                 1. enable(1)   - Enable the retransmission function
                 2. disable(2)  - Disable the retransmission function
                "
            SYNTAX INTEGER {
                enable(1),
                disable(2)
            }

        Vdsl2ChEnabling ::= TEXTUAL-CONVENTION
            STATUS current
            DESCRIPTION
                "Indicates if the bearer channel is enabling.
                 Options:
                 1. enable(1)   - Indicates if the bearer channel is enable
                 2. disable(2)  - Indicates if the bearer channel is disable
                "
            SYNTAX INTEGER {
                 enable(1),
                 disable(2)
            }

        Vdsl2DataPathModeType ::= TEXTUAL-CONVENTION
            STATUS      current
            DESCRIPTION
                "A set of VDSL2 line data path modes, with one bit
                 per mode.
                 Options:
                 1. Atm(1)   - Atm path mode
                 2. Ptm(2)   - Ptm path mode
                "
            SYNTAX INTEGER {
                atm(1),
                ptm(2)
            }

        Vdsl2CfgMode ::= TEXTUAL-CONVENTION
            STATUS current
            DESCRIPTION
                "The configured VDSL management mode.  Specified as an INTEGER.
                 Options:
                 1. tr129Mode(1)     - VDSL management mode
                 2. tiMode(2)        - TIVDSL management mode
                 3. tr165Mode(3)     - TR165VDSL management mode
                "
            SYNTAX INTEGER {
                tr129Mode(1),
                tiMode(2),
                tr165Mode(3)
            }

        Vdsl2StatusRtxUsed ::= TEXTUAL-CONVENTION
            STATUS current
            DESCRIPTION
                "This parameter specifies whether G.998.4 retransmission
                 is used in a given transmit direction.
                 Options:
                 1. rtxInuse(1)                             - RTX in use
                 2. rtxUnusedModeForbidden(2)               - RTX not in use, due to RTX_MODE = FORBIDDEN
                 3. rtxUnusedNotSupportedXtuc(3)            - RTX not in use, due to not supported by the XTU-C
                 4. rtxUnusedNotSupportedXtur(4)            - RTX not in use, due to not supported by the XTU-R
                 5. rtxUnusedNotSupportedXtucAndXtur(5)     - RTX not in use, due to not supported by the XTU-C and XTU-R
                 6. invalidValue(-1)                        - Invalid value
                "
            SYNTAX INTEGER {
                 rtxInuse(1),
                 rtxUnusedModeForbidden(2),
                 rtxUnusedNotSupportedXtuc(3),
                 rtxUnusedNotSupportedXtur(4),
                 rtxUnusedNotSupportedXtucAndXtur(5),
                 invalidValue(-1)
            }
    END
