-- ============================================================================
-- Copyright (C) 2010 by  HUAWEI TECHNOLOGIES. All rights reserved.
-- Description:  This MIB module defines MIB objects which provides voice user management.
-- Reference:
-- Version: V1.0
-- ============================================================================

    HUAWEI-ENT-VOICE-SIPAGUSER-MIB DEFINITIONS ::= BEGIN
        IMPORTS
        	MODULE-IDENTITY, OBJECT-TYPE, NOTIFICATION-TYPE, private,Integer32,Unsigned32
        		FROM SNMPv2-SMI
        	MODULE-COMPLIANCE, OBJECT-GROUP, NOTIFICATION-GROUP
        		FROM SNMPv2-CONF
        	TEXTUAL-CONVENTION
        		FROM SNMPv2-TC
        	IpAddress, TimeTicks, Counter32
        		FROM SNMPv2-SMI
        	RowStatus, DisplayString
        		FROM SNMPv2-TC
        	hwDatacomm
        		FROM HUAWEI-MIB;

        hwEntVoiceSipagUserMIB MODULE-IDENTITY
            LAST-UPDATED "201012210000Z"
      ORGANIZATION
                "Huawei Technologies Co.,Ltd."
      CONTACT-INFO
              "Huawei Industrial Base
              Bantian, Longgang
              Shenzhen 518129
              People's Republic of China
              Website: http://www.huawei.com
              Email: support@huawei.com
                         "
            DESCRIPTION
                "This MIB module defines MIB objects which provides voice user management.
                "

        --  Revision history
            REVISION     "201105050000Z"
            DESCRIPTION  "V1.0, create"

            ::= { hwDatacomm 251 }

        hwEntPstnUserConfigTable OBJECT-TYPE
            SYNTAX      SEQUENCE OF HwEntPstnUserConfigEntry
            MAX-ACCESS  not-accessible
            STATUS      current
            DESCRIPTION
                "This table is used to add, delete, modify, and query the PSTN user.
                The index of this table is hwEntPraUserName.
                "
            ::= { hwEntVoiceSipagUserMIB 1 }

        hwEntPstnUserConfigEntry OBJECT-TYPE
            SYNTAX      HwEntPstnUserConfigEntry
            MAX-ACCESS  not-accessible
            STATUS      current
            DESCRIPTION
                "This table is used to add, delete, modify, and query the PSTN user.
                The index of this entry is hwEntPstnUserName.
                "
            INDEX   {
                        hwEntPstnUserName
                    }
            ::= { hwEntPstnUserConfigTable 1 }

        HwEntPstnUserConfigEntry ::=
            SEQUENCE {
                hwEntPstnUserName                       DisplayString,
                hwEntPstnUserPort                       Integer32,
                hwEntPstnUserMgId	                    Integer32,
                hwEntPstnUserTelNo	                    DisplayString,
                hwEntPstnUserUserGroupId                Integer32,
                hwEntPstnUserRowStatus	                RowStatus,
                hwEntPstnUserPriority                   INTEGER,
                hwEntPstnUserPotsLineType               INTEGER,
                hwEntPstnUserDCTime                     Integer32,
                hwEntPstnUserFSKDelayInterval           Integer32,
                hwEntPstnUserCidTransSequence           INTEGER,
                hwEntPstnUserCidFormat                  INTEGER,
                hwEntPstnUserVQEAgc                     INTEGER,
                hwEntPstnUserVQESns                     INTEGER,
                hwEntPstnUserVQEAgcLevel                Integer32,
                hwEntPstnUserVQESnsLevel                Integer32,
                hwEntPstnUserDspInputGain               Integer32,
                hwEntPstnUserDspOutputGain              Integer32,
                hwEntPstnUserDetectANSbarBySingleTone   INTEGER,
                hwEntPstnUserBellANS                    INTEGER,
                hwEntPstnUserDspParaTemplate            DisplayString,
                hwEntPstnUserCidFskMode                 INTEGER,
                hwEntPstnUserCidTasPattern              INTEGER
               }

        hwEntPstnUserName OBJECT-TYPE
          SYNTAX      DisplayString(SIZE(1..32))
          MAX-ACCESS  not-accessible
          STATUS      current
          DESCRIPTION
              "
              Indicates the user's name.
              "
          ::= { hwEntPstnUserConfigEntry 1 }

       hwEntPstnUserPort OBJECT-TYPE
          SYNTAX      Integer32
          MAX-ACCESS  read-create
          STATUS      current
          DESCRIPTION
              "
              Indicates the user's port.
              Bits 31-30  (2 bits): reserved.
              Bits 29-20 (10 bits): slot index.
              Bits 19-10 (10 bits): subcard index.
              Bits 9-0   (10 bits): port index.
              "
          ::= { hwEntPstnUserConfigEntry 2 }

        hwEntPstnUserMgId OBJECT-TYPE
          SYNTAX      Integer32(0..16777215)
          MAX-ACCESS  read-create
          STATUS      current
          DESCRIPTION
              "
              Indicates the sipag ID.
              "
          ::= { hwEntPstnUserConfigEntry 3 }

        hwEntPstnUserTelNo OBJECT-TYPE
          SYNTAX      DisplayString(SIZE(0..32))
          MAX-ACCESS  read-create
          STATUS      current
          DESCRIPTION
              "
              Indicates the user's telephone number.
              "
          ::= { hwEntPstnUserConfigEntry 4 }


        hwEntPstnUserUserGroupId OBJECT-TYPE
          SYNTAX      Integer32(0..65535)
          MAX-ACCESS  read-create
          STATUS      current
          DESCRIPTION
              "
              Indicates the user's group id.
              "
          ::= { hwEntPstnUserConfigEntry 5 }

        hwEntPstnUserRowStatus OBJECT-TYPE
          SYNTAX      RowStatus
          MAX-ACCESS  read-create
          STATUS      current
          DESCRIPTION
              "
              Indicates the row status.
              Options:
              active(1)
 	          notInService(2)
 	          notReady(3)
 	          createAndGo(4)
 	          createAndWait(5)
              destroy(6)
              "
          ::= { hwEntPstnUserConfigEntry 6 }

        hwEntPstnUserPriority OBJECT-TYPE
          SYNTAX      INTEGER{cat1(1), -- the highest priority
                              cat2(2), -- the middle priority
                              cat3(3)  -- the lowest priority
                              }
          MAX-ACCESS  read-create
          STATUS      current
          DESCRIPTION
              "
              Indicates the priority of the terminal.
              Options:
              cat1(1)  -the highest priority
              cat2(2)  -the middle priority
              cat3(3)  -the lowest priority
              Default: cat3(3)
              "
          ::= { hwEntPstnUserConfigEntry 7 }

        hwEntPstnUserPotsLineType OBJECT-TYPE
          SYNTAX      INTEGER{del(1),     -- DEL
                              lcPBX(2),   -- loop calling PBX
                              ecPBX(3),   -- earth calling PBX
                              payPhone(4) -- Pay phone
                              }
          MAX-ACCESS  read-create
          STATUS      current
          DESCRIPTION
              "
              Indicates the pots line type.
              Options:
              del(1)    -DEL
              lcPBX(2)  -Loop Calling PBX
              ecPBX(3)  -Earth Calling PBX
              payPhone(4) -PayPhone
              Default: del(1)
              "
          ::= { hwEntPstnUserConfigEntry 8 }

        hwEntPstnUserDCTime OBJECT-TYPE
          SYNTAX      Integer32(0..100)
          MAX-ACCESS  read-create
          STATUS      current
          DESCRIPTION
              "
              Indicates the power-off interval.
              Default: 10
              Unit: 10ms
              "
          ::= { hwEntPstnUserConfigEntry 9 }

        hwEntPstnUserFSKDelayInterval OBJECT-TYPE
          SYNTAX      Integer32(0..100)
          MAX-ACCESS  read-create
          STATUS      current
          DESCRIPTION
              "
              Indicates the FSK delay interval.
              Default: 80
              Unit: 10ms
              "
          ::= { hwEntPstnUserConfigEntry 10 }

        hwEntPstnUserCidTransSequence OBJECT-TYPE
          SYNTAX      INTEGER{afterRing(1),  -- transmit CID after ringing
                              beforeRing(2)  -- transmit CID before ringing
                              }
          MAX-ACCESS  read-create
          STATUS      current
          DESCRIPTION
              "
              Indicates the time for delivering the caller ID.
              Options:
              afterRing(1)  -transmit CID after ringing
              beforeRing(2) -transmit CID before ringing
              Default: afterRing(1)
              "
          ::= { hwEntPstnUserConfigEntry 11 }

        hwEntPstnUserCidFormat OBJECT-TYPE
          SYNTAX      INTEGER{sdmfFsk(1), mdmfFsk(2), dtmf(3), r15(4), etsi(5)}
          MAX-ACCESS  read-create
          STATUS      current
          DESCRIPTION
              "
              Indicates the format of the caller ID.
              Options:
              1. sdmfFsk(1)   -SDMF FSK format
              2. mdmfFsk(2)   -MDMF FSK format
              3. dtmf(3)      -DTMF format
              4. r15(4)       -R15 format
              5. etsi(5)      -ETSI format
              Default: sdmfFsk(1)
              "
          ::= { hwEntPstnUserConfigEntry 12 }

        hwEntPstnUserVQEAgc OBJECT-TYPE
          SYNTAX      INTEGER{enable(1), disable(2)}
          MAX-ACCESS  read-create
          STATUS      current
          DESCRIPTION
              "
              Indicates enable AGC or not.
              Options:
              enable(1)
              disable(2)
              Default: disable(2)
              "
          ::= { hwEntPstnUserConfigEntry 13 }

        hwEntPstnUserVQESns OBJECT-TYPE
          SYNTAX      INTEGER{enable(1),disable(2)}
          MAX-ACCESS  read-create
          STATUS      current
          DESCRIPTION
              "
              Indicates enable SNS or not.
              Options:
              1. enable(1)
              2. disable(2)
              Default: disable(2)
              "
          ::= { hwEntPstnUserConfigEntry 14 }

        hwEntPstnUserVQEAgcLevel OBJECT-TYPE
          SYNTAX      Integer32(0..15)
          MAX-ACCESS  read-create
          STATUS      current
          DESCRIPTION
              "
              Indicates set AGC target value.
              0..15 corresponding to -9..-24dbm0.
              Default: 13(-22dbm0)
              "
          ::= { hwEntPstnUserConfigEntry 15 }

        hwEntPstnUserVQESnsLevel OBJECT-TYPE
          SYNTAX      Integer32(6..20)
          MAX-ACCESS  read-create
          STATUS      current
          DESCRIPTION
              "
              Indicates set VQE noise suppression level.
              Default: 12
              Unit: db
              "
          ::= { hwEntPstnUserConfigEntry 16 }

        hwEntPstnUserDspInputGain OBJECT-TYPE
          SYNTAX      Integer32(0..15)
          MAX-ACCESS  read-create
          STATUS      current
          DESCRIPTION
              "
              Indicates Dsp input gain.
              0..15 corresponding to -10..5db.
        	  Default: 10(0db)
              "
          ::= { hwEntPstnUserConfigEntry 17 }

        hwEntPstnUserDspOutputGain OBJECT-TYPE
          SYNTAX      Integer32(0..20)
          MAX-ACCESS  read-create
          STATUS      current
          DESCRIPTION
              "
              Indicates Dsp output gain.
              0..20 corresponding to -10..10db.
        	  Default: 10(0db)
              "
          ::= { hwEntPstnUserConfigEntry 18 }


        hwEntPstnUserDetectANSbarBySingleTone OBJECT-TYPE
          SYNTAX      INTEGER{enable(1),disable(2)}
          MAX-ACCESS  read-create
          STATUS      current
          DESCRIPTION
              "
              Indicates the flag of ANSbar signal detected by SingleTone.
              Options:
              1. enable(1)   -the ANSbar signal detected by SingleTone is supported
              2. disable(2)  -the ANSbar signal detected by SingleTone is not supported
              Default: disable(2)
              "
          ::= { hwEntPstnUserConfigEntry 19 }


        hwEntPstnUserBellANS OBJECT-TYPE
          SYNTAX      INTEGER{enable(1),disable(2)}
          MAX-ACCESS  read-create
          STATUS      current
          DESCRIPTION
              "
              Indicates the flag of Bell ANS.
              Options:
              1. enable(1)   -the Bell ANS is supported
              2. disable(2)  -the Bell ANS is not supported
              Default: disable(2)
              "
          ::= { hwEntPstnUserConfigEntry 20 }

        hwEntPstnUserDspParaTemplate OBJECT-TYPE
          SYNTAX      DisplayString(SIZE(0..31))
          MAX-ACCESS  read-create
          STATUS      current
          DESCRIPTION
              "
              Indicates the index of dsp parameter template name.
              "
          ::= { hwEntPstnUserConfigEntry 21 }

        hwEntPstnUserCidFskMode OBJECT-TYPE
          SYNTAX      INTEGER{bell202(1), ccittV23(2), ntt(3)}
          MAX-ACCESS  read-create
          STATUS      current
          DESCRIPTION
              "
              Indicates the mode of fsk.
              Options:
              bell202(1)   -bell 202
              ccittV23(2)  -ccitt v23
              ntt(3)       -ntt
              Default: bell202(1)
              "
          ::= { hwEntPstnUserConfigEntry 22 }


          hwEntPstnUserCidTasPattern OBJECT-TYPE
          SYNTAX      INTEGER{noTas(1), dtAs(2)}
          MAX-ACCESS  read-create
          STATUS      current
          DESCRIPTION
              "
              Indicates the mode of tas.
              Options:
              1. noTas(1)   -NO TAS
              2. dtAs(2)    -DT AS
              Default: noTas(1)
              "
          ::= { hwEntPstnUserConfigEntry 23 }

-- =================================================================================

        hwEntPstnUserOperTable OBJECT-TYPE
          SYNTAX      SEQUENCE OF HwEntPstnUserOperEntry
          MAX-ACCESS  not-accessible
          STATUS      current
          DESCRIPTION
            "
            This table is used to maintain PSTN users.
            The index of this entry is hwEntPstnUserOperName.
            "
          ::= { hwEntVoiceSipagUserMIB 2 }

        hwEntPstnUserOperEntry OBJECT-TYPE
          SYNTAX      HwEntPstnUserOperEntry
          MAX-ACCESS  not-accessible
          STATUS      current
          DESCRIPTION
            "
            This table is used to maintain PSTN users.
            The index of this entry is hwEntPstnUserOperName.
            "
          INDEX    {
                    hwEntPstnUserOperName
                   }
          ::= { hwEntPstnUserOperTable 1 }

        HwEntPstnUserOperEntry ::=
          SEQUENCE
          {
            hwEntPstnUserOperName        DisplayString,
            hwEntPstnUserSrvState	     INTEGER,
            hwEntPstnUserAdminState	     INTEGER,
            hwEntPstnUserAdminOper	     INTEGER,
            hwEntPstnUserMaxCobTime      Integer32,
            hwEntPstnUserOnexpire        INTEGER
          }

       hwEntPstnUserOperName OBJECT-TYPE
          SYNTAX      DisplayString(SIZE(1..32))
          MAX-ACCESS  not-accessible
          STATUS      current
          DESCRIPTION
              "
              Indicates the user's name.
              "
          ::= { hwEntPstnUserOperEntry 1 }

        hwEntPstnUserSrvState OBJECT-TYPE
          SYNTAX      INTEGER{idle(1), busy(2), fault(3), unusable(4), onhook(5), offHookNamal(6), offHookParking(7), ring(8)}
          MAX-ACCESS  read-only
          STATUS      current
          DESCRIPTION
              "
              Indicates the running status.
              Options:
              idle(1)
              busy(2)
              fault(3)
              unusable(4)
              onhook(5)
              offHookNamal(6)
              offHookParking(7)
              ring(8)
              "
          ::= { hwEntPstnUserOperEntry 2 }

        hwEntPstnUserAdminState OBJECT-TYPE
          SYNTAX      INTEGER{lBlock(1), rBlock(2), startSvc(3), shuttingDown(4), delayTest(5), vsqmTest(6)}
          MAX-ACCESS  read-only
          STATUS      current
          DESCRIPTION
              "
              Indicates the administration status.
              Options:
              lBlock(1)        -the service is blocked cause of the local reason
              rBlock(2)        -the service is blocked cause of the remote reason
              startSvc(3)      -the service is normal
              shuttingDown(4)  -the service is shutting down graceful
              delayTest(5)     -the user is waiting for testing
              vsqmTest(6)      -the user is in vsqm test
              "
          ::= { hwEntPstnUserOperEntry 3 }

        hwEntPstnUserAdminOper OBJECT-TYPE
          SYNTAX      INTEGER{startService(1), endService(2), deferEndingService(3)}
          MAX-ACCESS  read-write
          STATUS      current
          DESCRIPTION
              "
              Indicates the maintenance operation.
              Options:
              startService(1)       -start service
              endService(2)         -stop service
              deferEndingService(3) -stop service gracefully
              "
          ::= { hwEntPstnUserOperEntry 4 }

          hwEntPstnUserMaxCobTime OBJECT-TYPE
          SYNTAX      Integer32(1..1440)
          MAX-ACCESS  read-write
          STATUS      current
          DESCRIPTION
              "
              Indicates length of waiting timer for defer end service.
              Default: 240
              Unit: minute
              "
          ::= { hwEntPstnUserOperEntry 5 }

          hwEntPstnUserOnexpire OBJECT-TYPE
          SYNTAX      INTEGER{force(1),cancel(2)}
          MAX-ACCESS  read-write
          STATUS      current
          DESCRIPTION
              "
              Indicates disposal mode when defer end service timeout.
              Options:
              force(1)      -force user to end service when end-service timeout
              cancel(2)     -cancel end service when end-service timeout
              Default: force(1)
              "
          ::= { hwEntPstnUserOperEntry 6 }

-- ==================================================================================

         hwEntBraUserConfigTable OBJECT-TYPE
         SYNTAX      SEQUENCE OF HwEntBraUserConfigEntry
         MAX-ACCESS  not-accessible
         STATUS      current
         DESCRIPTION
           "
           This table is used to add, delete, modify, and query the BRA user.
           The index of this table is hwEntBraUserName.
           "
         ::= { hwEntVoiceSipagUserMIB 3 }

       hwEntBraUserConfigEntry OBJECT-TYPE
         SYNTAX      HwEntBraUserConfigEntry
         MAX-ACCESS  not-accessible
         STATUS      current
         DESCRIPTION
           "
           This table is used to add, delete, modify, and query the BRA user.
           The index of this entry is hwEntBraUserName.
           "
         INDEX    {
                   hwEntBraUserName
                  }
         ::= { hwEntBraUserConfigTable 1 }

       HwEntBraUserConfigEntry ::=
         SEQUENCE
         {
           hwEntBraUserName               DisplayString,
           hwEntBraUserPort               Integer32,
           hwEntBraUserMgId	              Integer32,
           hwEntBraUserTelNo	          DisplayString,
           hwEntBraUserUserGroupId        Integer32,
           hwEntBraUserRowStatus	      RowStatus,
           hwEntBraUserPriority           INTEGER,
           hwEntBraUserUniErrReport       INTEGER,
           hwEntBraUserAutoResumeLimit    Integer32
         }

       hwEntBraUserName OBJECT-TYPE
          SYNTAX      DisplayString(SIZE(1..32))
          MAX-ACCESS  not-accessible
          STATUS      current
          DESCRIPTION
              "
              Indicates the user's name.
              "
          ::= { hwEntBraUserConfigEntry 1 }

       hwEntBraUserPort OBJECT-TYPE
          SYNTAX      Integer32
          MAX-ACCESS  read-create
          STATUS      current
          DESCRIPTION
              "
              Indicates the user's port.
              Bits 31-30  (2 bits): reserved.
              Bits 29-20 (10 bits): slot index.
              Bits 19-10 (10 bits): subcard index.
              Bits 9-0   (10 bits): port index.
              "
          ::= { hwEntBraUserConfigEntry 2 }

       hwEntBraUserMgId OBJECT-TYPE
         SYNTAX      Integer32(0..16777215)
         MAX-ACCESS  read-create
         STATUS      current
         DESCRIPTION
             "
             Indicates the sipag ID.
             "
         ::= { hwEntBraUserConfigEntry 3 }

       hwEntBraUserTelNo OBJECT-TYPE
         SYNTAX      DisplayString(SIZE(0..32))
         MAX-ACCESS  read-create
         STATUS      current
         DESCRIPTION
             "
             Indicates the user telephone number.
             "
         ::= { hwEntBraUserConfigEntry 4 }

        hwEntBraUserUserGroupId OBJECT-TYPE
          SYNTAX      Integer32(0..65535)
          MAX-ACCESS  read-create
          STATUS      current
          DESCRIPTION
              "
              Indicates the user's group id.
              "
          ::= { hwEntBraUserConfigEntry 5 }

       hwEntBraUserRowStatus OBJECT-TYPE
         SYNTAX      RowStatus
         MAX-ACCESS  read-create
         STATUS      current
         DESCRIPTION
             "
             Indicates the row status.
             Options:
             active(1)
 	         notInService(2)
 	         notReady(3)
 	         createAndGo(4)
 	         createAndWait(5)
             destroy(6)
             "
         ::= { hwEntBraUserConfigEntry 6 }

       hwEntBraUserPriority OBJECT-TYPE
          SYNTAX      INTEGER{cat1(1), cat2(2), cat3(3)}
          MAX-ACCESS  read-create
          STATUS      current
          DESCRIPTION
              "
              Indicates the priority of the terminal.
              Options:
              cat1(1) -the highest priority
              cat2(2) -the middle priority
              cat3(3) -the lowest priority
              Default: cat3(3)
              "
          ::= { hwEntBraUserConfigEntry 7 }

      hwEntBraUserUniErrReport OBJECT-TYPE
          SYNTAX      INTEGER{enable(1),disable(2)}
          MAX-ACCESS  read-create
          STATUS      current
          DESCRIPTION
              "
              Indicates the flag of UNI fault report.
              Options:
              1. enable(1)
              2. disable(2)
              Default: disable(2)
              "
          ::= { hwEntBraUserConfigEntry 8 }

      hwEntBraUserAutoResumeLimit OBJECT-TYPE
          SYNTAX      Integer32(0..255)
          MAX-ACCESS  read-create
          STATUS      current
          DESCRIPTION
              "
              Indicates the threshold of auto resume times.
              Default: 20
              "
          ::= { hwEntBraUserConfigEntry 9 }

-- ================================================================================

       hwEntBraUserOperTable OBJECT-TYPE
         SYNTAX      SEQUENCE OF HwEntBraUserOperEntry
         MAX-ACCESS  not-accessible
         STATUS      current
         DESCRIPTION
           "
           This table is used to maintain BRA users.
           The index of this table is hwEntBraUserOperName.
           "
         ::= { hwEntVoiceSipagUserMIB 4 }

       hwEntBraUserOperEntry OBJECT-TYPE
         SYNTAX      HwEntBraUserOperEntry
         MAX-ACCESS  not-accessible
         STATUS      current
         DESCRIPTION
           "
           This table is used to maintain BRA users.
           The index of this entry is hwEntBraUserOperName.
           "
         INDEX    {
                     hwEntBraUserOperName
                  }
         ::= { hwEntBraUserOperTable 1 }

       HwEntBraUserOperEntry ::=
         SEQUENCE
         {
           hwEntBraUserOperName	         DisplayString,
           hwEntBraUserB0SrvState	     INTEGER,
           hwEntBraUserB1SrvState	     INTEGER,
           hwEntBraUserB0AdminState	     INTEGER,
           hwEntBraUserB1AdminState	     INTEGER,
           hwEntBraUserDState	         INTEGER,
           hwEntBraUserAdminOper	     INTEGER,
           hwEntBraUserMaxCobTime        Integer32,
           hwEntBraUserOnexpire          INTEGER
         }

       hwEntBraUserOperName OBJECT-TYPE
          SYNTAX      DisplayString(SIZE(1..32))
          MAX-ACCESS  not-accessible
          STATUS      current
          DESCRIPTION
              "
              Indicates the user's name.
              "
          ::= { hwEntBraUserOperEntry 1 }

       hwEntBraUserB0SrvState OBJECT-TYPE
         SYNTAX      INTEGER{idle(1), busy(2), fault(3), unusable(4), onhook(5), offHookNamal(6), offHookParking(7), ring(8)}
         MAX-ACCESS  read-only
         STATUS      current
         DESCRIPTION
             "
             Indicates the running status of the BRA B0 channel.
             Options:
             idle(1)
             busy(2)
             fault(3)
             unusable(4)
             onhook(5)
             offHookNamal(6)
             offHookParking(7)
             ring(8)
             "
         ::= { hwEntBraUserOperEntry 2 }

       hwEntBraUserB1SrvState OBJECT-TYPE
         SYNTAX      INTEGER{idle(1), busy(2), fault(3), unusable(4), onhook(5), offHookNamal(6), offHookParking(7), ring(8)}
         MAX-ACCESS  read-only
         STATUS      current
         DESCRIPTION
             "
             Indicates the running status of the BRA B1 channel.
             Options:
             idle(1)
             busy(2)
             fault(3)
             unusable(4)
             onhook(5)
             offHookNamal(6)
             offHookParking(7)
             ring(8)
             "
         ::= { hwEntBraUserOperEntry 3 }

        hwEntBraUserB0AdminState OBJECT-TYPE
         SYNTAX      INTEGER{lBlock(1), rBlock(2), startSvc(3), shuttingDown(4), delayTest(5), vsqmTest(6)}
         MAX-ACCESS  read-only
         STATUS      current
         DESCRIPTION
             "
             Indicates the administration status of the BRA B0 channel.
             Options:
             lBlock(1)        -the service is blocked cause of the local reason
             rBlock(2)        -the service is blocked cause of the remote reason
             startSvc(3)      -the service is normal
             shuttingDown(4)  -the service is shutting down graceful
             delayTest(5)     -the user is waiting for testing
             vsqmTest(6)      -the user is in vsqm test
             "
         ::= { hwEntBraUserOperEntry 4 }

         hwEntBraUserB1AdminState OBJECT-TYPE
         SYNTAX      INTEGER{lBlock(1), rBlock(2), startSvc(3), shuttingDown(4), delayTest(5), vsqmTest(6)}
         MAX-ACCESS  read-only
         STATUS      current
         DESCRIPTION
             "
             Indicates the administration status of the BRA B1 channel.
             Options:
             lBlock(1)        -the service is blocked cause of the local reason
             rBlock(2)        -the service is blocked cause of the remote reason
             startSvc(3)      -the service is normal
             shuttingDown(4)  -the service is shutting down graceful
             delayTest(5)     -the user is waiting for testing
             vsqmTest(6)      -the user is in vsqm test
             "
         ::= { hwEntBraUserOperEntry 5 }

        hwEntBraUserAdminOper OBJECT-TYPE
          SYNTAX      INTEGER{startService(1), endService(2), deferEndingService(3)}
          MAX-ACCESS  read-write
          STATUS      current
          DESCRIPTION
              "
              Indicates the maintenance operation of the BRA port.
              Options:
              startService(1)        -start service
              endService(2)          -stop service
              deferEndingService(3)  -stop service gracefully
              "
          ::= { hwEntBraUserOperEntry 6 }

         hwEntBraUserDState OBJECT-TYPE
         SYNTAX      INTEGER{established(1), blocked(2), released(3), teiAssigned(4), teiUnassigned(5)}
         MAX-ACCESS  read-only
         STATUS      current
         DESCRIPTION
             "
             Indicates the status of the BRA D channel.
             Options:
             established(1)
             blocked(2)
             released(3)
             teiAssigned(4)
             teiUnassigned(5)
             "
         ::= { hwEntBraUserOperEntry 7 }

       hwEntBraUserMaxCobTime OBJECT-TYPE
         SYNTAX      Integer32(1..1440)
         MAX-ACCESS  read-write
         STATUS      current
         DESCRIPTION
             "
             Indicates the length of waiting timer for defer end service.
             Default:240
             Unit: minute
             "
         ::= { hwEntBraUserOperEntry 8 }

       hwEntBraUserOnexpire OBJECT-TYPE
         SYNTAX      INTEGER{force(1),cancel(2)}
         MAX-ACCESS  read-write
         STATUS      current
         DESCRIPTION
             "
             Indicates the disposal mode when defer end service timeout.
             Options:
             force(1)    -force user to end service
             cancel(2)   -cancel user's end service
             Default: force(1)
             "
         ::= { hwEntBraUserOperEntry 9 }

 -- =================================================================================

        hwEntPraUserConfigTable OBJECT-TYPE
         SYNTAX      SEQUENCE OF HwEntPraUserConfigEntry
         MAX-ACCESS  not-accessible
         STATUS      current
         DESCRIPTION
           "
           This table is used to add, delete, modify, and query the PRA user.
           The index of this table is the hwEntPraUserName.
           "
         ::= { hwEntVoiceSipagUserMIB 5 }

       hwEntPraUserConfigEntry OBJECT-TYPE
         SYNTAX      HwEntPraUserConfigEntry
         MAX-ACCESS  not-accessible
         STATUS      current
         DESCRIPTION
           "
           This table is used to add, delete, modify, and query the PRA user.
           The index of this entry is the hwEntPraUserName.
           "
         INDEX    {
                   hwEntPraUserName
                  }
         ::= { hwEntPraUserConfigTable 1 }

       HwEntPraUserConfigEntry ::=
         SEQUENCE
         {
           hwEntPraUserName               DisplayString,
           hwEntPraUserPort               Integer32,
           hwEntPraUserMgId		          Integer32,
           hwEntPraUserTelNo              DisplayString,
           hwEntPraUserUserGroupId        Integer32,
           hwEntPraUserRowStatus	      RowStatus,
           hwEntPraUserPriority           INTEGER,
           hwEntPraUserUniErrReport       INTEGER,
           hwEntPraUserSubChnMask         BITS,
           hwEntPraUserAutoResumeLimit    Integer32
         }

       hwEntPraUserName OBJECT-TYPE
         SYNTAX      DisplayString(SIZE(1..32))
         MAX-ACCESS  not-accessible
         STATUS      current
         DESCRIPTION
             "
             Indicates the user's name.
             "
         ::= { hwEntPraUserConfigEntry 1 }

       hwEntPraUserPort OBJECT-TYPE
         SYNTAX      Integer32
         MAX-ACCESS  read-create
         STATUS      current
         DESCRIPTION
             "
             Indicates the user's port.
             Bits 31-30  (2 bits): reserved.
             Bits 29-20 (10 bits): slot index.
             Bits 19-10 (10 bits): subcard index.
             Bits 9-0   (10 bits): port index.
             "
         ::= { hwEntPraUserConfigEntry 2 }

       hwEntPraUserMgId OBJECT-TYPE
         SYNTAX      Integer32(0..16777215)
         MAX-ACCESS  read-create
         STATUS      current
         DESCRIPTION
             "
             Indicates the sipag ID.
             "
         ::= { hwEntPraUserConfigEntry 3 }

       hwEntPraUserTelNo OBJECT-TYPE
         SYNTAX      DisplayString(SIZE(0..32))
         MAX-ACCESS  read-create
         STATUS      current
         DESCRIPTION
             "
             Indicates the user's telphone number.
             "
         ::= { hwEntPraUserConfigEntry 4 }

      hwEntPraUserUserGroupId OBJECT-TYPE
          SYNTAX      Integer32(0..65535)
          MAX-ACCESS  read-create
          STATUS      current
          DESCRIPTION
              "
              Indicates the user's group id.
              "
          ::= { hwEntPraUserConfigEntry 5 }

       hwEntPraUserRowStatus OBJECT-TYPE
         SYNTAX      RowStatus
         MAX-ACCESS  read-create
         STATUS      current
         DESCRIPTION
             "
             Indicates the row status.
             Options:
             active(1)
 	         notInService(2)
 	         notReady(3)
 	         createAndGo(4)
 	         createAndWait(5)
             destroy(6)
             "
         ::= { hwEntPraUserConfigEntry 6 }

      hwEntPraUserPriority OBJECT-TYPE
          SYNTAX      INTEGER{cat1(1), cat2(2), cat3(3)}
          MAX-ACCESS  read-create
          STATUS      current
          DESCRIPTION
              "
              Indicates terminal priority.
              Options:
              cat1(1)   -the highest priority
              cat2(2)   -the middle priority
              cat3(3)   -the lowest priority
              Default: cat(3)
              "
          ::= { hwEntPraUserConfigEntry 7}

      hwEntPraUserUniErrReport OBJECT-TYPE
          SYNTAX      INTEGER{enable(1),disable(2)}
          MAX-ACCESS  read-create
          STATUS      current
          DESCRIPTION
              "
              Indicates the flag of UNI fault report.
              Options:
              enable(1)   -enable UNI fault report of e1 port
              disable(2)  -disable UNI fault report of e1 port
              Default: disable(2)
              "
          ::= { hwEntPraUserConfigEntry 8}

      hwEntPraUserSubChnMask OBJECT-TYPE
          SYNTAX      BITS{bchn0(0),bchn1(1),bchn2(2),bchn3(3),bchn4(4),bchn5(5),bchn6(6),bchn7(7),bchn8(8),bchn9(9),bchn10(10),
                           bchn11(11),bchn12(12),bchn13(13),bchn14(14),bchn15(15),bchn16(16),bchn17(17),bchn18(18),bchn19(19),bchn20(20),
                           bchn21(21),bchn22(22),bchn23(23),bchn24(24),bchn25(25),bchn26(26),bchn27(27),bchn28(28),bchn29(29),bchn30(30),
                           bchn31(31)}
          MAX-ACCESS  read-create
          STATUS      current
          DESCRIPTION
              "
              Indicates the sub channel mask code.
              Default: 11111111111111111111111111111111
              "
          ::= { hwEntPraUserConfigEntry 9}

      hwEntPraUserAutoResumeLimit OBJECT-TYPE
          SYNTAX      Integer32(0..255)
          MAX-ACCESS  read-create
          STATUS      current
          DESCRIPTION
              "
              Indicates the threshold of auto resume times.
              Default: 20
              "
          ::= { hwEntPraUserConfigEntry 10}

-- ==================================================================================

        hwEntPraUserOperTable OBJECT-TYPE
         SYNTAX      SEQUENCE OF HwEntPraUserOperEntry
         MAX-ACCESS  not-accessible
         STATUS      current
         DESCRIPTION
           "
           This table is used to maintain PRA users.
           The index of this table is hwEntPraUserOperNamee.
           "
         ::= { hwEntVoiceSipagUserMIB 6 }

       hwEntPraUserOperEntry OBJECT-TYPE
         SYNTAX      HwEntPraUserOperEntry
         MAX-ACCESS  not-accessible
         STATUS      current
         DESCRIPTION
           "
           This table is used to maintain PRA users.
           The index of this entry is hwEntPraUserOperName.
           "
         INDEX    {
                   hwEntPraUserOperName
                  }
         ::= { hwEntPraUserOperTable 1 }

       HwEntPraUserOperEntry ::=
         SEQUENCE
         {
           hwEntPraUserOperName          DisplayString,
           hwEntPraUserBchnSrvState      OCTET STRING,
           hwEntPraUserBchnAdminState    OCTET STRING,
           hwEntPraUserDState	         INTEGER,
           hwEntPraUserAdminOper	     INTEGER,
           hwEntPraUserMaxCobTime        Integer32,
           hwEntPraUserOnexpire          INTEGER
         }

       hwEntPraUserOperName OBJECT-TYPE
         SYNTAX      DisplayString(SIZE(1..32))
         MAX-ACCESS  not-accessible
         STATUS      current
         DESCRIPTION
             "
             Indicates the user's name.
             "
         ::= { hwEntPraUserOperEntry 1 }

       hwEntPraUserBchnSrvState OBJECT-TYPE
         SYNTAX      OCTET STRING(SIZE (0..32))
         MAX-ACCESS  read-only
         STATUS      current
         DESCRIPTION
             "
             Indicates the running service status of the service layer of the 32 B channels.
             Each character corresponds to a timeslot. The value of the character is as follows:
             1: Idle
             2: Busy
             3: Faulty
             4: Unavailable
             "
         ::= { hwEntPraUserOperEntry 2 }

       hwEntPraUserBchnAdminState OBJECT-TYPE
         SYNTAX      OCTET STRING(SIZE (0..32))
         MAX-ACCESS  read-only
         STATUS      current
         DESCRIPTION
             "
             Indicates the administration status of the service layer of the 32 B channels.
             Each character corresponds to a timeslot. The value of the character is as follows:
             1: blocked-locally
             2: blocked-remotely
             3: in-service
             4: shutting-down
             "
         ::= { hwEntPraUserOperEntry 3 }

       hwEntPraUserDState OBJECT-TYPE
         SYNTAX      INTEGER{released(1), established(2), blocked(3), teiAssigned(4), teiUnassigned(5)}
         MAX-ACCESS  read-only
         STATUS      current
         DESCRIPTION
             "
             Indicates the status of the PRA D channel.
             Options:
             released(1)
             established(2)
             blocked(3)
             teiAssigned(4)
             teiUnassigned(5)
             "
         ::= { hwEntPraUserOperEntry 4 }

        hwEntPraUserAdminOper OBJECT-TYPE
          SYNTAX      INTEGER{startService(1), endService(2), deferEndingService(3)}
          MAX-ACCESS  read-write
          STATUS      current
          DESCRIPTION
              "
              Indicates the service operation.
              Options:
              startService(1)         -start service
              endService(2)           -stop service
              deferEndingService(3)   -stop service gracefully
              "
          ::= { hwEntPraUserOperEntry 5 }

       hwEntPraUserMaxCobTime OBJECT-TYPE
         SYNTAX      Integer32(1..1440)
         MAX-ACCESS  read-write
         STATUS      current
         DESCRIPTION
             "
             Indicates length of waiting timer for PRA user defer end service.
             Default: 240
             Unit: minute
             "
         ::= { hwEntPraUserOperEntry 6 }

       hwEntPraUserOnexpire OBJECT-TYPE
         SYNTAX      INTEGER{force(1),cancel(2)}
         MAX-ACCESS  read-write
         STATUS      current
         DESCRIPTION
             "
             Indicates disposal mode when PRA user defer end service timeout.
             Options:
             force(1)  -force end service
             cancel(2) -cancel end service
             Default: force(1)
             "
         ::= { hwEntPraUserOperEntry 7 }

-- =================================================================================

     hwEntUserExtendNumberConfigTable OBJECT-TYPE
          SYNTAX      SEQUENCE OF HwEntUserExtendNumberConfigEntry
          MAX-ACCESS  not-accessible
          STATUS      current
          DESCRIPTION
            "
            This table is used to config extern number of sipag users.
            The indexes of this table are hwEntSipagUserName, hwEntUserExtendNumber.
            "
          ::= { hwEntVoiceSipagUserMIB 7 }

        hwEntUserExtendNumberConfigEntry OBJECT-TYPE
          SYNTAX      HwEntUserExtendNumberConfigEntry
          MAX-ACCESS  not-accessible
          STATUS      current
          DESCRIPTION
            "
            This table is used to config extern number of the SIP user.
            The indexes of this entry are hwEntSipagUserName, hwEntUserExtendNumber.
            "
          INDEX    {
                    hwEntSipagUserName,
                    hwEntUserExtendNumber
                   }
          ::= { hwEntUserExtendNumberConfigTable 1 }

        HwEntUserExtendNumberConfigEntry ::=
          SEQUENCE
          {
            hwEntSipagUserName                 DisplayString,
            hwEntUserExtendNumber              DisplayString,
            hwEntUserExtendUserGroupId  	   Integer32,
            hwEntUserExtendRowStatus           RowStatus
          }

       hwEntSipagUserName OBJECT-TYPE
          SYNTAX      DisplayString(SIZE(1..32))
          MAX-ACCESS  not-accessible
          STATUS      current
          DESCRIPTION
              "
              Indicates the SipAg user's name.
              "
          ::= { hwEntUserExtendNumberConfigEntry 1 }

        hwEntUserExtendNumber OBJECT-TYPE
          SYNTAX      DisplayString(SIZE(1..32))
          MAX-ACCESS  not-accessible
          STATUS      current
          DESCRIPTION
              "
              Indicates the extend number.
              "
          ::= { hwEntUserExtendNumberConfigEntry 2 }

       hwEntUserExtendUserGroupId OBJECT-TYPE
          SYNTAX      Integer32(0..65535)
          MAX-ACCESS  read-write
          STATUS      current
          DESCRIPTION
              "
              Indicates the user's group id.
              "
          ::= { hwEntUserExtendNumberConfigEntry 3 }

        hwEntUserExtendRowStatus OBJECT-TYPE
          SYNTAX      RowStatus
          MAX-ACCESS  read-write
          STATUS      current
          DESCRIPTION
              "
              Indicates the RowStatus.
              Options:
              active(1)
 	          notInService(2)
 	          notReady(3)
 	          createAndGo(4)
 	          createAndWait(5)
              destroy(6)
              "
          ::= { hwEntUserExtendNumberConfigEntry 4 }

-- ===============================================================================================

     hwEntServiceDataConfigTable OBJECT-TYPE
          SYNTAX      SEQUENCE OF HwEntServiceDataConfigEntry
          MAX-ACCESS  not-accessible
          STATUS      current
          DESCRIPTION
            "
            This table is used to config PSTN user's service data.
            The index of this table is hwEntServiceDataName.
            "
          ::= { hwEntVoiceSipagUserMIB 8 }

        hwEntServiceDataConfigEntry OBJECT-TYPE
          SYNTAX      HwEntServiceDataConfigEntry
          MAX-ACCESS  not-accessible
          STATUS      current
          DESCRIPTION
            "
            This table is used to config PSTN user's service data.
            The index of this entry is hwEntServiceDataName.
            "
          INDEX    {
                    hwEntServiceDataUserName,
                    hwEntServiceDataTelno
                   }
          ::= { hwEntServiceDataConfigTable 1 }

        HwEntServiceDataConfigEntry ::=
          SEQUENCE
          {
            hwEntServiceDataUserName             DisplayString,
            hwEntServiceDataTelno	         DisplayString,
            hwEntServiceDataCentrexNo            Unsigned32,
            hwEntServiceDataCentrexPrefix        DisplayString,
            hwEntServiceDataCentrexDialMode      INTEGER,
            hwEntServiceDataMwiMode              INTEGER,
            hwEntServiceDataHotTime              Integer32,
            hwEntServiceDataHotLineNum           DisplayString,
            hwEntServiceDataDialTone             INTEGER,
            hwEntServiceDataCfbNum               DisplayString,
            hwEntServiceDataCfnrNum              DisplayString,
            hwEntServiceDataCfuNum               DisplayString,
            hwEntServiceDataCfnrTime             Integer32,
            hwEntServiceDataRowStatus            RowStatus,
            hwEntUserAuthAuthName                DisplayString,
            hwEntUserAuthAuthPasswordMode        INTEGER,
            hwEntUserAuthAuthPassword            DisplayString,
            hwEntUserAuthAuthHA1                 DisplayString,
            hwEntUserRightFlagCallHold	         INTEGER,
            hwEntUserRightFlagThreeParty	     INTEGER,
            hwEntUserRightFlagConf	             INTEGER,
            hwEntUserRightFlagCt 	             INTEGER,
            hwEntUserRightFlagCw 	             INTEGER,
            hwEntUserRightFlagMcid               INTEGER,
            hwEntUserRightFlagMwi                INTEGER,
            hwEntUserRightFlagTp                 INTEGER,
            hwEntUserRightFlagCd                 INTEGER,
            hwEntUserRightFlagAnonymousCall      INTEGER,
            hwEntUserRightFlagHotLine            INTEGER,
            hwEntUserRightFlagUus1               INTEGER,
            hwEntUserRightFlagUus2               INTEGER,
            hwEntUserRightFlagUus3               INTEGER
          }

        hwEntServiceDataUserName OBJECT-TYPE
          SYNTAX      DisplayString(SIZE(0..32))
          MAX-ACCESS  not-accessible
          STATUS      current
          DESCRIPTION
              "
              Indicates the user name of the service data.
              "
          ::= { hwEntServiceDataConfigEntry 1 }

        hwEntServiceDataTelno OBJECT-TYPE
          SYNTAX      DisplayString(SIZE(0..32))
          MAX-ACCESS  not-accessible
          STATUS      current
          DESCRIPTION
              "
              Indicates the telephone number of the service data.
              "
          ::= { hwEntServiceDataConfigEntry 2 }

        hwEntServiceDataCentrexNo OBJECT-TYPE
          SYNTAX      Unsigned32(0..4294967295)
          MAX-ACCESS  read-create
          STATUS      current
          DESCRIPTION
              "
              Indicates the centrex number.
              "
          ::= { hwEntServiceDataConfigEntry 3 }

        hwEntServiceDataCentrexPrefix OBJECT-TYPE
          SYNTAX      DisplayString(SIZE(0..7))
          MAX-ACCESS  read-create
          STATUS      current
          DESCRIPTION
              "
              Indicates the centrex prefix.
              "
          ::= { hwEntServiceDataConfigEntry 4 }

        hwEntServiceDataCentrexDialMode OBJECT-TYPE
          SYNTAX      INTEGER{directly(1), secondary(2)}
          MAX-ACCESS  read-create
          STATUS      current
          DESCRIPTION
              "
              Indicates the centrex dial mode.
              Options:
              1. directly(1)   -dial directly
              2. secondary(2)  -dial secondary
              Default: directly(1)
              "
          ::= { hwEntServiceDataConfigEntry 5 }

        hwEntServiceDataMwiMode OBJECT-TYPE
          SYNTAX      INTEGER{deferred(1), immediate(2), combine(3)}
          MAX-ACCESS  read-create
          STATUS      current
          DESCRIPTION
              "
              Indicates the mwi mode.
              Options:
              deferred(1)
              immediate(2)
              combine(3)
              Default: deferred(1)
              "
          ::= { hwEntServiceDataConfigEntry 6 }

        hwEntServiceDataHotTime OBJECT-TYPE
          SYNTAX      Integer32(0..255)
          MAX-ACCESS  read-create
          STATUS      current
          DESCRIPTION
              "
              Indicates the hotline time.
              Default: 5
              Unit: second
              "
          ::= { hwEntServiceDataConfigEntry 7 }

        hwEntServiceDataHotLineNum OBJECT-TYPE
          SYNTAX      DisplayString(SIZE(0..32))
          MAX-ACCESS  read-create
          STATUS      current
          DESCRIPTION
              "
              Indicates the hotline number.
              "
          ::= { hwEntServiceDataConfigEntry 8 }

        hwEntServiceDataDialTone OBJECT-TYPE
          SYNTAX      INTEGER{normal(1),special(2),mw(3)}
          MAX-ACCESS  read-create
          STATUS      current
          DESCRIPTION
              "
              Indicates the dial tone.
              Options:
              normal(1)    -normal tone
              special(2)   -special tone
              mw(3)        -message waiting tone
              Default: normal(1)
              "
           ::= { hwEntServiceDataConfigEntry 9 }

        hwEntServiceDataCfbNum OBJECT-TYPE
          SYNTAX      DisplayString(SIZE(0..32))
          MAX-ACCESS  read-create
          STATUS      current
          DESCRIPTION
              "
              Indicates the cfb number.
              "
          ::= { hwEntServiceDataConfigEntry 10 }

        hwEntServiceDataCfnrNum OBJECT-TYPE
          SYNTAX      DisplayString(SIZE(0..32))
          MAX-ACCESS  read-create
          STATUS      current
          DESCRIPTION
              "
              Indicates the cfnr number.
              "
          ::= { hwEntServiceDataConfigEntry 11 }

        hwEntServiceDataCfuNum OBJECT-TYPE
          SYNTAX      DisplayString(SIZE(0..32))
          MAX-ACCESS  read-create
          STATUS      current
          DESCRIPTION
              "
              Indicates the cfu number.
              "
          ::= { hwEntServiceDataConfigEntry 12 }

        hwEntServiceDataCfnrTime OBJECT-TYPE
          SYNTAX      Integer32(0..65535)
          MAX-ACCESS  read-create
          STATUS      current
          DESCRIPTION
              "
              Indicates the cfnr time.
              Default: 100
              Unit: second
              "
          ::= { hwEntServiceDataConfigEntry 13 }

        hwEntServiceDataRowStatus OBJECT-TYPE
          SYNTAX      RowStatus
          MAX-ACCESS  read-create
          STATUS      current
          DESCRIPTION
              "
              Indicates the row status.
              Options:
              active(1)
 	          notInService(2)
 	          notReady(3)
 	          createAndGo(4)
 	          createAndWait(5)
              destroy(6)
              "
          ::= { hwEntServiceDataConfigEntry 14 }

        hwEntUserAuthAuthName OBJECT-TYPE
          SYNTAX      DisplayString(SIZE(0..64))
          MAX-ACCESS  read-write
          STATUS      current
          DESCRIPTION
              "
              Indicates the authorization username.
              "
          ::= { hwEntServiceDataConfigEntry 15 }

        hwEntUserAuthAuthPasswordMode OBJECT-TYPE
          SYNTAX      INTEGER{password(1),ha1(2)}
          MAX-ACCESS  read-write
          STATUS      current
          DESCRIPTION
              "
              Indicates the authorization mode of the password.
              Options:
              password(1)  -authorized by password
              ha1(2)       -authorized by ha1
              Default: password(1)
              "
          ::= { hwEntServiceDataConfigEntry 16 }

        hwEntUserAuthAuthPassword OBJECT-TYPE
          SYNTAX      DisplayString(SIZE(0..64))
          MAX-ACCESS  read-write
          STATUS      current
          DESCRIPTION
              "
              Indicates the authorization password.
              "
          ::= { hwEntServiceDataConfigEntry 17 }

        hwEntUserAuthAuthHA1  OBJECT-TYPE
          SYNTAX      DisplayString(SIZE(0..32))
          MAX-ACCESS  read-write
          STATUS      current
          DESCRIPTION
              "
              Indicates the authorization HA1 password.
              "
          ::= { hwEntServiceDataConfigEntry 18 }

        hwEntUserRightFlagCallHold OBJECT-TYPE
          SYNTAX      INTEGER{enable(1),disable(2)}
          MAX-ACCESS  read-write
          STATUS      current
          DESCRIPTION
              "
              Indicates the right flag of callhold.
              Options:
              enable(1)
              disable(2)
              Default: enable(1)
              "
          ::= { hwEntServiceDataConfigEntry 19 }

        hwEntUserRightFlagThreeParty OBJECT-TYPE
          SYNTAX      INTEGER{enable(1),disable(2)}
          MAX-ACCESS  read-write
          STATUS      current
          DESCRIPTION
              "
              Indicates the right flag of Three-party.
              Options:
              enable(1)
              disable(2)
              Default: enable(1)
              "
          ::= { hwEntServiceDataConfigEntry 20 }

        hwEntUserRightFlagConf OBJECT-TYPE
          SYNTAX      INTEGER{enable(1),disable(2)}
          MAX-ACCESS  read-write
          STATUS      current
          DESCRIPTION
              "
              Indicates the right flag of Conf.
              Options:
              enable(1)
              disable(2)
              Default: enable(1)
              "
          ::= { hwEntServiceDataConfigEntry 21 }

        hwEntUserRightFlagCt OBJECT-TYPE
          SYNTAX      INTEGER{enable(1),disable(2)}
          MAX-ACCESS  read-write
          STATUS      current
          DESCRIPTION
              "
              Indicates the right flag of CT.
              Options:
              enable(1)
              disable(2)
              Default: enable(1)
              "
          ::= { hwEntServiceDataConfigEntry 22 }

        hwEntUserRightFlagCw OBJECT-TYPE
          SYNTAX      INTEGER{enable(1),disable(2)}
          MAX-ACCESS  read-write
          STATUS      current
          DESCRIPTION
              "
              Indicates the right flag of CW.
              Options:
              enable(1)
              disable(2)
              Default: disable(2)
              "
          ::= { hwEntServiceDataConfigEntry 23 }

        hwEntUserRightFlagMcid OBJECT-TYPE
          SYNTAX      INTEGER{enable(1),disable(2)}
          MAX-ACCESS  read-write
          STATUS      current
          DESCRIPTION
              "
              Indicates the right flag of MCID.
              Options:
              enable(1)
              disable(2)
              Default: disable(2)
              "
          ::= { hwEntServiceDataConfigEntry 24 }

        hwEntUserRightFlagMwi OBJECT-TYPE
          SYNTAX      INTEGER{enable(1),disable(2)}
          MAX-ACCESS  read-write
          STATUS      current
          DESCRIPTION
              "
              Indicates the right flag of MWI.
              Options:
              enable(1)
              disable(2)
              Default: disable(2)
              "
          ::= { hwEntServiceDataConfigEntry 25 }

        hwEntUserRightFlagTp OBJECT-TYPE
          SYNTAX      INTEGER{enable(1),disable(2)}
          MAX-ACCESS  read-write
          STATUS      current
          DESCRIPTION
              "
              Indicates the right flag of TP.
              Options:
              enable(1)
              disable(2)
              Default: disable(2)
              "
          ::= { hwEntServiceDataConfigEntry 26 }

        hwEntUserRightFlagCd OBJECT-TYPE
          SYNTAX      INTEGER{enable(1),disable(2)}
          MAX-ACCESS  read-write
          STATUS      current
          DESCRIPTION
              "
              Indicates the right flag of CD.
              Options:
              enable(1)
              disable(2)
              Default: disable(2)
              "
          ::= { hwEntServiceDataConfigEntry 27 }

        hwEntUserRightFlagAnonymousCall OBJECT-TYPE
          SYNTAX      INTEGER{enable(1),disable(2)}
          MAX-ACCESS  read-write
          STATUS      current
          DESCRIPTION
              "
              Indicates the right flag of anonymous-call.
              Options:
              enable(1)
              disable(2)
              Default: disable(2)
              "
          ::= { hwEntServiceDataConfigEntry 28 }


        hwEntUserRightFlagHotLine OBJECT-TYPE
          SYNTAX      INTEGER{enable(1),disable(2)}
          MAX-ACCESS  read-write
          STATUS      current
          DESCRIPTION
              "
              Indicates the right flag of hotline.
              Options:
              enable(1)
              disable(2)
              Default: disable(2)
              "
          ::= { hwEntServiceDataConfigEntry 29 }

        hwEntUserRightFlagUus1 OBJECT-TYPE
          SYNTAX      INTEGER{enable(1),disable(2)}
          MAX-ACCESS  read-write
          STATUS      current
          DESCRIPTION
              "
              Indicates the right flag of UUS1.
              Options:
              enable(1)
              disable(2)
              Default: disable(2)
              "
          ::= { hwEntServiceDataConfigEntry 30 }

        hwEntUserRightFlagUus2 OBJECT-TYPE
          SYNTAX      INTEGER{enable(1),disable(2)}
          MAX-ACCESS  read-write
          STATUS      current
          DESCRIPTION
              "
              Indicates the right flag of UUS2.
              Options:
              enable(1)
              disable(2)
              Default: disable(2)
              "
          ::= { hwEntServiceDataConfigEntry 31 }

        hwEntUserRightFlagUus3 OBJECT-TYPE
          SYNTAX      INTEGER{enable(1),disable(2)}
          MAX-ACCESS  read-write
          STATUS      current
          DESCRIPTION
              "
              Indicates the right flag of UUS3.
              Options:
              enable(1)
              disable(2)
              Default: disable(2)
              "
          ::= { hwEntServiceDataConfigEntry 32 }


    --  ============== conformance information ==============
        hwEntVoiceSipagUserConformance OBJECT IDENTIFIER ::= { hwEntVoiceSipagUserMIB 10 }


        hwEntVoiceSipagUserCompliances OBJECT IDENTIFIER ::= { hwEntVoiceSipagUserConformance 1 }
        hwEntVoiceSipagUserCompliance MODULE-COMPLIANCE
               STATUS      current
               DESCRIPTION
                   "The compliance statement for systems supporting
                the this module."

               MODULE      -- this module
               MANDATORY-GROUPS    {hwEntPstnUserConfigGroup, hwEntPstnUserOperGroup, hwEntBraUserConfigGroup,
				hwEntBraUserOperGroup, hwEntPraUserConfigGroup, hwEntPraUserOperGroup,
				hwEntUserExtendNumberConfigGroup, hwEntServiceDataConfigGroup}

              ::= { hwEntVoiceSipagUserCompliances 1 }


        --  ============== groups ==============
        hwEntVoiceSipagUserGroups OBJECT IDENTIFIER ::= { hwEntVoiceSipagUserConformance 2 }

	   hwEntPstnUserConfigGroup OBJECT-GROUP
	     OBJECTS
	     {
	       	hwEntPstnUserName ,
                hwEntPstnUserPort ,
                hwEntPstnUserMgId,
                hwEntPstnUserTelNo,
                hwEntPstnUserUserGroupId,
                hwEntPstnUserRowStatus,
                hwEntPstnUserPriority,
                hwEntPstnUserPotsLineType,
                hwEntPstnUserDCTime,
                hwEntPstnUserFSKDelayInterval,
                hwEntPstnUserCidTransSequence,
                hwEntPstnUserCidFormat,
                hwEntPstnUserVQEAgc,
                hwEntPstnUserVQESns,
                hwEntPstnUserVQEAgcLevel,
                hwEntPstnUserVQESnsLevel,
                hwEntPstnUserDspInputGain,
                hwEntPstnUserDspOutputGain,
                hwEntPstnUserDetectANSbarBySingleTone,
                hwEntPstnUserBellANS,
                hwEntPstnUserDspParaTemplate,
                hwEntPstnUserCidFskMode,
                hwEntPstnUserCidTasPattern
	     }
	    STATUS current
            DESCRIPTION
                "The hwEntPstnUserConfig group."
            ::= { hwEntVoiceSipagUserGroups 1 }

 	hwEntPstnUserOperGroup OBJECT-GROUP
	     OBJECTS
	     {
	       	hwEntPstnUserOperName,
		hwEntPstnUserSrvState,
		hwEntPstnUserAdminState,
		hwEntPstnUserAdminOper,
		hwEntPstnUserMaxCobTime,
		hwEntPstnUserOnexpire
	     }
	    STATUS current
            DESCRIPTION
                "The hwEntPstnUserOper group."
            ::= { hwEntVoiceSipagUserGroups 2 }

 	hwEntBraUserConfigGroup OBJECT-GROUP
	     OBJECTS
	     {
	       	hwEntBraUserName,
		hwEntBraUserPort,
		hwEntBraUserMgId,
		hwEntBraUserTelNo,
		hwEntBraUserUserGroupId,
		hwEntBraUserRowStatus,
		hwEntBraUserPriority,
		hwEntBraUserUniErrReport,
		hwEntBraUserAutoResumeLimit
	     }
	    STATUS current
            DESCRIPTION
                "The hwEntBraUserConfig group."
            ::= { hwEntVoiceSipagUserGroups 3 }

 	hwEntBraUserOperGroup OBJECT-GROUP
	     OBJECTS
	     {
	       	hwEntBraUserOperName,
		hwEntBraUserB0SrvState,
		hwEntBraUserB1SrvState,
		hwEntBraUserB0AdminState,
		hwEntBraUserB1AdminState,
		hwEntBraUserDState,
		hwEntBraUserAdminOper,
		hwEntBraUserMaxCobTime,
		hwEntBraUserOnexpire
	     }
	    STATUS current
            DESCRIPTION
                "The hwEntBraUserOper group."
            ::= { hwEntVoiceSipagUserGroups 4 }

 	hwEntPraUserConfigGroup OBJECT-GROUP
	     OBJECTS
	     {
	       	hwEntPraUserName,
		hwEntPraUserPort,
		hwEntPraUserMgId,
		hwEntPraUserTelNo,
		hwEntPraUserUserGroupId,
		hwEntPraUserRowStatus,
		hwEntPraUserPriority,
		hwEntPraUserUniErrReport,
		hwEntPraUserSubChnMask,
		hwEntPraUserAutoResumeLimit
	     }
	    STATUS current
            DESCRIPTION
                "The hwEntPraUserConfig group."
            ::= { hwEntVoiceSipagUserGroups 5 }

 	hwEntPraUserOperGroup OBJECT-GROUP
	     OBJECTS
	     {
	       	hwEntPraUserOperName,
		hwEntPraUserBchnSrvState,
		hwEntPraUserBchnAdminState,
		hwEntPraUserDState,
		hwEntPraUserAdminOper,
		hwEntPraUserMaxCobTime,
		hwEntPraUserOnexpire
	     }
	    STATUS current
            DESCRIPTION
                "The hwEntPraUserOper group."
            ::= { hwEntVoiceSipagUserGroups 6 }

	hwEntUserExtendNumberConfigGroup OBJECT-GROUP
	     OBJECTS
	     {
	       	hwEntSipagUserName,
		hwEntUserExtendNumber,
		hwEntUserExtendUserGroupId,
		hwEntUserExtendRowStatus
	     }
	    STATUS current
            DESCRIPTION
                "The hwEntUserExtendNumberConfig group."
            ::= { hwEntVoiceSipagUserGroups 7 }

 	hwEntServiceDataConfigGroup OBJECT-GROUP
	     OBJECTS
	     {
	       	hwEntServiceDataUserName,
		hwEntServiceDataTelno,
		hwEntServiceDataCentrexNo,
		hwEntServiceDataCentrexPrefix,
		hwEntServiceDataCentrexDialMode,
		hwEntServiceDataMwiMode,
		hwEntServiceDataHotTime,
		hwEntServiceDataHotLineNum,
		hwEntServiceDataDialTone,
		hwEntServiceDataCfbNum,
		hwEntServiceDataCfnrNum,
		hwEntServiceDataCfuNum,
		hwEntServiceDataCfnrTime,
		hwEntServiceDataRowStatus,
		hwEntUserAuthAuthName,
		hwEntUserAuthAuthPasswordMode,
		hwEntUserAuthAuthPassword,
		hwEntUserAuthAuthHA1,
		hwEntUserRightFlagCallHold,
		hwEntUserRightFlagThreeParty,
		hwEntUserRightFlagConf,
		hwEntUserRightFlagCt,
		hwEntUserRightFlagCw,
		hwEntUserRightFlagMcid,
		hwEntUserRightFlagMwi,
		hwEntUserRightFlagTp,
		hwEntUserRightFlagCd,
		hwEntUserRightFlagAnonymousCall,
		hwEntUserRightFlagHotLine,
		hwEntUserRightFlagUus1,
		hwEntUserRightFlagUus2,
		hwEntUserRightFlagUus3
	     }
	    STATUS current
            DESCRIPTION
                "The hwEntServiceDataConfig group."
            ::= { hwEntVoiceSipagUserGroups 8 }


END
