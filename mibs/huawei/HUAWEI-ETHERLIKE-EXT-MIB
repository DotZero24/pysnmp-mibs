-- ============================================================================
-- Copyright (C) 2019 by  HUAWEI TECHNOLOGIES. All rights reserved.
-- Description: This MIB is used for defining Huawei's etherlike extended attributes, including
--              ETH port, vlan, service-port, MAC address, queue, Ip traffic parameters, HQos,
--              Net-role, traffic controling.
-- Reference: HUAWEI-DEVICE-MIB,HUAWEI-MIB,HUAWEI-VLAN-MIB,HUAWEI-ETHERNET-OPTICMODULE-MIB
-- Version: V5.78
-- ============================================================================

    HUAWEI-ETHERLIKE-EXT-MIB DEFINITIONS ::= BEGIN

        IMPORTS
            hwFrameIndex, hwSlotIndex, hwPortIndex, hwPortDesc, hwPortPrimaryStatus, hwPortSecondaryStatus, hwConfigChangeIP
                FROM HUAWEI-DEVICE-MIB
            huaweiMgmt
                FROM HUAWEI-MIB
            hwOpticsTemperature, hwOpticsPowerTxLowerThresholdValue,hwOpticsPowerTxUpperThresholdValue,hwOpticsTxPower,hwOpticsRxPower,
            hwOpticsPowerRxUpperThresholdValue,hwOpticsPowerRxLowerThresholdValue,hwOpticsTemperatureUpperThresholdValue,
            hwOpticsTemperatureLowerThresholdValue,hwOpticsVoltageUpperThresholdValue,hwOpticsVoltageLowerThresholdValue,
            hwOpticsSupplyVoltage,hwOpticsCurrentUpperThresholdValue,hwOpticsCurrentLowerThresholdValue,hwOpticsTxBiasCurrent,
            hwOpticsLaserTemperatureUpperThresholdValue,hwOpticsLaserTemperatureLowerThresholdValue,hwOpticsLaserTemperature,
            hwOpticsWaveLengthUpperThresholdValue,hwOpticsWaveLengthLowerThresholdValue,hwOpticsWaveLength,
            hwOpticsTecCurrentUpperThresholdValue,hwOpticsTecCurrentLowerThresholdValue,hwOpticsTecCurrent
                FROM HUAWEI-ETHERNET-OPTICMODULE-MIB
            ifIndex, InterfaceIndex
                FROM IF-MIB
            TimeTicks, Counter32, Counter64, IpAddress, OBJECT-TYPE, MODULE-IDENTITY,
            NOTIFICATION-TYPE, OBJECT-IDENTITY,Integer32,Unsigned32
                FROM SNMPv2-SMI
            SnmpAdminString
                FROM SNMP-FRAMEWORK-MIB
            hwVlanIndex
                FROM HUAWEI-VLAN-MIB
            hwProtection,hwPgGroupId,hwPsGroupLoadBalanceState
                FROM HUAWEI-PROTECTION-MIB
            InetAddressType,InetAddress,InetAddressPrefixLength,InetPortNumber
               FROM INET-ADDRESS-MIB
            TruthValue, RowStatus, MacAddress, TEXTUAL-CONVENTION, DisplayString,DateAndTime
                FROM SNMPv2-TC
            hwOntIndex
                FROM HUAWEI-DEVICE-MIB;

        hwEthernetPort MODULE-IDENTITY
            LAST-UPDATED "201903190000Z"
            ORGANIZATION "Huawei Technologies Co.,Ltd."
            CONTACT-INFO
                "Huawei Industrial Base
                 Bantian, Longgang
                 Shenzhen 518129
                 People's Republic of China
                 Website: http://www.huawei.com
                 Email: support@huawei.com
                "
            DESCRIPTION
                "This MIB is used for defining Huawei's etherlike extended attributes, including
                 ETH port, vlan, service-port, MAC address, queue, Ip traffic parameters, HQos,
                 Net-role, traffic controling.
                "
      --  Revision history
      REVISION     "201903190000Z"
      DESCRIPTION  "V5.78, modified the MAX-ACCESS of hwifEthernetComboWorkMode from read-only to read-write"

	  REVISION     "201903130000Z"
      DESCRIPTION  "V5.77, modified the description of hwQueueStatsStartTime"

	  REVISION     "201901230000Z"
      DESCRIPTION  "V5.76, modified the description of HwAggregatePortEntry"

	  REVISION     "201812210000Z"
      DESCRIPTION  "V5.75, modified the description of hwAggregatePortStatus, hwMacHashConflictRecordEntry, hwAggregatePortEntry"

      REVISION     "201811200000Z"
      DESCRIPTION  "V5.74, added new table hwExtProtocolForceForwardingPolicyTable."

      REVISION     "201810200000Z"
      DESCRIPTION  "V5.73, added leaf node hwifAggregateStatus of hwifAggregateTable.
                    Added new table hwAggregatePortTable."

      REVISION     "201810120000Z"
      DESCRIPTION  "V5.72, modified the description of hwifEthernetSpeed"

	  REVISION     "201809260000Z"
      DESCRIPTION  "V5.71, modified the description of hwQueuePerformanceStatsTable, hwQueuePerformanceStatsEntry, hwAggLoadbalancingConfigTable, hwAggLoadbalancingConfigEntry,
	                       hwAggLoadbalancingTable, hwAggLoadbalancingEntry"

      REVISION     "201809160000Z"
      DESCRIPTION  "V5.70, added leaf node hwPort10GLicControlObjects,hwPort10GlicPortNum,hwPort10GLicRtuAuthSwitch"

      REVISION     "201809100000Z"
      DESCRIPTION  "V5.69, modified the range of leaf node hwAggLBInportIndex."

      REVISION     "201808270000Z"
      DESCRIPTION  "V5.68, added leaf node hwAggLBInportIndex of hwAggLoadbalancingConfigTable."

      REVISION     "201808250000Z"
      DESCRIPTION  "V5.67, added leaf node hwOnuSwitchNotifyConfigIpv6."
      REVISION     "201808090000Z"
      DESCRIPTION  "V5.66, added leaf node hwEthernetLightTestTimeduration, hwEthernetLightTestTestStatus,
                           hwEthernetLightTestFinshStatus."

      REVISION     "201807060000Z"
      DESCRIPTION  "V5.65, added enumerated s100000M(100000) in hwifEthernetSpeed leaf node;
                    added enumerated onehundredge(4) in hwifEthernetPortType leaf node."

      REVISION     "201806120000Z"
      DESCRIPTION  "V5.64, added the enumerated value vxlan(18) to the hwExtSrvFlowSourceParaType leaf.
                    modified the description of hwExtSrvFlowSourceParaType and hwExtSrvFlowSourceMultiServiceUserPara.
                    added leaf node hwifAggregateRandomSeed of hwifAggregateTable.
                    added new table hwAggLoadbalancingConfigTable.
                    added new table hwAggLoadbalancingTable."

      REVISION     "201804260000Z"
      DESCRIPTION  "V5.63, added leaf nodes hwSRv6TunnelHardwareOverloadTrap, hwSRv6TunnelHardwareOverloadRestoreTrap.
                            added enumerated srv6tunnelhardware(6) in hwResourceType leaf node."

      REVISION     "201803270000Z"
      DESCRIPTION  "V5.62, added leaf nodes hwIPTunnelHardwareOverloadTrap, hwIPTunnelHardwareOverloadRestoreTrap, hwVPNHardwareOverloadTrap, hwVPNHardwareOverloadRestoreTrap.
                            added enumerated iptunnelhardware(4) and vpnhardware(5) in hwResourceType leaf node."

      REVISION     "201803200000Z"
      DESCRIPTION  "V5.61, modified the description of leaf nodes hwExtSrvFlowPara4, hwExtSrvFlowPara5."

      REVISION     "201803190000Z"
      DESCRIPTION  "V5.60, modified the range of leaf nodes hwifEthernetPauseFrameTag:
                    hwifEthernetComboWorkMode and hwifEthernetLinkflapping"

      REVISION     "201803150000Z"
      DESCRIPTION  "V5.59, Add the following leave into hwEthernetLineGlobalConfig:
                    hwOpticsModuleShowMode."

      REVISION     "201803010000Z"
      DESCRIPTION  "V5.58, modified the range of leaf nodes hwExtSrvFlowSourceMultiServiceType."

      REVISION     "201802240000Z"
      DESCRIPTION  "V5.57, added leaf node hwifEthernetTrafficRateBroadcast, hwifEthernetTrafficRateMulticast,
                           hwifEthernetTrafficRateUnknowncast."

      REVISION     "201802050000Z"
      DESCRIPTION  "V5.56, added leaf node hwTrafficSuppressRateBroadcast, hwTrafficSuppressRateMulticast,
                           hwTrafficSuppressRateUnknowncast."

	  REVISION     "201801180000Z"
      DESCRIPTION  "V5.55, modified the description of leaf nodes hwDslamNonUnicastUpportMonitorBroadcastThdDeftAutoValue, hwDslamNonUnicastUpportMonitorUnknownUnicastThdDeftAutoValue,
                           hwDslamNonUnicastUpportMonitorUnknownMulticastThdDeftAutoValue, hwDslamNonUnicastUpportMonitorBroadcastThd,
                           hwDslamNonUnicastUpportMonitorUnknownUnicastThd, hwDslamNonUnicastUpportMonitorUnknownMulticastThd,
                           hwDslamNonUnicastUpportMonitorBroadcastThdActiveValue, hwDslamNonUnicastUpportMonitorUnknownUnicastThdActiveValue,
                           hwDslamNonUnicastUpportMonitorUnknownMulticastThdActiveValue"

      REVISION     "201801160000Z"
      DESCRIPTION  "V5.54, modified the UNITS of leaf nodes hwDslamNonUnicastUpportMonitorBroadcastRate, hwDslamNonUnicastUpportMonitorUnknownUnicastRate,
                           hwDslamNonUnicastUpportMonitorUnknownMulticastRate, hwDslamNonUnicastUpportMonitorPeakBroadcastRate,
                           hwDslamNonUnicastUpportMonitorPeakUnknownUnicastRate, hwDslamNonUnicastUpportMonitorPeakUnknownMulticastRate."

      REVISION     "201712110000Z"
      DESCRIPTION  "V5.53, added leaf node hwDslamNonUnicastUpportMonitorSwitch, hwDslamNonUnicastUpportMonitorPeriod,
                           hwDslamNonUnicastUpportMonitorBroadcastThdDeftAutoValue,
                           hwDslamNonUnicastUpportMonitorUnknownUnicastThdDeftAutoValue,
                           hwDslamNonUnicastUpportMonitorUnknownMulticastThdDeftAutoValue,
                           hwDslamNonUnicastUpportMonitorNotifySwitch,
                           hwDslamNonUnicastUpportMonitorStartTime, hwDslamNonUnicastUpportMonitorEndTime.
                           added new table hwDslamNonUnicastUpportMonitor, hwDslamNonUnicastUpportMonitorMemberTable,
                           hwDslamNonUnicastUpportMonitorRecordTable, hwDslamNonUnicastUpportMonitorPeakRecordTable.
                           added new trap hwDslamNonUnicastUpportMonitorRecordTrap."

      REVISION     "201711290000Z"
      DESCRIPTION  "V5.52, modify description of leaf node hwifEthernetLineTest, add -1 which means notSupport."

      REVISION     "201711200000Z"
      DESCRIPTION  "V5.51, deleted leaf node hwDslamNonUnicastUpportMonitorSwitch, hwDslamNonUnicastUpportMonitorPeriod,
                           hwDslamNonUnicastUpportMonitorBroadcastThreshold,
                           hwDslamNonUnicastUpportMonitorUnknownUnicastThreshold,
                           hwDslamNonUnicastUpportMonitorUnknownMulticastThreshold,
                           hwDslamNonUnicastUpportMonitorNotifySwitch,
                           hwDslamNonUnicastUpportMonitorStartTime, hwDslamNonUnicastUpportMonitorEndTime.
                           deleted table hwDslamNonUnicastUpportMonitor, hwDslamNonUnicastUpportMonitorMemberTable,
                           hwDslamNonUnicastUpportMonitorRecordTable, hwDslamNonUnicastUpportMonitorPeakRecordTable.
                           deleted trap hwDslamNonUnicastUpportMonitorRecordTrap."

      REVISION     "201710300000Z"
      DESCRIPTION  "V5.50, added leaf node hwDslamNonUnicastUpportMonitorSwitch, hwDslamNonUnicastUpportMonitorPeriod,
                           hwDslamNonUnicastUpportMonitorBroadcastThreshold,
                           hwDslamNonUnicastUpportMonitorUnknownUnicastThreshold,
                           hwDslamNonUnicastUpportMonitorUnknownMulticastThreshold,
                           hwDslamNonUnicastUpportMonitorNotifySwitch,
                           hwDslamNonUnicastUpportMonitorStartTime, hwDslamNonUnicastUpportMonitorEndTime.
                           added new table hwDslamNonUnicastUpportMonitor, hwDslamNonUnicastUpportMonitorMemberTable,
                           hwDslamNonUnicastUpportMonitorRecordTable, hwDslamNonUnicastUpportMonitorPeakRecordTable.
                           added new trap hwDslamNonUnicastUpportMonitorRecordTrap."

      REVISION     "201710260000Z"
      DESCRIPTION  "V5.49, modified the range of leaf nodes hwifEthernetPauseFrameTag, add two enumeration value"

      REVISION     "201709250000Z"
      DESCRIPTION  "V5.48, added leaf node hwQueueStatisticsPassedGreenBytes,hwQueueStatisticsPassedGreenNumber,
      				hwQueueStatisticsPassedYellowBytes,hwQueueStatisticsPassedYellowNumber.
      				added leaf node hwQueueStatsPassedGreenBytes,hwQueueStatsPassedGreenNumber,
      				hwQueueStatsPassedYellowBytes,hwQueueStatsPassedYellowNumber."

      REVISION     "201709080000Z"
      DESCRIPTION  "V5.47,add leaf node hwFabricMacHashConflictAutoAdjust.
					added new table hwMacHashConflictRecordTable.
                    add leaf nodes hwMacHashConflictRecordIndex, hwMacHashConflictRecordMacAddress,
                    hwMacHashConflictRecordVlan, hwMacHashConflictRecordLocation, hwMacHashConflictRecordDetectedTime,
                    hwMacHashConflictRecordResolvedTime."

      REVISION     "201709060000Z"
      DESCRIPTION  "V5.46, modified the description of trap hwPacketAttackTrap.
                    added new trap hwInnerForwardingFaultAlarmTrap and hwInnerForwardingRecoverAlarmTrap.
                    added leaf node hwifAggregateHashOption of hwifAggregateTable."

      REVISION     "201708210000Z"
      DESCRIPTION  "V5.45,modified the description and value list of leaf node hwCarGroupSrvFlowEndPointType."

      REVISION     "201708140000Z"
      DESCRIPTION  "V5.44,modified the description of leaf node  hwExtSrvFlowSourcePara1,hwExtSrvFlowSourcePara2,hwExtSrvFlowSourcePara3 ."

      REVISION     "201708010000Z"
      DESCRIPTION  "V5.43,modified MAX-ACCESS of leaf node  hwQueueStatsTimeElapsed ."

      REVISION     "201707180000Z"
      DESCRIPTION  "V5.42, added new table hwQueuePerformanceStatsTable.
                    added leaf nodes hwQueueStatsIntervalType, hwQueueStatsIntervalNumId,
                    hwQueueStatsDroppedYellowNumber,hwQueueStatsDroppedGreenNumber,
                    hwQueueStatsDroppedUnRecognizedColorNumber,hwQueueStatsPassedNumber,
                    hwQueueStatsPassedBytes,hwQueueStatsTimeElapsed,
                    hwQueueStatsValidInterval,hwQueueStatsStartTime,
		    added leaf nodes hwQueueStatisticsDroppedUnRecognizedColorNumber, hwQueueStatisticsDroppedGreenNumber,
                    hwQueueStatisticsDroppedYellowNumber of hwQueueStatisticsstateTable."

      REVISION     "201707130000Z"
      DESCRIPTION  "V5.41, added leaf node hwifEthernetOfflineTxOffTime of hwEthernetTable."

      REVISION     "201707120000Z"
      DESCRIPTION  "V5.40, added leaf node hwCarGroupSrvFlowEndPointType of hwCarGroupSrvFlowTable."

      REVISION     "201706260000Z"
      DESCRIPTION  "V5.39, added leaf node hwMacAddressClearForOntPortDownSwitch.
                           added new trap hwPacketAttackTrap.
				           added leaf node hwPacketAttackMACAddress.
				           added leaf node hwPacketNumberOfMACAddress.
				           added leaf node hwPacketAttackPacketType.
				           added leaf node hwPacketNumberOfPacketType."
      REVISION     "201706210000Z"
      DESCRIPTION  "V5.38, modified the range of leaf nodes hwifEthernetMTU and hwXponPortMtu."

      REVISION     "201706080000Z"
      DESCRIPTION  "V5.37, added leaf node hwTrafficUpportMonitorUpstreamLast, hwTrafficUpportMonitorUpstream,
          hwTrafficUpportMonitorDownstreamLast, hwTrafficUpportMonitorDownstream,
	  hwDslamTrafficUpportMonitorUpstreamLast, hwDslamTrafficUpportMonitorDownstreamLast,
	  hwDslamTrafficUpportMonitorNotifySwitch, hwDslamTrafficUpportMonitorActiveThreshold,
	  hwDslamTrafficUpportMonitorStartTime, hwDslamTrafficUpportMonitorEndTime,
	  hwDslamTrafficUpportMonitorPeakRecordTable, hwDslamTrafficUpportMonitorPeakRecordEntry,
	  hwDslamTrafficUpportMonitorPeakRecordIfIndex, hwDslamTrafficUpportMonitorPeakUpstreamRecordTime,
	  hwDslamTrafficUpportMonitorPeakUpstream, hwDslamTrafficUpportMonitorPeakDownstreamRecordTime,
	  hwDslamTrafficUpportMonitorPeakDownstream.
	  Modified the SYNTAX of hwDslamTrafficUpportMonitorUpstream, hwDslamTrafficUpportMonitorDownstream."

      REVISION     "201705230000Z"
      DESCRIPTION  "V5.36, added leaf node hwifEthernetLinkflapping of hwEthernetTable."

      REVISION     "201704050000Z"
      DESCRIPTION  "V5.35, added leaf node hwRateProfileIndex of hwRateProfileTable."

	  REVISION     "201703270000Z"
      DESCRIPTION  "V5.34, added leaf nodes hwDslamTrafficUpportMonitor,hwDslamTrafficUpportMonitorSwitch
	  hwDslamTrafficUpportMonitorPeriod,hwDslamTrafficUpportMonitorThreshold,hwDslamTrafficUpportMonitorMemberTable,
	  hwDslamTrafficUpportMonitorMemberEntry,hwDslamTrafficUpportMonitorMemberIfIndex,hwDslamTrafficUpportMonitorRowStatus,
	  hwDslamTrafficUpportMonitorRecordTable,hwDslamTrafficUpportMonitorRecordEntry,hwDslamTrafficUpportMonitorRecordIfIndex,
	  hwDslamTrafficUpportMonitorRecordIndex,hwDslamTrafficUpportMonitorRecordTime,hwDslamTrafficUpportMonitorUptream,
	  hwDslamTrafficUpportMonitorDownStream."

      REVISION     "201703250000Z"
      DESCRIPTION  "V5.33, modified the range of leaf nodes hwifEthernetMTU."

	  REVISION     "201703130000Z"
      DESCRIPTION  "V5.32, added new table hwXponPortMtuTable."

	  REVISION     "201702250000Z"
      DESCRIPTION  "V5.31, modified the description of leaf nodes hwSrvFlowBundleMemberSortPara and hwExtSrvFlowBundleMemberSortPara."

      REVISION     "201701250000Z"
      DESCRIPTION  "V5.30, added leaf node hwUplinkSwitchNotifyConfigBtv."

      REVISION     "201612200000Z"
      DESCRIPTION  "V5.29, added leaf node hwShapingBurstSizeConfigMode."

      REVISION     "201612020000Z"
      DESCRIPTION  "V5.28,deleted the default value of the leaf node hwPriorityGroupCarStatRowStatus.
                          Modified the description of leaf nodes hwPriorityGroupCarStatTimeoutDuration, hwPriorityGroupCarStatRunningStatus and hwPriorityGroupCarStatRemainTime."

      REVISION     "201612010000Z"
      DESCRIPTION  "V5.27, added leaf nodes hwMacLimitActionSwitch, hwMacLimitSendEvent of hwEthernetPort.
                          Added trap nodes hwMacLimitOverflowTrap, hwMacLimitOverflowRecoverTrap of hwEthernetAlarmTrapsOids."

      REVISION     "201611150000Z"
      DESCRIPTION  "V5.26, added leaf node hwPriorityGroupCarStatRemainTime of hwPriorityGroupCarStatTable.
      		          Modified the index order of the hwPriorityGroupCarStatTable.
			  Modified the attribute of the hwPriorityGroupCarStatDirection.
      		          Modified the range value of the hwPriorityGroupCarStatTimeoutDuration."
      REVISION     "201610250000Z"
      DESCRIPTION  "V5.25, added leaf node hwIpTrafficWrrWeightGreen of hwIpTrafficParamTable.
      		          Modified the value range of the trap node hwIpTrafficParamChangeTrap.
      		          Modified the OID of table hwBoardCrcErrorAlarmControlTable."

      REVISION     "201610200000Z"
      DESCRIPTION  "V5.24, added leaf node hwifEthernetOpticModuleState of hwEthernetTable."

      REVISION     "201610190000Z"
      DESCRIPTION  "V5.23, modified the description of leaf nodes hwTrafficSuppressBroadcast, hwTrafficSuppressMulticast, hwTrafficSuppressUnknowncast and hwCtpEthJumboFrameEnable."

      REVISION     "201610100000Z"
      DESCRIPTION  "V5.22, modified the type of leaf node hwQueueStatisticsPassedNumber and hwQueueStatisticsDroppedNumber from Unsigned32 to Counter64.
                    added leaf node hwIpTrafficWrrWeightYellow of hwIpTrafficParamTable.
                    Modified the value range of the trap node hwIpTrafficParamChangeTrap."

      REVISION     "201609240000Z"
      DESCRIPTION  "V5.21, added new table hwBoardCrcErrorAlarmControlTable.
                    Added leaf nodes hwBoardCrcErrorAlarmSwitch, hwBoardCrcErrorAlarmDetectInterval, hwBoardCrcErrorAlarmDetectMultiplier."

      REVISION     "201609170000Z"
      DESCRIPTION  "V5.20, added leaf node hwCtpEthJumboFrameEnable of hwCtpEthAttributeCfgTable.
                    Modified the description of leaf nodes hwTrafficSuppressBroadcast, hwTrafficSuppressMulticast and hwTrafficSuppressUnknowncast"

      REVISION     "201609130000Z"
      DESCRIPTION  "V5.19, modified the description of hwIpTrafficE2EPriorityMappingIndex."

      REVISION     "201608290000Z"
      DESCRIPTION  "V5.18, added new table hwAutoDeleteUnusedProfileTable and hwPriorityGroupCarStatTable.
                    Added leaf nodes hwIpTrafficRateProfileName, hwIpTrafficQueuePolicyProfileIndex and hwIpTrafficPriorityGroupProfileName.
                    Added leaf node hwTrafficInnerPriForceModify.
                    Modified the value range of hwIpTrafficPriorityPolicy and hwPbitsToPbitsMappingIndex."

      REVISION     "201608190000Z"
      DESCRIPTION  "V5.17, added new table hwRateProfileTable, hwQueuePolicyProfileTable and hwPriorityGroupProfileTable."

      REVISION     "201606130000Z"
      DESCRIPTION  "V5.16, added leaf nodes hwIpTrafficE2EPriority, hwIpTrafficE2EPriorityMappingIndex."

      REVISION     "201604130000Z"
      DESCRIPTION  "V5.15, modified the value range of hwCarGroupIndex, hwCarGroupMemberIndex."

      REVISION     "201603230000Z"
      DESCRIPTION  "V5.14, modified the value range of hwProfileCosQueueMaxBufferSizeQueue0, hwProfileCosQueueMaxBufferSizeQueue1,
                    hwProfileCosQueueMaxBufferSizeQueue2, hwProfileCosQueueMaxBufferSizeQueue3,
                    hwProfileCosQueueMaxBufferSizeQueue4, hwProfileCosQueueMaxBufferSizeQueue5,
                    hwProfileCosQueueMaxBufferSizeQueue6, hwProfileCosQueueMaxBufferSizeQueue7,
                    hwQueueMaxBufferSizeQueue0,hwQueueMaxBufferSizeQueue1,hwQueueMaxBufferSizeQueue2,
                    hwQueueMaxBufferSizeQueue3,hwQueueMaxBufferSizeQueue4,hwQueueMaxBufferSizeQueue5,
                    hwQueueMaxBufferSizeQueue6 and hwQueueMaxBufferSizeQueue7."

      REVISION     "201603180000Z"
      DESCRIPTION  "V5.13, modified the value range of hwStaticMacIndex, hwStaticNextFreeIndex."

      REVISION     "201601300000Z"
      DESCRIPTION  "V5.12, modified the description of trap node hwMacConflictNewTrap."

      REVISION     "201601210000Z"
      DESCRIPTION  "V5.11, modified the description of hwXponCarportColorSensitive."

      REVISION     "201601160000Z"
      DESCRIPTION  "V5.10, added leaf node hwFlappingMacAddress,
                    modifyed the OBJECT of hwMacAddressFlappingOverTrap, hwMacAddressFlappingOverRestoreTrap."

      REVISION     "201512220000Z"
      DESCRIPTION  "V5.09, added leaf nodes hwProfileCosQueueMaxBufferSizeQueue0, hwProfileCosQueueMaxBufferSizeQueue1,
                    hwProfileCosQueueMaxBufferSizeQueue2, hwProfileCosQueueMaxBufferSizeQueue3,
                    hwProfileCosQueueMaxBufferSizeQueue4, hwProfileCosQueueMaxBufferSizeQueue5,
                    hwProfileCosQueueMaxBufferSizeQueue6 and hwProfileCosQueueMaxBufferSizeQueue7.
                    added new table hwQueueMaxBufferSizeTable."

      REVISION     "201512040000Z"
      DESCRIPTION  "V5.08, added leaf nodes hwMacAddressFlappingPortInfo,
                    hwMacAddressFlappingOverTrap,
                    hwMacAddressFlappingOverRestoreTrap."

      REVISION     "201511200000Z"
      DESCRIPTION  "V5.07, added leaf nodes hwMacAddressFlappingDetectionControl, hwMacAddressFlappingDetectionPeriod,
                    hwMacAddressFlappingDetectionLowerThreshold, hwMacAddressFlappingDetectionUpperThreshold."

      REVISION     "201511090000Z"
      DESCRIPTION  "V5.06, added two enumerated values byDoubleVlan(5) and by8021pList(6) in hwFlowMulitiServiceType leaf node."

      REVISION     "201510130000Z"
      DESCRIPTION  "V5.05, added new table hwIpTrafficNameToIndexTable."

      REVISION     "201510090000Z"
      DESCRIPTION  "V5.04, added leaf node hwIpTrafficColorSource.
                    added leaf nodes hwProfileCosQueueWREDIndexQue0, hwProfileCosQueueWREDIndexQue1,
                    hwProfileCosQueueWREDIndexQue2, hwProfileCosQueueWREDIndexQue3,
                    hwProfileCosQueueWREDIndexQue4, hwProfileCosQueueWREDIndexQue5,
                    hwProfileCosQueueWREDIndexQue6 and hwProfileCosQueueWREDIndexQue7."

      REVISION     "201509170000Z"
      DESCRIPTION  "V5.03, added enumerated rf(17) in hwExtSrvFlowSourceParaType leaf node."

      REVISION     "201509020000Z"
      DESCRIPTION  "V5.02, added the definition of the trap node hwMacConflictNewTrap"

      REVISION     "201508290000Z"
      DESCRIPTION  "V5.01, added the hwOnuSwitchNotify.
                    added leaf node hwOnuSwitchNotifyConfigIpv4.
		    modified the description of hwUplinkSwitchNotifyConfig."

      REVISION     "201508270000Z"
      DESCRIPTION  "V5.00, added new table hwPortAutoServiceParaTable."

      REVISION     "201508040000Z"
      DESCRIPTION  "V4.99, added the hwUplinkSwitchNotify.
                    added leaf node hwifAggregateLeastLinkNum of hwifAggregateTable.
                    modified the description of hwifAggregateMaxLinkNum."

      REVISION     "201507140000Z"
      DESCRIPTION  "V4.98, added the definition of the trap nodes: hwPortCmtsFrameAddFailTrap."

      REVISION     "201506230000Z"
      DESCRIPTION  "V4.97, added the definition of the trap nodes: hwPortAutoServiceAddFailureTrap, hwPortAutoServiceParaIncorrectTrap.
	                added the definition of the nodes: hwAutoServiceAddContent, hwAutoServiceProcResult.
                    "

      REVISION     "201506090000Z"
      DESCRIPTION  "V4.96, added the definition of the trap nodes: hwIPRouteHardwareOverloadTrap, hwIPRouteHardwareOverloadRestoreTrap.
	                added enumerated iproutehardware(3) in hwResourceType leaf node.
                    "

      REVISION     "201505070000Z"
      DESCRIPTION  "V4.95, added new table hwOntBindQosPolicyProfileTable."

      REVISION     "201504170000Z"
      DESCRIPTION  "V4.94, added enumerated off(3) and colorWred(4) in hwEarlyDropMode leaf node."

      REVISION     "201504160000Z"
      DESCRIPTION  "V4.93, modify the description of hwIpTrafficDSCP and hwIpTrafficDSCPMappingIndex."

      REVISION     "201504100000Z"
      DESCRIPTION  "V4.92, modify the description of the leaf nodes in hwAggregateStatisticsTable."

      REVISION     "201504020000Z"
      DESCRIPTION  "V4.91, modify the value range of hwCosPortOntId, hwCosPortGemIndex and hwFlowIndexQueryForPPPoESmltOnuId."

      REVISION     "201503160000Z"
      DESCRIPTION  "V4.90, modify mib leaf node of the hwExtSrvFlowVlanid value range, modified the MAX-ACCESS of leaf nodes hwCarGroupIndex."

      REVISION     "201503120000Z"
      DESCRIPTION  "V4.89, modify the gfast to fast of the hwExtSrvFlowParaType value range."

      REVISION     "201501200000Z"
      DESCRIPTION  "V4.88, modify mib leaf node hwExtSrvFlowNNIInnerVlanId, hwExtSrvFlowSimulationServiceType."

      REVISION     "201412300000Z"
      DESCRIPTION  "V4.87, added new table hwEthTrafficSuppressDefaultTable."

      REVISION     "201412200000Z"
      DESCRIPTION  "V4.86, modified the description of hwIpdslamBindIpTable, hwIpdslamBindIpEntry and hwIpdslamBindIpSubIndex."

      REVISION     "201412100000Z"
      DESCRIPTION  "V4.85, added leaf node hwifAggregateMasterPortIndex of hwifAggregateTable."

      REVISION     "201411280000Z"
      DESCRIPTION  "V4.84, added leaf node hwPortBindInboundQosPolicyProfileName."

      REVISION     "201411270000Z"
      DESCRIPTION  "V4.83, modified the value range of hwIpdslamBindIpMaskLength."

      REVISION     "201411180000Z"
      DESCRIPTION  "V4.82, modify mib leaf node hwIpTrafficCbs, hwIpTrafficPbs."

      REVISION     "201411070000Z"
      DESCRIPTION  "V4.81, added the enumerated value gfast(16) to the hwExtSrvFlowParaType leaf.
                    modified the description of hwExtSrvFlowPara1, hwExtSrvFlowPara2, hwExtSrvFlowPara3, hwExtSrvFlowPara4, hwExtSrvFlowPara5 and hwExtSrvFlowParaType."

      REVISION     "201410220000Z"
      DESCRIPTION  "V4.80, modify mib leaf node hwifEthernetTxPowerResumeDetect ."

      REVISION     "201410210000Z"
      DESCRIPTION  "V4.79, modified the MAX-ACCESS of leaf nodes hwifAggregateRowStatus, hwBoardBindRowStatus, hwPortVlanPolicingTrafficRowStatus,
                    hwCarGroupRowStatus, hwWREDRowStatus, hwCosQueueDepthRateSlotRowStatus, hwEarlyDropModeSlotRowStatus, hwSrvPortExtStatRowStatus,
		    hwStaticMacRowStatus, hwIsolateRowstatus, hwPortIsolateGroupRowStatus, hwDynamicMacRowStatus, hwUniServiceDataEntryStatus;
		    modified the MAX-ACCESS and value range of hwCarGroupIndex."

      REVISION     "201409150000Z"
      DESCRIPTION  "V4.78, added leaf nodes  hwifEthernetTxPowerResumeDetect,   hwifEthernetTxPowerDetectInterval,
      		     hwifEthernetTxPowerResumeDuration and hwifEthernetTxPowerManualResume ."

      REVISION     "201408300000Z"
      DESCRIPTION  "V4.77, modified the syntax of hwStaticMacMacAddr from MacAddress to OCTET STRING.
                    Modified the description of hwIpTrafficInnerPriority.
                    Modified the definition of hwEarlyDropColorBasedThresholdCos0, hwEarlyDropColorBasedThresholdCos1, hwEarlyDropColorBasedThresholdCos2,
                    hwEarlyDropColorBasedThresholdCos3, hwEarlyDropColorBasedThresholdCos4, hwEarlyDropColorBasedThresholdCos5, hwEarlyDropColorBasedThresholdCos6,
                    and hwEarlyDropColorBasedThresholdCos7"

      REVISION     "201408190000Z"
      DESCRIPTION  "V4.76, added leaf nodes hwSrvPortExtStatUsDiscardedPacketsByL3Forward and hwSrvPortExtStatDsDiscardedPacketsByL3Forward."

      REVISION     "201408180000Z"
      DESCRIPTION  "V4.75, modify mib leaf node hwIpTrafficDropPrecedence;
                    added hwIpTrafficDSCP,hwIpTrafficDSCPMappingIndex,hwIpTrafficDropPrecedence,hwIpTrafficColorDEI as objects of hwIpTrafficParamChangeTrap;
                    modify the definition of the trap nodes: hwEthernetPortAggCfgChangeTrap."

      REVISION     "201408050000Z"
      DESCRIPTION  "V4.74, added new two tables hwDscpToDscpMappingTable, hwDscpColorToPbitsMappingTable;
                    added new leaf nodes hwIpTrafficCouplingFlag, hwIpTrafficDSCP, hwIpTrafficDSCPMappingIndex, hwIpTrafficDropPrecedence, hwIpTrafficColorDEI;
                    modified tge leaf nodes hwPbitsToPbitsMapping0,hwPbitsToPbitsMapping1,hwPbitsToPbitsMapping2,hwPbitsToPbitsMapping3,hwPbitsToPbitsMapping4,
                    hwPbitsToPbitsMapping5,hwPbitsToPbitsMapping6, hwPbitsToPbitsMapping7,hwPbitsToPbitsMappingRowStatus, hwIPPrecToPbitsMapping0,
                    hwIPPrecToPbitsMapping1,hwIPPrecToPbitsMapping2,hwIPPrecToPbitsMapping3,hwIPPrecToPbitsMapping4,hwIPPrecToPbitsMapping5,hwIPPrecToPbitsMapping6,
                    hwIPPrecToPbitsMapping7,hwCarThresholdProfileCos0,hwCarThresholdProfileCos1,hwCarThresholdProfileCos2,hwCarThresholdProfileCos3,
                    hwCarThresholdProfileCos4,hwCarThresholdProfileCos5,hwCarThresholdProfileCos6,hwCarThresholdProfileCos7."

      REVISION     "201407220000Z"
      DESCRIPTION  "V4.73, add the definition of the following traps:
                    hwOpticsLaserTemperatureOutOfRangeAlarmTrap,
                    hwOpticsLaserTemperatureRestoreAlarmTrap,
                    hwOpticsWavelengthOutOfRangeAlarmTrap,
                    hwOpticsWavelengthRestoreAlarmTrap,
                    hwOpticTecCurrentOutOfRangeAlarmTrap,
                    hwOpticsTecCurrentRestoreAlarmTrap."

      REVISION     "201407140000Z"
      DESCRIPTION  "V4.72, modified the description of hwSrvFlowBundleIndex,
                    added leaf nodes hwMacAddressLearnPolicy and hwPriTagTransDownstream."

      REVISION     "201407090000Z"
      DESCRIPTION  "V4.71, added enumerated dyinggasp(8) in hwifEthernetOfflineReason leaf node."

      REVISION     "201407080000Z"
      DESCRIPTION  "V4.70, added the definition of the trap nodes: hwEnableMirrorPortExtendTrap, hwDisableMirrorPortExtendTrap,
                    hwMirrorSrcPortDescription, hwMirrorDstPortDescription."

      REVISION     "201406290000Z"
      DESCRIPTION  "V4.69, Modified hwEthernet to hwEthernetPort because the HUAWEI-MIB changed.
                    Modified the following not normative nodes to satisfy for the new OMSYS tool.
                    hwifAggregateModel
                    hwLeftBrdPrimaryStatus
                    hwRightBrdPrimaryStatus
                    hwRightBrdSecondaryStatus
                    hwIpTrafficIndex
                    hwCosWREDThreshold2
                    hwCosWREDThreshold4
                    hwTrafficTablePriorityMappingMode
                    hwSrvAttrChangeType
                    hwExtSrvFlowIndex."

      REVISION     "201406050000Z"
      DESCRIPTION  "V4.68, added the definition of the trap nodes: hwBoardMacOverloadTrap, hwBoardMacOverloadRestoreTrap."

      REVISION     "201405070000Z"
      DESCRIPTION  "V4.67, added leaf nodes hwEthernetMirrorDirection and hwDisableMirrorPortTrap for trap of hwEthernetAlarmTraps.
                    modified leaf node hwBiuPortStatusChangeInfoTrap to hwBitsPortStateChangeType."

      REVISION     "201404210000Z"
      DESCRIPTION  "V4.66, added leaf node hwEthernetLineOfflineAutoShutdown to indicate the switch status of the offline ETH port auto shutdown switch state."

      REVISION     "201404020000Z"
      DESCRIPTION  "V4.65, modified the value range of hwProfileCosQueueWeightQue0, hwProfileCosQueueWeightQue1, hwProfileCosQueueWeightQue2, hwProfileCosQueueWeightQue3,
                    hwProfileCosQueueWeightQue4, hwProfileCosQueueWeightQue5, hwProfileCosQueueWeightQue6 and hwProfileCosQueueWeightQue7 of hwQosPolicyProfileTable.
                    modified the description of hwProfileCosQueueWeightQue0, hwProfileCosQueueWeightQue1, hwProfileCosQueueWeightQue2, hwProfileCosQueueWeightQue3,
                    hwProfileCosQueueWeightQue4, hwProfileCosQueueWeightQue5, hwProfileCosQueueWeightQue6 and hwProfileCosQueueWeightQue7 of hwQosPolicyProfileTable.
                    modified the description of hwCosQueueWeightQue0, hwCosQueueWeightQue1, hwCosQueueWeightQue2, hwCosQueueWeightQue3, hwCosQueueWeightQue4,
                    hwCosQueueWeightQue5, hwCosQueueWeightQue6, hwCosQueueWeightQue7 of hwCosQueueSchedTable.
                    added new table hwBoardMacAddressLearningVlanConnectTable."

      REVISION     "201401160000Z"
      DESCRIPTION  "V4.64, added new table hwXponPortJumboEnableTable."

      REVISION     "201312310000Z"
      DESCRIPTION  "V4.63, modified the description of hwIpTrafficFixBandWidth, hwPortVlanPolicingVlanID and hwifEthernetOfflineReason."

      REVISION     "201312230000Z"
      DESCRIPTION  "V4.62, modified the description of hwifEthernetOfflineReason, hwPortStatisticsExcludeMulticastQueueEntry,
                    hwEthernetLoopbackTestResult and hwInfinibandEntry."

      REVISION     "201311250000Z"
      DESCRIPTION  "V4.61, added leaf node hwEthernetPortAggCfgChangeTrap for trap of hwEthernetCommonTraps."

      REVISION     "201311200000Z"
      DESCRIPTION  "V4.60, added leaf node hwEthernetPortCfgChangeTrap for trap of hwEthernetCommonTraps.
                    added new table hwPortStatisticsExcludeMulticastQueueTable."

      REVISION     "201310180000Z"
      DESCRIPTION  "V4.59, added new node hwifEthernetOfflineReason."

      REVISION     "201310080000Z"
      DESCRIPTION  "V4.58, modified the description of hwIpTrafficCir and hwIpTrafficCbs and the value range of hwIpTrafficCbs.
                    modified the description of hwCosQueueDepthRateQue0, hwCosQueueDepthRateQue1, hwCosQueueDepthRateQue2, hwCosQueueDepthRateQue3,
                    hwCosQueueDepthRateQue4, hwCosQueueDepthRateQue5, hwCosQueueDepthRateQue6 and hwCosQueueDepthRateQue7 of hwCosQueueDepthRateTable.
                    modified the description of hwProfileCosQueueDepthRateQue0, hwProfileCosQueueDepthRateQue1, hwProfileCosQueueDepthRateQue2,
                    hwProfileCosQueueDepthRateQue3, hwProfileCosQueueDepthRateQue4, hwProfileCosQueueDepthRateQue5, hwProfileCosQueueDepthRateQue6
                    and hwProfileCosQueueDepthRateQue7 of hwQosPolicyProfileTable."

      REVISION     "201309170000Z"
      DESCRIPTION  "V4.57, added leaf nodes hwProfileCosQueueDepthRateQue0, hwProfileCosQueueDepthRateQue1, hwProfileCosQueueDepthRateQue2,
                    hwProfileCosQueueDepthRateQue3, hwProfileCosQueueDepthRateQue4, hwProfileCosQueueDepthRateQue5, hwProfileCosQueueDepthRateQue6,
                    and hwProfileCosQueueDepthRateQue7 of hwQosPolicyProfileTable."

      REVISION     "201308020000Z"
      DESCRIPTION  "V4.56, added leaf node hwIpdslamQryConditionOntId for trap of hwIpdslamDisplayLocationTrap.
                    added new leaf hwExtDefaultPortEfmOamAdminStatus.
                    added new table hwEarlyDropPriBaseMappingTable.
                    added new leaf hwExtSrvFlowStatPerSwitch of hwExtSrvFlowTable.
                    modified the description of hwExtSrvFlowPara4.
                    Modified the value range of hwCosPortOntId from -1..254 to -1..255.
                    modified the description of hwIpTrafficPir and hwIpTrafficPbs and the value range of hwIpTrafficCir."

      REVISION     "201307120000Z"
      DESCRIPTION  "V4.55, added new node hwBindBoardReplaceErrorTrap."

      REVISION     "201306280000Z"
      DESCRIPTION  "V4.54, added leaf node hwifEthernetLoopbackTest of hwEthernetTable.
                    added node hwEthernetLoopbackTestResult, hwEthernetLoopbackTestTxFrames, hwEthernetLoopbackTestRxFrames
                    and hwEthernetLoopbackTestPacketLossRatio of hwEthernetTrapVarBindOids indicated loopback test result.
                    added hwEthernetLoopbackTestTrap of hwEthernetCommonTraps for loopback test trap.
                    added hwInfinibandTable and hwInfinibandTraps for infiniband port."

      REVISION     "201305140000Z"
      DESCRIPTION  "V4.53, added new node hwMulticastQueuePriority.
                    added enumerated ipneighbourhardware(2) in hwResourceType leaf node.
                    added the definition of the trap nodes: hwIPNeighbourHardwareOverloadTrap, hwIPNeighbourHardwareOverloadRestoreTrap."

      REVISION     "201304270000Z"
      DESCRIPTION  "V4.52, modified the description of hwExtSrvFlowPara1, hwExtSrvFlowPara2, hwExtSrvFlowPara3, hwExtSrvFlowPara4."

      REVISION     "201304070000Z"
      DESCRIPTION  "V4.51, added leaf node hwIpTrafficFixBandWidth of hwIpTrafficParamTable.
                    added enumerated value by8021pList(6) in hwExtSrvFlowMultiServiceType leaf node and modified the description.
                    modified the description of hwExtSrvFlowMultiServiceUserPara.
                    added enumerated docsis(15) in hwExtSrvFlowParaType leaf node.
                    modified the description of hwExtSrvFlowPara4,hwExtSrvFlowPara5 and hwExtSrvFlowParaType."

      REVISION     "201302010000Z"
      DESCRIPTION  "V4.50, added new table hwQosPolicyProfileTable.
                    added new table hwPortBindQosPolicyProfileTable.
                    added enumerated value srcDstIp(6) and ipEnhance(7) in hwifAggregateModel leaf node.
                    added enumerated value colorWred(4) in hwEarlyDropModeSlot leaf node and modified the description."

      REVISION     "201301300000Z"
      DESCRIPTION  "V4.49, added leaf node hwEthStatsEfmErroredFrameEvents of hwEthHistoryStatsTable.
                    added leaf node hwEthStatsEfmErroredFrameSecondSummaryEvents of hwEthHistoryStatsTable.
                    added leaf node hwEthStatsEfmErroredFramePeriodEvents of hwEthHistoryStatsTable."

      REVISION     "201212310000Z"
      DESCRIPTION  "V4.48, added leaf node hwQueueStatisticsPassedBytes of hwQueueStatisticsstateTable.
                    modified the type of leaf node hwVlanIsolateState from Integer32 to INTEGER."

      REVISION     "201212250000Z"
      DESCRIPTION  "V4.47, added leaf node hwifEthernetPortTypeAutoSensing to hwEthernetTable."

     REVISION     "201212120000Z"
      DESCRIPTION  "V4.46, added new node hwTrafficLimitOntMode."

      REVISION     "201212071616Z"
      DESCRIPTION  "V4.45, added leaf node hwifEthernetPortType to hwEthernetTable."

      REVISION     "201212060000Z"
      DESCRIPTION  "V4.44, added new table hwBoardSpeedModeTable."

      REVISION     "201211280000Z"
      DESCRIPTION  "V4.43, added new table hwResourceOverloadAwareTable.
                    added the definition of the trap nodes: hwMacOverloadTrap, hwMacOverloadRestoreTrap.
                    added leaf node hwResourceOverloadAwareCurValue to indicate the current resource occupancy.
                    added new table hwCarThresholdProfileTable.
                    added leaf node hwIpTrafficCarThresholdProfileIndex of hwIpTrafficParamTable."

      REVISION     "201211040000Z"
      DESCRIPTION  "V4.42, modified the description of hwIpdslamBindIpv6PrefixLength.
                    added node hwIpdslamBindIpMaskLength for binding IPv4 subnet.
                    modified the default value in the description of MIB nodes: hwDscpListMapToPriority2,hwDscpListMapToPriority3,hwDscpListMapToPriority4,
                    hwDscpListMapToPriority5,hwDscpListMapToPriority6,hwDscpListMapToPriority7.
                    modified the description of hwifAggregatePortName,hwAggregateStatisticsTable and hwAggregateStatisticsEntry."

      REVISION     "201210150000Z"
      DESCRIPTION  "V4.41, added leaf node hwFlowFluxSourceUpBytes of hwFlowFluxStatisticTable.
                    added leaf node hwFlowFluxSourceUpPackets of hwFlowFluxStatisticTable.
                    added leaf node hwFlowFluxSourceUpDiscardPackets of hwFlowFluxStatisticTable.
                    added leaf node hwFlowFluxSourceDownBytes of hwFlowFluxStatisticTable.
                    added leaf node hwFlowFluxSourceDownPackets of hwFlowFluxStatisticTable.
                    added leaf node hwFlowFluxSourceDownDiscardPackets of hwFlowFluxStatisticTable.
                    added leaf node hwFlowFluxDestinationUpBytes of hwFlowFluxStatisticTable.
                    added leaf node hwFlowFluxDestinationUpPackets of hwFlowFluxStatisticTable.
                    added leaf node hwFlowFluxDestinationUpDiscardPackets of hwFlowFluxStatisticTable.
                    added leaf node hwFlowFluxDestinationDownBytes of hwFlowFluxStatisticTable.
                    added leaf node hwFlowFluxDestinationDownPackets of hwFlowFluxStatisticTable.
                    added leaf node hwFlowFluxDestinationDownDiscardPackets of hwFlowFluxStatisticTable."

      REVISION     "201208030000Z"
      DESCRIPTION  "V4.40, modified the syntax and description of hwSrvAttrChangeType.
                    modified the value range of hwIpdslamConnectIndex, hwCarGroupSrvFlowIndex, hwExtSrvFlowIndexNext, hwExtSrvFlowIndex,
                    hwExtSrvFlowBundleIndex, hwFlowID, hwFlowIndex, hwSrvFlowBundleIndex, hwSrvFlowBundleQueryIndex, hwSrvFlowIndex, hwStaticMacFlowID,
                    and hwIpdslamQryConditionFlowBundleIndex.
                    modified enumerated value invalid(-1) in hwExtSrvFlowSimulationServiceType leaf node and modified the description."

      REVISION     "201206280000Z"
      DESCRIPTION  "V4.39, modified the description of hwEthStatsRxDropEvents."

      REVISION     "201205250000Z"
      DESCRIPTION  "V4.38, added new table hwSrvPortExtStatTable."


      REVISION     "201205030000Z"
      DESCRIPTION  "V4.37, added leaf node hwTrafficTablePriorityMappingMode for boards which support either TOS to 802.1p or DSCP to 802.1p
                    to determine which mode to use.
                    added leaf node hwMacAddressHashConfilictDetect to indicates the switch for MAC hash detect.
                    added enumerated value invalid(-1) in hwExtSrvFlowSimulationServiceType leaf node and modified the description.
                    added hwE2ECcTable."

      REVISION     "201202270000Z"
      DESCRIPTION  "V4.36, modified the syntax and description of hwEthStatsAlarmProfIndex."

      REVISION     "201202220000Z"
      DESCRIPTION  "V4.35, added leaf node hwEthernetLineAlarmSuppressInitial to indicate the switch status of suppressing alarm in initial state."

      REVISION     "201202200000Z"
      DESCRIPTION  "V4.34, modified description of some leaves of hwIpdslamConnectTable, hwIpTrafficParamTable, hwExtSrvFlowTable, hwEthernetTable, hwifAggregateTable,
                    hwCosPortTrafficTable, hwCosWREDThresholdTable, hwPbitsToPbitsMappingTable, hwQueueStatisticsstateTable, hwWREDTable,
                    hwQueueWREDTable, hwCtpEthAttributeCfgTable, hwExtProtocolForwardingPolicyTable,hwPortPermitForwardTable.
                    modified the description of leaf node hwCosQueueMappingMask.
                    modified the description of leaf node hwCosRemarkMask."

      REVISION     "201202150000Z"
      DESCRIPTION  "V4.33, modified the description of hwifEthernetAutoTxPowerOffDetectTime.
                    modified the description of some leaves of hwEthHistoryStatsTable."

      REVISION     "201202140000Z"
      DESCRIPTION  "V4.32, added enumerated value ge10(3) in hwPortSpeedType leaf node and modified the description,
                           added enumerated value s2500M(2500) in hwifEthernetSpeed leaf node and modified the description,"

      REVISION     "201201040000Z"
      DESCRIPTION  "V4.31, added table hwEthHistoryStatsAlarmProfTable.
                      added the definition of the trap node: hwEthPerformanceStatisOutOfRangeAlarmTrap,
                      hwEthPerformanceStatisRestoreAlarmTrap,hwEthPerformanceStatisOutOfRangeWarningTrap,hwEthPerformanceStatisRestoreWarningTrap.
                    added the fowllowing leaf nodes to hwEthernetTable:
                    hwEthBind15minAlarmTableIndex, to indicate the 15-min alarm profile bound to port,
                    hwEthBind15minWarningTableIndex to indicate the 15-min warning profile bound to port,
                    hwEthBind24hourAlarmTableIndex to indicate the 24-hour alarm profile bound to port,
                    hwEthBind24hourWarningTableIndex to indicate the 24-hour warning profile bound to port.
                    add  the fowllowing leaf nodes to hwEthHistoryStatsTable:
                    hwEthStatsStartTime, hwEthStatsValidNumber, hwEthStatsInvalidNumber, hwEthStatsStatusChangeTimes,
                    hwEthStatsRxUnicastPkts, hwEthStatsTxUnicastPkts, hwEthStatsRxAlignErrors, hwEthStatsTxCollisionPkts,
                    hwEthStatsTxSingleCollisionPkts, hwEthStatsTxMultipleCollisionPkts, hwEthStatsDiscardedUndersizedPkts,
                    hwEthStatsTxUnderSizedPkts, hwEthStatsTxFragmentsPkts, hwEthStatsTxJabbers, hwEthStatsTxOverSizedPkts,
                    hwEthStatsTx64OctetsPkts, hwEthStatsTx65to127OctetsPkts, hwEthStatsTx128to255OctetsPkts, hwEthStatsTx256to511OctetsPkts,
                    hwEthStatsTx512to1023OctetsPkts, hwEthStatsTx1024to1518OctetsPkts, hwEthStatsTxErrorPkts, hwEthStatsRxErrorPkts,
                    hwEthStatsTxDropPkts, hwEthStatsTxCRCErrorPkts.
                    added leaf node hwAggStatsClear to clear aggregate port statistics information in hwAggregateStatisticsTable.
                    "

      REVISION     "201112190000Z"
      DESCRIPTION  "V4.30, added hwPortPermitForwardTable.
                    added leaf node hwExtPermitForwardIfIdex of hwPortPermitForwardTable.
                    added leaf node hwExtPermitForwardSecondIndex of hwPortPermitForwardTable.
                    added leaf node hwExtCfmPermitForwarding of hwPortPermitForwardTable."

      REVISION     "201111270000Z"
      DESCRIPTION  "V4.29, added hwXponQueueShapingTable and hwEthQueueShapingTable.
                    modified the object's name of hwQueueGroupShapingTable.
                    modified the object's name of hwQueueGroupShapingEntry.
                    modified the object's name of hwQueueGroupSchedMode.
                    modified the object's name of hwQueueGroupShapingInboundTrafficIndex.
                    modified the object's name of hwQueueGroupShapingOutboundTrafficIndex.
                    modified the object's name of hwQueueGroupShapingTrafficRowStatus."

      REVISION     "201111240000Z"
      DESCRIPTION  "V4.28, added leaf node hwL2MacAgingMode to indicate MAC address aging mode.
                    added the table of hwCosGroupTblTable.
                    added the table of hwCarPortCosGroupTable.
                    added leaf node hwStaticMacPwIndex of hwStaticMacTable to indicate setting Static MAC address on PW.
                    added leaf node hwIpdslamQryConditionPwIndex for trap of hwIpdslamDisplayLocationTrap.
                    added leaf node hwCosPortCosGroupTableIndex of hwCosPortTrafficTable to indicate the index of the CoS-group table bound to the GEM port.
                    modified the value range of hwCosPortTrafficCos.
                   "

      REVISION     "201111170000Z"
      DESCRIPTION  "V4.27, added leaf node hwifEthernetAutoTxPowerOffSwitch to indicate the switch of TX auto poweroff.
                    added leaf node hwifEthernetAutoTxPowerOffDetectTime to indicate LOS time of TX auto poweroff.
                    added leaf node hwifEthernetTxPowerState to indicate the TX status."

      REVISION     "201111090000Z"
      DESCRIPTION  "V4.26, modified the description of hwMaxMacLearn."

      REVISION     "201110190000Z"
      DESCRIPTION  "V4.25, added the trap of hwSrvFlowBatModifyInfoTrap for batch modifying the service ports.
                   added the following leaf nodes for the trap of hwSrvFlowBatModifyInfoTrap.
                   added leaf node hwSrvFlowBatOperType to indicate the batch operation type of the service port.
                   added leaf node hwSrvFlowBatOperPara to indicate the value of the service port parameter.
                   added leaf node hwSrvFlowBatModiyNum to indicate the number of the service ports.
                   added leaf node hwSrvFlowBatFlowIndexList to indicate the the service port index list.
                   "

      REVISION     "201110050000Z"
      DESCRIPTION  "V4.24, modified the object's name of hwOpticsTxPowerOutOfRangeAlarmTrap and hwOpticsTxPowerRestoreAlarmTrap."

      REVISION     "201109300000Z"
      DESCRIPTION  "V4.23, added enumerated value off(5) in hwEarlyDropModeSlot leaf node, and added the description of hwEarlyDropModeSlot.
                    added leaf node hwDownMcTrafficPolicy to indicate the traffic policy of downstream multicast packets."

      REVISION     "201109260000Z"
      DESCRIPTION  "V4.22, added leaf node hwEthernetLineAlarmRecoverOnShutdown to indicate the status of alarm recovering."

      REVISION     "201109200000Z"
      DESCRIPTION  "V4.21, modified the syntax of hwQueueStatisticsPassedNumber and hwQueueStatisticsDroppedNumber.
                    modified the value range of hwDscpToPbitsMappingIndex.
                    modified the description of hwExtSrvFlowPara5 and hwExtSrvFlowParaType."

      REVISION     "201108160000Z"
      DESCRIPTION  "V4.20, imported the following reference nodes from HUAWEI-ETHERNET-OPTICMODULE-MIB:
                    hwOpticsTemperatureUpperThresholdValue,
                    hwOpticsTemperatureLowerThresholdValue,
                    hwOpticsVoltageUpperThresholdValue,
                    hwOpticsVoltageLowerThresholdValue,
                    hwOpticsSupplyVoltage,
                    hwOpticsCurrentUpperThresholdValue,
                    hwOpticsCurrentLowerThresholdValue,
                    hwOpticsTxBiasCurrent."

      REVISION     "201108090000Z"
      DESCRIPTION  "V4.19, added enumerated value mplsLabel(5) in hwifAggregateModel leaf node,
                    and added the description of hwifAggregateModel."

      REVISION     "201107250000Z"
      DESCRIPTION  "V4.18, added hwCosQueueDepthRateSlotTable, hwEarlyDropModeSlotTable and hwEarlyDropColorBasedYellowThresholdTable.
                    added enumerated value IPv4oE(0) in hwExtSrvFlowMultiServiceUserPara.
                    modified the description of hwExtSrvFlowPara5.
                    added enumerated value xponEndToEnd(14) for leaf node hwExtSrvFlowParaType.
                    modified the description of the leaf node hwExtSrvFlowPara1,hwExtSrvFlowPara2, hwExtSrvFlowPara3,hwExtSrvFlowPara4 and hwExtSrvFlowPara5,
                    indicates how to use the enumerated value of the leaf node hwExtSrvFlowParaType."

      REVISION     "201107200000Z"
      DESCRIPTION  "V4.17, added the following leaf node for trap of hwSrvAttrChangedInfoTrap: hwExtSrvFlowPara5.
                    added leaf node hwNNIMacLearningPriority to indicate the MAC learning priority of the network side in the mainboard.
                    added leaf node hwUNIMacLearningPriority to indicate the MAC learning priority of the user side in the mainboard.
                   "

      REVISION     "201107050000Z"
      DESCRIPTION  "V4.16, added the definition of the following trap nodes:
                    hwOpticsTemperatureOutOfRangeAlarmTrap,
                    hwOpticsTemperatureRestoreAlarmTrap,
                    hwOpticsVoltageOutOfRangeAlarmTrap,
                    hwOpticsVoltageRestoreAlarmTrap,
                    hwOpticsCurrentOutOfRangeAlarmTrap,
                    hwOpticsCurrentRestoreAlarmTrap."

      REVISION     "201106170000Z"
      DESCRIPTION  "V4.15, modified the description of the nodes: hwCosPortOntId."

      REVISION     "201105180000Z"
      DESCRIPTION  "V4.14, modified the description of the nodes: hwLeftBrdPrimaryStatus, hwLeftBrdSecondaryStatus,
                    hwRightBrdPrimaryStatus, hwRightBrdSecondaryStatus."

      REVISION     "201105170000Z"
      DESCRIPTION  "V4.13, added enumerated value ont(4) in hwFlowBridgePortType leaf node,
                   and added the description of hwFlowBridgePortType.
                   "

      REVISION     "201104270000Z"
      DESCRIPTION  "V4.12, added the following leaf nodes for trap of hwSrvAttrChangedInfoTrap:
                    hwExtSrvFlowTagTransform,
                    hwExtSrvFlowAdminStatus,
                    hwExtSrvFlowTransmitTrafficDescrIndex,
                    hwExtSrvFlowReceiveTrafficDescrIndex,
                    hwExtSrvFlowInboundTrafficTableName,
                    hwExtSrvFlowOutboundTrafficTableName,
                    hwExtSrvFlowNNIInnerVlanId,
                    hwExtSrvFlowNNIInnerPriority,
                    hwIpdslamConnectMaxMacLearn,
                    hwExtSrvFlowDescInfo,
                    hwExtSrvFlowRemoteDescInfo.
                   "

      REVISION     "201103290000Z"
      DESCRIPTION  "V4.11, modified the name of hwVlanId in hwMacToVlanEntry to hwMacToVlanId."

      REVISION     "201103130000Z"
      DESCRIPTION  "V4.10, added leaf node hwIpdslamBindIpAddressType to indicate the IP type bound to a flow.
                    Added leaf node hwIpdslamBindIpv6Address to indicate the IPv6 address bound to a flow.
                    Added leaf node hwIpdslamBindIpv6PrefixLength to indicate the prefix length of IPv6 address bound to a flow.
                    Added hwBoardMacLearningControlTable to set or get the MAC learning switch of the ETH board.
                   "

      REVISION     "201103030000Z"
      DESCRIPTION  "V4.09, added service type detect funtion for HG autofind."

      REVISION     "201102180000Z"
      DESCRIPTION  "V4.08, added the definition of the trap nodes: hwAlarmEthPowerDyingGaspFault, hwAlarmEthPowerDyingGaspRecover."

      REVISION     "201102090000Z"
      DESCRIPTION  "V4.07, added hwIpTrafficColorPolicy as an object of hwIpTrafficParamChangeTrap.
                    Changed the value range of hwAggStatsIndex."

      REVISION     "201101170000Z"
      DESCRIPTION  "V4.06, changed the value range of hwifAggregatePort, with the value invalid(-1) added.
                    Changed the value range of hwAlarmUpstreamEthernetPortConnectRecover, with the value hwPortDesc deleted."

      REVISION     "201101130000Z"
      DESCRIPTION  "V4.05, added enumerated value invalid(-1) in hwBoardTrafficModeType leaf node."

      REVISION     "201101120000Z"
      DESCRIPTION  "V4.04, added the definition of the trap nodes: hwAlarmEthernetPortAdminActivate, hwAlarmEthernetPortAdminDeActivate."

      REVISION     "201101100000Z"
      DESCRIPTION  "V4.03, added enumerated value ingressOuter802dot1p(4) in hwIpTrafficPriorityPolicy leaf node."

      REVISION     "201012020000Z"
      DESCRIPTION  "V4.02, added leaf nodes hwFlowFluxUpMCCells, hwFlowFluxUpMCPackets, hwFlowFluxDownMCCells and hwFlowFluxDownMCPackets."

      REVISION     "201011200000Z"
      DESCRIPTION  "V4.01, added leaf node hwIpTrafficColorPolicy for support setting early drop threshold with Td.
                    Added table node hwCosRemarkMask for describing the mapping between CoS and remarked CoS.
                    Added table node hwTagTransformTable for indicating the cability of the tag transformation.
                    Added enumerated value eocCnuEth(13) in hwExtSrvFlowParaType leaf node.
                    Added hwFlowIndexQueryForPPPoESmltTable.
                    Modified the description of tables.
                    Modified the MAX-ACCESS of hwBindBrdFSIndex from read-only to not-accessible.
                    Modified the description of hwExtSrvFlowMultiServiceUserPara, indicates how to use IPv6oE Flow Para.
                   "

      REVISION     "201009030000Z"
      DESCRIPTION  "V4.00, modified the MAX-ACCESS of hwVlanLoopIndex from read-only to not-accessible, and modified the description of hwVlanLoopIndex.
                    Modified the MAX-ACCESS of hwVlanLoopDstInnerVlanId and hwVlanLoopTimeout from read-write to read-only.
                    Corrected the grammar mistake in the description of hwVlanLoopTable.
                   "

      REVISION     "201008260000Z"
      DESCRIPTION  "V3.99, modified parameter error hwPortIndex to hwSlotIndex for hwAlarmSoftwareVersionNotSame in MIB file.
                    Added the description for hwBindResult and hwBindOperateFlag.
                    Modified the description of hwSrvAttrChangeType, and its type is changed from INTEGER to BITS.
                   "

      REVISION     "201008160000Z"
      DESCRIPTION  "V3.98, added hwSrvFlowBundleChangedOperType, hwSrvFlowBundleChangedBundleStr,
                    hwSrvFlowBundleChangedBundleType, hwSrvFlowBundleTrap.
                    Append enumerable values for hwExtSrvFlowParaType and modify the description of hwExtSrvFlowPara5."

      REVISION     "201008120000Z"
      DESCRIPTION  "V3.97, modified the description of hwPortStateChangeInfoTrap.
                    Modified parameter type of hwPortSpeedType. "

      REVISION     "201007070000Z"
      DESCRIPTION  "V3.96, defined trap node hwPortAutounloopSwitchInfoTrap so that a trap message is generated
                    when the loopback on a port is canceled automatically.
                    Added leaf nodes hwLeftBrdPrimaryStatus, hwLeftBrdSecondaryStatus, hwRightBrdPrimaryStatus,
                    hwRightBrdSecondaryStatus for getting the port North America state.
                    Added the definition of the trap nodes: hwAlarmEthPoePowerHighFault, hwAlarmEthPoePowerHighRecover, hwAlarmEthPoeCurrHighFault, hwAlarmEthPoeCurrHighRecover.
                    Added a scalar leaf hwSrvOperType to indicate the operation type of the traffic stream.
                    Added a scalar leaf hwSrvAttrChangeType to indicate the operation type of modifying the traffic stream attribute.
                    Added a trap leaf hwSrvAddInfoTrap to enable a trap to be sent when a traffic stream is set up.
                    Added a trap leaf hwSrvDelInfoTrap to enable a trap to be sent when a traffic stream is deleted.
                    Added a trap leaf hwSrvAttrChangedInfoTrap to enable a trap to be sent when the traffic stream attribute is modified.
                    Modified the description of MIB.
                    Modified the description.
                    Added an enumerated value for hwGlobalStatisticOper.
                    Modified parameter for hwPortChangeState.
                    "

      REVISION     "201006220000Z"
      DESCRIPTION  "V3.95, modified the name of ifindex in hwBoardBindEntry to hwBindBrdFSIndex.
                    Modified the name of hwBindBrdIndex in hwBoardBindEntry to hwBindBrdAnotherFSIndex.
                    Added enumerated value invalid(-1) in hwifAggregateOperType leaf node for syntax error.
                    Added the definition of the following trap nodes:
                    hwOpticsTxPowerOutOfRangeAlarmTrap,
                    hwOpticsTxPowerRestoreAlarmTrap,
                    hwOpticsRxPowerOutOfRangeAlarmTrap,
                    hwOpticsRxPowerRestoreAlarmTrap."

      REVISION     "201006200000Z"
      DESCRIPTION  "V3.94, modified syntax of hwIpdslamQryCondition.
                    Added hwIpTrafficParamChangeTrap.
                    Added hwExtSrvFlowOntPortType.
                    Modified the value range of hwCosPortGemIndex from -1~127 to -1~1023."

      REVISION     "201005260000Z"
      DESCRIPTION  "V3.93, modified the definition of the trap node hwPortStateChangeInfoTrap."

      REVISION     "201005200000Z"
      DESCRIPTION  "V3.92, added bind Trap, port speed type change and port state change Trap."

      REVISION     "201005110000Z"
      DESCRIPTION  "V3.91, added leaf node hwAggStatsSpeed, hwAggStatsOutboundErrors in hwAggregateStatisticsTable."

      REVISION     "201005100000Z"
      DESCRIPTION  "V3.90, modified value range of hwIpTrafficCir, hwIpTrafficCbs, hwIpTrafficPir, hwIpTrafficPbs."

      REVISION     "201003230000Z"
      DESCRIPTION  "V3.89, modified hwDscpToPbitsMappingTable.
                    Added hwExtProtocolForwardingPolicyTable.
                    Added table hwIPPrecToPbitsMappingTable and hwPortCarModeTable.
                    Modified hwIpdslamDisplayLocationTrap."

      REVISION     "201003150000Z"
      DESCRIPTION  "V3.88, added table hwAggregateStatisticsTable."

      REVISION     "201003010000Z"
      DESCRIPTION  "V3.87, modified the syntax error."

      REVISION     "201002250000Z"
      DESCRIPTION  "V3.86, modified description of hwFlowMulitiServicePara."

      REVISION     "201002230000Z"
      DESCRIPTION  "V3.85, added the definition of the trap nodes
                    hwBiuPortStatusChangeInfoTrap"

      REVISION     "201001280000Z"
      DESCRIPTION  "V3.83, added the definition of the trap nodes
                    hwPgGroupLoadBalanceStateChangeTrap"

      REVISION     "201001280000Z"
      DESCRIPTION  "V3.82, added hwXdslEtherStatsTable."

      REVISION     "201001260000Z"
      DESCRIPTION  "V3.81, deleted hwColorWREDThresholdTable.
                   add hwExtDefaultPolicy."

      REVISION     "201001120000Z"
      DESCRIPTION  "V3.80, added the definition of the trap nodes
                       hwAlarmEthernetPortTransceiverTypeChange
                       hwAlarmSoftwareVersionNotSame
                       hwAlarmUpstreamPortConnectfail
                       hwAlarmLOLOccurInBITSInputPort
                       hwAlarmEthernetPortStatusChanges
                       hwAlarmOpticalTransceiverAbsence
                       hwAlarmLOSOccurs
                       hwAlarmLinkBetweenStackPortsFails
                       hwAlarmUpstreamEthernetPortConnectRecover
                       hwAlarmOpticalPortTemperatureRecover
                       hwAlarmBITSInputRecover
                       hwAlarmEthernetPortLinkStatusChange
                       hwAlarmOpticalTransceiverRecover
                       hwAlarmOpticalPortRecoverFromLOS
                       hwAlarmLinkBetweenStackPortsRecover
                               "

      REVISION     "200912260000Z"
      DESCRIPTION  "V3.79, changed SMI to SMIv2 standard."

      REVISION     "200912240000Z"
      DESCRIPTION  "V3.78, changed the value range of hwCosQueueSchedMode, with the value WFQ(3) added."

      REVISION     "200912200000Z"
      DESCRIPTION  "V3.77, added hwDscpToPbitsMappingTable."

      REVISION     "200911200000Z"
      DESCRIPTION  "V3.73, added leaf node hwifAggregateMaxLinkNum in hwifAggregateTable for specifying the maximum number of aggregated links."

      REVISION     "200910270000Z"
      DESCRIPTION  "V3.71, added table node hwCarGroupTable and hwCarGroupSrvFlowTable for supporting the HQOS policy of Flow Group level 2 CAR"

      REVISION     "200904070000Z"
      DESCRIPTION  "V3.58, added table node hwBoardvlanrangestateTable for configuring whether the service
                   board supports to create VLAN RANGE service-port "

      REVISION     "200812300000Z"
      DESCRIPTION  "V3.50, added table node hwBoardBindTable for supporting binding function between board aggregate."

      ::= { huaweiMgmt 14 }

--  Textual conventions
      PortList ::= TEXTUAL-CONVENTION
          STATUS current
          DESCRIPTION
              "Each octet within this value specifies a set of eight
              ports, with the first octet specifying ports 1 through
              8, the second octet specifying ports 9 through 16, etc.
              Within each octet, the most significant bit represents
              the lowest numbered port, and the least significant bit
              represents the highest numbered port. Thus, each port
              of the bridge is represented by a single bit within the
              value of this object. If that bit has a value of '1'
              then that port is included in the set of ports; the port
              is not included if its bit has a value of '0'."
      SYNTAX OCTET STRING

   hwL2IfMibObject OBJECT IDENTIFIER ::= { hwEthernetPort 1 }

   hwSlotPortMax OBJECT-TYPE
      SYNTAX Integer32
      MAX-ACCESS read-only
      STATUS current
      DESCRIPTION
          "Describes L2 global interface objects.
          "
      ::= { hwL2IfMibObject 1 }

   hwSwitchPortMax OBJECT-TYPE
      SYNTAX Integer32
      MAX-ACCESS read-only
      STATUS current
      DESCRIPTION
          "Max ports that this switch includes
          "
      ::= { hwL2IfMibObject 2 }

   hwMacExpire OBJECT-TYPE
      SYNTAX TimeTicks
      MAX-ACCESS read-write
      STATUS current
      DESCRIPTION
          "Indicates the aging time of a dynamic MAC address.
           Range: 1000-100000000.
           Unit: cent seconds.
           When this leaf is set to 0, it indicates that the MAC address does not age.
           Default: 30000 cent seconds, that is, 300 seconds.
          "
      ::= { hwL2IfMibObject 3 }

   hwEthernetTable OBJECT-TYPE
      SYNTAX SEQUENCE OF HwEthernetEntry
      MAX-ACCESS not-accessible
      STATUS current
      DESCRIPTION
          "Indicates the line parameter configuration table of an ETH port.
           It is used for setting the rate, duplex, auto-negotiation, MDI,
           traffic control, Combo mode of an Ethernet port.
           The index of this table is ifIndex.
          "
      ::= { hwL2IfMibObject 4 }

   hwEthernetEntry OBJECT-TYPE
      SYNTAX HwEthernetEntry
      MAX-ACCESS not-accessible
      STATUS current
      DESCRIPTION
          "Indicates the line parameter configuration table of an ETH port.
           It is used for setting the rate, duplex, auto-negotiation, MDI,
           traffic control, Combo mode of an Ethernet port.
           The index of this entry is ifIndex.
          "
      INDEX { ifIndex }
      ::= { hwEthernetTable 1 }

   HwEthernetEntry ::=
      SEQUENCE {
          hwifEthernetDuplex
              INTEGER,
          hwifEthernetMTU
              Integer32,
          hwifEthernetSpeed
              INTEGER,
          hwifEthernetLoopback
              INTEGER,
          hwifEthernetMdi
              INTEGER,
          hwMaxMacLearn
              Integer32,
          hwifMacAddressLearn
              INTEGER,
          hwifTag
              INTEGER,
          hwifEthernetNegotiate
              TruthValue,
          hwifEthernetPeerNegotiate
              TruthValue,
          hwifEthernetPauseFrameTag
              INTEGER,
          hwifEthernetPauseFrameSending
              TruthValue,
          hwifEthernetVlanDefault
              Integer32,
          hwifEthernetOnlineState
              TruthValue,
          hwifEthernetLineSelfAdaptMode
              TruthValue,
          hwifEthernetTrafficBroadcast
              Integer32,
          hwifEthernetTrafficMulticast
              Integer32,
          hwifEthernetTrafficUnknowncast
              Integer32,
          hwifEthernetJumboEnable
              INTEGER,
          hwifPortDefPriority
              Integer32,
          hwifEthernetComboWorkMode
              INTEGER,
          hwifEthernetLineTest
              INTEGER,
          hwifEthernetAutoTxPowerOffSwitch
              INTEGER,
          hwifEthernetAutoTxPowerOffDetectTime
              Integer32,
          hwifEthernetTxPowerState
              INTEGER,
          hwEthBind15minAlarmTableIndex
              Integer32,
          hwEthBind15minWarningTableIndex
              Integer32,
          hwEthBind24hourAlarmTableIndex
              Integer32,
          hwEthBind24hourWarningTableIndex
              Integer32,
          hwifEthernetPortType
              INTEGER,
          hwifEthernetPortTypeAutoSensing
              INTEGER,
          hwifEthernetLoopbackTest
              INTEGER,
          hwifEthernetOfflineReason
              INTEGER,
           hwifEthernetTxPowerResumeDetect
              INTEGER,
            hwifEthernetTxPowerDetectInterval
              Integer32,
          hwifEthernetTxPowerResumeDuration
              Integer32,
          hwifEthernetTxPowerManualResume
              INTEGER,
          hwifEthernetOpticModuleState
              Integer32,
          hwifEthernetLinkflapping
              Integer32,
          hwifEthernetOfflineTxOffTime
              Integer32,
          hwifEthernetTrafficRateBroadcast
              Integer32,
          hwifEthernetTrafficRateMulticast
              Integer32,
          hwifEthernetTrafficRateUnknowncast
              Integer32,
          hwEthernetLightTestTimeduration
              Integer32,
          hwEthernetLightTestTestStatus
              INTEGER,
          hwEthernetLightTestFinshStatus
              INTEGER
       }

   hwifEthernetDuplex OBJECT-TYPE
      SYNTAX INTEGER
          {
          full(1),
          half(2),
          auto(3),
          autoFull(4),
          autoHalf(5),
          invalid(-1)
          }
      MAX-ACCESS read-write
      STATUS current
      DESCRIPTION
         "Ethernet port duplex mode.
          Options:
          1. full(1)     -indicates that at one moment, the port can be sending packets and receiving packets
          2. half(2)     -indicates that at one moment, the port can be sending packets or receiving packets
          3. auto(3)     -indicates that the port duplex mode is automatic
          4. autoFull(4) -indicates that the port duplex mode is automatic full
          5. autoHalf(5) -indicates that the port duplex mode is automatic half
          6. invalid(-1) -invalid value
          Currently only two duplex modes are supported: full(1) and half(2).
          When auto-negotiation is disabled on a port, the duplex mode can be set.
          "
      ::= { hwEthernetEntry 1 }

   hwifEthernetMTU OBJECT-TYPE
      SYNTAX Integer32 (-1..0|1519..9280)
      MAX-ACCESS read-write
      STATUS current
      DESCRIPTION
           "This object is used for setting the MTU of a ETH port
           0 indicates to restore the default value.
           -1 indicates the value is invalid.
           Range: -1-0, 1519-9280
           "
      ::= { hwEthernetEntry 2 }

   hwifEthernetSpeed OBJECT-TYPE
      SYNTAX INTEGER
          {
          auto(0),
          s10M(10),
          s100M(100),
          s1000M(1000),
          s2500M(2500),
          s10000M(10000),
          s100000M(100000),
          autoS10M(11),
          autoS100M(101),
          autoS1000M(1001),
          autoS10000M(10001),
          invalid(-1)
          }
      MAX-ACCESS read-write
      STATUS current
      DESCRIPTION
         "Ethernet port rate.
          Options:
          1. auto(0)             -Ethernet port rate 0
          2. s10M(10)            -Ethernet port rate forced 10M
          3. s100M(100)          -Ethernet port rate forced 100M
          4. s1000M(1000)        -Ethernet port rate forced 1000M
          5. s2500M(2500)        -Ethernet port rate forced 2500M
          6. s10000M(10000)      -Ethernet port rate forced 10000M
          7. s100000M(100000)    -Ethernet port rate forced 100000M
          8. autoS10M(11)        -Ethernet port rate auto 10M
          9. autoS100M(101)      -Ethernet port rate auto 100M
          10. autoS1000M(1001)   -Ethernet port rate auto 1000M
          11. autoS10000M(10001) -Ethernet port rate auto 10000M
          12. invalid(-1)        -invalid value
          The basic principle for configuring the Ethernet port rate is that the rates of the corresponding
          ports on two interconnected devices must be the same, thus preventing communication failure.
          The FE optical port supports only the port rate of 100 Mbit/s.
          The GE optical port supports the port rates of 1000Mbit/s and 2500 Mbit/s.
          The 10GE optical port supports only the port rate of 10000 Mbit/s.
          The 100GE optical port supports only the port rate of 100000 Mbit/s.
          The GE electrical ports support the port rates of 10 Mbit/s, 100 Mbit/s, and 1000 Mbit/s and auto-negotiation.
          Only when the auto-negotiation is disabled on a port, rate configuration can be set.
          "
      ::= { hwEthernetEntry 3 }

   hwifEthernetLoopback OBJECT-TYPE
      SYNTAX INTEGER
          {
          noloopback(1),
          internalloopback(2),
          externalloopback(3)
          }
      MAX-ACCESS read-write
      STATUS current
      DESCRIPTION
         "Ethernet port loop back mode.
          Options:
          1. noloopback(1)       -cancel loopback
          2. internalloopback(2) -local loopback
          3. externalloopback(3) -remote loopback
          Ports only on the H801SPUA board support the loopback configuration.
          "
      ::= { hwEthernetEntry 4 }

   hwifEthernetMdi OBJECT-TYPE
      SYNTAX INTEGER
          {
          mdiII(1),
          mdiX(2),
          mdiAuto(3),
          invalid(-1)
          }
      MAX-ACCESS read-write
      STATUS current
      DESCRIPTION
         "Ethernet port cable type.
          Options:
          1. mdiII(1)    -direct connection cable
          2. mdiX(2)     -cross-over cable
          3. mdiAuto(3)  -auto-sensing
          4. invalid(-1) -invalid value
          After the network cable auto-sensing mode of an Ethernet port is set successfully, the type of
          the network cable connecting to the port must match the configured network cable auto-sensing mode.

          The Ethernet optical port does not support the network cable auto-sensing mode.

          If the Ethernet electrical port works in forced mode, the network cable type of the port cannot be
          configured to the auto-sensing mode. If the Ethernet electrical port works in auto-negotiation mode,
          the network cable type of the port cannot be configured to using the straight through cable or using
          the crossover cable.
          "
      ::= { hwEthernetEntry 5 }

   hwMaxMacLearn OBJECT-TYPE
      SYNTAX Integer32 (0..600 | 65535)
      MAX-ACCESS read-write
      STATUS current
      DESCRIPTION
         "The max MAC learned by the Ethernet port.
          The invalid value is 65535.
          "
      ::= { hwEthernetEntry 6 }

   hwifMacAddressLearn OBJECT-TYPE
      SYNTAX INTEGER
          {
          enabled(1),
          disabled(2)
          }
      MAX-ACCESS read-write
      STATUS current
      DESCRIPTION
          "Status indicates if the interface is allowed to learn MAC address.
           Options:
           1. enabled(1)  -Indicates the interface can learn MAC address.
           2. disabled(2) -Indicates the interface can't learn MAC address.
           Enable the self-learning of the MAC address at the interface
          "
      ::= { hwEthernetEntry 7 }

   hwifTag OBJECT-TYPE
      SYNTAX INTEGER
          {
          tag(1),
          untag(2),
          multi(3)
          }
      MAX-ACCESS read-write
      STATUS current
      DESCRIPTION
          "Ethernet interface tag.
           Options:
           1. tag(1)    -This value is not supported.
           2. untag(2)  -This value is not supported.
           3. multi(3)  -This value is not supported.
          "
      ::= { hwEthernetEntry 8 }

   hwifEthernetNegotiate OBJECT-TYPE
      SYNTAX TruthValue
      MAX-ACCESS read-write
      STATUS current
      DESCRIPTION
          "Ethernet port negotiation mode.
           Options:
           1. true(1)  -auto-negotiation mode of an Ethernet port is enabled, Ethernet port automatically
                        negotiates the port rate and duplex mode with the interconnected Ethernet port
           2. false(2) -auto-negotiation mode of an Ethernet port is disabledthe port works at the rate
                        and in the duplex mode that are set in forced mode
          "
      ::= { hwEthernetEntry 9 }

   hwifEthernetPeerNegotiate OBJECT-TYPE
      SYNTAX TruthValue
      MAX-ACCESS read-only
      STATUS current
      DESCRIPTION
          "Ethernet peer port auto-negotiation node (which is needed by MA5100 V2R1 product,
           and can be selected by other products of the fixed network depending on the practice.)
          "
      ::= { hwEthernetEntry 10 }

   hwifEthernetPauseFrameTag OBJECT-TYPE
      SYNTAX INTEGER
          {
          on(1),
          off(2),
          rxpause(3),
          txpause(4)
          }
      MAX-ACCESS read-write
      STATUS current
      DESCRIPTION
         "Whether the Ethernet port supports Pause frame flow control.
          Options:
          1. on(1)      -support Tx Pause and Rx Pause
          2. off(2)     -not support
          3. rxpause(3) -support Rx Pause not support Tx Pause
          4. txpause(4) -support Tx Pause not support Rx Pause
          When traffic of an Ethernet port is heavy, use this leaf to control traffic to prevent
          network congestion, which may cause the loss of data packets. After traffic control of
          an Ethernet port is enabled, when traffic of EE port exceeds 1 Gbit/s and traffic of FE
          port exceeds 100 Mbit/s, the device sends PAUSE frames to inform the remote PC to reduce
          traffic so as to reduce the packet loss rate.

          The control function requires the supports from both the MA5600T and the peer device.
          If the peer device supports traffic control, enable the traffic control of the MA5600T;
          if the peer device does not support the traffic control, disable the traffic control of
          the MA5600T.
          "
      ::= { hwEthernetEntry 11 }

   hwifEthernetPauseFrameSending OBJECT-TYPE
      SYNTAX TruthValue
      MAX-ACCESS read-only
      STATUS current
      DESCRIPTION
          "Ethernet pause frame sending tag (Notes: only for Huawei product of Ma5100)
           Whether the network interface is sending Pause frame (which is needed by
           MA5100 V2R1 product, and can be selected by other products of the fixed network
           depending on the practice.)
           Options:
           1. true(1)  -the network interface is sending Pause frame
           2. false(2) -the network interface does not send Pause frame
          "
      ::= { hwEthernetEntry 12 }

   hwifEthernetVlanDefault OBJECT-TYPE
      SYNTAX Integer32 (-1 | 1..4093)
      MAX-ACCESS read-write
      STATUS current
      DESCRIPTION
          "Describes the native VLAN of an Ethernet port.
           When you need to set the packets of the upstream Ethernet
           port with the VLAN tag, operate this leaf. After the native
           VLAN of the Ethernet port is configured successfully,

           If the VLAN ID of the Ethernet port is the same as that
           of the native VLAN, the packets of the upstream Ethernet
           port do not contain the VLAN tag, that is, the packets are untagged.

           If the VLAN ID of the Ethernet port is not the same as that
           of the native VLAN, the packets of the upstream Ethernet
           port contain the VLAN tag.

           Before specifying the native VLAN of a port, make sure that the port
           has been added to the VLAN.

           This does not work:
           when you set the native VLAN on a sub-port of an aggregated port.
           When you set the native on an aggregated master port,
           the configuration of all physical ports within the aggregated group is changed.
           Range: 1-4093
           Default: 1
          "
      ::= { hwEthernetEntry 13 }

   hwifEthernetOnlineState OBJECT-TYPE
      SYNTAX TruthValue
      MAX-ACCESS read-only
      STATUS current
      DESCRIPTION
          "Ethernet port online status (Notes: only for Huawei product of Ma5100).
           Whether the network interface is online (which is needed by MA5100 V2R1
           product, and can be selected by other products of the fixed network depending on the practice).
           Options:
           1. true(1)  -the network interface is online
           2. false(2) -the network interface is offline
          "
      ::= { hwEthernetEntry 14 }

   hwifEthernetLineSelfAdaptMode OBJECT-TYPE
      SYNTAX TruthValue
      MAX-ACCESS read-write
      STATUS current
      DESCRIPTION
          "Connecting adaptatively tag,default false.
            Options:
            1. true(1)  -adapting by itself
            2. false(2) -adapting by manual

           The self-adaptation switch:
           In the case of true, the self-adaptation is enabled, and the device will be self-adaptive,
           cross-over cable or not.
           In the case of false, the self-adaptation is disabled, and the device will not be self-adaptive,
           thus the network cable should be connected by the user.
          "
      ::= { hwEthernetEntry 15 }

   hwifEthernetTrafficBroadcast OBJECT-TYPE
      SYNTAX Integer32 (-1..13)
      MAX-ACCESS read-write
      STATUS current
      DESCRIPTION
          "Indicates the broadcast traffic suppression on an Ethernet port.
           Range: -1,0-13
           13: indicates full-suppression of traffic, and 0 indicates no traffic suppression.
           -1: indicates invalid value.
           The suppression levels and corresponding bandwidth ranges are listed as follows:
           ---------------------------------------------------------------
           NO. Min bandwidth(kbps) Max bandwidth(kbps) Package number(pps)
           ---------------------------------------------------------------
             0      Not suppressed      Not suppressed      Not suppressed
             1                   6                 145                  12
             2                  12                 291                  24
             3                  24                 582                  48
             4                  48                1153                  95
             5                  97                2319                 191
             6                 195                4639                 382
             7                 390                9265                 763
             8                 781               18531                1526
             9                1562               37063                3052
            10                3125               74126                6104
            11                6249              148241               12207
            12               12499              296483               24414
            13                   0                   0                   0
           ---------------------------------------------------------------
           Default: 7
          "
      ::= { hwEthernetEntry 16 }

   hwifEthernetTrafficMulticast OBJECT-TYPE
      SYNTAX Integer32 (-1..13)
      MAX-ACCESS read-write
      STATUS current
      DESCRIPTION
          "Indicates the unknown multicast traffic suppression on an Ethernet port.
           Range: -1,0-13
           13: indicates full-suppression of traffic, and 0 indicates no traffic suppression.
           -1: indicates invalid value.
           The suppression levels and corresponding bandwidth ranges are listed as follows:
           ---------------------------------------------------------------
           NO. Min bandwidth(kbps) Max bandwidth(kbps) Package number(pps)
           ---------------------------------------------------------------
             0      Not suppressed      Not suppressed      Not suppressed
             1                   6                 145                  12
             2                  12                 291                  24
             3                  24                 582                  48
             4                  48                1153                  95
             5                  97                2319                 191
             6                 195                4639                 382
             7                 390                9265                 763
             8                 781               18531                1526
             9                1562               37063                3052
            10                3125               74126                6104
            11                6249              148241               12207
            12               12499              296483               24414
            13                   0                   0                   0
           ---------------------------------------------------------------
           Default: 7
          "
      ::= { hwEthernetEntry 17 }

   hwifEthernetTrafficUnknowncast OBJECT-TYPE
      SYNTAX Integer32 (-1..13)
      MAX-ACCESS read-write
      STATUS current
      DESCRIPTION
          "Indicates the unknown unicast traffic suppression on an Ethernet port.
           Range: -1,0-13
           13: indicates full-suppression of traffic, and 0 indicates no traffic suppression.
           -1: indicates invalid value.
           The suppression levels and corresponding bandwidth ranges are listed as follows:
           ---------------------------------------------------------------
           NO. Min bandwidth(kbps) Max bandwidth(kbps) Package number(pps)
           ---------------------------------------------------------------
             0      Not suppressed      Not suppressed      Not suppressed
             1                   6                 145                  12
             2                  12                 291                  24
             3                  24                 582                  48
             4                  48                1153                  95
             5                  97                2319                 191
             6                 195                4639                 382
             7                 390                9265                 763
             8                 781               18531                1526
             9                1562               37063                3052
            10                3125               74126                6104
            11                6249              148241               12207
            12               12499              296483               24414
            13                   0                   0                   0
           ---------------------------------------------------------------
           Default: 7
          "
      ::= { hwEthernetEntry 18 }

   hwifEthernetJumboEnable OBJECT-TYPE
      SYNTAX INTEGER
          {
          invalid(-1),
          enabled(1),
          disabled(2)
          }
      MAX-ACCESS read-write
      STATUS current
      DESCRIPTION
          "This object is used to enable or disable jumbo frames.
           When the carriers' servers need to exchange a large amount of data with their devices,
           operate this object to enable jumbo frames.
           After the operation is executed successfully,
           the corresponding port on the control board can transparently transmit the frames whose size is between 1519 bytes and 9280 bytes.
           By default, the Ethernet port disable jumbo frames.
           Options:
           1. invalid(-1) -invalid
           2. enabled(1)  -enable the jumbo frames
           3. disabled(2) -disabled the jumbo frames
          "
      ::= { hwEthernetEntry 19 }

   hwifPortDefPriority OBJECT-TYPE
      SYNTAX Integer32 (0..7)
      MAX-ACCESS read-write
      STATUS current
      DESCRIPTION
          "Port default 802.1p priority (Notes: Default value is 0.)
           ------------------------------------------------------------
                  F/ S/ P     Port Priority
           ------------------------------------------------------------
                  0/ 3/ 0       3
                  0/ 3/ 1       4
                  0/ 3/ 2       5
                  0/ 3/ 3       6
                  0/ 3/ 4       7
                  0/ 3/ 5       5
                  0/ 3/ 6       4
                  0/ 3/ 7       3
           ------------------------------------------------------------
          "
      ::= { hwEthernetEntry 20 }

   hwifEthernetComboWorkMode OBJECT-TYPE
      SYNTAX INTEGER
          {
          invalid(-1),
          electric(1),
          optic(2),
          autoFiber(5)
          }
      MAX-ACCESS read-write
      STATUS current
      DESCRIPTION
          "Work mode information of combo port.
           Options:
           1. electric(1)   -combo port works in electric mode
           2. optic(2)      -combo port works in optic mode
           3. autoFiber(5)  -combo port works in auto adapter mode
           4. invalid(-1)   -invalid
          "
      ::= { hwEthernetEntry 21 }

   hwifEthernetLineTest OBJECT-TYPE
      SYNTAX INTEGER
          {
          test(1),
          notSupport(-1)
          }
      MAX-ACCESS read-write
      STATUS current
      DESCRIPTION
          "It used to test the line status.
           Options:
           1. test(1)         -Test the line operation
           2. notSupport(-1)  -Indicates the board does not support this operation
          "
      ::= { hwEthernetEntry 22 }

   hwifEthernetAutoTxPowerOffSwitch OBJECT-TYPE
      SYNTAX INTEGER
          {
          invalid(-1),
          enabled(1),
          disabled(2)
          }
      MAX-ACCESS read-write
      STATUS current
      DESCRIPTION
          "Indicates the switch of Tx auto power off.
           Options:
           1. invalid(-1)    -invalid value
           2. enabled(1)     -enable Tx auto poweroff
           3. disabled(2)    -disable Tx auto poweroff
           Default: disable(2).
          "
      ::= { hwEthernetEntry 23 }

   hwifEthernetAutoTxPowerOffDetectTime OBJECT-TYPE
      SYNTAX Integer32 (-1 | 1..60)
      UNITS "minutes"
      MAX-ACCESS read-write
      STATUS current
      DESCRIPTION
          "Indicates the detecting LOS time of TX auto power off.
           Set:
           '1-60' means valid value to be set,
           Get:
           '-1' means invalid value,
           Unit: minutes
          "
      ::= { hwEthernetEntry 24 }

   hwifEthernetTxPowerState OBJECT-TYPE
      SYNTAX INTEGER
          {
          invalid(-1),
          on(1),
          off(2)
          }
      MAX-ACCESS read-only
      STATUS current
      DESCRIPTION
          "Indicates the state of ethernet port Tx.
           Options:
           1. invalid(-1)    -invalid value
           2. on(1)          -ethernet port Tx is on
           3. off(2)         -ethernet port Tx is off
          "
      ::= { hwEthernetEntry 25 }

   hwEthBind15minAlarmTableIndex OBJECT-TYPE
      SYNTAX Integer32(-1..16)
      MAX-ACCESS read-write
      STATUS current
      DESCRIPTION
          "Indicates the 15 minutes alarm profile index for the ethernet port.
           Set:
            '0' means to unbind 15 minutes alarm profile,
            '1-16' means to bind 15 minutes alarm profile to the ethernet port
           Get:
            '-1' means operation not support,
            '0' means the port has not bound 15 minutes alarm profile,
            '1-16' means the 15 minutes alarm profile index for the ethernet port.
          "
      ::= { hwEthernetEntry 26 }

   hwEthBind15minWarningTableIndex OBJECT-TYPE
      SYNTAX Integer32(-1..16)
      MAX-ACCESS read-write
      STATUS current
      DESCRIPTION
          "Indicates the 15 minutes warning profile index for the ethernet port.
           Set:
            '0' means to unbind 15 minutes warning profile,
            '1-16' means to bind 15 minutes warning profile to the ethernet port
           Get:
            '-1' means operation not support,
            '0' means the port has not bound 15 minutes warning profile,
            '1-16' means the 15 minutes warning profile index for the ethernet port.
           "
      ::= { hwEthernetEntry 27 }

  hwEthBind24hourAlarmTableIndex OBJECT-TYPE
      SYNTAX Integer32(-1..16)
      MAX-ACCESS read-write
      STATUS current
      DESCRIPTION
          "Indicates the 24 hours alarm profile index for the ethernet port.
           Set:
            '0' means to unbind 24 hours alarm profile,
            '1-16' means to bind 24 hours alarm profile to the ethernet port
           Get:
            '-1' means operation not support,
            '0' means the port has not bound 24 hours alarm profile,
            '1-16' means the 24 hours alarm profile index for the ethernet port.
          "
      ::= { hwEthernetEntry 28 }

  hwEthBind24hourWarningTableIndex OBJECT-TYPE
      SYNTAX Integer32(-1..16)
      MAX-ACCESS read-write
      STATUS current
      DESCRIPTION
          "Indicates the 24 hours warning profile index for the ethernet port.
           Set:
            '0' means to unbind 24 hours warning profile,
            '1-16' means to bind 24 hours warning profile to the ethernet port
           Get:
            '-1' means operation not support,
            '0' means the port has not bound 24 hours warning profile,
            '1-16' means the 24 hours warning profile index for the ethernet port.
          "
      ::= { hwEthernetEntry 29 }

  hwifEthernetPortType OBJECT-TYPE
      SYNTAX INTEGER
          {
          fe(1),
          ge(2),
          xge(3),
          onehundredge(4),
          invalid(-1)
          }
      MAX-ACCESS read-write
      STATUS current
      DESCRIPTION
          "Indicates the ethernet port type.
           Options:
           1. fe(1)              -Ethernet port type FE
           2. ge(2)              -Ethernet port type GE
           3. xge(3)             -Ethernet port type 10GE
           4. onehundredge(4)    -Ethernet port type 100GE
           5. invalid(-1)        -invalid value
           Only FE and GE are supported currently.
          "
      ::= { hwEthernetEntry 30 }

   hwifEthernetPortTypeAutoSensing OBJECT-TYPE
      SYNTAX INTEGER
          {
          enable(1),
          disable(2),
          invalid(-1)
          }
      MAX-ACCESS read-write
      STATUS current
      DESCRIPTION
          "Indicates the switch for the port type auto-sensing.
           When the switch is enabled, the port will working on GE or FE mode according to that of link partner.
           Options:
           1. enable(1)  --enable the port type auto-sensing.
           2. disable(2) --disable the port type auto-sensing.
           3. invalid(-1)  --invalid value.
          "
      ::= { hwEthernetEntry 31 }

   hwifEthernetLoopbackTest OBJECT-TYPE
      SYNTAX INTEGER
          {
          test(1)
          }
      MAX-ACCESS read-write
      STATUS current
      DESCRIPTION
          "It used to start loopback test.
          Options:
          1. test(1)    -Start loopback test.
          "
      ::= { hwEthernetEntry 32 }

   hwifEthernetOfflineReason OBJECT-TYPE
      SYNTAX INTEGER
          {
          invalid(-1),
          unknown(1),
          boardabnormal(2),
          opticalmoduleoffline(3),
          los(4),
          shutdownbyuser(5),
          ringdetected(6),
          ethoamtriggeredlinkdown(7),
          dyinggasp(8)
          }
      MAX-ACCESS read-only
      STATUS current
      DESCRIPTION
          "Indicates the offline reason of ethernet port.
           Options:
           1. invalid(-1)                        -invalid value
           2. unknown(1)                         -unknown
           3. boardabnormal(2)                   -board abnormal
           4. opticalmoduleoffline(3)            -optical module offline
           5. los(4)                             -LOS detected
           6. shutdownbyuser(5)                  -port shuted down by user
           7. ringdetected(6)                    -ring detected
           8. ethoamtriggeredlinkdown(7)         -ETHOAM triggered link down
           9. dyinggasp(8)                       -peer end loss of power
          "
      ::= { hwEthernetEntry 33 }

    hwifEthernetTxPowerResumeDetect OBJECT-TYPE
      SYNTAX INTEGER
          {
          invalid(-1),
          manual(1),
          auto(2)
          }
      MAX-ACCESS read-write
      STATUS current

      DESCRIPTION
          "Indicates the switch of Tx auto power resume detection.
           Options:
           1. invalid(-1)  -invalid value
           2. manual(1)  -Tx  power resume detection manually
           3. auto(2)        -Tx  power resume detection automatically
           Default: manual(1).
          "
      ::= { hwEthernetEntry 34 }

     hwifEthernetTxPowerDetectInterval OBJECT-TYPE
      SYNTAX Integer32 (-1 | 100..300)
      UNITS "seconds"
      MAX-ACCESS read-write
      STATUS current
      DESCRIPTION
          "Indicates the interval of Tx power pulse.
           '100-300' means valid value,
           '-1' means invalid value,
           Unit: seconds
          "
      ::= { hwEthernetEntry 35 }

   hwifEthernetTxPowerResumeDuration OBJECT-TYPE
      SYNTAX Integer32 (-1 | 100..3000)
      UNITS "milliseconds"
      MAX-ACCESS read-write
      STATUS current
      DESCRIPTION
          "Indicates the duration of Tx power pulse.
           '100-3000' means valid value,
           '-1' means invalid value,
           Unit: milliseconds
          "
      ::= { hwEthernetEntry 36 }

   hwifEthernetTxPowerManualResume OBJECT-TYPE
      SYNTAX INTEGER
          {
          invalid(-1),
          start(1)
          }
      MAX-ACCESS read-write
      STATUS current
      DESCRIPTION
          "Indicates the operation of manual resumption.
           Options:
           1. invalid(-1)  -invalid value
           2. start(1)     -start Tx power resumption
          "
      ::= { hwEthernetEntry 37 }

   hwifEthernetOpticModuleState OBJECT-TYPE
      SYNTAX Integer32 (1..4 | 2147483647)
      MAX-ACCESS read-only
      STATUS current
      DESCRIPTION
          "Indicates the state of optical module.
           Options:
           1. normal(1)
           2. absent(2)
           3. abnormal(3)
           4. mismatch(4)
           '2147483647' means invalid value.
          "
      ::= { hwEthernetEntry 38 }

   hwifEthernetLinkflapping OBJECT-TYPE
      SYNTAX Integer32 (-1..0|10..5000)
      UNITS "millisecond"
      MAX-ACCESS read-write
      STATUS current
      DESCRIPTION
           "This object is used for setting the link flapping time of a ETH port
           0 indicates disable the ETH port link flapping.
           10-5000 indicates enable ETH link flapping.
		   -1: indicates invalid value.
           Range: -1 0, 10-5000ms,multiple of 10ms.
		   Default:0
           "
      ::= { hwEthernetEntry 39 }

      hwifEthernetOfflineTxOffTime OBJECT-TYPE
      SYNTAX Integer32 (-1|0..1000)
      UNITS "millisecond"
      MAX-ACCESS read-write
      STATUS current
      DESCRIPTION
          "Indicates the the offline time on an Ethernet port.
           Range: -1,0-1000
           0-1000: indicates the offline time when link down.
           0 means the offline time function is off.
           -1: indicates invalid value.
           Default: 0
          "
      ::= { hwEthernetEntry 40 }

      hwifEthernetTrafficRateBroadcast OBJECT-TYPE
      SYNTAX Integer32 (-1..24414)
      MAX-ACCESS read-write
      STATUS current
      DESCRIPTION
          "Indicates the broadcast traffic suppression on an Ethernet port.
           Range: -1,0-24414
           Unit: pps.
           24414: indicates full-suppression of traffic, and 0 indicates no traffic suppression.
           -1: indicates invalid value.
           Default: -1.
          "
      ::= { hwEthernetEntry 41 }

      hwifEthernetTrafficRateMulticast OBJECT-TYPE
      SYNTAX Integer32 (-1..24414)
      MAX-ACCESS read-write
      STATUS current
      DESCRIPTION
          "Indicates the unknown multicast traffic suppression on an Ethernet port.
           Range: -1,0-24414
           Unit: pps.
           24414: indicates full-suppression of traffic, and 0 indicates no traffic suppression.
           -1: indicates invalid value.
           Default: -1.
          "
      ::= { hwEthernetEntry 42 }

      hwifEthernetTrafficRateUnknowncast OBJECT-TYPE
      SYNTAX Integer32 (-1..24414)
      MAX-ACCESS read-write
      STATUS current
      DESCRIPTION
          "Indicates the unknown unicast traffic suppression on an Ethernet port.
           Range: -1,0-24414
           Unit: pps.
           24414: indicates full-suppression of traffic, and 0 indicates no traffic suppression.
           -1: indicates invalid value.
           Default: -1.
          "
      ::= { hwEthernetEntry 43 }

      hwEthernetLightTestTimeduration OBJECT-TYPE
      SYNTAX Integer32 (-1..3600)
      MAX-ACCESS read-write
      STATUS current
      DESCRIPTION
          "This object is used to configure the time duration of light test, 0s ~ 3600s,
          0s means stopping the testing immidiately.
          "
      ::= { hwEthernetEntry 44 }

      hwEthernetLightTestTestStatus OBJECT-TYPE
      SYNTAX INTEGER
          {
          enable(1),
          disable(2),
          invalid(-1)
          }
      MAX-ACCESS read-write
      STATUS current
      DESCRIPTION
          "This object is used to configure the laser test status.
           Options:
           1. enable(1)            - laser tx is enable
           2. disable(2)           - laser tx is disable
           3. invalid(-1)          - invalid value
           Default:enable(1).
          "
      ::= { hwEthernetEntry 45 }

      hwEthernetLightTestFinshStatus OBJECT-TYPE
      SYNTAX INTEGER
          {
          enable(1),
          disable(2),
          original(3),
          invalid(-1)
          }
      MAX-ACCESS read-write
      STATUS current
      DESCRIPTION
          "This object is used to configure the laser status after the test is completed.
           Options:
           1. enable(1)        - laser tx is enable
           2. disable(2)       - laser tx is disable
           3. original(3)      - returned to its original status
           4. invalid(-1)      - invalid value
           Default:original(3)
          "
      ::= { hwEthernetEntry 46 }

   hwifVLANTrunkStatusTable OBJECT-TYPE
      SYNTAX SEQUENCE OF HwIfVLANTrunkStatusEntry
      MAX-ACCESS not-accessible
      STATUS current
      DESCRIPTION
          "Indicates the VLAN trunk feature.
           The index of this table is hwifVLANTrunkIndex.
          "
      ::= { hwL2IfMibObject 5 }

   hwifVLANTrunkStatusEntry OBJECT-TYPE
      SYNTAX HwIfVLANTrunkStatusEntry
      MAX-ACCESS not-accessible
      STATUS current
      DESCRIPTION
          "Indicates the VLAN trunk feature.
           The index of this entry is hwifVLANTrunkIndex.
          "
      INDEX { hwifVLANTrunkIndex }
      ::= { hwifVLANTrunkStatusTable 1 }

   HwIfVLANTrunkStatusEntry ::=
      SEQUENCE {
          hwifVLANTrunkIndex
              InterfaceIndex,
          hwifVLANTrunkGvrpRegistration
              INTEGER,
          hwifVLANTrunkPassListLow
              OCTET STRING,
          hwifVLANTrunkPassListHigh
              OCTET STRING,
          hwifVLANTrunkAllowListLow
              OCTET STRING,
          hwifVLANTrunkAllowListHigh
              OCTET STRING
       }

   hwifVLANTrunkIndex OBJECT-TYPE
      SYNTAX InterfaceIndex
      MAX-ACCESS read-only
      STATUS current
      DESCRIPTION
          "Vlan trunk index
           interface index of VLANTrunk
          "
      ::= { hwifVLANTrunkStatusEntry 1 }

   hwifVLANTrunkGvrpRegistration OBJECT-TYPE
      SYNTAX INTEGER
          {
          normal(1),
          fixed(2),
          forbidden(3)
          }
      MAX-ACCESS read-write
      STATUS current
      DESCRIPTION
          "GVRP registration information.
           Options:
           1. normal(1)    -This is the default configration. Allow create, register and unretiser vlans dynamiclly at this port.
           2. fixed(2)     -Allow create and register vlan manully at this port.
                            And prevent from unregistering vlans or registering known vlans of this port at another trunk port.
           3. forbidden(3) -Unregister all vlans but vlan 1, forbid to create or register any other vlans at this port.
          "
      ::= { hwifVLANTrunkStatusEntry 2 }

   hwifVLANTrunkPassListLow OBJECT-TYPE
      SYNTAX OCTET STRING
      MAX-ACCESS read-only
      STATUS current
      DESCRIPTION
          "The low vlan trunk pass list.total vlan includes  8*255= 2040 vlan ids
           Each octet within this value specifies a set of eight
           ports, with the first octet specifying ports 1 through
           8, the second octet specifying ports 9 through 16, etc.
           Within each octet, the most significant bit represents
           the lowest numbered port, and the least significant bit
           represents the highest numbered port. Thus, each port
           of the bridge is represented by a single bit within the
           value of this object.  If that bit has a value of '1'
           then that port is included in the set of ports; the port
           is not included if its bit has a value of '0'.
           The VLANs that actually pass the VLAN port (low 2040 VLANs (1-2040)), in the length of 255.
          "
      ::= { hwifVLANTrunkStatusEntry 3 }

   hwifVLANTrunkPassListHigh OBJECT-TYPE
      SYNTAX OCTET STRING
      MAX-ACCESS read-only
      STATUS current
      DESCRIPTION
          "The high  vlan trunk pass list. The total vlan includes 8*255= 2040 vlan ids
           Each octet within this value specifies a set of eight
           ports, with the first octet specifying ports 1 through
           8, the second octet specifying ports 9 through 16, etc.
           Within each octet, the most significant bit represents
           the lowest numbered port, and the least significant bit
           represents the highest numbered port. Thus, each port
           of the bridge is represented by a single bit within the
           value of this object.  If that bit has a value of '1'
           then that port is included in the set of ports; the port
           is not included if its bit has a value of '0'.

           The VLANs that pass the VLAN port (1960 VLANs (2041-4000)), in the length of 245.
          "
      ::= { hwifVLANTrunkStatusEntry 4 }

   hwifVLANTrunkAllowListLow OBJECT-TYPE
      SYNTAX OCTET STRING
      MAX-ACCESS read-write
      STATUS current
      DESCRIPTION
          "The low interface of vlan .total interface includes 8*255= 2040 vlan ids
           Each octet within this value specifies a set of eight
           ports, with the first octet specifying ports 1 through
           8, the second octet specifying ports 9 through 16, etc.
           Within each octet, the most significant bit represents
           the lowest numbered port, and the least significant bit
           represents the highest numbered port. Thus, each port
           of the bridge is represented by a single bit within the
           value of this object.  If that bit has a value of '1'
           then that port is included in the set of ports; the port
           is not included if its bit has a value of '0'.

           The VLANs that are allowed to pass  the VLAN port(2040 VLANs (1-2040)),in the length of 255.
          "
      ::= { hwifVLANTrunkStatusEntry 5 }

   hwifVLANTrunkAllowListHigh OBJECT-TYPE
      SYNTAX OCTET STRING
      MAX-ACCESS read-write
      STATUS current
      DESCRIPTION
          "The high  inteface of vlan .total interface includes 8*255= 2040 vlan ids
           Each octet within this value specifies a set of eight
           ports, with the first octet specifying ports 1 through
           8, the second octet specifying ports 9 through 16, etc.
           Within each octet, the most significant bit represents
           the lowest numbered port, and the least significant bit
           represents the highest numbered port.  Thus, each port
           of the bridge is represented by a single bit within the
           value of this object.  If that bit has a value of '1'
           then that port is included in the set of ports; the port
           is not included if its bit has a value of '0'.

           The VLANs allowed to pass the VLAN port (low 2040 VLANs (1-2040)), in length of 255.
          "
      ::= { hwifVLANTrunkStatusEntry 6 }

   hwSystemSwitchMode OBJECT-TYPE
      SYNTAX INTEGER
          {
          standbyPortUp(1),
          standbyPortDown(2)
          }
      MAX-ACCESS read-write
      STATUS current
      DESCRIPTION
          "
           Options:
           1. standbyPortUp(1)         -Auto system switch mode (undo shutdown standby port)
           2. standbyPortDown(2)       -Manual system switch mode (shutdown standby port)
          "
      ::= { hwL2IfMibObject 6 }

   hwFabricMacLearning OBJECT-TYPE
      SYNTAX INTEGER
          {
          enable(1),
          disable(2)
          }
      MAX-ACCESS read-write
      STATUS current
      DESCRIPTION
          "Indicates the MAC address learning switch of the LSW chip of the control board.
           Options:
           1. enable(1)  -indicates that the MAC address learning switch is enabled
           2. disable(2) -indicates that the MAC address learning switch is disabled
           Default: enable(1)
          "
      ::= { hwL2IfMibObject 7 }

   hwUNIMacLearningPriority OBJECT-TYPE
        SYNTAX Integer32(0..3)
        MAX-ACCESS  read-write
        STATUS      current
        DESCRIPTION
            "Indicates the MAC learning priority of the user side in the mainboard.
             Range: 0-3
             Default: 0
             "
      ::= { hwL2IfMibObject 8 }

    hwNNIMacLearningPriority OBJECT-TYPE
       SYNTAX Integer32(0..3)
        MAX-ACCESS  read-write
        STATUS      current
        DESCRIPTION
            "Indicates the MAC learning priority of the network side in the mainboard.
             Range: 0-3
             Default: 3
             "
      ::= { hwL2IfMibObject 9 }

    hwL2MacAgingMode OBJECT-TYPE
       SYNTAX INTEGER
           {
            bidirectional(1),
            unidirectional(2)
           }
        MAX-ACCESS  read-write
        STATUS      current
        DESCRIPTION
            "Indicates the MAC address aging mode.
             Options:
             1. bidirectional(1)  -indicates that the MAC address aging mode is bidirectional.
             2. unidirectional(2) -indicates that the MAC address aging mode is unidirectional.
             Default: bidirectional(1)
             "
      ::= { hwL2IfMibObject 10 }

   hwMacAddressLearnPolicy OBJECT-TYPE
      SYNTAX INTEGER
          {
          svlanBased(1),
          cvlanBased(2)
          }
      MAX-ACCESS read-write
      STATUS current
      DESCRIPTION
          "Indicates the MAC address learning policy.
           Options:
           1. svlanBased(1)  -indicates that the MAC address learning is based on SVLAN(service VLAN)
           2. cvlanBased(2)  -indicates that the MAC address learning is based on CVLAN(client VLAN)
           Default: svlanBased(1)
          "
      ::= { hwL2IfMibObject 12 }

   hwMacAddressFlappingDetectionControl OBJECT-TYPE
      SYNTAX INTEGER
          {
          enabled(1),
          disabled(2)
          }
      MAX-ACCESS read-write
      STATUS current
      DESCRIPTION
          "Indicates the switch for the MAC address flapping detection.
           Options:
           1. enabled(1)  -Enable the MAC address flapping detection.
           2. disabled(2) -Disable the MAC address flapping detection.
           Default: disabled(2)
          "
      ::= { hwL2IfMibObject 13 }

     hwMacAddressFlappingDetectionPeriod OBJECT-TYPE
        SYNTAX Integer32(10..300)
        MAX-ACCESS  read-write
        STATUS      current
        DESCRIPTION
            "Indicates the MAC address flapping detection period.
             Range: 10-300
             Unit: second
             Default: 300
             "
      ::= { hwL2IfMibObject 14 }

   hwMacAddressFlappingDetectionLowerThreshold OBJECT-TYPE
        SYNTAX Integer32(3..100)
        MAX-ACCESS  read-write
        STATUS      current
        DESCRIPTION
            "Indicates the MAC address flapping detection lower threshold. The upper threshold
             must be bigger than the lower threshold.
             Range: 3-100
             Default: 3
             "
      ::= { hwL2IfMibObject 15 }

   hwMacAddressFlappingDetectionUpperThreshold OBJECT-TYPE
        SYNTAX Integer32(3..100)
        MAX-ACCESS  read-write
        STATUS      current
        DESCRIPTION
            "Indicates the MAC address flapping detection upper threshold. The lower threshold
             must be smaller than the upper threshold.
             Range: 3-100
             Default: 100
             "
      ::= { hwL2IfMibObject 16 }

    hwFabricMacHashConflictAutoAdjust OBJECT-TYPE
      SYNTAX INTEGER
          {
          enabled(1),
          disabled(2)
          }
      MAX-ACCESS read-write
      STATUS current
      DESCRIPTION
          "Indicates the switch for the MAC hash conflict auto adjust.
           Options:
           1. enabled(1)  -indicates that the MAC address hash conflict auto adjust function is enabled.
           2. disabled(2) -indicates that the MAC address hash conflict auto adjust function is disabled.
           Default: disabled(2)
          "
      ::= { hwL2IfMibObject 17 }

   hwMacHashConflictRecordTable OBJECT-TYPE
      SYNTAX SEQUENCE OF HwMacHashConflictRecordEntry
      MAX-ACCESS not-accessible
      STATUS current
      DESCRIPTION
          "Indicates the line parameter configuration table of an MAC hash conflict.
           It is used to query MAC hash congfig log.
           This table mainly involves configuring parameters such as MacAddress, Vlan,
           Location, DetectedTime, ResolvedTime.
           The index of this table is hwMacHashConflictRecordIndex.
          "
      ::= { hwL2IfMibObject 18 }

    hwMacHashConflictRecordEntry OBJECT-TYPE
       SYNTAX HwMacHashConflictRecordEntry
       MAX-ACCESS not-accessible
       STATUS current
       DESCRIPTION
           "Indicates the line parameter configuration table of an MAC hash conflict.
           It is used to add, query, modify an MAC hash congfig log.
           This table mainly involves configuring parameters such as MacAddress, Vlan,
           Location, DetectedTime, ResolvedTime.
           The index of this entry is hwMacHashConflictRecordIndex.
           "
      INDEX { hwMacHashConflictRecordIndex }
      ::= { hwMacHashConflictRecordTable 1 }

    HwMacHashConflictRecordEntry ::=
      SEQUENCE {
          hwMacHashConflictRecordIndex
          Integer32,
          hwMacHashConflictRecordMacAddress
          MacAddress,
          hwMacHashConflictRecordVlan
          Integer32,
          hwMacHashConflictRecordLocation
          OCTET STRING,
          hwMacHashConflictRecordDetectedTime
          DateAndTime,
          hwMacHashConflictRecordResolvedTime
          DateAndTime
       }

     hwMacHashConflictRecordIndex OBJECT-TYPE
      SYNTAX Integer32 (1..50)
      MAX-ACCESS not-accessible
      STATUS current
      DESCRIPTION
          "Indicates the index of the MAC hash conflict,
           bind MAC hash conflict identification.
          "
      DEFVAL { 1 }
      ::= { hwMacHashConflictRecordEntry 1 }

     hwMacHashConflictRecordMacAddress OBJECT-TYPE
     SYNTAX MacAddress
     MAX-ACCESS read-only
     STATUS current
     DESCRIPTION
          "The MAC address of an MAC hash conflict"
      ::= { hwMacHashConflictRecordEntry 2 }

     hwMacHashConflictRecordVlan OBJECT-TYPE
     SYNTAX Integer32 (1..4095)
     MAX-ACCESS read-only
     STATUS current
     DESCRIPTION
          "The conflict MAC binding vlan ID"
      ::= { hwMacHashConflictRecordEntry 3 }

    hwMacHashConflictRecordLocation OBJECT-TYPE
    SYNTAX OCTET STRING
    MAX-ACCESS read-only
    STATUS current
    DESCRIPTION
         "The location of detecting MAC hash conflict"
    ::= { hwMacHashConflictRecordEntry 4 }

    hwMacHashConflictRecordDetectedTime OBJECT-TYPE
    SYNTAX DateAndTime
    MAX-ACCESS read-only
    STATUS current
    DESCRIPTION
         "Indicates the time of detecting MAC hash conflict"
      ::= { hwMacHashConflictRecordEntry 5 }

    hwMacHashConflictRecordResolvedTime OBJECT-TYPE
    SYNTAX DateAndTime
    MAX-ACCESS read-only
    STATUS current
    DESCRIPTION
         "Indicates the time of resolving MAC hash conflict"
        ::= { hwMacHashConflictRecordEntry 6 }

   hwExtInterface OBJECT IDENTIFIER ::= { hwEthernetPort 2 }

   hwifXXTable OBJECT-TYPE
      SYNTAX SEQUENCE OF HwIfXXEntry
      MAX-ACCESS not-accessible
      STATUS current
      DESCRIPTION
         "Indicates the port information extension table, which is used to describe the port
          extension features, such as whether a port is an aggregation port.
          The index of this table is ifIndex.
          "
      ::= { hwExtInterface 1 }

   hwifXXEntry OBJECT-TYPE
      SYNTAX HwIfXXEntry
      MAX-ACCESS not-accessible
      STATUS current
      DESCRIPTION
         "Indicates the port information extension table, which is used to describe the port
          extension features, such as whether a port is an aggregation port.
          The index of this entry is ifIndex.
          "
      INDEX { ifIndex }
      ::= { hwifXXTable 1 }

   HwIfXXEntry ::=
      SEQUENCE {
          hwifAggregatePort
              INTEGER,
          hwifMirrorPort
              TruthValue,
          hwifUnknowncastControl
              Integer32,
          hwifMcastControl
              Integer32,
          hwifFlowControl
              TruthValue,
          hwifSrcMacControl
              TruthValue,
          hwifClearStat
              INTEGER,
          hwifLinkStateChangeNum
              Counter32,
          hwifLinkUpTime
              Counter32,
          hwifClearCountTimeStamp
              TimeTicks
       }

   hwifAggregatePort OBJECT-TYPE
      SYNTAX INTEGER
          {
          noAggregatePort(1),
          masterPort(2),
          subPort(3),
          invalid(-1)
          }
      MAX-ACCESS read-only
      STATUS current
      DESCRIPTION
         "whether an Ethernet port is in an aggregation group and whether the port is a master member or slave member.
          Options:
          1. noAggregatePort(1) -Ethernet port is not in an aggregation
          2. masterPort(2)      -Ethernet port is an aggregation master member
          3. subPort(3)         -Ethernet port is an aggregation slave member
          4. invalid(-1)        -invalid value
          "
      ::= { hwifXXEntry 1 }

   hwifMirrorPort OBJECT-TYPE
      SYNTAX TruthValue
      MAX-ACCESS read-write
      STATUS current
      DESCRIPTION
          "
          Whether it is a mirror port.
          "
      ::= { hwifXXEntry 2 }

   hwifUnknowncastControl OBJECT-TYPE
      SYNTAX Integer32 (5..100)
      MAX-ACCESS read-write
      STATUS current
      DESCRIPTION
          "
          Unknown unicast suppression traffic node, in range of (5-100) %
          "
      ::= { hwifXXEntry 3 }

   hwifMcastControl OBJECT-TYPE
      SYNTAX Integer32 (5..100)
      MAX-ACCESS read-write
      STATUS current
      DESCRIPTION
          "
          Broadcast storm suppression, in range of (5-100) %.
          "
      ::= { hwifXXEntry 4 }

   hwifFlowControl OBJECT-TYPE
      SYNTAX TruthValue
      MAX-ACCESS read-write
      STATUS current
      DESCRIPTION
          "
          Flow control status
          "
      ::= { hwifXXEntry 5 }

   hwifSrcMacControl OBJECT-TYPE
      SYNTAX TruthValue
      MAX-ACCESS read-write
      STATUS current
      DESCRIPTION
          "
          Whether the source MAC address is being filtered.
          "
      ::= { hwifXXEntry 6 }

   hwifClearStat OBJECT-TYPE
      SYNTAX INTEGER {
          clear(1),
          invalid(-1)
      }
      MAX-ACCESS read-write
      STATUS current
      DESCRIPTION
        "Clear port statistics information.
         Options:
         1. clear(1)    -In the set operation, clear port statistics information
         2. invalid(-1) -In the get operation, the invalid value -1 is returned.
          "
      ::= { hwifXXEntry 7 }

   hwifLinkStateChangeNum OBJECT-TYPE
      SYNTAX Counter32
      MAX-ACCESS read-only
      STATUS current
      DESCRIPTION
          "Short duration breaks in the link status"
      ::= { hwifXXEntry  8 }

   hwifLinkUpTime OBJECT-TYPE
      SYNTAX Counter32
      MAX-ACCESS read-only
      STATUS current
      DESCRIPTION
          "Indicates the time since last link protocol reset/down"
      ::= { hwifXXEntry 9 }

   hwifClearCountTimeStamp OBJECT-TYPE
      SYNTAX TimeTicks
      MAX-ACCESS read-only
      STATUS current
      DESCRIPTION
          "Gives the time at which the counters that measure cumulative statistics"
      ::= { hwifXXEntry 10 }

   hwifAggregateTable OBJECT-TYPE
      SYNTAX SEQUENCE OF HwIfAggregateEntry
      MAX-ACCESS not-accessible
      STATUS current
      DESCRIPTION
          "Indicates the aggregation management table of an Ethernet port. It implements
           dividing multiple Ethernet ports into one aggregation group to realize
           protection and load sharing among ports. After that, protection and load
           sharing can be realized on the ports in an aggregation group.
           The index of this table is hwifAggregateIndex.
          "
      ::= { hwExtInterface 2 }

   hwifAggregateEntry OBJECT-TYPE
      SYNTAX HwIfAggregateEntry
      MAX-ACCESS not-accessible
      STATUS current
      DESCRIPTION
          "Indicates the aggregation management table of an Ethernet port. It implements
           dividing multiple Ethernet ports into one aggregation group to realize
           protection and load sharing among ports. After that, protection and load
           sharing can be realized on the ports in an aggregation group.
           The index of this entry is hwifAggregateIndex.
          "
      INDEX { hwifAggregateIndex }
      ::= { hwifAggregateTable 1 }

   HwIfAggregateEntry ::=
      SEQUENCE {
          hwifAggregateIndex
              InterfaceIndex,
          hwifAggregatePortName
              OCTET STRING,
          hwifAggregatePortListPorts
              PortList,
          hwifAggregateModel
              INTEGER,
          hwifAggregateRowStatus
              RowStatus,
          hwifAggregateWorkMode
              INTEGER,
          hwifAggregateOperType
              INTEGER,
          hwifAggregateMaxLinkNum
              Integer32,
          hwifAggregateMasterPortIndex
              InterfaceIndex,
          hwifAggregateLeastLinkNum
              Integer32,
          hwifAggregateHashOption
              INTEGER,
          hwifAggregateRandomSeed
              Integer32,
          hwifAggregateStatus
              INTEGER
       }

   hwifAggregateIndex OBJECT-TYPE
      SYNTAX InterfaceIndex
      MAX-ACCESS not-accessible
      STATUS current
      DESCRIPTION
         "IfIndex of the master port in an aggregation group.
          "
      ::= { hwifAggregateEntry 1 }

   hwifAggregatePortName OBJECT-TYPE
      SYNTAX OCTET STRING (SIZE (0..40))
      MAX-ACCESS read-write
      STATUS current
      DESCRIPTION
         "Setting the description of a link-aggregation group of Ethernet ports.
          Range: 0-40
          "
      ::= { hwifAggregateEntry 2 }

   hwifAggregatePortListPorts OBJECT-TYPE
      SYNTAX PortList
      MAX-ACCESS read-write
      STATUS current
      DESCRIPTION
          "The value of hwifAggregatePortListPorts is an octet string.
           One bit in each octet indicates one port, so the octet string can indicate eight ports.
           When a bit is set to 0, it indicates that the corresponding port does not belong to
           this aggregation group. When a bit is set to 1, it indicates that the corresponding
           port belongs to this aggregation group.

           The order is as follows: The maximum number of ports in a slot is 64, so the ports need
           to occupy eight octets. The order, from left to right, is presented as eight groups,
           0-7, 8-15, 16-23, 24-31, 32-39, 40-47, 48-55, and 56-63. In each octet, the port IDs in
           ascending order is presented from low bit to high bit. On the MA5600T, the slot ID starts
           from 0.
           For example, the mask of port 0/1/0 is (HEX) 0000000000000000 0100000000000000
           (the first eight bytes are the mask of the port in slot 0).
          "
      ::= { hwifAggregateEntry 3 }

   hwifAggregateModel OBJECT-TYPE
      SYNTAX INTEGER
          {
          ingress(1),
          ingressEgress(2),
          roundRobin(3),
          egress(4),
          mplsLabel(5),
          srcDstIp(6),
          ipEnhance(7)
          }
      MAX-ACCESS read-write
      STATUS current
      DESCRIPTION
         "Mode of a link-aggregating group.
          Options:
          1. ingress(1)        -load sharing only according to the source MAC
          2. ingressEgress(2)  -Ingress+egress, load sharing according to source MAC and the destination MAC
          3. roundRobin(3)     -round load sharing
          4. egress(4)         -load sharing only according to destination MAC
          5. mplsLabel(5)     -load sharing only according to mpls label
          6. srcDstIp(6)     -load sharing according to source IP and destination IP
          7. ipEnhance(7)     -load sharing according to source IP, destination IP, protocol number etc
          Only ingress(1), ingressEgress(2), mplsLabel(5), srcDstIp(6) and ipEnhance(7) is supported.
          "
      ::= { hwifAggregateEntry 4 }

   hwifAggregateRowStatus OBJECT-TYPE
      SYNTAX RowStatus
      MAX-ACCESS read-create
      STATUS current
      DESCRIPTION
         "The present operation status of the row."
      ::= { hwifAggregateEntry 5 }

   hwifAggregateWorkMode OBJECT-TYPE
      SYNTAX INTEGER
          {
          manual(1),
          lacpStatic(2)
          }
      MAX-ACCESS read-write
      STATUS current
      DESCRIPTION
          "Workmode of a link-aggregation.
          Options:
          1. manual(1)      -manual link aggregation
          2. lacpStatic(2)  -lacp static link aggregation
          "
      ::= { hwifAggregateEntry 6 }

   hwifAggregateOperType OBJECT-TYPE
      SYNTAX INTEGER
          {
          add(1),
          del(2),
          invalid(-1)
          }
      MAX-ACCESS read-write
      STATUS current
      DESCRIPTION
          "Operation type of link-aggregation, use hwifAggregatePortListPorts note to set the
           port list to be added/deleted in an aggregation group.
           Options:
           1. add(1)      -add port(s) to a link-aggregation
           2. del(2)      -delete port(s) from a link-aggregation
           3. invalid(-1) -invalid value
          "
      ::= { hwifAggregateEntry 7 }

   hwifAggregateMaxLinkNum OBJECT-TYPE
      SYNTAX Integer32 (1..255)
      MAX-ACCESS read-write
      STATUS current
      DESCRIPTION
         "Setting the maximum number of links in an aggregation group.
          When you add an aggregation group, hwifAggregateMaxLinkNum is optional,
          If this leaf is not set, the value is 255 by default.
          Only when hwifAggregateWorkMode is set to static LACP, the maximum number of links is
          configurable.
          Range: 1-255
          Default: 255
          "
      ::= { hwifAggregateEntry 8 }

   hwifAggregateMasterPortIndex OBJECT-TYPE
      SYNTAX InterfaceIndex
      MAX-ACCESS read-only
      STATUS current
      DESCRIPTION
         "IfIndex of the master port in an aggregation group.
          "
      ::= { hwifAggregateEntry 9 }

   hwifAggregateLeastLinkNum OBJECT-TYPE
      SYNTAX Integer32 (1..255)
      MAX-ACCESS read-write
      STATUS current
      DESCRIPTION
         "Setting the least number of links in an aggregation group.
          When you add an aggregation group, hwifAggregateLeastLinkNum is optional,
          If this leaf is not set, the value is 255 by default.
          Only when hwifAggregateWorkMode is set to static LACP, the least number of links is
          configurable.
          Range: 1-255
          Default: 255
          "
      ::= { hwifAggregateEntry 10 }

   hwifAggregateHashOption OBJECT-TYPE
      SYNTAX INTEGER
          {
          default(1),
          crc(2),
          xor8(3),
          xor3(4)
          }
      MAX-ACCESS read-write
      STATUS current
      DESCRIPTION
         "Setting the hash option algorithm of a link-aggregating group.
          Options:
          1. default(1) -Indicates the default route selection algorithm.
          2. crc(2)     -Indicates that the CRC algorithm is used to calculate packets outgoing.
          3. xor8(3)    -Indicates that the 8-bit XOR algorithm is used to calculate packets outgoing.
          4. xor3(4)    -Indicates that the 3-bit XOR algorithm is used to calculate packets outgoing.
          Default: default(1)
          "
      ::= { hwifAggregateEntry 11 }

   hwifAggregateRandomSeed OBJECT-TYPE
      SYNTAX Integer32 (0..15)
      MAX-ACCESS read-write
      STATUS current
      DESCRIPTION
         "Setting the random seed value of the link-aggregation group.
          When you add an aggregation group, hwifAggregateRandomSeed is optional,
          If this leaf is not set, the value is 0 by default.
          Range: 0-15
          Default: 0
          "
      ::= { hwifAggregateEntry 12 }

   hwifAggregateStatus OBJECT-TYPE
       SYNTAX INTEGER
       {
           forwarding(1),
           block(2)
       }
       MAX-ACCESS read-only
       STATUS current
       DESCRIPTION
           "Indicates the forwarding status of the link-aggregation group."
      ::= { hwifAggregateEntry 13 }

   hwMacToVlanTable OBJECT-TYPE
      SYNTAX SEQUENCE OF HwMacToVlanEntry
      MAX-ACCESS not-accessible
      STATUS current
      DESCRIPTION
          "Indicates VLAN and the ID list of PVC according to the MAC address.
           The index of this table is hwMacAddress.
          "
      ::= { hwExtInterface 3 }

   hwMacToVlanEntry OBJECT-TYPE
      SYNTAX HwMacToVlanEntry
      MAX-ACCESS not-accessible
      STATUS current
      DESCRIPTION
          "Indicates VLAN and the ID list of PVC according to the MAC address.
           The index of this entry is hwMacAddress.
          "
      INDEX { hwMacAddress }
      ::= { hwMacToVlanTable 1 }

   HwMacToVlanEntry ::=
      SEQUENCE {
          hwMacAddress
              MacAddress,
          hwInterface
              Integer32,
          hwMacToVlanId
              Integer32,
          hwConnectId
              Integer32
       }

   hwMacAddress OBJECT-TYPE
      SYNTAX MacAddress
      MAX-ACCESS read-only
      STATUS current
      DESCRIPTION
          "
          The MAC learned by the system
          "
      ::= { hwMacToVlanEntry 1 }

   hwInterface OBJECT-TYPE
       SYNTAX Integer32
       MAX-ACCESS read-only
       STATUS current
       DESCRIPTION
           "
           the interface index related to the port
           "
       ::= { hwMacToVlanEntry 2 }

   hwMacToVlanId OBJECT-TYPE
      SYNTAX Integer32
      MAX-ACCESS read-only
      STATUS current
      DESCRIPTION
          "
          Mac binding vlan ID
          "
      ::= { hwMacToVlanEntry 3 }

   hwConnectId OBJECT-TYPE
      SYNTAX Integer32
      MAX-ACCESS read-only
      STATUS current
      DESCRIPTION
          "
          the atm pvc connect id of the port if it used as atm interface
          "
      ::= { hwMacToVlanEntry 4 }

   hwIfEthernetMirrorTable OBJECT-TYPE
      SYNTAX SEQUENCE OF HwIfEthernetMirrorEntry
      MAX-ACCESS not-accessible
      STATUS current
      DESCRIPTION
          "
          Ethernet interface mirror table.
          The index of this table is hwifEthernetMirrorDstPort.
          "
      ::= { hwExtInterface 4 }

   hwIfEthernetMirrorEntry OBJECT-TYPE
      SYNTAX HwIfEthernetMirrorEntry
      MAX-ACCESS not-accessible
      STATUS current
      DESCRIPTION
          "
          Ethernet interface mirror table.
          The index of this entry is hwifEthernetMirrorDstPort.
          "
      INDEX { hwifEthernetMirrorDstPort }
      ::= { hwIfEthernetMirrorTable 1 }

   HwIfEthernetMirrorEntry ::=
      SEQUENCE {
          hwifEthernetMirrorDstPort
              Integer32,
          hwifEthernetMirrorSrcPort
              PortList
       }

   hwifEthernetMirrorDstPort OBJECT-TYPE
      SYNTAX Integer32
      MAX-ACCESS read-only
      STATUS current
      DESCRIPTION
          "
          Destination mirror port, whose format is the same as ifIndex
          "
      ::= { hwIfEthernetMirrorEntry 1 }

   hwifEthernetMirrorSrcPort OBJECT-TYPE
      SYNTAX PortList
      MAX-ACCESS read-write
      STATUS current
      DESCRIPTION
          "
          The mirror port to the source port
          "
      ::= { hwIfEthernetMirrorEntry 2 }

   hwifXStatTable OBJECT-TYPE
      SYNTAX SEQUENCE OF HwifXStatEntry
      MAX-ACCESS not-accessible
      STATUS current
      DESCRIPTION
          "Table of the FE/GE interface statistics.
          An interface containing objects at the
          subnetwork layer and below for a particular
          interface.
          The index of this table is ifIndex."
      ::= { hwExtInterface 5 }

   hwifXStatEntry OBJECT-TYPE
      SYNTAX HwifXStatEntry
      MAX-ACCESS not-accessible
      STATUS current
      DESCRIPTION
          "Table of the FE/GE interface statistics.
          An interface containing objects at the
          subnetwork layer and below for a particular
          interface.
          The index of this entry is ifIndex."
      INDEX { ifIndex }
      ::= { hwifXStatTable 1 }

   HwifXStatEntry ::=
      SEQUENCE {
          hwifInArpPkts
              Counter64,
          hwifInIcmpkts
              Counter64,
          hwifOutArpPkts
              Counter64,
          hwifOutIcmpPkts
              Counter64,
          hwifOutCRCAlignErrors
              Counter64,
          hwifOutUndersizePkts
              Counter64,
          hwifOutOversizePkts
              Counter64,
          hwifOutFragments
              Counter64,
          hwifOutJabbers
              Counter64,
          hwifOutCollisions
              Counter64,
          hwifOutPkts64Octets
              Counter64,
          hwifOutPkts65to127Octets
              Counter64,
          hwifOutPkts128to255Octets
              Counter64,
          hwifOutPkts256to511Octets
              Counter64,
          hwifOutPkts512to1023Octets
              Counter64,
          hwifOutPkts1024to1518Octets
              Counter64,
          hwifInCRCAlignErrors
              Counter64,
          hwifInUndersizePkts
              Counter64,
          hwifInOversizePkts
              Counter64,
          hwifInFragments
              Counter64,
          hwifInJabbers
              Counter64,
          hwifInPkts64Octets
              Counter64,
          hwifInPkts65to127Octets
              Counter64,
          hwifInPkts128to255Octets
              Counter64,
          hwifInPkts256to511Octets
              Counter64,
          hwifInPkts512to1023Octets
              Counter64,
          hwifInPkts1024to1518Octets
              Counter64
       }

   hwifInArpPkts OBJECT-TYPE
      SYNTAX Counter64
      MAX-ACCESS read-only
      STATUS current
      DESCRIPTION
          "The total number of arp packets received on the
           interface"
      ::= { hwifXStatEntry 1 }

   hwifInIcmpkts OBJECT-TYPE
      SYNTAX Counter64
      MAX-ACCESS read-only
      STATUS current
      DESCRIPTION
          "The total number of icmp packets received on the
           interface"
      ::= { hwifXStatEntry 2 }

   hwifOutArpPkts OBJECT-TYPE
      SYNTAX Counter64
      MAX-ACCESS read-only
      STATUS current
      DESCRIPTION
          "The total number of arp packets transmitted out of the
           interface"
      ::= { hwifXStatEntry 3 }

   hwifOutIcmpPkts OBJECT-TYPE
      SYNTAX Counter64
      MAX-ACCESS read-only
      STATUS current
      DESCRIPTION
          "The total number of icmp packets transmitted out of the
           interface"
      ::= { hwifXStatEntry 4 }

   hwifOutCRCAlignErrors OBJECT-TYPE
      SYNTAX Counter64
      UNITS "Packets"
      MAX-ACCESS read-only
      STATUS current
      DESCRIPTION
          "The total number of packets received that
           had a length (excluding framing bits, but
           including FCS octets) of between 64 and 1518
           octets, inclusive, but had either a bad
           Frame Check Sequence (FCS) with an integral
           number of octets (FCS Error) or a bad FCS with
           a non-integral number of octets (Alignment Error)."
      ::= { hwifXStatEntry 5 }

   hwifOutUndersizePkts OBJECT-TYPE
      SYNTAX Counter64
      UNITS "Packets"
      MAX-ACCESS read-only
      STATUS current
      DESCRIPTION
          "The total number of packets received that were
           less than 64 octets long (excluding framing bits,
           but including FCS octets) and were otherwise well
           formed."
      ::= { hwifXStatEntry 6 }

   hwifOutOversizePkts OBJECT-TYPE
      SYNTAX Counter64
      UNITS "Packets"
      MAX-ACCESS read-only
      STATUS current
      DESCRIPTION
          "The total number of packets received that were
           longer than 1518 octets (excluding framing bits,
           but including FCS octets) and were otherwise
           well formed."
      ::= { hwifXStatEntry 7 }

   hwifOutFragments OBJECT-TYPE
      SYNTAX Counter64
      UNITS "Packets"
      MAX-ACCESS read-only
      STATUS current
      DESCRIPTION
          "The total number of packets received that were less than
           64 octets in length (excluding framing bits but including
           FCS octets) and had either a bad Frame Check Sequence
           (FCS) with an integral number of octets (FCS Error) or a
           bad FCS with a non-integral number of octets (Alignment
           Error).

           Note that it is entirely normal for etherStatsFragments to
           increment.  This is because it counts both runts (which are
           normal occurrences due to collisions) and noise hits."
      ::= { hwifXStatEntry 8 }

   hwifOutJabbers OBJECT-TYPE
      SYNTAX Counter64
      UNITS "Packets"
      MAX-ACCESS read-only
      STATUS current
      DESCRIPTION
          "The total number of packets received that were
           longer than 1518 octets (excluding framing bits,
           but including FCS octets), and had either a bad
           Frame Check Sequence (FCS) with an integral number
           of octets (FCS Error) or a bad FCS with a non-integral
           number of octets (Alignment Error).

           Note that this definition of jabber is different
           than the definition in IEEE-802.3 section 8.2.1.5
           (10BASE5) and section 10.3.1.4 (10BASE2).  These
           documents define jabber as the condition where any
           packet exceeds 20 ms.  The allowed range to detect
           jabber is between 20 ms and 150 ms."
      ::= { hwifXStatEntry 9 }

   hwifOutCollisions OBJECT-TYPE
      SYNTAX Counter64
      UNITS "Collisions"
      MAX-ACCESS read-only
      STATUS current
      DESCRIPTION
          "The best estimate of the total number of collisions
           on this Ethernet segment.

           The value returned will depend on the location of the
           RMON probe. Section 8.2.1.3 (10BASE-5) and section
           10.3.1.3 (10BASE-2) of IEEE standard 802.3 states that a
           station must detect a collision, in the receive mode, if
           three or more stations are transmitting simultaneously.  A
           repeater port must detect a collision when two or more
           stations are transmitting simultaneously.  Thus a probe
           placed on a repeater port could record more collisions
           than a probe connected to a station on the same segment
           would.

           Probe location plays a much smaller role when considering
           10BASE-T.  14.2.1.4 (10BASE-T) of IEEE standard 802.3
           defines a collision as the simultaneous presence of signals
           on the DO and RD circuits (transmitting and receiving
           at the same time).  A 10BASE-T station can only detect
           collisions when it is transmitting.  Thus probes placed on
           a station and a repeater, should report the same number of
           collisions.

           Note also that an RMON probe inside a repeater should
           ideally report collisions between the repeater and one or
           more other hosts (transmit collisions as defined by IEEE
           802.3k) plus receiver collisions observed on any coax
           segments to which the repeater is connected."
      ::= { hwifXStatEntry 10 }

   hwifOutPkts64Octets OBJECT-TYPE
      SYNTAX Counter64
      UNITS "Packets"
      MAX-ACCESS read-only
      STATUS current
      DESCRIPTION
          "The total number of packets (including bad
           packets) received that were 64 octets in length
           (excluding framing bits but including FCS octets)."
      ::= { hwifXStatEntry 11 }

   hwifOutPkts65to127Octets OBJECT-TYPE
      SYNTAX Counter64
      UNITS "Packets"
      MAX-ACCESS read-only
      STATUS current
      DESCRIPTION
          "The total number of packets (including bad
           packets) received that were between
           65 and 127 octets in length inclusive
           (excluding framing bits but including FCS octets)."
      ::= { hwifXStatEntry 12 }

   hwifOutPkts128to255Octets OBJECT-TYPE
      SYNTAX Counter64
      UNITS "Packets"
      MAX-ACCESS read-only
      STATUS current
      DESCRIPTION
          "The total number of packets (including bad
           packets) received that were between
           128 and 255 octets in length inclusive
           (excluding framing bits but including FCS octets)."
      ::= { hwifXStatEntry 13 }

   hwifOutPkts256to511Octets OBJECT-TYPE
      SYNTAX Counter64
      UNITS "Packets"
      MAX-ACCESS read-only
      STATUS current
      DESCRIPTION
          "The total number of packets (including bad
           packets) received that were between
           256 and 511 octets in length inclusive
           (excluding framing bits but including FCS octets)."
      ::= { hwifXStatEntry 14 }

   hwifOutPkts512to1023Octets OBJECT-TYPE
      SYNTAX Counter64
      UNITS "Packets"
      MAX-ACCESS read-only
      STATUS current
      DESCRIPTION
          "The total number of packets (including bad
           packets) received that were between
           512 and 1023 octets in length inclusive
           (excluding framing bits but including FCS octets)."
      ::= { hwifXStatEntry 15 }

   hwifOutPkts1024to1518Octets OBJECT-TYPE
      SYNTAX Counter64
      UNITS "Packets"
      MAX-ACCESS read-only
      STATUS current
      DESCRIPTION
          "The total number of packets (including bad
           packets) received that were between
           1024 and 1518 octets in length inclusive
           (excluding framing bits but including FCS octets)."
      ::= { hwifXStatEntry 16 }

   hwifInCRCAlignErrors OBJECT-TYPE
      SYNTAX Counter64
      UNITS "Packets"
      MAX-ACCESS read-only
      STATUS current
      DESCRIPTION
          "The total number of packets send that
           had a length (excluding framing bits, but
           including FCS octets) of between 64 and 1518
           octets, inclusive, but had either a bad
           Frame Check Sequence (FCS) with an integral
           number of octets (FCS Error) or a bad FCS with
           a non-integral number of octets (Alignment Error)."
      ::= { hwifXStatEntry 17 }

   hwifInUndersizePkts OBJECT-TYPE
      SYNTAX Counter64
      UNITS "Packets"
      MAX-ACCESS read-only
      STATUS current
      DESCRIPTION
          "The total number of packets send that were
           less than 64 octets long (excluding framing bits,
           but including FCS octets) and were otherwise well
           formed."
      ::= { hwifXStatEntry 18 }

   hwifInOversizePkts OBJECT-TYPE
      SYNTAX Counter64
      UNITS "Packets"
      MAX-ACCESS read-only
      STATUS current
      DESCRIPTION
          "The total number of packets send that were
           longer than 1518 octets (excluding framing bits,
           but including FCS octets) and were otherwise
           well formed."
      ::= { hwifXStatEntry 19 }

   hwifInFragments OBJECT-TYPE
      SYNTAX Counter64
      UNITS "Packets"
      MAX-ACCESS read-only
      STATUS current
      DESCRIPTION
          "The total number of packets send that were less than
           64 octets in length (excluding framing bits but including
           FCS octets) and had either a bad Frame Check Sequence
           (FCS) with an integral number of octets (FCS Error) or a
           bad FCS with a non-integral number of octets (Alignment
           Error).

           Note that it is entirely normal for etherStatsFragments to
           increment.  This is because it counts both runts (which are
           normal occurrences due to collisions) and noise hits."
      ::= { hwifXStatEntry 20 }

   hwifInJabbers OBJECT-TYPE
      SYNTAX Counter64
      UNITS "Packets"
      MAX-ACCESS read-only
      STATUS current
      DESCRIPTION
          "The total number of packets send that were
           longer than 1518 octets (excluding framing bits,
           but including FCS octets), and had either a bad
           Frame Check Sequence (FCS) with an integral number
           of octets (FCS Error) or a bad FCS with a non-integral
           number of octets (Alignment Error).

           Note that this definition of jabber is different
           than the definition in IEEE-802.3 section 8.2.1.5
           (10BASE5) and section 10.3.1.4 (10BASE2).  These
           documents define jabber as the condition where any
           packet exceeds 20 ms.  The allowed range to detect
           jabber is between 20 ms and 150 ms."
      ::= { hwifXStatEntry 21 }

   hwifInPkts64Octets OBJECT-TYPE
      SYNTAX Counter64
      UNITS "Packets"
      MAX-ACCESS read-only
      STATUS current
      DESCRIPTION
          "The total number of packets (including bad
           packets) send that were 64 octets in length
           (excluding framing bits but including FCS octets)."
      ::= { hwifXStatEntry 22 }

   hwifInPkts65to127Octets OBJECT-TYPE
      SYNTAX Counter64
      UNITS "Packets"
      MAX-ACCESS read-only
      STATUS current
      DESCRIPTION
          "The total number of packets (including bad
           packets) send that were between
           65 and 127 octets in length inclusive
           (excluding framing bits but including FCS octets)."
      ::= { hwifXStatEntry 23 }

   hwifInPkts128to255Octets OBJECT-TYPE
      SYNTAX Counter64
      UNITS "Packets"
      MAX-ACCESS read-only
      STATUS current
      DESCRIPTION
          "The total number of packets (including bad
           packets) send that were between
           128 and 255 octets in length inclusive
           (excluding framing bits but including FCS octets)."
      ::= { hwifXStatEntry 24 }

   hwifInPkts256to511Octets OBJECT-TYPE
      SYNTAX Counter64
      UNITS "Packets"
      MAX-ACCESS read-only
      STATUS current
      DESCRIPTION
          "The total number of packets (including bad
           packets) send that were between
           256 and 511 octets in length inclusive
           (excluding framing bits but including FCS octets)."
      ::= { hwifXStatEntry 25 }

   hwifInPkts512to1023Octets OBJECT-TYPE
      SYNTAX Counter64
      UNITS "Packets"
      MAX-ACCESS read-only
      STATUS current
      DESCRIPTION
          "The total number of packets (including bad
           packets) send that were between
           512 and 1023 octets in length inclusive
           (excluding framing bits but including FCS octets)."
      ::= { hwifXStatEntry 26 }

   hwifInPkts1024to1518Octets OBJECT-TYPE
      SYNTAX Counter64
      UNITS "Packets"
      MAX-ACCESS read-only
      STATUS current
      DESCRIPTION
          "The total number of packets (including bad
           packets) send  that were between
           1024 and 1518 octets in length inclusive
           (excluding framing bits but including FCS octets)."
      ::= { hwifXStatEntry 27 }

   hwBoardBindTable OBJECT-TYPE
      SYNTAX SEQUENCE OF HwBoardBindEntry
      MAX-ACCESS not-accessible
      STATUS current
      DESCRIPTION
         "Indicates the board bonding table. It is used for setting the bonding between boards.
          In addition, it supports the query of the status of the interconnected ports on bound
          boards. When you need to bind two boards or query the status of the interconnected
          ports on either board, use this table. The bound boards can be configured with inter-board
          aggregation and service configuration commands are delivered to the two boards.
          The index of this table is hwBindBrdFSIndex.
          "
      ::= { hwExtInterface 6 }

   hwBoardBindEntry OBJECT-TYPE
      SYNTAX HwBoardBindEntry
      MAX-ACCESS not-accessible
      STATUS current
      DESCRIPTION
         "Indicates the board bonding table. It is used for setting the bonding between boards.
          In addition, it supports the query of the status of the interconnected ports on bound
          boards. When you need to bind two boards or query the status of the interconnected
          ports on either board, use this table. The bound boards can be configured with inter-board
          aggregation and service configuration commands are delivered to the two boards.
          The index of this entry is hwBindBrdFSIndex.
          "
      INDEX { hwBindBrdFSIndex }
      ::= { hwBoardBindTable 1 }

   HwBoardBindEntry ::=
      SEQUENCE {
         hwBindBrdFSIndex
             InterfaceIndex,
         hwBindBrdAnotherFSIndex
             Integer32,
         hwLeftBrdLinkStatus
             Integer32,
         hwRightBrdLinkStatus
             Integer32,
         hwBoardBindRowStatus
             RowStatus,
         hwLeftBrdPrimaryStatus
             INTEGER,
         hwLeftBrdSecondaryStatus
             BITS,
         hwRightBrdPrimaryStatus
             INTEGER,
         hwRightBrdSecondaryStatus
             BITS
      }

   hwBindBrdFSIndex OBJECT-TYPE
      SYNTAX InterfaceIndex
      MAX-ACCESS not-accessible
      STATUS current
      DESCRIPTION
          "Ifindex of bound board in left slot."
      ::= { hwBoardBindEntry 1 }

   hwBindBrdAnotherFSIndex OBJECT-TYPE
      SYNTAX Integer32
      MAX-ACCESS read-write
      STATUS current
      DESCRIPTION
          "Ifindex of bound board in right slot."
      ::= { hwBoardBindEntry 2 }

   hwLeftBrdLinkStatus OBJECT-TYPE
      SYNTAX Integer32
      MAX-ACCESS read-only
      STATUS current
      DESCRIPTION
          "Link status of bound board in left slot.
           1:link up  2:link down   2: default"
      ::= { hwBoardBindEntry 3 }

   hwRightBrdLinkStatus OBJECT-TYPE
      SYNTAX Integer32
      MAX-ACCESS read-only
      STATUS current
      DESCRIPTION
          "Link status of bound board in right slot.
           1:link up  2:link down   2: default"
      ::= { hwBoardBindEntry 4 }

   hwBoardBindRowStatus OBJECT-TYPE
      SYNTAX RowStatus
      MAX-ACCESS read-create
      STATUS current
      DESCRIPTION
          "The present operation status of the row."
      ::= { hwBoardBindEntry 5 }

   hwLeftBrdPrimaryStatus OBJECT-TYPE
      SYNTAX INTEGER
      {
      isNr(1),
      isAnr(2),
      isRst(3),
      isAnrst(4),
      oosAu(5),
      oosMa(6),
      oosAuma(7),
      oosAurst(8),
      oosMaanr(9)
      }
      MAX-ACCESS read-only
      STATUS current
      DESCRIPTION
         "The primary status of the Board. This parameter indicates the current overall
         service condition of an entity, i.e., whether it is in-service or out-of-service.
         Options:
         1. isNr(1)     - In service, normal
         2. isAnr(2)    - In service, abnormal
         3. isRst(3)    - In service, restricted
         4. isAnrst(4)  - In service, abnormal & restricted
         5. oosAu(5)    - Out of service, autonomous
         6. oosMa(6)    - Out of service, management
         7. oosAuma(7)  - Out of service, autonomous & management
         8. oosAurst(8) - Out of service, autonomous & restricted
         9. oosMaanr(9) - Out of service, management & abnormal
         "
      ::= { hwBoardBindEntry 6 }

   hwLeftBrdSecondaryStatus OBJECT-TYPE
      SYNTAX BITS
      {
      sstAins(0),
      sstFaf(1),
      sstFlt(2),
      sstLpbk(3),
      sstMea(4),
      sstSgeo(5),
      sstStbyh(6),
      sstTs(7),
      sstUas(8),
      sstUeq(9),
      sstWrk(10),
      sstPwr(11)
      }
      MAX-ACCESS read-only
      STATUS current
      DESCRIPTION
        "This parameter indicates the secondary status of the board. The parameter provides additional
        information pertaining to PST and PSTQ. For example, it may indicate the type and/or reason of
        the external command, the event that occurred in the Network Element, etc. Multiple values may
        apply to an entity at a given moment. The highest bit of SST value indicates the sst-ains(0) status;
        the second highest bit of SST value indicates the sst-faf(1) status, and the rest can be deduced by analogy.
        This BITS structure can report the following status:
        1.  sstAins(0)  - This bit position positively reports that the status of the board is automatic in-service
        2.  sstFaf(1)   - Facility failure
        3.  sstFlt(2)   - Fault
        4.  sstLpbk(3)  - Loopback
        5.  sstMea(4)   - Mismatch of equipment and ettributes
        6.  sstSgeo(5)  - Supporting entity outage
        7.  sstStbyh(6) - Standby-hot
        8.  sstTs(7)    - Test
        9.  sstUas(8)   - Unassigned
        10. sstUeq(9)   - Unequipped
        11. sstWrk(10)  - Working
        12. sstPwr(11)  - Power
        "
      ::= { hwBoardBindEntry 7 }

   hwRightBrdPrimaryStatus OBJECT-TYPE
      SYNTAX INTEGER
      {
      isNr(1),
      isAnr(2),
      isRst(3),
      isAnrst(4),
      oosAu(5),
      oosMa(6),
      oosAuma(7),
      oosAurst(8),
      oosMaanr(9)
      }
      MAX-ACCESS read-only
      STATUS current
      DESCRIPTION
         "The primary status of the Board. This parameter indicates the current overall
         service condition of an entity, i.e., whether it is in-service or out-of-service.
         Options:
         1. isNr(1)     - In service, normal
         2. isAnr(2)    - In service, abnormal
         3. isRst(3)    - In service, restricted
         4. isAnrst(4)  - In service, abnormal & restricted
         5. oosAu(5)    - Out of service, autonomous
         6. oosMa(6)    - Out of service, management
         7. oosAuma(7)  - Out of service, autonomous & management
         8. oosAurst(8) - Out of service, autonomous & restricted
         9. oosMaanr(9) - Out of service, management & abnormal
         "
      ::= { hwBoardBindEntry 8 }

   hwRightBrdSecondaryStatus OBJECT-TYPE
      SYNTAX BITS
      {
      sstAins(0),
      sstFaf(1),
      sstFlt(2),
      sstLpbk(3),
      sstMea(4),
      sstSgeo(5),
      sstStbyh(6),
      sstTs(7),
      sstUas(8),
      sstUeq(9),
      sstWrk(10),
      sstPwr(11)
      }
      MAX-ACCESS read-only
      STATUS current
      DESCRIPTION

        "This parameter indicates the secondary status of the board. The parameter provides additional
        information pertaining to PST and PSTQ. For example, it may indicate the type and/or reason of
        the external command, the event that occurred in the Network Element, etc. Multiple values may
        apply to an entity at a given moment. The highest bit of SST value indicates the sst-ains(0) status;
        the second highest bit of SST value indicates the sst-faf(1) status, and the rest can be deduced by analogy.
        This BITS structure can report the following status:
        1.  sstAins(0)  - This bit position positively reports that the status of the board is automatic in-service
        2.  sstFaf(1)   - Facility failure
        3.  sstFlt(2)   - Fault
        4.  sstLpbk(3)  - Loopback
        5.  sstMea(4)   - Mismatch of equipment and attributes
        6.  sstSgeo(5)  - Supporting entity outage
        7.  sstStbyh(6) - Standby-hot
        8.  sstTs(7)    - Test
        9.  sstUas(8)   - Unassigned
        10. sstUeq(9)   - Unequipped
        11. sstWrk(10)  - Working
        12. sstPwr(11)  - Power
        "
      ::= { hwBoardBindEntry 9 }

   hwVlanLoopTable OBJECT-TYPE
      SYNTAX SEQUENCE OF HwVlanLoopEntry
      MAX-ACCESS not-accessible
      STATUS current
      DESCRIPTION
          "Interface Vlan Loop table entry
           The index of this table is hwVlanLoopIndex
          "
      ::= { hwExtInterface 7 }

   hwVlanLoopEntry OBJECT-TYPE
      SYNTAX HwVlanLoopEntry
      MAX-ACCESS not-accessible
      STATUS current
      DESCRIPTION
          "Interface Vlan Loop table entry
           The index of this entry is hwVlanLoopIndex
          "
      INDEX { hwVlanLoopIndex }
      ::= { hwVlanLoopTable 1 }

   HwVlanLoopEntry ::=
      SEQUENCE {
          hwVlanLoopIndex
              Integer32,
          hwVlanLoopSrcIfIndex
              Integer32,
          hwVlanLoopSrcOuterVlanId
              Integer32,
          hwVlanLoopSrcInnerVlanId
              Integer32,
          hwVlanLoopDstIfIndex
              Integer32,
          hwVlanLoopDstOuterVlanId
              Integer32,
          hwVlanLoopDstInnerVlanId
              Integer32,
          hwVlanLoopTimeout
              Integer32,
          hwVlanLoopRowStatus
              RowStatus
       }

   hwVlanLoopIndex OBJECT-TYPE
      SYNTAX Integer32
      MAX-ACCESS not-accessible
      STATUS current
      DESCRIPTION
          "Indicates the vlan loop index, a unique value to identify the vlan loop.
           Recently, the index value can only be fixed to 1.
          "
      ::= { hwVlanLoopEntry 1 }

   hwVlanLoopSrcIfIndex OBJECT-TYPE
      SYNTAX Integer32
      MAX-ACCESS read-write
      STATUS current
      DESCRIPTION
          "Source vlan loop port, whose format is the same as ifIndex "
      ::= { hwVlanLoopEntry 2 }

   hwVlanLoopSrcOuterVlanId OBJECT-TYPE
      SYNTAX Integer32 (1..4095)
      MAX-ACCESS read-write
      STATUS current
      DESCRIPTION
          "The outer vlan id of the source port , the bound of parameter is 1 to 4095 "
      ::= { hwVlanLoopEntry 3 }

   hwVlanLoopSrcInnerVlanId OBJECT-TYPE
      SYNTAX Integer32 (1..4095)
      MAX-ACCESS read-write
      STATUS current
      DESCRIPTION
          "The inner vlan id of the source port , the bound of patameter is 1 to 4095"
      ::= { hwVlanLoopEntry 4 }

   hwVlanLoopDstIfIndex OBJECT-TYPE
       SYNTAX Integer32
       MAX-ACCESS read-write
       STATUS current
       DESCRIPTION
           "The destination vlan loop port, whose format is the same as ifIndex "
       ::= { hwVlanLoopEntry 5 }

   hwVlanLoopDstOuterVlanId OBJECT-TYPE
       SYNTAX Integer32 (1..4095)
       MAX-ACCESS read-write
       STATUS current
       DESCRIPTION
           "The outer vlan id of the destination port , the bound of patameter is 1 to 4095 "
       ::= { hwVlanLoopEntry 6 }

   hwVlanLoopDstInnerVlanId OBJECT-TYPE
       SYNTAX Integer32 (1..4095)
       MAX-ACCESS read-only
       STATUS current
       DESCRIPTION
           "The inner vlan id of the destination port , the bound of patameter is 1 to 4095"
       ::= { hwVlanLoopEntry 7 }

   hwVlanLoopTimeout OBJECT-TYPE
       SYNTAX Integer32
       MAX-ACCESS read-only
       STATUS current
       DESCRIPTION
           "The remain time of the vlan loop before stopped.
           Recently, this leaf is not supported.
           Unit: second
           "
       ::= { hwVlanLoopEntry 8 }

   hwVlanLoopRowStatus OBJECT-TYPE
       SYNTAX RowStatus
       MAX-ACCESS read-create
       STATUS current
       DESCRIPTION
           "Indicates the row status.
           To create vlan loop, set this leaf to createAndGo(4).
           To delete vlan loop, set this leaf to destroy(6).
           When this leaf is queried, the value is fixed to active(1).
           Options:
           1. active(1)      -indicates the query operation
           2. createAndGo(4) -indicates creating vlan loop
           3. destroy(6)     -indicates deleting vlan loop
           "
       ::= { hwVlanLoopEntry 9 }

--hwAggregateStatisticsTable
   hwAggregateStatisticsTable OBJECT-TYPE
       SYNTAX     SEQUENCE OF HwAggregateStatisticsEntry
       MAX-ACCESS not-accessible
       STATUS     current
       DESCRIPTION
           "A collection of statistics kept for an aggregation.
            The value of statistics is the sum of all etherports under an aggregation.
            The index of this table is hwAggStatsIndex."
       ::= { hwExtInterface 9 }

   hwAggregateStatisticsEntry OBJECT-TYPE
       SYNTAX     HwAggregateStatisticsEntry
       MAX-ACCESS not-accessible
       STATUS     current
       DESCRIPTION
           "A collection of statistics kept for an aggregation.
            The value of statistics is the sum of all etherports under an aggregation.
           The index of this entry is hwAggStatsIndex."
       INDEX { hwAggStatsIndex }
       ::= { hwAggregateStatisticsTable 1 }

   HwAggregateStatisticsEntry ::= SEQUENCE {
       hwAggStatsIndex                                   Integer32,
       hwAggStatsDropEvents                              Counter64,
       hwAggStatsRecvOctets                              Counter64,
       hwAggStatsSendOctets                              Counter64,
       hwAggStatsTotalOctets                             Counter64,
       hwAggStatsRecvPkts                                Counter64,
       hwAggStatsSendPkts                                Counter64,
       hwAggStatsTotalPkts                               Counter64,
       hwAggStatsBroadcastRecvPkts                       Counter64,
       hwAggStatsBroadcastSendPkts                       Counter64,
       hwAggStatsBroadcastTotalPkts                      Counter64,
       hwAggStatsMulticastRecvPkts                       Counter64,
       hwAggStatsMulticastSendPkts                       Counter64,
       hwAggStatsMulticastTotalPkts                      Counter64,
       hwAggStatsCRCAlignErrors                          Counter64,
       hwAggStatsUndersizePkts                           Counter64,
       hwAggStatsOversizePkts                            Counter64,
       hwAggStatsFragments                               Counter64,
       hwAggStatsJabbers                                 Counter64,
       hwAggStatsCollisions                              Counter64,
       hwAggStatsPkts64Octets                            Counter64,
       hwAggStatsPkts65to127Octets                       Counter64,
       hwAggStatsPkts128to255Octets                      Counter64,
       hwAggStatsPkts256to511Octets                      Counter64,
       hwAggStatsPkts512to1023Octets                     Counter64,
       hwAggStatsPkts1024to1518Octets                    Counter64,
       hwAggStatsPkts1519to2047Octets                    Counter64,
       hwAggStatsPkts2048to4095Octets                    Counter64,
       hwAggStatsPkts4096to9216Octets                    Counter64,
       hwAggStatsPktsRecvPauseInfo                       Counter64,
       hwAggStatsPktsSendPauseInfo                       Counter64,
       hwAggStatsPktsSendSingleCollisionInfo             Counter64,
       hwAggStatsPktsSendMultiCollisionInfo              Counter64,
       hwAggStatsUpDiscardPacketsInfo                    Counter64,
       hwAggStatsDownDiscardPacketsInfo                  Counter64,
       hwAggStatsAlignmentErrorFramesInfo                Counter64,
       hwAggStatsSpeed                                   Unsigned32,
       hwAggStatsOutboundErrors                          Counter64,
       hwAggStatsClear                                   INTEGER
   }

   hwAggStatsIndex OBJECT-TYPE
       SYNTAX     Integer32
       MAX-ACCESS not-accessible
       STATUS     current
       DESCRIPTION
           "The value of this object(ifindex) uniquely identifies this
           aggregate entry."
       ::= { hwAggregateStatisticsEntry 1 }

   hwAggStatsDropEvents OBJECT-TYPE
       SYNTAX     Counter64
       MAX-ACCESS read-only
       STATUS     current
       DESCRIPTION
           "The total number of events in which packets
           were dropped by the probe due to lack of resources.
           Note that this number is not necessarily the number of
           packets dropped; it is just the number of times this
           condition has been detected.
           '18446744073709551615' means invalid value."
       ::= { hwAggregateStatisticsEntry 2 }

   hwAggStatsRecvOctets OBJECT-TYPE
       SYNTAX     Counter64
       UNITS      "Octets"
       MAX-ACCESS read-only
       STATUS     current
       DESCRIPTION
           "The total number of octets of data (including
           those in bad packets) received on the
           network (excluding framing bits but including
           FCS octets).
           '18446744073709551615' means invalid value."
       ::= { hwAggregateStatisticsEntry 3 }

   hwAggStatsSendOctets OBJECT-TYPE
       SYNTAX     Counter64
       UNITS      "Octets"
       MAX-ACCESS read-only
       STATUS     current
       DESCRIPTION
           "The total number of octets of data (including
           those in bad packets) sent on the
           network (excluding framing bits but including
           FCS octets).
           '18446744073709551615' means invalid value."
       ::= { hwAggregateStatisticsEntry 4 }

   hwAggStatsTotalOctets OBJECT-TYPE
       SYNTAX     Counter64
       UNITS      "Octets"
       MAX-ACCESS read-only
       STATUS     current
       DESCRIPTION
           "The total number of octets of data (including
           those in bad packets) on the
           network (excluding framing bits but including
           FCS octets).
           '18446744073709551615' means invalid value."
       ::= { hwAggregateStatisticsEntry 5 }

   hwAggStatsRecvPkts OBJECT-TYPE
       SYNTAX     Counter64
       UNITS      "Packets"
       MAX-ACCESS read-only
       STATUS     current
       DESCRIPTION
           "The total number of packets (including bad packets,
           broadcast packets, and multicast packets) received.
           '18446744073709551615' means invalid value."
       ::= { hwAggregateStatisticsEntry 6 }

   hwAggStatsSendPkts OBJECT-TYPE
       SYNTAX     Counter64
       UNITS      "Packets"
       MAX-ACCESS read-only
       STATUS     current
       DESCRIPTION
           "The total number of packets (including bad packets,
           broadcast packets, and multicast packets) sent.
           '18446744073709551615' means invalid value."
       ::= { hwAggregateStatisticsEntry 7 }

   hwAggStatsTotalPkts OBJECT-TYPE
       SYNTAX     Counter64
       UNITS      "Packets"
       MAX-ACCESS read-only
       STATUS     current
       DESCRIPTION
           "The total number of packets (including bad packets,
            broadcast packets, and multicast packets).
           '18446744073709551615' means invalid value."
       ::= { hwAggregateStatisticsEntry 8 }

   hwAggStatsBroadcastRecvPkts OBJECT-TYPE
       SYNTAX     Counter64
       UNITS      "Packets"
       MAX-ACCESS read-only
       STATUS     current
       DESCRIPTION
           "The total number of good packets received that were
           directed to the broadcast address.  Note that this
           does not include multicast packets.
           '18446744073709551615' means invalid value."
       ::= { hwAggregateStatisticsEntry 9 }

   hwAggStatsBroadcastSendPkts OBJECT-TYPE
       SYNTAX     Counter64
       UNITS      "Packets"
       MAX-ACCESS read-only
       STATUS     current
       DESCRIPTION
           "The total number of good packets send that were
           directed to the broadcast address.  Note that this
           does not include multicast packets.
           '18446744073709551615' means invalid value."
       ::= { hwAggregateStatisticsEntry 10 }

   hwAggStatsBroadcastTotalPkts OBJECT-TYPE
       SYNTAX     Counter64
       UNITS      "Packets"
       MAX-ACCESS read-only
       STATUS     current
       DESCRIPTION
           "The total number of good packets that were
           directed to the broadcast address.  Note that this
           does not include multicast packets.
           '18446744073709551615' means invalid value."
       ::= { hwAggregateStatisticsEntry 11 }

   hwAggStatsMulticastRecvPkts OBJECT-TYPE
       SYNTAX     Counter64
       UNITS      "Packets"
       MAX-ACCESS read-only
       STATUS     current
       DESCRIPTION
           "The total number of good packets received that were
           directed to a multicast address.  Note that this number
           does not include packets directed to the broadcast
           address.
           '18446744073709551615' means invalid value."
       ::= { hwAggregateStatisticsEntry 12 }

   hwAggStatsMulticastSendPkts OBJECT-TYPE
       SYNTAX     Counter64
       UNITS      "Packets"
       MAX-ACCESS read-only
       STATUS     current
       DESCRIPTION
           "The total number of good packets sent that were
           directed to a multicast address.  Note that this number
           does not include packets directed to the broadcast
           address.
           '18446744073709551615' means invalid value."
       ::= { hwAggregateStatisticsEntry 13 }

   hwAggStatsMulticastTotalPkts OBJECT-TYPE
       SYNTAX     Counter64
       UNITS      "Packets"
       MAX-ACCESS read-only
       STATUS     current
       DESCRIPTION
           "The total number of good packets that were
           directed to a multicast address.  Note that this number
           does not include packets directed to the broadcast
           address.
           '18446744073709551615' means invalid value."
       ::= { hwAggregateStatisticsEntry 14 }

   hwAggStatsCRCAlignErrors OBJECT-TYPE
       SYNTAX     Counter64
       UNITS      "Packets"
       MAX-ACCESS read-only
       STATUS     current
       DESCRIPTION
           "The total number of packets received that
           had a length (excluding framing bits, but
           including FCS octets) of between 64 and 1518
           octets, inclusive, but had either a bad
           Frame Check Sequence (FCS) with an integral
           number of octets (FCS Error) or a bad FCS with
           a non-integral number of octets (Alignment Error).
           '18446744073709551615' means invalid value."
       ::= { hwAggregateStatisticsEntry 15 }

   hwAggStatsUndersizePkts OBJECT-TYPE
       SYNTAX     Counter64
       UNITS      "Packets"
       MAX-ACCESS read-only
       STATUS     current
       DESCRIPTION
           "The total number of packets received that were
           less than 64 octets long (excluding framing bits,
           but including FCS octets) and were otherwise well
           formed.
           '18446744073709551615' means invalid value."
       ::= { hwAggregateStatisticsEntry 16 }

   hwAggStatsOversizePkts OBJECT-TYPE
       SYNTAX     Counter64
       UNITS      "Packets"
       MAX-ACCESS read-only
       STATUS     current
       DESCRIPTION
           "The total number of packets received that were
           longer than 1518 octets (excluding framing bits,
           but including FCS octets) and were otherwise
           well formed.
           '18446744073709551615' means invalid value."
       ::= { hwAggregateStatisticsEntry 17 }

   hwAggStatsFragments OBJECT-TYPE
       SYNTAX     Counter64
       UNITS      "Packets"
       MAX-ACCESS read-only
       STATUS     current
       DESCRIPTION
           "The total number of packets received that were less than
           64 octets in length (excluding framing bits but including
           FCS octets) and had either a bad Frame Check Sequence
           (FCS) with an integral number of octets (FCS Error) or a
           bad FCS with a non-integral number of octets (Alignment
           Error).

           Note that it is entirely normal for hwAggStatsFragments to
           increment.  This is because it counts both runts (which are
           normal occurrences due to collisions) and noise hits.
           '18446744073709551615' means invalid value."
       ::= { hwAggregateStatisticsEntry 18 }

   hwAggStatsJabbers OBJECT-TYPE
       SYNTAX     Counter64
       UNITS      "Packets"
       MAX-ACCESS read-only
       STATUS     current
       DESCRIPTION
           "The total number of packets received that were
           longer than 1518 octets (excluding framing bits,
           but including FCS octets), and had either a bad
           Frame Check Sequence (FCS) with an integral number
           of octets (FCS Error) or a bad FCS with a non-integral
           number of octets (Alignment Error).

           Note that this definition of jabber is different
           than the definition in IEEE-802.3 section 8.2.1.5
           (10BASE5) and section 10.3.1.4 (10BASE2).  These
           documents define jabber as the condition where any
           packet exceeds 20 ms.  The allowed range to detect
           jabber is between 20 ms and 150 ms.
           '18446744073709551615' means invalid value."
       ::= { hwAggregateStatisticsEntry 19 }

   hwAggStatsCollisions OBJECT-TYPE
       SYNTAX     Counter64
       UNITS      "Collisions"
       MAX-ACCESS read-only
       STATUS     current
       DESCRIPTION
           "The best estimate of the total number of collisions
           on this Ethernet segment.

           The value returned will depend on the location of the
           RMON probe. Section 8.2.1.3 (10BASE-5) and section
           10.3.1.3 (10BASE-2) of IEEE standard 802.3 states that a
           station must detect a collision, in the receive mode, if
           three or more stations are transmitting simultaneously.  A
           repeater port must detect a collision when two or more
           stations are transmitting simultaneously.  Thus a probe
           placed on a repeater port could record more collisions
           than a probe connected to a station on the same segment
           would.

           Probe location plays a much smaller role when considering
           10BASE-T.  14.2.1.4 (10BASE-T) of IEEE standard 802.3
           defines a collision as the simultaneous presence of signals
           on the DO and RD circuits (transmitting and receiving
           at the same time).  A 10BASE-T station can only detect
           collisions when it is transmitting.  Thus probes placed on
           a station and a repeater, should report the same number of
           collisions.

           Note also that an RMON probe inside a repeater should
           ideally report collisions between the repeater and one or
           more other hosts (transmit collisions as defined by IEEE
           802.3k) plus receiver collisions observed on any coax
           segments to which the repeater is connected.
           '18446744073709551615' means invalid value."
       ::= { hwAggregateStatisticsEntry 20 }

   hwAggStatsPkts64Octets OBJECT-TYPE
       SYNTAX     Counter64
       UNITS      "Packets"
       MAX-ACCESS read-only
       STATUS     current
       DESCRIPTION
           "The total number of packets (including bad
           packets) received that were 64 octets in length
           (excluding framing bits but including FCS octets).
           '18446744073709551615' means invalid value."
       ::= { hwAggregateStatisticsEntry 21 }

   hwAggStatsPkts65to127Octets OBJECT-TYPE
       SYNTAX     Counter64
       UNITS      "Packets"
       MAX-ACCESS read-only
       STATUS     current
       DESCRIPTION
           "The total number of packets (including bad
           packets) received that were between
           65 and 127 octets in length inclusive
           (excluding framing bits but including FCS octets).
           '18446744073709551615' means invalid value."
       ::= { hwAggregateStatisticsEntry 22 }

   hwAggStatsPkts128to255Octets OBJECT-TYPE
       SYNTAX     Counter64
       UNITS      "Packets"
       MAX-ACCESS read-only
       STATUS     current
       DESCRIPTION
           "The total number of packets (including bad
           packets) received that were between
           128 and 255 octets in length inclusive
           (excluding framing bits but including FCS octets).
           '18446744073709551615' means invalid value."
       ::= { hwAggregateStatisticsEntry 23 }

   hwAggStatsPkts256to511Octets OBJECT-TYPE
       SYNTAX     Counter64
       UNITS      "Packets"
       MAX-ACCESS read-only
       STATUS     current
       DESCRIPTION
           "The total number of packets (including bad
           packets) received that were between
           256 and 511 octets in length inclusive
           (excluding framing bits but including FCS octets).
           '18446744073709551615' means invalid value."
       ::= { hwAggregateStatisticsEntry 24 }

   hwAggStatsPkts512to1023Octets OBJECT-TYPE
       SYNTAX     Counter64
       UNITS      "Packets"
       MAX-ACCESS read-only
       STATUS     current
       DESCRIPTION
           "The total number of packets (including bad
           packets) received that were between
           512 and 1023 octets in length inclusive
           (excluding framing bits but including FCS octets).
           '18446744073709551615' means invalid value."
       ::= { hwAggregateStatisticsEntry 25 }

   hwAggStatsPkts1024to1518Octets OBJECT-TYPE
       SYNTAX     Counter64
       UNITS      "Packets"
       MAX-ACCESS read-only
       STATUS     current
       DESCRIPTION
           "The total number of packets (including bad
           packets) received that were between
           1024 and 1518 octets in length inclusive
           (excluding framing bits but including FCS octets).
           '18446744073709551615' means invalid value."
       ::= { hwAggregateStatisticsEntry 26 }

   hwAggStatsPkts1519to2047Octets OBJECT-TYPE
       SYNTAX     Counter64
       UNITS      "Packets"
       MAX-ACCESS read-only
       STATUS     current
       DESCRIPTION
           "Total number of frames of 1519-2047 bytes.
           '18446744073709551615' means invalid value."
       ::= { hwAggregateStatisticsEntry 27 }

   hwAggStatsPkts2048to4095Octets OBJECT-TYPE
       SYNTAX     Counter64
       UNITS      "Packets"
       MAX-ACCESS read-only
       STATUS     current
       DESCRIPTION
           "Total number of frames of 2048-4095 bytes.
           '18446744073709551615' means invalid value."
       ::= { hwAggregateStatisticsEntry 28 }

   hwAggStatsPkts4096to9216Octets OBJECT-TYPE
       SYNTAX     Counter64
       UNITS      "Packets"
       MAX-ACCESS read-only
       STATUS     current
       DESCRIPTION
           "Total number of frames of 4096-9216 bytes.
           '18446744073709551615' means invalid value."
       ::= { hwAggregateStatisticsEntry 29 }

   hwAggStatsPktsRecvPauseInfo OBJECT-TYPE
       SYNTAX     Counter64
       UNITS      "Packets"
       MAX-ACCESS read-only
       STATUS     current
       DESCRIPTION
           "Number of PAUSE frames received by the port.
           '18446744073709551615' means invalid value."
       ::= { hwAggregateStatisticsEntry 30 }

   hwAggStatsPktsSendPauseInfo OBJECT-TYPE
       SYNTAX     Counter64
       UNITS      "Packets"
       MAX-ACCESS read-only
       STATUS     current
       DESCRIPTION
           "Number of PAUSE frames send from the port.
           '18446744073709551615' means invalid value."
       ::= { hwAggregateStatisticsEntry 31 }

   hwAggStatsPktsSendSingleCollisionInfo OBJECT-TYPE
       SYNTAX     Counter64
       UNITS      "Packets"
       MAX-ACCESS read-only
       STATUS     current
       DESCRIPTION
           "The total number of packets sent correctly after a single collision.
           '18446744073709551615' means invalid value."
       ::= { hwAggregateStatisticsEntry 32 }

   hwAggStatsPktsSendMultiCollisionInfo OBJECT-TYPE
       SYNTAX     Counter64
       UNITS      "Packets"
       MAX-ACCESS read-only
       STATUS     current
       DESCRIPTION
           "The total number of packets sent correctly after multiple collisions.
           '18446744073709551615' means invalid value."
       ::= { hwAggregateStatisticsEntry 33 }

   hwAggStatsUpDiscardPacketsInfo OBJECT-TYPE
       SYNTAX     Counter64
       UNITS      "Packets"
       MAX-ACCESS read-only
       STATUS     current
       DESCRIPTION
           "The total number of up stream discarded packets.
           '18446744073709551615' means invalid value."
       ::= { hwAggregateStatisticsEntry 34 }

   hwAggStatsDownDiscardPacketsInfo OBJECT-TYPE
       SYNTAX     Counter64
       UNITS      "Packets"
       MAX-ACCESS read-only
       STATUS     current
       DESCRIPTION
           "The total number of down stream discarded packets.
           '18446744073709551615' means invalid value."
       ::= { hwAggregateStatisticsEntry 35 }

   hwAggStatsAlignmentErrorFramesInfo OBJECT-TYPE
       SYNTAX     Counter64
       UNITS      "Frames"
       MAX-ACCESS read-only
       STATUS     current
       DESCRIPTION
           "The total number of alignment error frames.
           '18446744073709551615' means invalid value."
       ::= { hwAggregateStatisticsEntry 36 }

   hwAggStatsSpeed OBJECT-TYPE
       SYNTAX     Unsigned32
       UNITS      "Kbps"
       MAX-ACCESS read-only
       STATUS     current
       DESCRIPTION
           "The total speed of Aggregate ports."
       ::= { hwAggregateStatisticsEntry 37 }

   hwAggStatsOutboundErrors OBJECT-TYPE
       SYNTAX     Counter64
       UNITS      "Packets"
       MAX-ACCESS read-only
       STATUS     current
       DESCRIPTION
           "The total number of outbound packets that could not be transmitted because of errors.
           '18446744073709551615' means invalid value."
       ::= { hwAggregateStatisticsEntry 38 }


   hwAggStatsClear OBJECT-TYPE
      SYNTAX INTEGER {
          clear(1),
          invalid(-1)
      }
      MAX-ACCESS read-write
      STATUS current
      DESCRIPTION
        "Clear aggregate port statistics information.
         Options:
         1. clear(1)    -In the set operation, clear port statistics information
         2. invalid(-1) -In the get operation, the invalid value -1 is returned.
        "
      ::= { hwAggregateStatisticsEntry 100 }

--hwAggregateStatisticsTable

   hwBoardSpeedModeTable OBJECT-TYPE
       SYNTAX     SEQUENCE OF HwBoardSpeedModeEntry
       MAX-ACCESS not-accessible
       STATUS     current
       DESCRIPTION
           "Indicates the speed mode of the board.
            The index of this table is hwFrameIndex and hwSlotIndex."
       ::= { hwExtInterface 10 }

   hwBoardSpeedModeEntry OBJECT-TYPE
       SYNTAX     HwBoardSpeedModeEntry
       MAX-ACCESS not-accessible
       STATUS     current
       DESCRIPTION
           "Indicates the speed mode of the board.
            The index of this entry is  hwFrameIndex and hwSlotIndex."
       INDEX { hwFrameIndex, hwSlotIndex }
       ::= { hwBoardSpeedModeTable 1 }

   HwBoardSpeedModeEntry ::=
      SEQUENCE {
       hwBoardSpeedMode
       Integer32
   }

   hwBoardSpeedMode OBJECT-TYPE
       SYNTAX     Integer32
       MAX-ACCESS read-write
       STATUS     current
       DESCRIPTION
         "The speed mode of the board.
          Options:
          1: port 0-7 GE(1)
          2: port 0-7 10GE(2)
          3: port 0-3 GE, port 4-7 10GE(3)
          Default: port 0-7 GE(1)."
       ::= { hwBoardSpeedModeEntry 1 }

   hwBoardCrcErrorAlarmControlTable OBJECT IDENTIFIER  ::= { hwExtInterface 12 }

   hwBoardCrcErrorAlarmSwitch OBJECT-TYPE
       SYNTAX INTEGER
           {
           enable(1),
           disable(2)
           }
       MAX-ACCESS read-write
       STATUS current
       DESCRIPTION
           "Enable/Disable the board CRC error alarm function.
            Options:
            1. enable(1)                  -Enable the board CRC error alarm function.
            2. disable(2)                 -Disable the board CRC error alarm function.
	    Default: disable(2).
           "
       ::= { hwBoardCrcErrorAlarmControlTable 1 }

   hwBoardCrcErrorAlarmDetectInterval OBJECT-TYPE
       SYNTAX Integer32 (30..1800)
       MAX-ACCESS read-write
       STATUS current
       DESCRIPTION
           "Indicates the interval for CRC error alarm detection for a board. Range: 30-1800s. Default value: 60s.
           "
       ::= { hwBoardCrcErrorAlarmControlTable 2 }

   hwBoardCrcErrorAlarmDetectMultiplier OBJECT-TYPE
       SYNTAX Integer32 (3..100)
       MAX-ACCESS read-write
       STATUS current
       DESCRIPTION
           "Indicates the number of CRC error alarm detection periods. If increasing CRC errors are detected in n consecutive periods, an error alarm is generated.
	    If no CRC error increase is detected in n consecutive periods, a recovery alarm is generated. Range: 3-100. Default value: 10.
           "
       ::= { hwBoardCrcErrorAlarmControlTable 3 }


   hwExtIpdslam OBJECT IDENTIFIER ::= { hwEthernetPort 3 }

   hwIpdslamConnectTable OBJECT-TYPE
       SYNTAX SEQUENCE OF HwIpdslamConnectEntry
       MAX-ACCESS not-accessible
       STATUS current
       DESCRIPTION
           "Indicates the table that contains certain extended attributes of a service flow.
            The index of this table is hwIpdslamConnectIndex.
           "
       ::= { hwExtIpdslam 1 }

   hwIpdslamConnectEntry OBJECT-TYPE
       SYNTAX HwIpdslamConnectEntry
       MAX-ACCESS not-accessible
       STATUS current
       DESCRIPTION
           "Indicates the table that contains certain extended attributes of a service flow.
            The index of this entry is hwIpdslamConnectIndex.
           "
       INDEX { hwIpdslamConnectIndex }
       ::= { hwIpdslamConnectTable 1 }

   HwIpdslamConnectEntry ::=
       SEQUENCE {
           hwIpdslamConnectIndex
               Integer32,
           hwIpdslamConnectFlowControl
               INTEGER,
           hwIpdslamConnectMaxMacLearn
               Integer32,
           hwIpdslamConnectMacLearnd
               Integer32,
           hwIpdslamConnectPriorityLevel
               INTEGER,
           hwIpdslamConnectSrcVportPhysical
               Integer32,
           hwIpdslamConnectDstVportPhysical
               Integer32,
           hwIpdslamConnectInnerVlanId
               Integer32,
           hwIpdslamConnectInnerVlanPriority
               Integer32,
           hwIpdslamConnectMulticastForwardingMode
               INTEGER
        }

   hwIpdslamConnectIndex OBJECT-TYPE
       SYNTAX Integer32
       MAX-ACCESS read-only
       STATUS current
       DESCRIPTION
           "For the broadband service, this leaf is the same as hwExtSrvFlowIndex,
            which indicates the service flow index,
            a unique value to identify a service flow.
           "
       ::= { hwIpdslamConnectEntry 1 }

   hwIpdslamConnectFlowControl OBJECT-TYPE
       SYNTAX INTEGER
           {
           bothOff(1),
           srcDown(2),
           dstDown(3),
           srcDownAndDstDown(4),
           srcUp(5),
           srcBoth(6),
           srcUpAndDstDown(7),
           srcBothAndDstDown(8),
           dstUp(9),
           dstUpAndSrcDown(10),
           dstBoth(11),
           dstBothAndSrcDown(12),
           dstUpAndSrcUp(13),
           dstUpAndSrcBoth(14),
           dstBothAndSrcUp(15),
           dstBothAndSrcBoth(16)
           }
       MAX-ACCESS read-write
       STATUS current
       DESCRIPTION
           "Enable/disable the connection flow control, and the source destination direction is determined by the direction created by PVC.
            The connect flow control.
            Options:
            1. bothOff(1)                 -The value is not supported.
            2. srcDown(2)                 -The value is not supported.
            3. dstDown(3)                 -The value is not supported.
            4. srcDownAndDstDown(4)       -The value is not supported.
            5. srcUp(5)                   -The value is not supported.
            6. srcBoth(6)                 -The value is not supported.
            7. srcUpAndDstDown(7)         -The value is not supported.
            8. srcBothAndDstDown(8)       -The value is not supported.
            9. dstUp(9)                   -The value is not supported.
            10. dstUpAndSrcDown(10)       -The value is not supported.
            11. dstBoth(11)               -The value is not supported.
            12. dstBothAndSrcDown(12)     -The value is not supported.
            13. dstUpAndSrcUp(13)         -The value is not supported.
            14. dstUpAndSrcBoth(14)       -The value is not supported.
            15. dstBothAndSrcUp(15)       -The value is not supported.
            16. dstBothAndSrcBoth(16)     -The value is not supported.
           "
       ::= { hwIpdslamConnectEntry 2 }

   hwIpdslamConnectMaxMacLearn OBJECT-TYPE
       SYNTAX Integer32 (-1|0..1023)
       MAX-ACCESS read-write
       STATUS current
       DESCRIPTION
           "Indicates the maximum number of learnable MAC addresses of the service port.
            Due to different hardware capabilities, the ports of different types support
            different value ranges. The ATM or xDSL port supports the range of 0-255,
            where 255 indicates unlimited. Here, the default value is 255.
            The Ethernet or xPON port supports the range of 0-1023, where 1023 indicates
            unlimited. Here, the default value is 1023.
           "
       ::= { hwIpdslamConnectEntry 3 }

   hwIpdslamConnectMacLearnd OBJECT-TYPE
       SYNTAX Integer32
       MAX-ACCESS read-only
       STATUS current
       DESCRIPTION
           "The number of MACs this connection has learned.
           "
       ::= { hwIpdslamConnectEntry 4 }

   hwIpdslamConnectPriorityLevel OBJECT-TYPE
       SYNTAX INTEGER
           {
           high(1),
           low(2)
           }
       MAX-ACCESS read-write
       STATUS current
       DESCRIPTION
           "The priority of this connection.
           Options:
           1. high(1)   -The value is not supported.
           2. low(2)    -The value is not supported.
           Before the priority function is enabled in LAN, the order of priority for each connection in LAN can be specified.
           "
       ::= { hwIpdslamConnectEntry 5 }

   hwIpdslamConnectSrcVportPhysical OBJECT-TYPE
       SYNTAX    Integer32
       MAX-ACCESS read-write
       STATUS current
       DESCRIPTION
           "The source virtual physical port of this connection.
           The port can't be bigger than or equal to 65535.
                           "
       ::= { hwIpdslamConnectEntry 6 }

   hwIpdslamConnectDstVportPhysical OBJECT-TYPE
       SYNTAX    Integer32
       MAX-ACCESS read-write
       STATUS current
       DESCRIPTION
           "The destination virtual physical port of this connection.
           The port can't be bigger than or equal to 65535.
                           "
       ::= { hwIpdslamConnectEntry 7 }

   hwIpdslamConnectInnerVlanId OBJECT-TYPE
       SYNTAX Integer32 (-1..4095)
       MAX-ACCESS read-write
       STATUS current
       DESCRIPTION
           "Indicates the network-side inner VLAN ID of switch-oriented service flow.
            The value of this leaf is variable with the value of hwExtSrvFlowTagTransform.
            If the value of hwExtSrvFlowTagTransform is set to 3, 4, 5, this leaf can be set to 1-4095.
            If the vlaue of hwExtSrvFlowTagTransform is set to 0, 1, 2 ,6, 7, 8, this leaf can not be set,
            and the invalid value -1 will be returned.
            This leaf is the same as hwExtSrvFlowNNIInnerVlanId.
           "
           DEFVAL { 1 }
       ::= { hwIpdslamConnectEntry 8 }

   hwIpdslamConnectInnerVlanPriority OBJECT-TYPE
       SYNTAX Integer32 (0..7|255)
       MAX-ACCESS read-write
       STATUS current
       DESCRIPTION
           "Indicates the network-side inner VLAN priority of switch-oriented service flow.
            The value of this leaf is variable with the value of hwExtSrvFlowTagTransform.
            If the value of hwExtSrvFlowTagTransform is set to 3, 4, 5, this leaf can be set to 0-7.
            If the vlaue of hwExtSrvFlowTagTransform is set to 0, 1, 2 ,6, 7, 8, this leaf can not be set,
            and the invalid value 255 will be returned.
            This leaf is the same as hwExtSrvFlowNNIInnerPriority.
            It is recommended that the IP traffic table be used to configure the inner
            VLAN priority of service flow instead of using hwExtSrvFlowNNIInnerPriority
            or hwIpdslamConnectInnerVlanPriority.
           "
       DEFVAL { 0 }
       ::= { hwIpdslamConnectEntry 9 }

   hwIpdslamConnectMulticastForwardingMode OBJECT-TYPE
       SYNTAX INTEGER {
           outervlan(1),
           outervlanInnervlan(2)
       }
       MAX-ACCESS read-write
       STATUS current
       DESCRIPTION
           "The flag of Multicast forwarding mode on service board.
           Options:
           1. outervlan(1)           -Indicates outer VLAN.
           2. outervlanInnervlan(2)  -Indicates outer VLAN and inner VLAN.
           "
       DEFVAL { outervlan }
       ::= { hwIpdslamConnectEntry 10 }

--hwIpdslamBindIpTable
   hwIpdslamBindIpTable OBJECT-TYPE
       SYNTAX SEQUENCE OF HwIpdslamBindIpEntry
       MAX-ACCESS not-accessible
       STATUS current
       DESCRIPTION
           "Used for binding an IP address to a service port. To statically configure the permitted IP address of
            a service port, use this table.
            After the IP address is bound to a service port successfully, the device allows only the upstream packets
            whose source IP address is the bound IP address to pass.
            The indexes of this table are hwIpdslamBindIpConnectIndex and hwIpdslamBindIpSubIndex, indicating the index of the service port.
            The service port corresponding to this index must already be created in hwExtSrvFlowEntry.
            hwIpdslamBindIpSubIndex is the index used for specifying the position on the service port for binding the
            IP address.
           "
       ::= { hwExtIpdslam 2 }

   hwIpdslamBindIpEntry OBJECT-TYPE
       SYNTAX HwIpdslamBindIpEntry
       MAX-ACCESS not-accessible
       STATUS current
       DESCRIPTION
           "Used for binding an IP address to a service port. To statically configure the permitted IP address of
            a service port, use this table.
            After the IP address is bound to a service port successfully, the device allows only the upstream packets
            whose source IP address is the bound IP address to pass.
            The indexes of this entry are hwIpdslamBindIpConnectIndex and hwIpdslamBindIpSubIndex, indicating the index of the service port.
            The service port corresponding to this index must already be created in hwExtSrvFlowEntry.
            hwIpdslamBindIpSubIndex is the index used for specifying the position on the service port for binding the
            IP address.
           "
       INDEX { hwIpdslamBindIpConnectIndex,hwIpdslamBindIpSubIndex }
       ::= { hwIpdslamBindIpTable 1 }

   HwIpdslamBindIpEntry ::=
       SEQUENCE {
           hwIpdslamBindIpConnectIndex
               Integer32,
           hwIpdslamBindIpSubIndex
               Integer32,
           hwIpdslamBindIpAddress
               IpAddress,
           hwIpdslamBindIpAddressRowStatus
               RowStatus,
           hwIpdslamBindIpAddressType
               InetAddressType,
           hwIpdslamBindIpv6Address
               InetAddress,
           hwIpdslamBindIpv6PrefixLength
               Unsigned32,
           hwIpdslamBindIpMaskLength
               Unsigned32
        }

   hwIpdslamBindIpConnectIndex OBJECT-TYPE
       SYNTAX      Integer32
       MAX-ACCESS  not-accessible
       STATUS      current
       DESCRIPTION
           "Indicates the index of the service port bound to a specified IP address.
            The service port corresponding to this index must already be created in
            hwExtSrvFlowEntry.
           "
       ::= { hwIpdslamBindIpEntry 1 }

   hwIpdslamBindIpSubIndex OBJECT-TYPE
       SYNTAX      Integer32
       MAX-ACCESS  not-accessible
       STATUS      current
       DESCRIPTION
           "This index is used for specifying the position on the service port for binding the IP address.
            hwIpdslamBindIpSubIndex is filled with -1, all IP addresses of the service port are deleted.
           "
       ::= { hwIpdslamBindIpEntry 2 }

   hwIpdslamBindIpAddress OBJECT-TYPE
       SYNTAX IpAddress
       MAX-ACCESS read-write
       STATUS current
       DESCRIPTION
           "Indicates the IP address bound to a specified service port.
           "
       ::= { hwIpdslamBindIpEntry 3 }

   hwIpdslamBindIpAddressRowStatus OBJECT-TYPE
       SYNTAX      RowStatus
       MAX-ACCESS  read-create
       STATUS      current
       DESCRIPTION
           "Indicates the row status.
            Options:
            1. active(1)
            2. createAndGo(4)
            3. destroy(6)
            During creation, hwIpdslamBindIpSubIndex may not be specified and can be
            automatically allocated by the system. In this case, you can fill in -1 for
            hwIpdslamBindIpSubIndex. After the system allocates a value successfully,
            and the system returns the allocated value to the NMS.
            During deletion, if you do not specify hwIpdslamBindIpSubIndex, that is,
            hwIpdslamBindIpSubIndex is filled with -1, all IP addresses of the service port are deleted.
           "
       ::= { hwIpdslamBindIpEntry 4 }

   hwIpdslamBindIpAddressType OBJECT-TYPE
       SYNTAX InetAddressType
       MAX-ACCESS read-write
       STATUS current
       DESCRIPTION
           "Indicates the IP address type to bind.
            Options:
            1. ipv4(1)  -indicates that the IP address type is ipv4
            2. ipv6(2)  -indicates that the IP address type is ipv6
            During creation, if hwIpdslamBindIpAddressType is not specified, it defaults to ipv4 when
            hwIpdslamBindIpAddress is specified.
           "
       ::= { hwIpdslamBindIpEntry 5 }

   hwIpdslamBindIpv6Address OBJECT-TYPE
       SYNTAX InetAddress
       MAX-ACCESS read-write
       STATUS current
       DESCRIPTION
           "Indicates the IPv6 address bound to a specified service port.
            It must be a valid unicast IPv6 address.
           "
       ::= { hwIpdslamBindIpEntry 6 }

   hwIpdslamBindIpv6PrefixLength OBJECT-TYPE
       SYNTAX Unsigned32
       MAX-ACCESS read-write
       STATUS current
       DESCRIPTION
           "Indicates the prefix length of the IPv6 address bound to a specified service port.
            i.e. Valid value only includes 48,56,60,64 and 128.
           "
       ::= { hwIpdslamBindIpEntry 7 }

   hwIpdslamBindIpMaskLength OBJECT-TYPE
       SYNTAX Unsigned32 (17..32|4294967295)
       MAX-ACCESS read-write
       STATUS current
       DESCRIPTION
           "Indicates the Mask length of the IPv4 address bound to a specified service port.
            Range: 17-32.
            The invalid value is 4294967295.
           "
       ::= { hwIpdslamBindIpEntry 8 }

--hwIpdslamBindMacTable
   hwIpdslamBindMacTable OBJECT-TYPE
       SYNTAX SEQUENCE OF HwIpdslamBindMacEntry
       MAX-ACCESS not-accessible
       STATUS current
       DESCRIPTION
           "Indicates MAC address binding feature.
            The indexes of this table are hwIpdslamBindMacConnectIndex and hwIpdslamBindMacSubIndex.

           "
       ::= { hwExtIpdslam 3 }

   hwIpdslamBindMacEntry OBJECT-TYPE
       SYNTAX HwIpdslamBindMacEntry
       MAX-ACCESS not-accessible
       STATUS current
       DESCRIPTION
           "Indicates MAC address binding feature.
            The indexes of this entry are hwIpdslamBindMacConnectIndex and hwIpdslamBindMacSubIndex.
           "
       INDEX { hwIpdslamBindMacConnectIndex,hwIpdslamBindMacSubIndex }
       ::= { hwIpdslamBindMacTable 1 }

   HwIpdslamBindMacEntry ::=
       SEQUENCE {
           hwIpdslamBindMacConnectIndex
               Integer32,
           hwIpdslamBindMacSubIndex
               Integer32,
           hwIpdslamBindMacAddress
               MacAddress,
           hwIpdslamBindMacAddressRowStatus
               RowStatus
        }

   hwIpdslamBindMacConnectIndex OBJECT-TYPE
       SYNTAX      Integer32
       MAX-ACCESS  not-accessible
       STATUS      current
       DESCRIPTION
           "Bind MAC address connect identification
           "
       ::= { hwIpdslamBindMacEntry 1 }

   hwIpdslamBindMacSubIndex OBJECT-TYPE
       SYNTAX      Integer32
       MAX-ACCESS  not-accessible
       STATUS      current
       DESCRIPTION
           "Bind MAC address sub index
           "
       ::= { hwIpdslamBindMacEntry 2 }

   hwIpdslamBindMacAddress OBJECT-TYPE
       SYNTAX MacAddress
       MAX-ACCESS read-write
       STATUS current
       DESCRIPTION
           "The MAC address to bind
           "
       ::= { hwIpdslamBindMacEntry 3 }

   hwIpdslamBindMacAddressRowStatus OBJECT-TYPE
       SYNTAX      RowStatus
       MAX-ACCESS  read-create
       STATUS      current
       DESCRIPTION
                   "Bind MAC address operate (add(4),delete(6))
                   "
       ::= { hwIpdslamBindMacEntry 4 }

--hwIpdslamQryLocation
   hwIpdslamQryLocation OBJECT IDENTIFIER ::= { hwExtIpdslam 4 }

   hwIpdslamQryCondition OBJECT-TYPE
       SYNTAX OCTET STRING (SIZE (0..17))
       MAX-ACCESS read-write
       STATUS current
       DESCRIPTION
           "Indicates the content to be queried. Currently, only MAC address query is supported.
            The following is an example of the input format of the MAC address:
            Assuming that a MAC address is 00-e0-fc-11-00-00,
            it should be input as 00-e0-fc-11-00-00.
           "
       ::= { hwIpdslamQryLocation 1 }

   hwIpdslamQryType OBJECT-TYPE
       SYNTAX INTEGER
           {
           mac(1),
           ip(2),
           invalid(-1)
           }
       MAX-ACCESS read-write
       STATUS current
       DESCRIPTION
           "Indicates the query condition.
            Options:
            1. mac(1)      -indicates the query is by a MAC address.
            2. ip(2)       -indicates that the query is by an IP address.
            3. invalid(-1) -indicates invalid.
            Currently, only MAC address query is supported.
           "
       ::= { hwIpdslamQryLocation 2 }

-- hwCosQueueMappingMask
   hwCosQueueMappingMask OBJECT-TYPE
       SYNTAX Unsigned32
       MAX-ACCESS read-write
       STATUS current
       DESCRIPTION
           "As an independent leaf node, describes the mapping between 802.1p priority and queue.

            The queue ID is 0-7. Every four bits represents the queue ID to which an 802.1p priority corresponds.
            When hwCosQueueMappingMask is set to 0xffffffff(4294967295), it means restoring it to default settings.

            The default mapping is as follows: Packets with priority 7 join queue 7, packets with priority 6 join queue 6, and so on.
            The corresponding bits are:
            0111 0110 0101 0100 0011 0010 0001 0000
               7    6    5    4    3    2    1    0
            Default: 1985229328
           "
       ::= { hwExtIpdslam 5 }

-- hwCosQueueSchedTable
   hwCosQueueSchedTable OBJECT IDENTIFIER ::= { hwExtIpdslam 6 }

   hwCosQueueSchedMode OBJECT-TYPE
       SYNTAX INTEGER
           {
           strictPriority(1),
           wrr(2),
           wfq(3)
           }
       MAX-ACCESS read-write
       STATUS current
       DESCRIPTION
           "Indicates the queue scheduling mode.
            Options:
            1. strictPriority(1) -PQ
            2. wrr(2) -WRR
            3. wfq(3) -WFQ

            In the case of PQ scheduling, PQ takes out all packets from a queue with a high priority and transmits them.
            After such a transmission is completed, PQ performs the same on all packets in a queue with an intermediate priority,
            a queue with a normal priority, and a queue with a low priority one by one.
            In this way, packets in a queue with the highest priority precede packets in a queue with a less higher priority and
            therefore are processed preferentially, even in case of congestion.
            This ensures that packets for key services are processed first.

            WRR and WFQ are of weighted scheduling type.
            Unlike WRR, WFQ scheduling is based on byte quantity rather than packet quantity. This requires more precise weight assignment.
           "
       ::= { hwCosQueueSchedTable 1 }

   hwCosQueueWeightQue0 OBJECT-TYPE
       SYNTAX Integer32(0..100|255)
       MAX-ACCESS read-write
       STATUS current
       DESCRIPTION
          "Indicates the weight of queue 0.
           Range: 0-100, 255
           When set the weight of queue to 255, it indicates that the queue is unused.
           When modifying the weight of queue 0, if the queue schedule mode is wrr, make sure that the sum of weights equals to 100,
           if the queue schedule mode is wfq, make sure that the sum of weights is no bigger than 100.
          "
       ::= { hwCosQueueSchedTable 2 }

   hwCosQueueWeightQue1 OBJECT-TYPE
       SYNTAX Integer32(0..100|255)
       MAX-ACCESS read-write
       STATUS current
       DESCRIPTION
           "Indicates the weight of queue 1.
            Range: 0-100, 255
            When set the weight of queue to 255, it indicates that the queue is unused.
            When modifying the weight of queue 1, if the queue schedule mode is wrr, make sure that the sum of weights equals to 100,
            if the queue schedule mode is wfq, make sure that the sum of weights is no bigger than 100.           "
       ::= { hwCosQueueSchedTable 3 }

   hwCosQueueWeightQue2 OBJECT-TYPE
       SYNTAX Integer32(0..100|255)
       MAX-ACCESS read-write
       STATUS current
       DESCRIPTION
           "Indicates the weight of queue 2.
            Range: 0-100, 255
            When set the weight of queue to 255, it indicates that the queue is unused.
            When modifying the weight of queue 2, if the queue schedule mode is wrr, make sure that the sum of weights equals to 100,
            if the queue schedule mode is wfq, make sure that the sum of weights is no bigger than 100.
           "
       ::= { hwCosQueueSchedTable 4 }

   hwCosQueueWeightQue3 OBJECT-TYPE
       SYNTAX Integer32(0..100|255)
       MAX-ACCESS read-write
       STATUS current
       DESCRIPTION
           "Indicates the weight of queue 3.
            Range: 0-100, 255
            When set the weight of queue to 255, it indicates that the queue is unused.
            When modifying the weight of queue 3, if the queue schedule mode is wrr, make sure that the sum of weights equals to 100,
            if the queue schedule mode is wfq, make sure that the sum of weights is no bigger than 100.
           "
       ::= { hwCosQueueSchedTable 5 }

   hwCosQueueWeightQue4 OBJECT-TYPE
       SYNTAX Integer32(0..100|255)
       MAX-ACCESS read-write
       STATUS current
       DESCRIPTION
          "Indicates the weight of queue 4.
           Range: 0-100, 255
           When set the weight of queue to 255, it indicates that the queue is unused.
           When modifying the weight of queue 4, if the queue schedule mode is wrr, make sure that the sum of weights equals to 100,
           if the queue schedule mode is wfq, make sure that the sum of weights is no bigger than 100.
          "
       ::= { hwCosQueueSchedTable 6 }

   hwCosQueueWeightQue5 OBJECT-TYPE
       SYNTAX Integer32(0..100|255)
       MAX-ACCESS read-write
       STATUS current
       DESCRIPTION
           "Indicates the weight of queue 5.
            Range: 0-100, 255
            When set the weight of queue to 255, it indicates that the queue is unused.
            When modifying the weight of queue 5, if the queue schedule mode is wrr, make sure that the sum of weights equals to 100,
            if the queue schedule mode is wfq, make sure that the sum of weights is no bigger than 100.
           "
       ::= { hwCosQueueSchedTable 7 }

   hwCosQueueWeightQue6 OBJECT-TYPE
        SYNTAX Integer32 (0..100|255)
        MAX-ACCESS read-write
        STATUS current
        DESCRIPTION
            "Indicates the weight of queue 6.
             Range: 0-100, 255
             When set the weight of queue to 255, it indicates that the queue is unused.
             When modifying the weight of queue 6, if the queue schedule mode is wrr, make sure that the sum of weights equals to 100,
             if the queue schedule mode is wfq, make sure that the sum of weights is no bigger than 100.
            "
        ::= { hwCosQueueSchedTable 8 }

   hwCosQueueWeightQue7 OBJECT-TYPE
         SYNTAX Integer32 (0..100|255)
         MAX-ACCESS read-write
         STATUS current
         DESCRIPTION
             "Indicates the weight of queue 7.
              Range: 0-100, 255
              When set the weight of queue to 255, it indicates that the queue is unused.
              When modifying the weight of queue 7, if the queue schedule mode is wrr, make sure that the sum of weights equals to 100,
              if the queue schedule mode is wfq, make sure that the sum of weights is no bigger than 100.
             "
         ::= { hwCosQueueSchedTable 9 }

-- hwCosQueueDepthRateTable
   hwCosQueueDepthRateTable OBJECT IDENTIFIER ::= { hwExtIpdslam 7 }

   hwCosQueueDepthRateQue0 OBJECT-TYPE
       SYNTAX Integer32(-1|0..100)
       MAX-ACCESS read-write
       STATUS current
       DESCRIPTION
           "Indicates the depth of queue 0, that is, percentage of the buffer exclusively occupied by queue 0.
            Range: 0-100, -1
            The larger the percentage, the more packets can be buffered. The sum of percentages must be 100%.
            When the percentages are restored to default settings, -1 as a unified queue depth is issued for eight queues.
            When setting the queue depth, enter at least 7 queues (0-6). The eighth queue depth is automatically calculated.
            Value range for each queue is 0-100.
           "
       ::= { hwCosQueueDepthRateTable 1 }

   hwCosQueueDepthRateQue1 OBJECT-TYPE
       SYNTAX Integer32(-1|0..100)
       MAX-ACCESS read-write
       STATUS current
       DESCRIPTION
           "Indicates the depth of queue 1, that is, percentage of the buffer exclusively occupied by queue 1.
            Range: 0-100, -1
            The larger the percentage, the more packets can be buffered. The sum of percentages must be 100%.
            When the percentages are restored to default settings, -1 as a unified queue depth is issued for eight queues.
            When setting the queue depth, enter at least 7 queues (0-6). The eighth queue depth is automatically calculated.
            Value range for each queue is 0-100.
           "
       ::= { hwCosQueueDepthRateTable 2 }

   hwCosQueueDepthRateQue2 OBJECT-TYPE
       SYNTAX Integer32(-1|0..100)
       MAX-ACCESS read-write
       STATUS current
       DESCRIPTION
           "Indicates the depth of queue 2, that is, percentage of the buffer exclusively occupied by queue 2.
            Range: 0-100, -1
            The larger the percentage, the more packets can be buffered. The sum of percentages must be 100%.
            When the percentages are restored to default settings, -1 as a unified queue depth is issued for eight queues.
            When setting the queue depth, enter at least 7 queues (0-6). The eighth queue depth is automatically calculated.
            Value range for each queue is 0-100.
           "
       ::= { hwCosQueueDepthRateTable 3 }

   hwCosQueueDepthRateQue3 OBJECT-TYPE
       SYNTAX Integer32(-1|0..100)
       MAX-ACCESS read-write
       STATUS current
       DESCRIPTION
           "Indicates the depth of queue 3, that is, percentage of the buffer exclusively occupied by queue 3.
            Range: 0-100, -1
            The larger the percentage, the more packets can be buffered. The sum of percentages must be 100%.
            When the percentages are restored to default settings, -1 as a unified queue depth is issued for eight queues.
            When setting the queue depth, enter at least 7 queues (0-6). The eighth queue depth is automatically calculated.
            Value range for each queue is 0-100.
           "
       ::= { hwCosQueueDepthRateTable 4 }

   hwCosQueueDepthRateQue4 OBJECT-TYPE
       SYNTAX Integer32(-1|0..100)
       MAX-ACCESS read-write
       STATUS current
       DESCRIPTION
           "Indicates the depth of queue 4, that is, percentage of the buffer exclusively occupied by queue 4.
            Range: 0-100, -1
            The larger the percentage, the more packets can be buffered. The sum of percentages must be 100%.
            When the percentages are restored to default settings, -1 as a unified queue depth is issued for eight queues.
            When setting the queue depth, enter at least 7 queues (0-6). The eighth queue depth is automatically calculated.
            Value range for each queue is 0-100.
           "
       ::= { hwCosQueueDepthRateTable 5 }

   hwCosQueueDepthRateQue5 OBJECT-TYPE
       SYNTAX Integer32(-1|0..100)
       MAX-ACCESS read-write
       STATUS current
       DESCRIPTION
           "Indicates the depth of queue 5, that is, percentage of the buffer exclusively occupied by queue 5.
            Range: 0-100, -1
            The larger the percentage, the more packets can be buffered. The sum of percentages must be 100%.
            When the percentages are restored to default settings, -1 as a unified queue depth is issued for eight queues.
            When setting the queue depth, enter at least 7 queues (0-6). The eighth queue depth is automatically calculated.
            Value range for each queue is 0-100.
           "
       ::= { hwCosQueueDepthRateTable 6 }

   hwCosQueueDepthRateQue6 OBJECT-TYPE
       SYNTAX Integer32(-1|0..100)
       MAX-ACCESS read-write
       STATUS current
       DESCRIPTION
           "Indicates the depth of queue 6, that is, percentage of the buffer exclusively occupied by queue 6.
            Range: 0-100, -1
            The larger the percentage, the more packets can be buffered. The sum of percentages must be 100%.
            When the percentages are restored to default settings, -1 as a unified queue depth is issued for eight queues.
            When setting the queue depth, enter at least 7 queues (0-6). The eighth queue depth is automatically calculated.
            Value range for each queue is 0-100.
           "
       ::= { hwCosQueueDepthRateTable 7 }

   hwCosQueueDepthRateQue7 OBJECT-TYPE
       SYNTAX Integer32(-1|0..100)
       MAX-ACCESS read-write
       STATUS current
       DESCRIPTION
           "Indicates the depth of queue 7, that is, percentage of the buffer exclusively occupied by queue 7.
            Range: 0-100, -1
            The larger the percentage, the more packets can be buffered. The sum of percentages must be 100%.
            When the percentages are restored to default settings, -1 as a unified queue depth is issued for eight queues.
            When setting the queue depth, enter at least 7 queues (0-6). The eighth queue depth is automatically calculated.
            Value range for each queue is 0-100.
           "
       ::= { hwCosQueueDepthRateTable 8 }

--hwIpTrafficParamTable
   hwIpTrafficParamTable OBJECT-TYPE
       SYNTAX SEQUENCE OF HwIpTrafficParamEntry
       MAX-ACCESS not-accessible
       STATUS current
       DESCRIPTION
           "Indicates the IP traffic profile.
            It is used to add, query, modify, or delete an IP traffic profile.
            This table mainly involves configuring CAR parameters such as CIR, PIR,
            CBS, and PBS and re-marking priority.
            The index of this table is hwIpTrafficIndex.
           "
       ::= { hwExtIpdslam 8 }

   hwIpTrafficParamEntry OBJECT-TYPE
       SYNTAX HwIpTrafficParamEntry
       MAX-ACCESS not-accessible
       STATUS current
       DESCRIPTION
           "Indicates the IP traffic profile.
            It is used to add, query, modify, or delete an IP traffic profile.
            This table mainly involves configuring CAR parameters such as CIR, PIR,
            CBS, and PBS and re-marking priority.
            The index of this entry is hwIpTrafficIndex.
           "
       INDEX { hwIpTrafficIndex }
       ::= { hwIpTrafficParamTable 1 }


   HwIpTrafficParamEntry ::=
       SEQUENCE {
           hwIpTrafficIndex
               Integer32,
           hwIpTrafficName
               OCTET STRING,
           hwIpTrafficCir
               Integer32,
           hwIpTrafficCbs
               Integer32,
           hwIpTrafficPir
               Integer32,
           hwIpTrafficPbs
               Integer32,
           hwIpTrafficCm
               INTEGER,
           hwIpTrafficPriority
               Integer32,
           hwIpTrafficPriorityPolicy
               INTEGER,
           hwIpTrafficRowStatus
               RowStatus,
           hwIpTrafficInnerPriority
               Integer32,
           hwIpTrafficInnerPriorityMappingIndex
               Integer32,
           hwIpTrafficPriorityMappingIndex
                Integer32,
           hwIpTrafficColorPolicy
                INTEGER,
           hwIpTrafficCarThresholdProfileIndex
               Integer32,
           hwIpTrafficFixBandWidth
               Integer32,
           hwIpTrafficCouplingFlag
               INTEGER,
           hwIpTrafficDSCP
               Integer32,
           hwIpTrafficDSCPMappingIndex
               Integer32,
           hwIpTrafficDropPrecedence
               INTEGER,
           hwIpTrafficColorDEI
               INTEGER,
           hwIpTrafficColorSource
               INTEGER,
           hwIpTrafficE2EPriority
               Integer32,
           hwIpTrafficE2EPriorityMappingIndex
               Integer32,
           hwIpTrafficRateProfileName
             OCTET STRING,
           hwIpTrafficQueuePolicyProfileIndex
             Integer32,
           hwIpTrafficPriorityGroupProfileName
             OCTET STRING,
           hwIpTrafficWrrWeightYellow
             Integer32,
           hwIpTrafficWrrWeightGreen
             Integer32
        }

   hwIpTrafficIndex OBJECT-TYPE
       SYNTAX Integer32 (-1|1..1024)
       MAX-ACCESS accessible-for-notify
       STATUS current
       DESCRIPTION
           "Indicates the table index.
            Range: 1-1024, -1
            When creating an IP traffic profile, you can specify or not specify a profile index.
            If you specify it to 4294967295, the system will automatically allocates an idle index.
            The system has seven default IP traffic profiles (profiles 1 to 7)
            referenced by services of different traffic levels.
           "
       ::= { hwIpTrafficParamEntry 1 }

   hwIpTrafficName OBJECT-TYPE
       SYNTAX OCTET STRING  (SIZE (1..32))
       MAX-ACCESS read-write
       STATUS current
       DESCRIPTION
           "Indicates the traffic table name.
            Each IP traffic profile has a unique name. When creating an IP traffic profile,
            you can specify or not specify a profile name. If you do not specify it,
            the system automatically generates a default profile name.
            The IP traffic profile name is of a character string type, a string of 1-32 characters.
            There are all together 92 valid characters for the name. These characters include the following:
            uppercase and lowercase English letters (52 characters), numerals (0-9),
            and 30 symbols: ! # $ % & ' ( ) * + , - . / : ; < = > @ [ \ ] ^ _ ` { | } ~.
           "
       ::= { hwIpTrafficParamEntry 2 }

   hwIpTrafficCir OBJECT-TYPE
       SYNTAX Integer32 (-1|0..10240000)
       MAX-ACCESS read-write
       STATUS current
       DESCRIPTION
           "Indicates the committed information rate (CIR).
            Range: -1, 0-10240000 kbit/s.
            Unit: kbit/s.
            CIR is a mandatory parameter. This parameter must be an integer multiple of 64.
            If the entered value is not an integer multiple of 64,
            it rounds down to the nearest integer multiple of 64.
            When the CIR value ranges from 0 to 63, value 0 takes effect. For boards that do not support the CIR with values less than 64, 64 takes effect if the configured value is less than 64.
            -1 indicates CIR off.
           "
       ::= { hwIpTrafficParamEntry 3 }

   hwIpTrafficCbs OBJECT-TYPE
       SYNTAX Integer32 (-1|0..1024000000)
       MAX-ACCESS read-write
       STATUS current
       DESCRIPTION
           "Indicates the committed burst size (CBS).
            Range: -1, 0-1024000000 bytes.
            Unit: bytes.
            CBS is an optional parameter. If the parameter is not specified,
            it can be obtained by formula min(2000+cir*32,1024000000).
            For boards that do not support CBS with values less than 2000, 2000 takes effect if the configured value is less than 2000.
            -1 indicates CBS off.
           "
       ::= { hwIpTrafficParamEntry 4 }

   hwIpTrafficPir OBJECT-TYPE
       SYNTAX Integer32 (-1|64..10240000)
       MAX-ACCESS read-write
       STATUS current
       DESCRIPTION
           "Indicates the peak information rate (PIR).
            Range: -1, 64-10240000 kbit/s.
            Unit: kbit/s.
            PIR is an optional parameter. If the parameter is not specified,
            it can be obtained through formula max(min(2*cir,10240000),64).
            The PIR must be greater than or equal to the CIR.
            -1 indicates PIR off.
           "
       ::= { hwIpTrafficParamEntry 5 }

   hwIpTrafficPbs OBJECT-TYPE
       SYNTAX Integer32 (-1|2000..1024000000)
       MAX-ACCESS read-write
       STATUS current
       DESCRIPTION
           "Indicates the peak burst size (PBS).
            Range: -1, 2000-1024000000 bytes.
            Unit: bytes.
            PBS is an optional parameter.If the parameter is not specified,
            it can be obtained by formula min(2000+32*pir,1024000000).
            -1 indicates PBS off.
           "
       ::= { hwIpTrafficParamEntry 6 }

   hwIpTrafficCm OBJECT-TYPE
       SYNTAX INTEGER
           {
           colorBlind(1),
           colorAware(2)
           }
       MAX-ACCESS read-write
       STATUS current
       DESCRIPTION
           "Indicates the color-aware mode of the IP traffic profile.
            Options:
            1. colorBlind(1)      -Indicates color blind mode.
            2. colorAware(2)      -Indicates color aware mode.
           "
       ::= { hwIpTrafficParamEntry 7 }

   hwIpTrafficPriority OBJECT-TYPE
       SYNTAX Integer32
       MAX-ACCESS read-write
       STATUS current
       DESCRIPTION
           "Indicates the outer priority of the IP traffic profile.
            The higher 16 bits indicate the outer priority mapping policy and the lower 16 bits indicate the outer priority.
            The outer priority storage mode of the IP traffic profile is shown as follows:

            ---------------------------------------------------------
            |      31-16                     |      15-0             |
            ---------------------------------------------------------
            | Outer priority mapping policy  |   Outer priority      |
            ---------------------------------------------------------

            Here,
            Outer priority mapping policy:
            0xFF (specified priority), 0xFE (priority mapped from the outer CoS field on the ingress),
            0xFD (priority copied from the ToS field), 0xFC (priority mapped from the inner CoS field on the ingress),
            and 0xFB (priority mapped from the packet DSCP field on the ingress).
            Outer priority: Range: 0-7.
            Outer priority here indicates the specified priority when the priority copy policy is to specify a priority.
            Outer priority here indicates the default priority when the priority copy policy is to map the priority.
            For example, if the outer priority mapping policy is 0xFB and the priority is 2,
            the value of hwIpTrafficPriority is 0xFB0002, that is, 16449538.
           "
       ::= { hwIpTrafficParamEntry 8 }

   hwIpTrafficPriorityPolicy OBJECT-TYPE
       SYNTAX INTEGER
           {
           localPriority(1),
           egressOuter802dot1p(2),
           inner802dot1p(3),
           ingressOuter802dot1p(4),
           queuePolicyProfile(5)
           }
       MAX-ACCESS read-write
       STATUS current
       DESCRIPTION
           "Indicates the queue-joining trust priority policy of the IP traffic profile.
            Options:
            1. localPriority(1)              -Indicates the queue-joining trust the priority set by IP traffic profile.
            2. egressOuter802dot1p(2)        -Indicates the queue-joining trust the priority in the outer 802.1p tag of the egress packet.
            3. inner802dot1p(3)              -The value is not supported.
            4. ingressOuter802dot1p(4)       -Indicates the queue-joining trust the priority in the outer 802.1p tag of the ingress packet.
                                              When the IP traffic table applying to the service flow in the inbound direction of the user port,
                                              the queue-joining trust the priority in the outer 802.1p tag of the egress packet.
                                              When the IP traffic table applying to the service flow in the outbound direction of the user port,
                                              the queue-joining trust the priority in the outer 802.1p tag of the ingress packet.
            5. queuePolicyProfile(5)         -Indicates the queue-joining use the configuration of queue policy profile specified in hwIpTrafficQueuePolicyProfileIndex.
            Only support localPriority(1), egressOuter802dot1p(2), ingressOuter802dot1p(4) and queuePolicyProfile(5) in current version.
           "
       ::= { hwIpTrafficParamEntry 9 }

   hwIpTrafficRowStatus OBJECT-TYPE
       SYNTAX RowStatus
       MAX-ACCESS read-create
       STATUS current
       DESCRIPTION
           "Indicates the row status.
            Options:
            1. active(1)
            2. createAndGo(4)
            3. destroy(6)
            To create an IP traffic profile, set this leaf to createAndGo(4);
            to delete an IP traffic profile, set this leaf to destroy(6).
            When an IP traffic profile is queried, this leaf is displayed as active(1).
            The IP traffic profiles with indexes 1-7 do not support the create operation.
           "
       ::= { hwIpTrafficParamEntry 10 }

   hwIpTrafficInnerPriority OBJECT-TYPE
       SYNTAX Integer32
       MAX-ACCESS read-write
       STATUS current
       DESCRIPTION
           "Indicates the inner priority of the IP traffic profile.
            The higher 16 bits indicate the inner priority mapping policy and the lower 16 bits indicate the inner priority.
            The inner priority storage mode of the IP traffic profile is shown as follows:

                     --------------------------------------------------------
                     |           31-16                |         15-0         |
                     --------------------------------------------------------
                     |  Inner priority mapping policy |  Inner priority      |
                     --------------------------------------------------------
            Here,
            Inner priority mapping policy:
            0xFF (specified priority), 0xFE (priority mapped from the outer CoS field on the ingress),
            0xFD (priority copied from the ToS field), 0xFC (priority mapped from the inner CoS field on the ingress),
            0xFB (priority mapped from the packet DSCP field on the ingress) and 0xFA (do not edit).
            Inner priority: Range: 0-7.
            Inner priority here indicates the specified priority when the priority copy policy is to specify a priority.
            Inner priority here indicates the default priority when the priority copy policy is to copy the priority.
            Inner priority is invalid when the priority copy policy is 0xFA (do not edit). Therefore, you must enter 0xff.
            For example, if the inner priority copy policy is 0xFE and the default priority is 4,
            the value of hwIpTrafficInnerPriority is 0xFE0004, that is, 16646148.
           "
       ::= { hwIpTrafficParamEntry 11 }

   hwIpTrafficInnerPriorityMappingIndex OBJECT-TYPE
       SYNTAX Integer32 (-1|1..4)
       MAX-ACCESS read-write
       STATUS current
       DESCRIPTION
           "When the inner VLAN priority mapping policy is mapping from the outer or inner CoS domain on the ingress,
            the index (range: 1-4) of the service port priority mapping profile is used.
            The referenced service port priority mapping profile must exist in hwPbitsToPbitsMappingTable.
            When the inner VLAN priority mapping policy is mapping from the packet DSCP domain on the ingress,
            the index (range: 1-4) of the DSCP-to-802.1p priority mapping profile is used.
            The referenced DSCP-to-802.1p priority mapping profile must exist in hwDscpToPbitsMappingTable.
            -1 indicates the default value.
           "
       ::= { hwIpTrafficParamEntry 12 }

   hwIpTrafficPriorityMappingIndex OBJECT-TYPE
       SYNTAX Integer32 (-1|1..4)
       MAX-ACCESS read-write
       STATUS current
       DESCRIPTION
           "When the outer VLAN priority mapping policy is mapping from the outer or inner CoS domain on the ingress,
            the index (range: 1-4) of the service port priority mapping profile is used.
            The referenced service port priority mapping profile must exist in hwPbitsToPbitsMappingTable.
            When the outer VLAN priority mapping policy is mapping from the packet DSCP domain on the ingress,
            the index (range: 1-4) of the DSCP-to-802.1p priority mapping profile is used.
            The referenced DSCP-to-802.1p priority mapping profile must exist in hwDscpToPbitsMappingTable.
            -1 indicates the default value.
           "
       ::= { hwIpTrafficParamEntry 13 }

    hwIpTrafficColorPolicy OBJECT-TYPE
        SYNTAX INTEGER
        {
            dei(1),
            cos(2)
        }
        MAX-ACCESS read-write
        STATUS current
        DESCRIPTION
            "Indicates the color policy of the IP traffic profile.
             Options:
             1. dei(1)    -Indicate the dei mode.
             2. cos(2)    -Indicate the CoS mode.
            "
        ::= { hwIpTrafficParamEntry 14 }

    hwIpTrafficCarThresholdProfileIndex OBJECT-TYPE
        SYNTAX Integer32 (-1|1..4)
        MAX-ACCESS read-write
        STATUS current
        DESCRIPTION
            "Indicates the car-threshold profile of the IP traffic profile"
        ::= { hwIpTrafficParamEntry 15 }

    hwIpTrafficFixBandWidth OBJECT-TYPE
        SYNTAX Integer32 (-1|0..10240000)
        MAX-ACCESS read-write
        STATUS current
        DESCRIPTION
            "Indicates the fixed bandwidth to be allocated by the DBA. This parameter takes effect to the E2E service flow only on a GPON board.
             Range: -1, 0-10240000 kbit/s.
             Unit: kbit/s.
             hwIpTrafficFixBandWidth must be smaller than or equal to CIR.
             -1 indicates fixed bandwidth is not supported.
            "
        ::= { hwIpTrafficParamEntry 16 }

   hwIpTrafficCouplingFlag OBJECT-TYPE
	SYNTAX INTEGER
		{
		disable(0),
		enable(1)
		}
	MAX-ACCESS read-write
	STATUS current
	DESCRIPTION
            "The Coupling Flag CF is set to either 0 or 1. The choice of the value for CF has the effect of controlling the volume of the yellow
             Service Frames admitted to the network. When CF is set to 0, the long term average bit rate of bytes in yellow service frames admitted
             to the network is bounded by EIR which is equal to PIR-CIR. When CF is set to 1, the long term average bit rate of bytes in yellow
             Service Frames admitted to the network is bounded by PIR depending on volume of the offered green Service Frames.
             In both cases the burst size of the yellow Service Frames admitted to the network is bounded which is equal to PIR-CIR.
             Options:
             1. disable(0) --disable the function of double-color.
             2. enable(1)  --enable the function of double-color.
            "
	::= { hwIpTrafficParamEntry 17 }

   hwIpTrafficDSCP OBJECT-TYPE
	SYNTAX Integer32
	MAX-ACCESS read-write
	STATUS current
	DESCRIPTION
            "Indicates the DSCP source.
             The most significant 16 bits indicate the DSCP policy, and the least significant 16 bits indicate the DSCP value.
                    --------------------------------------------------------
                    |           31-16                |         15-0         |
                    --------------------------------------------------------
                    |       DSCP mark policy         |      DSCP value      |
                    --------------------------------------------------------
             Options of the DSCP policy are as follows:
             OxFF: indicates that the DSCP field is not edited.
             OxFE: indicates that the mapping is based on user-dscp.
             0xFD: indicates the specified DSCP value.
             Other values are not supported.

             When the DSCP policy is user-dscp(OxFE), the hwIpTrafficDSCPMappingIndex must be set.
             When the DSCP policy is not user-dscp(OxFE), the hwIpTrafficDSCPMappingIndex must be -1 or not set.

             The DSCP value ranges from 0 to 63 and takes effect only when the DSCP policy is 0xFD.

             For example, if the DSCP mark policy is 0xFD and the specified DSCP is 6,
             the value of hwIpTrafficDSCP is 0xFD0006, that is, 16580614.
            "
	::= { hwIpTrafficParamEntry 18 }

   hwIpTrafficDSCPMappingIndex OBJECT-TYPE
	SYNTAX Integer32 (-1|1..4)
	MAX-ACCESS read-write
	STATUS current
	DESCRIPTION
           "Indicates the index of the referenced DSCP mapping profile.
            When the hwIpTrafficDSCP is set to user-dscp(OxFE), the mapping profile index must be set to a valid profile.
            When the hwIpTrafficDSCP is not set to user-dscp(OxFE), the mapping profile index must be set to -1 or not set.
            -1 indicates that the function is not supported or this node does not take effect under the DSCP policy.
	   "
	::= { hwIpTrafficParamEntry 19 }

   hwIpTrafficDropPrecedence OBJECT-TYPE
	SYNTAX INTEGER
		{
		invalid(-1),
		remarkedOuterPriority(0),
		remarkedInnerPriority(1)
		}
	MAX-ACCESS read-write
	STATUS current
	DESCRIPTION
           "Indicates the packet discarding policy.
            Options:
	    1. invalid(-1)   -indicates that this function is not supported.
            2. remarkedOuterPriority(0)  -indicates that the internal packet discarding priority is the priority of the mapped outer VLAN.
            3. remarkedInnerPriority(1)  -indicates that the internal packet discarding priority is the priority of the mapped inner VLAN.
           "
	::= { hwIpTrafficParamEntry 20 }

   hwIpTrafficColorDEI OBJECT-TYPE
	SYNTAX INTEGER
		{
		unmarkDei(0),
		outerDei(1),
		innerDei(2),
		outerInnerDei(3)
		}
	MAX-ACCESS read-write
	STATUS current
	DESCRIPTION
	   "Indicates the color mark. It indicates whether and where the color is marked.
	    Options:
	    1. unmarkDei(0)     -indicates that the color is not marked.
	    2. outerDei(1)      -indicates that the color is marked on the outer VLAN's DEI.
	    3. innerDei(2)      -indicates that the color is marked on the inner VLAN's DEI.
	    4. outerInnerDei(3) -indicates that the color is marked on DEIs of both the inner and outer VLANs.
	   "
	::= { hwIpTrafficParamEntry 21 }

   hwIpTrafficColorSource OBJECT-TYPE
	SYNTAX INTEGER
		{
		invalid(-1),
		outerDei(1),
		innerDei(2)
		}
	MAX-ACCESS read-write
	STATUS current
	DESCRIPTION
	   "Indicates the color source. It indicates where the color is marked.
	    Default: outerDei(1).
	    Options:
	    1. invalid(-1)      -invalid value.
	    2. outerDei(1)      -indicates that the color is marked on the outer VLAN's DEI.
	    3. innerDei(2)      -indicates that the color is marked on the inner VLAN's DEI.
	   "
	::= { hwIpTrafficParamEntry 22 }

	hwIpTrafficE2EPriority OBJECT-TYPE
       SYNTAX Integer32
       MAX-ACCESS read-write
       STATUS current
       DESCRIPTION
           "Indicates the e2e priority of the IP traffic profile.
            The higher 16 bits indicate the outer priority mapping policy and the lower 16 bits indicate the e2e priority.
            The e2e priority storage mode of the IP traffic profile is shown as follows:

            ---------------------------------------------------------
            |      31-16                     |      15-0             |
            ---------------------------------------------------------
            |   e2e priority mapping policy  |     e2e priority      |
            ---------------------------------------------------------

            Here,
            e2e priority mapping policy:
            0xFE (priority mapped from the outer CoS field on the ingress),
            0xFB (priority mapped from the packet DSCP field on the ingress)and 0xFA (do not edit).
            e2e priority: Range: 0-7.
            e2e priority here indicates the default priority when the priority copy policy is to map the priority.
            e2e priority is invalid when the priority copy policy is 0xFA (do not edit). Therefore, you must enter 0xff.
            For example, if the e2e priority mapping policy is 0xFB and the priority is 2,
            the value of hwIpTrafficE2EPriority is 0xFB0002, that is, 16449538.
           "
       ::= { hwIpTrafficParamEntry 23 }

   hwIpTrafficE2EPriorityMappingIndex OBJECT-TYPE
       SYNTAX Integer32
       MAX-ACCESS read-write
       STATUS current
       DESCRIPTION
           "When the e2e VLAN priority mapping policy is mapping from the outer CoS domain on the ingress,
            the index (range: 1-16) of the service port priority mapping profile is used.
            The referenced service port priority mapping profile must exist in hwPbitsToPbitsMappingTable.
            When the e2e VLAN priority mapping policy is mapping from the packet DSCP domain on the ingress,
            the index (range: 1-50) of the DSCP-to-802.1p priority mapping profile is used.
            The referenced DSCP-to-802.1p priority mapping profile must exist in hwDscpToPbitsMappingTable.
            -1 indicates the default value.
           "
       ::= { hwIpTrafficParamEntry 24 }

  hwIpTrafficRateProfileName OBJECT-TYPE
      SYNTAX OCTET STRING (SIZE(0..32))
      MAX-ACCESS read-write
      STATUS current
      DESCRIPTION
          "Indicates the name of the rate profile.
          "
      ::= { hwIpTrafficParamEntry 25 }


 hwIpTrafficQueuePolicyProfileIndex OBJECT-TYPE
     SYNTAX Integer32 (-1|1..4)
     MAX-ACCESS read-write
     STATUS current
     DESCRIPTION
         "Indicates the index of the queue policy profile.
          Range: 1-4
         "
     ::= { hwIpTrafficParamEntry 26 }

 hwIpTrafficPriorityGroupProfileName OBJECT-TYPE
     SYNTAX OCTET STRING (SIZE(0..32))
     MAX-ACCESS read-write
     STATUS current
     DESCRIPTION
         "Indicates the name of the priority group profile.
         "
     ::= { hwIpTrafficParamEntry 27 }

  hwIpTrafficWrrWeightYellow OBJECT-TYPE
        SYNTAX Integer32 (0|1..12)
        MAX-ACCESS read-write
        STATUS current
        DESCRIPTION
            "Indicates the WRR weight for yellow color packet.
             Range: 0, 1-12
             Default: 0
             0 indicates WRR weight is auto calculated by PIR and CIR.
            "
        ::= { hwIpTrafficParamEntry 28 }

    hwIpTrafficWrrWeightGreen OBJECT-TYPE
     SYNTAX Integer32 (0|1..12)
     MAX-ACCESS read-write
     STATUS current
     DESCRIPTION
         "Indicates the WRR weight for green color packet.
          Range: 0, 1-12
          Default: 0
          0 indicates WRR weight is auto calculated by PIR and CIR.
         "
     ::= { hwIpTrafficParamEntry 29 }

   hwBoardTrafficModeTable OBJECT-TYPE
       SYNTAX SEQUENCE OF HwBoardTrafficModeEntry
       MAX-ACCESS not-accessible
       STATUS current
       DESCRIPTION
           "Indicates the CAR mode. It is used to modify and query the board CAR mode and does not support the
            create or delete operation. Before the CAR mode of a board is modified, the board cannot have any
            service port or port CAR configuration. When the CAR mode of a board is modified, hwFrameIndex and
            hwSlotIndex must be specified and leaf hwBoardTrafficModeType must be issued.
            The indexes of this table are hwFrameIndex and hwSlotIndex.
           "
       ::= { hwExtIpdslam 9 }

   hwBoardTrafficModeEntry OBJECT-TYPE
       SYNTAX HwBoardTrafficModeEntry
       MAX-ACCESS not-accessible
       STATUS current
       DESCRIPTION
           "Indicates the CAR mode. It is used to modify and query the board CAR mode and does not support the
            create or delete operation. Before the CAR mode of a board is modified, the board cannot have any
            service port or port CAR configuration. When the CAR mode of a board is modified, hwFrameIndex and
            hwSlotIndex must be specified and leaf hwBoardTrafficModeType must be issued.
            The indexes of this entry are hwFrameIndex and hwSlotIndex.
           "
       INDEX { hwFrameIndex,hwSlotIndex }
       ::= { hwBoardTrafficModeTable 1 }

   HwBoardTrafficModeEntry ::=
       SEQUENCE {
           hwBoardTrafficModeType
           INTEGER
        }

   hwBoardTrafficModeType OBJECT-TYPE
       SYNTAX INTEGER
           {
           servicePort(1),
           portCos(2),
           invalid(-1)
           }
       MAX-ACCESS read-write
       STATUS current
       DESCRIPTION
           "Indicates the board CAR mode. It can be flow CAR or port+CoS CAR.
            If the board supports the port CAR mode, this leaf is used to configure the port CAR mode
            in batches for all ports.
            The port CAR mode is set by hwPortCarModeTable.
            Options:
            1. servicePort(1)       -When the board CAR mode is set to servicePort(1),
                                     the CAR is performed based on service port.
            2. portCos(2)           -when the board CAR mode is set to portCos(2),
                                     the index of the traffic profile used when the service port is created becomes invalid,
                                     and the CAR is controlled according to the priorities of packets on the port.
            3. invalid(-1)          -When this leaf is queried, if the board supports the port CAR mode and
                                     the port CAR mode of ports are different, the value is invalid(-1).
            Default: servicePort(1)
           "
       ::= { hwBoardTrafficModeEntry 1 }

--hwCosPortTrafficTable
   hwCosPortTrafficTable OBJECT-TYPE
       SYNTAX SEQUENCE OF HwCosPortTrafficEntry
       MAX-ACCESS not-accessible
       STATUS current
       DESCRIPTION
           "Indicates the port+CoS CAR table. It is used to add, query, modify, or delete the IP traffic
            profile used by the port+CoS CAR. The indexes of this table are ifIndex, hwCosPortExtPara1,
            hwCosPortOntId, hwCosPortGemIndex and hwCosPortTrafficCos. The port+CoS CAR can be set only
            when the board CAR mode is portCos(2). When querying or modifying the port+CoS CAR, you must
            enter both the IP traffic profiles used by the upstream traffic and downstream traffic (either
            the names or indexes of the upstream and downstream IP traffic profiles can be entered).
           "
       ::= { hwExtIpdslam 10 }

   hwCosPortTrafficEntry OBJECT-TYPE
       SYNTAX HwCosPortTrafficEntry
       MAX-ACCESS not-accessible
       STATUS current
       DESCRIPTION
           "Indicates the port+CoS CAR table. It is used to add, query, modify, or delete the IP traffic
            profile used by the port+CoS CAR. The indexes of this entry are ifIndex, hwCosPortExtPara1,
            hwCosPortOntId, hwCosPortGemIndex and hwCosPortTrafficCos. The port+CoS CAR can be set only
            when the board CAR mode is portCos(2). When querying or modifying the port+CoS CAR, you must
            enter both the IP traffic profiles used by the upstream traffic and downstream traffic (either
            the names or indexes of the upstream and downstream IP traffic profiles can be entered).
           "
       INDEX { ifIndex, hwCosPortExtPara1, hwCosPortOntId, hwCosPortGemIndex, hwCosPortTrafficCos }
       ::= { hwCosPortTrafficTable 1 }


   HwCosPortTrafficEntry ::=
       SEQUENCE {
           hwCosPortTrafficCos
               Integer32,
           hwCosPortInboundTrafficIndex
               Integer32,
           hwCosPortOutboundTrafficIndex
               Integer32,
           hwCosPortTrafficRowStatus
               RowStatus,
           hwCosPortExtPara1
               Integer32,
           hwCosPortInboundTrafficName
               OCTET STRING,
           hwCosPortOutboundTrafficName
               OCTET STRING,
           hwCosPortOntId
               Integer32,
           hwCosPortGemIndex
               Integer32,
           hwCosPortCosGroupTableIndex
               Integer32
        }

   hwCosPortTrafficCos OBJECT-TYPE
       SYNTAX Integer32 (0..15)
       MAX-ACCESS not-accessible
       STATUS current
       DESCRIPTION
           "It is one of table indexes. Its meaning varies with the value range. When the value range is 0-7, it indicates the priority for
            the specified CoS field of packets.When the value range is 8-15, it indicates the index for the CoS group of packets.
            Before rate limitation based on CoS group is performed, the CoS-group table must be bound.
            Only one of the two rate limitation modes can be selected at a time for a GEM port.
            Range: 0-15
           "
       ::= { hwCosPortTrafficEntry 1 }

   hwCosPortInboundTrafficIndex OBJECT-TYPE
       SYNTAX Integer32 (1..1024)
       MAX-ACCESS read-write
       STATUS current
       DESCRIPTION
           "Indicates the index of the IP traffic profile used by upstream packets.
            Range: 1-1024
            The IP traffic profile indicated by this index must exist in hwIpTrafficParamTable.
           "
       ::= { hwCosPortTrafficEntry 2 }

   hwCosPortOutboundTrafficIndex OBJECT-TYPE
       SYNTAX Integer32 (1..1024)
       MAX-ACCESS read-write
       STATUS current
       DESCRIPTION
           "Indicates the index of the IP traffic profile used by downstream packets.
            Range: 1-1024
            The IP traffic profile indicated by this index must exist in hwIpTrafficParamTable.
           "
       ::= { hwCosPortTrafficEntry 3 }

   hwCosPortTrafficRowStatus OBJECT-TYPE
       SYNTAX RowStatus
       MAX-ACCESS read-create
       STATUS current
       DESCRIPTION
           "Indicates the row status.
            In creation, you must set this leaf to createAndGo(4) and must enter both the IP traffic profiles used by the upstream traffic
            and downstream traffic (either the names or indexes of the upstream and downstream IP traffic profiles can be entered);
            in deletion, set this leaf to destroy(6);
            in query, this leaf is displayed as active(1).
            Options:
            1. active(1)      -indicates the query operation
            2. createAndGo(4) -indicates creating a cos port traffic
            3. destroy(6)     -indicates deleting a cos port traffic
           "
       ::= { hwCosPortTrafficEntry 4 }

   hwCosPortExtPara1 OBJECT-TYPE
       SYNTAX Integer32
       MAX-ACCESS not-accessible
       STATUS current
       DESCRIPTION
           "It is one of table indexes. It is a difference parameter between access modes, indicating the GEM port ID.
            This leaf is valid when the GPON board works in the distributing mode and invalid in other cases. Value
            -1 indicates that the leaf is invalid.
            Default: -1
           "
       ::= { hwCosPortTrafficEntry 5 }

   hwCosPortInboundTrafficName OBJECT-TYPE
       SYNTAX OCTET STRING  (SIZE (0..32))
       MAX-ACCESS read-write
       STATUS current
       DESCRIPTION
           "Indicates the name of the IP address used by upstream packets.
            The IP traffic profile indicated by this name must exist in hwIpTrafficParamTable.
           "
       ::= { hwCosPortTrafficEntry 6 }

   hwCosPortOutboundTrafficName OBJECT-TYPE
       SYNTAX OCTET STRING  (SIZE (0..32))
       MAX-ACCESS read-write
       STATUS current
       DESCRIPTION
           "Indicates the name of the IP address used by downstream packets.
            The IP traffic profile indicated by this name must exist in hwIpTrafficParamTable.
           "
       ::= { hwCosPortTrafficEntry 7 }

   hwCosPortOntId OBJECT-TYPE
       SYNTAX Integer32 (-1|0..255)
       MAX-ACCESS not-accessible
       STATUS current
       DESCRIPTION
           "It is one of table indexes. It is a difference parameter between access modes, indicating the ONT ID.
            Range: -1, 0-255
            This leaf is valid when the GPON works in the profile mode or when the board is an EPON board. In other
            cases, this index is invalid. Value 4294967295 indicates that the leaf is invalid.
            Default: -1
           "
       ::= { hwCosPortTrafficEntry 8 }

   hwCosPortGemIndex OBJECT-TYPE
       SYNTAX Integer32 (-1|0..1023)
       MAX-ACCESS not-accessible
       STATUS current
       DESCRIPTION
           "It is one of table indexes. It is a difference parameter between access modes, indicating the GEM index.
            Range: -1, 0-1023
            This leaf is valid when the GPON board works in the profile mode and invalid in other cases. Value
            -1 indicates that the leaf is invalid.
            Default: -1
           "
       ::= { hwCosPortTrafficEntry 9 }

   hwCosPortCosGroupTableIndex OBJECT-TYPE
       SYNTAX Integer32 (-1|1..16)
       MAX-ACCESS read-only
       STATUS current
       DESCRIPTION
           "It indicates the index of the CoS-group table bound to the GEM port.
            Range: -1 | 1-16
            The value -1 indicates that this leaf is invalid.
           "
       ::= { hwCosPortTrafficEntry 10 }

-- hwIsCtrlPacket2CPU
   hwIsCtrlPacket2CPU OBJECT-TYPE
       SYNTAX INTEGER
           {
           enable(1),
           disable(2)
           }
       MAX-ACCESS read-write
       STATUS current
       DESCRIPTION
           "Indicates the switch for transmitting control packets to the CPU
            when the maximum number of learnable dynamic MAC addresses is set to 0.
            Options:
            1. enable(1)   -indicates that the PPPoA LCP_config, PPPoA LCP_terminate_req,
                            PPPoE discovery, IGMP, ICMP, DHCP, and OAM packets reported by
                            the service port are transmitted to the CPU when the maximum
                            number of learnable MAC addresses of the service port is 0.
            2. disable(2)  -indicates that after the transmission of control packets to the
                            CPU is disabled, control packets are not transmitted to the CPU
                            when the maximum number of learnable MAC addresses of the service
                            port is 0.
           "
       ::= { hwExtIpdslam 11 }

-- hwIpTrafficIndexNext
   hwIpTrafficIndexNext OBJECT-TYPE
       SYNTAX Integer32
       MAX-ACCESS read-only
       STATUS current
       DESCRIPTION
           "This object contains an appropriate value to be used for hwIpTrafficIndex
            when creating entries are being created in the hwIpTrafficParamTable.
            The value 0 indicates that no unassigned entries are available.
            To obtain the hwIpTrafficIndex value for a new entry,
            the manager issues a management protocol retrieval operation to obtain the current value of this object.
            After each retrieval, the agent must modify the value to the next unassigned index.
            After a manager retrieves a value, the agent will determine through its local policy when this
            index value will be made available for reuse.
           "
       ::= { hwExtIpdslam 12 }

-- hwCosWREDThresholdTable
   hwCosWREDThresholdTable OBJECT IDENTIFIER ::= { hwExtIpdslam 13 }

   hwCosWREDThreshold0 OBJECT-TYPE
       SYNTAX Integer32 (-1..100)
       MAX-ACCESS read-write
       STATUS current
       DESCRIPTION
           "Indicates the early drop threshold of queue 0.
            Range: -1,0-100
            -1 is the invalid value.
            When configuring the priority threshold of CoS queues, make sure that hwEarlyDropMode be priBase(1).
           "
       ::= { hwCosWREDThresholdTable 1 }

   hwCosWREDThreshold1 OBJECT-TYPE
       SYNTAX Integer32 (-1..100)
       MAX-ACCESS read-write
       STATUS current
       DESCRIPTION
           "Indicates the early drop threshold of queue 1.
            Range: -1,0-100. -1 is the invalid value.
            When configuring the priority threshold of CoS queues, make sure that hwEarlyDropMode be priBase(1).
           "
       ::= { hwCosWREDThresholdTable 2 }

   hwCosWREDThreshold2 OBJECT-TYPE
       SYNTAX Integer32 (-1..100)
       MAX-ACCESS read-write
       STATUS current
       DESCRIPTION
           "Indicates the early drop threshold of queue 2.
            Range: -1,0-100.
            -1 is the invalid value.
            When configuring the priority threshold of CoS queues, make sure that hwEarlyDropMode be priBase(1).
           "
       ::= { hwCosWREDThresholdTable 3 }

   hwCosWREDThreshold3 OBJECT-TYPE
       SYNTAX Integer32 (-1..100)
       MAX-ACCESS read-write
       STATUS current
       DESCRIPTION
           "Indicates the early drop threshold of queue 3.
            Range: -1,0-100.
            -1 is the invalid value.
            When configuring the priority threshold of CoS queues, make sure that hwEarlyDropMode be priBase(1).
           "
       ::= { hwCosWREDThresholdTable 4 }

   hwCosWREDThreshold4 OBJECT-TYPE
       SYNTAX Integer32 (-1..100)
       MAX-ACCESS read-write
       STATUS current
       DESCRIPTION
           "Indicates the early drop threshold of queue 4.
            Range: -1,0-100.
            -1 is the invalid value.
            When configuring the priority threshold of CoS queues, make sure that hwEarlyDropMode be priBase(1).
           "
       ::= { hwCosWREDThresholdTable 5 }

   hwCosWREDThreshold5 OBJECT-TYPE
       SYNTAX Integer32 (-1..100)
       MAX-ACCESS read-write
       STATUS current
       DESCRIPTION
           "Indicates the early drop threshold of queue 5.
            Range: -1,0-100.
            -1 is the invalid value.
            When configuring the priority threshold of CoS queues, make sure that hwEarlyDropMode be priBase(1).
           "
       ::= { hwCosWREDThresholdTable 6 }

   hwCosWREDThreshold6 OBJECT-TYPE
       SYNTAX Integer32 (-1..100)
       MAX-ACCESS read-write
       STATUS current
       DESCRIPTION
           "Indicates the early drop threshold of queue 6.
            Range: -1,0-100.
            -1 is the invalid value.
            When configuring the priority threshold of CoS queues, make sure that hwEarlyDropMode be priBase(1).
           "
       ::= { hwCosWREDThresholdTable 7 }

   hwCosWREDThreshold7 OBJECT-TYPE
       SYNTAX Integer32 (-1..100)
       MAX-ACCESS read-write
       STATUS current
       DESCRIPTION
           "Indicates the early drop threshold of queue 7.
            Range: -1,0-100.
            -1 is the invalid value.
            When configuring the priority threshold of CoS queues, make sure that hwEarlyDropMode be priBase(1).
           "
       ::= { hwCosWREDThresholdTable 8 }

-- hwCarThresholdTable
   hwCarThresholdTable OBJECT IDENTIFIER ::= { hwExtIpdslam 14 }

   hwCarThresholdCos0 OBJECT-TYPE
       SYNTAX Integer32 (0..100)
       MAX-ACCESS read-write
       STATUS current
       DESCRIPTION
           "Indicates the CAR threshold of CoS 0. The four options are 12, 25, 50, and 100.
            Default: 100
            When traffic with CoS 0 reaches this threshold, the packets are discarded.
           "
       ::= { hwCarThresholdTable 1 }

   hwCarThresholdCos1 OBJECT-TYPE
       SYNTAX Integer32 (0..100)
       MAX-ACCESS read-write
       STATUS current
       DESCRIPTION
           "Indicates the CAR threshold of CoS 1. The four options are 12, 25, 50, and 100.
            Default: 100
            When traffic with CoS 1 reaches this threshold, the packets are discarded.
           "
       ::= { hwCarThresholdTable 2 }

   hwCarThresholdCos2 OBJECT-TYPE
       SYNTAX Integer32 (0..100)
       MAX-ACCESS read-write
       STATUS current
       DESCRIPTION
           "Indicates the CAR threshold of CoS 2. The four options are 12, 25, 50, and 100.
            Default: 100
            When traffic with CoS 2 reaches this threshold, the packets are discarded.
           "
       ::= { hwCarThresholdTable 3 }

   hwCarThresholdCos3 OBJECT-TYPE
       SYNTAX Integer32 (0..100)
       MAX-ACCESS read-write
       STATUS current
       DESCRIPTION
           "Indicates the CAR threshold of CoS 3. The four options are 12, 25, 50, and 100.
            Default: 100
            When traffic with CoS 3 reaches this threshold, the packets are discarded.
           "
       ::= { hwCarThresholdTable 4 }

   hwCarThresholdCos4 OBJECT-TYPE
       SYNTAX Integer32 (0..100)
       MAX-ACCESS read-write
       STATUS current
       DESCRIPTION
           "Indicates the CAR threshold of CoS 4. The four options are 12, 25, 50, and 100.
            Default: 100
            When traffic with CoS 4 reaches this threshold, the packets are discarded.
           "
       ::= { hwCarThresholdTable 5 }

   hwCarThresholdCos5 OBJECT-TYPE
       SYNTAX Integer32 (0..100)
       MAX-ACCESS read-write
       STATUS current
       DESCRIPTION
           "Indicates the CAR threshold of CoS 5. The four options are 12, 25, 50, and 100.
            Default: 100
            When traffic with CoS 5 reaches this threshold, the packets are discarded.
           "
       ::= { hwCarThresholdTable 6 }

   hwCarThresholdCos6 OBJECT-TYPE
       SYNTAX Integer32 (0..100)
       MAX-ACCESS read-write
       STATUS current
       DESCRIPTION
           "Indicates the CAR threshold of CoS 6. The four options are 12, 25, 50, and 100.
            Default: 100
            When traffic with CoS 6 reaches this threshold, the packets are discarded.
           "
       ::= { hwCarThresholdTable 7 }

   hwCarThresholdCos7 OBJECT-TYPE
       SYNTAX Integer32 (0..100)
       MAX-ACCESS read-write
       STATUS current
       DESCRIPTION
           "Indicates the CAR threshold of CoS 7. The four options are 12, 25, 50, and 100.
            Default: 100
            When traffic with CoS 7 reaches this threshold, the packets are discarded.
           "
       ::= { hwCarThresholdTable 8 }

   -- hwQueueGroupShapingTable
   hwQueueGroupShapingTable OBJECT-TYPE
       SYNTAX SEQUENCE OF HwQueueGroupShapingEntry
       MAX-ACCESS not-accessible
       STATUS current
       DESCRIPTION
           "Indicates a traffic shaping table, which is used to perform traffic shaping on certain queues on a port.

            The system currently supports traffic shaping on only queues 3 and 4 and at the same time PQ scheduling
            is applied invariably between them.

            The indexes of this table are ifIndex and hwQueueGroup.
            ifIndex indicates the index of F/S/P on which traffic shaping is performed.
            hwQueueGroup indicates a queue group on which traffic shaping is performed.

            This parameter has 32 bits and each bit represents a queue.
            To perform traffic shaping on a queue group, you just need to adjust bits to 1.
            The system currently supports up to eight queues. Traffic shaping, however, is performed only on queues 3 and 4.
            Hence, the index is variably 00000000 00000000 00000000 00011000 (in binary), that is, 0x18 (in hexadecimal notation).
           "
       ::= { hwExtIpdslam 15 }

   hwQueueGroupShapingEntry OBJECT-TYPE
       SYNTAX HwQueueGroupShapingEntry
       MAX-ACCESS not-accessible
       STATUS current
       DESCRIPTION
           "Indicates a traffic shaping table, which is used to perform traffic shaping on certain queues on a port.

            The system currently supports traffic shaping on only queues 3 and 4 and at the same time PQ scheduling
            is applied invariably between them.

            The indexes of this entry are ifIndex and hwQueueGroup.
            ifIndex indicates the index of F/S/P on which traffic shaping is performed.
            hwQueueGroup indicates a queue group on which traffic shaping is performed.

            This parameter has 32 bits and each bit represents a queue.
            To perform traffic shaping on a queue group, you just need to adjust bits to 1.
            The system currently supports up to eight queues. Traffic shaping, however, is performed only on queues 3 and 4.
            Hence, the index is variably 00000000 00000000 00000000 00011000 (in binary), that is, 0x18 (in hexadecimal notation).
           "
       INDEX { ifIndex, hwQueueGroup }
       ::= { hwQueueGroupShapingTable 1 }


   HwQueueGroupShapingEntry ::=
       SEQUENCE {
           hwQueueGroup
               Integer32,
           hwQueueGroupSchedMode
               INTEGER,
           hwQueueGroupShapingInboundTrafficIndex
               Integer32,
           hwQueueGroupShapingOutboundTrafficIndex
               Integer32,
           hwQueueGroupShapingTrafficRowStatus
               RowStatus
        }

   hwQueueGroup OBJECT-TYPE
       SYNTAX Integer32
       MAX-ACCESS not-accessible
       STATUS current
       DESCRIPTION
           "Indicates a queue group on which traffic shaping is performed.
            This parameter has 32 bits and each bit represents a queue.
            To perform traffic shaping on a queue group, you just need to adjust bits to 1.

            The system currently supports up to eight queues.
            Traffic shaping, however, is performed only on queues 3 and 4.
            Hence, the index is variably 00000000 00000000 00000000 00011000 (in binary), that is, 0x18 (in hexadecimal notation).
           "
       ::= { hwQueueGroupShapingEntry 1 }

   hwQueueGroupSchedMode OBJECT-TYPE
       SYNTAX INTEGER
           {
           strictPriority(1),
           wrr(2)
           }
       MAX-ACCESS read-write
       STATUS current
       DESCRIPTION
           "Indicates the queue scheduling mode.
            The system currently supports only PQ scheduling (enumerated value: strictPriority(1)).
            In the case of PQ scheduling, PQ takes out all packets from a queue with a high priority and transmits them.
            After such a transmission is completed, PQ performs the same on all packets in a queue with an intermediate priority,
            a queue with a normal priority, and a queue with a low priority one by one.
            In this way, packets in a queue with the highest priority precede packets in a queue with a less higher priority and
            therefore are processed preferentially, even in case of congestion.
            This ensures that packets for key services are processed first.
            Options:
            1. strictPriority(1) -indicates the strict priority queue scheduling mode
            2. wrr(2)            -indicates the weighted round robin mode
           "
       ::= { hwQueueGroupShapingEntry 2 }

   hwQueueGroupShapingInboundTrafficIndex OBJECT-TYPE
       SYNTAX Integer32
       MAX-ACCESS read-write
       STATUS current
       DESCRIPTION
           "Indicates the index of the IP traffic profile referenced by inbound packets.
           "
       ::= { hwQueueGroupShapingEntry 3 }

   hwQueueGroupShapingOutboundTrafficIndex OBJECT-TYPE
       SYNTAX Integer32
       MAX-ACCESS read-write
       STATUS current
       DESCRIPTION
           "Indicates the index of the IP traffic profile referenced by outbound packets.
           "
       ::= { hwQueueGroupShapingEntry 4 }

   hwQueueGroupShapingTrafficRowStatus OBJECT-TYPE
       SYNTAX RowStatus
       MAX-ACCESS read-create
       STATUS current
       DESCRIPTION
           "Indicates the row status.
            Options:
            1. active(1)
            2. createAndGo(4)
            3. destroy(6)
            To create traffic shaping, set this leaf to createAndGo(4) (currently, only ADP, ADQ, and VDT series boards support traffic shaping).
            To delete traffic shaping, set this leaf to destroy(6).
            When traffic shaping is queried, this leaf is displayed as active(1).
           "
       ::= { hwQueueGroupShapingEntry 5 }

-- hwEarlyDropMode
   hwEarlyDropMode OBJECT-TYPE
       SYNTAX INTEGER
           {
           priBase(1),
           colorBase(2),
           off(3),
           colorWred(4)
           }
       MAX-ACCESS read-write
       STATUS current
       DESCRIPTION
           "Sets the global early drop mode of the system.
            Options:
            1. priBase(1)   -indicating priority-based early drop
            2. colorBase(2) -indicating color-based early drop
            3. off(3)       -indicating disable the early drop function
            4. colorWred(4) -indicating color-wred early drop
            Default: colorBase(2)

            In the case of priority-based early drop, if packets with a specified priority reach the preset threshold (queue depth percentage)
            of their destination queue, subsequent packets of the same priority will be dropped instead of entering the queue.
            In the case of color-based early drop, you can configure and query early drop parameters of packets of different colors.
            In the case of off, the early drop function is disabled.
            In the case of color-wred early drop, packets with different colors will discard by WRED(weighted random early detection) strategy.
            For example, you can configure and query the early drop lower threshold, early drop upper threshold, and early drop possibility of
            green packets or yellow packets.
           "
       ::= { hwExtIpdslam 16 }

   hwPortVlanPolicingTable OBJECT-TYPE
       SYNTAX SEQUENCE OF HwPortVlanPolicingEntry
       MAX-ACCESS not-accessible
       STATUS current
       DESCRIPTION
           "Indicates the port+VLAN CAR table. It is used to add, query, modify, or delete the IP traffic profile used by the port+VLAN CAR.
            The indexes of this table are ifIndex and hwPortVlanPolicingVlanID. When querying or modifying the port+VLAN CAR, you must enter
            both the upstream and downstream IP traffic profiles (either the names or indexes of the upstream and downstream IP traffic profiles
            can be entered).
           "
       ::= { hwExtIpdslam 17 }

   hwPortVlanPolicingEntry OBJECT-TYPE
       SYNTAX HwPortVlanPolicingEntry
       MAX-ACCESS not-accessible
       STATUS current
       DESCRIPTION
           "Indicates the port+VLAN CAR table. It is used to add, query, modify, or delete the IP traffic profile used by the port+VLAN CAR.
            The indexes of this entry are ifIndex and hwPortVlanPolicingVlanID. When querying or modifying the port+VLAN CAR, you must enter
            both the upstream and downstream IP traffic profiles (either the names or indexes of the upstream and downstream IP traffic profiles
            can be entered).
           "
       INDEX { ifIndex, hwPortVlanPolicingVlanID }
       ::= { hwPortVlanPolicingTable 1 }

   HwPortVlanPolicingEntry ::=
       SEQUENCE {
           hwPortVlanPolicingVlanID
               Integer32,
           hwPortVlanPolicingInboundTrafficIndex
               Integer32,
           hwPortVlanPolicingOutboundTrafficIndex
               Integer32,
           hwPortVlanPolicingInboundTrafficName
               OCTET STRING,
           hwPortVlanPolicingOutboundTrafficName
               OCTET STRING,
           hwPortVlanPolicingTrafficRowStatus
               RowStatus
        }

   hwPortVlanPolicingVlanID OBJECT-TYPE
       SYNTAX Integer32
       MAX-ACCESS not-accessible
       STATUS current
       DESCRIPTION
           "It is one of the table indexes, indicating the VLAN of the CAR group.
            The value 0 indicates that VLAN does not need to be specified when configuring a CAR-port.
           "
       ::= { hwPortVlanPolicingEntry 1 }

-- 1.3.6.1.4.1.2011.5.14.3.17.1.2
   hwPortVlanPolicingInboundTrafficIndex OBJECT-TYPE
       SYNTAX Integer32
       MAX-ACCESS read-write
       STATUS current
       DESCRIPTION
           "Indicates the index of the IP traffic profile used by upstream packets.
            Range: 1-1024
            The IP traffic profile indicated by this index must exist in hwIpTrafficParamTable.
           "
       ::= { hwPortVlanPolicingEntry 2 }

   hwPortVlanPolicingOutboundTrafficIndex OBJECT-TYPE
       SYNTAX Integer32
       MAX-ACCESS read-write
       STATUS current
       DESCRIPTION
           "Indicates the index of the IP traffic profile used by downstream packets.
            Range: 1-1024
            The IP traffic profile indicated by this index must exist in hwIpTrafficParamTable.
           "
       ::= { hwPortVlanPolicingEntry 3 }

   hwPortVlanPolicingInboundTrafficName OBJECT-TYPE
       SYNTAX OCTET STRING (SIZE(0..32))
       MAX-ACCESS read-write
       STATUS current
       DESCRIPTION
           "Indicates the name of the IP address used by upstream packets.
            The IP traffic profile indicated by this name must exist in hwIpTrafficParamTable.
           "
       ::= { hwPortVlanPolicingEntry 4 }

   hwPortVlanPolicingOutboundTrafficName OBJECT-TYPE
       SYNTAX OCTET STRING (SIZE(0..32))
       MAX-ACCESS read-write
       STATUS current
       DESCRIPTION
           "Indicates the name of the IP address used by downstream packets.
            The IP traffic profile indicated by this name must exist in hwIpTrafficParamTable.
           "
       ::= { hwPortVlanPolicingEntry 5 }

   hwPortVlanPolicingTrafficRowStatus OBJECT-TYPE
       SYNTAX RowStatus
       MAX-ACCESS read-create
       STATUS current
       DESCRIPTION
           "Indicates the row status.
            Options:
            1. active(1)
            2. createAndGo(4)
            3. destroy(6)
            In creation, you must set this leaf to createAndGo(4) and must enter both the
            IP traffic profiles used by the upstream traffic and downstream traffic
            (either the names or indexes of the upstream and downstream IP traffic
            profiles can be entered); in deletion, set this leaf to destroy(6);
            in query, this leaf is displayed as active(1).
           "
       ::= { hwPortVlanPolicingEntry 6 }

   hwPbitsToPbitsMappingTable OBJECT-TYPE
       SYNTAX SEQUENCE OF HwPbitsToPbitsMappingEntry
       MAX-ACCESS not-accessible
       STATUS current
       DESCRIPTION
           "Indicates the service port priority mapping profile.
            It is used to modify and query the service port mapping relationships.
            The index of this table is hwPbitsToPbitsMappingIndex.
            Currently, the system supports only four service port priority mapping tables.
            The first priority mapping table has fixed mappings 0-0, 1-1,...7-7, that is,
            the priority is copied. The other three priority mapping tables can be customized
            by users; for example, mappings 0-0, 1-1, 2-2, 3-3, 4-3, 5-3, 6-3, and 7-3 can be
            configured.
            A service port priority mapping table can be queried or modified, but cannot be
            created or deleted. The service port priority mapping table with index 1 cannot be
            modified.
           "
       ::= { hwExtIpdslam 18 }

   hwPbitsToPbitsMappingEntry OBJECT-TYPE
       SYNTAX HwPbitsToPbitsMappingEntry
       MAX-ACCESS not-accessible
       STATUS current
       DESCRIPTION
           "Indicates the service port priority mapping profile.
            It is used to modify and query the service port mapping relationships.
            The index of this entry is hwPbitsToPbitsMappingIndex.
            Currently, the system supports only four service port priority mapping tables.
            The first priority mapping table has fixed mappings 0-0, 1-1,...7-7, that is,
            the priority is copied. The other three priority mapping tables can be customized
            by users; for example, mappings 0-0, 1-1, 2-2, 3-3, 4-3, 5-3, 6-3, and 7-3 can be
            configured.
            A service port priority mapping table can be queried or modified, but cannot be
            created or deleted. The service port priority mapping table with index 1 cannot be
            modified.
           "
       INDEX { hwPbitsToPbitsMappingIndex }
       ::= { hwPbitsToPbitsMappingTable 1 }

   HwPbitsToPbitsMappingEntry ::=
       SEQUENCE {
           hwPbitsToPbitsMappingIndex
               Integer32,
           hwPbitsToPbitsMapping0
               Integer32,
           hwPbitsToPbitsMapping1
               Integer32,
           hwPbitsToPbitsMapping2
               Integer32,
           hwPbitsToPbitsMapping3
               Integer32,
           hwPbitsToPbitsMapping4
               Integer32,
           hwPbitsToPbitsMapping5
               Integer32,
           hwPbitsToPbitsMapping6
               Integer32,
           hwPbitsToPbitsMapping7
               Integer32,
           hwPbitsToPbitsMappingRowStatus
               RowStatus
        }

   hwPbitsToPbitsMappingIndex OBJECT-TYPE
       SYNTAX Integer32 (1..16)
       MAX-ACCESS not-accessible
       STATUS current
       DESCRIPTION
           "Indicates the index of the service port priority mapping table.
            Range: 1-16
            Currently, the system supports four service port priority mapping tables.
           "
       ::= { hwPbitsToPbitsMappingEntry 1 }

   hwPbitsToPbitsMapping0 OBJECT-TYPE
       SYNTAX Integer32
       MAX-ACCESS read-write
       STATUS current
       DESCRIPTION
           "Indicates the output 802.1p priority of the mapping with priority 0.
            Values are as follows:
                     ----------------------------------------------------
                     |  31-24  |  23-16   |  15-8   |      7-0          |
                     ----------------------------------------------------
                     |  flag   |  yellow  |  green  | green-and-yellow  |
                     ----------------------------------------------------
            Bits 0-7: indicate the output priority of yellow and green packets with priority 0.
            Bits 8-15: indicate the output priority of green packets with priority 0.
            Bits 16-23: indicate the output priority of yellow packets with priority 0.
            Bits 24-31: indicate the color of packets whose priority is to be modified.

            0: indicates that the priorities of both yellow and green packets are modified (bits 0-7).
            1: indicates that the priorities of yellow and green packets are modified respectively
               (bits 8-15 for green packets and bits 16-23 for yellow packets).
            Other values are invalid.

            Default: 0
           "
       ::= { hwPbitsToPbitsMappingEntry 2 }

   hwPbitsToPbitsMapping1 OBJECT-TYPE
       SYNTAX Integer32
       MAX-ACCESS read-write
       STATUS current
       DESCRIPTION
           "Indicates the output 802.1p priority of the mapping with priority 1.
            Values are as follows:
                     ----------------------------------------------------
                     |  31-24  |  23-16   |  15-8   |      7-0          |
                     ----------------------------------------------------
                     |  flag   |  yellow  |  green  | green-and-yellow  |
                     ----------------------------------------------------
            Bits 0-7: indicate the output priority of yellow and green packets with priority 1.
            Bits 8-15: indicate the output priority of green packets with priority 1.
            Bits 16-23: indicate the output priority of yellow packets with priority 1.
            Bits 24-31: indicate the color of packets whose priority is to be modified.

            0: indicates that the priorities of both yellow and green packets are modified (bits 0-7).
            1: indicates that the priorities of yellow and green packets are modified respectively
               (bits 8-15 for green packets and bits 16-23 for yellow packets).
            Other values are invalid.

            Default: 1
           "
       ::= { hwPbitsToPbitsMappingEntry 3 }

   hwPbitsToPbitsMapping2 OBJECT-TYPE
       SYNTAX Integer32
       MAX-ACCESS read-write
       STATUS current
       DESCRIPTION
           "Indicates the output 802.1p priority of the mapping with priority 2.
            Values are as follows:
                     ----------------------------------------------------
                     |  31-24  |  23-16   |  15-8   |      7-0          |
                     ----------------------------------------------------
                     |  flag   |  yellow  |  green  | green-and-yellow  |
                     ----------------------------------------------------
            Bits 0-7: indicate the output priority of yellow and green packets with priority 2.
            Bits 8-15: indicate the output priority of green packets with priority 2.
            Bits 16-23: indicate the output priority of yellow packets with priority 2.
            Bits 24-31: indicate the color of packets whose priority is to be modified.

            0: indicates that the priorities of both yellow and green packets are modified (bits 0-7).
            1: indicates that the priorities of yellow and green packets are modified respectively
               (bits 8-15 for green packets and bits 16-23 for yellow packets).
            Other values are invalid.

            Default: 2
           "
       ::= { hwPbitsToPbitsMappingEntry 4 }

   hwPbitsToPbitsMapping3 OBJECT-TYPE
       SYNTAX Integer32
       MAX-ACCESS read-write
       STATUS current
       DESCRIPTION
           "Indicates the output 802.1p priority of the mapping with priority 3.
            Values are as follows:
                     ----------------------------------------------------
                     |  31-24  |  23-16   |  15-8   |      7-0          |
                     ----------------------------------------------------
                     |  flag   |  yellow  |  green  | green-and-yellow  |
                     ----------------------------------------------------
            Bits 0-7: indicate the output priority of yellow and green packets with priority 3.
            Bits 8-15: indicate the output priority of green packets with priority 3.
            Bits 16-23: indicate the output priority of yellow packets with priority 3.
            Bits 24-31: indicate the color of packets whose priority is to be modified.

            0: indicates that the priorities of both yellow and green packets are modified (bits 0-7).
            1: indicates that the priorities of yellow and green packets are modified respectively
               (bits 8-15 for green packets and bits 16-23 for yellow packets).
            Other values are invalid.

            Default: 3
           "
       ::= { hwPbitsToPbitsMappingEntry 5 }

   hwPbitsToPbitsMapping4 OBJECT-TYPE
       SYNTAX Integer32
       MAX-ACCESS read-write
       STATUS current
       DESCRIPTION
           "Indicates the output 802.1p priority of the mapping with priority 4.
            Values are as follows:
                     ----------------------------------------------------
                     |  31-24  |  23-16   |  15-8   |      7-0          |
                     ----------------------------------------------------
                     |  flag   |  yellow  |  green  | green-and-yellow  |
                     ----------------------------------------------------
            Bits 0-7: indicate the output priority of yellow and green packets with priority 4.
            Bits 8-15: indicate the output priority of green packets with priority 4.
            Bits 16-23: indicate the output priority of yellow packets with priority 4.
            Bits 24-31: indicate the color of packets whose priority is to be modified.

            0: indicates that the priorities of both yellow and green packets are modified (bits 0-7).
            1: indicates that the priorities of yellow and green packets are modified respectively
               (bits 8-15 for green packets and bits 16-23 for yellow packets).
            Other values are invalid.

            Default: 4
           "
       ::= { hwPbitsToPbitsMappingEntry 6 }

   hwPbitsToPbitsMapping5 OBJECT-TYPE
       SYNTAX Integer32
       MAX-ACCESS read-write
       STATUS current
       DESCRIPTION
           "Indicates the output 802.1p priority of the mapping with priority 5.
            Values are as follows:
                     ----------------------------------------------------
                     |  31-24  |  23-16   |  15-8   |      7-0          |
                     ----------------------------------------------------
                     |  flag   |  yellow  |  green  | green-and-yellow  |
                     ----------------------------------------------------
            Bits 0-7: indicate the output priority of yellow and green packets with priority 5.
            Bits 8-15: indicate the output priority of green packets with priority 5.
            Bits 16-23: indicate the output priority of yellow packets with priority 5.
            Bits 24-31: indicate the color of packets whose priority is to be modified.

            0: indicates that the priorities of both yellow and green packets are modified (bits 0-7).
            1: indicates that the priorities of yellow and green packets are modified respectively
               (bits 8-15 for green packets and bits 16-23 for yellow packets).
            Other values are invalid.

            Default: 5
           "
       ::= { hwPbitsToPbitsMappingEntry 7 }

   hwPbitsToPbitsMapping6 OBJECT-TYPE
       SYNTAX Integer32
       MAX-ACCESS read-write
       STATUS current
       DESCRIPTION
           "Indicates the output 802.1p priority of the mapping with priority 6.
            Values are as follows:
                     ----------------------------------------------------
                     |  31-24  |  23-16   |  15-8   |      7-0          |
                     ----------------------------------------------------
                     |  flag   |  yellow  |  green  | green-and-yellow  |
                     ----------------------------------------------------
            Bits 0-7: indicate the output priority of yellow and green packets with priority 6.
            Bits 8-15: indicate the output priority of green packets with priority 6.
            Bits 16-23: indicate the output priority of yellow packets with priority 6.
            Bits 24-31: indicate the color of packets whose priority is to be modified.

            0: indicates that the priorities of both yellow and green packets are modified (bits 0-7).
            1: indicates that the priorities of yellow and green packets are modified respectively
               (bits 8-15 for green packets and bits 16-23 for yellow packets).
            Other values are invalid.

            Default: 6
           "
       ::= { hwPbitsToPbitsMappingEntry 8 }

   hwPbitsToPbitsMapping7 OBJECT-TYPE
       SYNTAX Integer32
       MAX-ACCESS read-write
       STATUS current
       DESCRIPTION
           "Indicates the output 802.1p priority of the mapping with priority 7.
            Values are as follows:
                     ----------------------------------------------------
                     |  31-24  |  23-16   |  15-8   |      7-0          |
                     ----------------------------------------------------
                     |  flag   |  yellow  |  green  | green-and-yellow  |
                     ----------------------------------------------------
            Bits 0-7: indicate the output priority of yellow and green packets with priority 7.
            Bits 8-15: indicate the output priority of green packets with priority 7.
            Bits 16-23: indicate the output priority of yellow packets with priority 7.
            Bits 24-31: indicate the color of packets whose priority is to be modified.

            0: indicates that the priorities of both yellow and green packets are modified (bits 0-7).
            1: indicates that the priorities of yellow and green packets are modified respectively
               (bits 8-15 for green packets and bits 16-23 for yellow packets).
            Other values are invalid.

            Default: 7
           "
       ::= { hwPbitsToPbitsMappingEntry 9 }

   hwPbitsToPbitsMappingRowStatus OBJECT-TYPE
       SYNTAX RowStatus
       MAX-ACCESS read-create
       STATUS current
       DESCRIPTION
           "Indicates the row status.
            It supports only the query function. active(1) is displayed in the query result.
            Options:
            1. active(1) -indicates the query operation
           "
       ::= { hwPbitsToPbitsMappingEntry 10 }

-- hwFlowPriorityCarTagMode
   hwFlowPriorityCarTagMode OBJECT-TYPE
       SYNTAX INTEGER
           {
           externalFirst(1),
           internalFirst(2)
           }
       MAX-ACCESS read-write
       STATUS current
       DESCRIPTION
           "Used to modify or query the tag priority mode of the system.
            Options:
            1. externalFirst(1)     -Indicates the external tag First.
            2. internalFirst(2)     -Indicates the internal tag First.
            Default: internalFirst(2)
            This scalar leaf supports the modify and query operations only.
           "
       ::= { hwExtIpdslam 19 }

--hwBoardvlanrangestateTable
   hwBoardvlanrangestateTable OBJECT-TYPE
       SYNTAX SEQUENCE OF HwBoardvlanrangestateEntry
       MAX-ACCESS not-accessible
       STATUS current
       DESCRIPTION
           "Indicates VLAN RANGE flow feature.
            The indexes of this table are hwFrameIndex and hwSlotIndex."
       ::= { hwExtIpdslam 20 }

   hwBoardvlanrangestateEntry OBJECT-TYPE
       SYNTAX HwBoardvlanrangestateEntry
       MAX-ACCESS not-accessible
       STATUS current
       DESCRIPTION
           "Indicates VLAN RANGE flow feature.
            The indexes of this entry are hwFrameIndex and hwSlotIndex.
           "
       INDEX { hwFrameIndex,hwSlotIndex }
       ::= { hwBoardvlanrangestateTable 1 }

   HwBoardvlanrangestateEntry ::=
       SEQUENCE {
           hwBoardvlanrangestate
           INTEGER
        }

   hwBoardvlanrangestate OBJECT-TYPE
       SYNTAX INTEGER
           {
           disable(1),
           enable(2)
           }
       MAX-ACCESS read-write
       STATUS current
       DESCRIPTION
           "VLAN Range state.This object can be set to 'disable' or 'enable'
            Options:
            1. disable(1) -enable VLAN Range state.
            2. enable(2)  -disable VLAN Range state.
           "
       ::= { hwBoardvlanrangestateEntry 1 }

   hwXponCarportColorSensitive OBJECT-TYPE
       SYNTAX INTEGER
           {
           enable(1),
           disable(2)
           }
       MAX-ACCESS read-write
       STATUS current
       DESCRIPTION
           "Used to enable or disable the xPON color perception.
            Options:
            1. enable(1)  -the xPON color perception is enable
            2. disable(2) -the xPON color perception is disable
            Default: disable(2)
            This scalar leaf supports the modify and query operations only.
           "
       ::= { hwExtIpdslam 21 }

--hwQueueStatisticsstateTable
   hwQueueStatisticsstateTable OBJECT-TYPE
       SYNTAX SEQUENCE OF HwQueueStatisticsstateEntry
       MAX-ACCESS not-accessible
       STATUS current
       DESCRIPTION
           "Learns about the packet pass-through or drop status of a specified queue on a downstream port.
            After a packet is sent downstream, the statistics of pass-through packets are increased by 1 if the packet passes.
            Otherwise, the statistics of dropped packets are increased by 1.
            Also learns about the byte pass-through status of a specified queue on a downstream port.
            After a byte is sent downstream, the statistics of pass-through bytes are increased by 1 if the byte passes.
            The indexes of this table are hwQueueifIndex and hwQueueId.
           "
       ::= { hwExtIpdslam 22 }

   hwQueueStatisticsstateEntry OBJECT-TYPE
       SYNTAX HwQueueStatisticsstateEntry
       MAX-ACCESS not-accessible
       STATUS current
       DESCRIPTION
           "Learns about the packet pass-through or drop status of a specified queue on a downstream port.
            After a packet is sent downstream, the statistics of pass-through packets are increased by 1 if the packet passes.
            Otherwise, the statistics of dropped packets are increased by 1.
            Also learns about the byte pass-through status of a specified queue on a downstream port.
            After a byte is sent downstream, the statistics of pass-through bytes are increased by 1 if the byte passes.
            The indexes of this entry are hwQueueifIndex and hwQueueId.
           "
       INDEX { hwQueueifIndex, hwQueueId }
       ::= { hwQueueStatisticsstateTable 1 }

   HwQueueStatisticsstateEntry ::=
       SEQUENCE {
           hwQueueifIndex
               Unsigned32,
           hwQueueId
               Integer32,
           hwQueueStatisticsPassedNumber
               Counter64,
           hwQueueStatisticsDroppedNumber
               Counter64,
           hwQueueStatisticsReset
               Integer32,
           hwQueueStatisticsPassedBytes
               Counter64,
           hwQueueStatisticsDroppedUnRecognizedColorNumber
               Counter64,
           hwQueueStatisticsDroppedGreenNumber
               Counter64,
           hwQueueStatisticsDroppedYellowNumber
               Counter64,
           hwQueueStatisticsPassedGreenBytes
               Counter64,
           hwQueueStatisticsPassedGreenNumber
               Counter64,
           hwQueueStatisticsPassedYellowBytes
               Counter64,
           hwQueueStatisticsPassedYellowNumber
               Counter64
        }

   hwQueueifIndex OBJECT-TYPE
       SYNTAX Unsigned32 (0..4294967295)
       MAX-ACCESS read-only
       STATUS current
       DESCRIPTION
           "Indicates the index of F/S/P on which packets are queried or deleted.
            Its value must be a unique value greater than 0.
            Its algorithm and value are the same as ifindex which is defined in IF-MIB (RFC 2233).
           "
       ::= { hwQueueStatisticsstateEntry 1 }

   hwQueueId OBJECT-TYPE
       SYNTAX Integer32 (0..7)
       MAX-ACCESS read-only
       STATUS current
       DESCRIPTION
           "Indicates a specified queue ID.
            Range: 0-7
            The queues are real queues (errors are prompted when there are actually four queues on a board).
           "
       ::= { hwQueueStatisticsstateEntry 2 }

   hwQueueStatisticsPassedNumber OBJECT-TYPE
       SYNTAX Counter64
       MAX-ACCESS read-only
       STATUS current
       DESCRIPTION
           "Indicates the number of pass-through packets.
            After a packet is sent downstream, the statistics of pass-through packets are increased by 1 if the packet passes.
            '18446744073709551615' means invalid value.
           "
       ::= { hwQueueStatisticsstateEntry 3 }

   hwQueueStatisticsDroppedNumber OBJECT-TYPE
       SYNTAX Counter64
       MAX-ACCESS read-only
       STATUS current
       DESCRIPTION
           "Indicates the number of dropped packets.
            After a packet is sent downstream, the statistics of dropped packets are increased by 1 if the packet fails to pass.
            '18446744073709551615' means invalid value.
           "
       ::= { hwQueueStatisticsstateEntry 4 }

   hwQueueStatisticsReset OBJECT-TYPE
       SYNTAX Integer32
       MAX-ACCESS read-write
       STATUS current
       DESCRIPTION
           "Indicates whether to delete packets statistics.
            If hwQueueStatisticsReset is 1, it indicates that packets statistics of a specified queue will be deleted and counting will restart.
           "
       ::= { hwQueueStatisticsstateEntry 5 }

   hwQueueStatisticsPassedBytes OBJECT-TYPE
       SYNTAX Counter64
       MAX-ACCESS read-only
       STATUS current
       DESCRIPTION
           "Indicates the number of pass-through bytes.
            After a byte is sent downstream, the statistics of pass-through bytes are increased by 1 if the byte passes.
           '18446744073709551615' means invalid value."
       ::= { hwQueueStatisticsstateEntry 6 }

   hwQueueStatisticsDroppedUnRecognizedColorNumber OBJECT-TYPE
       SYNTAX Counter64
       MAX-ACCESS read-only
       STATUS current
       DESCRIPTION
           "Indicates the number of unRecognized dropped packets.
            After a packet is sent downstream, the statistics of dropped packets are increased by 1 if the packet fails to pass.
            '18446744073709551615' means invalid value.
           "
       ::= { hwQueueStatisticsstateEntry 7 }

   hwQueueStatisticsDroppedGreenNumber OBJECT-TYPE
       SYNTAX Counter64
       MAX-ACCESS read-only
       STATUS current
       DESCRIPTION
           "Indicates the number of green dropped packets.
            After a packet is sent downstream, the statistics of dropped packets are increased by 1 if the packet fails to pass.
            '18446744073709551615' means invalid value.
           "
       ::= { hwQueueStatisticsstateEntry 8 }

   hwQueueStatisticsDroppedYellowNumber OBJECT-TYPE
       SYNTAX Counter64
       MAX-ACCESS read-only
       STATUS current
       DESCRIPTION
           "Indicates the number of yellow dropped packets.
            After a packet is sent downstream, the statistics of dropped packets are increased by 1 if the packet fails to pass.
            '18446744073709551615' means invalid value.
           "
       ::= { hwQueueStatisticsstateEntry 9 }

   hwQueueStatisticsPassedGreenBytes OBJECT-TYPE
       SYNTAX Counter64
       MAX-ACCESS read-only
       STATUS current
       DESCRIPTION
           "Indicates the number of pass-through bytes of green packets.
            After a byte is sent downstream, the statistics of pass-through bytes are increased by 1 if the byte passes.
           '18446744073709551615' means invalid value.
           "
       ::= { hwQueueStatisticsstateEntry 10 }

   hwQueueStatisticsPassedGreenNumber OBJECT-TYPE
       SYNTAX Counter64
       MAX-ACCESS read-only
       STATUS current
       DESCRIPTION
           "Indicates the number of green pass-through packets.
            After a packet is sent downstream, the statistics of pass-through packets are increased by 1 if the packet passes.
            '18446744073709551615' means invalid value.
            "
       ::= { hwQueueStatisticsstateEntry 11 }

   hwQueueStatisticsPassedYellowBytes OBJECT-TYPE
       SYNTAX Counter64
       MAX-ACCESS read-only
       STATUS current
       DESCRIPTION
           "Indicates the number of pass-through bytes of yellow packets.
            After a byte is sent downstream, the statistics of pass-through bytes are increased by 1 if the byte passes.
           '18446744073709551615' means invalid value.
           "
       ::= { hwQueueStatisticsstateEntry 12 }

   hwQueueStatisticsPassedYellowNumber OBJECT-TYPE
       SYNTAX Counter64
       MAX-ACCESS read-only
       STATUS current
       DESCRIPTION
           "Indicates the number of yellow pass-through packets.
            After a packet is sent downstream, the statistics of pass-through packets are increased by 1 if the packet passes.
            '18446744073709551615' means invalid value.
            "
       ::= { hwQueueStatisticsstateEntry 13 }

--hwCarGroupTable
   hwCarGroupTable OBJECT-TYPE
       SYNTAX SEQUENCE OF HwCarGroupEntry
       MAX-ACCESS not-accessible
       STATUS current
       DESCRIPTION
           "Indicates the service port CAR group table. It is used to add, modify, query, or delete a service port CAR group.
            The index of this table is hwCarGroupIndex. When adding a service port CAR group, if you set hwCarGroupIndex to -1,
            the system will allocate an idle index. When adding a service port CAR group, you must enter both the upstream and
            downstream IP traffic profiles (either the names or indexes of the upstream and downstream IP traffic profiles can
            be entered).
           "
       ::= { hwExtIpdslam 23 }

   hwCarGroupEntry OBJECT-TYPE
       SYNTAX HwCarGroupEntry
       MAX-ACCESS not-accessible
       STATUS current
       DESCRIPTION
           "Indicates the service port CAR group table. It is used to add, modify, query, or delete a service port CAR group.
            The index of this entry is hwCarGroupIndex. When adding a service port CAR group, if you set hwCarGroupIndex to -1,
            the system will allocate an idle index. When adding a service port CAR group, you must enter both the upstream and
            downstream IP traffic profiles (either the names or indexes of the upstream and downstream IP traffic profiles can
            be entered).
           "
       INDEX { hwCarGroupIndex }
       ::= { hwCarGroupTable 1 }

   HwCarGroupEntry ::=
       SEQUENCE {
           hwCarGroupIndex
               Integer32,
           hwCarGroupInboundTrafficIndex
               Integer32,
           hwCarGroupOutboundTrafficIndex
               Integer32,
           hwCarGroupInboundTrafficName
             OCTET STRING,
           hwCarGroupOutboundTrafficName
             OCTET STRING,
           hwCarGroupRowStatus
               RowStatus
        }

   hwCarGroupIndex OBJECT-TYPE
       SYNTAX Integer32 (-1|1..32768)
       MAX-ACCESS read-only
       STATUS current
       DESCRIPTION
           "Table index, indicating the index of the service port CAR group.
            Range: 1-32768.
            When adding a service port CAR group, if you set hwCarGroupIndex to -1,
            the system will allocate an idle index.
           "
       ::= { hwCarGroupEntry 1 }

   hwCarGroupInboundTrafficIndex OBJECT-TYPE
       SYNTAX Integer32 (1..1024)
       MAX-ACCESS read-write
       STATUS current
       DESCRIPTION
           "Indicates the index of the IP traffic profile used by upstream packets.
            Range: 1-1024
            The IP traffic profile indicated by this index must exist in hwIpTrafficParamTable.
           "
       ::= { hwCarGroupEntry 2 }

   hwCarGroupOutboundTrafficIndex OBJECT-TYPE
       SYNTAX Integer32 (1..1024)
       MAX-ACCESS read-write
       STATUS current
       DESCRIPTION
           "Indicates the index of the IP traffic profile used by downstream packets.
            Range: 1-1024
            The IP traffic profile indicated by this index must exist in hwIpTrafficParamTable.
           "
       ::= { hwCarGroupEntry 3 }

   hwCarGroupInboundTrafficName OBJECT-TYPE
       SYNTAX OCTET STRING (SIZE(0..32))
       MAX-ACCESS read-write
       STATUS current
       DESCRIPTION
           "Indicates the name of the IP address used by upstream packets.
            The IP traffic profile indicated by this name must exist in hwIpTrafficParamTable.
           "
       ::= { hwCarGroupEntry 4 }

   hwCarGroupOutboundTrafficName OBJECT-TYPE
       SYNTAX OCTET STRING (SIZE(0..32))
       MAX-ACCESS read-write
       STATUS current
       DESCRIPTION
           "Indicates the name of the IP address used by downstream packets.
            The IP traffic profile indicated by this name must exist in hwIpTrafficParamTable.
           "
       ::= { hwCarGroupEntry 5 }

   hwCarGroupRowStatus OBJECT-TYPE
       SYNTAX RowStatus
       MAX-ACCESS read-create
       STATUS current
       DESCRIPTION
           "Indicates the row status.
            Options:
            1. active(1)      -indicates the query operation
            2. createAndGo(4) -indicates creating a CAR group
            3. destroy(6)     -indicates deleting a CAR group
            In creation, you must set this leaf to createAndGo(4)
            and must enter both the IP traffic profiles used by the
            upstream traffic and downstream traffic (either the names
            or indexes of the upstream and downstream IP traffic profiles
            can be entered); in deletion, set this leaf to destroy(6);
            in query, this leaf is displayed as active(1).
           "
       ::= { hwCarGroupEntry 6 }

--hwCarGroupSrvFlowTable
   hwCarGroupSrvFlowTable OBJECT-TYPE
       SYNTAX SEQUENCE OF HwCarGroupSrvFlowEntry
       MAX-ACCESS not-accessible
       STATUS current
       DESCRIPTION
           "Indicates the member table of a service port CAR group. It is used to add, query, or delete a member from
            a service port group. The indexes of this table are hwCarGroupMemberIndex and hwCarGroupSrvFlowIndex.
           "
       ::= { hwExtIpdslam 24 }

   hwCarGroupSrvFlowEntry OBJECT-TYPE
       SYNTAX HwCarGroupSrvFlowEntry
       MAX-ACCESS not-accessible
       STATUS current
       DESCRIPTION
           "Indicates the member table of a service port CAR group. It is used to add, query, or delete a member from
            a service port group. The indexes of this entry are hwCarGroupMemberIndex and hwCarGroupSrvFlowIndex.
           "
       INDEX { hwCarGroupMemberIndex , hwCarGroupSrvFlowIndex }
       ::= { hwCarGroupSrvFlowTable 1 }

   HwCarGroupSrvFlowEntry ::=
       SEQUENCE {
           hwCarGroupMemberIndex
               Integer32,
           hwCarGroupSrvFlowIndex
               Integer32,
           hwCarGroupSrvFlowOperType
               INTEGER,
		   hwCarGroupSrvFlowEndPointType
		       INTEGER
        }

   hwCarGroupMemberIndex OBJECT-TYPE
       SYNTAX Integer32 (1..32768)
       MAX-ACCESS read-only
       STATUS current
       DESCRIPTION
           "Indicates the index of the service port CAR group.
            Range: 1-32768
            The service port CAR group indicated by this index must exist in hwCarGroupTable.
           "
       ::= { hwCarGroupSrvFlowEntry 1 }

   hwCarGroupSrvFlowIndex OBJECT-TYPE
       SYNTAX Integer32
       MAX-ACCESS read-only
       STATUS current
       DESCRIPTION
           "Indicates the index of the service port CAR group.
            The service port CAR group indicated by this index must exist in hwExtSrvFlowTable.
            In the xPON access mode, the service ports to be added to the same CAR group must belong to the same PON port.
            In the case of type C or type D protection, the service ports to be added to the same CAR group must be on the same ONT.
            The service port of the vlan-range type cannot be added to a CAR group. For details, see hwExtSrvFlowTable.
           "
       ::= { hwCarGroupSrvFlowEntry 2 }

   hwCarGroupSrvFlowOperType  OBJECT-TYPE
       SYNTAX INTEGER
           {
           add(1),
           del(2)
           }
       MAX-ACCESS read-write
       STATUS current
       DESCRIPTION
           "Indicates the operation type.
            Options:
            1. add(1)        -Add a service port to a CAR group.
            2. del(2)        -Delete a service port to a CAR group.
            To add a service port to a CAR group,
            you must set this leaf to add(1); to delete a service port from a CAR group, you must set this leaf to del(2);
            to query a service port that exists in a CAR group, this leaf is displayed as add(1).
           "
       ::= { hwCarGroupSrvFlowEntry 3 }

   hwCarGroupSrvFlowEndPointType OBJECT-TYPE
       SYNTAX INTEGER
           {
           destination(1),
           source(2),
           invalid(-1)
           }
       MAX-ACCESS read-write
       STATUS current
       DESCRIPTION
           "
            Indicates the end-point type of a connection-oriented service flow.
            Options:
            1. destination(1)  -indicates the destination end-point of a connection-oriented service port.
            2. source(2)       -indicates the source end-point of a connection-oriented service port.
            3: invalid(-1)     -indicates the switch-oriented service port.
            When adding the source of a connection-oriented service port to a Car-Group, you must set the value of this leaf to source(2).
            When adding the destination of a connection-oriented service port to a Car-Group, you can set the value of this leaf to destination(1), or not bind this leaf.
            When adding a switched-oriented service port to a Car-Group, you can set the value of this leaf to any valid value, or not bind this leaf.
            When a service port in a Car-Group is queried, if this port is a switch-oriented service port, the value of this leaf is invalid(-1);
            if this port is the source of a connection-oriented service port, the value of this leaf is source (2);
            if this port is the destination of a connection-oriented service port, the value of this leaf is destination (1)."
       ::= { hwCarGroupSrvFlowEntry 4 }

   hwDscpToPbitsMappingTable OBJECT-TYPE
       SYNTAX SEQUENCE OF HwDscpToPbitsMappingEntry
       MAX-ACCESS not-accessible
       STATUS current
       DESCRIPTION
           "Indicates the DSCP-to-802.1p priority mapping profile.
            It is used to modify and query the DSCP-to-802.1p priority mapping relationships in the system.
            The index of this table is hwDscpToPbitsMappingIndex.
            By default, the system supports four DSCP-to-802.1p priority mapping profiles. These priority
            mapping tables can be queried or modified, but cannot be created or deleted. The DSCP-to-802.1p
            priority mapping table with index 1 cannot be modified.
           "
       ::= { hwExtIpdslam 26 }

   hwDscpToPbitsMappingEntry OBJECT-TYPE
       SYNTAX HwDscpToPbitsMappingEntry
       MAX-ACCESS not-accessible
       STATUS current
       DESCRIPTION
           "Indicates the DSCP-to-802.1p priority mapping profile.
            It is used to modify and query the DSCP-to-802.1p priority mapping relationships in the system.
            The index of this entry is hwDscpToPbitsMappingIndex.
            By default, the system supports four DSCP-to-802.1p priority mapping profiles. These priority
            mapping tables can be queried or modified, but cannot be created or deleted. The DSCP-to-802.1p
            priority mapping table with index 1 cannot be modified.
           "
       INDEX { hwDscpToPbitsMappingIndex }
       ::= { hwDscpToPbitsMappingTable 1 }

   HwDscpToPbitsMappingEntry ::=
       SEQUENCE {
           hwDscpToPbitsMappingIndex
               Integer32,
           hwDscpListMapToPriority0
               BITS,
           hwDscpListMapToPriority1
               BITS,
           hwDscpListMapToPriority2
               BITS,
           hwDscpListMapToPriority3
               BITS,
           hwDscpListMapToPriority4
               BITS,
           hwDscpListMapToPriority5
               BITS,
           hwDscpListMapToPriority6
               BITS,
           hwDscpListMapToPriority7
               BITS,
           hwDscpToPbitsMappingRowStatus
               RowStatus
        }

   hwDscpToPbitsMappingIndex OBJECT-TYPE
       SYNTAX Integer32 (1..50)
       MAX-ACCESS not-accessible
       STATUS current
       DESCRIPTION
           "Indicates the index of the DSCP-to-802.1p priority mapping table.
            Range: 1-50
            By default, the system supports four DSCP-to-802.1p priority mapping tables.
           "
       ::= { hwDscpToPbitsMappingEntry 1 }

   hwDscpListMapToPriority0 OBJECT-TYPE
       SYNTAX BITS
           {
           dscp0(0),
           dscp1(1),
           dscp2(2),
           dscp3(3),
           dscp4(4),
           dscp5(5),
           dscp6(6),
           dscp7(7),
           dscp8(8),
           dscp9(9),
           dscp10(10),
           dscp11(11),
           dscp12(12),
           dscp13(13),
           dscp14(14),
           dscp15(15),
           dscp16(16),
           dscp17(17),
           dscp18(18),
           dscp19(19),
           dscp20(20),
           dscp21(21),
           dscp22(22),
           dscp23(23),
           dscp24(24),
           dscp25(25),
           dscp26(26),
           dscp27(27),
           dscp28(28),
           dscp29(29),
           dscp30(30),
           dscp31(31),
           dscp32(32),
           dscp33(33),
           dscp34(34),
           dscp35(35),
           dscp36(36),
           dscp37(37),
           dscp38(38),
           dscp39(39),
           dscp40(40),
           dscp41(41),
           dscp42(42),
           dscp43(43),
           dscp44(44),
           dscp45(45),
           dscp46(46),
           dscp47(47),
           dscp48(48),
           dscp49(49),
           dscp50(50),
           dscp51(51),
           dscp52(52),
           dscp53(53),
           dscp54(54),
           dscp55(55),
           dscp56(56),
           dscp57(57),
           dscp58(58),
           dscp59(59),
           dscp60(60),
           dscp61(61),
           dscp62(62),
           dscp63(63)
           }
       MAX-ACCESS read-write
       STATUS current
       DESCRIPTION
           "Indicates the mask of the DSCP that is mapped to 802.1p priority 0. If a bit of the mask is set to 1,
            it indicates that the corresponding DSCP value is mapped to the 802.1p priority. The mask has 64 bits
            in total, corresponding to DSCP 0 to DSCP 63. Note that in a byte, the high bit indicates a small DSCP
            value. For example, if bit 7 is set to 1, this bit indicates DSCP 0.
            Range: 0-0xFFFFFFFFFFFFFFFF
            Default: 0xFF00000000000000
           "
       ::= { hwDscpToPbitsMappingEntry 2 }

   hwDscpListMapToPriority1 OBJECT-TYPE
       SYNTAX BITS
           {
           dscp0(0),
           dscp1(1),
           dscp2(2),
           dscp3(3),
           dscp4(4),
           dscp5(5),
           dscp6(6),
           dscp7(7),
           dscp8(8),
           dscp9(9),
           dscp10(10),
           dscp11(11),
           dscp12(12),
           dscp13(13),
           dscp14(14),
           dscp15(15),
           dscp16(16),
           dscp17(17),
           dscp18(18),
           dscp19(19),
           dscp20(20),
           dscp21(21),
           dscp22(22),
           dscp23(23),
           dscp24(24),
           dscp25(25),
           dscp26(26),
           dscp27(27),
           dscp28(28),
           dscp29(29),
           dscp30(30),
           dscp31(31),
           dscp32(32),
           dscp33(33),
           dscp34(34),
           dscp35(35),
           dscp36(36),
           dscp37(37),
           dscp38(38),
           dscp39(39),
           dscp40(40),
           dscp41(41),
           dscp42(42),
           dscp43(43),
           dscp44(44),
           dscp45(45),
           dscp46(46),
           dscp47(47),
           dscp48(48),
           dscp49(49),
           dscp50(50),
           dscp51(51),
           dscp52(52),
           dscp53(53),
           dscp54(54),
           dscp55(55),
           dscp56(56),
           dscp57(57),
           dscp58(58),
           dscp59(59),
           dscp60(60),
           dscp61(61),
           dscp62(62),
           dscp63(63)
           }
       MAX-ACCESS read-write
       STATUS current
       DESCRIPTION
           "Indicates the mask of the DSCP is mapped to 802.1p priority 1. If a bit of the mask
            is set to 1, it indicates that the corresponding DSCP value is mapped to the 802.1p
            priority. The mask has 64 bits in total, corresponding to DSCP 0 to DSCP 63. Note
            that in a byte, the high bit indicates a small DSCP value. For example, if bit 7
            is set to 1, this bit indicates DSCP 0.
            Range: 0-0xFFFFFFFFFFFFFFFF
            Default: 0x00FF000000000000
           "
       ::= { hwDscpToPbitsMappingEntry 3 }

   hwDscpListMapToPriority2 OBJECT-TYPE
       SYNTAX BITS
           {
           dscp0(0),
           dscp1(1),
           dscp2(2),
           dscp3(3),
           dscp4(4),
           dscp5(5),
           dscp6(6),
           dscp7(7),
           dscp8(8),
           dscp9(9),
           dscp10(10),
           dscp11(11),
           dscp12(12),
           dscp13(13),
           dscp14(14),
           dscp15(15),
           dscp16(16),
           dscp17(17),
           dscp18(18),
           dscp19(19),
           dscp20(20),
           dscp21(21),
           dscp22(22),
           dscp23(23),
           dscp24(24),
           dscp25(25),
           dscp26(26),
           dscp27(27),
           dscp28(28),
           dscp29(29),
           dscp30(30),
           dscp31(31),
           dscp32(32),
           dscp33(33),
           dscp34(34),
           dscp35(35),
           dscp36(36),
           dscp37(37),
           dscp38(38),
           dscp39(39),
           dscp40(40),
           dscp41(41),
           dscp42(42),
           dscp43(43),
           dscp44(44),
           dscp45(45),
           dscp46(46),
           dscp47(47),
           dscp48(48),
           dscp49(49),
           dscp50(50),
           dscp51(51),
           dscp52(52),
           dscp53(53),
           dscp54(54),
           dscp55(55),
           dscp56(56),
           dscp57(57),
           dscp58(58),
           dscp59(59),
           dscp60(60),
           dscp61(61),
           dscp62(62),
           dscp63(63)
           }
       MAX-ACCESS read-write
       STATUS current
       DESCRIPTION
           "Indicates the mask of the DSCP is mapped to 802.1p priority 2. If a bit of the
            mask is set to 1, it indicates that the corresponding DSCP value is mapped to
            the 802.1p priority. The mask has 64 bits in total, corresponding to DSCP 0
            to DSCP 63. Note that in a byte, the high bit indicates a small DSCP value.
            For example, if bit 7 is set to 1, this bit indicates DSCP 0.
            Range: 0-0xFFFFFFFFFFFFFFFF
            Default: 0x0000FF0000000000
           "
       ::= { hwDscpToPbitsMappingEntry 4 }

   hwDscpListMapToPriority3 OBJECT-TYPE
       SYNTAX BITS
           {
           dscp0(0),
           dscp1(1),
           dscp2(2),
           dscp3(3),
           dscp4(4),
           dscp5(5),
           dscp6(6),
           dscp7(7),
           dscp8(8),
           dscp9(9),
           dscp10(10),
           dscp11(11),
           dscp12(12),
           dscp13(13),
           dscp14(14),
           dscp15(15),
           dscp16(16),
           dscp17(17),
           dscp18(18),
           dscp19(19),
           dscp20(20),
           dscp21(21),
           dscp22(22),
           dscp23(23),
           dscp24(24),
           dscp25(25),
           dscp26(26),
           dscp27(27),
           dscp28(28),
           dscp29(29),
           dscp30(30),
           dscp31(31),
           dscp32(32),
           dscp33(33),
           dscp34(34),
           dscp35(35),
           dscp36(36),
           dscp37(37),
           dscp38(38),
           dscp39(39),
           dscp40(40),
           dscp41(41),
           dscp42(42),
           dscp43(43),
           dscp44(44),
           dscp45(45),
           dscp46(46),
           dscp47(47),
           dscp48(48),
           dscp49(49),
           dscp50(50),
           dscp51(51),
           dscp52(52),
           dscp53(53),
           dscp54(54),
           dscp55(55),
           dscp56(56),
           dscp57(57),
           dscp58(58),
           dscp59(59),
           dscp60(60),
           dscp61(61),
           dscp62(62),
           dscp63(63)
           }
       MAX-ACCESS read-write
       STATUS current
       DESCRIPTION
           "Indicates the mask of the DSCP is mapped to 802.1p priority 3. If a bit of the mask is set
            to 1, it indicates that the corresponding DSCP value is mapped to the 802.1p priority.
            The mask has 64 bits in total, corresponding to DSCP 0 to DSCP 63. Note that in a byte,
            the high bit indicates a small DSCP value. For example, if bit 7 is set to 1, this bit
            indicates DSCP 0.
            Range: 0-0xFFFFFFFFFFFFFFFF
            Default: 0x000000FF00000000
           "
       ::= { hwDscpToPbitsMappingEntry 5 }

   hwDscpListMapToPriority4 OBJECT-TYPE
       SYNTAX BITS
           {
           dscp0(0),
           dscp1(1),
           dscp2(2),
           dscp3(3),
           dscp4(4),
           dscp5(5),
           dscp6(6),
           dscp7(7),
           dscp8(8),
           dscp9(9),
           dscp10(10),
           dscp11(11),
           dscp12(12),
           dscp13(13),
           dscp14(14),
           dscp15(15),
           dscp16(16),
           dscp17(17),
           dscp18(18),
           dscp19(19),
           dscp20(20),
           dscp21(21),
           dscp22(22),
           dscp23(23),
           dscp24(24),
           dscp25(25),
           dscp26(26),
           dscp27(27),
           dscp28(28),
           dscp29(29),
           dscp30(30),
           dscp31(31),
           dscp32(32),
           dscp33(33),
           dscp34(34),
           dscp35(35),
           dscp36(36),
           dscp37(37),
           dscp38(38),
           dscp39(39),
           dscp40(40),
           dscp41(41),
           dscp42(42),
           dscp43(43),
           dscp44(44),
           dscp45(45),
           dscp46(46),
           dscp47(47),
           dscp48(48),
           dscp49(49),
           dscp50(50),
           dscp51(51),
           dscp52(52),
           dscp53(53),
           dscp54(54),
           dscp55(55),
           dscp56(56),
           dscp57(57),
           dscp58(58),
           dscp59(59),
           dscp60(60),
           dscp61(61),
           dscp62(62),
           dscp63(63)
           }
       MAX-ACCESS read-write
       STATUS current
       DESCRIPTION
           "Indicates the mask of the DSCP is mapped to 802.1p priority 4. If a bit of the mask
            is set to 1, it indicates that the corresponding DSCP value is mapped to the 802.1p
            priority. The mask has 64 bits in total, corresponding to DSCP 0 to DSCP 63. Note
            that in a byte, the high bit indicates a small DSCP value. For example, if bit 7 is
            set to 1, this bit indicates DSCP 0.
            Range: 0-0xFFFFFFFFFFFFFFFF
            Default: 0x00000000FF000000
           "
       ::= { hwDscpToPbitsMappingEntry 6 }

   hwDscpListMapToPriority5 OBJECT-TYPE
       SYNTAX BITS
           {
           dscp0(0),
           dscp1(1),
           dscp2(2),
           dscp3(3),
           dscp4(4),
           dscp5(5),
           dscp6(6),
           dscp7(7),
           dscp8(8),
           dscp9(9),
           dscp10(10),
           dscp11(11),
           dscp12(12),
           dscp13(13),
           dscp14(14),
           dscp15(15),
           dscp16(16),
           dscp17(17),
           dscp18(18),
           dscp19(19),
           dscp20(20),
           dscp21(21),
           dscp22(22),
           dscp23(23),
           dscp24(24),
           dscp25(25),
           dscp26(26),
           dscp27(27),
           dscp28(28),
           dscp29(29),
           dscp30(30),
           dscp31(31),
           dscp32(32),
           dscp33(33),
           dscp34(34),
           dscp35(35),
           dscp36(36),
           dscp37(37),
           dscp38(38),
           dscp39(39),
           dscp40(40),
           dscp41(41),
           dscp42(42),
           dscp43(43),
           dscp44(44),
           dscp45(45),
           dscp46(46),
           dscp47(47),
           dscp48(48),
           dscp49(49),
           dscp50(50),
           dscp51(51),
           dscp52(52),
           dscp53(53),
           dscp54(54),
           dscp55(55),
           dscp56(56),
           dscp57(57),
           dscp58(58),
           dscp59(59),
           dscp60(60),
           dscp61(61),
           dscp62(62),
           dscp63(63)
           }
       MAX-ACCESS read-write
       STATUS current
       DESCRIPTION
           "Indicates the mask of the DSCP is mapped to 802.1p priority 5. If a bit of the mask
            is set to 1, it indicates that the corresponding DSCP value is mapped to the 802.1p
            priority. The mask has 64 bits in total, corresponding to DSCP 0 to DSCP 63. Note
            that in a byte, the high bit indicates a small DSCP value. For example, if bit 7
            is set to 1, this bit indicates DSCP 0.
            Range: 0-0xFFFFFFFFFFFFFFFF
            Default: 0x0000000000FF0000
           "
       ::= { hwDscpToPbitsMappingEntry 7 }

   hwDscpListMapToPriority6 OBJECT-TYPE
       SYNTAX BITS
           {
           dscp0(0),
           dscp1(1),
           dscp2(2),
           dscp3(3),
           dscp4(4),
           dscp5(5),
           dscp6(6),
           dscp7(7),
           dscp8(8),
           dscp9(9),
           dscp10(10),
           dscp11(11),
           dscp12(12),
           dscp13(13),
           dscp14(14),
           dscp15(15),
           dscp16(16),
           dscp17(17),
           dscp18(18),
           dscp19(19),
           dscp20(20),
           dscp21(21),
           dscp22(22),
           dscp23(23),
           dscp24(24),
           dscp25(25),
           dscp26(26),
           dscp27(27),
           dscp28(28),
           dscp29(29),
           dscp30(30),
           dscp31(31),
           dscp32(32),
           dscp33(33),
           dscp34(34),
           dscp35(35),
           dscp36(36),
           dscp37(37),
           dscp38(38),
           dscp39(39),
           dscp40(40),
           dscp41(41),
           dscp42(42),
           dscp43(43),
           dscp44(44),
           dscp45(45),
           dscp46(46),
           dscp47(47),
           dscp48(48),
           dscp49(49),
           dscp50(50),
           dscp51(51),
           dscp52(52),
           dscp53(53),
           dscp54(54),
           dscp55(55),
           dscp56(56),
           dscp57(57),
           dscp58(58),
           dscp59(59),
           dscp60(60),
           dscp61(61),
           dscp62(62),
           dscp63(63)
           }
       MAX-ACCESS read-write
       STATUS current
       DESCRIPTION
           "Indicates the mask of the DSCP is mapped to 802.1p priority 6. If a bit of the mask is
            set to 1, it indicates that the corresponding DSCP value is mapped to the 802.1p priority.
            The mask has 64 bits in total, corresponding to DSCP 0 to DSCP 63. Note that in a byte,
            the high bit indicates a small DSCP value. For example, if bit 7 is set to 1, this bit
            indicates DSCP 0.
            Range: 0-0xFFFFFFFFFFFFFFFF
            Default: 0x000000000000FF00
           "
       ::= { hwDscpToPbitsMappingEntry 8 }

   hwDscpListMapToPriority7 OBJECT-TYPE
       SYNTAX BITS
           {
           dscp0(0),
           dscp1(1),
           dscp2(2),
           dscp3(3),
           dscp4(4),
           dscp5(5),
           dscp6(6),
           dscp7(7),
           dscp8(8),
           dscp9(9),
           dscp10(10),
           dscp11(11),
           dscp12(12),
           dscp13(13),
           dscp14(14),
           dscp15(15),
           dscp16(16),
           dscp17(17),
           dscp18(18),
           dscp19(19),
           dscp20(20),
           dscp21(21),
           dscp22(22),
           dscp23(23),
           dscp24(24),
           dscp25(25),
           dscp26(26),
           dscp27(27),
           dscp28(28),
           dscp29(29),
           dscp30(30),
           dscp31(31),
           dscp32(32),
           dscp33(33),
           dscp34(34),
           dscp35(35),
           dscp36(36),
           dscp37(37),
           dscp38(38),
           dscp39(39),
           dscp40(40),
           dscp41(41),
           dscp42(42),
           dscp43(43),
           dscp44(44),
           dscp45(45),
           dscp46(46),
           dscp47(47),
           dscp48(48),
           dscp49(49),
           dscp50(50),
           dscp51(51),
           dscp52(52),
           dscp53(53),
           dscp54(54),
           dscp55(55),
           dscp56(56),
           dscp57(57),
           dscp58(58),
           dscp59(59),
           dscp60(60),
           dscp61(61),
           dscp62(62),
           dscp63(63)
           }
       MAX-ACCESS read-write
       STATUS current
       DESCRIPTION
           "Indicates the mask of the DSCP is mapped to 802.1p priority 7. If a bit of the mask is
            set to 1, it indicates that the corresponding DSCP value is mapped to the 802.1p priority.
            The mask has 64 bits in total, corresponding to DSCP 0 to DSCP 63. Note that in a byte,
            the high bit indicates a small DSCP value. For example, if bit 7 is set to 1, this bit
            indicates DSCP 0.
            Range: 0-0xFFFFFFFFFFFFFFFF
            Default: 0x00000000000000FF
           "
       ::= { hwDscpToPbitsMappingEntry 9 }

   hwDscpToPbitsMappingRowStatus OBJECT-TYPE
       SYNTAX RowStatus
       MAX-ACCESS read-create
       STATUS current
       DESCRIPTION
           "Indicates the row status.
            It supports only the query function. active(1) is displayed in the query result.
            Option:
            1. active(1) -indicates the query operation
           "
       ::= { hwDscpToPbitsMappingEntry 10 }

-- hwWREDTable
   hwWREDTable OBJECT-TYPE
       SYNTAX SEQUENCE OF HwWREDEntry
       MAX-ACCESS not-accessible
       STATUS current
       DESCRIPTION
           "Configures or queries a WRED profile.
            The index of this table is hwWREDIndex.
            During the creation of a WRED profile, if hwWREDIndex is specified to -1,
            it indicates that the index of the WRED profile is assigned by the system.
           "
           ::= { hwExtIpdslam 27 }

   hwWREDEntry OBJECT-TYPE
       SYNTAX HwWREDEntry
       MAX-ACCESS not-accessible
       STATUS current
       DESCRIPTION
           "Configures or queries a WRED profile.
            The index of this entry is hwWREDIndex.
            During the creation of a WRED profile, if hwWREDIndex is specified to -1,
            it indicates that the index of the WRED profile is assigned by the system.
           "
       INDEX { hwWREDIndex }
       ::= { hwWREDTable 1 }

   HwWREDEntry ::=
       SEQUENCE
        {
         hwWREDIndex
           Integer32,
         hwWREDGreenLowLimit
           Integer32,
         hwWREDGreenHighLimit
           Integer32,
         hwWREDGreenProbability
           Integer32,
         hwWREDYellowLowLimit
           Integer32,
         hwWREDYellowHighLimit
           Integer32,
         hwWREDYellowProbability
           Integer32,
         hwWREDRowStatus
             RowStatus
        }

   hwWREDIndex OBJECT-TYPE
       SYNTAX Integer32
       MAX-ACCESS read-only
       STATUS current
       DESCRIPTION
           "Indicates the index of a WRED profile that is operated. It uniquely identifies the WRED profile.
            You can fill in -1 as the value of hwWREDIndex and issue the setting.
            Then, the system automatically allocates an idle index and returns the index to the NMS.
           "
       ::= { hwWREDEntry 1 }

   hwWREDGreenLowLimit OBJECT-TYPE
       SYNTAX Integer32 (-1|0..100)
       MAX-ACCESS read-write
       STATUS current
       DESCRIPTION
           "Indicates the early drop low limit threshold of green packets.
            Range: -1, 0-100.
            -1 is the invalid value.
            hwWREDGreenLowLimit, hwWREDGreenHighLimit, and hwWREDGreenProbability must be specified at the same time.
           "
       ::= { hwWREDEntry 2 }

   hwWREDGreenHighLimit OBJECT-TYPE
       SYNTAX Integer32 (-1|0..100)
       MAX-ACCESS read-write
       STATUS current
       DESCRIPTION
           "Indicates the early drop high limit threshold of green packets.
            Range: -1, 0-100.
            -1 is the invalid value.
            hwWREDGreenLowLimit, hwWREDGreenHighLimit, and hwWREDGreenProbability must be specified at the same time.
           "
       ::= { hwWREDEntry 3 }

   hwWREDGreenProbability OBJECT-TYPE
       SYNTAX Integer32 (-1|0..100)
       MAX-ACCESS read-write
       STATUS current
       DESCRIPTION
           "Indicates the early drop probability of green packets.
            Range: -1, 0-100.
            -1 is the invalid value.
            hwWREDGreenLowLimit, hwWREDGreenHighLimit, and hwWREDGreenProbability must be specified at the same time.
           "
       ::= { hwWREDEntry 4 }

   hwWREDYellowLowLimit OBJECT-TYPE
       SYNTAX Integer32 (-1|0..100)
       MAX-ACCESS read-write
       STATUS current
       DESCRIPTION
           "Indicates the early drop low limit threshold of yellow packets.
            Range: -1, 0-100.
            -1 is the invalid value.
            hwWREDYellowLowLimit, hwWREDYellowHighLimit, and hwWREDYellowProbability must be specified at the same time.
           "
       ::= { hwWREDEntry 5 }

   hwWREDYellowHighLimit OBJECT-TYPE
       SYNTAX Integer32 (-1|0..100)
       MAX-ACCESS read-write
       STATUS current
       DESCRIPTION
           "Indicates the early drop high limit threshold of yellow packets.
            Range: -1, 0-100.
            -1 is the invalid value.
            hwWREDYellowLowLimit, hwWREDYellowHighLimit, and hwWREDYellowProbability must be specified at the same time.
           "
       ::= { hwWREDEntry 6 }

   hwWREDYellowProbability OBJECT-TYPE
       SYNTAX Integer32 (-1|0..100)
       MAX-ACCESS read-write
       STATUS current
       DESCRIPTION
           "Indicates the early drop probability of yellow packets.
            Range: -1, 0-100.
            -1 is the invalid value.
            hwWREDYellowLowLimit, hwWREDYellowHighLimit, and hwWREDYellowProbability must be specified at the same time.
           "
       ::= { hwWREDEntry 7 }

   hwWREDRowStatus OBJECT-TYPE
       SYNTAX RowStatus
       MAX-ACCESS read-create
       STATUS current
       DESCRIPTION
           "Indicates the row status.
            Options:
            1. active(1)
            2. createAndGo(4)
            3. destroy(6)

            To create a WRED profile, set this leaf to createAndGo(4) and specify the three leaves of hwWREDGreenLowLimit,
            hwWREDGreenHighLimit, and hwWREDGreenProbability concurrently and the other three leaves of hwWREDYellowLowLimit,
            hwWREDYellowHighLimit, and hwWREDYellowProbability, too.

            To delete a WRED profile, set this leaf to destroy(6).

            When a WRED profile is queried, this leaf is displayed as active(1).
           "
       ::= { hwWREDEntry 8 }

   hwQueueWREDTable OBJECT-TYPE
       SYNTAX SEQUENCE OF HwQueueWREDEntry
       MAX-ACCESS not-accessible
       STATUS current
       DESCRIPTION
           "Describes the binding between queues and a WRED profile.
            The index of hwQueueWREDTable is hwQueueWREDId. hwQueueWREDId indicates a specified queue ID.
            Range: 1-8
            Before binding/unbinding queues to/from a WRED profile,
            make sure that the WRED profile be already created in hwWREDTable and hwEarlyDropMode be colorBase(2).
            The index of this table is hwQueueWREDIndex.
           "
       ::= { hwExtIpdslam 28 }

   hwQueueWREDEntry OBJECT-TYPE
       SYNTAX HwQueueWREDEntry
       MAX-ACCESS not-accessible
       STATUS current
       DESCRIPTION
           "Describes the binding between queues and a WRED profile.
            The index of hwQueueWREDTable is hwQueueWREDId. hwQueueWREDId indicates a specified queue ID.
            Range: 1-8
            Before binding/unbinding queues to/from a WRED profile,
            make sure that the WRED profile be already created in hwWREDTable and hwEarlyDropMode be colorBase(2).
            The index of this entry is hwQueueWREDIndex.
           "
       INDEX { hwQueueWREDId }
       ::= { hwQueueWREDTable 1 }

   HwQueueWREDEntry ::=
       SEQUENCE
       {
        hwQueueWREDId
          Integer32,
        hwQueueWREDIndex
          Integer32
        }

   hwQueueWREDId OBJECT-TYPE
       SYNTAX Integer32 (1..8)
       MAX-ACCESS read-only
       STATUS current
       DESCRIPTION
           "Indicates a specified queue ID.
            Range: 1-8
            Each queue can be separately bound to a WRED profile but you are allowed to bind one queue to the WRED profile at a time.
           "
       ::= { hwQueueWREDEntry 1 }

   hwQueueWREDIndex OBJECT-TYPE
       SYNTAX Integer32
       MAX-ACCESS read-write
       STATUS current
       DESCRIPTION
           "Indicates the index of a WRED profile to be bound.
            Make sure that the WRED profile be already created in hwWREDTable and the WRED profile information be complete
            (that is, including the early drop information).
            At the same time, to bind queues to a WRED profile, make sure that hwEarlyDropMode be colorBase(2).

            If hwQueueWREDIndex is specified to -1, it indicates that the binding between queues and a WRED profile is removed.
           "
       ::= { hwQueueWREDEntry 2 }

--hwIPPrecToPbitsMappingTable
   hwIPPrecToPbitsMappingTable OBJECT-TYPE
       SYNTAX SEQUENCE OF HwIPPrecToPbitsMappingEntry
       MAX-ACCESS not-accessible
       STATUS current
       DESCRIPTION
           "Indicates the IP precedence to pbits mapping table. This table is used to configure or query the mapping
            between the IP precedence and pbits. It only supports the modify operation but not the create or delete
            operation. The fist record of this table is the default record of the system and cannot be modified.
            The index of this table is hwIPPrecToPbitsMappingIndex.
           "
       ::= { hwExtIpdslam 29 }

   hwIPPrecToPbitsMappingEntry OBJECT-TYPE
       SYNTAX HwIPPrecToPbitsMappingEntry
       MAX-ACCESS not-accessible
       STATUS current
       DESCRIPTION
           "Indicates the IP precedence to pbits mapping table. This table is used to configure or query the mapping
            between the IP precedence and pbits. It only supports the modify operation but not the create or delete
            operation. The fist record of this table is the default record of the system and cannot be modified.
            The index of this entry is hwIPPrecToPbitsMappingIndex.
           "
       INDEX { hwIPPrecToPbitsMappingIndex }
       ::= { hwIPPrecToPbitsMappingTable 1 }

   HwIPPrecToPbitsMappingEntry ::=
       SEQUENCE {
           hwIPPrecToPbitsMappingIndex
               Integer32,
           hwIPPrecToPbitsMapping0
               Integer32,
           hwIPPrecToPbitsMapping1
               Integer32,
           hwIPPrecToPbitsMapping2
               Integer32,
           hwIPPrecToPbitsMapping3
               Integer32,
           hwIPPrecToPbitsMapping4
               Integer32,
           hwIPPrecToPbitsMapping5
               Integer32,
           hwIPPrecToPbitsMapping6
               Integer32,
           hwIPPrecToPbitsMapping7
               Integer32,
           hwIPPrecToPbitsMappingRowStatus
               RowStatus
        }

   hwIPPrecToPbitsMappingIndex OBJECT-TYPE
       SYNTAX Integer32 (1..4)
       MAX-ACCESS not-accessible
       STATUS current
       DESCRIPTION
           "Indicates the index of the priority table used to translate packet's priority.
            Range: 1-4
            The system supports four user-ToS priority mapping tables.
           "
       ::= { hwIPPrecToPbitsMappingEntry 1 }

   hwIPPrecToPbitsMapping0 OBJECT-TYPE
       SYNTAX Integer32
       MAX-ACCESS read-write
       STATUS current
       DESCRIPTION
           "Indicates the output 802.1p priority of the mapping with IP preference 0.
            Values are as follows:
                     ----------------------------------------------------
                     |  31-24  |  23-16   |  15-8   |      7-0          |
                     ----------------------------------------------------
                     |  flag   |  yellow  |  green  | green-and-yellow  |
                     ----------------------------------------------------
            Bits 0-7: indicate the output priority of yellow and green packets with IP preference 0.
            Bits 8-15: indicate the output priority of green packets with IP preference 0.
            Bits 16-23: indicate the output priority of yellow packets with IP preference 0.
            Bits 24-31: indicate the color of packets whose priority is to be modified.

            0: indicates that the priorities of both yellow and green packets are modified (bits 0-7).
            1: indicates that the priorities of yellow and green packets are modified respectively
               (bits 8-15 for green packets and bits 16-23 for yellow packets).
            Other values are invalid.

            Default: 0
           "
       ::= { hwIPPrecToPbitsMappingEntry 2 }

   hwIPPrecToPbitsMapping1 OBJECT-TYPE
       SYNTAX Integer32
       MAX-ACCESS read-write
       STATUS current
       DESCRIPTION
           "Indicates the output 802.1p priority of the mapping with IP preference 1.
            Values are as follows:
                     ----------------------------------------------------
                     |  31-24  |  23-16   |  15-8   |      7-0          |
                     ----------------------------------------------------
                     |  flag   |  yellow  |  green  | green-and-yellow  |
                     ----------------------------------------------------
            Bits 0-7: indicate the output priority of yellow and green packets with IP preference 1.
            Bits 8-15: indicate the output priority of green packets with IP preference 1.
            Bits 16-23: indicate the output priority of yellow packets with IP preference 1.
            Bits 24-31: indicate the color of packets whose priority is to be modified.

            0: indicates that the priorities of both yellow and green packets are modified (bits 0-7).
            1: indicates that the priorities of yellow and green packets are modified respectively
               (bits 8-15 for green packets and bits 16-23 for yellow packets).
            Other values are invalid.

            Default: 1
           "
       ::= { hwIPPrecToPbitsMappingEntry 3 }

   hwIPPrecToPbitsMapping2 OBJECT-TYPE
       SYNTAX Integer32
       MAX-ACCESS read-write
       STATUS current
       DESCRIPTION
           "Indicates the output 802.1p priority of the mapping with IP preference 2.
            Values are as follows:
                     ----------------------------------------------------
                     |  31-24  |  23-16   |  15-8   |      7-0          |
                     ----------------------------------------------------
                     |  flag   |  yellow  |  green  | green-and-yellow  |
                     ----------------------------------------------------
            Bits 0-7: indicate the output priority of yellow and green packets with IP preference 2.
            Bits 8-15: indicate the output priority of green packets with IP preference 2.
            Bits 16-23: indicate the output priority of yellow packets with IP preference 2.
            Bits 24-31: indicate the color of packets whose priority is to be modified.

            0: indicates that the priorities of both yellow and green packets are modified (bits 0-7).
            1: indicates that the priorities of yellow and green packets are modified respectively
               (bits 8-15 for green packets and bits 16-23 for yellow packets).
            Other values are invalid.

            Default: 2
           "
       ::= { hwIPPrecToPbitsMappingEntry 4 }

   hwIPPrecToPbitsMapping3 OBJECT-TYPE
       SYNTAX Integer32
       MAX-ACCESS read-write
       STATUS current
       DESCRIPTION
           "Indicates the output 802.1p priority of the mapping with IP preference 0.
            Values are as follows:
                     ----------------------------------------------------
                     |  31-24  |  23-16   |  15-8   |      7-0          |
                     ----------------------------------------------------
                     |  flag   |  yellow  |  green  | green-and-yellow  |
                     ----------------------------------------------------
            Bits 0-7: indicate the output priority of yellow and green packets with IP preference 3.
            Bits 8-15: indicate the output priority of green packets with IP preference 3.
            Bits 16-23: indicate the output priority of yellow packets with IP preference 3.
            Bits 24-31: indicate the color of packets whose priority is to be modified.

            0: indicates that the priorities of both yellow and green packets are modified (bits 0-7).
            1: indicates that the priorities of yellow and green packets are modified respectively
               (bits 8-15 for green packets and bits 16-23 for yellow packets).
            Other values are invalid.

            Default: 3
           "
       ::= { hwIPPrecToPbitsMappingEntry 5 }

   hwIPPrecToPbitsMapping4 OBJECT-TYPE
       SYNTAX Integer32
       MAX-ACCESS read-write
       STATUS current
       DESCRIPTION
           "Indicates the output 802.1p priority of the mapping with IP preference 4.
            Values are as follows:
                     ----------------------------------------------------
                     |  31-24  |  23-16   |  15-8   |      7-0          |
                     ----------------------------------------------------
                     |  flag   |  yellow  |  green  | green-and-yellow  |
                     ----------------------------------------------------
            Bits 0-7: indicate the output priority of yellow and green packets with IP preference 4.
            Bits 8-15: indicate the output priority of green packets with IP preference 4.
            Bits 16-23: indicate the output priority of yellow packets with IP preference 4.
            Bits 24-31: indicate the color of packets whose priority is to be modified.

            0: indicates that the priorities of both yellow and green packets are modified (bits 0-7).
            1: indicates that the priorities of yellow and green packets are modified respectively
               (bits 8-15 for green packets and bits 16-23 for yellow packets).
            Other values are invalid.

            Default: 4
           "
       ::= { hwIPPrecToPbitsMappingEntry 6 }

   hwIPPrecToPbitsMapping5 OBJECT-TYPE
       SYNTAX Integer32
       MAX-ACCESS read-write
       STATUS current
       DESCRIPTION
           "Indicates the output 802.1p priority of the mapping with IP preference 5.
            Values are as follows:
                     ----------------------------------------------------
                     |  31-24  |  23-16   |  15-8   |      7-0          |
                     ----------------------------------------------------
                     |  flag   |  yellow  |  green  | green-and-yellow  |
                     ----------------------------------------------------
            Bits 0-7: indicate the output priority of yellow and green packets with IP preference 5.
            Bits 8-15: indicate the output priority of green packets with IP preference 5.
            Bits 16-23: indicate the output priority of yellow packets with IP preference 5.
            Bits 24-31: indicate the color of packets whose priority is to be modified.

            0: indicates that the priorities of both yellow and green packets are modified (bits 0-7).
            1: indicates that the priorities of yellow and green packets are modified respectively
               (bits 8-15 for green packets and bits 16-23 for yellow packets).
            Other values are invalid.

            Default: 5
           "
       ::= { hwIPPrecToPbitsMappingEntry 7 }

   hwIPPrecToPbitsMapping6 OBJECT-TYPE
       SYNTAX Integer32
       MAX-ACCESS read-write
       STATUS current
       DESCRIPTION
           "Indicates the output 802.1p priority of the mapping with IP preference 6.
            Values are as follows:
                     ----------------------------------------------------
                     |  31-24  |  23-16   |  15-8   |      7-0          |
                     ----------------------------------------------------
                     |  flag   |  yellow  |  green  | green-and-yellow  |
                     ----------------------------------------------------
            Bits 0-7: indicate the output priority of yellow and green packets with IP preference 6.
            Bits 8-15: indicate the output priority of green packets with IP preference 6.
            Bits 16-23: indicate the output priority of yellow packets with IP preference 6.
            Bits 24-31: indicate the color of packets whose priority is to be modified.

            0: indicates that the priorities of both yellow and green packets are modified (bits 0-7).
            1: indicates that the priorities of yellow and green packets are modified respectively
               (bits 8-15 for green packets and bits 16-23 for yellow packets).
            Other values are invalid.

            Default: 6
           "
       ::= { hwIPPrecToPbitsMappingEntry 8 }

   hwIPPrecToPbitsMapping7 OBJECT-TYPE
       SYNTAX Integer32
       MAX-ACCESS read-write
       STATUS current
       DESCRIPTION
           "Indicates the output 802.1p priority of the mapping with IP preference 7.
            Values are as follows:
                     ----------------------------------------------------
                     |  31-24  |  23-16   |  15-8   |      7-0          |
                     ----------------------------------------------------
                     |  flag   |  yellow  |  green  | green-and-yellow  |
                     ----------------------------------------------------
            Bits 0-7: indicate the output priority of yellow and green packets with IP preference 7.
            Bits 8-15: indicate the output priority of green packets with IP preference 7.
            Bits 16-23: indicate the output priority of yellow packets with IP preference 7.
            Bits 24-31: indicate the color of packets whose priority is to be modified.

            0: indicates that the priorities of both yellow and green packets are modified (bits 0-7).
            1: indicates that the priorities of yellow and green packets are modified respectively
               (bits 8-15 for green packets and bits 16-23 for yellow packets).
            Other values are invalid.

            Default: 7
           "
       ::= { hwIPPrecToPbitsMappingEntry 9 }

   hwIPPrecToPbitsMappingRowStatus OBJECT-TYPE
       SYNTAX RowStatus
       MAX-ACCESS read-create
       STATUS current
       DESCRIPTION
           "Indicates the row status.
            It supports only the query function. active(1) is always returned in the query operation.
            Options:
            1. active(1) -indicates the query operation
           "
       ::= { hwIPPrecToPbitsMappingEntry 10 }

--hwPortCarModeTable
   hwPortCarModeTable OBJECT-TYPE
       SYNTAX SEQUENCE OF HwPortCarModeEntry
       MAX-ACCESS not-accessible
       STATUS current
       DESCRIPTION
           "Used to query and modify the port CAR mode.
            The index of this table is ifIndex.
           "
       ::= { hwExtIpdslam 30 }

   hwPortCarModeEntry OBJECT-TYPE
       SYNTAX HwPortCarModeEntry
       MAX-ACCESS not-accessible
       STATUS current
       DESCRIPTION
           "Used to query and modify the port CAR mode.
            The index of this entry is ifIndex.
           "
       INDEX { ifIndex }
       ::= { hwPortCarModeTable 1 }

   HwPortCarModeEntry ::=
       SEQUENCE {
         hwPortCarMode
           INTEGER
        }

   hwPortCarMode OBJECT-TYPE
       SYNTAX INTEGER
           {
           servicePort(1),
           portCos(2)
           }
       MAX-ACCESS read-write
       STATUS current
       DESCRIPTION
           "Indicates the port CAR mode. The port CAR mode can be by service port or by port and CoS.
            Options:
            1. servicePort(1)  -When the port CAR mode is set to servicePort(1),
                                it indicates that CAR is performed based on the service port.
            2. portCos(2)      -When the port CAR mode is set to portCos(2), the traffic profile
                                referenced during the creation of the service port is invalid.
                                In this case, CAR is performed based on the priority of the packet on the port.
            Default: servicePort(1)
           "
       ::= { hwPortCarModeEntry 1 }

   -- hwCosRemarkMask
   hwCosRemarkMask OBJECT-TYPE
       SYNTAX Unsigned32
       MAX-ACCESS read-write
       STATUS current
       DESCRIPTION
           "As an independent leaf node, describes the mapping between CoS and remarked CoS.

            The remarked CoS ID is 0-7. Every four bits represents the CoS ID to which a Cos corresponds.
            When hwCosRemarkMask is set to 0xffffffff(4294967295), it means restoring it to default settings.

            The default mapping is as follows: Packets with priority 7 join queue 7, packets with priority 6 join queue 6, and so on.
            The corresponding bits are:
            0111 0110 0101 0100 0011 0010 0001 0000
               7    6    5    4    3    2    1    0
            Default: 1985229328
           "
       ::= { hwExtIpdslam 31 }

   --hwTagTransformTable
   hwTagTransformTable OBJECT-TYPE
       SYNTAX SEQUENCE OF HwTagTransformEntry
       MAX-ACCESS not-accessible
       STATUS current
       DESCRIPTION
           "Used to enable or disable the ability of the tag-transformation.
            The indexes of this table are hwFrameIndex and hwSlotIndex.
           "
       ::= { hwExtIpdslam 32 }

   hwTagTransformEntry OBJECT-TYPE
       SYNTAX HwTagTransformEntry
       MAX-ACCESS not-accessible
       STATUS current
       DESCRIPTION
           "Used to enable or disable the ability of the tag-transformation.
            The indexes of this entry are hwFrameIndex and hwSlotIndex.
           "
       INDEX { hwFrameIndex,hwSlotIndex }
       ::= { hwTagTransformTable 1 }

   HwTagTransformEntry ::=
       SEQUENCE {
           hwTagTransform
             INTEGER
     }

   hwTagTransform OBJECT-TYPE
       SYNTAX INTEGER
           {
           disable(1),
           enable(2)
           }
       MAX-ACCESS read-write
       STATUS current
       DESCRIPTION
           "Indicates the ability of the tag transformation.
            Options:
            1. disable(1)    -Indicates that the board does not support tag transformation.
            2.  enable(2)    -Indicates that the board supports tag transformation.
            Default: disable(1)
            "
       ::= { hwTagTransformEntry 1 }

   --hwBoardMacLearningControlTable
   hwBoardMacLearningControlTable OBJECT-TYPE
       SYNTAX SEQUENCE OF HwBoardMacLearningControlEntry
       MAX-ACCESS not-accessible
       STATUS current
       DESCRIPTION
           "Used to enable or disable the board MAC learning ability in each specified VLAN.
            The indexes of this table are hwFrameIndex and hwSlotIndex.
           "
       ::= { hwExtIpdslam 33 }

   hwBoardMacLearningControlEntry OBJECT-TYPE
       SYNTAX HwBoardMacLearningControlEntry
       MAX-ACCESS not-accessible
       STATUS current
       DESCRIPTION
           "Used to enable or disable the board MAC learning ability in each specified VLAN.
            The indexes of this entry are hwFrameIndex and hwSlotIndex.
           "
       INDEX { hwFrameIndex,hwSlotIndex }
       ::= { hwBoardMacLearningControlTable 1 }

   HwBoardMacLearningControlEntry ::=
       SEQUENCE {
           hwMacLearningControlArray
             OCTET STRING
     }

   hwMacLearningControlArray OBJECT-TYPE
       SYNTAX OCTET STRING  (SIZE (512..512))
       MAX-ACCESS read-write
       STATUS current
       DESCRIPTION
           "Bit 0 - 4095, each indicates the MAC learning ability in corresponding VLAN.
            If bit 1000 is set to 0, it indicates that the MAC learning ability in VLAN 1000 is  enabled,
            and contrarily, if it is set to 1, that the MAC learning ability is disabled.
            VLAN 0, 4094, 4095 and the system reserved VLANs cannot be set, the fixed value is 0.
            The vlan starts from the least significant bit.
            Default: enable(0)
            "
       ::= { hwBoardMacLearningControlEntry 1 }

   -- hwCosQueueDepthRateSlotTable
   hwCosQueueDepthRateSlotTable OBJECT-TYPE
       SYNTAX SEQUENCE OF HwCosQueueDepthRateSlotEntry
       MAX-ACCESS not-accessible
       STATUS current
       DESCRIPTION
           "Sets the depth of queue in the board.
            The indexes of this table are hwFrameIndex and hwSlotIndex.
           "
       ::= { hwExtIpdslam 34 }

    hwCosQueueDepthRateSlotEntry OBJECT-TYPE
       SYNTAX HwCosQueueDepthRateSlotEntry
       MAX-ACCESS not-accessible
       STATUS current
       DESCRIPTION
           "Sets the depth of queue in the board.
            The indexes of this entry are hwFrameIndex and hwSlotIndex.
           "
       INDEX { hwFrameIndex, hwSlotIndex }
       ::= { hwCosQueueDepthRateSlotTable 1 }

    HwCosQueueDepthRateSlotEntry ::=
       SEQUENCE {
           hwCosQueueDepthRateSlotQue0
             Integer32,
           hwCosQueueDepthRateSlotQue1
             Integer32,
           hwCosQueueDepthRateSlotQue2
             Integer32,
           hwCosQueueDepthRateSlotQue3
             Integer32,
           hwCosQueueDepthRateSlotQue4
             Integer32,
           hwCosQueueDepthRateSlotQue5
             Integer32,
           hwCosQueueDepthRateSlotQue6
             Integer32,
           hwCosQueueDepthRateSlotQue7
             Integer32,
           hwCosQueueDepthRateSlotRowStatus
             RowStatus
     }

    hwCosQueueDepthRateSlotQue0 OBJECT-TYPE
       SYNTAX Integer32(0..100)
       MAX-ACCESS read-write
       STATUS current
       DESCRIPTION
           "Indicates the depth of queue 0, that is, percentage of the buffer exclusively occupied by queue 0.
            Range: 0-100
            The larger the percentage, the more packets can be buffered. The sum of percentages must be 100%.

            The depth of queue 0 can also be configured in hwCosQueueDepthRateQue0 of hwCosQueueDepthRateTable in HUAWEI-ETHERLIKE-EXT-MIB.
            The final status of the depth of queue 0 is determined by its global-level switch and board-level switch.
            When the board-level switch isn't configured, global-level switch takes effect.
            If board-level switch is configured, board-level switch takes effects.
           "
       ::= { hwCosQueueDepthRateSlotEntry 1 }

    hwCosQueueDepthRateSlotQue1 OBJECT-TYPE
       SYNTAX Integer32(0..100)
       MAX-ACCESS read-write
       STATUS current
       DESCRIPTION
           "Indicates the depth of queue 1, that is, percentage of the buffer exclusively occupied by queue 1.
            Range: 0-100
            The larger the percentage, the more packets can be buffered. The sum of percentages must be 100%.

            The depth of queue 1 can also be configured in hwCosQueueDepthRateQue1 of hwCosQueueDepthRateTable in HUAWEI-ETHERLIKE-EXT-MIB.
            The final status of the depth of queue 1 is determined by its global-level switch and board-level switch.
            When the board-level switch isn't configured, global-level switch takes effect.
            If board-level switch is configured, board-level switch takes effects.
           "
       ::= { hwCosQueueDepthRateSlotEntry 2 }

    hwCosQueueDepthRateSlotQue2 OBJECT-TYPE
       SYNTAX Integer32(0..100)
       MAX-ACCESS read-write
       STATUS current
       DESCRIPTION
           "Indicates the depth of queue 2, that is, percentage of the buffer exclusively occupied by queue 2.
            Range: 0-100
            The larger the percentage, the more packets can be buffered. The sum of percentages must be 100%.

            The depth of queue 2 can also be configured in hwCosQueueDepthRateQue2 of hwCosQueueDepthRateTable in HUAWEI-ETHERLIKE-EXT-MIB.
            The final status of the depth of queue 2 is determined by its global-level switch and board-level switch.
            When the board-level switch isn't configured, global-level switch takes effect.
            If board-level switch is configured, board-level switch takes effects.
           "
       ::= { hwCosQueueDepthRateSlotEntry 3 }

    hwCosQueueDepthRateSlotQue3 OBJECT-TYPE
       SYNTAX Integer32(0..100)
       MAX-ACCESS read-write
       STATUS current
       DESCRIPTION
           "Indicates the depth of queue 3, that is, percentage of the buffer exclusively occupied by queue 3.
            Range: 0-100
            The larger the percentage, the more packets can be buffered. The sum of percentages must be 100%.

            The depth of queue 3 can also be configured in hwCosQueueDepthRateQue3 of hwCosQueueDepthRateTable in HUAWEI-ETHERLIKE-EXT-MIB.
            The final status of the depth of queue 3 is determined by its global-level switch and board-level switch.
            When the board-level switch isn't configured, global-level switch takes effect.
            If board-level switch is configured, board-level switch takes effects.
           "
       ::= { hwCosQueueDepthRateSlotEntry 4 }

    hwCosQueueDepthRateSlotQue4 OBJECT-TYPE
       SYNTAX Integer32(0..100)
       MAX-ACCESS read-write
       STATUS current
       DESCRIPTION
           "Indicates the depth of queue 4, that is, percentage of the buffer exclusively occupied by queue 4.
            Range: 0-100
            The larger the percentage, the more packets can be buffered. The sum of percentages must be 100%.

            The depth of queue 4 can also be configured in hwCosQueueDepthRateQue4 of hwCosQueueDepthRateTable in HUAWEI-ETHERLIKE-EXT-MIB.
            The final status of the depth of queue 4 is determined by its global-level switch and board-level switch.
            When the board-level switch isn't configured, global-level switch takes effect.
            If board-level switch is configured, board-level switch takes effects.
           "
       ::= { hwCosQueueDepthRateSlotEntry 5 }

    hwCosQueueDepthRateSlotQue5 OBJECT-TYPE
       SYNTAX Integer32(0..100)
       MAX-ACCESS read-write
       STATUS current
       DESCRIPTION
           "Indicates the depth of queue 5, that is, percentage of the buffer exclusively occupied by queue 5.
            Range: 0-100
            The larger the percentage, the more packets can be buffered. The sum of percentages must be 100%.

            The depth of queue 5 can also be configured in hwCosQueueDepthRateQue5 of hwCosQueueDepthRateTable in HUAWEI-ETHERLIKE-EXT-MIB.
            The final status of the depth of queue 5 is determined by its global-level switch and board-level switch.
            When the board-level switch isn't configured, global-level switch takes effect.
            If board-level switch is configured, board-level switch takes effects.
           "
       ::= { hwCosQueueDepthRateSlotEntry 6 }

    hwCosQueueDepthRateSlotQue6 OBJECT-TYPE
       SYNTAX Integer32(0..100)
       MAX-ACCESS read-write
       STATUS current
       DESCRIPTION
           "Indicates the depth of queue 6, that is, percentage of the buffer exclusively occupied by queue 6.
            Range: 0-100
            The larger the percentage, the more packets can be buffered. The sum of percentages must be 100%.

            The depth of queue 6 can also be configured in hwCosQueueDepthRateQue6 of hwCosQueueDepthRateTable in HUAWEI-ETHERLIKE-EXT-MIB.
            The final status of the depth of queue 6 is determined by its global-level switch and board-level switch.
            When the board-level switch isn't configured, global-level switch takes effect.
            If board-level switch is configured, board-level switch takes effects.
           "
       ::= { hwCosQueueDepthRateSlotEntry 7 }

    hwCosQueueDepthRateSlotQue7 OBJECT-TYPE
       SYNTAX Integer32(0..100)
       MAX-ACCESS read-write
       STATUS current
       DESCRIPTION
           "Indicates the depth of queue 7, that is, percentage of the buffer exclusively occupied by queue 7.
            Range: 0-100
            The larger the percentage, the more packets can be buffered. The sum of percentages must be 100%.

            The depth of queue 7 can also be configured in hwCosQueueDepthRateQue7 of hwCosQueueDepthRateTable in HUAWEI-ETHERLIKE-EXT-MIB.
            The final status of the depth of queue 7 is determined by its global-level switch and board-level switch.
            When the board-level switch isn't configured, global-level switch takes effect.
            If board-level switch is configured, board-level switch takes effects.
           "
       ::= { hwCosQueueDepthRateSlotEntry 8 }

    hwCosQueueDepthRateSlotRowStatus OBJECT-TYPE
           SYNTAX RowStatus
           MAX-ACCESS read-create
           STATUS current
           DESCRIPTION
               "Indicates the row status and is used for creating or deleting
                a vlan connect item.
                Options:
                1. active(1)
                2. createAndGo(4)
                3. destroy(6)
                Only options createAndGo(4) and destroy(6) are supported the set operation.
                During query, active(1) is always returned for this leaf.
               "
         ::= { hwCosQueueDepthRateSlotEntry 255 }

   -- hwEarlyDropModeSlotTable
   hwEarlyDropModeSlotTable OBJECT-TYPE
       SYNTAX SEQUENCE OF HwEarlyDropModeSlotEntry
       MAX-ACCESS not-accessible
       STATUS current
       DESCRIPTION
           "Sets the early drop mode of the board.
            The indexes of this table are hwFrameIndex and hwSlotIndex.
           "
       ::= { hwExtIpdslam 35 }

    hwEarlyDropModeSlotEntry OBJECT-TYPE
       SYNTAX HwEarlyDropModeSlotEntry
       MAX-ACCESS not-accessible
       STATUS current
       DESCRIPTION
           "Sets the early drop mode of the board.
            The indexes of this entry are hwFrameIndex and hwSlotIndex.
           "
       INDEX { hwFrameIndex, hwSlotIndex }
       ::= { hwEarlyDropModeSlotTable 1 }

    HwEarlyDropModeSlotEntry ::=
       SEQUENCE {
           hwEarlyDropModeSlot
             INTEGER,
           hwEarlyDropModeSlotRowStatus
             RowStatus
     }

    hwEarlyDropModeSlot OBJECT-TYPE
       SYNTAX INTEGER
           {
           priBase(1),
           colorBase(2),
           off(3),
           colorWred(4)
           }
       MAX-ACCESS read-write
       STATUS current
       DESCRIPTION
           "Options:
             1. priBase(1)   -indicating priority-based early drop
             2. colorBase(2) -indicating color-based early drop
             3. off(3) -indicating disable the early drop function
             4. colorWred(4) -indicating color-wred early drop

             In the case of priority-based early drop, if packets with a specified priority reach the preset threshold (queue depth percentage)
             of their destination queue, subsequent packets of the same priority will be dropped instead of entering the queue.
             In the case of color-based early drop, you can configure and query early drop parameters of packets of different colors.
             In the case of off, the early drop function is disabled.
             In the case of color-wred early drop, packets with different colors will discard by WRED(weighted random early detection) strategy.
             For example, you can configure and query the early drop lower threshold, early drop upper threshold, and early drop possibility of
             green packets or yellow packets.
            "
         ::= { hwEarlyDropModeSlotEntry 1 }

    hwEarlyDropModeSlotRowStatus OBJECT-TYPE
           SYNTAX RowStatus
           MAX-ACCESS read-create
           STATUS current
           DESCRIPTION
               "Indicates the row status and is used for creating or deleting the early drop mode of the board.
                Options:
                1. active(1)
                2. createAndGo(4)
                3. destroy(6)
                Only options createAndGo(4) and destroy(6) are supported the set operation.
                During query, active(1) is always returned for this leaf.
               "
         ::= { hwEarlyDropModeSlotEntry 255 }

-- hwEarlyDropColorBasedYellowThresholdTable
   hwEarlyDropColorBasedYellowThresholdTable OBJECT IDENTIFIER ::= { hwExtIpdslam 36 }

   hwEarlyDropColorBasedThresholdCos0 OBJECT-TYPE
       SYNTAX Integer32 (0..100)
       MAX-ACCESS read-write
       STATUS current
       DESCRIPTION
           "Indicates the CAR threshold of CoS 0.
            When traffic with CoS 0 reaches this threshold, the packets that are marked to yellow will be discarded.
           "
       ::= { hwEarlyDropColorBasedYellowThresholdTable 1 }

   hwEarlyDropColorBasedThresholdCos1 OBJECT-TYPE
       SYNTAX Integer32 (0..100)
       MAX-ACCESS read-write
       STATUS current
       DESCRIPTION
           "Indicates the CAR threshold of CoS 1.
            When traffic with CoS 1 reaches this threshold, the packets that are marked to yellow will be discarded.
           "
       ::= { hwEarlyDropColorBasedYellowThresholdTable 2 }

   hwEarlyDropColorBasedThresholdCos2 OBJECT-TYPE
       SYNTAX Integer32 (0..100)
       MAX-ACCESS read-write
       STATUS current
       DESCRIPTION
           "Indicates the CAR threshold of CoS 2.
            When traffic with CoS 2 reaches this threshold, the packets that are marked to yellow will be discarded.
           "
       ::= { hwEarlyDropColorBasedYellowThresholdTable 3 }

   hwEarlyDropColorBasedThresholdCos3 OBJECT-TYPE
       SYNTAX Integer32 (0..100)
       MAX-ACCESS read-write
       STATUS current
       DESCRIPTION
           "Indicates the CAR threshold of CoS 3.
            When traffic with CoS 3 reaches this threshold, the packets that are marked to yellow will be discarded.
           "
       ::= { hwEarlyDropColorBasedYellowThresholdTable 4 }

   hwEarlyDropColorBasedThresholdCos4 OBJECT-TYPE
       SYNTAX Integer32 (0..100)
       MAX-ACCESS read-write
       STATUS current
       DESCRIPTION
           "Indicates the CAR threshold of CoS 4.
            When traffic with CoS 4 reaches this threshold, the packets that are marked to yellow will be discarded.
           "
       ::= { hwEarlyDropColorBasedYellowThresholdTable 5 }

   hwEarlyDropColorBasedThresholdCos5 OBJECT-TYPE
       SYNTAX Integer32 (0..100)
       MAX-ACCESS read-write
       STATUS current
       DESCRIPTION
           "Indicates the CAR threshold of CoS 5.
            When traffic with CoS 5 reaches this threshold, the packets that are marked to yellow will be discarded.
           "
       ::= { hwEarlyDropColorBasedYellowThresholdTable 6 }

   hwEarlyDropColorBasedThresholdCos6 OBJECT-TYPE
       SYNTAX Integer32 (0..100)
       MAX-ACCESS read-write
       STATUS current
       DESCRIPTION
           "Indicates the CAR threshold of CoS 6.
            When traffic with CoS 6 reaches this threshold, the packets that are marked to yellow will be discarded.
           "
       ::= { hwEarlyDropColorBasedYellowThresholdTable 7 }

   hwEarlyDropColorBasedThresholdCos7 OBJECT-TYPE
       SYNTAX Integer32 (0..100)
       MAX-ACCESS read-write
       STATUS current
       DESCRIPTION
           "Indicates the CAR threshold of CoS 7.
            When traffic with CoS 7 reaches this threshold, the packets that are marked to yellow will be discarded.
           "
       ::= { hwEarlyDropColorBasedYellowThresholdTable 8 }

   hwCosGroupTblTable OBJECT-TYPE
       SYNTAX SEQUENCE OF HwCosGroupTblEntry
       MAX-ACCESS not-accessible
       STATUS current
       DESCRIPTION
           "The index of this table is hwCosGroupTblIndex.
            This table describes the relationship between the CoS entry in the CoS-group table and the group of the entry.
            It supports the query and set operations.
           "
       ::= { hwExtIpdslam 37 }

   hwCosGroupTblEntry OBJECT-TYPE
       SYNTAX HwCosGroupTblEntry
       MAX-ACCESS not-accessible
       STATUS current
       DESCRIPTION
           "The index of this entry is hwCosGroupTblIndex.
            This table describes the relationship between the CoS entry in the CoS-group table and the group of the entry.
            It supports the query and set operations.
           "
       INDEX { hwCosGroupTblIndex }
       ::= { hwCosGroupTblTable 1 }

   HwCosGroupTblEntry ::=
       SEQUENCE {
           hwCosGroupTblIndex
               Integer32,
           hwCos0GroupIndex
               Integer32,
           hwCos1GroupIndex
               Integer32,
           hwCos2GroupIndex
               Integer32,
           hwCos3GroupIndex
               Integer32,
           hwCos4GroupIndex
               Integer32,
           hwCos5GroupIndex
               Integer32,
           hwCos6GroupIndex
               Integer32,
           hwCos7GroupIndex
               Integer32
        }

   hwCosGroupTblIndex OBJECT-TYPE
       SYNTAX Integer32 (1..16)
       MAX-ACCESS not-accessible
       STATUS current
       DESCRIPTION
           "CoS-group table index
            Range: 1-16
           "
       ::= { hwCosGroupTblEntry 1 }

   hwCos0GroupIndex OBJECT-TYPE
       SYNTAX Integer32 (0..7)
       MAX-ACCESS read-write
       STATUS current
       DESCRIPTION
           "CoS group of CoS0
            Range: 0-7
            Default value: 0
           "
       ::= { hwCosGroupTblEntry 2 }

   hwCos1GroupIndex OBJECT-TYPE
       SYNTAX Integer32 (0..7)
       MAX-ACCESS read-write
       STATUS current
       DESCRIPTION
           "CoS group of CoS1
            Range: 0-7
            Default value: 1
           "
       ::= { hwCosGroupTblEntry 3 }

   hwCos2GroupIndex OBJECT-TYPE
       SYNTAX Integer32 (0..7)
       MAX-ACCESS read-write
       STATUS current
       DESCRIPTION
           "CoS group of CoS2
            Range: 0-7
            Default value: 2
           "
       ::= { hwCosGroupTblEntry 4 }

   hwCos3GroupIndex OBJECT-TYPE
       SYNTAX Integer32 (0..7)
       MAX-ACCESS read-write
       STATUS current
       DESCRIPTION
           "CoS group of CoS3
            Range: 0-7
            Default value: 3
           "
       ::= { hwCosGroupTblEntry 5 }

   hwCos4GroupIndex OBJECT-TYPE
       SYNTAX Integer32 (0..7)
       MAX-ACCESS read-write
       STATUS current
       DESCRIPTION
           "CoS group of CoS4
            Range: 0-7
            Default value: 4
           "
       ::= { hwCosGroupTblEntry 6 }

   hwCos5GroupIndex OBJECT-TYPE
       SYNTAX Integer32 (0..7)
       MAX-ACCESS read-write
       STATUS current
       DESCRIPTION
           "CoS group of CoS5
            Range: 0-7
            Default value: 5
           "
       ::= { hwCosGroupTblEntry 7 }

   hwCos6GroupIndex OBJECT-TYPE
       SYNTAX Integer32 (0..7)
       MAX-ACCESS read-write
       STATUS current
       DESCRIPTION
           "CoS group of CoS6
            Range: 0-7
            Default value: 6
           "
       ::= { hwCosGroupTblEntry 8 }

   hwCos7GroupIndex OBJECT-TYPE
       SYNTAX Integer32 (0..7)
       MAX-ACCESS read-write
       STATUS current
       DESCRIPTION
           "CoS group of CoS7
            Range: 0-7
            Default value: 7
           "
       ::= { hwCosGroupTblEntry 9 }

-- hwCarPortCosGroupTable
   hwCarPortCosGroupTable OBJECT-TYPE
       SYNTAX SEQUENCE OF HwCarPortCosGroupEntry
       MAX-ACCESS not-accessible
       STATUS current
       DESCRIPTION
           "This table is used to set, delete, and query the CoS-group table bound to the GEM port. The traffic profile can be used to limit the rate for the CoS group only after the GEM port is bound to the CoS-group table.
            The indexes of this table are ifIndex, hwCosPortGroupExtPara1, and hwCosPortGroupExtPara2. The value 0x7FFFFFFF indicates that the index is invalid.
            The binding between the GEM port and the CoS-group table can be set only when the board CAR mode is portCos(2).
           "
       ::= { hwExtIpdslam 38 }

   hwCarPortCosGroupEntry OBJECT-TYPE
       SYNTAX HwCarPortCosGroupEntry
       MAX-ACCESS not-accessible
       STATUS current
       DESCRIPTION
           "This table is used to set, delete, and query the CoS-group table bound to the GEM port. The traffic profile can be used to limit the rate for the CoS group only after the GEM port is bound to the CoS-group table.
            The indexes of this entry are ifIndex, hwCosPortGroupExtPara1, and hwCosPortGroupExtPara2. The value 0x7FFFFFFF indicates that the index is invalid.
            The binding between the GEM port and the CoS-group table can be set only when the board CAR mode is portCos(2).
           "
       INDEX { ifIndex, hwCosPortGroupExtPara1, hwCosPortGroupExtPara2 }
       ::= { hwCarPortCosGroupTable 1 }

   HwCarPortCosGroupEntry ::=
      SEQUENCE {
          hwCosPortGroupExtPara1
              Integer32,
          hwCosPortGroupExtPara2
              Integer32,
          hwCosPortGroupTableIndex
              Integer32,
          hwCosPortGroupRowStatus
              RowStatus
        }

   hwCosPortGroupExtPara1 OBJECT-TYPE
       SYNTAX Integer32
       MAX-ACCESS not-accessible
       STATUS current
       DESCRIPTION
           "It is one of table indexes. Its meaning varies with the GPON working mode.
            When the GPON board works in the distributing mode, this leaf indicates the GEM port ID. When the GPON board works in the profile mode, this leaf indicates the ONT ID. The value 0x07FFFFFFF indicates that this leaf value is invalid.
           "
       ::= { hwCarPortCosGroupEntry 1 }

   hwCosPortGroupExtPara2 OBJECT-TYPE
       SYNTAX Integer32
       MAX-ACCESS not-accessible
       STATUS current
       DESCRIPTION
           "It is one of table indexes. Its meaning varies with the GPON working mode.
            When the GPON board works in the distributing mode, this leaf is meaningless and must use an invalid value. When the GPON board works in the profile mode, this leaf indicates the GEM index for bound GEM ports, and indicates the GEM ID for unbound GEM ports. The value 0x07FFFFFFF indicates that this leaf value is invalid.
           "
       ::= { hwCarPortCosGroupEntry 2 }

   hwCosPortGroupTableIndex OBJECT-TYPE
       SYNTAX Integer32 (1..16)
       MAX-ACCESS read-write
       STATUS current
       DESCRIPTION
           "It describes the index of the CoS-group table bound to the GEM port.
            Range: 1-16
            This leaf must be set in the add and modify operations of the table, and is not required in the delete operation of the table.
           "
       ::= { hwCarPortCosGroupEntry 3 }

   hwCosPortGroupRowStatus OBJECT-TYPE
       SYNTAX RowStatus
       MAX-ACCESS read-create
       STATUS current
       DESCRIPTION
           "Indicates the row status.
            In creation, you must set this leaf to createAndGo(4) and must enter the cos-group-table index;
            in deletion, set this leaf to destroy(6);
            in query, this leaf is displayed as active(1).
            Options:
            1. active(1)      -indicates the query operation
            2. createAndGo(4) -indicates creating
            3. destroy(6)     -indicates deleting
           "
       ::= { hwCarPortCosGroupEntry 4 }

-- hwXponQueueShapingTable
   hwXponQueueShapingTable OBJECT-TYPE
       SYNTAX SEQUENCE OF HwXponQueueShapingEntry
       MAX-ACCESS not-accessible
       STATUS current
       DESCRIPTION
           "Indicates XPON board queue shaping table.
            It is used to add, query, modify, or delete the queue shaping on XPON board.
            The indexes of this table are hwXponQueueShapingIfIndex, hwXponQueueShapingOntId, hwXponQueueId and hwXponQueueDirection.
           "
       ::= { hwExtIpdslam 39 }

   hwXponQueueShapingEntry OBJECT-TYPE
       SYNTAX HwXponQueueShapingEntry
       MAX-ACCESS not-accessible
       STATUS current
       DESCRIPTION
           "Indicates XPON board queue shaping table.
            It is used to add, query, modify, or delete the queue shaping on XPON board.
            The indexes of this entry are hwXponQueueShapingIfIndex, hwXponQueueShapingOntId, hwXponQueueId and hwXponQueueDirection.
           "
       INDEX { hwXponQueueShapingIfIndex, hwXponQueueShapingOntId, hwXponQueueId, hwXponQueueDirection }
       ::= { hwXponQueueShapingTable 1 }

   HwXponQueueShapingEntry ::=
       SEQUENCE {
           hwXponQueueShapingIfIndex
               Integer32,
           hwXponQueueShapingOntId
               Integer32,
           hwXponQueueId
               Integer32,
           hwXponQueueDirection
               INTEGER,
           hwXponQueueShapingTrafficIndex
               Integer32,
           hwXponQueueShapingTrafficRowStatus
               RowStatus
        }

   hwXponQueueShapingIfIndex OBJECT-TYPE
       SYNTAX Integer32
       MAX-ACCESS not-accessible
       STATUS current
       DESCRIPTION
           "Indicates the port index for configuring a queue shaping.
            The index uniquely identifies a port.
            The value and algorithm of this index are the same as those of the ifIndex.
           "
       ::= { hwXponQueueShapingEntry 1 }

   hwXponQueueShapingOntId OBJECT-TYPE
       SYNTAX Integer32
       MAX-ACCESS not-accessible
       STATUS current
       DESCRIPTION
           "Indicates the ONT ID for configuring a queue shaping.
           "
       ::= { hwXponQueueShapingEntry 2 }

   hwXponQueueId OBJECT-TYPE
       SYNTAX Integer32 (0..7)
       MAX-ACCESS not-accessible
       STATUS current
       DESCRIPTION
           "Indicates the queue ID for configuring a queue shaping.
            Range: 0-7
           "
       ::= { hwXponQueueShapingEntry 3 }

   hwXponQueueDirection OBJECT-TYPE
       SYNTAX INTEGER
       {
           outBound(1),
           inBound(2)
       }
       MAX-ACCESS not-accessible
       STATUS current
       DESCRIPTION
           "Indicates the direction for configuring a queue shaping.
            Currently the XPON board only supports outBound(1).
            Options:
            1. outBound(1)   -indicates that the index of the IP traffic profile is used by downstream packets.
            2. inBound(2)     -indicates that the index of the IP traffic profile is used by upstream packets.
           "
       ::= { hwXponQueueShapingEntry 4 }

   hwXponQueueShapingTrafficIndex OBJECT-TYPE
       SYNTAX Integer32
       MAX-ACCESS read-write
       STATUS current
       DESCRIPTION
           "Indicates the index of the IP traffic profile referenced by queue shaping."
       ::= { hwXponQueueShapingEntry 5 }

   hwXponQueueShapingTrafficRowStatus OBJECT-TYPE
       SYNTAX RowStatus
       MAX-ACCESS read-create
       STATUS current
       DESCRIPTION
           "Indicates the row status.
            Options:
            1. active(1)
            2. createAndGo(4)
            3. destroy(6)
            To create a queue shaping, set this leaf to createAndGo(4).
            To delete a queue shaping, set this leaf to destroy(6).
            When a queue shaping is queried, this leaf is displayed as active(1).
           "
       ::= { hwXponQueueShapingEntry 6 }

-- hwEthQueueShapingTable
   hwEthQueueShapingTable OBJECT-TYPE
       SYNTAX SEQUENCE OF HwEthQueueShapingEntry
       MAX-ACCESS not-accessible
       STATUS current
       DESCRIPTION
           "Indicates etherner board queue shaping table.
            It is used to add, query, modify, or delete the queue shaping on etherner board.
            The indexes of this table are hwEthQueueShapingIfIndex, hwEthQueueId and hwEthQueueDirection.
           "
       ::= { hwExtIpdslam 40 }

   hwEthQueueShapingEntry OBJECT-TYPE
       SYNTAX HwEthQueueShapingEntry
       MAX-ACCESS not-accessible
       STATUS current
       DESCRIPTION
           "Indicates etherner board queue shaping table.
            It is used to add, query, modify, or delete the queue shaping on etherner board.
            The indexes of this entry are hwEthQueueShapingIfIndex, hwEthQueueId and hwEthQueueDirection.
           "
       INDEX { hwEthQueueShapingIfIndex, hwEthQueueId, hwEthQueueDirection }
       ::= { hwEthQueueShapingTable 1 }

   HwEthQueueShapingEntry ::=
       SEQUENCE {
           hwEthQueueShapingIfIndex
               Integer32,
           hwEthQueueId
               Integer32,
           hwEthQueueDirection
               INTEGER,
           hwEthQueueShapingTrafficIndex
               Integer32,
           hwEthQueueShapingTrafficRowStatus
               RowStatus
        }

   hwEthQueueShapingIfIndex OBJECT-TYPE
       SYNTAX Integer32
       MAX-ACCESS not-accessible
       STATUS current
       DESCRIPTION
           "Indicates the port index for configuring a queue shaping.
            The index uniquely identifies a port.
            The value and algorithm of this index are the same as those of the ifIndex.
           "
       ::= { hwEthQueueShapingEntry 1 }

   hwEthQueueId OBJECT-TYPE
       SYNTAX Integer32 (0..7)
       MAX-ACCESS not-accessible
       STATUS current
       DESCRIPTION
           "Indicates the queue ID for configuring a queue shaping.
            Range: 0-7
           "
       ::= { hwEthQueueShapingEntry 2 }

   hwEthQueueDirection OBJECT-TYPE
       SYNTAX INTEGER
       {
           outBound(1),
           inBound(2)
       }
       MAX-ACCESS not-accessible
       STATUS current
       DESCRIPTION
           "Indicates the direction for configuring a queue shaping.
            Options:
            1. outBound(1)   -indicates that the index of the IP traffic profile is used by downstream packets.
            2. inBound(2)     -indicates that the index of the IP traffic profile is used by upstream packets.
           "
       ::= { hwEthQueueShapingEntry 3 }

   hwEthQueueShapingTrafficIndex OBJECT-TYPE
       SYNTAX Integer32
       MAX-ACCESS read-write
       STATUS current
       DESCRIPTION
           "Indicates the index of the IP traffic profile referenced by queue shaping."
       ::= { hwEthQueueShapingEntry 4 }

   hwEthQueueShapingTrafficRowStatus OBJECT-TYPE
       SYNTAX RowStatus
       MAX-ACCESS read-create
       STATUS current
       DESCRIPTION
           "Indicates the row status.
            Options:
            1. active(1)
            2. createAndGo(4)
            3. destroy(6)
            To create a queue shaping, set this leaf to createAndGo(4).
            To delete a queue shaping, set this leaf to destroy(6).
            When a queue shaping is queried, this leaf is displayed as active(1).
           "
       ::= { hwEthQueueShapingEntry 5 }

   hwTrafficTablePriorityMappingMode OBJECT-TYPE
       SYNTAX INTEGER
       {
           userTos(1),
           userDscp(2)
       }
       MAX-ACCESS read-write
       STATUS current
	   DESCRIPTION
	       "Indicates the traffic table prority mapping mode.
	        Options:
	        1. userTos(1)       -indicates that the mapping mode is ToS to 802.1p.
	        2. userDscp(2)      -indicates that the mapping mode is DSCP to 802.1p.
	        Default: userTos(1)
	        The mode is used for the boards which don't support ToS to 802.1p and DSCP to 802.1p concurrently
	        but support either ToS to 802.1p or DSCP to 802.1p.If the mode is configured with userTos, all
	        service flows on the boards are working with userTos mapping mode, even if the mapping mode of the
	        service flows on the boards are configured with userDscp.If the mode is configured with userDscp,
	        all service flows on the boards are working with userDscp mapping mode, even if the mapping mode of
	        the service flows on the boards are configured with userTos.
	       "
	   ::= { hwExtIpdslam 41 }


   hwMacAddressHashConfilictDetect OBJECT-TYPE
       SYNTAX INTEGER
           {
           enable(1),
           disable(2)
           }
       MAX-ACCESS read-write
       STATUS current
       DESCRIPTION
           "Indicates the switch for MAC hash detect.
            Options:
            1. enable(1)  -indicates the switch for MAC hash detect is enable
            2. disable(2) -indicates the switch for MAC hash detect disable
            Default: disable(2)
           "
       ::= { hwExtIpdslam 42 }

-- hwE2ECcTable
   hwE2ECcTable OBJECT-TYPE
       SYNTAX SEQUENCE OF HwE2ECcEntry
       MAX-ACCESS not-accessible
       STATUS current
       DESCRIPTION
           "Indicates end to end congestion control.
            It is used to enable or disable the end to end (E2E) congestion control function on a board.
            If the E2E congestion control function is enabled, the buffer of the SCUH control board can be
            expanded through configuring the buffer of the SPUA board.
            In this way, packets can be saved in the buffer of the SPUA board but will not be discarded
            if congestion occurs on the SCUH control board.
            The indexes of this table are hwFrameIndex and hwSlotIndex.
           "
       ::= { hwExtIpdslam 43 }

  hwE2ECcEntry OBJECT-TYPE
       SYNTAX HwE2ECcEntry
       MAX-ACCESS not-accessible
       STATUS current
       DESCRIPTION
           "Indicates end to end congestion control.
            It is used to enable or disable the end to end (E2E) congestion control function on a board.
            If the E2E congestion control function is enabled, the buffer of the SCUH control board can be
            expanded through configuring the buffer of the SPUA board.
            In this way, packets can be saved in the buffer of the SPUA board but will not be discarded
            if congestion occurs on the SCUH control board.
            The indexes of this entry are hwFrameIndex and hwSlotIndex.
           "
       INDEX { hwFrameIndex, hwSlotIndex }
       ::= { hwE2ECcTable 1 }

   HwE2ECcEntry ::=
       SEQUENCE {
           hwE2ECcSwitch
               INTEGER,
           hwE2ECcQueueBufferRaio0
               Integer32,
           hwE2ECcQueueBufferRaio1
               Integer32,
           hwE2ECcQueueBufferRaio2
               Integer32,
           hwE2ECcQueueBufferRaio3
               Integer32,
           hwE2ECcQueueBufferRaio4
               Integer32,
           hwE2ECcQueueBufferRaio5
               Integer32,
           hwE2ECcQueueBufferRaio6
               Integer32,
           hwE2ECcQueueBufferRaio7
               Integer32,
           hwE2ECcQueueBufferRaio8
               Integer32,
           hwE2ECcQueueBufferRaio9
               Integer32,
           hwE2ECcQueueBufferRaio10
               Integer32,
           hwE2ECcQueueBufferRaio11
               Integer32,
           hwE2ECcQueueBufferRaio12
               Integer32,
           hwE2ECcQueueBufferRaio13
               Integer32,
           hwE2ECcQueueBufferRaio14
               Integer32,
           hwE2ECcQueueBufferRaio15
               Integer32
        }

   hwE2ECcSwitch OBJECT-TYPE
       SYNTAX INTEGER
           {
           enabled(1),
           disabled(2),
           notSupport(-1)
           }
       MAX-ACCESS read-write
       STATUS current
       DESCRIPTION
           "It is used to enable or disable the end to end (E2E) congestion control function on a board.
            Options:
            1. enabled(1)     -enables the E2E congestion control function on a board
            2. disabled(2)    -disables the E2E congestion control function on a board
            3. notSupport(-1) -indicates the board does not support this operation
           "
       ::= { hwE2ECcEntry 1 }

   hwE2ECcQueueBufferRaio0 OBJECT-TYPE
       SYNTAX Integer32 (0..100)
       MAX-ACCESS read-write
       STATUS current
       DESCRIPTION
           "Indicates the buffer size ratio of queue 0.
            Range: 0-100
           "
       ::= { hwE2ECcEntry 2 }

   hwE2ECcQueueBufferRaio1 OBJECT-TYPE
       SYNTAX Integer32 (0..100)
       MAX-ACCESS read-write
       STATUS current
       DESCRIPTION
           "Indicates the buffer size ratio of queue 1.
            Range: 0-100
           "
       ::= { hwE2ECcEntry 3 }

    hwE2ECcQueueBufferRaio2 OBJECT-TYPE
       SYNTAX Integer32 (0..100)
       MAX-ACCESS read-write
       STATUS current
       DESCRIPTION
           "Indicates the buffer size ratio of queue 2.
            Range: 0-100
           "
       ::= { hwE2ECcEntry 4 }

    hwE2ECcQueueBufferRaio3 OBJECT-TYPE
       SYNTAX Integer32 (0..100)
       MAX-ACCESS read-write
       STATUS current
       DESCRIPTION
           "Indicates the buffer size ratio of queue 3.
            Range: 0-100
           "
       ::= { hwE2ECcEntry 5 }

    hwE2ECcQueueBufferRaio4 OBJECT-TYPE
       SYNTAX Integer32 (0..100)
       MAX-ACCESS read-write
       STATUS current
       DESCRIPTION
           "Indicates the buffer size ratio of queue 4.
            Range: 0-100
           "
       ::= { hwE2ECcEntry 6 }

    hwE2ECcQueueBufferRaio5 OBJECT-TYPE
       SYNTAX Integer32 (0..100)
       MAX-ACCESS read-write
       STATUS current
       DESCRIPTION
           "Indicates the buffer size ratio of queue 5.
            Range: 0-100
           "
       ::= { hwE2ECcEntry 7 }

    hwE2ECcQueueBufferRaio6 OBJECT-TYPE
       SYNTAX Integer32 (0..100)
       MAX-ACCESS read-write
       STATUS current
       DESCRIPTION
           "Indicates the buffer size ratio of queue 6.
            Range: 0-100
           "
       ::= { hwE2ECcEntry 8 }

    hwE2ECcQueueBufferRaio7 OBJECT-TYPE
       SYNTAX Integer32 (0..100)
       MAX-ACCESS read-write
       STATUS current
       DESCRIPTION
           "Indicates the buffer size ratio of queue 7.
            Range: 0-100
           "
       ::= { hwE2ECcEntry 9 }

    hwE2ECcQueueBufferRaio8 OBJECT-TYPE
       SYNTAX Integer32 (0..100)
       MAX-ACCESS read-write
       STATUS current
       DESCRIPTION
           "Indicates the buffer size ratio of queue 8.
            Range: 0-100
           "
       ::= { hwE2ECcEntry 10 }

    hwE2ECcQueueBufferRaio9 OBJECT-TYPE
       SYNTAX Integer32 (0..100)
       MAX-ACCESS read-write
       STATUS current
       DESCRIPTION
           "Indicates the buffer size ratio of queue 9.
            Range: 0-100
           "
       ::= { hwE2ECcEntry 11 }

    hwE2ECcQueueBufferRaio10 OBJECT-TYPE
       SYNTAX Integer32 (0..100)
       MAX-ACCESS read-write
       STATUS current
       DESCRIPTION
           "Indicates the buffer size ratio of queue 10.
            Range: 0-100
           "
       ::= { hwE2ECcEntry 12 }

    hwE2ECcQueueBufferRaio11 OBJECT-TYPE
       SYNTAX Integer32 (0..100)
       MAX-ACCESS read-write
       STATUS current
       DESCRIPTION
           "Indicates the buffer size ratio of queue 11.
            Range: 0-100
           "
       ::= { hwE2ECcEntry 13 }

    hwE2ECcQueueBufferRaio12 OBJECT-TYPE
       SYNTAX Integer32 (0..100)
       MAX-ACCESS read-write
       STATUS current
       DESCRIPTION
           "Indicates the buffer size ratio of queue 12.
            Range: 0-100
           "
       ::= { hwE2ECcEntry 14 }

    hwE2ECcQueueBufferRaio13 OBJECT-TYPE
       SYNTAX Integer32 (0..100)
       MAX-ACCESS read-write
       STATUS current
       DESCRIPTION
           "Indicates the buffer size ratio of queue 13.
            Range: 0-100
           "
       ::= { hwE2ECcEntry 15 }

    hwE2ECcQueueBufferRaio14 OBJECT-TYPE
       SYNTAX Integer32 (0..100)
       MAX-ACCESS read-write
       STATUS current
       DESCRIPTION
           "Indicates the buffer size ratio of queue 14.
            Range: 0-100
           "
       ::= { hwE2ECcEntry 16 }

    hwE2ECcQueueBufferRaio15 OBJECT-TYPE
       SYNTAX Integer32 (0..100)
       MAX-ACCESS read-write
       STATUS current
       DESCRIPTION
           "Indicates the buffer size ratio of queue 15.
            Range: 0-100
           "
       ::= { hwE2ECcEntry 17 }

-- hwCarThresholdProfileTable
   hwCarThresholdProfileTable OBJECT-TYPE
       SYNTAX SEQUENCE OF HwCarThresholdProfileEntry
       MAX-ACCESS not-accessible
       STATUS current
       DESCRIPTION
           "Indicates the car-threshold profile table.
            It is used to add, query, modify, or delete the car-threshold profile.
            The index of this table is hwCarThresholdProfileIndex."
       ::= { hwExtIpdslam 44 }

  hwCarThresholdProfileEntry OBJECT-TYPE
       SYNTAX HwCarThresholdProfileEntry
       MAX-ACCESS not-accessible
       STATUS current
       DESCRIPTION
           "Indicates the car-threshold profile table.
            It is used to add, query, modify, or delete the car-threshold profile.
            The index of this entry is hwCarThresholdProfileIndex."
       INDEX { hwCarThresholdProfileIndex }
       ::= { hwCarThresholdProfileTable 1 }

   HwCarThresholdProfileEntry ::=
       SEQUENCE {
           hwCarThresholdProfileIndex
               Integer32,
           hwCarThresholdProfileCos0
               Integer32,
           hwCarThresholdProfileCos1
               Integer32,
           hwCarThresholdProfileCos2
               Integer32,
           hwCarThresholdProfileCos3
               Integer32,
           hwCarThresholdProfileCos4
               Integer32,
           hwCarThresholdProfileCos5
               Integer32,
           hwCarThresholdProfileCos6
               Integer32,
           hwCarThresholdProfileCos7
               Integer32,
           hwCarThresholdProfileRowStatus
               RowStatus
        }

   hwCarThresholdProfileIndex OBJECT-TYPE
       SYNTAX Integer32 (1..4)
       MAX-ACCESS not-accessible
       STATUS current
       DESCRIPTION
           "Indicates the table index.
            Range: 1-4
           "
       ::= { hwCarThresholdProfileEntry 1 }

   hwCarThresholdProfileCos0 OBJECT-TYPE
       SYNTAX Integer32
       MAX-ACCESS read-write
       STATUS current
       DESCRIPTION
           "Indicates the CAR threshold of the mapping with Cos0.
            Values are as follows:
                     ----------------------------------------------------
                     |  31-24  |  23-16   |  15-8   |      7-0          |
                     ----------------------------------------------------
                     |  flag   |  yellow  |  green  | green-and-yellow  |
                     ----------------------------------------------------
            Bits 0-7: indicate the CAR threshold of yellow and green packets with Cos0.
            Bits 8-15: indicate the CAR threshold of green packets with Cos0.
            Bits 16-23: indicate the CAR threshold of yellow packets with Cos0.
            Bit 24-31: indicate the color of packets whose CAR threshold is to be modified.
                       0: indicates that the CAR threshold of both yellow and green packets are modified (bits 0-7).
                       1: indicates that the CAR threshold of yellow and green packets are modified respectively
                          (bits 8-15 for green packets and bits 16-23 for yellow packets).
            Other values are invalid.

            Default: 100
            "
       ::= { hwCarThresholdProfileEntry 2 }

   hwCarThresholdProfileCos1 OBJECT-TYPE
       SYNTAX Integer32
       MAX-ACCESS read-write
       STATUS current
       DESCRIPTION
           "Indicates the CAR threshold of the mapping with Cos1.
            Values are as follows:
                     ----------------------------------------------------
                     |  31-24  |  23-16   |  15-8   |      7-0          |
                     ----------------------------------------------------
                     |  flag   |  yellow  |  green  | green-and-yellow  |
                     ----------------------------------------------------
            Bits 0-7: indicate the CAR threshold of yellow and green packets with Cos1.
            Bits 8-15: indicate the CAR threshold of green packets with Cos1.
            Bits 16-23: indicate the CAR threshold of yellow packets with Cos1.
            Bit 24-31: indicate the color of packets whose CAR threshold is to be modified.
                       0: indicates that the CAR threshold of both yellow and green packets are modified (bits 0-7).
                       1: indicates that the CAR threshold of yellow and green packets are modified respectively
                          (bits 8-15 for green packets and bits 16-23 for yellow packets).
            Other values are invalid.

            Default: 100
            "
       ::= { hwCarThresholdProfileEntry 3 }

   hwCarThresholdProfileCos2 OBJECT-TYPE
       SYNTAX Integer32
       MAX-ACCESS read-write
       STATUS current
       DESCRIPTION
           "Indicates the CAR threshold of the mapping with Cos2.
            Values are as follows:
                     ----------------------------------------------------
                     |  31-24  |  23-16   |  15-8   |      7-0          |
                     ----------------------------------------------------
                     |  flag   |  yellow  |  green  | green-and-yellow  |
                     ----------------------------------------------------
            Bits 0-7: indicate the CAR threshold of yellow and green packets with Cos2.
            Bits 8-15: indicate the CAR threshold of green packets with Cos2.
            Bits 16-23: indicate the CAR threshold of yellow packets with Cos2.
            Bit 24-31: indicate the color of packets whose CAR threshold is to be modified.
                       0: indicates that the CAR threshold of both yellow and green packets are modified (bits 0-7).
                       1: indicates that the CAR threshold of yellow and green packets are modified respectively
                          (bits 8-15 for green packets and bits 16-23 for yellow packets).
            Other values are invalid.

            Default: 100
            "
       ::= { hwCarThresholdProfileEntry 4 }

   hwCarThresholdProfileCos3 OBJECT-TYPE
       SYNTAX Integer32
       MAX-ACCESS read-write
       STATUS current
       DESCRIPTION
           "Indicates the CAR threshold of the mapping with Cos3.
            Values are as follows:
                     ----------------------------------------------------
                     |  31-24  |  23-16   |  15-8   |      7-0          |
                     ----------------------------------------------------
                     |  flag   |  yellow  |  green  | green-and-yellow  |
                     ----------------------------------------------------
            Bits 0-7: indicate the CAR threshold of yellow and green packets with Cos3.
            Bits 8-15: indicate the CAR threshold of green packets with Cos3.
            Bits 16-23: indicate the CAR threshold of yellow packets with Cos3.
            Bit 24-31: indicate the color of packets whose CAR threshold is to be modified.
                       0: indicates that the CAR threshold of both yellow and green packets are modified (bits 0-7).
                       1: indicates that the CAR threshold of yellow and green packets are modified respectively
                          (bits 8-15 for green packets and bits 16-23 for yellow packets).
            Other values are invalid.

            Default: 100
            "
       ::= { hwCarThresholdProfileEntry 5 }

   hwCarThresholdProfileCos4 OBJECT-TYPE
       SYNTAX Integer32
       MAX-ACCESS read-write
       STATUS current
       DESCRIPTION
           "Indicates the CAR threshold of the mapping with Cos4.
            Values are as follows:
                     ----------------------------------------------------
                     |  31-24  |  23-16   |  15-8   |      7-0          |
                     ----------------------------------------------------
                     |  flag   |  yellow  |  green  | green-and-yellow  |
                     ----------------------------------------------------
            Bits 0-7: indicate the CAR threshold of yellow and green packets with Cos4.
            Bits 8-15: indicate the CAR threshold of green packets with Cos4.
            Bits 16-23: indicate the CAR threshold of yellow packets with Cos4.
            Bit 24-31: indicate the color of packets whose CAR threshold is to be modified.
                       0: indicates that the CAR threshold of both yellow and green packets are modified (bits 0-7).
                       1: indicates that the CAR threshold of yellow and green packets are modified respectively
                          (bits 8-15 for green packets and bits 16-23 for yellow packets).
            Other values are invalid.

            Default: 100
            "
       ::= { hwCarThresholdProfileEntry 6 }

   hwCarThresholdProfileCos5 OBJECT-TYPE
       SYNTAX Integer32
       MAX-ACCESS read-write
       STATUS current
       DESCRIPTION
           "Indicates the CAR threshold of the mapping with Cos5.
            Values are as follows:
                     ----------------------------------------------------
                     |  31-24  |  23-16   |  15-8   |      7-0          |
                     ----------------------------------------------------
                     |  flag   |  yellow  |  green  | green-and-yellow  |
                     ----------------------------------------------------
            Bits 0-7: indicate the CAR threshold of yellow and green packets with Cos5.
            Bits 8-15: indicate the CAR threshold of green packets with Cos5.
            Bits 16-23: indicate the CAR threshold of yellow packets with Cos5.
            Bit 24-31: indicate the color of packets whose CAR threshold is to be modified.
                       0: indicates that the CAR threshold of both yellow and green packets are modified (bits 0-7).
                       1: indicates that the CAR threshold of yellow and green packets are modified respectively
                          (bits 8-15 for green packets and bits 16-23 for yellow packets).
            Other values are invalid.

            Default: 100
            "
       ::= { hwCarThresholdProfileEntry 7 }

   hwCarThresholdProfileCos6 OBJECT-TYPE
       SYNTAX Integer32
       MAX-ACCESS read-write
       STATUS current
       DESCRIPTION
           "Indicates the CAR threshold of the mapping with Cos6.
            Values are as follows:
                     ----------------------------------------------------
                     |  31-24  |  23-16   |  15-8   |      7-0          |
                     ----------------------------------------------------
                     |  flag   |  yellow  |  green  | green-and-yellow  |
                     ----------------------------------------------------
            Bits 0-7: indicate the CAR threshold of yellow and green packets with Cos6.
            Bits 8-15: indicate the CAR threshold of green packets with Cos6.
            Bits 16-23: indicate the CAR threshold of yellow packets with Cos6.
            Bit 24-31: indicate the color of packets whose CAR threshold is to be modified.
                       0: indicates that the CAR threshold of both yellow and green packets are modified (bits 0-7).
                       1: indicates that the CAR threshold of yellow and green packets are modified respectively
                          (bits 8-15 for green packets and bits 16-23 for yellow packets).
            Other values are invalid.

            Default: 100
            "
       ::= { hwCarThresholdProfileEntry 8 }

   hwCarThresholdProfileCos7 OBJECT-TYPE
       SYNTAX Integer32
       MAX-ACCESS read-write
       STATUS current
       DESCRIPTION
           "Indicates the CAR threshold of the mapping with Cos7.
            Values are as follows:
                     ----------------------------------------------------
                     |  31-24  |  23-16   |  15-8   |      7-0          |
                     ----------------------------------------------------
                     |  flag   |  yellow  |  green  | green-and-yellow  |
                     ----------------------------------------------------
            Bits 0-7: indicate the CAR threshold of yellow and green packets with Cos7.
            Bits 8-15: indicate the CAR threshold of green packets with Cos7.
            Bits 16-23: indicate the CAR threshold of yellow packets with Cos7.
            Bit 24-31: indicate the color of packets whose CAR threshold is to be modified.
                       0: indicates that the CAR threshold of both yellow and green packets are modified (bits 0-7).
                       1: indicates that the CAR threshold of yellow and green packets are modified respectively
                          (bits 8-15 for green packets and bits 16-23 for yellow packets).
            Other values are invalid.

            Default: 100
            "
       ::= { hwCarThresholdProfileEntry 9 }

   hwCarThresholdProfileRowStatus OBJECT-TYPE
       SYNTAX RowStatus
       MAX-ACCESS read-create
       STATUS current
       DESCRIPTION
           "Indicates the row status, used for creating or deleting a car-threshold profile.
            Options:
            1. active(1)
            2. createAndGo(4)
            3. destroy(6)
            To create a car-threshold profile, you must specify hwCarThresholdProfileIndex and set
            hwCarThresholdProfileRowStatus to createAndGo(4) to perform the set operation.
            Other attributes of the car-threshold profile are optional.
            To delete a car-threshold profile, set hwCarThresholdProfileRowStatus to destroy(6) to
            perform the set operation.
            During query, the value of this leaf is the fixed active(1)."
       ::= { hwCarThresholdProfileEntry 10 }

   hwTrafficLimitOntMode OBJECT-TYPE
       SYNTAX INTEGER
           {
           shaping(1),
           car(2)
           }
       MAX-ACCESS read-write
       STATUS current
       DESCRIPTION
           "Indicates the mode of ONT Traffic limit.
            Options:
            1. shaping(1)  -indicates the mode of ONT Traffic limit is shaping
            2. car(2) -indicates the mode of ONT Traffic limit is CAR
            Default: shaping(1)
           "
       ::= { hwExtIpdslam 45 }

-- hwQosPolicyProfileTable
   hwQosPolicyProfileTable OBJECT-TYPE
       SYNTAX SEQUENCE OF HwQosPolicyProfileEntry
       MAX-ACCESS not-accessible
       STATUS current
       DESCRIPTION
           "Describes the attributes of a QoS policy profile, used for adding or deleting
            a QoS policy profile, or modifying the status of the attributes in an existing
            QoS policy profile.
            The index of this table is hwQosPolicyProfileName.
           "
       ::= { hwExtIpdslam 46 }

   hwQosPolicyProfileEntry OBJECT-TYPE
       SYNTAX HwQosPolicyProfileEntry
       MAX-ACCESS not-accessible
       STATUS current
       DESCRIPTION
           "Describes the attributes of a QoS policy profile, used for adding or deleting
            a QoS policy profile, or modifying the status of the attributes in an existing
            QoS policy profile.
            The index of this entry is hwQosPolicyProfileName.
           "
       INDEX { hwQosPolicyProfileName }
       ::= { hwQosPolicyProfileTable 1 }

   HwQosPolicyProfileEntry ::=
       SEQUENCE {
           hwQosPolicyProfileName
                  OCTET STRING,
           hwProfileCosQueueMappingMask
                  Unsigned32,
           hwProfileCosQueueSchedMode
                  INTEGER,
           hwProfileCosQueueWeightQue0
                  Integer32,
           hwProfileCosQueueWeightQue1
                  Integer32,
           hwProfileCosQueueWeightQue2
                  Integer32,
           hwProfileCosQueueWeightQue3
                  Integer32,
           hwProfileCosQueueWeightQue4
                  Integer32,
           hwProfileCosQueueWeightQue5
                  Integer32,
           hwProfileCosQueueWeightQue6
                  Integer32,
           hwProfileCosQueueWeightQue7
                  Integer32,
           hwProfileCosQueueDepthRateQue0
                  Integer32,
           hwProfileCosQueueDepthRateQue1
                  Integer32,
           hwProfileCosQueueDepthRateQue2
                  Integer32,
           hwProfileCosQueueDepthRateQue3
                  Integer32,
           hwProfileCosQueueDepthRateQue4
                  Integer32,
           hwProfileCosQueueDepthRateQue5
                  Integer32,
           hwProfileCosQueueDepthRateQue6
                  Integer32,
           hwProfileCosQueueDepthRateQue7
                  Integer32,
           hwProfileCosQueueWREDIndexQue0
                  Integer32,
           hwProfileCosQueueWREDIndexQue1
                  Integer32,
           hwProfileCosQueueWREDIndexQue2
                  Integer32,
           hwProfileCosQueueWREDIndexQue3
                  Integer32,
           hwProfileCosQueueWREDIndexQue4
                  Integer32,
           hwProfileCosQueueWREDIndexQue5
                  Integer32,
           hwProfileCosQueueWREDIndexQue6
                  Integer32,
           hwProfileCosQueueWREDIndexQue7
                  Integer32,
           hwProfileCosQueueMaxBufferSizeQueue0
                  Integer32,
           hwProfileCosQueueMaxBufferSizeQueue1
                  Integer32,
           hwProfileCosQueueMaxBufferSizeQueue2
                  Integer32,
           hwProfileCosQueueMaxBufferSizeQueue3
                  Integer32,
           hwProfileCosQueueMaxBufferSizeQueue4
                  Integer32,
           hwProfileCosQueueMaxBufferSizeQueue5
                  Integer32,
           hwProfileCosQueueMaxBufferSizeQueue6
                  Integer32,
           hwProfileCosQueueMaxBufferSizeQueue7
                  Integer32,
           hwQosPolicyProfileRowStatus
                  RowStatus
        }

   hwQosPolicyProfileName OBJECT-TYPE
       SYNTAX OCTET STRING (SIZE (1..32))
       MAX-ACCESS not-accessible
       STATUS current
       DESCRIPTION
           "Indicates the name of the QoS policy profile.
            Range: a string of 1-32 characters
            The input index consists of the QoS policy profile name and
            the length of the QoS policy profile name.
            The input QoS policy profile name must be ASCII codes.
            Assume that you need to create a huawei QoS policy profile.
            Because the ASCII value of huawei is 104.117.97.119.101.105 and
            the length of huawei is 6, the index is 6.104.117.97.119.101.105.
           "
       ::= { hwQosPolicyProfileEntry 1 }

   hwProfileCosQueueMappingMask OBJECT-TYPE
       SYNTAX Unsigned32
       MAX-ACCESS read-write
       STATUS current
       DESCRIPTION
           "As a table leaf node, describes the mapping between 802.1p priority and queue.

            The queue ID is 0-7. Every four bits represents the queue ID to which an 802.1p priority corresponds.
            When hwProfileCosQueueMappingMask is set to 0xffffffff(4294967295), it means restoring it to default settings.

            The default mapping is as follows: Packets with priority 7 join queue 7, packets with priority 6 join queue 6, and so on.
            The corresponding bits are:
            0111 0110 0101 0100 0011 0010 0001 0000
               7    6    5    4    3    2    1    0
            Default: 1985229328
           "
       ::= { hwQosPolicyProfileEntry 2 }

   hwProfileCosQueueSchedMode OBJECT-TYPE
       SYNTAX INTEGER
           {
               strictPriority(1),
               wrr(2),
               wfq(3)
           }
       MAX-ACCESS read-write
       STATUS current
       DESCRIPTION
           "Indicates the queue scheduling mode.
            Options:
            1. strictPriority(1) -PQ
            2. wrr(2) -WRR
            3. wfq(3) -WFQ

            In the case of PQ scheduling, PQ takes out all packets from a queue with a high priority and transmits them.
            After such a transmission is completed, PQ performs the same on all packets in a queue with an
            intermediate priority,
            a queue with a normal priority, and a queue with a low priority one by one.
            In this way, packets in a queue with the highest priority precede packets in a queue with a less higher
            priority and therefore are processed preferentially, even in case of congestion.
            This ensures that packets for key services are processed first.

            WRR and WFQ are of weighted scheduling type.
            Unlike WRR, WFQ scheduling is based on byte quantity rather than packet quantity. This requires more
       precise weight assignment.
           "
       ::= { hwQosPolicyProfileEntry 3 }

   hwProfileCosQueueWeightQue0 OBJECT-TYPE
       SYNTAX Integer32(0..100)
       MAX-ACCESS read-write
       STATUS current
       DESCRIPTION
          "Indicates the weight of queue 0.
           Range: 0-100
           When modifying the weight of queue 0, if the queue schedule mode is wrr, make sure that the sum of weights equals to 100,
           if the queue schedule mode is wfq, make sure that the sum of weights is no bigger than 100.
          "
       ::= { hwQosPolicyProfileEntry 4 }

   hwProfileCosQueueWeightQue1 OBJECT-TYPE
       SYNTAX Integer32(0..100)
       MAX-ACCESS read-write
       STATUS current
       DESCRIPTION
           "Indicates the weight of queue 1.
            Range: 0-100
            When modifying the weight of queue 1, if the queue schedule mode is wrr, make sure that the sum of weights equals to 100,
            if the queue schedule mode is wfq, make sure that the sum of weights is no bigger than 100.
           "
       ::= { hwQosPolicyProfileEntry 5 }

   hwProfileCosQueueWeightQue2 OBJECT-TYPE
       SYNTAX Integer32(0..100)
       MAX-ACCESS read-write
       STATUS current
       DESCRIPTION
           "Indicates the weight of queue 2.
            Range: 0-100
            When modifying the weight of queue 2, if the queue schedule mode is wrr, make sure that the sum of weights equals to 100,
            if the queue schedule mode is wfq, make sure that the sum of weights is no bigger than 100.
           "
       ::= { hwQosPolicyProfileEntry 6 }

   hwProfileCosQueueWeightQue3 OBJECT-TYPE
       SYNTAX Integer32(0..100)
       MAX-ACCESS read-write
       STATUS current
       DESCRIPTION
           "Indicates the weight of queue 3.
            Range: 0-100
            When modifying the weight of queue 3, if the queue schedule mode is wrr, make sure that the sum of weights equals to 100,
            if the queue schedule mode is wfq, make sure that the sum of weights is no bigger than 100.
           "
       ::= { hwQosPolicyProfileEntry 7 }

   hwProfileCosQueueWeightQue4 OBJECT-TYPE
       SYNTAX Integer32(0..100)
       MAX-ACCESS read-write
       STATUS current
       DESCRIPTION
          "Indicates the weight of queue 4.
           Range: 0-100
           When modifying the weight of queue 4, if the queue schedule mode is wrr, make sure that the sum of weights equals to 100,
           if the queue schedule mode is wfq, make sure that the sum of weights is no bigger than 100.
          "
       ::= { hwQosPolicyProfileEntry 8 }

   hwProfileCosQueueWeightQue5 OBJECT-TYPE
       SYNTAX Integer32(0..100)
       MAX-ACCESS read-write
       STATUS current
       DESCRIPTION
           "Indicates the weight of queue 5.
            Range: 0-100
            When modifying the weight of queue 5, if the queue schedule mode is wrr, make sure that the sum of weights equals to 100,
            if the queue schedule mode is wfq, make sure that the sum of weights is no bigger than 100.
           "
       ::= { hwQosPolicyProfileEntry 9 }

   hwProfileCosQueueWeightQue6 OBJECT-TYPE
       SYNTAX Integer32 (0..100)
       MAX-ACCESS read-write
       STATUS current
       DESCRIPTION
           "Indicates the weight of queue 6.
            Range: 0-100
            When modifying the weight of queue 6, if the queue schedule mode is wrr, make sure that the sum of weights equals to 100,
            if the queue schedule mode is wfq, make sure that the sum of weights is no bigger than 100.
           "
       ::= { hwQosPolicyProfileEntry 10 }

   hwProfileCosQueueWeightQue7 OBJECT-TYPE
       SYNTAX Integer32 (0..100)
       MAX-ACCESS read-write
       STATUS current
       DESCRIPTION
           "Indicates the weight of queue 7.
            Range: 0-100
            When modifying the weight of queue 7, if the queue schedule mode is wrr, make sure that the sum of weights equals to 100,
            if the queue schedule mode is wfq, make sure that the sum of weights is no bigger than 100.
           "
       ::= { hwQosPolicyProfileEntry 11 }

   hwProfileCosQueueDepthRateQue0 OBJECT-TYPE
       SYNTAX Integer32 (-1|0..100)
       MAX-ACCESS read-write
       STATUS current
       DESCRIPTION
           "Indicates the depth rate of queue 0.
            Range: 0-100, -1
            The larger the percentage, the more packets can be buffered. The sum of percentages must be 100%.
            When the percentages are restored to invalid settings, -1 as a unified queue depth is issued for eight queues.
            When setting the queue depth, enter at least 7 queues (0-6). The eighth queue depth is automatically calculated.
            Value range for each queue is 0-100.
           "
       ::= { hwQosPolicyProfileEntry 12 }

   hwProfileCosQueueDepthRateQue1 OBJECT-TYPE
       SYNTAX Integer32 (-1|0..100)
       MAX-ACCESS read-write
       STATUS current
       DESCRIPTION
           "Indicates the depth rate of queue 1.
            Range: 0-100, -1
            The larger the percentage, the more packets can be buffered. The sum of percentages must be 100%.
            When the percentages are restored to invalid settings, -1 as a unified queue depth is issued for eight queues.
            When setting the queue depth, enter at least 7 queues (0-6). The eighth queue depth is automatically calculated.
            Value range for each queue is 0-100.
           "
       ::= { hwQosPolicyProfileEntry 13 }

   hwProfileCosQueueDepthRateQue2 OBJECT-TYPE
       SYNTAX Integer32 (-1|0..100)
       MAX-ACCESS read-write
       STATUS current
       DESCRIPTION
           "Indicates the depth rate of queue 2.
            Range: 0-100, -1
            The larger the percentage, the more packets can be buffered. The sum of percentages must be 100%.
            When the percentages are restored to invalid settings, -1 as a unified queue depth is issued for eight queues.
            When setting the queue depth, enter at least 7 queues (0-6). The eighth queue depth is automatically calculated.
            Value range for each queue is 0-100.
           "
       ::= { hwQosPolicyProfileEntry 14 }

   hwProfileCosQueueDepthRateQue3 OBJECT-TYPE
       SYNTAX Integer32 (-1|0..100)
       MAX-ACCESS read-write
       STATUS current
       DESCRIPTION
           "Indicates the depth rate of queue 3.
            Range: 0-100, -1
            The larger the percentage, the more packets can be buffered. The sum of percentages must be 100%.
            When the percentages are restored to invalid settings, -1 as a unified queue depth is issued for eight queues.
            When setting the queue depth, enter at least 7 queues (0-6). The eighth queue depth is automatically calculated.
            Value range for each queue is 0-100.
           "
       ::= { hwQosPolicyProfileEntry 15 }

   hwProfileCosQueueDepthRateQue4 OBJECT-TYPE
       SYNTAX Integer32 (-1|0..100)
       MAX-ACCESS read-write
       STATUS current
       DESCRIPTION
           "Indicates the depth rate of queue 4.
            Range: 0-100, -1
            The larger the percentage, the more packets can be buffered. The sum of percentages must be 100%.
            When the percentages are restored to invalid settings, -1 as a unified queue depth is issued for eight queues.
            When setting the queue depth, enter at least 7 queues (0-6). The eighth queue depth is automatically calculated.
            Value range for each queue is 0-100.
           "
       ::= { hwQosPolicyProfileEntry 16 }

   hwProfileCosQueueDepthRateQue5 OBJECT-TYPE
       SYNTAX Integer32 (-1|0..100)
       MAX-ACCESS read-write
       STATUS current
       DESCRIPTION
           "Indicates the depth rate of queue 5.
            Range: 0-100, -1
            The larger the percentage, the more packets can be buffered. The sum of percentages must be 100%.
            When the percentages are restored to invalid settings, -1 as a unified queue depth is issued for eight queues.
            When setting the queue depth, enter at least 7 queues (0-6). The eighth queue depth is automatically calculated.
            Value range for each queue is 0-100.
           "
       ::= { hwQosPolicyProfileEntry 17 }

   hwProfileCosQueueDepthRateQue6 OBJECT-TYPE
       SYNTAX Integer32 (-1|0..100)
       MAX-ACCESS read-write
       STATUS current
       DESCRIPTION
           "Indicates the depth rate of queue 6.
            Range: 0-100, -1
            The larger the percentage, the more packets can be buffered. The sum of percentages must be 100%.
            When the percentages are restored to invalid settings, -1 as a unified queue depth is issued for eight queues.
            When setting the queue depth, enter at least 7 queues (0-6). The eighth queue depth is automatically calculated.
            Value range for each queue is 0-100.
           "
       ::= { hwQosPolicyProfileEntry 18 }

   hwProfileCosQueueDepthRateQue7 OBJECT-TYPE
       SYNTAX Integer32 (-1|0..100)
       MAX-ACCESS read-write
       STATUS current
       DESCRIPTION
           "Indicates the depth rate of queue 7.
            Range: 0-100, -1
            The larger the percentage, the more packets can be buffered. The sum of percentages must be 100%.
            When the percentages are restored to invalid settings, -1 as a unified queue depth is issued for eight queues.
            When setting the queue depth, enter at least 7 queues (0-6). The eighth queue depth is automatically calculated.
            Value range for each queue is 0-100.
           "
       ::= { hwQosPolicyProfileEntry 19 }

   hwProfileCosQueueWREDIndexQue0 OBJECT-TYPE
       SYNTAX Integer32
       MAX-ACCESS read-write
       STATUS current
       DESCRIPTION
           "Indicates the index of a WRED profile to be bound of queue 0.
            Make sure that the WRED profile be already created in hwWREDTable and the WRED profile information be complete
            (that is, including the early drop information).
            At the same time, to bind queues to a WRED profile, make sure that hwEarlyDropMode be colorBase(2).

            -1 indicates that the binding between queues and a WRED profile is removed.
            Default: -1.
           "
       ::= { hwQosPolicyProfileEntry 20 }

   hwProfileCosQueueWREDIndexQue1 OBJECT-TYPE
       SYNTAX Integer32
       MAX-ACCESS read-write
       STATUS current
       DESCRIPTION
           "Indicates the index of a WRED profile to be bound of queue 1.
            Make sure that the WRED profile be already created in hwWREDTable and the WRED profile information be complete
            (that is, including the early drop information).
            At the same time, to bind queues to a WRED profile, make sure that hwEarlyDropMode be colorBase(2).

            -1 indicates that the binding between queues and a WRED profile is removed.
            Default: -1.
           "
       ::= { hwQosPolicyProfileEntry 21 }

   hwProfileCosQueueWREDIndexQue2 OBJECT-TYPE
       SYNTAX Integer32
       MAX-ACCESS read-write
       STATUS current
       DESCRIPTION
           "Indicates the index of a WRED profile to be bound of queue 2.
            Make sure that the WRED profile be already created in hwWREDTable and the WRED profile information be complete
            (that is, including the early drop information).
            At the same time, to bind queues to a WRED profile, make sure that hwEarlyDropMode be colorBase(2).

            -1 indicates that the binding between queues and a WRED profile is removed.
            Default: -1.
           "
       ::= { hwQosPolicyProfileEntry 22 }

   hwProfileCosQueueWREDIndexQue3 OBJECT-TYPE
       SYNTAX Integer32
       MAX-ACCESS read-write
       STATUS current
       DESCRIPTION
           "Indicates the index of a WRED profile to be bound of queue 3.
            Make sure that the WRED profile be already created in hwWREDTable and the WRED profile information be complete
            (that is, including the early drop information).
            At the same time, to bind queues to a WRED profile, make sure that hwEarlyDropMode be colorBase(2).

            -1 indicates that the binding between queues and a WRED profile is removed.
            Default: -1.
           "
       ::= { hwQosPolicyProfileEntry 23 }

   hwProfileCosQueueWREDIndexQue4 OBJECT-TYPE
       SYNTAX Integer32
       MAX-ACCESS read-write
       STATUS current
       DESCRIPTION
           "Indicates the index of a WRED profile to be bound of queue 4.
            Make sure that the WRED profile be already created in hwWREDTable and the WRED profile information be complete
            (that is, including the early drop information).
            At the same time, to bind queues to a WRED profile, make sure that hwEarlyDropMode be colorBase(2).

            -1 indicates that the binding between queues and a WRED profile is removed.
            Default: -1.
           "
       ::= { hwQosPolicyProfileEntry 24 }

   hwProfileCosQueueWREDIndexQue5 OBJECT-TYPE
       SYNTAX Integer32
       MAX-ACCESS read-write
       STATUS current
       DESCRIPTION
           "Indicates the index of a WRED profile to be bound of queue 5.
            Make sure that the WRED profile be already created in hwWREDTable and the WRED profile information be complete
            (that is, including the early drop information).
            At the same time, to bind queues to a WRED profile, make sure that hwEarlyDropMode be colorBase(2).

            -1 indicates that the binding between queues and a WRED profile is removed.
            Default: -1.
           "
       ::= { hwQosPolicyProfileEntry 25 }

   hwProfileCosQueueWREDIndexQue6 OBJECT-TYPE
       SYNTAX Integer32
       MAX-ACCESS read-write
       STATUS current
       DESCRIPTION
           "Indicates the index of a WRED profile to be bound of queue 6.
            Make sure that the WRED profile be already created in hwWREDTable and the WRED profile information be complete
            (that is, including the early drop information).
            At the same time, to bind queues to a WRED profile, make sure that hwEarlyDropMode be colorBase(2).

            -1 indicates that the binding between queues and a WRED profile is removed.
            Default: -1.
           "
       ::= { hwQosPolicyProfileEntry 26 }

   hwProfileCosQueueWREDIndexQue7 OBJECT-TYPE
       SYNTAX Integer32
       MAX-ACCESS read-write
       STATUS current
       DESCRIPTION
           "Indicates the index of a WRED profile to be bound of queue 7.
            Make sure that the WRED profile be already created in hwWREDTable and the WRED profile information be complete
            (that is, including the early drop information).
            At the same time, to bind queues to a WRED profile, make sure that hwEarlyDropMode be colorBase(2).

            -1 indicates that the binding between queues and a WRED profile is removed.
            Default: -1.
           "
       ::= { hwQosPolicyProfileEntry 27 }

   hwProfileCosQueueMaxBufferSizeQueue0 OBJECT-TYPE
       SYNTAX Integer32 (-1|32..8192)
       MAX-ACCESS read-write
       STATUS current
       DESCRIPTION
           "Indicates the maximum depth of queue 0.
            Range: 32-8192.
            Default value: -1, indicating that the maximum depth of queue 0 is not configured.
           "
       ::= { hwQosPolicyProfileEntry 28 }

   hwProfileCosQueueMaxBufferSizeQueue1 OBJECT-TYPE
       SYNTAX Integer32 (-1|32..8192)
       MAX-ACCESS read-write
       STATUS current
       DESCRIPTION
           "Indicates the maximum depth of queue 1.
            Range: 32-8192.
            Default value: -1, indicating that the maximum depth of queue 1 is not configured.
           "
       ::= { hwQosPolicyProfileEntry 29 }

   hwProfileCosQueueMaxBufferSizeQueue2 OBJECT-TYPE
       SYNTAX Integer32 (-1|32..8192)
       MAX-ACCESS read-write
       STATUS current
       DESCRIPTION
           "Indicates the maximum depth of queue 2.
            Range: 32-8192.
            Default value: -1, indicating that the maximum depth of queue 2 is not configured.
           "
       ::= { hwQosPolicyProfileEntry 30 }

   hwProfileCosQueueMaxBufferSizeQueue3 OBJECT-TYPE
       SYNTAX Integer32 (-1|32..8192)
       MAX-ACCESS read-write
       STATUS current
       DESCRIPTION
           "Indicates the maximum depth of queue 3.
            Range: 32-8192.
            Default value: -1, indicating that the maximum depth of queue 3 is not configured.
           "
       ::= { hwQosPolicyProfileEntry 31 }

   hwProfileCosQueueMaxBufferSizeQueue4 OBJECT-TYPE
       SYNTAX Integer32 (-1|32..8192)
       MAX-ACCESS read-write
       STATUS current
       DESCRIPTION
           "Indicates the maximum depth of queue 4.
            Range: 32-8192.
            Default value: -1, indicating that the maximum depth of queue 4 is not configured.
           "
       ::= { hwQosPolicyProfileEntry 32 }

   hwProfileCosQueueMaxBufferSizeQueue5 OBJECT-TYPE
       SYNTAX Integer32 (-1|32..8192)
       MAX-ACCESS read-write
       STATUS current
       DESCRIPTION
           "Indicates the maximum depth of queue 5.
            Range: 32-8192.
            Default value: -1, indicating that the maximum depth of queue 5 is not configured.
           "
       ::= { hwQosPolicyProfileEntry 33 }

   hwProfileCosQueueMaxBufferSizeQueue6 OBJECT-TYPE
       SYNTAX Integer32 (-1|32..8192)
       MAX-ACCESS read-write
       STATUS current
       DESCRIPTION
           "Indicates the maximum depth of queue 6.
            Range: 32-8192.
            Default value: -1, indicating that the maximum depth of queue 6 is not configured.
           "
       ::= { hwQosPolicyProfileEntry 34 }

   hwProfileCosQueueMaxBufferSizeQueue7 OBJECT-TYPE
       SYNTAX Integer32 (-1|32..8192)
       MAX-ACCESS read-write
       STATUS current
       DESCRIPTION
           "Indicates the maximum depth of queue 7.
            Range: 32-8192.
            Default value: -1, indicating that the maximum depth of queue 7 is not configured.
           "
       ::= { hwQosPolicyProfileEntry 35 }

   hwQosPolicyProfileRowStatus   OBJECT-TYPE
       SYNTAX RowStatus
       MAX-ACCESS read-create
       STATUS current
       DESCRIPTION
           "Indicates the row status, used for creating or deleting a Qos policy profile.
            Options:
            1. active(1)
            2. createAndGo(4)
            3. destroy(6)
            To create a Qos policy profile, set hwQosPolicyProfileRowStatus to createAndGo(4)
            to perform the set operation. The other leaves are optional.
            To delete a Qos policy profile, set hwQosPolicyProfileRowStatus to
            destroy(6) to perform the set operation.
            To modify a Qos policy profile, you need not specify hwQosPolicyProfileRowStatus,
            but perform the set operation directly on the leaf of the
            corresponding attribute to be modified.
            During query, the value of this leaf is the fixed active(1).
           "
       ::= { hwQosPolicyProfileEntry 255 }

-- hwPortBindQosPolicyProfileTable
   hwPortBindQosPolicyProfileTable OBJECT-TYPE
       SYNTAX SEQUENCE OF HwPortBindQosPolicyProfileEntry
       MAX-ACCESS not-accessible
       STATUS current
       DESCRIPTION
           "This table is used for binding or unbinding a QoS policy profile to one port.
            The index of this table is ifIndex, hwPortBindQosPolicyProfileSecondIndex, hwPortBindQosPolicyProfileThirdIndex.
           "
       ::= { hwExtIpdslam 47 }

   hwPortBindQosPolicyProfileEntry OBJECT-TYPE
       SYNTAX HwPortBindQosPolicyProfileEntry
       MAX-ACCESS not-accessible
       STATUS current
       DESCRIPTION
           "This table is used for binding or unbinding a QoS policy profile to one port .
            The index of this entry is ifIndex, hwPortBindQosPolicyProfileSecondIndex, hwPortBindQosPolicyProfileThirdIndex.
           "
       INDEX { ifIndex, hwPortBindQosPolicyProfileSecondIndex, hwPortBindQosPolicyProfileThirdIndex }
       ::= { hwPortBindQosPolicyProfileTable 1 }

   HwPortBindQosPolicyProfileEntry ::=
       SEQUENCE {
           hwPortBindQosPolicyProfileSecondIndex
               Integer32,
           hwPortBindQosPolicyProfileThirdIndex
               Integer32,
           hwPortBindQosPolicyProfileName
               OCTET STRING,
           hwPortBindInboundQosPolicyProfileName
               OCTET STRING
        }

   hwPortBindQosPolicyProfileSecondIndex OBJECT-TYPE
       SYNTAX Integer32
       MAX-ACCESS not-accessible
       STATUS current
       DESCRIPTION
           "Reserved index, an invalid value needs to be input for this leaf.
            The invalid value is defined as -1.
           "
       ::= { hwPortBindQosPolicyProfileEntry 1 }

   hwPortBindQosPolicyProfileThirdIndex OBJECT-TYPE
       SYNTAX Integer32
       MAX-ACCESS not-accessible
       STATUS current
       DESCRIPTION
           "Reserved index, an invalid value needs to be input for this leaf.
            The invalid value is defined as -1.
           "
       ::= { hwPortBindQosPolicyProfileEntry 2 }

   hwPortBindQosPolicyProfileName OBJECT-TYPE
       SYNTAX OCTET STRING (SIZE (0..32))
       MAX-ACCESS read-write
       STATUS current
       DESCRIPTION
           "Indicates the name of the QoS policy profile bound to a port in the outbound direction.
            Range: a string of 0-32 characters
            This leaf identifies a QoS policy profile, which must be
            created in hwQosPolicyProfileTable. The null character string indicates
            that the binding relation between a port and a QoS policy profile is deleted.
           "
       ::= { hwPortBindQosPolicyProfileEntry 3 }

   hwPortBindInboundQosPolicyProfileName OBJECT-TYPE
       SYNTAX OCTET STRING (SIZE (0..32))
       MAX-ACCESS read-write
       STATUS current
       DESCRIPTION
           "Indicates the name of the QoS policy profile bound to a port in the inbound direction.
            Range: a string of 0-32 characters
            This leaf identifies a QoS policy profile, which must be
            created in hwQosPolicyProfileTable. The null character string indicates
            that the binding relation between a port and a QoS policy profile is deleted.
           "
       ::= { hwPortBindQosPolicyProfileEntry 4 }

   hwMulticastQueuePriority OBJECT-TYPE
       SYNTAX Integer32 (3..7)
       MAX-ACCESS read-write
       STATUS current
       DESCRIPTION
           "Indicates the priority of multicast service queue.
           "
       ::= { hwExtIpdslam 48 }

    -- hwEarlyDropPriBaseMappingTable
    hwEarlyDropPriBaseMappingTable OBJECT IDENTIFIER ::= { hwExtIpdslam 49 }

    hwEarlyDropPriBaseMappingCos0 OBJECT-TYPE
        SYNTAX INTEGER
            {
            class0(1),
            class1(2),
            class2(3)
            }
        MAX-ACCESS read-write
        STATUS current
        DESCRIPTION
            "Indicates the pri-base early-drop mapping of cos0.
            Options:
            1. class0(1) -indicates class 0 of early-drop
            2. class1(2) -indicates class 1 of early-drop
            3. class2(3) -indicates class 2 of early-drop
            Default: class0(1)
           "
        ::= { hwEarlyDropPriBaseMappingTable 1 }

    hwEarlyDropPriBaseMappingCos1 OBJECT-TYPE
        SYNTAX INTEGER
            {
            class0(1),
            class1(2),
            class2(3)
            }
        MAX-ACCESS read-write
        STATUS current
        DESCRIPTION
            "Indicates the pri-base early-drop mapping of cos1.
            Options:
            1. class0(1) -indicates class 0 of early-drop
            2. class1(2) -indicates class 1 of early-drop
            3. class2(3) -indicates class 2 of early-drop
            Default: class0(1)
           "
        ::= { hwEarlyDropPriBaseMappingTable 2 }

    hwEarlyDropPriBaseMappingCos2 OBJECT-TYPE
        SYNTAX INTEGER
            {
            class0(1),
            class1(2),
            class2(3)
            }
        MAX-ACCESS read-write
        STATUS current
        DESCRIPTION
            "Indicates the pri-base early-drop mapping of cos2.
            Options:
            1. class0(1) -indicates class 0 of early-drop
            2. class1(2) -indicates class 1 of early-drop
            3. class2(3) -indicates class 2 of early-drop
            Default: class0(1)
           "
        ::= { hwEarlyDropPriBaseMappingTable 3 }

    hwEarlyDropPriBaseMappingCos3 OBJECT-TYPE
        SYNTAX INTEGER
            {
            class0(1),
            class1(2),
            class2(3)
            }
        MAX-ACCESS read-write
        STATUS current
        DESCRIPTION
            "Indicates the pri-base early-drop mapping of cos3.
            Options:
            1. class0(1) -indicates class 0 of early-drop
            2. class1(2) -indicates class 1 of early-drop
            3. class2(3) -indicates class 2 of early-drop
            Default: class0(1)
           "
        ::= { hwEarlyDropPriBaseMappingTable 4 }

    hwEarlyDropPriBaseMappingCos4 OBJECT-TYPE
        SYNTAX INTEGER
            {
            class0(1),
            class1(2),
            class2(3)
            }
        MAX-ACCESS read-write
        STATUS current
        DESCRIPTION
            "Indicates the pri-base early-drop mapping of cos4.
            Options:
            1. class0(1) -indicates class 0 of early-drop
            2. class1(2) -indicates class 1 of early-drop
            3. class2(3) -indicates class 2 of early-drop
            Default: class0(1)
           "
        ::= { hwEarlyDropPriBaseMappingTable 5 }

    hwEarlyDropPriBaseMappingCos5 OBJECT-TYPE
        SYNTAX INTEGER
            {
            class0(1),
            class1(2),
            class2(3)
            }
        MAX-ACCESS read-write
        STATUS current
        DESCRIPTION
            "Indicates the pri-base early-drop mapping of cos5.
            Options:
            1. class0(1) -indicates class 0 of early-drop
            2. class1(2) -indicates class 1 of early-drop
            3. class2(3) -indicates class 2 of early-drop
            Default: class0(1)
           "
        ::= { hwEarlyDropPriBaseMappingTable 6 }

    hwEarlyDropPriBaseMappingCos6 OBJECT-TYPE
        SYNTAX INTEGER
            {
            class0(1),
            class1(2),
            class2(3)
            }
        MAX-ACCESS read-write
        STATUS current
        DESCRIPTION
            "Indicates the pri-base early-drop mapping of cos6.
            Options:
            1. class0(1) -indicates class 0 of early-drop
            2. class1(2) -indicates class 1 of early-drop
            3. class2(3) -indicates class 2 of early-drop
            Default: class0(1)
           "
        ::= { hwEarlyDropPriBaseMappingTable 7 }

    hwEarlyDropPriBaseMappingCos7 OBJECT-TYPE
        SYNTAX INTEGER
            {
            class0(1),
            class1(2),
            class2(3)
            }
        MAX-ACCESS read-write
        STATUS current
        DESCRIPTION
            "Indicates the pri-base early-drop mapping of cos7.
            Options:
            1. class0(1) -indicates class 0 of early-drop
            2. class1(2) -indicates class 1 of early-drop
            3. class2(3) -indicates class 2 of early-drop
            Default: class0(1)
           "
        ::= { hwEarlyDropPriBaseMappingTable 8 }

-- hwPortStatisticsExcludeMulticastQueueTable
   hwPortStatisticsExcludeMulticastQueueTable OBJECT-TYPE
       SYNTAX SEQUENCE OF HwPortStatisticsExcludeMulticastQueueEntry
       MAX-ACCESS not-accessible
       STATUS current
       DESCRIPTION
           "This table is used for setting exclude port multicase statistics queue ID.
            The index of this table is hwFrameIndex, hwSlotIndex.
           "
       ::= { hwExtIpdslam 50 }

   hwPortStatisticsExcludeMulticastQueueEntry OBJECT-TYPE
       SYNTAX HwPortStatisticsExcludeMulticastQueueEntry
       MAX-ACCESS not-accessible
       STATUS current
       DESCRIPTION
           "This table is used for setting exclude port multicase statistics queue ID.
            The index of this entry is hwFrameIndex, hwSlotIndex.
           "
       INDEX { hwFrameIndex, hwSlotIndex }
       ::= { hwPortStatisticsExcludeMulticastQueueTable 1 }

   HwPortStatisticsExcludeMulticastQueueEntry ::=
       SEQUENCE {
           hwPortStatisticsExcludeMulticastQueueID
               Integer32
        }

   hwPortStatisticsExcludeMulticastQueueID OBJECT-TYPE
       SYNTAX Integer32 (-1|0..7)
       MAX-ACCESS read-write
       STATUS current
       DESCRIPTION
           "Specify one queue from 0 to 7, port multicast yellow and green packet statistics will exclude the specified queue.
            -1 means not specify multicast statistics queue, port yellow and green packet statistics will include queue from 0 to 7.
            The default queue is 3.
           "
       ::= { hwPortStatisticsExcludeMulticastQueueEntry 1 }

   hwXponPortJumboEnableTable OBJECT-TYPE
       SYNTAX SEQUENCE OF HwXponPortJumboEnableEntry
       MAX-ACCESS not-accessible
       STATUS current
       DESCRIPTION
           "Indicates the jumbo frames configuration table of a xPON port.
            It is used for setting the jumbo frames of a xPON port.
            The index of this table is ifIndex.
           "
       ::= { hwExtIpdslam 51 }

   hwXponPortJumboEnableEntry OBJECT-TYPE
       SYNTAX HwXponPortJumboEnableEntry
       MAX-ACCESS not-accessible
       STATUS current
       DESCRIPTION
           "Indicates the jumbo frames configuration table of a xPON port.
            It is used for setting the jumbo frames of a xPON port.
            The index of this entry is ifIndex.
           "
       INDEX { ifIndex }
       ::= { hwXponPortJumboEnableTable 1 }

   HwXponPortJumboEnableEntry ::=
       SEQUENCE {
         hwXponPortJumboEnable
           INTEGER
        }

   hwXponPortJumboEnable OBJECT-TYPE
       SYNTAX INTEGER
           {
           invalid(-1),
           enabled(1),
           disabled(2)
           }
       MAX-ACCESS read-write
       STATUS current
       DESCRIPTION
           "This object is used to enable or disable jumbo frames.
            When the carriers' servers need to exchange a large amount of data with their devices,
            operate this object to enable jumbo frames.
            After the operation is executed successfully,
            the corresponding port on the control board can transparently transmit the frames whose size is between 1600 bytes and 9216 bytes.
            By default, the xPON port disable jumbo frames.
            Options:
            1. invalid(-1) -invalid
            2. enabled(1)  -enable the jumbo frames
            3. disabled(2) -disabled the jumbo frames
           "
       ::= { hwXponPortJumboEnableEntry 1 }

   hwDscpToDscpMappingTable OBJECT-TYPE
	SYNTAX SEQUENCE OF HwDscpToDscpMappingEntry
	MAX-ACCESS not-accessible
	STATUS current
	DESCRIPTION
           "Indicates the DSCP to DSCP mapping table. This table is used to configure or query the mapping
            between the DSCP and DSCP. It only supports the modify operation but not the create or delete operation.
            The fist record of this table is the default record of the system and cannot be modified.
            The index of this table is hwDscpToDscpMappingIndex.
           "
	::= { hwExtIpdslam 52 }

   hwDscpToDscpMappingEntry OBJECT-TYPE
	SYNTAX HwDscpToDscpMappingEntry
	MAX-ACCESS not-accessible
	STATUS current
	DESCRIPTION
	   "Indicates the DSCP to DSCP mapping table. This table is used to configure or query the mapping
            between the DSCP and DSCP. It only supports the modify operation but not the create or delete operation.
            The fist record of this table is the default record of the system and cannot be modified.
            The index of this entry is hwDscpToDscpMappingIndex.
           "
	INDEX { hwDscpToDscpMappingIndex }
	::= { hwDscpToDscpMappingTable 1 }

   HwDscpToDscpMappingEntry ::=
	SEQUENCE {
		hwDscpToDscpMappingIndex
			Integer32,
		hwDscpListMapToDscp0
			OCTET STRING,
		hwDscpListMapToDscp1
			OCTET STRING,
		hwDscpListMapToDscp2
			OCTET STRING,
		hwDscpListMapToDscp3
			OCTET STRING,
		hwDscpListMapToDscp4
			OCTET STRING,
		hwDscpListMapToDscp5
			OCTET STRING,
		hwDscpListMapToDscp6
			OCTET STRING,
		hwDscpListMapToDscp7
			OCTET STRING,
		hwDscpToDscpMapRowStatus
			RowStatus
	 }

   hwDscpToDscpMappingIndex OBJECT-TYPE
	SYNTAX Integer32 (1..4)
	MAX-ACCESS not-accessible
	STATUS current
	DESCRIPTION
          "Indicates the index of the DSCP-to-DSCP mapping table.
           Range: 1-4
           By default, the system supports four DSCP-to-DSCP mapping tables.
          "
	::= { hwDscpToDscpMappingEntry 1 }


   hwDscpListMapToDscp0 OBJECT-TYPE
	SYNTAX OCTET STRING (SIZE (16))
	MAX-ACCESS read-write
	STATUS current
	DESCRIPTION
	   "This leaf is a string of 16 bytes. Every two bytes (16 bits) indicate an DSCP.
	    The 16 bytes represent DSCPs 0 to 7 (from the left to the right) of a DSCP mapping.
	    The structure is as follows:
                     ----------------------------------------------------
                     |    15   |  14-12   |  11-6   |      5-0          |
                     ----------------------------------------------------
                     |  flag   | reserved | yellow  | green-and-yellow  |
                     |         |          |         |    or green       |
                     ----------------------------------------------------
            Bit 15: indicates the color type.
                    0: Bits 0-5 indicate the DSCP of yellow and green packets and bits 6-11 are ignored.
                    1: Bits 0-5 indicate the DSCP of green packets and bits 6-11 indicate the DSCP of yellow packets.
            Bits 12-14 are reserved and always set to 0. Value 1 is invalid.
            Bits 0-5: When bit 15 is 0, bits 0-5 indicate the DSCP of yellow and green packets;
                      when bit 15 is 1, bits 0-5 indicate the DSCP of green packets and bits 6-11 indicate the DSCP of yellow packets.
            Bits 6-11: When bit 15 is 0, bits 6-11 are invalid. When bit 15 is 1, bits 6-11 indicate the DSCP of yellow packets.
           "
	::= { hwDscpToDscpMappingEntry 2 }


   hwDscpListMapToDscp1 OBJECT-TYPE
	SYNTAX OCTET STRING (SIZE (16))
	MAX-ACCESS read-write
	STATUS current
	DESCRIPTION
	   "This leaf is a string of 16 bytes. Every two bytes (16 bits) indicate an DSCP.
	    The 16 bytes represent DSCPs 8 to 15 (from the left to the right) of a DSCP mapping.
	    The structure is as follows:
                     ----------------------------------------------------
                     |    15   |  14-12   |  11-6   |      5-0          |
                     ----------------------------------------------------
                     |  flag   | reserved | yellow  | green-and-yellow  |
                     |         |          |         |    or green       |
                     ----------------------------------------------------
            Bit 15: indicates the color type.
                    0: Bits 0-5 indicate the DSCP of yellow and green packets and bits 6-11 are ignored.
                    1: Bits 0-5 indicate the DSCP of green packets and bits 6-11 indicate the DSCP of yellow packets.
            Bits 12-14 are reserved and always set to 0. Value 1 is invalid.
            Bits 0-5: When bit 15 is 0, bits 0-5 indicate the DSCP of yellow and green packets;
                      when bit 15 is 1, bits 0-5 indicate the DSCP of green packets and bits 6-11 indicate the DSCP of yellow packets.
            Bits 6-11: When bit 15 is 0, bits 6-11 are invalid. When bit 15 is 1, bits 6-11 indicate the DSCP of yellow packets.
           "
	::= { hwDscpToDscpMappingEntry 3 }


   hwDscpListMapToDscp2 OBJECT-TYPE
	SYNTAX OCTET STRING (SIZE (16))
	MAX-ACCESS read-write
	STATUS current
	DESCRIPTION
	   "This leaf is a string of 16 bytes. Every two bytes (16 bits) indicate an DSCP.
	    The 16 bytes represent DSCPs 16 to 23 (from the left to the right) of a DSCP mapping.
	    The structure is as follows:
                     ----------------------------------------------------
                     |    15   |  14-12   |  11-6   |      5-0          |
                     ----------------------------------------------------
                     |  flag   | reserved | yellow  | green-and-yellow  |
                     |         |          |         |    or green       |
                     ----------------------------------------------------
            Bit 15: indicates the color type.
                    0: Bits 0-5 indicate the DSCP of yellow and green packets and bits 6-11 are ignored.
                    1: Bits 0-5 indicate the DSCP of green packets and bits 6-11 indicate the DSCP of yellow packets.
            Bits 12-14 are reserved and always set to 0. Value 1 is invalid.
            Bits 0-5: When bit 15 is 0, bits 0-5 indicate the DSCP of yellow and green packets;
                      when bit 15 is 1, bits 0-5 indicate the DSCP of green packets and bits 6-11 indicate the DSCP of yellow packets.
            Bits 6-11: When bit 15 is 0, bits 6-11 are invalid. When bit 15 is 1, bits 6-11 indicate the DSCP of yellow packets.
           "
	::= { hwDscpToDscpMappingEntry 4 }

   hwDscpListMapToDscp3 OBJECT-TYPE
	SYNTAX OCTET STRING (SIZE (16))
	MAX-ACCESS read-write
	STATUS current
	DESCRIPTION
	   "This leaf is a string of 16 bytes. Every two bytes (16 bits) indicate an DSCP.
	    The 16 bytes represent DSCPs 24 to 31 (from the left to the right) of a DSCP mapping.
	    The structure is as follows:
                     ----------------------------------------------------
                     |    15   |  14-12   |  11-6   |      5-0          |
                     ----------------------------------------------------
                     |  flag   | reserved | yellow  | green-and-yellow  |
                     |         |          |         |    or green       |
                     ----------------------------------------------------
            Bit 15: indicates the color type.
                    0: Bits 0-5 indicate the DSCP of yellow and green packets and bits 6-11 are ignored.
                    1: Bits 0-5 indicate the DSCP of green packets and bits 6-11 indicate the DSCP of yellow packets.
            Bits 12-14 are reserved and always set to 0. Value 1 is invalid.
            Bits 0-5: When bit 15 is 0, bits 0-5 indicate the DSCP of yellow and green packets;
                      when bit 15 is 1, bits 0-5 indicate the DSCP of green packets and bits 6-11 indicate the DSCP of yellow packets.
            Bits 6-11: When bit 15 is 0, bits 6-11 are invalid. When bit 15 is 1, bits 6-11 indicate the DSCP of yellow packets.
           "
	::= { hwDscpToDscpMappingEntry 5 }

   hwDscpListMapToDscp4 OBJECT-TYPE
	SYNTAX OCTET STRING (SIZE (16))
	MAX-ACCESS read-write
	STATUS current
	DESCRIPTION
	   "This leaf is a string of 16 bytes. Every two bytes (16 bits) indicate an DSCP.
	    The 16 bytes represent DSCPs 32 to 39 (from the left to the right) of a DSCP mapping.
	    The structure is as follows:
                     ----------------------------------------------------
                     |    15   |  14-12   |  11-6   |      5-0          |
                     ----------------------------------------------------
                     |  flag   | reserved | yellow  | green-and-yellow  |
                     |         |          |         |    or green       |
                     ----------------------------------------------------
            Bit 15: indicates the color type.
                    0: Bits 0-5 indicate the DSCP of yellow and green packets and bits 6-11 are ignored.
                    1: Bits 0-5 indicate the DSCP of green packets and bits 6-11 indicate the DSCP of yellow packets.
            Bits 12-14 are reserved and always set to 0. Value 1 is invalid.
            Bits 0-5: When bit 15 is 0, bits 0-5 indicate the DSCP of yellow and green packets;
                      when bit 15 is 1, bits 0-5 indicate the DSCP of green packets and bits 6-11 indicate the DSCP of yellow packets.
            Bits 6-11: When bit 15 is 0, bits 6-11 are invalid. When bit 15 is 1, bits 6-11 indicate the DSCP of yellow packets.
           "
	::= { hwDscpToDscpMappingEntry 6 }

   hwDscpListMapToDscp5 OBJECT-TYPE
	SYNTAX OCTET STRING (SIZE (16))
	MAX-ACCESS read-write
	STATUS current
	DESCRIPTION
	   "This leaf is a string of 16 bytes. Every two bytes (16 bits) indicate an DSCP.
	    The 16 bytes represent DSCPs 40 to 16 (from the left to the right) of a DSCP mapping.
	    The structure is as follows:
                     ----------------------------------------------------
                     |    15   |  14-12   |  11-6   |      5-0          |
                     ----------------------------------------------------
                     |  flag   | reserved | yellow  | green-and-yellow  |
                     |         |          |         |    or green       |
                     ----------------------------------------------------
            Bit 15: indicates the color type.
                    0: Bits 0-5 indicate the DSCP of yellow and green packets and bits 6-11 are ignored.
                    1: Bits 0-5 indicate the DSCP of green packets and bits 6-11 indicate the DSCP of yellow packets.
            Bits 12-14 are reserved and always set to 0. Value 1 is invalid.
            Bits 0-5: When bit 15 is 0, bits 0-5 indicate the DSCP of yellow and green packets;
                      when bit 15 is 1, bits 0-5 indicate the DSCP of green packets and bits 6-11 indicate the DSCP of yellow packets.
            Bits 6-11: When bit 15 is 0, bits 6-11 are invalid. When bit 15 is 1, bits 6-11 indicate the DSCP of yellow packets.
           "
	::= { hwDscpToDscpMappingEntry 7 }

   hwDscpListMapToDscp6 OBJECT-TYPE
	SYNTAX OCTET STRING (SIZE (16))
	MAX-ACCESS read-write
	STATUS current
	DESCRIPTION
	   "This leaf is a string of 16 bytes. Every two bytes (16 bits) indicate an DSCP.
	    The 16 bytes represent DSCPs 47 to 54 (from the left to the right) of a DSCP mapping.
	    The structure is as follows:
                     ----------------------------------------------------
                     |    15   |  14-12   |  11-6   |      5-0          |
                     ----------------------------------------------------
                     |  flag   | reserved | yellow  | green-and-yellow  |
                     |         |          |         |    or green       |
                     ----------------------------------------------------
            Bit 15: indicates the color type.
                    0: Bits 0-5 indicate the DSCP of yellow and green packets and bits 6-11 are ignored.
                    1: Bits 0-5 indicate the DSCP of green packets and bits 6-11 indicate the DSCP of yellow packets.
            Bits 12-14 are reserved and always set to 0. Value 1 is invalid.
            Bits 0-5: When bit 15 is 0, bits 0-5 indicate the DSCP of yellow and green packets;
                      when bit 15 is 1, bits 0-5 indicate the DSCP of green packets and bits 6-11 indicate the DSCP of yellow packets.
            Bits 6-11: When bit 15 is 0, bits 6-11 are invalid. When bit 15 is 1, bits 6-11 indicate the DSCP of yellow packets.
           "
	::= { hwDscpToDscpMappingEntry 8 }

   hwDscpListMapToDscp7 OBJECT-TYPE
	SYNTAX OCTET STRING (SIZE (16))
	MAX-ACCESS read-write
	STATUS current
	DESCRIPTION
	   "This leaf is a string of 16 bytes. Every two bytes (16 bits) indicate an DSCP.
	    The 16 bytes represent DSCPs 55 to 63 (from the left to the right) of a DSCP mapping.
	    The structure is as follows:
                     ----------------------------------------------------
                     |    15   |  14-12   |  11-6   |      5-0          |
                     ----------------------------------------------------
                     |  flag   | reserved | yellow  | green-and-yellow  |
                     |         |          |         |    or green       |
                     ----------------------------------------------------
            Bit 15: indicates the color type.
                    0: Bits 0-5 indicate the DSCP of yellow and green packets and bits 6-11 are ignored.
                    1: Bits 0-5 indicate the DSCP of green packets and bits 6-11 indicate the DSCP of yellow packets.
            Bits 12-14 are reserved and always set to 0. Value 1 is invalid.
            Bits 0-5: When bit 15 is 0, bits 0-5 indicate the DSCP of yellow and green packets;
                      when bit 15 is 1, bits 0-5 indicate the DSCP of green packets and bits 6-11 indicate the DSCP of yellow packets.
            Bits 6-11: When bit 15 is 0, bits 6-11 are invalid. When bit 15 is 1, bits 6-11 indicate the DSCP of yellow packets.
           "
	::= { hwDscpToDscpMappingEntry 9 }

   hwDscpToDscpMapRowStatus OBJECT-TYPE
	SYNTAX RowStatus
	MAX-ACCESS read-create
	STATUS current
	DESCRIPTION
	   "Indicates the row status.
            It supports only the query function. active(1) is displayed in the query result.
            Options:
            1. active(1) -indicates the query operation
           "
	::= { hwDscpToDscpMappingEntry 10 }


   hwDscpColorToPbitsMappingTable OBJECT-TYPE
	SYNTAX SEQUENCE OF HwDscpColorToPbitsMappingEntry
	MAX-ACCESS not-accessible
	STATUS current
	DESCRIPTION
		"Indicates the color-DSCP-to-802.1p priority mapping profile.It is used to modify and query
		 the color-DSCP-to-802.1p priority mapping relationships in the system.
		 The index of this table is hwDscpColorToPbitsMappingIndex.
		 By default, the system supports four color-DSCP-to-802.1p priority mapping profiles.
		 These priority mapping tables can be queried or modified, but cannot be created or deleted.
		 The color-DSCP-to-802.1p priority mapping table with index 1 cannot be modified.
		"
	::= { hwExtIpdslam 53 }

   hwDscpColorToPbitsMappingEntry OBJECT-TYPE
	SYNTAX HwDscpColorToPbitsMappingEntry
	MAX-ACCESS not-accessible
	STATUS current
	DESCRIPTION
		"Indicates the color-DSCP-to-802.1p priority mapping profile.It is used to modify and query
		 the color-DSCP-to-802.1p priority mapping relationships in the system.
		 The index of this entry is hwDscpColorToPbitsMappingIndex.
		 By default, the system supports four color-DSCP-to-802.1p priority mapping profiles.
		 These priority mapping tables can be queried or modified, but cannot be created or deleted.
		 The color-DSCP-to-802.1p priority mapping table with index 1 cannot be modified.
		"
	INDEX { hwDscpColorToPbitsMappingIndex }
	::= { hwDscpColorToPbitsMappingTable 1 }

   HwDscpColorToPbitsMappingEntry ::=
	SEQUENCE {
		hwDscpColorToPbitsMappingIndex
			Integer32,
		hwDscpColorListMapToPriority0
			OCTET STRING,
		hwDscpColorListMapToPriority1
			OCTET STRING,
		hwDscpColorListMapToPriority2
			OCTET STRING,
		hwDscpColorListMapToPriority3
			OCTET STRING,
		hwDscpColorListMapToPriority4
			OCTET STRING,
		hwDscpColorListMapToPriority5
			OCTET STRING,
		hwDscpColorListMapToPriority6
			OCTET STRING,
		hwDscpColorListMapToPriority7
			OCTET STRING,
		hwDscpColorToPbitsMapRowStatus
			RowStatus
	 }

   hwDscpColorToPbitsMappingIndex OBJECT-TYPE
	SYNTAX Integer32 (1..50)
	MAX-ACCESS not-accessible
	STATUS current
	DESCRIPTION
		"Indicates the index of the color-DSCP-to-802.1p priority mapping table.
                 Range: 1-50
                 By default, the system supports fifty DSCP-to-DSCP priority mapping tables.
                "
	::= { hwDscpColorToPbitsMappingEntry 1 }

   hwDscpColorListMapToPriority0 OBJECT-TYPE
	SYNTAX OCTET STRING (SIZE (8))
	MAX-ACCESS read-write
	STATUS current
	DESCRIPTION
	   "This leaf is a string of 8 bytes. Every one bytes (8 bits) indicate an 802.1p priority.
	    The 8 bytes represent priorities 0 to 7 (from the left to the right) of a DSCP mapping. The structure is as follows:
                     ----------------------------------------------------
                     |    7    |    6     |  5-3    |      2-0          |
                     ----------------------------------------------------
                     |  flag   | reserved | yellow  | green-and-yellow  |
                     |         |          |         |    or green       |
                     ----------------------------------------------------
            Bit 7: indicates the color type.
                    0: Bits 0-2 indicate the priority of yellow and green packets and bits 3-5 are ignored.
                    1: Bits 0-2 indicate the priority of green packets and bits 3-5 indicate the priority of yellow packets.
            Bits 6 are reserved and always set to 0. Value 1 is invalid.
            Bits 0-2: When bit 15 is 0, bits 0-2 indicate the priority of yellow and green packets;
                      when bit 15 is 1, bits 0-2 indicate the priority of green packets and bits 3-5 indicate the priority of yellow packets.
            Bits 3-5: When bit 15 is 0, bits 0-2 are invalid. When bit 7 is 1, bits 3-5 indicate the priority of yellow packets.
           "
	::= { hwDscpColorToPbitsMappingEntry 2 }

   hwDscpColorListMapToPriority1 OBJECT-TYPE
	SYNTAX OCTET STRING (SIZE (8))
	MAX-ACCESS read-write
	STATUS current
	DESCRIPTION
	   "This leaf is a string of 8 bytes. Every one bytes (8 bits) indicate an 802.1p priority.
	    The 8 bytes represent priorities 8 to 15 (from the left to the right) of a DSCP mapping. The structure is as follows:
                     ----------------------------------------------------
                     |    7    |    6     |  5-3    |      2-0          |
                     ----------------------------------------------------
                     |  flag   | reserved | yellow  | green-and-yellow  |
                     |         |          |         |    or green       |
                     ----------------------------------------------------
            Bit 7: indicates the color type.
                    0: Bits 0-2 indicate the priority of yellow and green packets and bits 3-5 are ignored.
                    1: Bits 0-2 indicate the priority of green packets and bits 3-5 indicate the priority of yellow packets.
            Bits 6 are reserved and always set to 0. Value 1 is invalid.
            Bits 0-2: When bit 15 is 0, bits 0-2 indicate the priority of yellow and green packets;
                      when bit 15 is 1, bits 0-2 indicate the priority of green packets and bits 3-5 indicate the priority of yellow packets.
            Bits 3-5: When bit 15 is 0, bits 0-2 are invalid. When bit 7 is 1, bits 3-5 indicate the priority of yellow packets.
           "
	::= { hwDscpColorToPbitsMappingEntry 3 }

   hwDscpColorListMapToPriority2 OBJECT-TYPE
	SYNTAX OCTET STRING (SIZE (8))
	MAX-ACCESS read-write
	STATUS current
	DESCRIPTION
	   "This leaf is a string of 8 bytes. Every one bytes (8 bits) indicate an 802.1p priority.
	    The 8 bytes represent priorities 16 to 23 (from the left to the right) of a DSCP mapping. The structure is as follows:
                     ----------------------------------------------------
                     |    7    |    6     |  5-3    |      2-0          |
                     ----------------------------------------------------
                     |  flag   | reserved | yellow  | green-and-yellow  |
                     |         |          |         |    or green       |
                     ----------------------------------------------------
            Bit 7: indicates the color type.
                    0: Bits 0-2 indicate the priority of yellow and green packets and bits 3-5 are ignored.
                    1: Bits 0-2 indicate the priority of green packets and bits 3-5 indicate the priority of yellow packets.
            Bits 6 are reserved and always set to 0. Value 1 is invalid.
            Bits 0-2: When bit 15 is 0, bits 0-2 indicate the priority of yellow and green packets;
                      when bit 15 is 1, bits 0-2 indicate the priority of green packets and bits 3-5 indicate the priority of yellow packets.
            Bits 3-5: When bit 15 is 0, bits 0-2 are invalid. When bit 7 is 1, bits 3-5 indicate the priority of yellow packets.
           "
	::= { hwDscpColorToPbitsMappingEntry 4 }

   hwDscpColorListMapToPriority3 OBJECT-TYPE
	SYNTAX OCTET STRING (SIZE (8))
	MAX-ACCESS read-write
	STATUS current
	DESCRIPTION
	   "This leaf is a string of 8 bytes. Every one bytes (8 bits) indicate an 802.1p priority.
	    The 8 bytes represent priorities 24 to 31 (from the left to the right) of a DSCP mapping. The structure is as follows:
                     ----------------------------------------------------
                     |    7    |    6     |  5-3    |      2-0          |
                     ----------------------------------------------------
                     |  flag   | reserved | yellow  | green-and-yellow  |
                     |         |          |         |    or green       |
                     ----------------------------------------------------
            Bit 7: indicates the color type.
                    0: Bits 0-2 indicate the priority of yellow and green packets and bits 3-5 are ignored.
                    1: Bits 0-2 indicate the priority of green packets and bits 3-5 indicate the priority of yellow packets.
            Bits 6 are reserved and always set to 0. Value 1 is invalid.
            Bits 0-2: When bit 15 is 0, bits 0-2 indicate the priority of yellow and green packets;
                      when bit 15 is 1, bits 0-2 indicate the priority of green packets and bits 3-5 indicate the priority of yellow packets.
            Bits 3-5: When bit 15 is 0, bits 0-2 are invalid. When bit 7 is 1, bits 3-5 indicate the priority of yellow packets.
           "
	::= { hwDscpColorToPbitsMappingEntry 5 }

   hwDscpColorListMapToPriority4 OBJECT-TYPE
	SYNTAX OCTET STRING (SIZE (8))
	MAX-ACCESS read-write
	STATUS current
	DESCRIPTION
	   "This leaf is a string of 8 bytes. Every one bytes (8 bits) indicate an 802.1p priority.
	    The 8 bytes represent priorities 32 to 39 (from the left to the right) of a DSCP mapping. The structure is as follows:
                     ----------------------------------------------------
                     |    7    |    6     |  5-3    |      2-0          |
                     ----------------------------------------------------
                     |  flag   | reserved | yellow  | green-and-yellow  |
                     |         |          |         |    or green       |
                     ----------------------------------------------------
            Bit 7: indicates the color type.
                    0: Bits 0-2 indicate the priority of yellow and green packets and bits 3-5 are ignored.
                    1: Bits 0-2 indicate the priority of green packets and bits 3-5 indicate the priority of yellow packets.
            Bits 6 are reserved and always set to 0. Value 1 is invalid.
            Bits 0-2: When bit 15 is 0, bits 0-2 indicate the priority of yellow and green packets;
                      when bit 15 is 1, bits 0-2 indicate the priority of green packets and bits 3-5 indicate the priority of yellow packets.
            Bits 3-5: When bit 15 is 0, bits 0-2 are invalid. When bit 7 is 1, bits 3-5 indicate the priority of yellow packets.
           "
	::= { hwDscpColorToPbitsMappingEntry 6 }

   hwDscpColorListMapToPriority5 OBJECT-TYPE
	SYNTAX OCTET STRING (SIZE (8))
	MAX-ACCESS read-write
	STATUS current
	DESCRIPTION
	   "This leaf is a string of 8 bytes. Every one bytes (8 bits) indicate an 802.1p priority.
	    The 8 bytes represent priorities 40 to 46 (from the left to the right) of a DSCP mapping. The structure is as follows:
                     ----------------------------------------------------
                     |    7    |    6     |  5-3    |      2-0          |
                     ----------------------------------------------------
                     |  flag   | reserved | yellow  | green-and-yellow  |
                     |         |          |         |    or green       |
                     ----------------------------------------------------
            Bit 7: indicates the color type.
                    0: Bits 0-2 indicate the priority of yellow and green packets and bits 3-5 are ignored.
                    1: Bits 0-2 indicate the priority of green packets and bits 3-5 indicate the priority of yellow packets.
            Bits 6 are reserved and always set to 0. Value 1 is invalid.
            Bits 0-2: When bit 15 is 0, bits 0-2 indicate the priority of yellow and green packets;
                      when bit 15 is 1, bits 0-2 indicate the priority of green packets and bits 3-5 indicate the priority of yellow packets.
            Bits 3-5: When bit 15 is 0, bits 0-2 are invalid. When bit 7 is 1, bits 3-5 indicate the priority of yellow packets.
           "
	::= { hwDscpColorToPbitsMappingEntry 7 }

   hwDscpColorListMapToPriority6 OBJECT-TYPE
	SYNTAX OCTET STRING (SIZE (8))
	MAX-ACCESS read-write
	STATUS current
	DESCRIPTION
	   "This leaf is a string of 8 bytes. Every one bytes (8 bits) indicate an 802.1p priority.
	    The 8 bytes represent priorities 47 to 54 (from the left to the right) of a DSCP mapping. The structure is as follows:
                     ----------------------------------------------------
                     |    7    |    6     |  5-3    |      2-0          |
                     ----------------------------------------------------
                     |  flag   | reserved | yellow  | green-and-yellow  |
                     |         |          |         |    or green       |
                     ----------------------------------------------------
            Bit 7: indicates the color type.
                    0: Bits 0-2 indicate the priority of yellow and green packets and bits 3-5 are ignored.
                    1: Bits 0-2 indicate the priority of green packets and bits 3-5 indicate the priority of yellow packets.
            Bits 6 are reserved and always set to 0. Value 1 is invalid.
            Bits 0-2: When bit 15 is 0, bits 0-2 indicate the priority of yellow and green packets;
                      when bit 15 is 1, bits 0-2 indicate the priority of green packets and bits 3-5 indicate the priority of yellow packets.
            Bits 3-5: When bit 15 is 0, bits 0-2 are invalid. When bit 7 is 1, bits 3-5 indicate the priority of yellow packets.
           "
	::= { hwDscpColorToPbitsMappingEntry 8 }

   hwDscpColorListMapToPriority7 OBJECT-TYPE
	SYNTAX OCTET STRING (SIZE (8))
	MAX-ACCESS read-write
	STATUS current
	DESCRIPTION
	   "This leaf is a string of 8 bytes. Every one bytes (8 bits) indicate an 802.1p priority.
	    The 8 bytes represent priorities 55 to 63 (from the left to the right) of a DSCP mapping. The structure is as follows:
                     ----------------------------------------------------
                     |    7    |    6     |  5-3    |      2-0          |
                     ----------------------------------------------------
                     |  flag   | reserved | yellow  | green-and-yellow  |
                     |         |          |         |    or green       |
                     ----------------------------------------------------
            Bit 7: indicates the color type.
                    0: Bits 0-2 indicate the priority of yellow and green packets and bits 3-5 are ignored.
                    1: Bits 0-2 indicate the priority of green packets and bits 3-5 indicate the priority of yellow packets.
            Bits 6 are reserved and always set to 0. Value 1 is invalid.
            Bits 0-2: When bit 15 is 0, bits 0-2 indicate the priority of yellow and green packets;
                      when bit 15 is 1, bits 0-2 indicate the priority of green packets and bits 3-5 indicate the priority of yellow packets.
            Bits 3-5: When bit 15 is 0, bits 0-2 are invalid. When bit 7 is 1, bits 3-5 indicate the priority of yellow packets.
           "
	::= { hwDscpColorToPbitsMappingEntry 9 }

   hwDscpColorToPbitsMapRowStatus OBJECT-TYPE
	SYNTAX RowStatus
	MAX-ACCESS read-create
	STATUS current
	DESCRIPTION
	   "Indicates the row status.
            It supports only the query function. active(1) is displayed in the query result.
            Options:
            1. active(1) -indicates the query operation
           "
	::= { hwDscpColorToPbitsMappingEntry 10 }

-- hwOntBindQosPolicyProfileTable
   hwOntBindQosPolicyProfileTable OBJECT-TYPE
       SYNTAX SEQUENCE OF HwOntBindQosPolicyProfileEntry
       MAX-ACCESS not-accessible
       STATUS current
       DESCRIPTION
           "This table is used for binding or unbinding a QoS policy profile to the ONT.
            The index of this table is ifIndex, hwOntBindQosPolicyProfileOntId.
           "
       ::= { hwExtIpdslam 54 }

   hwOntBindQosPolicyProfileEntry OBJECT-TYPE
       SYNTAX HwOntBindQosPolicyProfileEntry
       MAX-ACCESS not-accessible
       STATUS current
       DESCRIPTION
           "This table is used for binding or unbinding a QoS policy profile to the ONT.
            The index of this entry is ifIndex, hwOntBindQosPolicyProfileOntId.
           "
       INDEX { ifIndex, hwOntBindQosPolicyProfileOntId }
       ::= { hwOntBindQosPolicyProfileTable 1 }

   HwOntBindQosPolicyProfileEntry ::=
       SEQUENCE {
           hwOntBindQosPolicyProfileOntId
               Integer32,
           hwOntBindQosPolicyProfileName
               OCTET STRING
        }

   hwOntBindQosPolicyProfileOntId OBJECT-TYPE
       SYNTAX Integer32
       MAX-ACCESS not-accessible
       STATUS current
       DESCRIPTION
           "Indicates the ONT ID.
           "
       ::= { hwOntBindQosPolicyProfileEntry 1 }

   hwOntBindQosPolicyProfileName OBJECT-TYPE
       SYNTAX OCTET STRING (SIZE (0..32))
       MAX-ACCESS read-write
       STATUS current
       DESCRIPTION
           "Indicates the name of the QoS policy profile bound to the ONT.
            Range: a string of 0-32 characters
            This leaf identifies a QoS policy profile, which must be
            created in hwQosPolicyProfileTable. The null character string indicates
            that the binding relation between the ONT and the QoS policy profile is deleted.
           "
       ::= { hwOntBindQosPolicyProfileEntry 2 }


   -- 1.3.6.1.4.1.2011.5.14.3.55
   hwUplinkSwitchNotify OBJECT IDENTIFIER ::= { hwExtIpdslam 55 }

   -- 1.3.6.1.4.1.2011.5.14.3.55.1
   hwUplinkSwitchNotifyConfig OBJECT-TYPE
    SYNTAX INTEGER
           {
           enable(1),
           disable(2)
           }
       MAX-ACCESS read-write
       STATUS current
       DESCRIPTION
           "Switch of controlling sending gratuitous ARP packets in the upstream direction.
            Options:
            1. enable(1)  -enables the uplink notify function.
            2. disable(2) -disables the uplink notify function.
           "
           DEFVAL { disable }
       ::= { hwUplinkSwitchNotify 1 }

   -- 1.3.6.1.4.1.2011.5.14.3.55.2
   hwUplinkSwitchNotifyTimes OBJECT-TYPE
   	SYNTAX Integer32 (1..5)
   	MAX-ACCESS read-write
   	STATUS current
   	DESCRIPTION
        "Times of sending gratuitous ARP packets, igmp and mld report packets in the upstream direction."
   	DEFVAL { 1 }
   	::= { hwUplinkSwitchNotify 2 }

   -- 1.3.6.1.4.1.2011.5.14.3.55.3
   hwUplinkSwitchNotifyIpDetect OBJECT-TYPE
   	SYNTAX INTEGER
        {
        enable(1),
        disable(2)
        }
   	MAX-ACCESS read-write
   	STATUS current
   	DESCRIPTION
        "Switch of detecting the bound IP address.
         Options:
         1. enable(1)  -enables the bind ip detect function.
         2. disable(2) -disables the bind ip detect function.
        "
   	DEFVAL { disable }
   	::= { hwUplinkSwitchNotify 3 }

   -- 1.3.6.1.4.1.2011.5.14.3.55.4
   hwUplinkSwitchNotifyIpDetectTable OBJECT-TYPE
   	SYNTAX SEQUENCE OF HwUplinkSwitchNotifyIpDetectEntry
   	MAX-ACCESS not-accessible
   	STATUS current
   	DESCRIPTION
        "Bound IP address list to be detected.
         The index of this table is hwUplinkSwitchNotifyIpDetectServicePortIndex, hwUplinkSwitchNotifyIpDetectSubIndex.
		"
   	::= { hwUplinkSwitchNotify 4 }

   -- 1.3.6.1.4.1.2011.5.14.3.55.4.1
   hwUplinkSwitchNotifyIpDetectEntry OBJECT-TYPE
   	SYNTAX HwUplinkSwitchNotifyIpDetectEntry
   	MAX-ACCESS not-accessible
   	STATUS current
   	DESCRIPTION
        "Bound IP address list to be detected.
         The index of this entry is hwUplinkSwitchNotifyIpDetectServicePortIndex, hwUplinkSwitchNotifyIpDetectSubIndex.
		"
   	INDEX { hwUplinkSwitchNotifyIpDetectServicePortIndex, hwUplinkSwitchNotifyIpDetectSubIndex }
   	::= { hwUplinkSwitchNotifyIpDetectTable 1 }

   HwUplinkSwitchNotifyIpDetectEntry ::=
   	SEQUENCE {
   		hwUplinkSwitchNotifyIpDetectServicePortIndex
   			Integer32,
   		hwUplinkSwitchNotifyIpDetectSubIndex
   			Integer32,
   		hwUplinkSwitchNotifyIpDetectIpAddressType
   			InetAddressType,
   		hwUplinkSwitchNotifyIpDetectIpAddress
   			InetAddress,
   		hwUplinkSwitchNotifyIpDetectIpv6PrefixLength
   			Unsigned32,
   		hwUplinkSwitchNotifyIpDetectMac
   			MacAddress
   	 }

   -- 1.3.6.1.4.1.2011.5.14.3.55.4.1.1
   hwUplinkSwitchNotifyIpDetectServicePortIndex OBJECT-TYPE
   	SYNTAX Integer32
   	MAX-ACCESS not-accessible
   	STATUS current
   	DESCRIPTION
        "Indicates the index of the service port bound to a detected IP address.
         The service port corresponding to this index must already be created in
         hwExtSrvFlowEntry.
        "
   	::= { hwUplinkSwitchNotifyIpDetectEntry 1 }

   -- 1.3.6.1.4.1.2011.5.14.3.55.4.1.2
   hwUplinkSwitchNotifyIpDetectSubIndex OBJECT-TYPE
   	SYNTAX Integer32
   	MAX-ACCESS not-accessible
   	STATUS current
   	DESCRIPTION
   		"This index is used for specifying the position on the service port for detecting the IP address.
   		"
   	::= { hwUplinkSwitchNotifyIpDetectEntry 2 }

   -- 1.3.6.1.4.1.2011.5.14.3.55.4.1.3
   hwUplinkSwitchNotifyIpDetectIpAddressType OBJECT-TYPE
   	SYNTAX InetAddressType
   	MAX-ACCESS read-only
   	STATUS current
   	DESCRIPTION
   		"Indicates the IP address type to detect.
         Options:
         1. ipv4(1)  -indicates that the IP address type is ipv4
         2. ipv6(2)  -indicates that the IP address type is ipv6
        "
   	::= { hwUplinkSwitchNotifyIpDetectEntry 3 }

   -- 1.3.6.1.4.1.2011.5.14.3.55.4.1.4
   hwUplinkSwitchNotifyIpDetectIpAddress OBJECT-TYPE
   	SYNTAX InetAddress
   	MAX-ACCESS read-only
   	STATUS current
   	DESCRIPTION
   		"Indicates the IP address to detect.
        "
   	::= { hwUplinkSwitchNotifyIpDetectEntry 4 }

   -- 1.3.6.1.4.1.2011.5.14.3.55.4.1.5
   hwUplinkSwitchNotifyIpDetectIpv6PrefixLength OBJECT-TYPE
   	SYNTAX Unsigned32
   	MAX-ACCESS read-only
   	STATUS current
   	DESCRIPTION
   		"The IP address mask length."
   	::= { hwUplinkSwitchNotifyIpDetectEntry 5 }


   -- 1.3.6.1.4.1.2011.5.14.3.55.4.1.6
   hwUplinkSwitchNotifyIpDetectMac OBJECT-TYPE
   	SYNTAX MacAddress
   	MAX-ACCESS read-only
   	STATUS current
   	DESCRIPTION
   		"The MAC address obtained in IP address detection."
   	::= { hwUplinkSwitchNotifyIpDetectEntry 6 }

   -- 1.3.6.1.4.1.2011.5.14.3.55.5
   hwUplinkSwitchNotifyConfigBtv OBJECT-TYPE
    SYNTAX INTEGER
           {
           enable(1),
           disable(2)
           }
       MAX-ACCESS read-write
       STATUS current
       DESCRIPTION
           "Switch of controlling sending igmp and mld report packets in the upstream direction.
            Options:
            1. enable(1)  -enables the uplink notify function.
            2. disable(2) -disables the uplink notify function.
           "
           DEFVAL { disable }
       ::= { hwUplinkSwitchNotify 5 }

   -- 1.3.6.1.4.1.2011.5.14.3.56
   hwOnuSwitchNotify OBJECT IDENTIFIER ::= { hwExtIpdslam 56 }

   -- 1.3.6.1.4.1.2011.5.14.3.56.1
   hwOnuSwitchNotifyConfigIpv4 OBJECT-TYPE
    SYNTAX INTEGER
           {
           enable(1),
           disable(2)
           }
       MAX-ACCESS read-write
       STATUS current
       DESCRIPTION
           "Switch of controlling sending gratuitous ARP packets for users after the protection group on the ONU uplink port is switched over.
            Options:
            1. enable(1)  -enables the ONU switch notify function.
            2. disable(2) -disables the ONU switch notify function.
            Default: disable(2)
           "
       ::= { hwOnuSwitchNotify 1 }

   -- 1.3.6.1.4.1.2011.5.14.3.56.2
   hwOnuSwitchNotifyConfigIpv6 OBJECT-TYPE
    SYNTAX INTEGER
    			 {
           enable(1),
           disable(2)
           }
       MAX-ACCESS read-write
       STATUS current
       DESCRIPTION
           "Switch of controlling sending unsolicited NA packets for users after the protection group on the ONU uplink port is switched over.
            Options:
            1. enable(1)  -enables the ONU switch notify function.
            2. disable(2) -disables the ONU switch notify function.
            Default: disable(2)
           "
       ::= { hwOnuSwitchNotify 2 }

--hwIpTrafficNameToIndexTable
   hwIpTrafficNameToIndexTable OBJECT-TYPE
       SYNTAX SEQUENCE OF HwIpTrafficNameToIndexEntry
       MAX-ACCESS not-accessible
       STATUS current
       DESCRIPTION
           "Indicates the traffic profile name-traffic profile index mapping table.
            The index of this table is hwIpTrafficName.
           "
       ::= { hwExtIpdslam 57 }

   hwIpTrafficNameToIndexEntry OBJECT-TYPE
       SYNTAX HwIpTrafficNameToIndexEntry
       MAX-ACCESS not-accessible
       STATUS current
       DESCRIPTION
           "Indicates the traffic profile name-traffic profile index mapping table.
            The index of this entry is hwIpTrafficName.
           "
       INDEX { hwIpTrafficName }
       ::= { hwIpTrafficNameToIndexTable 1 }

   HwIpTrafficNameToIndexEntry ::=
       SEQUENCE {
         hwIpTrafficNameToIndexIdx
           Integer32
        }

   hwIpTrafficNameToIndexIdx OBJECT-TYPE
       SYNTAX Integer32
       MAX-ACCESS read-only
       STATUS current
       DESCRIPTION
           "Indicates the corresponding index of a given traffic profile name.
            The traffic profile name must have been created in hwIpTrafficParamTable.
           "
       ::= { hwIpTrafficNameToIndexEntry 1 }

   -- hwQueueMaxBufferSizeTable
   hwQueueMaxBufferSizeTable OBJECT-TYPE
       SYNTAX SEQUENCE OF HwQueueMaxBufferSizeEntry
       MAX-ACCESS not-accessible
       STATUS current
       DESCRIPTION
           "Indicates the maximum depth of a port queue or ONT queue configured based on boards.
            The indexes of this table are hwFrameIndex, hwSlotIndex, and hwQueueMaxBufferSizeType.
           "
       ::= { hwExtIpdslam 58 }

    hwQueueMaxBufferSizeEntry OBJECT-TYPE
       SYNTAX HwQueueMaxBufferSizeEntry
       MAX-ACCESS not-accessible
       STATUS current
       DESCRIPTION
           "Indicates the maximum depth of a port queue or ONT queue configured based on boards.
            The indexes of this entry are hwFrameIndex, hwSlotIndex, and hwQueueMaxBufferSizeType.
           "
       INDEX { hwFrameIndex, hwSlotIndex, hwQueueMaxBufferSizeType }
       ::= { hwQueueMaxBufferSizeTable 1 }

    HwQueueMaxBufferSizeEntry ::=
       SEQUENCE {
           hwQueueMaxBufferSizeType
             INTEGER,
           hwQueueMaxBufferSizeQueue0
             Integer32,
           hwQueueMaxBufferSizeQueue1
             Integer32,
           hwQueueMaxBufferSizeQueue2
             Integer32,
           hwQueueMaxBufferSizeQueue3
             Integer32,
           hwQueueMaxBufferSizeQueue4
             Integer32,
           hwQueueMaxBufferSizeQueue5
             Integer32,
           hwQueueMaxBufferSizeQueue6
             Integer32,
           hwQueueMaxBufferSizeQueue7
             Integer32,
           hwQueueMaxBufferSizeRowStatus
             RowStatus
     }

   hwQueueMaxBufferSizeType OBJECT-TYPE
      SYNTAX INTEGER
          {
          portQueue(0),
          ontQueue(1)
          }
      MAX-ACCESS not-accessible
      STATUS current
      DESCRIPTION
          "Indicates the type of the queue having the maximum depth based on boards.
           Options:
           1. portQueue(0)   -Indicates the maximum queue depth of ports on a board.
           2. ontQueue(1)    -Indicates the maximum queue depth of onts on a board.
          "
      ::= { hwQueueMaxBufferSizeEntry 1 }

    hwQueueMaxBufferSizeQueue0 OBJECT-TYPE
       SYNTAX Integer32 (-1|32..8192)
       MAX-ACCESS read-create
       STATUS current
       DESCRIPTION
           "Indicates the maximum depth of queue 0 based on boards.
            Range: 32-8192.
            Default value: -1, indicating that the maximum depth of queue 0 is not configured.
           "
       ::= { hwQueueMaxBufferSizeEntry 2 }

    hwQueueMaxBufferSizeQueue1 OBJECT-TYPE
       SYNTAX Integer32 (-1|32..8192)
       MAX-ACCESS read-create
       STATUS current
       DESCRIPTION
           "Indicates the maximum depth of queue 1 based on boards.
            Range: 32-8192.
            Default value: -1, indicating that the maximum depth of queue 1 is not configured.
           "
       ::= { hwQueueMaxBufferSizeEntry 3 }

    hwQueueMaxBufferSizeQueue2 OBJECT-TYPE
       SYNTAX Integer32 (-1|32..8192)
       MAX-ACCESS read-create
       STATUS current
       DESCRIPTION
           "Indicates the maximum depth of queue 2 based on boards.
            Range: 32-8192.
            Default value: -1, indicating that the maximum depth of queue 2 is not configured.
           "
       ::= { hwQueueMaxBufferSizeEntry 4 }

    hwQueueMaxBufferSizeQueue3 OBJECT-TYPE
       SYNTAX Integer32 (-1|32..8192)
       MAX-ACCESS read-create
       STATUS current
       DESCRIPTION
           "Indicates the maximum depth of queue 3 based on boards.
            Range: 32-8192.
            Default value: -1, indicating that the maximum depth of queue 3 is not configured.
           "
       ::= { hwQueueMaxBufferSizeEntry 5 }

    hwQueueMaxBufferSizeQueue4 OBJECT-TYPE
       SYNTAX Integer32 (-1|32..8192)
       MAX-ACCESS read-create
       STATUS current
       DESCRIPTION
           "Indicates the maximum depth of queue 4 based on boards.
            Range: 32-8192.
            Default value: -1, indicating that the maximum depth of queue 4 is not configured.
           "
       ::= { hwQueueMaxBufferSizeEntry 6 }

    hwQueueMaxBufferSizeQueue5 OBJECT-TYPE
       SYNTAX Integer32 (-1|32..8192)
       MAX-ACCESS read-create
       STATUS current
       DESCRIPTION
           "Indicates the maximum depth of queue 5 based on boards.
            Range: 32-8192.
            Default value: -1, indicating that the maximum depth of queue 5 is not configured.
           "
       ::= { hwQueueMaxBufferSizeEntry 7 }

    hwQueueMaxBufferSizeQueue6 OBJECT-TYPE
       SYNTAX Integer32 (-1|32..8192)
       MAX-ACCESS read-create
       STATUS current
       DESCRIPTION
           "Indicates the maximum depth of queue 6 based on boards.
            Range: 32-8192.
            Default value: -1, indicating that the maximum depth of queue 6 is not configured.
           "
       ::= { hwQueueMaxBufferSizeEntry 8 }

    hwQueueMaxBufferSizeQueue7 OBJECT-TYPE
       SYNTAX Integer32 (-1|32..8192)
       MAX-ACCESS read-create
       STATUS current
       DESCRIPTION
           "Indicates the maximum depth of queue 7 based on boards.
            Range: 32-8192.
            Default value: -1, indicating that the maximum depth of queue 7 is not configured.
           "
       ::= { hwQueueMaxBufferSizeEntry 9 }

    hwQueueMaxBufferSizeRowStatus OBJECT-TYPE
           SYNTAX RowStatus
           MAX-ACCESS read-create
           STATUS current
           DESCRIPTION
               "Indicates the row status and is used for creating or deleting
                a maximum depth of queue item.
                Options:
                1. active(1)
                2. createAndGo(4)
                3. destroy(6)
                Only options createAndGo(4) and destroy(6) are supported the set operation.
                During query, active(1) is always returned for this leaf.
               "
         ::= { hwQueueMaxBufferSizeEntry 255 }

 -- hwRateProfileTable
 hwRateProfileTable OBJECT-TYPE
      SYNTAX SEQUENCE OF HwRateProfileEntry
      MAX-ACCESS not-accessible
      STATUS current
      DESCRIPTION
          "Indicates the rate profile.
           It is used to add, query, modify, or delete an rate profile.
           This table mainly involves configuring CAR parameters such as CIR, PIR,
           CBS, and PBS.
           The index of this table is hwRateProfileName.
          "
      ::= {hwExtIpdslam 59 }

  hwRateProfileEntry OBJECT-TYPE
      SYNTAX HwRateProfileEntry
      MAX-ACCESS not-accessible
      STATUS current
      DESCRIPTION
          "Indicates the rate profile.
           It is used to add, query, modify, or delete an rate profile.
           This table mainly involves configuring CAR parameters such as CIR, PIR,
           CBS, and PBS.
           The index of this entry is hwRateProfileName.
          "
      INDEX { hwRateProfileName }
      ::= { hwRateProfileTable 1 }

  HwRateProfileEntry ::=
      SEQUENCE {
          hwRateProfileName
             OCTET STRING,
          hwRateProfileRowStatus
             RowStatus,
          hwRateProfileCir
             Integer32,
          hwRateProfileCbs
             Integer32,
          hwRateProfilePir
             Integer32,
          hwRateProfilePbs
             Integer32,
          hwRateProfileFixBandWidth
             Integer32,
          hwRateProfileColorMode
             INTEGER,
          hwRateProfileCarThresholdProfileIndex
             Integer32,
          hwRateProfileCouplingFlag
             INTEGER,
          hwRateProfileIndex
             Integer32
       }

  hwRateProfileName OBJECT-TYPE
      SYNTAX OCTET STRING (SIZE(1..32))
      MAX-ACCESS not-accessible
      STATUS current
      DESCRIPTION
          "Indicates the name of the rate profile.
          Range: a string of 1-32 characters
          The input index consists of the rate profile name and
          the length of the rate profile name.
          The input profile name must be ASCII codes.
          Assume that you need to create a rate profile named huawei.
          The ASCII value of huawei is 104.117.97.119.101.105 and
          the length of huawei is 6; therefore, the index is 6.104.117.97.119.101.105.
          "
      ::= { hwRateProfileEntry 1 }

  hwRateProfileRowStatus OBJECT-TYPE
      SYNTAX RowStatus
      MAX-ACCESS read-create
      STATUS current
      DESCRIPTION
          "Indicates the row status.
           Options:
           1. active(1)
           2. createAndGo(4)
           3. destroy(6)
          "
      ::= { hwRateProfileEntry 2 }

 hwRateProfileCir OBJECT-TYPE
     SYNTAX Integer32 (-1|0..10240000)
     MAX-ACCESS read-write
     STATUS current
     DESCRIPTION
         "Indicates the committed information RateProfile (CIR).
          Range: -1, 0-10240000 kbit/s.
          Unit: kbit/s.
          CIR is a mandatory parameter. This parameter must be an integer multiple of 64.
          If the entered value is not an integer multiple of 64,
          it rounds down to the nearest integer multiple of 64.
          When the CIR value ranges from 0 to 63, value 0 takes effect. For boards that do not support the CIR with values less than 64, 64 takes effect if the configured value is less than 64.
          -1 indicates CIR off.
         "
     ::= { hwRateProfileEntry 3 }

 hwRateProfileCbs OBJECT-TYPE
     SYNTAX Integer32 (-1|0..1024000000)
     MAX-ACCESS read-write
     STATUS current
     DESCRIPTION
         "Indicates the committed burst size (CBS).
          Range: -1, 0-1024000000 bytes.
          Unit: bytes.
          CBS is an optional parameter. If the parameter is not specified,
          it can be obtained by formula min(2000+cir*32,1024000000).
          For boards that do not support CBS with values less than 2000, 2000 takes effect if the configured value is less than 2000.
          -1 indicates CBS off.
         "
     ::= { hwRateProfileEntry 4 }

 hwRateProfilePir OBJECT-TYPE
     SYNTAX Integer32 (-1|64..10240000)
     MAX-ACCESS read-write
     STATUS current
     DESCRIPTION
         "Indicates the peak information RateProfile (PIR).
          Range: -1, 64-10240000 kbit/s.
          Unit: kbit/s.
          PIR is an optional parameter. If the parameter is not specified,
          it can be obtained through formula max(min(2*cir,10240000),64).
          The PIR must be greater than or equal to the CIR.
          -1 indicates PIR off.
         "
     ::= { hwRateProfileEntry 5 }

 hwRateProfilePbs OBJECT-TYPE
     SYNTAX Integer32 (-1|2000..1024000000)
     MAX-ACCESS read-write
     STATUS current
     DESCRIPTION
         "Indicates the peak burst size (PBS).
          Range: -1, 2000-1024000000 bytes.
          Unit: bytes.
          PBS is an optional parameter.If the parameter is not specified,
          it can be obtained by formula min(2000+32*pir,1024000000).
          -1 indicates PBS off.
         "
     ::= { hwRateProfileEntry 6 }

  hwRateProfileFixBandWidth OBJECT-TYPE
      SYNTAX Integer32 (-1|0..10240000)
      MAX-ACCESS read-write
      STATUS current
      DESCRIPTION
          "Indicates the fixed bandwidth to be allocated by the DBA. This parameter takes effect to the E2E service flow only on a GPON board.
           Range: -1, 0-10240000 kbit/s.
           Unit: kbit/s.
           hwRateProfileFixBandWidth must be smaller than or equal to CIR.
           -1 indicates fixed bandwidth is not supported.
          "
      ::= { hwRateProfileEntry 7 }

 hwRateProfileColorMode OBJECT-TYPE
     SYNTAX INTEGER
         {
         colorBlind(1),
         colorAware(2)
         }
     MAX-ACCESS read-write
     STATUS current
     DESCRIPTION
         "Indicates the color-aware mode of the Rate profile.
          Options:
          1. colorBlind(1)      -Indicates color blind mode.
          2. colorAware(2)      -Indicates color aware mode.
          Default: colorBlind(1)
         "
     ::= { hwRateProfileEntry 8 }

  hwRateProfileCarThresholdProfileIndex OBJECT-TYPE
      SYNTAX Integer32 (-1|1..4)
      MAX-ACCESS read-write
      STATUS current
      DESCRIPTION
          "Indicates the car-threshold profile of the Rate profile.
           -1 indicates car-threshold profile is disabled.
          "
      ::= { hwRateProfileEntry 9 }

 hwRateProfileCouplingFlag OBJECT-TYPE
      SYNTAX INTEGER
      {
        disable(0),
        enable(1)
      }
      MAX-ACCESS read-write
      STATUS current
      DESCRIPTION
          "The Coupling Flag CF is set to either 0 or 1. The choice of the value for CF has the effect of controlling the volume of the yellow
           Service Frames admitted to the network. When CF is set to 0, the long term average bit RateProfile of bytes in yellow service frames admitted
           to the network is bounded by EIR which is equal to PIR-CIR. When CF is set to 1, the long term average bit RateProfile of bytes in yellow
           Service Frames admitted to the network is bounded by PIR depending on volume of the offered green Service Frames.
           In both cases the burst size of the yellow Service Frames admitted to the network is bounded which is equal to PIR-CIR.
           Options:
           1. disable(0) --disable the function of double-color.
           2. enable(1)  --enable the function of double-color.
           Default: enable(1)
          "
     ::= { hwRateProfileEntry 10 }

 hwRateProfileIndex OBJECT-TYPE
      SYNTAX Integer32 (1..256)
      MAX-ACCESS read-write
      STATUS current
      DESCRIPTION
         "Indicates the index of the rate profile.
          Range: 1-256
          "
     ::= { hwRateProfileEntry 11 }

 -- hwQueuePolicyProfileTable
 hwQueuePolicyProfileTable OBJECT-TYPE
     SYNTAX SEQUENCE OF HwQueuePolicyProfileEntry
     MAX-ACCESS not-accessible
     STATUS current
     DESCRIPTION
         "Indicates the queue policy profile table. It is used to add, modify, query, or delete a queue policy profile.
          The index of this table is hwQueuePolicyProfileIndex.
         "
     ::= { hwExtIpdslam 60 }

 hwQueuePolicyProfileEntry OBJECT-TYPE
     SYNTAX HwQueuePolicyProfileEntry
     MAX-ACCESS not-accessible
     STATUS current
     DESCRIPTION
         "Indicates the queue policy profile table. It is used to add, modify, query, or delete a queue policy profile.
          The index of this entry is hwQueuePolicyProfileIndex.
         "
     INDEX { hwQueuePolicyProfileIndex }
     ::= { hwQueuePolicyProfileTable 1 }

 HwQueuePolicyProfileEntry ::=
     SEQUENCE {
         hwQueuePolicyProfileIndex
             Unsigned32,
         hwQueuePolicyProfilePrioritySource
             INTEGER,
         hwQueuePolicyProfilePriorityMappingIndex
             Integer32,
         hwQueuePolicyProfileDefaultQueueCos
             Integer32,
         hwQueuePolicyProfileRowStatus
             RowStatus
      }

 hwQueuePolicyProfileIndex OBJECT-TYPE
     SYNTAX Unsigned32 (1..4)
     MAX-ACCESS not-accessible
     STATUS current
     DESCRIPTION
         "Indicates the index of the queue policy profile.
          Range: 1-4
         "
     ::= { hwQueuePolicyProfileEntry 1 }

 hwQueuePolicyProfilePrioritySource OBJECT-TYPE
     SYNTAX INTEGER
     {
         outer8021p(1),
         inner8021p(2)
     }
     MAX-ACCESS read-write
     STATUS current
     DESCRIPTION
         "Indicates the priority source of the queue policy profile.
          Options:
          1. outer8021p(1) -indicates the priority source is outer 8021p.
          2. inner8021p(2) -indicates the priority source is inner 8021p.
          Default: outer8021p(1)
         "
     ::= { hwQueuePolicyProfileEntry 2 }

 hwQueuePolicyProfilePriorityMappingIndex OBJECT-TYPE
     SYNTAX Integer32 (1..8)
     MAX-ACCESS read-write
     STATUS current
     DESCRIPTION
         "Indicates the mapping profile index of the queue policy profile.
          Range: 1-8
          Default: 1
         "
     ::= { hwQueuePolicyProfileEntry 3 }

 hwQueuePolicyProfileDefaultQueueCos OBJECT-TYPE
     SYNTAX Integer32 (0..7)
     MAX-ACCESS read-write
     STATUS current
     DESCRIPTION
         "Indicates the default priority of the queue policy profile.
          Range: 0-7
          Default: 0
         "
     ::= { hwQueuePolicyProfileEntry 4 }

 hwQueuePolicyProfileRowStatus OBJECT-TYPE
     SYNTAX RowStatus
     MAX-ACCESS read-create
     STATUS current
     DESCRIPTION
         "Indicates the row status.
          Options:
          1. active(1)
          2. createAndGo(4)
          3. destroy(6)
         "
     ::= { hwQueuePolicyProfileEntry 5 }

 -- hwPriorityGroupProfileTable
 hwPriorityGroupProfileTable OBJECT-TYPE
     SYNTAX SEQUENCE OF HwPriorityGroupProfileEntry
     MAX-ACCESS not-accessible
     STATUS current
     DESCRIPTION
         "Indicates the priority group profile table. It is used to add, modify, query, or delete a priority group profile.
          The index of this table is hwPriorityGroupProfileName.
         "
     ::= { hwExtIpdslam 61 }

 hwPriorityGroupProfileEntry OBJECT-TYPE
     SYNTAX HwPriorityGroupProfileEntry
     MAX-ACCESS not-accessible
     STATUS current
     DESCRIPTION
         "Indicates the priority group profile table. It is used to add, modify, query, or delete a priority group profile.
          The index of this entry is hwPriorityGroupProfileName.
         "
     INDEX { hwPriorityGroupProfileName }
     ::= { hwPriorityGroupProfileTable 1 }

 HwPriorityGroupProfileEntry ::=
     SEQUENCE {
         hwPriorityGroupProfileName
             OCTET STRING,
         hwPriorityGroupProfilePrioritySource
             INTEGER,
         hwPriorityGroupProfilePriorityMappingIndex
             Integer32,
         hwPriorityGroupProfileDefaultGroupIndex
             Integer32,
         hwPriorityGroupProfileRowStatus
             RowStatus,
         hwPriorityGroupProfileGroup0RateProfileIndex
             Integer32,
         hwPriorityGroupProfileGroup1RateProfileIndex
             Integer32,
         hwPriorityGroupProfileGroup2RateProfileIndex
             Integer32,
         hwPriorityGroupProfileGroup3RateProfileIndex
             Integer32,
         hwPriorityGroupProfileGroup4RateProfileIndex
             Integer32,
         hwPriorityGroupProfileGroup5RateProfileIndex
             Integer32,
         hwPriorityGroupProfileGroup6RateProfileIndex
             Integer32,
         hwPriorityGroupProfileGroup7RateProfileIndex
             Integer32
      }

 hwPriorityGroupProfileName OBJECT-TYPE
     SYNTAX OCTET STRING (SIZE(1..32))
     MAX-ACCESS not-accessible
     STATUS current
     DESCRIPTION
         "Indicates the name of the priority group profile.
          Range: a string of 1-32 characters
          The input index consists of the priority group profile name and
          the length of the priority group profile name.
          The input profile name must be ASCII codes.
          Assume that you need to create a priority group profile named huawei.
          The ASCII value of huawei is 104.117.97.119.101.105 and
          the length of huawei is 6; therefore, the index is 6.104.117.97.119.101.105.
         "
     ::= { hwPriorityGroupProfileEntry 1 }

 hwPriorityGroupProfilePrioritySource OBJECT-TYPE
     SYNTAX INTEGER
     {
         outer8021p(1),
         inner8021p(2)
     }
     MAX-ACCESS read-write
     STATUS current
     DESCRIPTION
         "Indicates the priority source of the priority group profile.
          Options:
          1. outer8021p(1) -indicates the priority source is outer 8021p.
          2. inner8021p(2) -indicates the priority source is inner 8021p.
          Default: outer8021p(1)
         "
     ::= { hwPriorityGroupProfileEntry 2 }

 hwPriorityGroupProfilePriorityMappingIndex OBJECT-TYPE
     SYNTAX Integer32 (1..8)
     MAX-ACCESS read-write
     STATUS current
     DESCRIPTION
         "Indicates the CoS-group table index of the priority group profile.
          Range: 1-8
          Default: 1
         "
     ::= { hwPriorityGroupProfileEntry 3 }

 hwPriorityGroupProfileDefaultGroupIndex OBJECT-TYPE
     SYNTAX Integer32 (0..7)
     MAX-ACCESS read-write
     STATUS current
     DESCRIPTION
         "Indicates the default group index of the priority group profile.
          Range: 0-7
          Default: 0
         "
     ::= { hwPriorityGroupProfileEntry 4 }

 hwPriorityGroupProfileRowStatus OBJECT-TYPE
     SYNTAX RowStatus
     MAX-ACCESS read-create
     STATUS current
     DESCRIPTION
         "Indicates the row status.
          Options:
          1. active(1)
          2. createAndGo(4)
          3. destroy(6)
         "
     ::= { hwPriorityGroupProfileEntry 5 }

 hwPriorityGroupProfileGroup0RateProfileIndex OBJECT-TYPE
     SYNTAX Integer32(-1|1..256)
     MAX-ACCESS read-write
     STATUS current
     DESCRIPTION
         "Indicates the index of the rate profile bound to Car-group 0.
          -1 indicates priority group car is not configured.
         "
     ::= { hwPriorityGroupProfileEntry 6 }

 hwPriorityGroupProfileGroup1RateProfileIndex OBJECT-TYPE
     SYNTAX Integer32(-1|1..256)
     MAX-ACCESS read-write
     STATUS current
     DESCRIPTION
         "Indicates the index of the rate profile bound to Car-group 1.
          -1 indicates priority group car is not configured.
         "
     ::= { hwPriorityGroupProfileEntry 7 }

 hwPriorityGroupProfileGroup2RateProfileIndex OBJECT-TYPE
     SYNTAX Integer32(-1|1..256)
     MAX-ACCESS read-write
     STATUS current
     DESCRIPTION
         "Indicates the index of the rate profile bound to Car-group 2.
          -1 indicates priority group car is not configured.
         "
     ::= { hwPriorityGroupProfileEntry 8 }

 hwPriorityGroupProfileGroup3RateProfileIndex OBJECT-TYPE
     SYNTAX Integer32(-1|1..256)
     MAX-ACCESS read-write
     STATUS current
     DESCRIPTION
         "Indicates the index of the rate profile bound to Car-group 3.
          -1 indicates priority group car is not configured.
         "
     ::= { hwPriorityGroupProfileEntry 9 }

 hwPriorityGroupProfileGroup4RateProfileIndex OBJECT-TYPE
     SYNTAX Integer32(-1|1..256)
     MAX-ACCESS read-write
     STATUS current
     DESCRIPTION
         "Indicates the index of the rate profile bound to Car-group 4.
          -1 indicates priority group car is not configured.
         "
     ::= { hwPriorityGroupProfileEntry 10 }

 hwPriorityGroupProfileGroup5RateProfileIndex OBJECT-TYPE
     SYNTAX Integer32(-1|1..256)
     MAX-ACCESS read-write
     STATUS current
     DESCRIPTION
         "Indicates the index of the rate profile bound to Car-group 5.
          -1 indicates priority group car is not configured.
         "
     ::= { hwPriorityGroupProfileEntry 11 }

 hwPriorityGroupProfileGroup6RateProfileIndex OBJECT-TYPE
     SYNTAX Integer32(-1|1..256)
     MAX-ACCESS read-write
     STATUS current
     DESCRIPTION
         "Indicates the index of the rate profile bound to Car-group 6.
          -1 indicates priority group car is not configured.
         "
     ::= { hwPriorityGroupProfileEntry 12 }

 hwPriorityGroupProfileGroup7RateProfileIndex OBJECT-TYPE
     SYNTAX Integer32(-1|1..256)
     MAX-ACCESS read-write
     STATUS current
     DESCRIPTION
         "Indicates the index of the rate profile bound to Car-group 7.
          -1 indicates priority group car is not configured.
         "
   ::= { hwPriorityGroupProfileEntry 13 }

   -- hwAutoDeleteUnusedProfileTable
   hwAutoDeleteUnusedProfileTable OBJECT IDENTIFIER ::= { hwExtIpdslam 62 }

   hwAutoDeleteUnusedProfileType OBJECT-TYPE
       SYNTAX INTEGER
       {
           trafficTable(1),
           rateProfile(2),
           priorityGroupProfile(3),
           invalidValue(-1)
       }
       MAX-ACCESS read-write
       STATUS current
       DESCRIPTION
           "Indicates the profile type of deleting unused profile.
           Options:
           1. trafficTable(1)             - Traffic table
           2. rateProfile(2)              - Rate profile
           3. priorityGroupProfile(3)     - Pririty group profile
           4. invalidValue(-1)            - Invalid value
           "
       ::= { hwAutoDeleteUnusedProfileTable 1 }

   hwAutoDeleteUnusedProfileOperType OBJECT-TYPE
           SYNTAX INTEGER
           {
               first(1),
               all(2),
               invalidValue(-1)
           }
       MAX-ACCESS  read-write
       STATUS      current
       DESCRIPTION
           "Indicates the operation type of deleting unused profile.
           Options:
           1. first(1)          - Delete first profile
           2. all(2)            - Delete all profile
           3. invalidValue(-1)  - Invalid value
           "
       ::= { hwAutoDeleteUnusedProfileTable 2 }

   -- hwPriorityGroupCarStatTable
   hwPriorityGroupCarStatTable OBJECT-TYPE
       SYNTAX SEQUENCE OF HwPriorityGroupCarStatEntry
       MAX-ACCESS not-accessible
       STATUS current
       DESCRIPTION
           "Used for priority group car statistics collection.
 	   Indicates the table that contains the configuration information of priority group car statistics. It is used to create, modify,
 	   delete and query priority group car statistics.
 	   The indexes of this table are hwPriorityGroupCarStatFlowIndex, hwPriorityGroupCarStatGroupIndex and hwPriorityGroupCarStatDirection.
           "
       ::= { hwExtIpdslam 63 }

   hwPriorityGroupCarStatEntry OBJECT-TYPE
       SYNTAX HwPriorityGroupCarStatEntry
       MAX-ACCESS not-accessible
       STATUS current
       DESCRIPTION
           "Used for priority group car statistics collection.
 	   Indicates the table that contains the configuration information of priority group car statistics. It is used to create, modify,
 	   delete and query priority group car statistics.
 	   The indexes of this entry are hwPriorityGroupCarStatFlowIndex, hwPriorityGroupCarStatGroupIndex and hwPriorityGroupCarStatDirection.
           "
       INDEX { hwPriorityGroupCarStatFlowIndex, hwPriorityGroupCarStatDirection, hwPriorityGroupCarStatGroupIndex }
       ::= { hwPriorityGroupCarStatTable 1 }

   HwPriorityGroupCarStatEntry ::=
       SEQUENCE {
           hwPriorityGroupCarStatFlowIndex
               Integer32,
           hwPriorityGroupCarStatDirection
               INTEGER,
           hwPriorityGroupCarStatGroupIndex
               Integer32,
           hwPriorityGroupCarStatRowStatus
               RowStatus,
           hwPriorityGroupCarStatCountClear
               INTEGER,
           hwPriorityGroupCarStatTimeoutDuration
               Integer32,
           hwPriorityGroupCarStatRunningStatus
               INTEGER,
           hwPriorityGroupCarStatDiscardPackets
               Counter64,
           hwPriorityGroupCarStatRemainTime
               Integer32
             }

   hwPriorityGroupCarStatFlowIndex OBJECT-TYPE
       SYNTAX Integer32
       MAX-ACCESS not-accessible
       STATUS current
       DESCRIPTION
           "Indicates the service flow index, a unique value to identify a service flow.
           "
       ::= { hwPriorityGroupCarStatEntry 1 }

   hwPriorityGroupCarStatDirection OBJECT-TYPE
       SYNTAX INTEGER
       {
           inbound(1),
           outbound(2)
       }
       MAX-ACCESS not-accessible
       STATUS current
       DESCRIPTION
           "Indicates the direction of priority group car statistics.
           Options:
           1.inbound(1)    - indicates the direction of priority group car statistics is inbound
           2.outbound(2)   - indicates the direction of priority group car statistics is outbound
           "
       ::= { hwPriorityGroupCarStatEntry 2 }

   hwPriorityGroupCarStatGroupIndex OBJECT-TYPE
       SYNTAX Integer32 (0..7)
       MAX-ACCESS not-accessible
       STATUS current
       DESCRIPTION
           "Indicates the priority group index of priority group car statistics.
           "
       ::= { hwPriorityGroupCarStatEntry 3 }

   hwPriorityGroupCarStatRowStatus OBJECT-TYPE
       SYNTAX RowStatus
       MAX-ACCESS read-create
       STATUS current
       DESCRIPTION
           "Options:
           1. active(1)
           2. createAndGo(4)
           3. destroy(6)
           "
       ::= { hwPriorityGroupCarStatEntry 4 }

   hwPriorityGroupCarStatCountClear OBJECT-TYPE
       SYNTAX INTEGER
       {
           cleared(1),
           nouse(2)
       }
       MAX-ACCESS read-write
       STATUS current
       DESCRIPTION
           "Clears extended statistics of a specified priority group car.
           This node does not need to be specified during the start of extended statistics
           collection for a priority group car.
           Options:
           1.cleared(1) - reset the statistic to the specified priority group car
           2.nouse(2)   - in the query operation, this leaf is fixed to nouse
           "
       ::= { hwPriorityGroupCarStatEntry 5 }

   hwPriorityGroupCarStatTimeoutDuration OBJECT-TYPE
       SYNTAX Integer32(1..1440 | -1)
       MAX-ACCESS read-write
       STATUS current
       DESCRIPTION
           "Indicates the duration of the priority group-based CAR statistics.
           -1 indicates the priority group-based CAR statistics dose not stop."
       ::= { hwPriorityGroupCarStatEntry 6 }

   hwPriorityGroupCarStatRunningStatus   OBJECT-TYPE
       SYNTAX INTEGER
       {
           running(1),
           timeout(2)
       }
       MAX-ACCESS read-only
       STATUS current
       DESCRIPTION
           "Indicates the current status of statistics collection of a specified priority group car.
           This node has two enumerated values: running and timeout.
           Options:
           1.running(1) -indicate the statistic to the specified priority group car  is running
           2.timeout(2) -indicate the statistic to the specified priority group car  is time out
           "
       ::= { hwPriorityGroupCarStatEntry 7 }

   hwPriorityGroupCarStatDiscardPackets OBJECT-TYPE
       SYNTAX Counter64
       MAX-ACCESS read-only
       STATUS current
       DESCRIPTION
           "Indicates the number of discarded packets of a specified priority group car."
       ::= { hwPriorityGroupCarStatEntry 8 }

   hwPriorityGroupCarStatRemainTime OBJECT-TYPE
       SYNTAX Integer32(0..1440 | -1)
       MAX-ACCESS read-only
       STATUS current
       DESCRIPTION
           "Indicates the remaining time for the priority group-based CAR statistics.
           0 indicates starting priority group-based CAR statistics measurement overtime.
           -1 indicates the priority group-based CAR statistics dose not stop."
       ::= { hwPriorityGroupCarStatEntry 9 }

 hwTrafficInnerPriForceModify OBJECT-TYPE
     SYNTAX INTEGER
     {
         disable(1),
         enable(2)
     }
     MAX-ACCESS read-write
     STATUS current
     DESCRIPTION
         "Indicates the enabling status of the inner priority marking mode of the traffic profile.
          Options:
          1. disable(1) -Indicates that the inner priority marking mode of the traffic profile is disabled
          2. enable(2)  -indicates that the inner priority marking mode of the traffic profile is enabled
          Default: enable(2)
         "
     ::= { hwExtIpdslam 64 }

   hwShapingBurstSizeConfigMode OBJECT-TYPE
       SYNTAX INTEGER
           {
           auto(1),
           manual(2)
           }
       MAX-ACCESS read-write
       STATUS current
       DESCRIPTION
           "Indicates the mode of shaping burst-size configuration mode.
            Options:
            1. auto(1)   -indicates the shaping burst-size configuration mode is auto.
            2. manual(2) -indicates the shaping burst-size configuration mode is manual.
            Default: auto(1)
           "
       ::= { hwExtIpdslam 65 }

   hwXponPortMtuTable OBJECT-TYPE
       SYNTAX SEQUENCE OF HwXponPortMtuEntry
       MAX-ACCESS not-accessible
       STATUS current
       DESCRIPTION
           "Indicates the MTU configuration table of a xPON port.
            It is used for setting the MTU of a xPON port.
            The index of this table is ifIndex.
           "
       ::= { hwExtIpdslam 66 }

   hwXponPortMtuEntry OBJECT-TYPE
       SYNTAX HwXponPortMtuEntry
       MAX-ACCESS not-accessible
       STATUS current
       DESCRIPTION
           "Indicates the MTU configuration table of a xPON port.
            It is used for setting the MTU of a xPON port.
            The index of this entry is ifIndex.
           "
       INDEX { ifIndex }
       ::= { hwXponPortMtuTable 1 }

   HwXponPortMtuEntry ::=
       SEQUENCE {
         hwXponPortMtu
           Integer32
        }

    hwXponPortMtu OBJECT-TYPE
       SYNTAX Integer32 (-1..0|1519..9280)
       MAX-ACCESS read-write
       STATUS current
       DESCRIPTION
           "This object is used for setting the MTU of a xPON port.
	        0 indicates to restore the default value.
			-1 indicates the value is invalid.
	        Range: -1-0, 1519-9280
           "
       ::= { hwXponPortMtuEntry 1 }

--hwQueuePerformanceStatsTable  begin

   hwQueuePerformanceStatsTable OBJECT-TYPE
       SYNTAX SEQUENCE OF HwQueuePerformanceStatsEntry
       MAX-ACCESS not-accessible
       STATUS current
       DESCRIPTION
           "Indicates the information about packets passed or dropped by a queue on a port in a 15-minute or 24-hour statistical period and the information about passed bytes.
            The indexes of this table are ifIndex,hwQueueId,hwQueueStatsIntervalType,and hwQueueStatsIntervalNumId.
           "
       ::= { hwExtIpdslam 67 }

   hwQueuePerformanceStatsEntry OBJECT-TYPE
       SYNTAX HwQueuePerformanceStatsEntry
       MAX-ACCESS not-accessible
       STATUS current
       DESCRIPTION
           "Indicates the information about packets passed or dropped by a queue on a port in a 15-minute or 24-hour statistical period and the information about passed bytes.
            The indexes of this entry are ifIndex,hwQueueId,hwQueueStatsIntervalType,and hwQueueStatsIntervalNumId.
           "
       INDEX { hwQueueifIndex, hwQueueId, hwQueueStatsIntervalType, hwQueueStatsIntervalNumId }
       ::= { hwQueuePerformanceStatsTable 1 }

   HwQueuePerformanceStatsEntry ::=
       SEQUENCE {
              hwQueueStatsIntervalType                             INTEGER,
              hwQueueStatsIntervalNumId                            Integer32,
              hwQueueStatsDroppedYellowNumber                      Counter64,
              hwQueueStatsDroppedGreenNumber                       Counter64,
              hwQueueStatsDroppedUnRecognizedColorNumber           Counter64,
              hwQueueStatsPassedNumber                             Counter64,
              hwQueueStatsPassedBytes                              Counter64,
              hwQueueStatsTimeElapsed                              Integer32,
              hwQueueStatsValidInterval                            TruthValue,
              hwQueueStatsStartTime                                DateAndTime,
              hwQueueStatsPassedGreenBytes                         Counter64,
              hwQueueStatsPassedGreenNumber                        Counter64,
              hwQueueStatsPassedYellowBytes                        Counter64,
              hwQueueStatsPassedYellowNumber                       Counter64
                }

   hwQueueStatsIntervalType OBJECT-TYPE
       SYNTAX INTEGER
           {
           	intervaltime15min(0),
           	everbefore(1)
           }
       MAX-ACCESS not-accessible
       STATUS     current
       DESCRIPTION
           "The type of queue Performance Statistic.
            Options:
            1. intervaltime15min(0)   -current-15minutes or historic-15minutes
            2. everbefore(1)          -everbefore
           "
  ::= { hwQueuePerformanceStatsEntry 1 }

   hwQueueStatsIntervalNumId OBJECT-TYPE
       SYNTAX     Integer32 (0..96)
       MAX-ACCESS not-accessible
       STATUS     current
       DESCRIPTION
           "The interval number of queue Performance Statistic.
	       When hwQueueStatsIntervalType is intervaltime15min, 0 represents current 15 minutes interval.
	       "
       ::= { hwQueuePerformanceStatsEntry 2 }


   hwQueueStatsDroppedYellowNumber OBJECT-TYPE
       SYNTAX Counter64
       MAX-ACCESS read-only
       STATUS current
       DESCRIPTION
           "Indicates the number of dropped yellow packets.
            After a packet is sent downstream, the statistics of dropped packets are increased by 1 if the packet fails to pass.
            '18446744073709551615' means invalid value.
           "
       ::= { hwQueuePerformanceStatsEntry 3 }

   hwQueueStatsDroppedGreenNumber OBJECT-TYPE
       SYNTAX Counter64
       MAX-ACCESS read-only
       STATUS current
       DESCRIPTION
           "Indicates the number of dropped green packets.
            After a packet is sent downstream, the statistics of dropped packets are increased by 1 if the packet fails to pass.
            '18446744073709551615' means invalid value.
           "
       ::= { hwQueuePerformanceStatsEntry 4 }

   hwQueueStatsDroppedUnRecognizedColorNumber OBJECT-TYPE
       SYNTAX Counter64
       MAX-ACCESS read-only
       STATUS current
       DESCRIPTION
           "Indicates the number of dropped unrecognized color packets.
            After a packet is sent downstream, the statistics of dropped packets are increased by 1 if the packet fails to pass.
            '18446744073709551615' means invalid value.
           "
       ::= { hwQueuePerformanceStatsEntry 5 }

   hwQueueStatsPassedNumber OBJECT-TYPE
       SYNTAX Counter64
       MAX-ACCESS read-only
       STATUS current
       DESCRIPTION
           "Indicates the number of pass-through packets.
            After a packet is sent downstream, the statistics of pass-through packets are increased by 1 if the packet passes.
            '18446744073709551615' means invalid value.
           "
       ::= { hwQueuePerformanceStatsEntry 6 }

   hwQueueStatsPassedBytes OBJECT-TYPE
       SYNTAX Counter64
       MAX-ACCESS read-only
       STATUS current
       DESCRIPTION
           "Indicates the number of pass-through bytes.
            After a byte is sent downstream, the statistics of pass-through bytes are increased by 1 if the byte passes.
            '18446744073709551615' means invalid value.
           "
       ::= { hwQueuePerformanceStatsEntry 7 }

   hwQueueStatsTimeElapsed OBJECT-TYPE
       SYNTAX Integer32
       MAX-ACCESS read-only
       STATUS current
       DESCRIPTION
           "The elapsed time of the current interval.
           '-1' means invalid value."
       ::= { hwQueuePerformanceStatsEntry 8 }

   hwQueueStatsValidInterval OBJECT-TYPE
       SYNTAX TruthValue
       MAX-ACCESS read-only
       STATUS     current
       DESCRIPTION
           "Whether the interval number is valid."
       ::= { hwQueuePerformanceStatsEntry 9 }

    hwQueueStatsStartTime OBJECT-TYPE
       SYNTAX     DateAndTime
       MAX-ACCESS read-only
       STATUS     current
       DESCRIPTION
           "Start time of the interval.
           "
       ::= { hwQueuePerformanceStatsEntry 10 }

    hwQueueStatsPassedGreenBytes OBJECT-TYPE
       SYNTAX Counter64
       MAX-ACCESS read-only
       STATUS current
       DESCRIPTION
           "Indicates the number of pass-through bytes of green packets.
            After a byte is sent downstream, the statistics of pass-through bytes are increased by 1 if the byte passes.
           '18446744073709551615' means invalid value.
           "
       ::= { hwQueuePerformanceStatsEntry 11 }

   hwQueueStatsPassedGreenNumber OBJECT-TYPE
       SYNTAX Counter64
       MAX-ACCESS read-only
       STATUS current
       DESCRIPTION
           "Indicates the number of pass-through green packets.
            After a packet is sent downstream, the statistics of pass-through packets are increased by 1 if the packet passes.
            '18446744073709551615' means invalid value.
           "
       ::= { hwQueuePerformanceStatsEntry 12 }

   hwQueueStatsPassedYellowBytes OBJECT-TYPE
       SYNTAX Counter64
       MAX-ACCESS read-only
       STATUS current
       DESCRIPTION
           "Indicates the number of pass-through bytes of yellow packets.
            After a byte is sent downstream, the statistics of pass-through bytes are increased by 1 if the byte passes.
           '18446744073709551615' means invalid value.
           "
       ::= { hwQueuePerformanceStatsEntry 13 }

   hwQueueStatsPassedYellowNumber OBJECT-TYPE
       SYNTAX Counter64
       MAX-ACCESS read-only
       STATUS current
       DESCRIPTION
           "Indicates the number of pass-through yellow packets.
           	After a packet is sent downstream, the statistics of pass-through packets are increased by 1 if the packet passes.
            '18446744073709551615' means invalid value.
           "
       ::= { hwQueuePerformanceStatsEntry 14 }

--hwQueuePerformanceStatsTable  end

-- hwLanBoardExtTable
   hwExtLanBoard OBJECT IDENTIFIER ::= { hwEthernetPort 4 }

-- hwLanBoardExtTable
   hwLanBoardExtTable OBJECT-TYPE
       SYNTAX SEQUENCE OF HwLanBoardExtEntry
       MAX-ACCESS not-accessible
       STATUS current
       DESCRIPTION
           "Extended attribute table of LAN board.
            The indexes of this table are hwFrameIndex and hwSlotIndex.
           "
       ::= { hwExtLanBoard 1 }

   hwLanBoardExtEntry OBJECT-TYPE
       SYNTAX HwLanBoardExtEntry
       MAX-ACCESS not-accessible
       STATUS current
       DESCRIPTION
           "Extended attribute table of LAN board.
            The indexes of this entry are hwFrameIndex and hwSlotIndex.
           "
       INDEX { hwFrameIndex, hwSlotIndex }
       ::= { hwLanBoardExtTable 1 }

   HwLanBoardExtEntry ::=
       SEQUENCE {
           hwLanBoardExtWorkMode
               INTEGER,
           hwLanBoardExtPriorityControl
               INTEGER,
           hwLanBoardExtMulticastControl
               Integer32,
           hwLanBoardExtUnknowncastControl
               Integer32,
           hwLanBoardExtLogicLoop
               INTEGER,
           hwLanBoardExtBroadcastControl
               Integer32,
           hwLanBoardExtLowPriorityRatio
               Integer32,
           hwLanBoardExtHighPriorityRatio
               Integer32,
           hwLanBoardExtGMIIPauseFrameControl
               INTEGER,
           hwLanBoardExtPriorityLevel
               Integer32,
           hwLanBoardExtPitpStatus
               INTEGER,
           hwLanBoardExtPitpEthernetType
               Integer32,
           hwLanBoardExtPitpPortTagType
               Integer32,
           hwLanBoardExtPitpInfoTagType
               Integer32
        }

   hwLanBoardExtWorkMode OBJECT-TYPE
       SYNTAX INTEGER
           {
           general(1),
           ipdslam(2),
           atmgroup(3),
           ipcascade(4)
           }
       MAX-ACCESS read-write
       STATUS current
       DESCRIPTION
           "Mode of the LAN board.
            Options:
            1. general(1)   -Indicates normal mode, in which the chip of LSW works normally.
            2. ipdslam(2)   -Indicatse IPDSLAM mode, the VLAN function of LSW chip is replaced by logic.
            3. atmgroup(3)  -Indicatse ATM group mode, applied to the multicast of ATM mode,
                             which supports not only the VLAN connection from xDSL to the LAN board,
                             but also the connection between VLAN and other ATM ports in the LAN.
            4. ipcascade(4) -Indicates IP cascade mode.
           "
       ::= { hwLanBoardExtEntry 1 }

   hwLanBoardExtPriorityControl OBJECT-TYPE
       SYNTAX INTEGER
           {
           enabled(1),
           disabled(2)
           }
       MAX-ACCESS read-write
       STATUS current
       DESCRIPTION
           "Whether the LAN board supports the function of priority control.
           Options:
           1. enabled(1)  -Indicates the order of priority for each connection can also be specified.
           2. disabled(2) -Indicates the order of priority for each connection can't also be specified.
           "
       ::= { hwLanBoardExtEntry 2 }

   hwLanBoardExtMulticastControl OBJECT-TYPE
       SYNTAX Integer32
       MAX-ACCESS read-write
       STATUS current
       DESCRIPTION
           "
           The traffic suppression of broadcast packet, in unit of packet/second.
           "
       ::= { hwLanBoardExtEntry 3 }

   hwLanBoardExtUnknowncastControl OBJECT-TYPE
       SYNTAX Integer32
       MAX-ACCESS read-write
       STATUS current
       DESCRIPTION
           "
           The traffic suppression of unknown unicast, in unit of packet/second.
           "
       ::= { hwLanBoardExtEntry 4 }

   hwLanBoardExtLogicLoop OBJECT-TYPE
       SYNTAX INTEGER
           {
           noLoopback(1),
           gmiiRemote(2),
           utoipaRemote(3)
           }
       MAX-ACCESS read-write
       STATUS current
       DESCRIPTION
           "LAN board loopback mode.
           Options:
           1. noLoopback(1)    -Cancel loopback.
           2. gmiiRemote(2)    -GMII remote loopback.
           3. utoipaRemote(3)  -UTOPIA remote loopback.
           "
       ::= { hwLanBoardExtEntry 5 }

   hwLanBoardExtBroadcastControl OBJECT-TYPE
       SYNTAX Integer32
       MAX-ACCESS read-write
       STATUS current
       DESCRIPTION
           "
           Traffic suppression of broadcast packet control, in unit of packet/second.
           "
       ::= { hwLanBoardExtEntry 6 }


   hwLanBoardExtLowPriorityRatio OBJECT-TYPE
       SYNTAX Integer32 (1..15)
       MAX-ACCESS read-write
       STATUS current
       DESCRIPTION
           "Default low priority use for filling 802.1p field in ethernet packet upstream."
       ::= { hwLanBoardExtEntry 7 }

   hwLanBoardExtHighPriorityRatio OBJECT-TYPE
       SYNTAX Integer32 (1..15)
       MAX-ACCESS read-write
       STATUS current
       DESCRIPTION
           "Default high priority use for filling 802.1p field in ethernet packet upstream."
       ::= { hwLanBoardExtEntry 8 }

   hwLanBoardExtGMIIPauseFrameControl OBJECT-TYPE
       SYNTAX INTEGER
           {
           enabled(1),
           disabled(2)
           }
       MAX-ACCESS read-write
       STATUS current
       DESCRIPTION
           "Indicates if the LAN board support the function of priority control.
           Options:
           1. enabled(1)   -The LAN board can support the function of priority control.
           2. disabled(2)  -The LAN board can't support the function of priority control.
           "
       ::= { hwLanBoardExtEntry 9 }

   hwLanBoardExtPriorityLevel  OBJECT-TYPE
       SYNTAX Integer32 (0..6)
       MAX-ACCESS read-write
       STATUS current
       DESCRIPTION
           "
           The level will limit for priority level, eg.level equal 2,so low priority scope is 0-2,
           high priority scope is 3-7.
           "
       ::= { hwLanBoardExtEntry 10 }

   hwLanBoardExtPitpStatus  OBJECT-TYPE
       SYNTAX INTEGER
           {
           pitpoff(1),
           pitpvmodeenable(2),
           pitppmodeenable(3)
           }
       MAX-ACCESS read-write
       STATUS current
       DESCRIPTION
           "PITP switch state.
           Options:
           1. pitpoff(1)           -Indicates PITP vmode and pmode are both disable.
           2. pitpvmodeenable(2)   -Indicates PITP vmode enable.
           3. pitppmodeenable(3)   -Indicates PITP pmode enable.
           "
       DEFVAL { pitpoff }
       ::= { hwLanBoardExtEntry 11 }

   hwLanBoardExtPitpEthernetType  OBJECT-TYPE
       SYNTAX Integer32 (1536..65535)
       MAX-ACCESS read-write
       STATUS current
       DESCRIPTION
           "
           The ethernet protocol type of PITP PDU, the default is 0x8200.
           "
       DEFVAL { 33280 }
       ::= { hwLanBoardExtEntry 12 }

   hwLanBoardExtPitpPortTagType  OBJECT-TYPE
       SYNTAX Integer32 (1..65535)
       MAX-ACCESS read-write
       STATUS current
       DESCRIPTION
           "
           The port tag type of PITP PDU, the default is 0x0110.
           "
       DEFVAL { 272 }
       ::= { hwLanBoardExtEntry 13 }

   hwLanBoardExtPitpInfoTagType  OBJECT-TYPE
       SYNTAX Integer32 (1..65535)
       MAX-ACCESS read-write
       STATUS current
       DESCRIPTION
           "
           The infomation tag type of PITP PDU, the default is 0x0111.
           "
       DEFVAL { 273 }
       ::= { hwLanBoardExtEntry 14 }

--   traps
   hwEthernetTraps OBJECT IDENTIFIER ::= { hwEthernetPort 10 }

   hwEthernetTrapVarBindOids OBJECT IDENTIFIER ::= { hwEthernetTraps 0 }

   hwEthernetCommonTraps OBJECT IDENTIFIER ::= { hwEthernetTraps 1 }
   hwEthernetCommonTrapsOids OBJECT IDENTIFIER ::= { hwEthernetCommonTraps 0 }

   hwEthernetGeneralVarBindOids OBJECT IDENTIFIER ::= { hwEthernetTrapVarBindOids 1 }

   hwBitsPortStateChangeType OBJECT-TYPE
       SYNTAX INTEGER
        {
        up(1),
        down(2)
        }
       MAX-ACCESS accessible-for-notify
       STATUS current
       DESCRIPTION
         "
         Options:
         1. up(1)          -port state change to up from down
         2. down(2)        -port state change to down from up
         "
       ::= { hwEthernetGeneralVarBindOids 1 }

   hwBindResult OBJECT-TYPE
       SYNTAX Integer32
       MAX-ACCESS accessible-for-notify
       STATUS current
       DESCRIPTION
           "The result of binding board.
            0  means the result OK
            1  means the result error
           "
       ::= {  hwEthernetGeneralVarBindOids 2 }

   hwBindOperateFlag OBJECT-TYPE
       SYNTAX Integer32
       MAX-ACCESS accessible-for-notify
       STATUS current
       DESCRIPTION
           "The operate type of binding board.
           1 means to create bind group
           2 means to delete bind group
           4 means to add bind group member
           5 means to delete bind group member
           "
       ::= {  hwEthernetGeneralVarBindOids 3 }

   hwPortSpeedType OBJECT-TYPE
       SYNTAX INTEGER
       {
       ge(1),
       fe(2),
       ge10(3)
        }
       MAX-ACCESS accessible-for-notify
       STATUS current
       DESCRIPTION
           "The switched speed type of port.
            Options:
            1. ge(1)          -the switched speed type of port is ge
            2. fe(2)          -the switched speed type of port is fe
            3. ge10(3)        -the switched speed type of port is ge10
           "
       ::= {  hwEthernetGeneralVarBindOids 4 }

   hwPortChangeState OBJECT-TYPE
       SYNTAX      INTEGER
       {
       up(1),
       down (2)
        }
       MAX-ACCESS accessible-for-notify
       STATUS current
       DESCRIPTION
           "The state of the ETH port.
            Options:
            1. up(1)          -port state change to up from down
            2. down(2)        -port state change to down from up
           "
       ::= {  hwEthernetGeneralVarBindOids 5 }

   hwSrvOperType OBJECT-TYPE
       SYNTAX INTEGER
       {
       add(1),
       modify(2),
       delete(3)
       }
       MAX-ACCESS accessible-for-notify
       STATUS current
       DESCRIPTION
           "The operation type of the traffic stream.
            Options:
            1. add(1)    -means to create a traffic stream.
            2. modify(2) -means to modify a traffic stream (this operation is not supported currently).
            3. delete(3) -means to delete a traffic stream (this operation is not supported currently).
           "
       ::= {  hwEthernetGeneralVarBindOids 6 }

   hwSrvAttrChangeType OBJECT-TYPE
       SYNTAX BITS
       {
       tagRuleChanged(0),
       adminStatusChanged(1),
       inboundIndexChanged(2),
       outboundIindexChanged(3),
       inboundNameChanged(4),
       outboundNameChanged(5),
       upInnerVlanChanged(6),
       upInnerPriorityChanged(7),
       macLearnChanged(8),
       descriptionChanged(9),
       remoteDescriptionChanged(10),
       ontPortlistChanged(11)
       }
       MAX-ACCESS accessible-for-notify
       STATUS current
       DESCRIPTION
           "
           It means to modify the mask corresponding to the traffic stream attribute.
           Currently, multiple traffic stream attributes can be modified at a time.
           The description for each BIT of the reported traffic stream attribute mask is as follows.
           tagRuleChanged(0)            -indicates to modify the VLAN tag transforming mode of the traffic stream.
           adminStatusChanged(1)        -indicates to modify the administration status of the traffic stream.
           inboundIndexChanged(2)       -indicates to modify the index of the inbound traffic profile referenced by the traffic stream.
           outboundIindexChanged(3)      -indicates to modify the index of the outbound traffic profile referenced by the traffic stream.
           inboundNameChanged(4)        -indicates to modify the name of the inbound traffic profile referenced by the traffic stream.
           outboundNameChanged(5)       -indicates to modify the name of the outbound traffic profile referenced by the traffic stream.
           upInnerVlanChanged(6)       -indicates to modify the network inner VLAN tag of the traffic stream.
           upInnerPriorityChanged(7)   -indicates to modify the inner VLAN priority of the traffic stream.
           macLearnChanged(8)           -indicates to modify the maximum number of learnable dynamic MAC addresses of the traffic stream.
           descriptionChanged(9)         -indicates to modify the description of the traffic stream.
           remoteDescriptionChanged(10) -indicates to modify the remote description of the traffic stream.
           ontPortlistChanged(11)       -indicates to modify the ONT port list of the traffic stream.
           The mask has 32 bits in total. Note that in a byte, the high bit indicates a small attribute value.
           For example, if bit 1 is set to 1, this bit indicates adminStatusChanged.
            ---------------------------------------------------------------------
            |                     bit0-bit11                      | bit12-bit31 |
            ---------------------------------------------------------------------
            | tagRuleChanged(0)--ontPortlistChanged(11)       |  Reserved   |
            ---------------------------------------------------------------------
           "
       ::= {  hwEthernetGeneralVarBindOids 7 }

   hwSrvFlowBundleChangedOperType OBJECT-TYPE
       SYNTAX INTEGER
       {
       add(1),
       delete(2)
       }
       MAX-ACCESS accessible-for-notify
       STATUS current
       DESCRIPTION
           "The service virtual port bundle operate type.
            Options:
            1. add(1)    -indicates add the service virtual port bundle
            2. delete(2) -indicates delete the service virtual port bundle
           "
       ::= {  hwEthernetGeneralVarBindOids 8 }

   hwSrvFlowBundleChangedBundleStr OBJECT-TYPE
       SYNTAX OCTET STRING (SIZE(0..256))
       MAX-ACCESS accessible-for-notify
       STATUS current
       DESCRIPTION
           "The service virtual port bundle index."
       ::= {  hwEthernetGeneralVarBindOids 9 }

   hwSrvFlowBundleChangedBundleType OBJECT-TYPE
       SYNTAX INTEGER
       {
       byPbit(1)
       }
       MAX-ACCESS accessible-for-notify
       STATUS current
       DESCRIPTION
           "The service virtual port bundle type.
           Currently, only one type is supported, that is, byPbit(1),
           which indicates that the service flow bundle is for L3 access,
           and that the service flows are classified for 802.1p(P-Bits) CoS purpose.
           Options:
           1. byPbit(1) -indicates that the service flow bundle is for L3 access
                         and that the service flows are classified for 802.1p(P-Bits) CoS purpose
           "
       ::= {  hwEthernetGeneralVarBindOids 10 }

   hwSrvFlowBatOperType OBJECT-TYPE
       SYNTAX INTEGER
   		 {
       batdeleteflow(1),
       batdeleteflowdesc(2),
       batdeleteflowremotedesc(3),
       batmodifyflowmaxmacaddressnum(4)
       }
       MAX-ACCESS accessible-for-notify
       STATUS current
       DESCRIPTION
           "The service virtual port bat operation type.
           Options:
           1. batdeleteflow(1)                 -indicates to batch deleting the service flow port
           2. batdeleteflowdesc(2)             -indicates to batch deleting the description of the service flow port
           3. batdeleteflowremotedesc(3)       -indicates to batch deleting the remote description of the service flow port
           4. batmodifyflowmaxmacaddressnum(4) -indicates to batch modifying the mac-address max-mac-count of the service flow port
           "
       ::= {  hwEthernetGeneralVarBindOids 11 }

   hwSrvFlowBatOperPara OBJECT-TYPE
       SYNTAX Integer32
       MAX-ACCESS accessible-for-notify
       STATUS current
       DESCRIPTION
           "The value of service virtual port parameter.
           Currently, only the value of the parameter is supported, that is, the mac-address max-mac-count
           of the service flow port. When the hwSrvFlowBatOperType is batmodifyflowmaxmacaddressnum,the value of
           hwSrvFlowBatOperPara is from 0 to 1023.Others, the value is invalid.
           "
       ::= {  hwEthernetGeneralVarBindOids 12 }

   hwSrvFlowBatModiyNum OBJECT-TYPE
       SYNTAX Integer32
       MAX-ACCESS accessible-for-notify
       STATUS current
       DESCRIPTION
           "The nueber of the service virtual port.
           Currently, the max value of hwSrvFlowBatModiyNum is 256.
           "
       ::= {  hwEthernetGeneralVarBindOids 13 }

   hwSrvFlowBatFlowIndexList OBJECT-TYPE
       SYNTAX OCTET STRING
       MAX-ACCESS accessible-for-notify
       STATUS current
       DESCRIPTION
            "Indicates the list of service flow indexes, each index in the list identifies a service flow uniquely.
            Currently, the max length of the list is 1024, including 256 flow indexes. Per flow index uses four bytes.
            "
       ::= {  hwEthernetGeneralVarBindOids 14 }

   hwResourceOverloadAwareCurValue OBJECT-TYPE
       SYNTAX OCTET STRING
       MAX-ACCESS accessible-for-notify
       STATUS current
       DESCRIPTION
            "Indicates the current resource occupancy.
            "
       ::= {  hwEthernetGeneralVarBindOids 15 }

   hwEthernetLoopbackTestResult OBJECT-TYPE
       SYNTAX INTEGER
       {
       success(1),
       fail(2)
       }
       MAX-ACCESS accessible-for-notify
       STATUS current
       DESCRIPTION
            "Indicates the result of loopback test.
            Options:
            1. success(1) -indicates that the result of loopback test is successful.
            2. fail(2)    -indicates that the result of loopback test is failed.
            "
       ::= {  hwEthernetGeneralVarBindOids 16 }

   hwEthernetLoopbackTestTxFrames OBJECT-TYPE
       SYNTAX Unsigned32
       MAX-ACCESS accessible-for-notify
       STATUS current
       DESCRIPTION
            "Indicates the number of transmitted frames.
            "
       ::= {  hwEthernetGeneralVarBindOids 17 }

   hwEthernetLoopbackTestRxFrames OBJECT-TYPE
       SYNTAX Unsigned32
       MAX-ACCESS accessible-for-notify
       STATUS current
       DESCRIPTION
            "Indicates the number of received frames.
            "
       ::= {  hwEthernetGeneralVarBindOids 18 }

   hwEthernetLoopbackTestPacketLossRatio OBJECT-TYPE
       SYNTAX Unsigned32
       MAX-ACCESS accessible-for-notify
       STATUS current
       DESCRIPTION
            "Indicates the ratio of packet loss.
            Range: 0-100
            "
       ::= {  hwEthernetGeneralVarBindOids 19 }

   hwEthernetMirrorDirection OBJECT-TYPE
       SYNTAX OCTET STRING
       MAX-ACCESS accessible-for-notify
       STATUS current
       DESCRIPTION
            "Indicates the direction of mirror.
            Directions including egress, ingress and all are supported currently."
       ::= {  hwEthernetGeneralVarBindOids 20 }

   hwMirrorSrcPortDescription OBJECT-TYPE
       SYNTAX OCTET STRING
       MAX-ACCESS accessible-for-notify
       STATUS current
       DESCRIPTION
            "Indicates the description of the source port, with the format frameId/slotId/portid."
       ::= {  hwEthernetGeneralVarBindOids 21 }

   hwMirrorDstPortDescription OBJECT-TYPE
       SYNTAX OCTET STRING
       MAX-ACCESS accessible-for-notify
       STATUS current
       DESCRIPTION
            "Indicates the description of the destination port with the format frameId/slotId/portid or meth."
       ::= {  hwEthernetGeneralVarBindOids 22 }

   hwAutoServiceAddContent OBJECT-TYPE
       SYNTAX OCTET STRING
       MAX-ACCESS accessible-for-notify
       STATUS current
       DESCRIPTION
            "Contents for automatic service port creation upon an ONT being online."
       ::= {  hwEthernetGeneralVarBindOids 23 }

   hwAutoServiceProcResult OBJECT-TYPE
       SYNTAX OCTET STRING
       MAX-ACCESS accessible-for-notify
       STATUS current
       DESCRIPTION
            "Results for automatic service port creation upon an ONT being online."
       ::= {  hwEthernetGeneralVarBindOids 24 }

    hwMacAddressFlappingPortInfo OBJECT-TYPE
       SYNTAX OCTET STRING
       MAX-ACCESS accessible-for-notify
       STATUS current
       DESCRIPTION
            "Paras for MAC flapping."
       ::= {  hwEthernetGeneralVarBindOids 25 }

    hwFlappingMacAddress OBJECT-TYPE
       SYNTAX MacAddress
       MAX-ACCESS accessible-for-notify
       STATUS current
       DESCRIPTION
           "The flapping MAC address.
           "
       ::= { hwEthernetGeneralVarBindOids 26  }

   hwTrafficUpportMonitorUpstreamLast OBJECT-TYPE
      SYNTAX Integer32
      MAX-ACCESS accessible-for-notify
      STATUS current
      DESCRIPTION
          "Last Upstream Traffic.
          "
      ::= { hwEthernetGeneralVarBindOids 27  }

   hwTrafficUpportMonitorUpstream OBJECT-TYPE
      SYNTAX Integer32
      MAX-ACCESS accessible-for-notify
      STATUS current
      DESCRIPTION
          "Current Upstream Traffic.
          "
      ::= { hwEthernetGeneralVarBindOids 28  }

   hwTrafficUpportMonitorDownstreamLast OBJECT-TYPE
      SYNTAX Integer32
      MAX-ACCESS accessible-for-notify
      STATUS current
      DESCRIPTION
          "Last Downstream Traffic.
          "
      ::= { hwEthernetGeneralVarBindOids 29  }

   hwTrafficUpportMonitorDownstream OBJECT-TYPE
      SYNTAX Integer32
      MAX-ACCESS accessible-for-notify
      STATUS current
      DESCRIPTION
          "Current Downstream Traffic.
          "
      ::= { hwEthernetGeneralVarBindOids 30  }

   hwIpdslamDisplayLocationTrap NOTIFICATION-TYPE
       OBJECTS    {
                  hwIpdslamQryType ,
                  hwIpdslamQryCondition ,
                  ifIndex,
                  hwExtSrvFlowIndex,
                  hwVlanIndex,
                  hwIpdslamQryConditionFlowBundleIndex,
                  hwIpdslamQryConditionPwIndex,
                  hwIpdslamQryConditionOntId
                  }
       STATUS current
       DESCRIPTION
           "Trap of display location query.
            The trap that is generated when IP or MAC address changed."
       ::= { hwEthernetCommonTrapsOids 1 }

   hwQryGlobalStatisticTrap NOTIFICATION-TYPE
       OBJECTS    {
                  hwActivedXdslPortNum ,
                  hwActivedOntNum ,
                  hwActivedEthPortNum,
                  hwUplinkPortUpKbps,
                  hwUplinkPortDownKbps,
                  hwUplinkPortUpBandwidthOccupancyRate,
                  hwUplinkPortDownBandwidthOccupancyRate,
                  hwXponUniPortUpKbps,
                  hwXponUniPortDownKbps,
                  hwUpLinkPortMCastUpPercent,
                  hwUpLinkPortBCastUpPercent,
                  hwUpLinkPortUCastUpPercent,
                  hwUpLinkPortMCastDownPercent,
                  hwUpLinkPortBCastDownPercent,
                  hwUpLinkPortUCastDownPercent
                  }
       STATUS current
       DESCRIPTION
           "Trap of one key mode of query flow quantity.
            The trap that is generated when query global statistics."
       ::= { hwEthernetCommonTrapsOids 2 }

   hwBitsPortStatusChangeInfoTrap NOTIFICATION-TYPE
      OBJECTS    { hwFrameIndex, hwSlotIndex, hwPortIndex, hwBitsPortStateChangeType }
      STATUS current
      DESCRIPTION
          " The trap generated when BITS port state changes"
      ::= { hwEthernetCommonTrapsOids 3 }

   hwBindBoardOprateResultInfoTrap NOTIFICATION-TYPE
      OBJECTS    {
                 hwBindResult,
                 hwBindOperateFlag,
                 hwFrameIndex,
                 hwSlotIndex,
                 hwFrameIndex,
                 hwSlotIndex
                 }
      STATUS current
      DESCRIPTION
          " The trap generated when bind board or undo bind board, The first two FrameIndex And SlotIndex is Masterborad, and the other is SlaveBoard"
      ::= { hwEthernetCommonTrapsOids 4 }

   hwPortSpeedTypeSwitchResultInfoTrap NOTIFICATION-TYPE
      OBJECTS    {
                 hwFrameIndex,
                 hwSlotIndex,
                 hwPortIndex,
                 hwPortSpeedType
                 }
      STATUS current
      DESCRIPTION
          " The trap generated when port speed type switched"
      ::= { hwEthernetCommonTrapsOids 5 }

   hwPortStateChangeInfoTrap NOTIFICATION-TYPE
       OBJECTS    {
                  hwFrameIndex,
                  hwSlotIndex,
                  hwPortIndex,
                  hwPortChangeState,
                  hwPortPrimaryStatus,
                  hwPortSecondaryStatus
                  }
       STATUS current
       DESCRIPTION
           "  This trap message is generated when the port status changes,
              for example from up to down or from down to up. The parameter
              information about the trap message describes the current status
              of the link and the location where the trap message is generated.
              "
       ::= { hwEthernetCommonTrapsOids 6 }

   hwIpTrafficParamChangeTrap NOTIFICATION-TYPE
      OBJECTS    {
                 hwConfigChangeIP,
                 hwIpTrafficParamChangeCause,
                 hwIpTrafficIndex,
                 hwIpTrafficName,
                 hwIpTrafficCir,
                 hwIpTrafficCbs,
                 hwIpTrafficPir,
                 hwIpTrafficPbs,
                 hwIpTrafficParamPriority,
                 hwIpTrafficParamPriorityMappingPolicy,
                 hwIpTrafficPriorityPolicy,
                 hwIpTrafficCm,
                 hwIpTrafficColorPolicy,
                 hwIpTrafficFixBandWidth,
                 hwIpTrafficDSCP,
                 hwIpTrafficDSCPMappingIndex,
                 hwIpTrafficDropPrecedence,
                 hwIpTrafficColorDEI,
                 hwIpTrafficColorSource,
                 hwIpTrafficWrrWeightYellow,
                 hwIpTrafficWrrWeightGreen
                 }
      STATUS current
      DESCRIPTION
          "The trap generated when ip traffic profile created, deleted or modified."
      ::= { hwEthernetCommonTrapsOids 7 }

   hwPortAutounloopSwitchInfoTrap NOTIFICATION-TYPE
       OBJECTS    {
                  hwFrameIndex,
                  hwSlotIndex,
                  hwPortIndex
                  }
       STATUS current
       DESCRIPTION
           "A trap message is generated when the loopback on a port is canceled automatically."
       ::= { hwEthernetCommonTrapsOids 8 }

   hwSrvAddInfoTrap NOTIFICATION-TYPE
       OBJECTS    {
                  hwConfigChangeIP,
                  hwSrvOperType,
                  hwExtSrvFlowIndex,
                  hwExtSrvFlowMultiServiceType,
                  hwExtSrvFlowMultiServiceUserPara,
                  hwExtSrvFlowPara1,
                  hwExtSrvFlowPara2,
                  hwExtSrvFlowPara3,
                  hwExtSrvFlowPara4,
                  hwExtSrvFlowPara5,
                  hwExtSrvFlowParaType,
                  hwExtSrvFlowVlanid,
                  hwExtSrvFlowReceiveTrafficDescrIndex,
                  hwExtSrvFlowTransmitTrafficDescrIndex,
                  hwExtSrvFlowAdminStatus,
                  hwExtSrvFlowSimulationServiceType,
                  hwExtSrvFlowInboundTrafficTableName,
                  hwExtSrvFlowOutboundTrafficTableName,
                  hwExtSrvFlowInnerVlanId,
                  hwExtSrvFlowSourceType,
                  hwExtSrvFlowDestinationType,
                  hwExtSrvFlowSourceParaType,
                  hwExtSrvFlowSourcePara1,
                  hwExtSrvFlowSourcePara2,
                  hwExtSrvFlowSourcePara3,
                  hwExtSrvFlowSourcePara4,
                  hwExtSrvFlowSourcePara5,
                  hwExtSrvFlowSourceMultiServiceType,
                  hwExtSrvFlowSourceMultiServiceUserPara,
                  hwExtSrvFlowSourceInnerVlanId,
                  hwExtSrvFlowBundleIndex,
                  hwExtSrvFlowBundleMemberSortPara
                  }
       STATUS current
       DESCRIPTION
           "This trap is sent when a traffic stream is set up."
       ::= { hwEthernetCommonTrapsOids 9 }

   hwSrvDelInfoTrap NOTIFICATION-TYPE
       OBJECTS    {
                  hwConfigChangeIP,
                  hwExtSrvFlowIndex
                  }
       STATUS current
       DESCRIPTION
           "This trap is sent when a traffic stream is deleted."
       ::= { hwEthernetCommonTrapsOids 10 }

   hwSrvAttrChangedInfoTrap NOTIFICATION-TYPE
       OBJECTS    {
                  hwConfigChangeIP,
                  hwExtSrvFlowIndex,
                  hwSrvAttrChangeType,
                  hwExtSrvFlowTagTransform,
                  hwExtSrvFlowAdminStatus,
                  hwExtSrvFlowTransmitTrafficDescrIndex,
                  hwExtSrvFlowReceiveTrafficDescrIndex,
                  hwExtSrvFlowInboundTrafficTableName,
                  hwExtSrvFlowOutboundTrafficTableName,
                  hwExtSrvFlowNNIInnerVlanId,
                  hwExtSrvFlowNNIInnerPriority,
                  hwIpdslamConnectMaxMacLearn,
                  hwExtSrvFlowDescInfo,
                  hwExtSrvFlowRemoteDescInfo,
                  hwExtSrvFlowPara5
                  }
       STATUS current
       DESCRIPTION
           "This trap is sent when the traffic stream attribute is modified."
       ::= { hwEthernetCommonTrapsOids 11 }

   hwSrvFlowBundleTrap NOTIFICATION-TYPE
      OBJECTS    {
              hwConfigChangeIP,
              hwSrvFlowBundleChangedBundleStr,
              hwSrvFlowBundleChangedBundleType,
              hwSrvFlowBundleChangedOperType
              }
      STATUS current
      DESCRIPTION
          "The trap generated when service virtual port bundle created or deleted."
      ::= { hwEthernetCommonTrapsOids 12 }

    hwSrvFlowBatModifyInfoTrap NOTIFICATION-TYPE
      OBJECTS    {
              hwConfigChangeIP,
              hwSrvFlowBatOperType,
              hwSrvFlowBatOperPara,
              hwSrvFlowBatModiyNum,
              hwSrvFlowBatFlowIndexList
              }
      STATUS current
      DESCRIPTION
          "The trap generated when service virtual port batch modifyed."
      ::= { hwEthernetCommonTrapsOids 13 }

    hwEthernetLoopbackTestTrap NOTIFICATION-TYPE
      OBJECTS    {
              ifIndex,
              hwEthernetLoopbackTestResult,
              hwEthernetLoopbackTestTxFrames,
              hwEthernetLoopbackTestRxFrames,
              hwEthernetLoopbackTestPacketLossRatio
              }
      STATUS current
      DESCRIPTION
          "This trap will be sent when a ethernet loopback test finished successfully. The trap shows the result of the loopback test."
      ::= { hwEthernetCommonTrapsOids 14 }

    hwEthernetPortCfgChangeTrap NOTIFICATION-TYPE
      OBJECTS    {
              hwConfigChangeIP,
              hwFrameIndex,
              hwSlotIndex,
              hwPortIndex
              }
      STATUS current
      DESCRIPTION
          "The trap generated when ethernet port configuration modified."
      ::= { hwEthernetCommonTrapsOids 15 }

    hwEthernetPortAggCfgChangeTrap NOTIFICATION-TYPE
      OBJECTS     {
                  hwConfigChangeIP,
                  hwFrameIndex,
                  hwSlotIndex,
                  hwPortIndex
                  }
      STATUS current
      DESCRIPTION
          "The trap generated when a link-aggregation group of Ethernet ports is created, modified or deleted.
           If you run this command with all specified, the system reports only one trap with hwPortIndex set to 255 for boards configured with link aggregation.
          "
      ::= { hwEthernetCommonTrapsOids 16 }

   hwEthernetAlarmTraps OBJECT IDENTIFIER ::= { hwEthernetTraps 2 }
   hwEthernetAlarmTrapsOids OBJECT IDENTIFIER ::= { hwEthernetAlarmTraps 0 }

   hwAlarmEthernetPortOffline NOTIFICATION-TYPE
       OBJECTS { hwPortIndex }
       STATUS current
       DESCRIPTION
           "Alarm description: port offline
            explanation: LAN port offline, the line is not connected
            resolving method: change the line or check the peer port
            alarm description: the port is offline.
            The trap generated when the port is offline.
           "
       ::= { hwEthernetAlarmTrapsOids 1 }

   hwAlarmEthernetPeerPortNoNeg NOTIFICATION-TYPE
       OBJECTS { hwPortIndex }
       STATUS current
       DESCRIPTION
           "Alarm description: peer port does not support auto-negotiation.
           Explanation: this port is auto-negotiation alarm, while the peer port is non-auto-negotiation alarm.
           Resolution: Modify the mode of the peer port as auto-negotiation, or set the mode of this port as the non-auto-negotiation mode. In addition, ensure that the parameters under the non-auto-negotiation mode are consistent with the peer port, including the duplex mode, the rate and whether to support PAUSE frame.
           "
       ::= { hwEthernetAlarmTrapsOids 2 }

   hwAlarmEthernetMacLost NOTIFICATION-TYPE
       OBJECTS { hwSlotIndex, hwIpdslamConnectIndex }
       STATUS current
       DESCRIPTION
           "Alarm description: MAC is lost
           explanation: The user MAC connected with IP DSLAM is lost.
           Resolution: Adjust the max MAC learning of PVC.
           Because in the connection with IP DSLAM, the number of a PVC can learn is limited,the user MAC will be lost if the number is bigger than the limited number.

           "
       ::= { hwEthernetAlarmTrapsOids 3 }

   hwAlarmEthernetPortActive NOTIFICATION-TYPE
       OBJECTS { hwPortIndex }
       STATUS current
       DESCRIPTION
           "
           This trap is sent when the LAN port has been actived from other state.
           alarm description: port active
           explanation: LAN port active
           resolving method:No process to need
                           "
       ::= { hwEthernetAlarmTrapsOids 4 }

   hwAlarmEthernetPortDeActive NOTIFICATION-TYPE
       OBJECTS { hwPortIndex }
       STATUS current
       DESCRIPTION
           "
           This trap is sent when the lan port  has been deactivated from other state.
           alarm description: port deactivated
           explanation: LAN port deactivated
           resolving method:check port status is active
           "
       ::= { hwEthernetAlarmTrapsOids 5 }

   hwMacConflictTrap NOTIFICATION-TYPE
       OBJECTS    {
                  hwFrameIndex ,            --User-side FrameID(Type:integer)
                  hwSlotIndex ,             --User-side SlotID(Type:integer)
                  hwPortIndex,              --User-side PortID(Type:integer)
                  hwFrameIndex,             --Network-side FrameID(Type:integer)
                  hwSlotIndex,              --Network-side SlotID(Type:integer)
                  hwPortIndex,              --Network-side PortID(Type:integer)
                  hwConflictMacAddress,     --MAC address(Type:String, Valur:0~32 length)
                  hwVlanIndex               --VLAN ID(Type:integer)
                  }
       STATUS current
       DESCRIPTION
           "When the source MAC got by non-network-side ports is the same as one learned by network-side ports,
            this trap will be generated."
       ::= { hwEthernetAlarmTrapsOids 6 }

   hwAlarmEthernetPortTransceiverTypeChange NOTIFICATION-TYPE
      OBJECTS { hwFrameIndex, hwSlotIndex, hwPortIndex }
      STATUS current
      DESCRIPTION
        "This trap is sent when the transceiver type of the Ethernet port changes.
        "
      ::= { hwEthernetAlarmTrapsOids 7 }

   hwAlarmSoftwareVersionNotSame NOTIFICATION-TYPE
     OBJECTS { hwFrameIndex, hwSlotIndex, hwSlotIndex }
     STATUS current
     DESCRIPTION
       "Software versions of the boards to be bound are not the same.
        The parameter information about the trap location where the
        trap message is generated, The first hwSlotIndex indicate slot
        ID of left board and second hwSlotIndex indicate slot ID of right board.
       "
     ::= { hwEthernetAlarmTrapsOids 8 }

   hwAlarmUpstreamPortConnectfail NOTIFICATION-TYPE
     OBJECTS { hwFrameIndex, hwSlotIndex, hwPortIndex }
     STATUS current
     DESCRIPTION
       "This trap is sent when the upstream ethernet port connection fails or the state of it is abnormal.
       "
     ::= { hwEthernetAlarmTrapsOids 9 }

   hwAlarmLOLOccurInBITSInputPort NOTIFICATION-TYPE
     OBJECTS { hwFrameIndex, hwSlotIndex, hwPortIndex }
     STATUS current
     DESCRIPTION
       "This trap is sent when the loss of link (LOL) occurs in the BITS input port.
       "
     ::= { hwEthernetAlarmTrapsOids 10 }

   hwAlarmEthernetPortStatusChanges NOTIFICATION-TYPE
     OBJECTS { hwFrameIndex, hwSlotIndex, hwPortIndex }
     STATUS current
     DESCRIPTION
       "This trap is sent when the Ethernet port link status changes from up to down.
       "
     ::= { hwEthernetAlarmTrapsOids 11 }

   hwAlarmOpticalTransceiverAbsence NOTIFICATION-TYPE
     OBJECTS { hwFrameIndex, hwSlotIndex, hwPortIndex }
     STATUS current
     DESCRIPTION
       "This trap is sent when the optical transceiver is absence.
       "
     ::= { hwEthernetAlarmTrapsOids 12 }

   hwAlarmLOSOccurs NOTIFICATION-TYPE
     OBJECTS { hwFrameIndex, hwSlotIndex, hwPortIndex }
     STATUS current
     DESCRIPTION
       "This trap is sent when the LOS occurs on the Ethernet optical port.
       "
     ::= { hwEthernetAlarmTrapsOids 13 }

   hwAlarmLinkBetweenStackPortsFails NOTIFICATION-TYPE
     OBJECTS { hwFrameIndex, hwSlotIndex }
     STATUS current
     DESCRIPTION
       "This trap is sent when the Link between stack ports fails.
       "
     ::= { hwEthernetAlarmTrapsOids 14 }

   hwAlarmUpstreamEthernetPortConnectRecover NOTIFICATION-TYPE
     OBJECTS { hwFrameIndex, hwSlotIndex, hwPortIndex }
     STATUS current
     DESCRIPTION
       "This trap is sent when the upstream ethernet port connection failure recovers  or the state of it is normal.
       "
     ::= { hwEthernetAlarmTrapsOids 15 }

   hwAlarmOpticalPortTemperatureRecover NOTIFICATION-TYPE
     OBJECTS {  hwFrameIndex, hwSlotIndex, hwPortIndex, hwOpticsTemperature }
     STATUS current
     DESCRIPTION
       "This trap is sent when the temperature of the Ethernet optical port recovers to the normal range.
       "
     ::= { hwEthernetAlarmTrapsOids 16 }

   hwAlarmBITSInputRecover NOTIFICATION-TYPE
     OBJECTS {  hwFrameIndex, hwSlotIndex, hwPortIndex }
     STATUS current
     DESCRIPTION
       "This trap is sent when the BITS input port recovers from loss of link (LOL).
       "
     ::= { hwEthernetAlarmTrapsOids 17 }

   hwAlarmEthernetPortLinkStatusChange NOTIFICATION-TYPE
     OBJECTS {  hwFrameIndex, hwSlotIndex, hwPortIndex }
     STATUS current
     DESCRIPTION
       "This trap is sent when the Ethernet port link status changes from down to up.
       "
     ::= { hwEthernetAlarmTrapsOids 18 }

   hwAlarmOpticalTransceiverRecover NOTIFICATION-TYPE
     OBJECTS {  hwFrameIndex, hwSlotIndex, hwPortIndex }
     STATUS current
     DESCRIPTION
       "This trap is sent when the optical transceiver recovers to the normal state.
       "
     ::= { hwEthernetAlarmTrapsOids 19 }

   hwAlarmOpticalPortRecoverFromLOS NOTIFICATION-TYPE
     OBJECTS {  hwFrameIndex, hwSlotIndex, hwPortIndex }
     STATUS current
     DESCRIPTION
       "This trap is sent when the Ethernet optical port recovers from LOS.
       "
     ::= { hwEthernetAlarmTrapsOids 20 }


   hwAlarmLinkBetweenStackPortsRecover NOTIFICATION-TYPE
     OBJECTS {  hwFrameIndex, hwSlotIndex }
     STATUS current
     DESCRIPTION
       "This trap is sent when the link between stack ports on the boards to be bound returns to a normal status.
       "
     ::= { hwEthernetAlarmTrapsOids 21 }

   hwOpticsTxPowerOutOfRangeAlarmTrap NOTIFICATION-TYPE
     OBJECTS {
             hwFrameIndex,
             hwSlotIndex,
             hwPortIndex,
             hwOpticsPowerTxLowerThresholdValue,
             hwOpticsPowerTxUpperThresholdValue,
             hwOpticsTxPower
             }
     STATUS current
     DESCRIPTION
             "This trap is sent when the Tx power of the Ethernet optical port is out of the range."
     ::= { hwEthernetAlarmTrapsOids 22 }

   hwOpticsTxPowerRestoreAlarmTrap NOTIFICATION-TYPE
     OBJECTS {
             hwFrameIndex,
             hwSlotIndex,
             hwPortIndex,
             hwOpticsPowerTxLowerThresholdValue,
             hwOpticsPowerTxUpperThresholdValue,
             hwOpticsTxPower
             }
     STATUS current
     DESCRIPTION
             "This trap is sent when the Tx power of the Ethernet optical port recovers to the normal range."
     ::= { hwEthernetAlarmTrapsOids 23 }

   hwOpticsRxPowerOutOfRangeAlarmTrap NOTIFICATION-TYPE
     OBJECTS {
             hwFrameIndex,
             hwSlotIndex,
             hwPortIndex,
             hwOpticsPowerRxUpperThresholdValue,
             hwOpticsPowerRxLowerThresholdValue,
             hwOpticsRxPower
             }
     STATUS current
     DESCRIPTION
             "This trap is sent when the Rx power of the Ethernet optical port is out of the range."
     ::= { hwEthernetAlarmTrapsOids 24 }

   hwOpticsRxPowerRestoreAlarmTrap NOTIFICATION-TYPE
     OBJECTS {
             hwFrameIndex,
             hwSlotIndex,
             hwPortIndex,
             hwOpticsPowerRxUpperThresholdValue,
             hwOpticsPowerRxLowerThresholdValue,
             hwOpticsRxPower
             }
     STATUS current
     DESCRIPTION
             "This trap is sent when the Rx power of the Ethernet optical port recovers to the normal range."
     ::= { hwEthernetAlarmTrapsOids 25 }

   hwAlarmEthPoePowerHighFault NOTIFICATION-TYPE
     OBJECTS {  hwFrameIndex, hwSlotIndex, hwPortIndex }
     STATUS current
     DESCRIPTION
       "This trap is sent when the load power of the Power over Ethernet port exceeds the upper limit.
       "
     ::= { hwEthernetAlarmTrapsOids 26 }

   hwAlarmEthPoePowerHighRecover NOTIFICATION-TYPE
     OBJECTS {  hwFrameIndex, hwSlotIndex, hwPortIndex }
     STATUS current
     DESCRIPTION
       "This trap is sent when the load power of the Power over Ethernet port recovers.
       "
     ::= { hwEthernetAlarmTrapsOids 27 }

   hwAlarmEthPoeCurrHighFault NOTIFICATION-TYPE
     OBJECTS {  hwFrameIndex, hwSlotIndex, hwPortIndex }
     STATUS current
     DESCRIPTION
       "This trap is sent when the Overcurrent for the power supply of the Power over Ethernet port.
       "
     ::= { hwEthernetAlarmTrapsOids 28 }

   hwAlarmEthPoeCurrHighRecover NOTIFICATION-TYPE
     OBJECTS {  hwFrameIndex, hwSlotIndex, hwPortIndex }
     STATUS current
     DESCRIPTION
       "This trap is sent when the Overcurrent for the power supply of the Power over Ethernet port recovers.
       "
     ::= { hwEthernetAlarmTrapsOids 29 }

   hwAlarmEthernetPortAdminActivate NOTIFICATION-TYPE
     OBJECTS {  hwFrameIndex, hwSlotIndex, hwPortIndex }
     STATUS current
     DESCRIPTION
       "This trap is sent when the ETH port is activated.
       "
     ::= { hwEthernetAlarmTrapsOids 30 }

   hwAlarmEthernetPortAdminDeActivate NOTIFICATION-TYPE
     OBJECTS {  hwFrameIndex, hwSlotIndex, hwPortIndex }
     STATUS current
     DESCRIPTION
       "This trap is sent when the ETH port is deactivated.
       "
     ::= { hwEthernetAlarmTrapsOids 31 }

   hwAlarmEthPowerDyingGaspFault NOTIFICATION-TYPE
     OBJECTS {  hwFrameIndex, hwSlotIndex, hwPortIndex }
     STATUS current
     DESCRIPTION
       "This trap is sent when the remote device is powered off.
       "
     ::= { hwEthernetAlarmTrapsOids 32 }

   hwAlarmEthPowerDyingGaspRecover NOTIFICATION-TYPE
     OBJECTS {  hwFrameIndex, hwSlotIndex, hwPortIndex }
     STATUS current
     DESCRIPTION
       "This trap is sent when the remote device is powered on.
       "
     ::= { hwEthernetAlarmTrapsOids 33 }

   hwOpticsTemperatureOutOfRangeAlarmTrap NOTIFICATION-TYPE
     OBJECTS {
             hwFrameIndex,
             hwSlotIndex,
             hwPortIndex,
             hwOpticsTemperatureUpperThresholdValue,
             hwOpticsTemperatureLowerThresholdValue,
             hwOpticsTemperature
             }
     STATUS current
     DESCRIPTION
             "This trap is sent when the Temperature of the Ethernet optical port is out of the range."
     ::= { hwEthernetAlarmTrapsOids 34 }

   hwOpticsTemperatureRestoreAlarmTrap NOTIFICATION-TYPE
     OBJECTS {
             hwFrameIndex,
             hwSlotIndex,
             hwPortIndex,
             hwOpticsTemperatureUpperThresholdValue,
             hwOpticsTemperatureLowerThresholdValue,
             hwOpticsTemperature
             }
     STATUS current
     DESCRIPTION
             "This trap is sent when the Temperature of the Ethernet optical port recovers to the normal range."
     ::= { hwEthernetAlarmTrapsOids 35 }

   hwOpticsVoltageOutOfRangeAlarmTrap NOTIFICATION-TYPE
     OBJECTS {
             hwFrameIndex,
             hwSlotIndex,
             hwPortIndex,
             hwOpticsVoltageUpperThresholdValue,
             hwOpticsVoltageLowerThresholdValue,
             hwOpticsSupplyVoltage
             }
     STATUS current
     DESCRIPTION
             "This trap is sent when the Voltage of the Ethernet optical port is out of the range."
     ::= { hwEthernetAlarmTrapsOids 36 }

   hwOpticsVoltageRestoreAlarmTrap NOTIFICATION-TYPE
     OBJECTS {
             hwFrameIndex,
             hwSlotIndex,
             hwPortIndex,
             hwOpticsVoltageUpperThresholdValue,
             hwOpticsVoltageLowerThresholdValue,
             hwOpticsSupplyVoltage
             }
     STATUS current
     DESCRIPTION
             "This trap is sent when the Voltage of the Ethernet optical port recovers to the normal range."
     ::= { hwEthernetAlarmTrapsOids 37 }

   hwOpticsCurrentOutOfRangeAlarmTrap NOTIFICATION-TYPE
     OBJECTS {
             hwFrameIndex,
             hwSlotIndex,
             hwPortIndex,
             hwOpticsCurrentUpperThresholdValue,
             hwOpticsCurrentLowerThresholdValue,
             hwOpticsTxBiasCurrent
             }
     STATUS current
     DESCRIPTION
             "This trap is sent when the Current of the Ethernet optical port is out of the range."
     ::= { hwEthernetAlarmTrapsOids 38 }

   hwOpticsCurrentRestoreAlarmTrap NOTIFICATION-TYPE
     OBJECTS {
             hwFrameIndex,
             hwSlotIndex,
             hwPortIndex,
             hwOpticsCurrentUpperThresholdValue,
             hwOpticsCurrentLowerThresholdValue,
             hwOpticsTxBiasCurrent
             }
     STATUS current
     DESCRIPTION
             "This trap is sent when the Current of the Ethernet optical port recovers to the normal range."
     ::= { hwEthernetAlarmTrapsOids 39 }

   hwEthPerformanceStatisOutOfRangeAlarmTrap NOTIFICATION-TYPE
     OBJECTS {
             hwFrameIndex,
             hwSlotIndex,
             hwPortIndex,
             hwEthPMThresholdItem,
             hwEthPMCurrentValue,
             hwEthPMThresholdValue
             }
     STATUS current
     DESCRIPTION
             "This trap is sent when the Current alarm performance statistics of the Ethernet port is out of the range."
     ::= { hwEthernetAlarmTrapsOids 40 }

   hwEthPerformanceStatisRestoreAlarmTrap NOTIFICATION-TYPE
     OBJECTS {
             hwFrameIndex,
             hwSlotIndex,
             hwPortIndex,
             hwEthPMThresholdItem,
             hwEthPMCurrentValue,
             hwEthPMThresholdValue
             }
     STATUS current
     DESCRIPTION
             "This trap is sent when the Current alarm performance statistics of the Ethernet port recovers to the normal range."
     ::= { hwEthernetAlarmTrapsOids 41 }

   hwEthPerformanceStatisOutOfRangeWarningTrap NOTIFICATION-TYPE
     OBJECTS {
             hwFrameIndex,
             hwSlotIndex,
             hwPortIndex,
             hwEthPMThresholdItem,
             hwEthPMCurrentValue,
             hwEthPMThresholdValue
             }
     STATUS current
     DESCRIPTION
             "This trap is sent when the Current warning performance statistics of the Ethernet port is out of the range."
     ::= { hwEthernetAlarmTrapsOids 42 }

   hwEthPerformanceStatisRestoreWarningTrap NOTIFICATION-TYPE
     OBJECTS {
             hwFrameIndex,
             hwSlotIndex,
             hwPortIndex,
             hwEthPMThresholdItem,
             hwEthPMCurrentValue,
             hwEthPMThresholdValue
             }
     STATUS current
     DESCRIPTION
             "This trap is sent when the Current warning performance statistics of the Ethernet port recovers to the normal range."
     ::= { hwEthernetAlarmTrapsOids 43 }
    hwMacOverloadTrap NOTIFICATION-TYPE
      OBJECTS {
               hwResourceOverloadAwareUpperThreshold,
               hwResourceOverloadAwareLowerThreshold,
               hwResourceOverloadAwareCurValue
              }
      STATUS current
      DESCRIPTION
      "This trap is sent when the MAC address occupancy in the system exceeds the upper threshold."
      ::= { hwEthernetAlarmTrapsOids 44 }

    hwMacOverloadRestoreTrap NOTIFICATION-TYPE
      OBJECTS {
               hwResourceOverloadAwareUpperThreshold,
               hwResourceOverloadAwareLowerThreshold,
               hwResourceOverloadAwareCurValue
              }
      STATUS current
      DESCRIPTION
      "This trap is sent when the MAC address occupancy in the system is lower than the lower threshold."
      ::= { hwEthernetAlarmTrapsOids 45 }

    hwIPNeighbourHardwareOverloadTrap NOTIFICATION-TYPE
      OBJECTS {
               hwResourceOverloadAwareUpperThreshold,
               hwResourceOverloadAwareLowerThreshold,
               hwResourceOverloadAwareCurValue
              }
      STATUS current
      DESCRIPTION
      "This trap is sent when the IP neighbour hardware occupancy in the system exceeds the upper threshold."
      ::= { hwEthernetAlarmTrapsOids 46 }

    hwIPNeighbourHardwareOverloadRestoreTrap NOTIFICATION-TYPE
      OBJECTS {
               hwResourceOverloadAwareUpperThreshold,
               hwResourceOverloadAwareLowerThreshold,
               hwResourceOverloadAwareCurValue
              }
      STATUS current
      DESCRIPTION
      "This trap is sent when the IP neighbour hardware occupancy in the system is lower than the lower threshold."
      ::= { hwEthernetAlarmTrapsOids 47 }

    hwBindBoardReplaceErrorTrap NOTIFICATION-TYPE
      OBJECTS {
               hwFrameIndex,
               hwSlotIndex
              }
      STATUS current
      DESCRIPTION
      "This trap is sent when one bind board has been replaced while the other one hasn't been replaced."
      ::= { hwEthernetAlarmTrapsOids 48 }

    hwEnableMirrorPortTrap NOTIFICATION-TYPE
      OBJECTS {
               hwFrameIndex,
               hwSlotIndex,
               hwPortIndex,
               hwFrameIndex,
               hwSlotIndex,
               hwPortIndex,
               hwEthernetMirrorDirection
              }
      STATUS current
      DESCRIPTION
      "This trap is sent when a mirror port has been created.
      1: hwFrameIndex -indicates the source frame index.
      2: hwSlotIndex -indicates the source slot index.
      3: hwPortIndex -indicates the source port index.
      4: hwFrameIndex -indicates the destination frame index.
      5: hwSlotIndex -indicates the destination slot index.
      6: hwPortIndex -indicates the destination port index.
      7: hwEthernetMirrorDirection -indicates the mirror direction.
      "
      ::= { hwEthernetAlarmTrapsOids 49 }

    hwDisableMirrorPortTrap NOTIFICATION-TYPE
      OBJECTS {
               hwFrameIndex,
               hwSlotIndex,
               hwPortIndex,
               hwFrameIndex,
               hwSlotIndex,
               hwPortIndex,
               hwEthernetMirrorDirection
              }
      STATUS current
      DESCRIPTION
      "This trap is sent when a mirror port has been cancelled.
      1: hwFrameIndex -indicates the source frame index.
      2: hwSlotIndex -indicates the source slot index.
      3: hwPortIndex -indicates the source port index.
      4: hwFrameIndex -indicates the destination frame index.
      5: hwSlotIndex -indicates the destination slot index.
      6: hwPortIndex -indicates the destination port index.
      7: hwEthernetMirrorDirection -indicates the mirror direction.
      "
      ::= { hwEthernetAlarmTrapsOids 50 }

      hwBoardMacOverloadTrap NOTIFICATION-TYPE
      OBJECTS {
               hwFrameIndex,
               hwSlotIndex,
               hwResourceOverloadAwareUpperThreshold,
               hwResourceOverloadAwareLowerThreshold,
               hwResourceOverloadAwareCurValue
              }
      STATUS current
      DESCRIPTION
      "This trap is sent when the MAC address occupancy on the board exceeds the upper threshold."
      ::= { hwEthernetAlarmTrapsOids 51 }

    hwBoardMacOverloadRestoreTrap NOTIFICATION-TYPE
      OBJECTS {
               hwFrameIndex,
               hwSlotIndex,
               hwResourceOverloadAwareUpperThreshold,
               hwResourceOverloadAwareLowerThreshold,
               hwResourceOverloadAwareCurValue
              }
      STATUS current
      DESCRIPTION
      "This trap is sent when the MAC address occupancy on the board is lower than the lower threshold."
      ::= { hwEthernetAlarmTrapsOids 52 }

    hwEnableMirrorPortExtendTrap NOTIFICATION-TYPE
      OBJECTS {
               hwMirrorSrcPortDescription,
               hwMirrorDstPortDescription,
               hwEthernetMirrorDirection
              }
      STATUS current
      DESCRIPTION
      "This trap is sent when mirroring is configured by running the mirror port command in SU mode.
      1: hwMirrorSrcPortDescription -indicates the description of the source port with the format frameId/slotId/portid.
      2: hwMirrorDstPortDescription -indicates the description of the destination port with the format frameId/slotId/portid or meth.
      3: hwEthernetMirrorDirection -indicates the mirror direction.
      "
      ::= { hwEthernetAlarmTrapsOids 53 }

    hwDisableMirrorPortExtendTrap NOTIFICATION-TYPE
      OBJECTS {
               hwMirrorSrcPortDescription,
               hwMirrorDstPortDescription,
               hwEthernetMirrorDirection
              }
      STATUS current
      DESCRIPTION
      "This trap is sent when mirroring is canceled by running the undo mirror port command in SU mode.
      1: hwMirrorSrcPortDescription -indicates the description of the source port with the format frameId/slotId/portid.
      2: hwMirrorDstPortDescription -indicates the description of the destination port with the format frameId/slotId/portid or meth.
      3: hwEthernetMirrorDirection -indicates the mirror direction.
      "
      ::= { hwEthernetAlarmTrapsOids 54 }

    hwOpticsLaserTemperatureOutOfRangeAlarmTrap NOTIFICATION-TYPE
     OBJECTS {
             hwFrameIndex,
             hwSlotIndex,
             hwPortIndex,
             hwOpticsLaserTemperatureUpperThresholdValue,
             hwOpticsLaserTemperatureLowerThresholdValue,
             hwOpticsLaserTemperature
             }
     STATUS current
     DESCRIPTION
             "This trap is sent when the temperature of the Ethernet optical port laser is out of the range."
     ::= { hwEthernetAlarmTrapsOids 55 }

   hwOpticsLaserTemperatureRestoreAlarmTrap NOTIFICATION-TYPE
     OBJECTS {
             hwFrameIndex,
             hwSlotIndex,
             hwPortIndex,
             hwOpticsLaserTemperatureUpperThresholdValue,
             hwOpticsLaserTemperatureLowerThresholdValue,
             hwOpticsLaserTemperature
             }
     STATUS current
     DESCRIPTION
             "This trap is sent when the temperature of the Ethernet optical port laser recovers within the normal range."
     ::= { hwEthernetAlarmTrapsOids 56 }

    hwOpticsWavelengthOutOfRangeAlarmTrap NOTIFICATION-TYPE
     OBJECTS {
             hwFrameIndex,
             hwSlotIndex,
             hwPortIndex,
             hwOpticsWaveLengthUpperThresholdValue,
             hwOpticsWaveLengthLowerThresholdValue,
             hwOpticsWaveLength
             }
     STATUS current
     DESCRIPTION
             "This trap is sent when the wavelength sent by the optical module on the Ethernet port is out of the range."
     ::= { hwEthernetAlarmTrapsOids 57 }

   hwOpticsWavelengthRestoreAlarmTrap NOTIFICATION-TYPE
     OBJECTS {
             hwFrameIndex,
             hwSlotIndex,
             hwPortIndex,
             hwOpticsWaveLengthUpperThresholdValue,
             hwOpticsWaveLengthLowerThresholdValue,
             hwOpticsWaveLength
             }
     STATUS current
     DESCRIPTION
             "This trap is sent when the wavelength sent by the optical module on the Ethernet port recovers within the normal range."
     ::= { hwEthernetAlarmTrapsOids 58 }

    hwOpticTecCurrentOutOfRangeAlarmTrap NOTIFICATION-TYPE
     OBJECTS {
             hwFrameIndex,
             hwSlotIndex,
             hwPortIndex,
             hwOpticsTecCurrentUpperThresholdValue,
             hwOpticsTecCurrentLowerThresholdValue,
             hwOpticsTecCurrent
             }
     STATUS current
     DESCRIPTION
             "This trap is sent when the current of the thermoelectric cooler on the Ethernet optical port is out of the range."
     ::= { hwEthernetAlarmTrapsOids 59 }

   hwOpticsTecCurrentRestoreAlarmTrap NOTIFICATION-TYPE
     OBJECTS {
             hwFrameIndex,
             hwSlotIndex,
             hwPortIndex,
             hwOpticsTecCurrentUpperThresholdValue,
             hwOpticsTecCurrentLowerThresholdValue,
             hwOpticsTecCurrent
             }
     STATUS current
     DESCRIPTION
             "This trap is sent when the current of the thermoelectric cooler on the Ethernet optical port recovers within the normal range."
     ::= { hwEthernetAlarmTrapsOids 60 }

    hwIPRouteHardwareOverloadTrap NOTIFICATION-TYPE
      OBJECTS {
               hwFrameIndex,
               hwSlotIndex,
               hwResourceOverloadAwareUpperThreshold,
               hwResourceOverloadAwareLowerThreshold,
               hwResourceOverloadAwareCurValue
              }
      STATUS current
      DESCRIPTION
      "This trap is sent when the IP route hardware occupancy in the system exceeds the upper threshold."
      ::= { hwEthernetAlarmTrapsOids 61 }

    hwIPRouteHardwareOverloadRestoreTrap NOTIFICATION-TYPE
      OBJECTS {
               hwFrameIndex,
               hwSlotIndex,
               hwResourceOverloadAwareUpperThreshold,
               hwResourceOverloadAwareLowerThreshold,
               hwResourceOverloadAwareCurValue
              }
      STATUS current
      DESCRIPTION
      "This trap is sent when the IP route hardware occupancy in the system is lower than the lower threshold."
      ::= { hwEthernetAlarmTrapsOids 62 }

    hwPortAutoServiceAddFailureTrap NOTIFICATION-TYPE
      OBJECTS {
               hwFrameIndex,
               hwSlotIndex,
               hwPortIndex,
               hwOntIndex,
               hwAutoServiceAddContent,
               hwAutoServiceProcResult
              }
      STATUS current
      DESCRIPTION
      "Trap indicating that automatic service port creation upon an ONT being online fails."
      ::= { hwEthernetAlarmTrapsOids 63 }

    hwPortAutoServiceParaIncorrectTrap NOTIFICATION-TYPE
      OBJECTS {
               hwFrameIndex,
               hwSlotIndex,
               hwPortIndex,
               hwOntIndex,
               hwAutoServiceProcResult
              }
      STATUS current
      DESCRIPTION
      "Trap indicating that parameters for automatic service port creation are incorrect."
      ::= { hwEthernetAlarmTrapsOids 64 }

      hwPortCmtsFrameAddFailTrap NOTIFICATION-TYPE
      OBJECTS {
               hwFrameIndex,
               hwSlotIndex,
               hwPortIndex,
               hwOntIndex
              }
      STATUS current
      DESCRIPTION
      "This trap is sent when board resources are full and the extended frame cannot be added."
      ::= { hwEthernetAlarmTrapsOids 65 }

     hwMacConflictNewTrap NOTIFICATION-TYPE
       OBJECTS    {
                  hwFrameIndex,                --ID of the subrack which learned the MAC address(Type:integer)
                  hwSlotIndex,                 --ID of the slot which learned the MAC address(Type:integer)
                  hwPortIndex,                 --ID of the port which  learned the MAC address(Type:integer)
                  hwExtSrvFlowIndex,           --Index of the service port which learned the MAC address
                  hwFrameIndex,                --ID of the subrack with the conflict MAC address(Type:integer)
                  hwSlotIndex,                 --ID of the slot with the conflict MAC address(Type:integer)
                  hwPortIndex,                 --ID of the port with the conflict MAC address(Type:integer)
                  hwExtSrvFlowIndex,           --Index of the service port with the conflict MAC address
                  hwVlanIndex,                 --ID of the VLAN which learned the conflict MAC address(Type:integer)
                  hwConflictMacAddress         --The conflict MAC address(Type:String, Valur:0~32 length)
                  }
       STATUS current
       DESCRIPTION
           "When the source MAC got by a port is the same as one learnt by another, this trap will be generated.
            When the port is configured with PW, hwExtSrvFlowIndex indicates PW index, and the values of hwFrameIndex,
            hwSlotIndex and hwPortIndex are invalid value.
           "
       ::= { hwEthernetAlarmTrapsOids 66 }

     hwMacAddressFlappingOverTrap NOTIFICATION-TYPE
       OBJECTS    {
                  hwVlanIndex,                 --ID of the VLAN which learned the flapping MAC address(Type:integer)
                  hwFlappingMacAddress,         --The flapping MAC address(Type:String, Valur:0~32 length)
                  hwMacAddressFlappingPortInfo   --MAC Flapping Ports (Type:String)
                  }
       STATUS current
       DESCRIPTION
           "When the number of flapping MAC addresses reaches or exceeds the preset upper threshold, this trap will be generated."
       ::= { hwEthernetAlarmTrapsOids 67 }

     hwMacAddressFlappingOverRestoreTrap NOTIFICATION-TYPE
       OBJECTS    {
                  hwVlanIndex,                 --ID of the VLAN which learned the flapping MAC address(Type:integer)
                  hwFlappingMacAddress,         --The flapping MAC address(Type:String, Valur:0~32 length)
                  hwMacAddressFlappingPortInfo   --MAC Flapping Ports (Type:String)
                  }
       STATUS current
       DESCRIPTION
           "When the number of flapping MAC addresses is smaller than or equal to the preset lower threshold, this trap will be generated."
       ::= { hwEthernetAlarmTrapsOids 68 }

     hwMacLimitOverflowTrap NOTIFICATION-TYPE
       OBJECTS    {
                  hwFrameIndex,
                  hwSlotIndex,
                  hwPortIndex
                  }
       STATUS current
       DESCRIPTION
           "When the number of learnable MAC addresses of this port reaches the limit, this trap will be generated."
       ::= { hwEthernetAlarmTrapsOids 69 }

     hwMacLimitOverflowRecoverTrap NOTIFICATION-TYPE
       OBJECTS    {
                  hwFrameIndex,
                  hwSlotIndex,
                  hwPortIndex
                  }
       STATUS current
       DESCRIPTION
           "When the number of learnable MAC addresses of this port recovery normal, this trap will be generated."
       ::= { hwEthernetAlarmTrapsOids 70 }

    hwUpstreamDecreaseRecordTrap NOTIFICATION-TYPE
      OBJECTS    {
                hwFrameIndex,
                hwSlotIndex,
                hwPortIndex,
                hwDslamTrafficUpportMonitorThreshold,
                hwTrafficUpportMonitorUpstreamLast,
                hwTrafficUpportMonitorUpstream,
                hwTrafficUpportMonitorDownstreamLast,
                hwTrafficUpportMonitorDownstream
                 }
      STATUS current
      DESCRIPTION
          "When the number of reduced upstream traffic by the specified uplink-port exceeds the
          specified threshold, this trap will be generated."
      ::= { hwEthernetAlarmTrapsOids 71 }

    hwDownstreamDecreaseRecordTrap NOTIFICATION-TYPE
      OBJECTS    {
                hwFrameIndex,
                hwSlotIndex,
                hwPortIndex,
                hwDslamTrafficUpportMonitorThreshold,
                hwTrafficUpportMonitorUpstreamLast,
                hwTrafficUpportMonitorUpstream,
                hwTrafficUpportMonitorDownstreamLast,
                hwTrafficUpportMonitorDownstream
                 }
      STATUS current
      DESCRIPTION
          "When the number of reduced downstream traffic by the specified uplink-port exceeds the
          specified threshold, this trap will be generated."
      ::= { hwEthernetAlarmTrapsOids 72 }

    hwStreamDecreaseRecordTrap NOTIFICATION-TYPE
    OBJECTS    {
            hwFrameIndex,
            hwSlotIndex,
            hwPortIndex,
            hwDslamTrafficUpportMonitorThreshold,
            hwTrafficUpportMonitorUpstreamLast,
            hwTrafficUpportMonitorUpstream,
            hwTrafficUpportMonitorDownstreamLast,
            hwTrafficUpportMonitorDownstream
             }
    STATUS current
    DESCRIPTION
      "When the number of reduced upstream and downstream traffic by the specified uplink-port exceeds the
      specified threshold, this trap will be generated."
    ::= { hwEthernetAlarmTrapsOids 73 }

--hwPacketAttackTrap begin

	hwPacketAttackTrap NOTIFICATION-TYPE
       OBJECTS    {
                  hwPacketAttackMACAddress,
                  hwPacketNumberOfMACAddress,
                  hwPacketAttackPacketType,
				  hwPacketNumberOfPacketType
                  }
       STATUS current
       DESCRIPTION
           "The system records packet statistics based on port and protocol type when the current CPU usage exceeds the packet detection threshold."
       ::= { hwEthernetAlarmTrapsOids 74 }

--hwPacketAttackTrap end

    hwInnerForwardingFaultAlarmTrap NOTIFICATION-TYPE
    OBJECTS    {
            hwFrameIndex,
            hwSlotIndex,
            hwFrameIndex,
            hwSlotIndex
             }
    STATUS current
    DESCRIPTION
      "When the inner forwarding fault occurs, this trap will be generated."
    ::= { hwEthernetAlarmTrapsOids 75 }

    hwInnerForwardingRecoverAlarmTrap NOTIFICATION-TYPE
    OBJECTS    {
            hwFrameIndex,
            hwSlotIndex,
            hwFrameIndex,
            hwSlotIndex
             }
    STATUS current
    DESCRIPTION
      "When the inner forwarding recovery occurs, this trap will be generated."
    ::= { hwEthernetAlarmTrapsOids 76 }

    hwDslamNonUnicastUpportMonitorRecordTrap NOTIFICATION-TYPE
    OBJECTS   {
                hwFrameIndex,
                hwSlotIndex,
                hwPortIndex,
                hwDslamNonUnicastUpportMonitorBroadcastRate,
                hwDslamNonUnicastUpportMonitorUnknownUnicastRate,
                hwDslamNonUnicastUpportMonitorUnknownMulticastRate
              }
    STATUS current
    DESCRIPTION
      "The SNMP trap is generated when the number of non-unicast packets received by the uplink-port exceeds the threshold."
    ::= { hwEthernetAlarmTrapsOids 77 }

    hwIPTunnelHardwareOverloadTrap NOTIFICATION-TYPE
      OBJECTS {
               hwFrameIndex,
               hwSlotIndex,
               hwResourceOverloadAwareUpperThreshold,
               hwResourceOverloadAwareLowerThreshold,
               hwResourceOverloadAwareCurValue
              }
      STATUS current
      DESCRIPTION
      "This trap is sent when the IP tunnel hardware occupancy in the system exceeds the upper threshold."
      ::= { hwEthernetAlarmTrapsOids 78 }

    hwIPTunnelHardwareOverloadRestoreTrap NOTIFICATION-TYPE
      OBJECTS {
               hwFrameIndex,
               hwSlotIndex,
               hwResourceOverloadAwareUpperThreshold,
               hwResourceOverloadAwareLowerThreshold,
               hwResourceOverloadAwareCurValue
              }
      STATUS current
      DESCRIPTION
      "This trap is sent when the IP tunnel hardware occupancy in the system is lower than the lower threshold."
      ::= { hwEthernetAlarmTrapsOids 79 }

    hwVPNHardwareOverloadTrap NOTIFICATION-TYPE
      OBJECTS {
               hwFrameIndex,
               hwSlotIndex,
               hwResourceOverloadAwareUpperThreshold,
               hwResourceOverloadAwareLowerThreshold,
               hwResourceOverloadAwareCurValue
              }
      STATUS current
      DESCRIPTION
      "This trap is sent when the VNI peer hardware occupancy in the system exceeds the upper threshold."
      ::= { hwEthernetAlarmTrapsOids 80 }

    hwVPNHardwareOverloadRestoreTrap NOTIFICATION-TYPE
      OBJECTS {
               hwFrameIndex,
               hwSlotIndex,
               hwResourceOverloadAwareUpperThreshold,
               hwResourceOverloadAwareLowerThreshold,
               hwResourceOverloadAwareCurValue
              }
      STATUS current
      DESCRIPTION
      "This trap is sent when the VNI peer hardware occupancy in the system is lower than the lower threshold."
      ::= { hwEthernetAlarmTrapsOids 81 }

    hwSRv6TunnelHardwareOverloadTrap NOTIFICATION-TYPE
      OBJECTS {
               hwFrameIndex,
               hwSlotIndex,
               hwResourceOverloadAwareUpperThreshold,
               hwResourceOverloadAwareLowerThreshold,
               hwResourceOverloadAwareCurValue
              }
      STATUS current
      DESCRIPTION
      "This trap is sent when the segment-routing ipv6 tunnel hardware occupancy in the system exceeds the upper threshold."
      ::= { hwEthernetAlarmTrapsOids 82 }

    hwSRv6TunnelHardwareOverloadRestoreTrap NOTIFICATION-TYPE
      OBJECTS {
               hwFrameIndex,
               hwSlotIndex,
               hwResourceOverloadAwareUpperThreshold,
               hwResourceOverloadAwareLowerThreshold,
               hwResourceOverloadAwareCurValue
              }
      STATUS current
      DESCRIPTION
      "This trap is sent when the segment-routing ipv6 tunnel hardware occupancy in the system is lower than the lower threshold."
      ::= { hwEthernetAlarmTrapsOids 83 }

--   hwExtSrvFlow
   hwExtSrvFlow OBJECT IDENTIFIER ::= { hwEthernetPort 5 }

   hwExtSrvFlowIndexNext OBJECT-TYPE
       SYNTAX Integer32
       MAX-ACCESS read-only
       STATUS current
       DESCRIPTION
           "Indicates next available value for hwExtSrvFlowIndex of a service flow entry in hwExtSrvFlowTable.
            This will report values >=1 if a new service flow may be created or else the value 0 if this is not possible.

            A row creation operation in this table for an entry with an hwExtSrvFlowIndex value may fail
            if the current value of this object is not used as the index. Even if the value read is used,
            there is no guarantee that it will still be the valid index when the creation operation is attempted;
            another manager may have already got in during the intervening time interval. In this case,
            hwExtSrvFlowIndexNext should be re-read and the creation re-tried with the new value.

            This value will automatically change when the current value is used to create a new row.
           "
       ::= { hwExtSrvFlow 1 }


   hwExtSrvFlowTable OBJECT-TYPE
       SYNTAX SEQUENCE OF HwExtSrvFlowEntry
       MAX-ACCESS not-accessible
       STATUS current
       DESCRIPTION
           "Indicates the table that contains service flow configuration information. It is used to create, modify,
            delete and query service flows.
            The index of this table is hwExtSrvFlowIndex.
           "
       ::= { hwExtSrvFlow 2 }

   hwExtSrvFlowEntry OBJECT-TYPE
       SYNTAX HwExtSrvFlowEntry
       MAX-ACCESS not-accessible
       STATUS current
       DESCRIPTION
           "Indicates the table that contains service flow configuration information. It is used to create, modify,
            delete and query service flows.
            The index of this entry is hwExtSrvFlowIndex.
           "
       INDEX { hwExtSrvFlowIndex }
       ::= { hwExtSrvFlowTable 1 }

   HwExtSrvFlowEntry ::=
       SEQUENCE {
           hwExtSrvFlowIndex
               Integer32,
           hwExtSrvFlowPara1
               Integer32,
           hwExtSrvFlowPara2
               Integer32,
           hwExtSrvFlowPara3
               Integer32,
           hwExtSrvFlowPara4
               Integer32,
           hwExtSrvFlowPara5
               Integer32,
           hwExtSrvFlowParaType
               INTEGER,
           hwExtSrvFlowVlanid
               Integer32,
           hwExtSrvFlowReceiveTrafficDescrIndex
               Integer32,
           hwExtSrvFlowTransmitTrafficDescrIndex
               Integer32,
           hwExtSrvFlowMultiServiceType
               INTEGER,
           hwExtSrvFlowMultiServiceUserPara
               Integer32,
           hwExtSrvFlowAdminStatus
               INTEGER,
           hwExtSrvFlowOperStatus
               INTEGER,
           hwExtSrvFlowRowStatus
               RowStatus,
           hwExtSrvFlowInnerVlanId
               Integer32,
           hwExtSrvFlowDescInfo
               OCTET STRING,
           hwExtSrvFlowTagTransform
               INTEGER,
           hwExtSrvFlowSimulationServiceType
               INTEGER,
           hwExtSrvFlowRemoteDescInfo
               OCTET STRING,
           hwExtSrvFlowOutboundTrafficTableName
               OCTET STRING,
           hwExtSrvFlowInboundTrafficTableName
               OCTET STRING,
           hwExtSrvFlowRxUpc
               INTEGER,
           hwExtSrvFlowTxUpc
               INTEGER,
           hwExtSrvFlowNNIInnerVlanId
               Integer32,
           hwExtSrvFlowNNIInnerPriority
               Integer32,
           hwExtSrvFlowBundleIndex
               Integer32,
           hwExtSrvFlowBundleMemberSortPara
               Integer32,
           hwExtSrvFlowSourceType
               INTEGER,
           hwExtSrvFlowDestinationType
               INTEGER,
           hwExtSrvFlowSourceParaType
               INTEGER,
           hwExtSrvFlowSourcePara1
               Integer32,
           hwExtSrvFlowSourcePara2
               Integer32,
           hwExtSrvFlowSourcePara3
               Integer32,
           hwExtSrvFlowSourcePara4
               Integer32,
           hwExtSrvFlowSourcePara5
               Integer32,
           hwExtSrvFlowSourceMultiServiceType
               INTEGER,
           hwExtSrvFlowSourceMultiServiceUserPara
               Integer32,
           hwExtSrvFlowSourceInnerVlanId
               Integer32,
           hwExtSrvFlowOntPortListMask
               OCTET STRING,
           hwExtSrvFlowOntPortType
               INTEGER,
           hwExtSrvFlowStatPerSwitch
               INTEGER
             }

   hwExtSrvFlowIndex OBJECT-TYPE
       SYNTAX Integer32
       MAX-ACCESS accessible-for-notify
       STATUS current
       DESCRIPTION
           "Indicates the service flow index, a unique value to identify a service flow.
            To create a service flow, this leaf is optional. If a valid free value is specified,
            the value will be the index of the service flow to be created. If no value is specified,
            an index will be allocated automatically for the service flow.
           "
       ::= { hwExtSrvFlowEntry 1 }

   hwExtSrvFlowPara1 OBJECT-TYPE
       SYNTAX Integer32
       MAX-ACCESS read-write
       STATUS current
       DESCRIPTION
           "The meaning is variable with the value of hwExtSrvFlowParaType:
            If the value of hwExtSrvFlowParaType is set to 1, this leaf indicates the PVC connect ID.
            If the value of hwExtSrvFlowParaType is set to 2, 4, 6, 9, 10, 11, 12, 13, 14, 15, or 16, this leaf indicates the shelf ID.
            If hwExtSrvFlowParaType is set to 3, 5, or 8, this leaf indicates the PTM mode of VDSL2, SHDSL or ADSL2/2+.
            If the value of hwExtSrvFlowParaType is set to 7, this leaf indicates the IfIndex of the port.
           "
       ::= { hwExtSrvFlowEntry 2 }

   hwExtSrvFlowPara2 OBJECT-TYPE
       SYNTAX Integer32
       MAX-ACCESS read-write
       STATUS current
       DESCRIPTION
           "The meaning is variable with the value of hwExtSrvFlowParaType:
            If the value of hwExtSrvFlowParaType is set to 1, this leaf is reserved.
            If the value of hwExtSrvFlowParaType is set to 2, 4, 6, 9, 10, 11, 12, 13, 14, 15, or 16, this leaf indicates the slot ID.
            If the value of hwExtSrvFlowParaType is set to 3, 5, or 8, this leaf indicates the shelf ID.
            If the value of hwExtSrvFlowParaType is set to 7, this leaf indicates the VPI.
           "
       ::= { hwExtSrvFlowEntry 3 }

   hwExtSrvFlowPara3 OBJECT-TYPE
       SYNTAX Integer32
       MAX-ACCESS read-write
       STATUS current
       DESCRIPTION
           "The meaning is variable with the value of hwExtSrvFlowParaType:
            If the value of hwExtSrvFlowParaType is set to 1, this leaf is reserved.
            If the value of hwExtSrvFlowParaType is set to 2, 4, 6, 9, 10, 11, 12, 13, 14, 15, or 16, this leaf indicates the port ID.
            If the value of hwExtSrvFlowParaType is set to 3, 5, or 8, this leaf indicates the slot ID.
            If the value of hwExtSrvFlowParaType is set to 7, this leaf indicates the VCI.
           "
       ::= { hwExtSrvFlowEntry 4 }

   hwExtSrvFlowPara4 OBJECT-TYPE
       SYNTAX Integer32
       MAX-ACCESS read-write
       STATUS current
       DESCRIPTION
           "The meaning is variable with the value of hwExtSrvFlowParaType:
            If the value of hwExtSrvFlowParaType is set to 1, 2, 7, or 16, this leaf is reserved.
            If the value of hwExtSrvFlowParaType is set to 3, 5, or 8, this leaf indicates the port ID.
            If the value of hwExtSrvFlowParaType is set to 4, this leaf indicates the ONT ID
            for the GPON profile mode and GEM port ID for the GPON distributed mode.
            If the value of hwExtSrvFlowParaType is set to 6, 9, 10, 11, or 12, this leaf indicates the ONT ID.
            If VLAN range service flow for all ONTs is created, the value of this leaf is -1.
            If the value of hwExtSrvFlowParaType is set to 13, this leaf indicates the CNU ID.
            If the value of hwExtSrvFlowParaType is set to 14, this leaf indicates the ONT ID and the type of service-port endpoint, as follows:
            --------------------------------------------------------
            | bit16-bit31   | bit0-bit15                           |
            --------------------------------------------------------
            | ONT ID        |  the type of service-port endpoint   |
                               0: ONT lan-eth port
                               1: ONT iphost port
                               2: ONT lan-vdsl port
                               3: ONT ippath port
                             255: ONT WAN port
            --------------------------------------------------------
            If the value of hwExtSrvFlowParaType is set to 15, this leaf indicates the CM index.
           "
       ::= { hwExtSrvFlowEntry 5 }

   hwExtSrvFlowPara5 OBJECT-TYPE
       SYNTAX Integer32
       MAX-ACCESS read-write
       STATUS current
       DESCRIPTION
           "The meaning is variable with the value of hwExtSrvFlowParaType:
            If the value of hwExtSrvFlowParaType is set to 1, 2, 3, 5, 6, 7, 8, 15, or 16, this leaf is reserved.
            If the value of hwExtSrvFlowParaType is set to 4, this leaf indicates the GEM port index for
            the GPON profile mode and is reserved for the GPON distributed mode.
            The returned value is -1 if this leaf is reserved.
            If the value of hwExtSrvFlowParaType is set to 9, 10, 11, 12, this leaf indicates the port mask
            of ports on ONT, bit0 indicates port 1, bit1 indicates port 2, and so on, the max port number is 8,
            only for ONT service flow.
            If the value of hwExtSrvFlowParaType is set to 13, this leaf indicates the port mask of ports on CNU,
            bit0 indicates port 1, bit1 indicates port 2, and so on, the max port number is 4.
            If the value of hwExtSrvFlowParaType is set to 14, this leaf is valid only when the service-port
            is configured on the ONT Ethernet, LAN-VDSL or IPPATH port.
            Specially, bit16 indicates the WIFI port on Coaxial Network Unit.
           "
       ::= { hwExtSrvFlowEntry 6 }

   hwExtSrvFlowParaType OBJECT-TYPE
       SYNTAX INTEGER
           {
            pvc(1),
            eth(2),
            vdsl(3),
            gpon(4),
            shdsl(5),
            epon(6),
            vcl(7),
            adsl(8),
            gponOntEth(9),
            eponOntEth(10),
            gponOntIphost(11),
            eponOntIphost(12),
            eocCnuEth(13),
            xponEndToEnd(14),
            docsis(15),
            fast(16)
           }
       MAX-ACCESS read-write
       STATUS current
       DESCRIPTION
           "The mode of create flow.
            Options:
            1. pvc(1)             -indicates that PVC is the logical port for service flow,
                                   applicable for xDSL ATM mode access and AIUG ATM service.
                                   It is recommended that vcl(7) instead of pvc(1) be used.
            2. eth(2)             -indicates that the flow is based on Ethernet port.
            3. vdsl(3)            -indicates VDSL2 access, only for the PTM mode.
            4. gpon(4)            -indicates GPON access.
            5. shdsl(5)           -indicates SHDSL access, only for the PTM mode.
            6. epon(6)            -indicates EPON access.
            7. vcl(7)             -indicates that VCL(VC port) is the logical port for service flow,
                                   applicable for xDSL ATM mode access and AIUG ATM service.
                                   It is recommended that vcl(7) instead of pvc(1) be used.
            8. adsl(8)            -indicates ADSL access.
            9. gponOntEth(9)      -indicates eth access on the ONT of GPON, only for ONT service flow.
            10. eponOntEth(10)    -indicates eth access on the ONT of EPON, only for ONT service flow.
            11. gponOntIphost(11) -indicates iphost access on the ONT of GPON, only for ONT service flow.
            12. eponOntIphost(12) -indicates iphost access on the ONT of EPON, only for ONT service flow.
            13. eocCnuEth(13)     -indicates eth access on the Coaxial Network Unit of EoC, only for Coaxial Network Unit service flow.
            14. xponEndToEnd(14)  -indicates eth access, iphost access, or WAN access on the ONT of xPON, only for ONT service flow.
            15. docsis(15)        -indicates DOCSIS access.
            16. fast(16)          -indicates G.fast access.
           "
       DEFVAL { pvc }
       ::= { hwExtSrvFlowEntry 7 }

   hwExtSrvFlowVlanid OBJECT-TYPE
       SYNTAX Integer32 (-1|1..4095)
       MAX-ACCESS read-write
       STATUS current
       DESCRIPTION
           "Service VLAN ID, identifying the global VLAN for switch-oriented service flow.
           "
       DEFVAL { 1 }
       ::= { hwExtSrvFlowEntry 8 }

      hwExtSrvFlowReceiveTrafficDescrIndex OBJECT-TYPE
       SYNTAX Integer32
       MAX-ACCESS read-write
       STATUS current
       DESCRIPTION
           "Indicates the index of the IP traffic table (hwIpTrafficParamTable)
            applying to the service flow in the outbound direction of the user
            port (for terminal users, it is the Rx direction).
           "
       DEFVAL { 1 }
       ::= { hwExtSrvFlowEntry 9 }

   hwExtSrvFlowTransmitTrafficDescrIndex OBJECT-TYPE
       SYNTAX Integer32
       MAX-ACCESS read-write
       STATUS current
       DESCRIPTION
           "Indicates the index of the IP traffic table (hwIpTrafficParamTable) applying to
            the service flow in the inbound direction of the user port (for terminal users,
            it is the Tx direction).
           "
       DEFVAL { 1 }
       ::= { hwExtSrvFlowEntry 10 }

   hwExtSrvFlowMultiServiceType OBJECT-TYPE
       SYNTAX INTEGER
               {
                byUserVlan(1),
                byEncap(2),
                by8021p(3),
                byVlanEncap(4),
                byDoubleVlan(5),
                by8021pList(6),
                singleService(255)
              }
       MAX-ACCESS read-write
       STATUS current
       DESCRIPTION
           "Indicates the traffic classification criteria on the port or logical port for user services.
            Options:
            1. byUserVlan(1)       -indicates traffic classification by C-VLAN.
            2. byEncap(2)          -indicates traffic classification by EtherType.
            3. by8021p(3)          -indicates traffic classification by C-VLAN+802.1p.
            4. byVlanEncap(4)      -indicates traffic classification by C-VLAN+EtherType
            5. byDoubleVlan(5)     -indicates traffic classification by S-VLAN+C-VLAN.
            6. by8021pList(6)      -indicates traffic classification by C-VLAN+802.1pList.
            7. singleService(255)  -indicates traffic classification by port or logical port.
            To create a service flow, this leaf is optional. If a value is not specified,
            singleService(255) is adopted by default, which indicates traffic classification by port or logical port.
           "

       ::= { hwExtSrvFlowEntry 11 }

   hwExtSrvFlowMultiServiceUserPara OBJECT-TYPE
       SYNTAX Integer32
       MAX-ACCESS read-write
       STATUS current
       DESCRIPTION
           "Indicates the traffic classification parameter on the port or logical port for user service.
            The meaning is variable with the value of hwExtSrvFlowMultiServiceType:
            If the value of hwExtSrvFlowMultiServiceType is set to byUserVlan(1),
            this leaf indicates the C-VLAN ID. The value range of the C-VLAN ID is 1-4095.
            The value 0 indicates priority-tagged, the value 0xFFFF indicates untagged,
            and the value 0xFFFE indicates any (other all) traffic. For VLAN range service flow,
            this leaf includes the start C-VLAN ID (1-4095) and the end C-VLAN ID (1-4095):

               ------------------------------------------------------
              | bit31-bit28 | bit27-bit16 | bit15-bit12 | bit11-bit0 |
              --------------------------------------------------------
              |    Reserved  | End VLAN ID |  reserve    |   VLAN ID  |
              --------------------------------------------------------

           If the value of hwExtSrvFlowMultiServiceType is set to byEncap(2), this leaf indicates
           the EtherType. The value IPoE(1) indicates IPv4(0x0800), IPv6(0x86dd),ARP(0x0806), RARP(0x8035)
           and other non-PPPoE traffic; the value PPPoE(2) indicates PPPoE traffic(0x8863 & 0x8864).
           the value IPv6oE(3) indicates IPv6 traffic(0x86dd);
           the value IPv4oE(0) indicates IPoE traffic but without IPv6 traffic;
           If the value of hwExtSrvFlowMultiServiceType is set to by8021p(3), this leaf indicates
           the combination of the C-VLAN ID (0-4095; 0 indicates priority-tagged)
           and the 802.1p priority (0-7):

              ----------------------------------------------------------
              | bit31-bit16 | bit15-bit13   |   bit12     | bit11-bit0 |
              ----------------------------------------------------------
              |    Reserved  | Priority(0-7) |  reserve    |   VLAN ID  |
              ----------------------------------------------------------

           If the value of hwExtSrvFlowMultiServiceType is set to byVlanEncap(4), this leaf indicates
           the combination of the C-VLAN ID (0-4095; 0 indicates priority-tagged, and 0x1FFF indicates
           untagged) and the EtherType (0: IPv4oE; 1: IPoE; 2: PPPoE; 3: IPv6oE):

              ---------------------------------------------------------------
              | bit31-bit16 | bit15-bit13   |   bit12           | bit11-bit0 |
              ---------------------------------------------------------------
              |    Reserved  | EtherType     |  Untagged flag    |   VLAN ID  |
              ----------------------------------------------------------------

           If the hwExtSrvFlowMultiServiceType is byDoubleVlan(5),
           the hwExtSrvFlowMultiServiceUserPara means the C-VLAN
           (inner VLAN, 1-4095) and S-VLAN (outer VLAN, 1-4095)

              ------------------------------------------------------------
              | bit31-bit28 | bit27-bit16   |  bit15-bit12  | bit11-bit0 |
              ------------------------------------------------------------
              |    Reserved  | Inner VLAN    |    reserve    |Outer VLAN  |
              ------------------------------------------------------------

           If the hwExtSrvFlowMultiServiceType is by8021pList(6),
           the hwExtSrvFlowMultiServiceUserPara means the 802.1p list bitmap and
           C-VLAN (outer VLAN, 1-4095 or 0xFFFE). The C-VLAN value 0xFFFE indicates any VLAN.
           For example, if the PriorityMask is 0x05, the priority list is 0 and 2.

              ------------------------------------------------
              | bit31-bit24 | bit23-bit16   |   bit15-bit0 |
              ----------------------------------------------
              |    Reserved  | PriorityMask |   VLAN ID  |
              -----------------------------------------------

           If the hwExtSrvFlowMultiServiceType is singleService (255),
           the hwExtSrvFlowMultiServiceType is invalid.
          "
       ::= { hwExtSrvFlowEntry 12 }

   hwExtSrvFlowAdminStatus   OBJECT-TYPE
      SYNTAX   INTEGER  {
             up(1),
             down(2)
            }
      MAX-ACCESS   read-create
      STATUS       current
      DESCRIPTION
           "Indicates the administrative status of the service flow.
            Options:
            1. up(1)    -indicates that traffic is allowed to pass.
            2. down(2)  -indicates that traffic is blocked.
            Default: up(1)
           "
      DEFVAL { up }
      ::= { hwExtSrvFlowEntry 13}

   hwExtSrvFlowOperStatus  OBJECT-TYPE
      SYNTAX   INTEGER  {
             up(1),
             down(2),
             unknown(3)
            }
      MAX-ACCESS   read-only
      STATUS       current
      DESCRIPTION
          "Indicates the run status of the service flow.
           It is read only.
           Options:
           1. up(1)      -indicates the flow operstatus is up
           2. down(2)    -indicates the flow operstatus is down
           3. unknown(3) -indicates the flow operstatus is unknown
          "
      ::= { hwExtSrvFlowEntry 14}

   hwExtSrvFlowRowStatus        OBJECT-TYPE
      SYNTAX       RowStatus
      MAX-ACCESS   read-create
      STATUS       current
      DESCRIPTION
          "Indicates the row status. To create a service flow,
           set this leaf to createAndGo(4). To delete a service flow,
           set this leaf to destroy(6).
           When this leaf is queried, the value is fixed to active(1).
           Options:
           1. active(1)      -indicates the query operation
           2. createAndGo(4) -indicates creating a service flow
           3. destroy(6)     -indicates deleting a service flow
          "
      DEFVAL { active }
      ::= { hwExtSrvFlowEntry 15}

   hwExtSrvFlowInnerVlanId OBJECT-TYPE
      SYNTAX Integer32 (-1 | 1..4095)
      MAX-ACCESS read-write
      STATUS current
      DESCRIPTION
          "Multi-Service up inner vlan id,
           the bound of parameter is 1 to 4095.
          "
      DEFVAL { -1 }
      ::= { hwExtSrvFlowEntry 16 }

   hwExtSrvFlowDescInfo OBJECT-TYPE
      SYNTAX OCTET STRING  (SIZE (0..64))
      MAX-ACCESS read-write
      STATUS current
      DESCRIPTION
          "Indicates the description of a service flow, used for describing certain
           information about a service flow, such as the telephone number or location
           of the user. Note that the value may be not unique.
           The default value of the description string is null.
          "
      ::= { hwExtSrvFlowEntry 17 }

   hwExtSrvFlowTagTransform OBJECT-TYPE
      SYNTAX INTEGER
          {
          add(0),
          transparent(1),
          translate(2),
          translateAndAdd(3),
          addDouble(4),
          translateDouble(5),
          translateAndRemove(6),
          remove(7),
          removeDouble(8)
          }
      MAX-ACCESS read-write
      STATUS current
      DESCRIPTION
          "Indicates the VLAN tag transforming mode of the service flow,
           which means how the VLAN tags are changed in the upstream direction
           (from user-side to the network-side) when the traffic passes through the access node.
           Normally, in the reverse direction, transforming is reversed. For example,
           in the upstream direction, if it is 'adding one VLAN tag',
           and in the downstream direction it will be 'removing one VLAN tag'.
           Currently, nine transforming modes are supported:
           Options:
           1. add(0)                  -indicates adding one VLAN tag to the traffic in the upstream direction
           2. transparent(1)          -indicates retaining the VLAN tag of the traffic in the upstream direction
                                       The S-VLAN ID allocated must be the same as the C-VLAN (user VLAN) ID
           3. translate(2)            -indicates translating the C-VLAN to the S-VLAN
           4. translateAndAdd(3)      -indicates translating the C-VLAN to the S-VLAN
                                       and adding one VLAN tag as a new C-VLAN
           5. addDouble(4)            -indicates adding two VLAN tags to the traffic
           6. translateDouble(5)      -indicates translating the S-VLAN and C-VLAN to the new S-VLAN and the new C-VLAN
           7. translateAndRemove(6)   -indicates translating the S-VLAN and C-VLAN to a new S-VLAN and no C-VLAN
                                       for the input traffic with double VLANs
           8. remove(7)               -indicates removing one VLAN tag (the outer one if there are two VLAN tags) from the traffic
                                       Only the connection-oriented service flow supports this mode
           9. removeDouble(8)         -indicates removing two VLAN tags from the traffic
                                       Only the connection-oriented service flow supports this mode.
          "
      DEFVAL { add }
      ::= { hwExtSrvFlowEntry 18 }

   hwExtSrvFlowSimulationServiceType OBJECT-TYPE
      SYNTAX INTEGER
          {
              invalid(-1),
              default(0),
              aoe(1),
              tdmoe(2),
              ethernetTransparent(3),
              vcloe(4)
          }
      MAX-ACCESS read-write
      STATUS current
      DESCRIPTION
          "Indicates the type of a simulation service.
           Options:
           1. invalid(-1) -indicates a connection-oriented service flow, only for read
           2. default(0)  -indicates a switch-oriented service flow rather than a simulation service
                           The S-VLAN (hwExtSrvFlowVlanid) is mandatory
           3. aoe(1)      -indicates an AoE (ATM over Ethernet) service flow for ATM PWE3 service
           4. tdmoe(2)    -indicates a TDMoE (TDM over Ethernet) service flow for E1/STM-1
                           upstream transmission and TDM PWE3 service
           5. ethernetTransparent(3) -indicates the Ethernet transparent service flow. That is, all
                                      the Ethernet traffic from the user side is transparently transmitted
                                      to the network side
           6. vcloe(4)    --indicates a virtual channel link over Ethernet (VCLoE) service flow,
                            which is a virtual service channel automatically created by the system.
           Default: default(0)
           If this leaf is set to a value other than default(0), the S-VLAN (hwExtSrvFlowVlanid)
           of the service is invalid.
          "
      DEFVAL { default }
      ::= { hwExtSrvFlowEntry 19 }

   hwExtSrvFlowRemoteDescInfo OBJECT-TYPE
      SYNTAX OCTET STRING  (SIZE (0..64))
      MAX-ACCESS read-write
      STATUS current
      DESCRIPTION
          "Indicates the description of remote end of a service flow,
           used for describing certain information about a service flow so-called RID.
           Note that the value may be not unique.
           The default value of the description string is null.
          "
      ::= { hwExtSrvFlowEntry 20 }

   hwExtSrvFlowOutboundTrafficTableName OBJECT-TYPE
      SYNTAX OCTET STRING  (SIZE (0..32))
      MAX-ACCESS read-write
      STATUS current
      DESCRIPTION
          "Indicates the name of IP traffic table (hwIpTrafficParamTable)
           applying to the service flow in the outbound direction of the user port.
          "
      ::= { hwExtSrvFlowEntry 21 }

   hwExtSrvFlowInboundTrafficTableName OBJECT-TYPE
      SYNTAX OCTET STRING  (SIZE (0..32))
      MAX-ACCESS read-write
      STATUS current
      DESCRIPTION
          "Indicates the name of IP traffic table (hwIpTrafficParamTable)
           applying to the service flow in the inbound direction of the user port.
          "
      ::= { hwExtSrvFlowEntry 22 }

   hwExtSrvFlowRxUpc OBJECT-TYPE
      SYNTAX   INTEGER
          {
          invalid(-1),
          on(1),
          off(2)
          }
      MAX-ACCESS read-write
      STATUS current
      DESCRIPTION
          "Upc value of Rx in ATM service. This leaf supports only invalid.
           Options:
           1. invalid(-1) -Indicates not support this feature.
           2. on(1)       -Indicate Rx Upc on.
           3. off(2)      -Indicate Rx Upc off.
          "
      ::= { hwExtSrvFlowEntry 23 }

   hwExtSrvFlowTxUpc OBJECT-TYPE
      SYNTAX   INTEGER  {
                    invalid(-1),
                    on(1),
                    off(2)
                   }
       MAX-ACCESS read-write
       STATUS current
       DESCRIPTION
           "Upc value of Tx in ATM service. This leaf supports only invalid.
            Options:
            1. invalid(-1) -Indicates not support this feature.
            2. on(1)       -Indicate Tx Upc on.
            3. off(2)      -Indicate Tx Upc off.
           "
       ::= { hwExtSrvFlowEntry 24 }

   hwExtSrvFlowNNIInnerVlanId OBJECT-TYPE
      SYNTAX Integer32 (-1..4095)
      MAX-ACCESS read-write
      STATUS current
      DESCRIPTION
           "Indicates the network-side inner VLAN ID of switch-oriented service flow.
            The value of this leaf is variable with the value of hwExtSrvFlowTagTransform.
            If the value of hwExtSrvFlowTagTransform is set to 3, 4, 5, this leaf can be set to 1-4095.
            If the vlaue of hwExtSrvFlowTagTransform is set to 0, 1, 2 ,6, 7, 8, this leaf can not be set,
            and the invalid value -1 will be returned.
            The system uses value 0 of this leaf for some automatically create service flows,
            and users cannot use value 0.
           "
       ::= { hwExtSrvFlowEntry 25 }

   hwExtSrvFlowNNIInnerPriority OBJECT-TYPE
      SYNTAX Integer32 (-1 | 0..7)
      MAX-ACCESS read-write
      STATUS current
      DESCRIPTION
          "Indicates the network-side inner VLAN priority of switch-oriented service flow.
           The value of this leaf is variable with the value of hwExtSrvFlowTagTransform.
           If the value of hwExtSrvFlowTagTransform is set to 3, 4, 5, this leaf can be set to 0-7.
           If the vlaue of hwExtSrvFlowTagTransform is set to 0, 1, 2 ,6, 7, 8, this leaf can not be set,
           and the invalid value -1 will be returned.
           It is recommended that the IP traffic table be used to configure the inner
           VLAN priority of a service flow instead of using hwExtSrvFlowNNIInnerPriority.
          "
      ::= { hwExtSrvFlowEntry 26 }

   hwExtSrvFlowBundleIndex OBJECT-TYPE
       SYNTAX Integer32
       MAX-ACCESS read-write
       STATUS current
       DESCRIPTION
           "Indicates the service flow bundle index.
            A service flow bundle is an entity including certain service flows from
            one L3 access user such as residential gateway device. Traffic associated
            with different service flows sharing the same bundle follows the same
            forwarding path across the access node. And the service flows are
            classified for 802.1p CoS purpose.
            If a service flow is not belong to any flow bundle when creating, this leaf can not be set, and
            the invalid value -1 will be returned.
           "
       ::= { hwExtSrvFlowEntry 27 }

   hwExtSrvFlowBundleMemberSortPara OBJECT-TYPE
       SYNTAX Integer32 (-1 | 0..65791)
       MAX-ACCESS read-write
       STATUS current
       DESCRIPTION
           "Indicates the corresponding key value of a service flow in service flow bundle.
            Now service flow bundle type must be byPbit(1), indicating that the key para is CoS.
            The range of CoS is 0-7.
            If a service flow is not belong to any flow bundle when creating, this leaf can not be set, and
            the invalid value -1 will be returned.
            If the high 16 bits of the value is 0,it is in cos mode.the low 8 bits of it represents the value of cos.
            If the high 16 bits of the value is 1,it is in cos-list mode.the low 8 bits of it represents the bitmap of cos-list.
           "
       ::= { hwExtSrvFlowEntry 28 }

   hwExtSrvFlowSourceType OBJECT-TYPE
       SYNTAX INTEGER
           {
           root(1),
           leaf(2)
           }
       MAX-ACCESS read-write
       STATUS current
       DESCRIPTION
           "Indicates the source end-point type of a service flow.
            Options:
            1. root(1) -indicates that the source end-point is a switch domain.
                        A switch domain for service flow indicates an S-VLAN.
            2. leaf(2) -indicates that the source end-point is a port or logical port.
                        A port or logical port for service flow indicates a flow point (FP).
            The source end-point locates the network side.
            If the source end-point type is root(1) and the destination is leaf(2), the flow is called switch-oriented.
            If the source end-point type is leaf(2) and the destination is leaf(2), the flow is connection-oriented.
           "
       DEFVAL { root }
       ::= { hwExtSrvFlowEntry 29 }

   hwExtSrvFlowDestinationType OBJECT-TYPE
       SYNTAX INTEGER
           {
           invalid(-1),
           leaf(2)
           }
       MAX-ACCESS read-write
       STATUS current
       DESCRIPTION
           "Indicates the destination end-point type of a service flow.
            Options:
            1. invalid(-1)  -indicates invalid.
            2. leaf(2)      -indicates that the source end-point is a port or logical port.
            A port or logical port for service flow indicates a flow point (FP).
            The destination end-point locates the user side or cascade side, and the type must be leaf(2).
           "
       DEFVAL { leaf }
       ::= { hwExtSrvFlowEntry 30 }

   hwExtSrvFlowSourceParaType OBJECT-TYPE
       SYNTAX INTEGER
           {
           invalid(-1),
           eth(2),
           rf(17),
           vxlan(18)
           }
       MAX-ACCESS read-write
       STATUS current
       DESCRIPTION
           "The value and meaning of the parameter:
            Options:
            1. invalid(-1) -indicates invalid.
            2. eth(2)      -indicates that the source end-point of the service flow is based on Ethernet port.
            3. rf(17)      -indicates that the source end-point of the service flow is based on RF port.
            4. vxlan(18)   -indicates that the source end-point of the service flow is based on VxLan.
            "
       ::= { hwExtSrvFlowEntry 31 }

   hwExtSrvFlowSourcePara1 OBJECT-TYPE
       SYNTAX Integer32
       MAX-ACCESS read-write
       STATUS current
       DESCRIPTION
           "The meaning is variable with the value of hwExtSrvFlowSourceParaType:
            If the value of hwExtSrvFlowSourceParaType is set to 2, this leaf indicates the shelf ID.
			If the value of hwExtSrvFlowSourceParaType is -1 and the created service flow is of strict S+C, the value of this leaf indicates the shelf ID.
            If a service flow is not connection-oriented, the returned value of this leaf is -1, which indicates invalid.
           "
       ::= { hwExtSrvFlowEntry 32 }

   hwExtSrvFlowSourcePara2 OBJECT-TYPE
       SYNTAX Integer32
       MAX-ACCESS read-write
       STATUS current
       DESCRIPTION
           "The meaning is variable with the value of hwExtSrvFlowSourceParaType:
            If the value of hwExtSrvFlowSourceParaType is set to 2, this leaf indicates the slot ID.
			If the value of hwExtSrvFlowSourceParaType is -1 and the created service flow is of strict S+C, the value of this leaf indicates the slot ID.
            If a service flow is not connection-oriented, the returned value of this leaf is -1, which indicates invalid.
           "
       ::= { hwExtSrvFlowEntry 33 }

   hwExtSrvFlowSourcePara3 OBJECT-TYPE
       SYNTAX Integer32
       MAX-ACCESS read-write
       STATUS current
       DESCRIPTION
           "The meaning is variable with the value of hwExtSrvFlowSourceParaType:
            If the value of hwExtSrvFlowSourceParaType is set to 2, this leaf indicates the port ID.
			If the value of hwExtSrvFlowSourceParaType is -1 and the created service flow is of strict S+C, the value of this leaf indicates the port ID.
            If a service flow is not connection-oriented, the returned value of this leaf is -1, which indicates invalid.
           "
       ::= { hwExtSrvFlowEntry 34 }

   hwExtSrvFlowSourcePara4 OBJECT-TYPE
       SYNTAX Integer32
       MAX-ACCESS read-write
       STATUS current
       DESCRIPTION
           "The meaning is variable with the value of hwExtSrvFlowSourceParaType:
            If the value of hwExtSrvFlowSourceParaType is set to 2, this leaf is reserved and the returned value is -1.
            If a service flow is not connection-oriented, the returned value of this leaf is -1, which indicates invalid.
           "
       ::= { hwExtSrvFlowEntry 35 }

   hwExtSrvFlowSourcePara5 OBJECT-TYPE
       SYNTAX Integer32
       MAX-ACCESS read-write
       STATUS current
       DESCRIPTION
           "The meaning is variable with the value of hwExtSrvFlowSourceParaType:
            If the value of hwExtSrvFlowSourceParaType is set to 2, this leaf is reserved and the returned value is -1.
            If a service flow is not connection-oriented, the returned value of this leaf is -1, which indicates invalid.
           "
       ::= { hwExtSrvFlowEntry 36 }

   hwExtSrvFlowSourceMultiServiceType OBJECT-TYPE
       SYNTAX INTEGER
           {
           invalid(-1),
           byUserVlan(1),
           byDoubleVlan(5),
           singleService(255)
           }
       MAX-ACCESS read-write
       STATUS current
       DESCRIPTION
           "Indicates the traffic classification criteria on the port or logical port.
            For the source end-point.
            Options:
            1. invalid(-1)     -invalid
            2. byUserVlan(1)   -indicates traffic classification by outer VLAN ID
            3. byDoubleVlan(5) -indicates traffic classification by S-VLAN (outer VLAN)+C-VLAN (inner VLAN)
            4. singleService(255)  -indicates traffic classification by port or logical port.
            To create a service flow, this leaf is optional. If a value is not specified,
            singleService(255) is adopted by default, which indicates traffic classification by port or logical port.
           "
       DEFVAL { singleService }
       ::= { hwExtSrvFlowEntry 37 }

   hwExtSrvFlowSourceMultiServiceUserPara OBJECT-TYPE
       SYNTAX Integer32
       MAX-ACCESS read-write
       STATUS current
       DESCRIPTION
           "The flow classification parameter on the port or logical port for user service.
            The meaning is variable with the value of hwExtSrvFlowSourceMultiServiceType:
            If the hwExtSrvFlowSourceMultiServiceType is byUserVlan(1),
            the hwExtSrvFlowSourceMultiServiceUserPara means the outer VLAN.
            The value 1 - 4095 means C-VLAN ID, and the value 0xFFFF means untagged traffic.
            The value 0xFFFE means any (other all) traffic.

            bit31-bit28  bit27-bit16 bit15-bit12 bit11-bit0
            reserve      reserve      reserve     VLAN ID

            If the hwExtSrvFlowSourceMultiServiceType is byDoubleVlan(5),
            the hwExtSrvFlowSourceMultiServiceUserPara means the C-VLAN(inner VLAN, 1-4095)
            and S-VLAN(outer VLAN, 1-4095) combination:

            bit31-bit28 bit27-bit16 bit15-bit12 bit11-bit0
            reserve      Inner VLAN   reserve    Outer VLAN

           "
       ::= { hwExtSrvFlowEntry 38 }

   hwExtSrvFlowSourceInnerVlanId OBJECT-TYPE
       SYNTAX Integer32 (-1 | 1..4095)
       MAX-ACCESS read-write
       STATUS current
       DESCRIPTION
           "Multi-Service up inner vlan id, the bound of parameter is 1 to 4095.
            If a service flow is not connection-oriented, or the value of this leaf is not set,
            the returned value of this leaf is -1, which indicates invalid.
           "
       ::= { hwExtSrvFlowEntry 39 }

   hwExtSrvFlowOntPortListMask OBJECT-TYPE
      SYNTAX OCTET STRING (SIZE (0..32))
      MAX-ACCESS read-write
      STATUS current
      DESCRIPTION
      "This leaf is required when the service flow is created on a specified ONT port.
             The 8-character string maps eight ports. The value 1 of a character indicates that the corresponding port is valid,
             and the value 0 of a character indicates that the corresponding port is invalid.
             For example, 11000000 indicates ports 1 and 2, and 01010101 indicates ports 2, 4, 6, and 8.
             The port type depends on hwExtSrvFlowOntPortType.
             If hwExtSrvFlowOntPortType is set to eth(1), it indicates an ETH port.
             If hwExtSrvFlowOntPortType is set to iphost(2), it indicates an VOIP port.
             Currently, VOIP has only one port (port 1), that is, 10000000.
      "
      ::= { hwExtSrvFlowEntry 40 }

   hwExtSrvFlowOntPortType OBJECT-TYPE
       SYNTAX INTEGER
           {
           eth(1),
           iphost(2),
           invalid(255)
           }
       MAX-ACCESS read-write
       STATUS current
       DESCRIPTION
           "Indicates the ONT port type.
            Options:
            1. eth(1)        -indicates the eth port
            2. iphost(2)     -indicates the VOIP port
            3. invalid(255)  -indicates this parameter is invalid
            During the service flow creation on a specified ONT port, if this leaf is not specified, eth(1) is adopted by default.
           "
       DEFVAL { eth }
       ::= { hwExtSrvFlowEntry 41 }

   hwExtSrvFlowStatPerSwitch OBJECT-TYPE
      SYNTAX INTEGER
          {
          enable(1),
          disable(2)
          }
       MAX-ACCESS read-write
       STATUS current
       DESCRIPTION
           "Indicates the switch of service-port statistics performance.
            Options:
            1. enable(1)      -indicates the switch of service-port statistics performance is enable
            2. disable(2)     -indicates the switch of service-port statistics performance is disable
           "
       DEFVAL { disable }
       ::= { hwExtSrvFlowEntry 42 }

-- hwFlowFluxStatisticTable
   hwFlowFluxStatisticTable OBJECT-TYPE
       SYNTAX SEQUENCE OF HwFlowFluxStatisticEntry
       MAX-ACCESS not-accessible
       STATUS current
       DESCRIPTION
           "Indicates the table that contains statistics per service flow for traffic received and transmitted.
            The index of this table is hwFlowID.
           "
       ::= { hwExtSrvFlow 3 }

   hwFlowFluxStatisticEntry OBJECT-TYPE
   SYNTAX HwFlowFluxStatisticEntry
       MAX-ACCESS not-accessible
       STATUS current
       DESCRIPTION
           "Indicates the table that contains statistics per service flow for traffic received and transmitted.
            The index of this entry is hwFlowID.
           "
       INDEX { hwFlowID  }
       ::= { hwFlowFluxStatisticTable 1 }

   HwFlowFluxStatisticEntry ::=
       SEQUENCE {
         hwFlowID
           Integer32,
         hwFlowFluxUpCells
           Unsigned32,
         hwFlowFluxUpPackets
           Counter64,
         hwFlowFluxDownCells
           Unsigned32,
         hwFlowFluxDownPackets
           Counter64,
         hwFlowFluxAdminStatus
            INTEGER,
         hwFlowFluxUpBytes
           Counter64,
         hwFlowFluxDownBytes
           Counter64,
         hwFlowFluxUpDiscardPackets
           Counter64,
         hwFlowFluxDnDiscardPackets
           Counter64,
         hwFlowFluxUpMCCells
           Counter64,
         hwFlowFluxUpMCPackets
           Counter64,
         hwFlowFluxDownMCCells
           Counter64,
         hwFlowFluxDownMCPackets
           Counter64,

         hwFlowFluxSourceUpBytes
           Counter64,
         hwFlowFluxSourceUpPackets
           Counter64,
         hwFlowFluxSourceUpDiscardPackets
           Counter64,
         hwFlowFluxSourceDownBytes
           Counter64,
         hwFlowFluxSourceDownPackets
           Counter64,
         hwFlowFluxSourceDownDiscardPackets
           Counter64,
         hwFlowFluxDestinationUpBytes
           Counter64,
         hwFlowFluxDestinationUpPackets
           Counter64,
         hwFlowFluxDestinationUpDiscardPackets
           Counter64,
         hwFlowFluxDestinationDownBytes
           Counter64,
         hwFlowFluxDestinationDownPackets
           Counter64,
         hwFlowFluxDestinationDownDiscardPackets
           Counter64
        }

   hwFlowID OBJECT-TYPE
       SYNTAX Integer32
       MAX-ACCESS read-only
       STATUS current
       DESCRIPTION
           "This leaf is the same as hwExtSrvFlowIndex, which indicates the service flow index, a unique
            value to identify a service flow.
           "
       ::= { hwFlowFluxStatisticEntry 1 }

   hwFlowFluxUpCells OBJECT-TYPE
       SYNTAX Unsigned32
       MAX-ACCESS read-only
       STATUS current
       DESCRIPTION
           "Indicates the statistics of upstream cells of the service flow. It is valid for ATM access."
       ::= { hwFlowFluxStatisticEntry 2 }

   hwFlowFluxUpPackets OBJECT-TYPE
       SYNTAX Counter64
       MAX-ACCESS read-only
       STATUS current
       DESCRIPTION
           "Indicates the statistics of upstream packets of the service flow."
       ::= { hwFlowFluxStatisticEntry 3 }

   hwFlowFluxDownCells OBJECT-TYPE
       SYNTAX Unsigned32
       MAX-ACCESS read-only
       STATUS current
       DESCRIPTION
           "Indicates the statistics of downstream cells of the service flow. It is valid for ATM access."
       ::= { hwFlowFluxStatisticEntry 4 }

   hwFlowFluxDownPackets OBJECT-TYPE
       SYNTAX Counter64
       MAX-ACCESS read-only
       STATUS current
       DESCRIPTION
           "Indicates the statistics of downstream packets of the service flow."
       ::= { hwFlowFluxStatisticEntry 5 }

   hwFlowFluxAdminStatus OBJECT-TYPE
       SYNTAX INTEGER
           {
               reset(0),
               invalid(-1)
           }
       MAX-ACCESS read-write
       STATUS current
       DESCRIPTION
           "Used to reset the statistics only. The value must be set to reset(0).
            Options:
            1. reset(0)    -reset the statistics
            2. invalid(-1) -invalid
           "
       ::= { hwFlowFluxStatisticEntry 6 }

   hwFlowFluxUpBytes OBJECT-TYPE
       SYNTAX Counter64
       MAX-ACCESS read-only
       STATUS current
       DESCRIPTION
           "Indicates the statistics of upstream bytes of the service flow."
       ::= { hwFlowFluxStatisticEntry 7 }

   hwFlowFluxDownBytes OBJECT-TYPE
       SYNTAX Counter64
       MAX-ACCESS read-only
       STATUS current
       DESCRIPTION
           "Indicates the statistics of downstream bytes of the service flow."
       ::= { hwFlowFluxStatisticEntry 8 }

   hwFlowFluxUpDiscardPackets OBJECT-TYPE
       SYNTAX Counter64
       MAX-ACCESS read-only
       STATUS current
       DESCRIPTION
           "Indicates the statistics of upstream discarded packets of the service flow."
       ::= { hwFlowFluxStatisticEntry 9 }

   hwFlowFluxDnDiscardPackets OBJECT-TYPE
       SYNTAX Counter64
       MAX-ACCESS read-only
       STATUS current
       DESCRIPTION
           "Indicates the statistics of downstream discarded packets of the service flow."
       ::= { hwFlowFluxStatisticEntry 10 }

   hwFlowFluxUpMCCells OBJECT-TYPE
       SYNTAX Counter64
       MAX-ACCESS read-only
       STATUS current
       DESCRIPTION
            "Indicates the flux of upstream multicast cells of the service flow.(cells/s)"
       ::= { hwFlowFluxStatisticEntry 11 }

   hwFlowFluxUpMCPackets OBJECT-TYPE
       SYNTAX Counter64
       MAX-ACCESS read-only
       STATUS current
       DESCRIPTION
            "Indicates the flux of upstream multicast packets of the service flow.(packets/s)"
       ::= { hwFlowFluxStatisticEntry 12 }

   hwFlowFluxDownMCCells OBJECT-TYPE
       SYNTAX Counter64
       MAX-ACCESS read-only
       STATUS current
       DESCRIPTION
            "Indicates the flux of downstream multicast cells of the service flow.(cells/s)"
       ::= { hwFlowFluxStatisticEntry 13 }

   hwFlowFluxDownMCPackets OBJECT-TYPE
       SYNTAX Counter64
       MAX-ACCESS read-only
       STATUS current
       DESCRIPTION
            "Indicates the flux of downstream multicast packets of the service flow.(packets/s)"
       ::= { hwFlowFluxStatisticEntry 14 }

   hwFlowFluxSourceUpBytes OBJECT-TYPE
       SYNTAX Counter64
       MAX-ACCESS read-only
       STATUS current
       DESCRIPTION
            "Indicates the statistics of source upstream bytes of the service flow.Only connection-oriented
             flow supports this leaf, others return 0xff"
       ::= { hwFlowFluxStatisticEntry 15 }

   hwFlowFluxSourceUpPackets OBJECT-TYPE
       SYNTAX Counter64
       MAX-ACCESS read-only
       STATUS current
       DESCRIPTION
            "Indicates the statistics of source upstream packets of the service flow.Only connection-oriented
             flow supports this leaf, others return 0xff"
       ::= { hwFlowFluxStatisticEntry 16 }

   hwFlowFluxSourceUpDiscardPackets OBJECT-TYPE
       SYNTAX Counter64
       MAX-ACCESS read-only
       STATUS current
       DESCRIPTION
            "Indicates the statistics of source upstream discarded packets of the service flow.Only connection-oriented
             flow supports this leaf, others return 0xff"
       ::= { hwFlowFluxStatisticEntry 17 }

   hwFlowFluxSourceDownBytes OBJECT-TYPE
       SYNTAX Counter64
       MAX-ACCESS read-only
       STATUS current
       DESCRIPTION
            "Indicates the statistics of source downstream bytes of the service flow.Only connection-oriented
             flow supports this leaf, others return 0xff"
       ::= { hwFlowFluxStatisticEntry 18 }

   hwFlowFluxSourceDownPackets OBJECT-TYPE
       SYNTAX Counter64
       MAX-ACCESS read-only
       STATUS current
       DESCRIPTION
            "Indicates the statistics of source downstream packets of the service flow.Only connection-oriented
             flow supports this leaf, others return 0xff"
       ::= { hwFlowFluxStatisticEntry 19 }

   hwFlowFluxSourceDownDiscardPackets OBJECT-TYPE
       SYNTAX Counter64
       MAX-ACCESS read-only
       STATUS current
       DESCRIPTION
            "Indicates the statistics of source downstream discarded packets of the service flow.Only
            connection-oriented flow supports this leaf, others return 0xff"
       ::= { hwFlowFluxStatisticEntry 20 }

   hwFlowFluxDestinationUpBytes OBJECT-TYPE
       SYNTAX Counter64
       MAX-ACCESS read-only
       STATUS current
       DESCRIPTION
            "Indicates the statistics of destination upstream bytes of the service flow.Only connection-oriented
             flow supports this leaf, others return 0xff"
       ::= { hwFlowFluxStatisticEntry 21 }

   hwFlowFluxDestinationUpPackets OBJECT-TYPE
       SYNTAX Counter64
       MAX-ACCESS read-only
       STATUS current
       DESCRIPTION
            "Indicates the statistics of destination upstream packets of the service flow.Only connection-oriented
             flow supports this leaf, others return 0xff"
       ::= { hwFlowFluxStatisticEntry 22 }

   hwFlowFluxDestinationUpDiscardPackets OBJECT-TYPE
       SYNTAX Counter64
       MAX-ACCESS read-only
       STATUS current
       DESCRIPTION
            "Indicates the statistics of destination upstream discarded packets of the service flow.Only
            connection-oriented flow supports this leaf, others return 0xff"
       ::= { hwFlowFluxStatisticEntry 23 }

   hwFlowFluxDestinationDownBytes OBJECT-TYPE
       SYNTAX Counter64
       MAX-ACCESS read-only
       STATUS current
       DESCRIPTION
            "Indicates the statistics of destination downstream bytes of the service flow.Only connection-oriented
             flow supports this leaf, others return 0xff"
       ::= { hwFlowFluxStatisticEntry 24 }

   hwFlowFluxDestinationDownPackets OBJECT-TYPE
       SYNTAX Counter64
       MAX-ACCESS read-only
       STATUS current
       DESCRIPTION
            "Indicates the statistics of destination downstream packets of the service flow.Only connection-oriented
             flow supports this leaf, others return 0xff"
       ::= { hwFlowFluxStatisticEntry 25 }

   hwFlowFluxDestinationDownDiscardPackets OBJECT-TYPE
       SYNTAX Counter64
       MAX-ACCESS read-only
       STATUS current
       DESCRIPTION
            "Indicates the statistics of destination downstream discarded packets of the service flow.Only
            connection-oriented flow supports this leaf, others return 0xff"
       ::= { hwFlowFluxStatisticEntry 26 }


-- hwFlowBindChannelTable
   hwFlowBindChannelTable OBJECT-TYPE
       SYNTAX SEQUENCE OF HwFlowBindChannelEntry
       MAX-ACCESS not-accessible
       STATUS current
       DESCRIPTION
           "Indicates the table that contains information about the binding relationship between the service
            flow and the latency channel.
            The index of this table is hwFlowID.
           "
       ::= { hwExtSrvFlow 4 }

   hwFlowBindChannelEntry OBJECT-TYPE
       SYNTAX HwFlowBindChannelEntry
       MAX-ACCESS not-accessible
       STATUS current
       DESCRIPTION
           "Indicates the table that contains information about the binding relationship between the service
            flow and the latency channel.
            The index of this entry is hwFlowID.
           "
       INDEX { hwFlowID  }
       ::= { hwFlowBindChannelTable 1 }

   HwFlowBindChannelEntry ::=
       SEQUENCE {
         hwFlowLatencyChannel
           Integer32
        }

   hwFlowLatencyChannel OBJECT-TYPE
       SYNTAX Integer32 (1..2)
       MAX-ACCESS read-write
       STATUS current
       DESCRIPTION
           "Indicates the VDSL2 latency channel number.
            For QoS purpose, the VDSL2 line may support dual-latency channel,
            and the number may be 1 or 2.
            The default latency channel number bound to the service flow is 1.
           "
       DEFVAL { 1 }
       ::= { hwFlowBindChannelEntry 1 }

-- hwFlowIndexQueryTable
   hwFlowIndexQueryTable OBJECT-TYPE
       SYNTAX SEQUENCE OF HwFlowIndexQueryEntry
       MAX-ACCESS not-accessible
       STATUS current
       DESCRIPTION
           "Indicates the table that contains service flow index query information. It is used to query the
            service flow index according to the port or logical port and traffic classification information.
            The indexes of this table are ifIndex, hwFlowBridgePortType, hwFlowPortExtPara1, hwFlowPortExtPara2,
            hwFlowPortExtPara3, hwFlowMulitiServiceType and hwFlowMulitiServicePara.
           "
       ::= { hwExtSrvFlow 5 }

   hwFlowIndexQueryEntry OBJECT-TYPE
       SYNTAX HwFlowIndexQueryEntry
       MAX-ACCESS not-accessible
       STATUS current
       DESCRIPTION
           "Indicates the table that contains service flow index query information. It is used to query the
            service flow index according to the port or logical port and traffic classification information.
            The indexes of this entry are ifIndex, hwFlowBridgePortType, hwFlowPortExtPara1, hwFlowPortExtPara2,
            hwFlowPortExtPara3, hwFlowMulitiServiceType and hwFlowMulitiServicePara.
           "
       INDEX { ifIndex,
               hwFlowBridgePortType,hwFlowPortExtPara1,hwFlowPortExtPara2, hwFlowPortExtPara3,
               hwFlowMulitiServiceType,hwFlowMulitiServicePara
              }
       ::= { hwFlowIndexQueryTable 1 }

   HwFlowIndexQueryEntry ::=
       SEQUENCE {
         hwFlowBridgePortType
           INTEGER,
         hwFlowPortExtPara1
           Integer32,
         hwFlowPortExtPara2
           Integer32,
         hwFlowPortExtPara3
           Integer32,
         hwFlowMulitiServiceType
           INTEGER,
         hwFlowMulitiServicePara
           Integer32,
         hwFlowIndex
           Integer32
        }

   hwFlowBridgePortType OBJECT-TYPE
       SYNTAX INTEGER
           {
           vcPort(1),
           ethernetPtm(2),
           gemPort(3),
           ontId(4)
           }
       MAX-ACCESS not-accessible
       STATUS current
       DESCRIPTION
           "Indicates the type of the physical or logical bridge port.
            Options:
            1. vcPort(1)      -indicates a VC port to be a bridge port, capable for ATM mode access.
            2. ethernetPtm(2) -indicates an Ethernet port or PTM mode xDSL port to be a bridge port.
            3. gemPort(3)     -indicates a GPON GEM port to be a bridge port.
            4. ontId(4)       -indicates a GPON or EPON ONT to be a bridge port.
           "
       ::= { hwFlowIndexQueryEntry 1 }

   hwFlowPortExtPara1 OBJECT-TYPE
       SYNTAX Integer32
       MAX-ACCESS not-accessible
       STATUS current
       DESCRIPTION
           "The meaning is variable with the value of hwFlowBridgePortType:
            If the value of hwFlowBridgePortType is set to vcPort(1): this leaf indicates the VPI.
            If the value of hwExtSrvFlowParaType is set to ethernetPtm(2): this leaf is invalid.
            If the value of hwExtSrvFlowParaType is set to gemPort(3), this leaf indicates the
            ONT ID for the GPON profile mode and GEM port ID for the GPON distributed mode.
            If the value of hwExtSrvFlowParaType is set to gpon(4) or epon(6), this leaf indicates the ONT ID
            of the GPON or EPON.
           "
       ::= { hwFlowIndexQueryEntry 2 }

   hwFlowPortExtPara2 OBJECT-TYPE
       SYNTAX Integer32
       MAX-ACCESS not-accessible
       STATUS current
       DESCRIPTION
           "The meaning is variable with the value of hwFlowBridgePortType:
            If the value of hwFlowBridgePortType is set to vcPort(1), this leaf indicates the VCI.
            If the value of hwExtSrvFlowParaType is set to ethernetPtm(2), this leaf is invalid.
            If the value of hwExtSrvFlowParaType is set to gemPort(3), this leaf indicates the
            GEM port index for the GPON profile mode and invalid for the GPON distributed mode.
            If the value of hwExtSrvFlowParaType is set to gpon(4) or epon(6), this leaf is invalid.
           "
       ::= { hwFlowIndexQueryEntry 3 }

   hwFlowPortExtPara3 OBJECT-TYPE
       SYNTAX Integer32
       MAX-ACCESS not-accessible
       STATUS current
       DESCRIPTION
           "Indicates the reserved parameter to describe a bridge port.
           "
       ::= { hwFlowIndexQueryEntry 4 }

   hwFlowMulitiServiceType OBJECT-TYPE
       SYNTAX INTEGER
                    {
                     byUserVlan(1),
                     byEncap(2),
                     by8021p(3),
                     byVlanEncap(4),
                     byDoubleVlan(5),
                     by8021pList(6),
                     singleService(255)
                    }
       MAX-ACCESS not-accessible
       STATUS current
       DESCRIPTION
           "This leaf is the same as hwExtSrvFlowMultiServiceType,
            which indicates the traffic classification criteria on the port or logical port.
            For details, see the description of hwExtSrvFlowMultiServiceType.
            Options:
            1. byUserVlan(1)      -the service type is byUserVlan
            2. byEncap(2)         -the service type is byEncap
            3. by8021p(3)         -the service type is by8021p
            4. byVlanEncap(4)     -the service type is byVlanEncap
            5. byDoubleVlan(5)    -the service type is byDoubleVlan
            6. by8021pList(6)     -the service type is by8021pList
            7. singleService(255) -the service type is singleServices
           "
       ::= { hwFlowIndexQueryEntry 5 }

   hwFlowMulitiServicePara OBJECT-TYPE
       SYNTAX Integer32
       MAX-ACCESS not-accessible
       STATUS current
       DESCRIPTION
           "This leaf is the same as hwExtSrvFlowMultiServiceUserPara,
            and the meaning is variable with the value of hwFlowMulitiServiceType.
            For details, see the description of hwExtSrvFlowMultiServiceUserPara.
           "
       ::= { hwFlowIndexQueryEntry 6 }

   hwFlowIndex OBJECT-TYPE
       SYNTAX Integer32
       MAX-ACCESS read-only
       STATUS current
       DESCRIPTION
           "Indicates the service flow index, a unique value to identify a service flow.
            In this table, giving the information about the port and traffic classification parameters,
            the flow index can be obtained through hwFlowIndex.
           "
       ::= { hwFlowIndexQueryEntry 7 }

-- hwSrvFlowBundleTable
   hwSrvFlowBundleTable OBJECT-TYPE
       SYNTAX SEQUENCE OF HwSrvFlowBundleEntry
       MAX-ACCESS not-accessible
       STATUS current
       DESCRIPTION
           "Indicates the table that contains service flow bundle configuration information. It is used to
            create, delete and query service flow bundles.
            The index of this table is hwSrvFlowBundleIndex.
           "
       ::= { hwExtSrvFlow 6 }

   hwSrvFlowBundleEntry OBJECT-TYPE
       SYNTAX HwSrvFlowBundleEntry
       MAX-ACCESS not-accessible
       STATUS current
       DESCRIPTION
           "Indicates the table that contains service flow bundle configuration information. It is used to
            create, delete and query service flow bundles.
            The index of this entry is hwSrvFlowBundleIndex.
           "
       INDEX { hwSrvFlowBundleIndex }
       ::= { hwSrvFlowBundleTable 1 }

   HwSrvFlowBundleEntry ::=
       SEQUENCE {
           hwSrvFlowBundleIndex
               Integer32,
           hwSrvFlowBundleType
               INTEGER,
           hwSrvFlowBundleRowStatus
               RowStatus
        }

   hwSrvFlowBundleIndex OBJECT-TYPE
       SYNTAX Integer32
       MAX-ACCESS not-accessible
       STATUS current
       DESCRIPTION
           "Indicates the service flow bundle index,
            a unique value to identify a service flow bundle.If -1 is specified,
            an index will be allocated automatically for the service flow bundle.
           "
       ::= { hwSrvFlowBundleEntry 1 }

   hwSrvFlowBundleType OBJECT-TYPE
       SYNTAX INTEGER { byPbit(1) }
       MAX-ACCESS read-write
       STATUS current
       DESCRIPTION
           "Indicates the type of a service flow bundle.
            Currently, only one type is supported, that is, byPbit(1),
            which indicates that the service flow bundle is for L3 access,
            and that the service flows are classified for 802.1p(P-Bits) CoS purpose.
            Options:
            1. byPbit(1) -indicates that the service flow bundle is for L3 access,
                          and that the service flows are classified for 802.1p(P-Bits) CoS purpose.
           "
       ::= { hwSrvFlowBundleEntry 2 }

   hwSrvFlowBundleRowStatus OBJECT-TYPE
       SYNTAX RowStatus
       MAX-ACCESS read-create
       STATUS current
       DESCRIPTION
           "Indicates the row status. To create a service flow bundle,
            set hwSrvFlowBundleRowStatus to createAndGo(4).
            To delete a service flow bundle, set hwSrvFlowBundleRowStatus to destroy(6).
            Options:
            1. active(1)      -indicates the query operation
            2. createAndGo(4) -indicates creating a flow bundle
            3. destroy(6)     -indicates deleting a flow bundle
           "
       ::= { hwSrvFlowBundleEntry 3 }

-- hwSrvFlowBundleQueryTable
   hwSrvFlowBundleQueryTable OBJECT-TYPE
       SYNTAX SEQUENCE OF HwSrvFlowBundleQueryEntry
       MAX-ACCESS not-accessible
       STATUS current
       DESCRIPTION
           "Indicates the table that contains service flow bundle query information. It is
            used to query service flow bundles.
            The indexes of this table are hwSrvFlowBundleQueryIndex and hwSrvFlowIndex.
           "
       ::= { hwExtSrvFlow 7 }

   hwSrvFlowBundleQueryEntry OBJECT-TYPE
       SYNTAX HwSrvFlowBundleQueryEntry
       MAX-ACCESS not-accessible
       STATUS current
       DESCRIPTION
           "Indicates the table that contains service flow bundle query information. It is
            used to query service flow bundles.
            The indexes of this entry are hwSrvFlowBundleQueryIndex and hwSrvFlowIndex.
           "
       INDEX { hwSrvFlowBundleQueryIndex, hwSrvFlowIndex }
       ::= { hwSrvFlowBundleQueryTable 1 }

   HwSrvFlowBundleQueryEntry ::=
       SEQUENCE {
           hwSrvFlowBundleQueryIndex
               Integer32,
           hwSrvFlowIndex
               Integer32,
           hwSrvFlowBundleMemberSortPara
               Integer32
        }

   hwSrvFlowBundleQueryIndex OBJECT-TYPE
       SYNTAX Integer32
       MAX-ACCESS not-accessible
       STATUS current
       DESCRIPTION
           "Indicates the service flow bundle index, a unique value to identify a service flow bundle."
       ::= { hwSrvFlowBundleQueryEntry 1 }

   hwSrvFlowIndex OBJECT-TYPE
       SYNTAX Integer32
       MAX-ACCESS not-accessible
       STATUS current
       DESCRIPTION
           "Indicates the service flow index, a unique value to identify a service flow."
       ::= { hwSrvFlowBundleQueryEntry 2 }

   hwSrvFlowBundleMemberSortPara OBJECT-TYPE
       SYNTAX Integer32
       MAX-ACCESS read-only
       STATUS current
       DESCRIPTION
           "Indicates the corresponding key value of a service flow in service flow bundle.
            Currently, the service flow bundle type must be byPbit(1), and hwSrvFlowBundleMemberSortPara indicates the CoS value.
            If the high 16 bits of the value is 0,it is in cos mode.the low 8 bits of it represents the value of cos.
            If the high 16 bits of the value is 1,it is in cos-list mode.the low 8 bits of it represents the bitmap of cos-list.
           "
       ::= { hwSrvFlowBundleQueryEntry 3 }

-- hwFlowIndexQueryForPPPoESmltTable
   hwFlowIndexQueryForPPPoESmltTable OBJECT-TYPE
       SYNTAX SEQUENCE OF HwFlowIndexQueryForPPPoESmltEntry
       MAX-ACCESS not-accessible
       STATUS current
       DESCRIPTION
           "Indicates the service flow index query information for PPPoE simulation. It is used to query the
            service flow index according to the ifIndex and ONU ID. It supports the xDSL ports and the xPON ports only.
            The indexes of this table are ifIndex and hwFlowIndexQueryForPPPoESmltOnuId.
           "
       ::= { hwExtSrvFlow 8 }

   hwFlowIndexQueryForPPPoESmltEntry OBJECT-TYPE
       SYNTAX HwFlowIndexQueryForPPPoESmltEntry
       MAX-ACCESS not-accessible
       STATUS current
       DESCRIPTION
           "Indicates the service flow index query information for PPPoE simulation. It is used to query the
            service flow index according to the ifIndex and ONU ID. It supports the xDSL ports and the xPON ports only.
            The indexes of this entry are ifIndex and hwFlowIndexQueryForPPPoESmltOnuId.
           "
       INDEX { ifIndex,
               hwFlowIndexQueryForPPPoESmltOnuId }
       ::= { hwFlowIndexQueryForPPPoESmltTable 1 }

   HwFlowIndexQueryForPPPoESmltEntry::=
       SEQUENCE {
           hwFlowIndexQueryForPPPoESmltOnuId
               Integer32,
           hwFlowIndexList
               OCTET STRING
        }

   hwFlowIndexQueryForPPPoESmltOnuId OBJECT-TYPE
       SYNTAX Integer32 (-1 | 0..255)
       MAX-ACCESS not-accessible
       STATUS current
       DESCRIPTION
           "Indicates the ONU ID of the ONU in the PPPoE simulation scenario. This leaf is valid when the ifIndex indicates that the port
            type is xDSL. This leaf should be set to -1 when the service flow is queried according to ifindex only.
           "
       ::= { hwFlowIndexQueryForPPPoESmltEntry 1 }

   hwFlowIndexList OBJECT-TYPE
       SYNTAX OCTET STRING (SIZE(0..1028))
       MAX-ACCESS read-only
       STATUS current
       DESCRIPTION
           "Indicates the list of service flow indexes, each index in the list identifies a service flow uniquely. In this table, if given
            the ifIndex and ONU ID, the active PPPoE service flow indexes created on the corresponding port can be obtained through
            hwFlowIndexList according to the following rules.
            Firstly, the maximal number of service flow index in the list is 256. If the service flow number on the corresponding port is
            more than 256, only the first 256 service flow will be returned.
            Secondly, if there is active PPPoE service flow on the corresponding port, the active PPPoE service flow will be returned.
            Otherwise, the active service flow will be returned.
           "
       ::= { hwFlowIndexQueryForPPPoESmltEntry 2 }

   hwSrvPortExtStatTable OBJECT-TYPE
       SYNTAX SEQUENCE OF HwSrvPortExtStatEntry
       MAX-ACCESS not-accessible
       STATUS current
       DESCRIPTION
            "Used for extended packet statistics collection based on service flows.
            Indicates the table that contains service flow configuration information. It is used to create, modify,
            delete and query service flows.
            The index of this table is hwExtSrvFlowIndex.
           "
       ::= { hwExtSrvFlow 9 }

   hwSrvPortExtStatEntry OBJECT-TYPE
       SYNTAX HwSrvPortExtStatEntry
       MAX-ACCESS not-accessible
       STATUS current
       DESCRIPTION
           "Used for extended packet statistics collection based on service flows.
            Indicates the table that contains service flow configuration information. It is used to create, modify,
            delete and query service flows.
            The index of this entry is hwExtSrvFlowIndex.
           "
       INDEX { hwExtSrvFlowIndex }
       ::= { hwSrvPortExtStatTable 1 }

   HwSrvPortExtStatEntry ::=
       SEQUENCE {
           hwSrvPortExtStatRowStatus
               RowStatus,
           hwSrvPortExtStatCountClear
               INTEGER,
           hwSrvPortExtStatTimeoutDuration
               Integer32,
           hwSrvPortExtStatRunningStatus
               INTEGER,
           hwSrvPortExtStatUsBytes
               Counter64,
           hwSrvPortExtStatUsPackets
               Counter64,
           hwSrvPortExtStatUsDiscardPackets
               Counter64,
           hwSrvPortExtStatDsBytes
               Counter64,
           hwSrvPortExtStatDsPackets
               Counter64,
           hwSrvPortExtStatDsDiscardPackets
               Counter64,
           hwSrvPortExtStatUsPacketsForPriority0
               Counter64,
           hwSrvPortExtStatUsPacketsForPriority1
               Counter64,
           hwSrvPortExtStatUsPacketsForPriority2
               Counter64,
           hwSrvPortExtStatUsPacketsForPriority3
               Counter64,
           hwSrvPortExtStatUsPacketsForPriority4
               Counter64,
           hwSrvPortExtStatUsPacketsForPriority5
               Counter64,
           hwSrvPortExtStatUsPacketsForPriority6
               Counter64,
           hwSrvPortExtStatUsPacketsForPriority7
               Counter64,
           hwSrvPortExtStatUsDiscardPacketsForPriority0
               Counter64,
           hwSrvPortExtStatUsDiscardPacketsForPriority1
               Counter64,
           hwSrvPortExtStatUsDiscardPacketsForPriority2
               Counter64,
           hwSrvPortExtStatUsDiscardPacketsForPriority3
               Counter64,
           hwSrvPortExtStatUsDiscardPacketsForPriority4
               Counter64,
           hwSrvPortExtStatUsDiscardPacketsForPriority5
               Counter64,
           hwSrvPortExtStatUsDiscardPacketsForPriority6
               Counter64,
           hwSrvPortExtStatUsDiscardPacketsForPriority7
               Counter64,
           hwSrvPortExtStatDsPacketsForPriority0
               Counter64,
           hwSrvPortExtStatDsPacketsForPriority1
               Counter64,
           hwSrvPortExtStatDsPacketsForPriority2
               Counter64,
           hwSrvPortExtStatDsPacketsForPriority3
               Counter64,
           hwSrvPortExtStatDsPacketsForPriority4
               Counter64,
           hwSrvPortExtStatDsPacketsForPriority5
               Counter64,
           hwSrvPortExtStatDsPacketsForPriority6
               Counter64,
           hwSrvPortExtStatDsPacketsForPriority7
               Counter64,
           hwSrvPortExtStatUnknownPriorityDownstreamPackets
               Counter64,
           hwSrvPortExtStatDsDiscardPacketsForPriority0
               Counter64,
           hwSrvPortExtStatDsDiscardPacketsForPriority1
               Counter64,
           hwSrvPortExtStatDsDiscardPacketsForPriority2
               Counter64,
           hwSrvPortExtStatDsDiscardPacketsForPriority3
               Counter64,
           hwSrvPortExtStatDsDiscardPacketsForPriority4
               Counter64,
           hwSrvPortExtStatDsDiscardPacketsForPriority5
               Counter64,
           hwSrvPortExtStatDsDiscardPacketsForPriority6
               Counter64,
           hwSrvPortExtStatDsDiscardPacketsForPriority7
               Counter64,
           hwSrvPortExtStatUnknownPriorityDownstreamDiscardPackets
               Counter64,
           hwSrvPortExtStatDsDiscardPacketsForUnicast
               Counter64,
           hwSrvPortExtStatDsDiscardPacketsForUnknownUnicast
               Counter64,
           hwSrvPortExtStatDsDiscardPacketsForMulticast
               Counter64,
           hwSrvPortExtStatDsDiscardPacketsForUnknownMulticast
               Counter64,
           hwSrvPortExtStatUsDiscardedPacketsByVlanCheck
               Counter64,
           hwSrvPortExtStatUsDiscardedPacketsByExpectedPppoeEncapsulation
               Counter64,
           hwSrvPortExtStatUsDiscardedPacketsByExpectedIpoeEncapsulation
               Counter64,
           hwSrvPortExtStatUsDiscardedPacketsByExpectedPppoaEncapsulation
               Counter64,
           hwSrvPortExtStatUsDiscardedPacketsByExpectedIpoaEncapsulation
               Counter64,
           hwSrvPortExtStatUsDiscardedPacketsByIPSpoofing
               Counter64,
           hwSrvPortExtStatUsDiscardedPacketsBySourceMacAddressFilter
               Counter64,
           hwSrvPortExtStatUsDiscardedPacketsByDestinationMacAddressFilter
               Counter64,
           hwSrvPortExtStatUsDiscardedPacketsByHashConflict
               Counter64,
           hwSrvPortExtStatUsDiscardedPacketsByOverMacLimitation
               Counter64,
           hwSrvPortExtStatUsDiscardedPacketsByVmacCheck
               Counter64,
           hwSrvPortExtStatUsDiscardedPacketsByCar
               Counter64,
           hwSrvPortExtStatUsdiscardedPacketsMacSpoofing
               Counter64,
           hwSrvPortExtStatDsDiscardedPacketsByUnknownUnicastSuppression
               Counter64,
           hwSrvPortExtStatDsDiscardedPacketsByUnknownBroadcastSuppression
               Counter64,
           hwSrvPortExtStatDsDiscardedPacketsByUnknownMulticastSuppression
               Counter64,
           hwSrvPortExtStatDsDiscardedPacketsByVLANCheck
               Counter64,
           hwSrvPortExtStatDsDiscardedPacketsByExpectedPppoeEncapsulation
               Counter64,
           hwSrvPortExtStatDsDiscardedPacketsByExpectedIpoeEncapsulation
               Counter64,
           hwSrvPortExtStatDsDiscardedPacketsByUnexpectedPppoaEncapsulation
               Counter64,
           hwSrvPortExtStatDsDiscardedPacketsByEncapsulationLengthError
               Counter64,
           hwSrvPortExtStatDsDiscardedPacketsByVmacCheck
               Counter64,
           hwSrvPortExtStatDsDiscardedPacketsByCar
               Counter64,
           hwSrvPortExtStatDsDiscardedPacketsByQueue
               Counter64,
           hwSrvPortExtStatUsDiscardedPacketsByL3Forward
               Counter64,
           hwSrvPortExtStatDsDiscardedPacketsByL3Forward
               Counter64
             }

   hwSrvPortExtStatRowStatus OBJECT-TYPE
       SYNTAX RowStatus
       MAX-ACCESS read-create
       STATUS current
       DESCRIPTION
           "Starts or stops extended statistics collection of a specified service flow.
           Options:
           1. active(1)            - when this leaf is queried, the value is fixed to active(1)
           2. createAndGo(4)     - deliver a extend traffic statistic to a specified flow
           3. destroy(6)         - delete the extend traffic statistic to the specified flow
           "
       DEFVAL { active }
       ::= { hwSrvPortExtStatEntry 1 }

   hwSrvPortExtStatCountClear OBJECT-TYPE
       SYNTAX INTEGER
       {
           cleared(1),
           nouse(2)
       }
       MAX-ACCESS   read-write
       STATUS       current
       DESCRIPTION
           "Clears extended statistics of a specified service flow.
           This node does not need to be specified during the start of extended statistics
           collection for a service flow.
           Options:
           1.cleared(1) - reset the extend traffic statistic to the specified flow
           2.nouse(2)   - in the query operation, this leaf is fixed to nouse(2)
           "
       ::= { hwSrvPortExtStatEntry 2 }

   hwSrvPortExtStatTimeoutDuration OBJECT-TYPE
       SYNTAX Integer32(1..1440)
       MAX-ACCESS read-write
       STATUS current
       DESCRIPTION
           "For a service flow that supports long-duration (exceeding 1440 minutes) extended statistics collection,
           this node is optional during the start of statistics collection.
           However, when a service flow does not support long-duration extended statistics collection,
           an error will be returned if this node is not specified."
       ::= { hwSrvPortExtStatEntry 3 }

   hwSrvPortExtStatRunningStatus   OBJECT-TYPE
       SYNTAX   INTEGER
       {
           running(1),
           timeout(2)
       }
       MAX-ACCESS   read-only
       STATUS       current
       DESCRIPTION
           "Indicates the current status of extended statistics collection of a specified service flow.
           This node has two enumerated values: running and timeout.
           Options:
           1.running(1) -indicate the extend traffic statistic to the specified flow is running(1)
           2.timeout(2) -indicate the extend traffic statistic to the specified flow is time out
           "
       ::= { hwSrvPortExtStatEntry 4 }

   hwSrvPortExtStatUsBytes OBJECT-TYPE
       SYNTAX Counter64
       MAX-ACCESS read-only
       STATUS current
       DESCRIPTION
           "Indicates the number of upstream bytes of a specified service flow."
       ::= { hwSrvPortExtStatEntry 5 }

   hwSrvPortExtStatUsPackets OBJECT-TYPE
       SYNTAX Counter64
       MAX-ACCESS read-only
       STATUS current
       DESCRIPTION
           "Indicates the number of upstream packets of a specified service flow."
       ::= { hwSrvPortExtStatEntry 6 }

   hwSrvPortExtStatUsDiscardPackets OBJECT-TYPE
       SYNTAX Counter64
       MAX-ACCESS read-only
       STATUS current
       DESCRIPTION
           "Indicates the number of discarded upstream packets of a specified service flow."
       ::= { hwSrvPortExtStatEntry 7 }

   hwSrvPortExtStatDsBytes OBJECT-TYPE
       SYNTAX Counter64
       MAX-ACCESS read-only
       STATUS current
       DESCRIPTION
           "Indicates the number of downstream bytes of a specified service flow."
       ::= { hwSrvPortExtStatEntry 8 }

   hwSrvPortExtStatDsPackets OBJECT-TYPE
       SYNTAX Counter64
       MAX-ACCESS read-only
       STATUS current
       DESCRIPTION
           "Indicates the number of downstream packets of a specified service flow."
       ::= { hwSrvPortExtStatEntry 9 }

   hwSrvPortExtStatDsDiscardPackets OBJECT-TYPE
       SYNTAX Counter64
       MAX-ACCESS read-only
       STATUS current
       DESCRIPTION
           "Indicates the number of discarded downstream packets of a specified service flow."
       ::= { hwSrvPortExtStatEntry 10 }

   hwSrvPortExtStatUsPacketsForPriority0 OBJECT-TYPE
       SYNTAX Counter64
       MAX-ACCESS read-only
       STATUS current
       DESCRIPTION
           "Indicates the number of upstream packets with flow priority 0."
       ::= { hwSrvPortExtStatEntry 11 }

   hwSrvPortExtStatUsPacketsForPriority1 OBJECT-TYPE
       SYNTAX Counter64
       MAX-ACCESS read-only
       STATUS current
       DESCRIPTION
           "Indicates the number of upstream packets with flow priority 1."
       ::= { hwSrvPortExtStatEntry 12 }

   hwSrvPortExtStatUsPacketsForPriority2 OBJECT-TYPE
       SYNTAX Counter64
       MAX-ACCESS read-only
       STATUS current
       DESCRIPTION
           "Indicates the number of upstream packets with flow priority 2."
       ::= { hwSrvPortExtStatEntry 13 }

   hwSrvPortExtStatUsPacketsForPriority3 OBJECT-TYPE
       SYNTAX Counter64
       MAX-ACCESS read-only
       STATUS current
       DESCRIPTION
           "Indicates the number of upstream packets with flow priority 3."
       ::= { hwSrvPortExtStatEntry 14 }

   hwSrvPortExtStatUsPacketsForPriority4 OBJECT-TYPE
       SYNTAX Counter64
       MAX-ACCESS read-only
       STATUS current
       DESCRIPTION
           "Indicates the number of upstream packets with flow priority 4."
       ::= { hwSrvPortExtStatEntry 15 }

   hwSrvPortExtStatUsPacketsForPriority5 OBJECT-TYPE
       SYNTAX Counter64
       MAX-ACCESS read-only
       STATUS current
       DESCRIPTION
           "Indicates the number of upstream packets with flow priority 5."
       ::= { hwSrvPortExtStatEntry 16 }

   hwSrvPortExtStatUsPacketsForPriority6 OBJECT-TYPE
       SYNTAX Counter64
       MAX-ACCESS read-only
       STATUS current
       DESCRIPTION
           "Indicates the number of upstream packets with flow priority 6."
       ::= { hwSrvPortExtStatEntry 17 }

   hwSrvPortExtStatUsPacketsForPriority7 OBJECT-TYPE
       SYNTAX Counter64
       MAX-ACCESS read-only
       STATUS current
       DESCRIPTION
           "Indicates the number of upstream packets with flow priority 7."
       ::= { hwSrvPortExtStatEntry 18 }

   hwSrvPortExtStatUsDiscardPacketsForPriority0 OBJECT-TYPE
       SYNTAX Counter64
       MAX-ACCESS read-only
       STATUS current
       DESCRIPTION
           "Indicates the number of discarded upstream packets with flow priority 0."
       ::= { hwSrvPortExtStatEntry 19 }

   hwSrvPortExtStatUsDiscardPacketsForPriority1 OBJECT-TYPE
       SYNTAX Counter64
       MAX-ACCESS read-only
       STATUS current
       DESCRIPTION
           "Indicates the number of discarded upstream packets with flow priority 1."
       ::= { hwSrvPortExtStatEntry 20 }

   hwSrvPortExtStatUsDiscardPacketsForPriority2 OBJECT-TYPE
       SYNTAX Counter64
       MAX-ACCESS read-only
       STATUS current
       DESCRIPTION
           "Indicates the number of discarded upstream packets with flow priority 2."
       ::= { hwSrvPortExtStatEntry 21 }

   hwSrvPortExtStatUsDiscardPacketsForPriority3 OBJECT-TYPE
       SYNTAX Counter64
       MAX-ACCESS read-only
       STATUS current
       DESCRIPTION
           "Indicates the number of discarded upstream packets with flow priority 3."
       ::= { hwSrvPortExtStatEntry 22 }

   hwSrvPortExtStatUsDiscardPacketsForPriority4 OBJECT-TYPE
       SYNTAX Counter64
       MAX-ACCESS read-only
       STATUS current
       DESCRIPTION
           "Indicates the number of discarded upstream packets with flow priority 4."
       ::= { hwSrvPortExtStatEntry 23 }

   hwSrvPortExtStatUsDiscardPacketsForPriority5 OBJECT-TYPE
       SYNTAX Counter64
       MAX-ACCESS read-only
       STATUS current
       DESCRIPTION
           "Indicates the number of discarded upstream packets with flow priority 5."
       ::= { hwSrvPortExtStatEntry 24 }

   hwSrvPortExtStatUsDiscardPacketsForPriority6 OBJECT-TYPE
       SYNTAX Counter64
       MAX-ACCESS read-only
       STATUS current
       DESCRIPTION
           "Indicates the number of discarded upstream packets with flow priority 6."
       ::= { hwSrvPortExtStatEntry 25 }

   hwSrvPortExtStatUsDiscardPacketsForPriority7 OBJECT-TYPE
       SYNTAX Counter64
       MAX-ACCESS read-only
       STATUS current
       DESCRIPTION
           "Indicates the number of discarded upstream packets with flow priority 7."
       ::= { hwSrvPortExtStatEntry 26 }

   hwSrvPortExtStatDsPacketsForPriority0 OBJECT-TYPE
       SYNTAX Counter64
       MAX-ACCESS read-only
       STATUS current
       DESCRIPTION
           "Indicates the number of downstream packets with flow priority 0."
       ::= { hwSrvPortExtStatEntry 27 }

   hwSrvPortExtStatDsPacketsForPriority1 OBJECT-TYPE
       SYNTAX Counter64
       MAX-ACCESS read-only
       STATUS current
       DESCRIPTION
           "Indicates the number of downstream packets with flow priority 1."
       ::= { hwSrvPortExtStatEntry 28 }

   hwSrvPortExtStatDsPacketsForPriority2 OBJECT-TYPE
       SYNTAX Counter64
       MAX-ACCESS read-only
       STATUS current
       DESCRIPTION
           "Indicates the number of downstream packets with flow priority 2."
       ::= { hwSrvPortExtStatEntry 29 }

   hwSrvPortExtStatDsPacketsForPriority3 OBJECT-TYPE
       SYNTAX Counter64
       MAX-ACCESS read-only
       STATUS current
       DESCRIPTION
           "Indicates the number of downstream packets with flow priority 3."
       ::= { hwSrvPortExtStatEntry 30 }

   hwSrvPortExtStatDsPacketsForPriority4 OBJECT-TYPE
       SYNTAX Counter64
       MAX-ACCESS read-only
       STATUS current
       DESCRIPTION
           "Indicates the number of downstream packets with flow priority 4."
       ::= { hwSrvPortExtStatEntry 31 }

   hwSrvPortExtStatDsPacketsForPriority5 OBJECT-TYPE
       SYNTAX Counter64
       MAX-ACCESS read-only
       STATUS current
       DESCRIPTION
           "Indicates the number of downstream packets with flow priority 5."
       ::= { hwSrvPortExtStatEntry 32 }

   hwSrvPortExtStatDsPacketsForPriority6 OBJECT-TYPE
       SYNTAX Counter64
       MAX-ACCESS read-only
       STATUS current
       DESCRIPTION
           "Indicates the number of downstream packets with flow priority 6."
       ::= { hwSrvPortExtStatEntry 33 }

   hwSrvPortExtStatDsPacketsForPriority7 OBJECT-TYPE
       SYNTAX Counter64
       MAX-ACCESS read-only
       STATUS current
       DESCRIPTION
           "Indicates the number of downstream packets with flow priority 7."
       ::= { hwSrvPortExtStatEntry 34 }

   hwSrvPortExtStatUnknownPriorityDownstreamPackets OBJECT-TYPE
       SYNTAX Counter64
       MAX-ACCESS read-only
       STATUS current
       DESCRIPTION
           "Indicates the number of downstream packets with an unknown flow priority."
       ::= { hwSrvPortExtStatEntry 35 }

   hwSrvPortExtStatDsDiscardPacketsForPriority0 OBJECT-TYPE
       SYNTAX Counter64
       MAX-ACCESS read-only
       STATUS current
       DESCRIPTION
           "Indicates the number of discarded downstream packets with flow priority 0."
       ::= { hwSrvPortExtStatEntry 36 }

   hwSrvPortExtStatDsDiscardPacketsForPriority1 OBJECT-TYPE
       SYNTAX Counter64
       MAX-ACCESS read-only
       STATUS current
       DESCRIPTION
           "Indicates the number of discarded downstream packets with flow priority 1."
       ::= { hwSrvPortExtStatEntry 37 }

   hwSrvPortExtStatDsDiscardPacketsForPriority2 OBJECT-TYPE
       SYNTAX Counter64
       MAX-ACCESS read-only
       STATUS current
       DESCRIPTION
           "Indicates the number of discarded downstream packets with flow priority 2."
       ::= { hwSrvPortExtStatEntry 38 }

   hwSrvPortExtStatDsDiscardPacketsForPriority3 OBJECT-TYPE
       SYNTAX Counter64
       MAX-ACCESS read-only
       STATUS current
       DESCRIPTION
           "Indicates the number of discarded downstream packets with flow priority 3."
       ::= { hwSrvPortExtStatEntry 39 }

   hwSrvPortExtStatDsDiscardPacketsForPriority4 OBJECT-TYPE
       SYNTAX Counter64
       MAX-ACCESS read-only
       STATUS current
       DESCRIPTION
           "Indicates the number of discarded downstream packets with flow priority 4."
       ::= { hwSrvPortExtStatEntry 40 }

   hwSrvPortExtStatDsDiscardPacketsForPriority5 OBJECT-TYPE
       SYNTAX Counter64
       MAX-ACCESS read-only
       STATUS current
       DESCRIPTION
           "Indicates the number of discarded downstream packets with flow priority 5."
       ::= { hwSrvPortExtStatEntry 41 }

   hwSrvPortExtStatDsDiscardPacketsForPriority6 OBJECT-TYPE
       SYNTAX Counter64
       MAX-ACCESS read-only
       STATUS current
       DESCRIPTION
           "Indicates the number of discarded downstream packets with flow priority 6."
       ::= { hwSrvPortExtStatEntry 42 }

   hwSrvPortExtStatDsDiscardPacketsForPriority7 OBJECT-TYPE
       SYNTAX Counter64
       MAX-ACCESS read-only
       STATUS current
       DESCRIPTION
           "Indicates the number of discarded downstream packets with flow priority 7."
       ::= { hwSrvPortExtStatEntry 43 }

   hwSrvPortExtStatUnknownPriorityDownstreamDiscardPackets OBJECT-TYPE
       SYNTAX Counter64
       MAX-ACCESS read-only
       STATUS current
       DESCRIPTION
           "Indicates the number of discarded downstream packets with an unknown flow priority."
       ::= { hwSrvPortExtStatEntry 44 }

   hwSrvPortExtStatDsDiscardPacketsForUnicast OBJECT-TYPE
       SYNTAX Counter64
       MAX-ACCESS read-only
       STATUS current
       DESCRIPTION
           "Indicates the number of known unicast packets discarded in the downstream direction."
       ::= { hwSrvPortExtStatEntry 45 }

   hwSrvPortExtStatDsDiscardPacketsForUnknownUnicast OBJECT-TYPE
       SYNTAX Counter64
       MAX-ACCESS read-only
       STATUS current
       DESCRIPTION
           "Indicates the number of unknown unicast packets discarded in the downstream direction."
       ::= { hwSrvPortExtStatEntry 46 }

   hwSrvPortExtStatDsDiscardPacketsForMulticast OBJECT-TYPE
       SYNTAX Counter64
       MAX-ACCESS read-only
       STATUS current
       DESCRIPTION
           "Indicates the number of known multicast packets discarded in the downstream direction."
       ::= { hwSrvPortExtStatEntry 47 }

   hwSrvPortExtStatDsDiscardPacketsForUnknownMulticast OBJECT-TYPE
       SYNTAX Counter64
       MAX-ACCESS read-only
       STATUS current
       DESCRIPTION
           "Indicates the number of unknown multicast packets discarded in the downstream direction."
       ::= { hwSrvPortExtStatEntry 48 }

   hwSrvPortExtStatUsDiscardedPacketsByVlanCheck OBJECT-TYPE
       SYNTAX Counter64
       MAX-ACCESS read-only
       STATUS current
       DESCRIPTION
           "Indicates the number of upstream packets discarded due to a VLAN check failure.
           Specifically, this node is used to collect the statistics of upstream packets
           that are discarded because their VLANs are different from the VLAN of the service flow."
       ::= { hwSrvPortExtStatEntry 49 }

   hwSrvPortExtStatUsDiscardedPacketsByExpectedPppoeEncapsulation OBJECT-TYPE
       SYNTAX Counter64
       MAX-ACCESS read-only
       STATUS current
       DESCRIPTION
           "Indicates the number of upstream packets discarded due to unexpected PPPoE encapsulation.
           Specifically, this node is used to collect the statistics of upstream packets
           that are discarded because they do not support the PPPoE protocol."
       ::= { hwSrvPortExtStatEntry 50 }

   hwSrvPortExtStatUsDiscardedPacketsByExpectedIpoeEncapsulation OBJECT-TYPE
       SYNTAX Counter64
       MAX-ACCESS read-only
       STATUS current
       DESCRIPTION
           "Indicates the number of upstream packets discarded due to unexpected IPoE encapsulation.
           Specifically, this node is used to collect the statistics of upstream packets
           that are discarded because they do not support the IPoE protocol."
       ::= { hwSrvPortExtStatEntry 51 }

   hwSrvPortExtStatUsDiscardedPacketsByExpectedPppoaEncapsulation OBJECT-TYPE
       SYNTAX Counter64
       MAX-ACCESS read-only
       STATUS current
       DESCRIPTION
           "Indicates the number of upstream packets discarded due to unexpected PPPoA encapsulation.
           Specifically, this node is used to collect the statistics of upstream packets
           that are discarded because they do not support the PPPoA protocol."
       ::= { hwSrvPortExtStatEntry 52 }

   hwSrvPortExtStatUsDiscardedPacketsByExpectedIpoaEncapsulation OBJECT-TYPE
       SYNTAX Counter64
       MAX-ACCESS read-only
       STATUS current
       DESCRIPTION
           "Indicates the number of upstream packets discarded due to unexpected IPoA encapsulation.
           Specifically, this node is used to collect the statistics of upstream packets
           that are discarded because they do not support the IPoA protocol."
       ::= { hwSrvPortExtStatEntry 53 }

   hwSrvPortExtStatUsDiscardedPacketsByIPSpoofing OBJECT-TYPE
       SYNTAX Counter64
       MAX-ACCESS read-only
       STATUS current
       DESCRIPTION
           "Indicates the number of upstream packets discarded due to anti-IP spoofing.
           Specifically, this node is used to collect the statistics of upstream packets
           that are discarded because their source IP addresses are different from the IP address bound to the service flow."
       ::= { hwSrvPortExtStatEntry 54 }

   hwSrvPortExtStatUsDiscardedPacketsBySourceMacAddressFilter OBJECT-TYPE
       SYNTAX Counter64
       MAX-ACCESS read-only
       STATUS current
       DESCRIPTION
           "Indicates the number of upstream packets discarded due to source MAC address filtering.
           Specifically, this node is used to collect the statistics of upstream packets
           that are discarded because their source MAC addresses are filtered out."
       ::= { hwSrvPortExtStatEntry 55 }

   hwSrvPortExtStatUsDiscardedPacketsByDestinationMacAddressFilter OBJECT-TYPE
       SYNTAX Counter64
       MAX-ACCESS read-only
       STATUS current
       DESCRIPTION
           "Indicates the number of upstream packets discarded due to destination MAC address filtering.
           Specifically, this node is used to collect the statistics of upstream packets
           that are discarded because their destination MAC addresses are filtered out."
       ::= { hwSrvPortExtStatEntry 56 }

   hwSrvPortExtStatUsDiscardedPacketsByHashConflict OBJECT-TYPE
       SYNTAX Counter64
       MAX-ACCESS read-only
       STATUS current
       DESCRIPTION
           "Indicates the number of upstream packets discarded due to a hash conflict."
       ::= { hwSrvPortExtStatEntry 57 }

   hwSrvPortExtStatUsDiscardedPacketsByOverMacLimitation OBJECT-TYPE
       SYNTAX Counter64
       MAX-ACCESS read-only
       STATUS current
       DESCRIPTION
           "Indicates the number of upstream packets discarded due to threshold-crossing of MAC address quantity.
           Specifically, this node is used to collect the statistics of upstream packets
           that are discarded because the number of learned MAC addresses exceeds the upper limit."
       ::= { hwSrvPortExtStatEntry 58 }

   hwSrvPortExtStatUsDiscardedPacketsByVmacCheck OBJECT-TYPE
       SYNTAX Counter64
       MAX-ACCESS read-only
       STATUS current
       DESCRIPTION
           "Indicates the number of upstream packets discarded due to a VMAC check failure.
           Specifically, this node is used to collect the statistics of upstream packets
           that are discarded because of VMAC check inconsistency."
       ::= { hwSrvPortExtStatEntry 59 }

   hwSrvPortExtStatUsDiscardedPacketsByCar OBJECT-TYPE
       SYNTAX Counter64
       MAX-ACCESS read-only
       STATUS current
       DESCRIPTION
           "Indicates the number of upstream packets discarded due to CAR."
       ::= { hwSrvPortExtStatEntry 60 }

   hwSrvPortExtStatUsdiscardedPacketsMacSpoofing OBJECT-TYPE
       SYNTAX Counter64
       MAX-ACCESS read-only
       STATUS current
       DESCRIPTION
           "Indicates the number of upstream packets discarded due to anti-MAC spoofing.
           Specifically, this node is used to collect the statistics of upstream packets
           that are discarded because their source MAC addresses are different from the MAC address
           bound to the service flow."
       ::= { hwSrvPortExtStatEntry 61 }

   hwSrvPortExtStatDsDiscardedPacketsByUnknownUnicastSuppression OBJECT-TYPE
       SYNTAX Counter64
       MAX-ACCESS read-only
       STATUS current
       DESCRIPTION
           "Indicates the number of downstream packets discarded due to unknown unicast suppression.
           Specifically, this node is used to collect the statistics of downstream packets that are discarded
           because the system implements traffic suppression on unknown unicast packets."
       ::= { hwSrvPortExtStatEntry 62 }

   hwSrvPortExtStatDsDiscardedPacketsByUnknownBroadcastSuppression OBJECT-TYPE
       SYNTAX Counter64
       MAX-ACCESS read-only
       STATUS current
       DESCRIPTION
           "Indicates the number of downstream packets discarded due to unknown broadcast suppression.
           Specifically, this node is used to collect the statistics of downstream packets
           that are discarded because the system implements traffic suppression on unknown broadcast packets."
       ::= { hwSrvPortExtStatEntry 63 }

   hwSrvPortExtStatDsDiscardedPacketsByUnknownMulticastSuppression OBJECT-TYPE
       SYNTAX Counter64
       MAX-ACCESS read-only
       STATUS current
       DESCRIPTION
           "Indicates the number of downstream packets discarded due to unknown multicast suppression.
           Specifically, this node is used to collect the statistics of downstream packets
           that are discarded because the system implements traffic suppression on unknown multicast packets."
       ::= { hwSrvPortExtStatEntry 64 }

   hwSrvPortExtStatDsDiscardedPacketsByVLANCheck OBJECT-TYPE
       SYNTAX Counter64
       MAX-ACCESS read-only
       STATUS current
       DESCRIPTION
           "Indicates the number of downstream packets discarded due to a VLAN check failure.
           Specifically, this node is used to collect the statistics of downstream packets
           that are discarded because their VLANs are different the VLAN of the service flow."
       ::= { hwSrvPortExtStatEntry 65 }

   hwSrvPortExtStatDsDiscardedPacketsByExpectedPppoeEncapsulation OBJECT-TYPE
       SYNTAX Counter64
       MAX-ACCESS read-only
       STATUS current
       DESCRIPTION
           "Indicates the number of downstream packets discarded due to unexpected PPPoE encapsulation.
           Specifically, this node is used to collect the statistics of downstream packets
           that are discarded because they do not support the PPPoE protocol."
       ::= { hwSrvPortExtStatEntry 66 }

   hwSrvPortExtStatDsDiscardedPacketsByExpectedIpoeEncapsulation OBJECT-TYPE
       SYNTAX Counter64
       MAX-ACCESS read-only
       STATUS current
       DESCRIPTION
           "Indicates the number of downstream packets discarded due to unexpected IPoE encapsulation.
           Specifically, this node is used to collect the statistics of downstream packets
           that are discarded because they do not support the IPoE protocol."
       ::= { hwSrvPortExtStatEntry 67 }

   hwSrvPortExtStatDsDiscardedPacketsByUnexpectedPppoaEncapsulation OBJECT-TYPE
       SYNTAX Counter64
       MAX-ACCESS read-only
       STATUS current
       DESCRIPTION
           "Indicates the number of downstream packets discarded due to unexpected PPPoA encapsulation.
           Specifically, this node is used to collect the statistics of downstream packets
           that are discarded because they do not support the PPPoA protocol."
       ::= { hwSrvPortExtStatEntry 68 }

   hwSrvPortExtStatDsDiscardedPacketsByEncapsulationLengthError OBJECT-TYPE
       SYNTAX Counter64
       MAX-ACCESS read-only
       STATUS current
       DESCRIPTION
           "Indicates the number of downstream packets discarded due to length errors during encapsulation conversion.
           Specifically, this node is used to collect the statistics of downstream packets
           that are discarded because their lengths are found incorrect during encapsulation conversion."
       ::= { hwSrvPortExtStatEntry 69 }

   hwSrvPortExtStatDsDiscardedPacketsByVmacCheck OBJECT-TYPE
       SYNTAX Counter64
       MAX-ACCESS read-only
       STATUS current
       DESCRIPTION
           "Indicates the number of downstream packets discarded due to a VMAC check failure.
           Specifically, this node is used to collect the statistics of downstream packets
           that are discarded because of VMAC check inconsistency."
       ::= { hwSrvPortExtStatEntry 70 }

   hwSrvPortExtStatDsDiscardedPacketsByCar OBJECT-TYPE
       SYNTAX Counter64
       MAX-ACCESS read-only
       STATUS current
       DESCRIPTION
           "Indicates the number of downstream packets discarded due to CAR."
       ::= { hwSrvPortExtStatEntry 71 }

   hwSrvPortExtStatDsDiscardedPacketsByQueue OBJECT-TYPE
       SYNTAX Counter64
       MAX-ACCESS read-only
       STATUS current
       DESCRIPTION
           "Indicates the number of downstream packets discarded due to queue overflow.
           This node is used to collect the statistics of downstream packets that are discarded
           because they fail to enter queues."
       ::= { hwSrvPortExtStatEntry 72 }

   hwSrvPortExtStatUsDiscardedPacketsByL3Forward OBJECT-TYPE
       SYNTAX Counter64
       MAX-ACCESS read-only
       STATUS current
       DESCRIPTION
           "Indicates the number of upstream packets discarded due to L3 Forward.
           This node is used to collect the statistics of upstream packets that are discarded
           by L3 forward."
       ::= { hwSrvPortExtStatEntry 73 }

    hwSrvPortExtStatDsDiscardedPacketsByL3Forward OBJECT-TYPE
       SYNTAX Counter64
       MAX-ACCESS read-only
       STATUS current
       DESCRIPTION
           "Indicates the number of downstream packets discarded due to L3 Forward.
           This node is used to collect the statistics of downstream packets that are discarded
           by L3 forward."
       ::= { hwSrvPortExtStatEntry 74 }

-- hwStaticMacTable
   hwStaticMacTable OBJECT-TYPE
       SYNTAX SEQUENCE OF HwStaticMacEntry
       MAX-ACCESS not-accessible
       STATUS current
       DESCRIPTION
           "Describes static MAC addresses and used for setting, querying, and deleting static MAC addresses.
            The index of this table is hwStaticMacIndex, a free index can be obtained through hwStaticMacNextFreeIndex.
           "
       ::= { hwEthernetPort 11 }

   hwStaticMacEntry OBJECT-TYPE
       SYNTAX HwStaticMacEntry
       MAX-ACCESS not-accessible
       STATUS current
       DESCRIPTION
           "Describes static MAC addresses and used for setting, querying, and deleting static MAC addresses.
            The index of this entry is hwStaticMacIndex, a free index can be obtained through hwStaticMacNextFreeIndex.
           "
       INDEX { hwStaticMacIndex }
       ::= { hwStaticMacTable 1 }

   HwStaticMacEntry ::=
       SEQUENCE {
       hwStaticMacIndex
           Unsigned32,
       hwStaticMacIfIndex
           Unsigned32,
       hwStaticMacVlanID
           Unsigned32,
       hwStaticMacVPI
           Integer32,
       hwStaticMacVCI
           Integer32,
       hwStaticMacFlowID
           Unsigned32,
       hwStaticMacMacAddr
           OCTET STRING,
       hwStaticMacRowStatus
           RowStatus,
       hwStaticMacPwIndex
           Unsigned32
        }

   hwStaticMacIndex   OBJECT-TYPE
       SYNTAX Unsigned32
       MAX-ACCESS read-write
       STATUS current
       DESCRIPTION
           "Indicates the index of a static MAC address. The index is used by the software for recording an entry.
            The MAC address corresponding to the index must be null, and a free index can be obtained for the MAC
            address through hwStaticMacNextFreeIndex.
           "
       ::= { hwStaticMacEntry 1 }

   hwStaticMacIfIndex OBJECT-TYPE
       SYNTAX Unsigned32
       MAX-ACCESS read-write
       STATUS current
       DESCRIPTION
           "Indicates the port index for configuring a static MAC address on a specified port.
            The index uniquely identifies a port.
            The value and algorithm of this index are the same as those of the ifIndex.
            If you query the MAC address that is bound to a PW, then the returned value is 0xFFFFFFFF, which indicates an invalid value.
           "
       ::= { hwStaticMacEntry 2 }

   hwStaticMacVlanID OBJECT-TYPE
       SYNTAX Unsigned32 (1..4093)
       MAX-ACCESS read-write
       STATUS current
       DESCRIPTION
           "Indicates the VLAN to which a static MAC address belongs.
            Range: 1-4093
           "
       ::= { hwStaticMacEntry 3 }

   hwStaticMacVPI OBJECT-TYPE
       SYNTAX Integer32
       MAX-ACCESS read-write
       STATUS current
       DESCRIPTION
           "Indicates the VPI value among the ATM/xDSL service port parameters.
            The following four leaves determine a single-service service port:
            hwStaticMacIfIndex, hwStaticMacVlanID, hwStaticMacVPI, and hwStaticMacVCI.
            hwStaticMacVPI is no longer used in actual applications and is mainly
            used for the purpose of compatibility with earlier versions. Currently,
            to set the static MAC address of a service port, hwStaticMacFlowID is
            used for specifying the service port index.
            If you query the MAC address that is bound to a specified service port
            on the xDSL board, the result means the VPI of the service port.
            If the type of service port is xPON, then it indicates the ONT ID.
            If the type of service port is GIU or if you query the MAC address bound to a PW, then the returned value is -1, which
            indicates an invalid value.
           "
       ::= { hwStaticMacEntry 4 }

   hwStaticMacVCI OBJECT-TYPE
       SYNTAX Integer32
       MAX-ACCESS read-write
       STATUS current
       DESCRIPTION
           "Indicates the VCI value among the ATM/xDSL service port parameters.
            The following four leaves determine a single-service service port:
            hwStaticMacIfIndex, hwStaticMacVlanID, hwStaticMacVPI, and hwStaticMacVCI.
            hwStaticMacVCI is no longer used in actual applications and is mainly
            used for the purpose of compatibility with earlier versions. Currently,
            to set the static MAC address of a service port, hwStaticMacFlowID is
            used for specifying the service port index.
            If you query the MAC address that is bound to a specified service port
            on the xDSL board, the result means the VCI of the service port.
            If the type of service port is xPON, then it indicates the GEM index.
            If the type of service port is GIU or if you query the MAC address bound to a PW, then the returned value is -1,
            which indicates an invalid value.
           "
       ::= { hwStaticMacEntry 5 }

   hwStaticMacFlowID OBJECT-TYPE
       SYNTAX Unsigned32
       MAX-ACCESS read-write
       STATUS current
       DESCRIPTION
           "Indicates the index of a service port.
            The service port must be already created through hwExtSrvFlowTable.
            During query, -1 indicates invalid."
       ::= { hwStaticMacEntry 6 }

   hwStaticMacMacAddr OBJECT-TYPE
       SYNTAX OCTET STRING(SIZE (6..17))
       MAX-ACCESS read-write
       STATUS current
       DESCRIPTION
           "Indicates the MAC address that needs to be configured as a static MAC address.
            The following is an example of the input format of the MAC address:
            If the MAC address is 00e0-fc11-0000, enter # 0x00 0xe0 0xfc 0x11 0x00 0x00 or the character string 00-e0-fc-11-00-00.
            A device may support only one format.
           "
       ::= { hwStaticMacEntry 7 }

   hwStaticMacRowStatus OBJECT-TYPE
       SYNTAX RowStatus
       MAX-ACCESS read-create
       STATUS current
       DESCRIPTION
           "Indicates the row status, used for creating or deleting a static MAC address.
            Only options createAndGo(4) and destroy(6) are supported.
            Pay attention to the following points when creating a static MAC address:
            1. To set a static MAC address on an Ethernet port, input hwStaticMacIndex,
            at the same time set and issue hwStaticMacIfIndex, hwStaticMacVlanID,
            and hwStaticMacMacAddr, and set hwStaticMacRowStatus to createAndGo(4).
            2. To set a static MAC address on a service port, input hwStaticMacIndex,
            at the same time set and issue hwStaticMacFlowID, and set hwStaticMacRowStatus to createAndGo(4).
            3. To set a static MAC address on a PW, input hwStaticMacIndex,
            at the same time set and issue hwStaticMacVlanID,  and hwStaticMacMacAddr,
            and hwStaticPwIndex, and set hwStaticMacRowStatus to createAndGo(4).
            To delete a static MAC address, input hwStaticMacIndex, and set hwStaticMacRowStatus to destroy(6).
            In the query operation, the value of hwStaticMacRowStatus is always active(1).
            Options:
            1. active(1)      -indicates the query operation
            2. createAndGo(4) -indicates set a static MAC address on an ethernet port or a service port
            3. destroy(6)     -indicates delete a static MAC address on an ethernet port or a service port
           "
       ::= { hwStaticMacEntry 8 }

    hwStaticMacPwIndex OBJECT-TYPE
        SYNTAX Unsigned32
        MAX-ACCESS  read-write
        STATUS  current
        DESCRIPTION
            "Indicates the PW index value for configuring a static MAC address on a special PW.
             The index uniquely identifies a PW.
             The default value is 0xFFFFFFFF,which indicates it's an invalid value.
            "
       ::= { hwStaticMacEntry 9}

-- hwStaticMacNextFreeIndex
   hwStaticMacNextFreeIndex OBJECT-TYPE
       SYNTAX Integer32
       MAX-ACCESS read-only
       STATUS current
       DESCRIPTION
           "Used for obtaining a free index during the creation of a static MAC address.
            The obtained value is used when hwStaticMacIndex is input.
           "
        ::= { hwEthernetPort 12 }

-- hwPortIsolate
   hwPortIsolate OBJECT IDENTIFIER ::= { hwEthernetPort 13 }

   hwPortIsolateTable OBJECT-TYPE
       SYNTAX SEQUENCE OF HwPortIsolateEntry
       MAX-ACCESS not-accessible
       STATUS current
       DESCRIPTION
           "Indicates the Ethernet port isolation table.
            The indexes of this table are hwFrameIsolateIndex, hwSlotIsolateIndex and hwPortIsolateIndex.
           "
       ::= { hwPortIsolate 1 }

   hwPortIsolateEntry OBJECT-TYPE
       SYNTAX HwPortIsolateEntry
       MAX-ACCESS not-accessible
       STATUS current
       DESCRIPTION
           "Indicates the Ethernet port isolation table.
            The indexes of this entry are hwFrameIsolateIndex, hwSlotIsolateIndex and hwPortIsolateIndex.
           "
       INDEX { hwFrameIsolateIndex,
               hwSlotIsolateIndex,
               hwPortIsolateIndex }
       ::= { hwPortIsolateTable 1 }

   HwPortIsolateEntry ::=
       SEQUENCE {
           hwFrameIsolateIndex
               Integer32,
           hwSlotIsolateIndex
               Integer32,
           hwPortIsolateIndex
               Integer32,
           hwIsolateRowstatus
               RowStatus,
           hwIsolateStatus
               INTEGER,
           hwIsolateBroadcast
               INTEGER,
           hwIsolateUnknownMulticast
               INTEGER,
           hwIsolateUnknownUnicast
               INTEGER
            }

   hwFrameIsolateIndex OBJECT-TYPE
       SYNTAX Integer32 (0..65535)
       MAX-ACCESS not-accessible
       STATUS current
       DESCRIPTION
           "Index of this table."
       ::= { hwPortIsolateEntry 1 }

   hwSlotIsolateIndex OBJECT-TYPE
       SYNTAX Integer32 (0..255)
       MAX-ACCESS not-accessible
       STATUS current
       DESCRIPTION
           "Index of this table."
       ::= { hwPortIsolateEntry 2 }

   hwPortIsolateIndex OBJECT-TYPE
       SYNTAX Integer32 (0..255)
       MAX-ACCESS not-accessible
       STATUS current
       DESCRIPTION
           "Index of this table."
       ::= { hwPortIsolateEntry 3 }

   hwIsolateRowstatus OBJECT-TYPE
       SYNTAX RowStatus
       MAX-ACCESS   read-create
       STATUS       current
       DESCRIPTION
           "Indicates the row status. This leaf supports only the query operation;
            in the query operation, the returned value of this leaf is always active(1).
            Options:
            1. active(1) -indicates the query operation
           "
           DEFVAL { active }
       ::= { hwPortIsolateEntry 4}

   hwIsolateStatus OBJECT-TYPE
       SYNTAX   INTEGER
       {
            enable(1),
            disable(2)
       }
       MAX-ACCESS read-write
       STATUS current
       DESCRIPTION
           "Indicates the port isolation status. The default value of an upstream port
            is disable(2). The default value of a downstream port is enable(1).
            Options:
            1. enable(1)  -indicates the port isolation status is enable
            2. disable(2) -indicates the port isolation status is disable
           "
       ::= { hwPortIsolateEntry 5 }

   hwIsolateBroadcast OBJECT-TYPE
       SYNTAX INTEGER
        {
            enabled(1),
            disabled(2)
        }
       MAX-ACCESS read-write
       STATUS current
       DESCRIPTION
           "Enable or disable the system isolation switch of broadcast frame between
            different down link ports in the same smart vlan.Default state is disable.
            Options:
            1. enabled(1)  -Indicates the broadcast frame isolation status is enable.
            2. disabled(2) -Indicates the broadcast frame isolation status is disable.
           "
           DEFVAL { disabled }
       ::= { hwPortIsolateEntry 6 }

   hwIsolateUnknownMulticast OBJECT-TYPE
       SYNTAX INTEGER
        {
            enabled(1),
            disabled(2)
        }
       MAX-ACCESS read-write
       STATUS current
       DESCRIPTION
           "Enable or disable the system isolation switch of unknown multicast frame between
            different down link ports in the same smart vlan.Default state is disable.
            Options:
            1. enabled(1)  -Indicates the unknown multicast frame isolation status is enable.
            2. disabled(2) -Indicates the unknown multicast frame isolation status is disable.
           "
           DEFVAL { disabled }
       ::= { hwPortIsolateEntry 7 }

   hwIsolateUnknownUnicast OBJECT-TYPE
       SYNTAX INTEGER
           {
           enabled(1),
           disabled(2)
           }
       MAX-ACCESS read-write
       STATUS current
       DESCRIPTION
           "Enable or disable the system isolation switch of unknown unicast frame between
            different down link ports in the same smart vlan.Default state is disable.
            Options:
            1. enabled(1)  -Indicates the unknown unicast frame isolation status is enable.
            2. disabled(2) -Indicates the unknown unicast frame isolation status is disable.
           "
           DEFVAL { disabled }
       ::= { hwPortIsolateEntry 8 }

   hwPortIsolateGroupTable OBJECT-TYPE
       SYNTAX SEQUENCE OF HwPortIsolateGroupEntry
       MAX-ACCESS not-accessible
       STATUS current
       DESCRIPTION
           "The port isolation group.
            The indexes of this table are hwPortIsolateGroupIndex and hwPortIsolateGroupIfIndex.
           "
       ::= { hwPortIsolate 2 }

   hwPortIsolateGroupEntry OBJECT-TYPE
       SYNTAX HwPortIsolateGroupEntry
       MAX-ACCESS not-accessible
       STATUS current
       DESCRIPTION
           "The port isolation group.
            The indexes of this entry are hwPortIsolateGroupIndex and hwPortIsolateGroupIfIndex.
           "
       INDEX {hwPortIsolateGroupIndex, hwPortIsolateGroupIfIndex}
       ::= { hwPortIsolateGroupTable 1 }

   HwPortIsolateGroupEntry ::=
       SEQUENCE {
         hwPortIsolateGroupIndex
           Integer32,
         hwPortIsolateGroupIfIndex
           Integer32,
         hwPortIsolateGroupRowStatus
           RowStatus
        }

   hwPortIsolateGroupIndex OBJECT-TYPE
       SYNTAX Integer32 (0..255)
       MAX-ACCESS read-write
       STATUS current
       DESCRIPTION
           "this Para indicates the isolation group ID"
       ::= { hwPortIsolateGroupEntry 1 }

   hwPortIsolateGroupIfIndex OBJECT-TYPE
       SYNTAX Integer32
       MAX-ACCESS read-write
       STATUS current
       DESCRIPTION
           "this Para indicates the Fram/Slot/Port"
       ::= { hwPortIsolateGroupEntry 2 }

   hwPortIsolateGroupRowStatus OBJECT-TYPE
       SYNTAX RowStatus
       MAX-ACCESS   read-create
       STATUS       current
       DESCRIPTION
           "This object is used to add, delete the port of isolate
            group in this table. To add a new port into group, this
            object should set to 'createAndGo'. To delete a port from
            group,this object is is initially set to 'destroy'
            Options:
            1. active(1)      -indicates the query operation
            2. createAndGo(4) -add a new port into group
            3. destroy(6)     -delete a port from group
           "
       ::= { hwPortIsolateGroupEntry 3}

-- hwDynamicMac
   hwDynamicMac OBJECT IDENTIFIER ::= { hwEthernetPort 14 }

   hwDynamicMacConfigTable OBJECT-TYPE
       SYNTAX SEQUENCE OF HwDynamicMacConfigEntry
       MAX-ACCESS not-accessible
       STATUS current
       DESCRIPTION
           "Dynamic MAC address config property.
            The index of this table is ifIndex.
           "
       ::= { hwDynamicMac 1 }

   hwDynamicMacConfigEntry OBJECT-TYPE
       SYNTAX HwDynamicMacConfigEntry
       MAX-ACCESS not-accessible
       STATUS current
       DESCRIPTION
           "Dynamic MAC address config property.
            The index of this entry is ifIndex.
           "
       INDEX { ifIndex }
       ::= { hwDynamicMacConfigTable 1 }

   HwDynamicMacConfigEntry ::=
       SEQUENCE {
           hwPortMaxDynamicMacCount
               Unsigned32
           }

   hwPortMaxDynamicMacCount   OBJECT-TYPE
       SYNTAX Unsigned32 (0..16384)
       MAX-ACCESS read-write
       STATUS current
       DESCRIPTION
           "The MAX number of dynamic mac address can be learned per port."
       ::= { hwDynamicMacConfigEntry 2 }

   hwDynamicMacTable OBJECT-TYPE
       SYNTAX SEQUENCE OF HwDynamicMacEntry
       MAX-ACCESS not-accessible
       STATUS current
       DESCRIPTION
           "Indicates the Dynamic MAC address in system.
            The indexes of this table are ifIndex and hwDynamicMacIndex.
           "
       ::= { hwDynamicMac 2 }

   hwDynamicMacEntry OBJECT-TYPE
       SYNTAX HwDynamicMacEntry
       MAX-ACCESS not-accessible
       STATUS current
       DESCRIPTION
           "Indicates the Dynamic MAC address in system.
            The indexes of this entry are ifIndex and hwDynamicMacIndex.
           "
       INDEX { ifIndex, hwDynamicMacIndex }
       ::= { hwDynamicMacTable 1 }

   HwDynamicMacEntry ::=
       SEQUENCE {
           hwDynamicMacIndex
               Unsigned32,
           hwDynamicMacVlanId
               Unsigned32,
           hwDynamicMacAddr
               MacAddress,
           hwTimeTillExpired
               Unsigned32,
           hwDynamicMacRowStatus
               RowStatus
           }

   hwDynamicMacIndex   OBJECT-TYPE
       SYNTAX Unsigned32 (0..16384)
       MAX-ACCESS read-only
       STATUS current
       DESCRIPTION
           "The dynamic MAC address index. "
       ::= { hwDynamicMacEntry 1 }

   hwDynamicMacVlanId   OBJECT-TYPE
       SYNTAX Unsigned32 (1..4094)
       MAX-ACCESS read-write
       STATUS current
       DESCRIPTION
           "The VLAN of dynamic MAC address. "
       ::= { hwDynamicMacEntry 2 }

   hwDynamicMacAddr   OBJECT-TYPE
       SYNTAX MacAddress
       MAX-ACCESS read-write
       STATUS current
       DESCRIPTION
           "The mac address, and its format is XX-XX-XX-XX-XX-XX."
       ::= { hwDynamicMacEntry 3 }

   hwTimeTillExpired   OBJECT-TYPE
       SYNTAX Unsigned32 (10..1000000)
       MAX-ACCESS read-only
       STATUS current
       DESCRIPTION
           "The time of the MAC address till expired."
       ::= { hwDynamicMacEntry 4 }

   hwDynamicMacRowStatus OBJECT-TYPE
       SYNTAX RowStatus
       MAX-ACCESS read-create
       STATUS current
       DESCRIPTION
           "The variable is used to decide what operation will be done
           when set from SNMP. The supported operations is only destroy.
           "
       ::= { hwDynamicMacEntry 5 }

   hwDynamicMacLearningMode OBJECT-TYPE
       SYNTAX INTEGER
           {
               unlimited(1),
               limited(2)
           }
       MAX-ACCESS read-write
       STATUS current
       DESCRIPTION
           "MAC address learning mode.
           Options:
           1. unlimited(1)   -MAC learning number is not limited.
           2. limited(2)     -MAC learning number is limited.
           "
       ::= { hwDynamicMac 3 }

-- hwEthHistoryStats
   hwEthHistoryStats OBJECT IDENTIFIER ::= { hwEthernetPort 16 }

   hwEthHistoryStatsTable OBJECT-TYPE
       SYNTAX SEQUENCE OF HwEthHistoryStatsEntry
       MAX-ACCESS not-accessible
       STATUS current
       DESCRIPTION
           "Ether History Statistic.
           The indexes of this table are ifIndex, hwEthStatsIntervalType and hwEthStatsIntervalNum."
       ::= { hwEthHistoryStats 1 }

   hwEthHistoryStatsEntry OBJECT-TYPE
       SYNTAX HwEthHistoryStatsEntry
       MAX-ACCESS not-accessible
       STATUS current
       DESCRIPTION
           "Ether History Statistic.
           The indexes of this entry are ifIndex, hwEthStatsIntervalType and hwEthStatsIntervalNum."
       INDEX { ifIndex ,
               hwEthStatsIntervalType,
               hwEthStatsIntervalNum
             }
       ::= { hwEthHistoryStatsTable 1 }

   HwEthHistoryStatsEntry ::=
       SEQUENCE
       {
           hwEthStatsIntervalType                INTEGER,
           hwEthStatsIntervalNum                 Integer32,
           hwEthStatsRxDropEvents                Counter64,
           hwEthStatsRxOctets                    Counter64,
           hwEthStatsRxPkts                      Counter64,
           hwEthStatsRxBroadcastPkts             Counter64,
           hwEthStatsRxMulticastPkts             Counter64,
           hwEthStatsRxPauseFramePkts            Counter64,
           hwEthStatsRxCRCAlignErrors            Counter64,
           hwEthStatsRxUndersizePkts             Counter64,
           hwEthStatsRxOversizePkts              Counter64,
           hwEthStatsRxFragments                 Counter64,
           hwEthStatsRxJabbers                   Counter64,
           hwEthStatsRxCollisions                Counter64,
           hwEthStatsRxPkts64Octets              Counter64,
           hwEthStatsRxPkts65to127Octets         Counter64,
           hwEthStatsRxPkts128to255Octets        Counter64,
           hwEthStatsRxPkts256to511Octets        Counter64,
           hwEthStatsRxPkts512to1023Octets       Counter64,
           hwEthStatsRxPkts1024to1518Octets      Counter64,
           hwEthStatsRxPkts1519to2047Octets      Counter64,
           hwEthStatsRxPkts2048to4095Octets      Counter64,
           hwEthStatsRxPkts4096to9216Octets      Counter64,
           hwEthStatsTxOctets                    Counter64,
           hwEthStatsTxPkts                      Counter64,
           hwEthStatsTxBroadcastPkts             Counter64,
           hwEthStatsTxMulticastPkts             Counter64,
           hwEthStatsTxPauseFramePkts            Counter64,
           hwTimeElapsed                         Integer32,
           hwValidInterval                       TruthValue,
           hwEthStatsStartTime                   OCTET STRING,
           hwEthStatsValidNumber                 Integer32,
           hwEthStatsInvalidNumber               Integer32,
           hwEthStatsStatusChangeTimes           Integer32,
           hwEthStatsRxUnicastPkts               Counter64,
           hwEthStatsTxUnicastPkts               Counter64,
           hwEthStatsRxAlignErrors               Counter64,
           hwEthStatsTxCollisionPkts             Counter64,
           hwEthStatsTxSingleCollisionPkts       Counter64,
           hwEthStatsTxMultipleCollisionPkts     Counter64,
           hwEthStatsDiscardedUndersizedPkts     Counter64,
           hwEthStatsTxUnderSizedPkts            Counter64,
           hwEthStatsTxFragmentsPkts             Counter64,
           hwEthStatsTxJabbers                   Counter64,
           hwEthStatsTxOverSizedPkts             Counter64,
           hwEthStatsTx64OctetsPkts              Counter64,
           hwEthStatsTx65to127OctetsPkts         Counter64,
           hwEthStatsTx128to255OctetsPkts        Counter64,
           hwEthStatsTx256to511OctetsPkts        Counter64,
           hwEthStatsTx512to1023OctetsPkts       Counter64,
           hwEthStatsTx1024to1518OctetsPkts      Counter64,
           hwEthStatsTxErrorPkts                 Counter64,
           hwEthStatsRxErrorPkts                 Counter64,
           hwEthStatsTxDropPkts                  Counter64,
           hwEthStatsTxCRCErrorPkts              Counter64,
           hwEthStatsEfmErroredFrameEvents                Unsigned32,
           hwEthStatsEfmErroredFrameSecondSummaryEvents   Unsigned32,
           hwEthStatsEfmErroredFramePeriodEvents          Unsigned32
       }

   hwEthStatsIntervalType OBJECT-TYPE
       SYNTAX INTEGER
           {
           intervaltime15min(0),
           intervaltime24h(1),
           everbefore(2)
           }
       MAX-ACCESS not-accessible
       STATUS     current
       DESCRIPTION
           "The type of Ether History Statistic.
            Options:
            1. intervaltime15min(0)   -15 minutes
            2. intervaltime24h(1)     -24 hours
            3. everbefore(2)          -everbefore
           "
       ::= { hwEthHistoryStatsEntry 1 }

   hwEthStatsIntervalNum OBJECT-TYPE
       SYNTAX     Integer32 (0..96)
       MAX-ACCESS not-accessible
       STATUS     current
       DESCRIPTION
           "The interval number of Ether History Statistic. When hwEthStatsIntervalType is intervaltime15min,
           0 represents current 15 minutes interval, and when hwEthStatsIntervalType is intervaltime24h,
           0 represents current 24 hours interval"
       ::= { hwEthHistoryStatsEntry 2 }


   hwEthStatsRxDropEvents OBJECT-TYPE
       SYNTAX     Counter64
       MAX-ACCESS read-only
       STATUS     current
       DESCRIPTION
           "Number of received discarded packets.
           '18446744073709551615' means invalid value."
       ::= { hwEthHistoryStatsEntry 3 }

   hwEthStatsRxOctets OBJECT-TYPE
       SYNTAX     Counter64
       MAX-ACCESS read-only
       STATUS     current
       DESCRIPTION
           "Number of received octets.
           '18446744073709551615' means invalid value."
       ::= { hwEthHistoryStatsEntry 4 }

   hwEthStatsRxPkts OBJECT-TYPE
       SYNTAX     Counter64
       MAX-ACCESS read-only
       STATUS     current
       DESCRIPTION
           "Number of received frames.
           '18446744073709551615' means invalid value."
       ::= { hwEthHistoryStatsEntry 5 }

   hwEthStatsRxBroadcastPkts OBJECT-TYPE
       SYNTAX     Counter64
       MAX-ACCESS read-only
       STATUS     current
       DESCRIPTION
           "Number of received broadcast frames.
           '18446744073709551615' means invalid value."
       ::= { hwEthHistoryStatsEntry 6 }

   hwEthStatsRxMulticastPkts OBJECT-TYPE
       SYNTAX     Counter64
       MAX-ACCESS read-only
       STATUS     current
       DESCRIPTION
           "Number of received multicast frames.
           '18446744073709551615' means invalid value."
       ::= { hwEthHistoryStatsEntry 7 }

   hwEthStatsRxPauseFramePkts OBJECT-TYPE
       SYNTAX     Counter64
       MAX-ACCESS read-only
       STATUS     current
       DESCRIPTION
           "Number of received pause frames.
           '18446744073709551615' means invalid value."
       ::= { hwEthHistoryStatsEntry 8 }

   hwEthStatsRxCRCAlignErrors OBJECT-TYPE
       SYNTAX     Counter64
       MAX-ACCESS read-only
       STATUS     current
       DESCRIPTION
           "Number of CRC error frames.
           '18446744073709551615' means invalid value."
       ::= { hwEthHistoryStatsEntry 9 }

   hwEthStatsRxUndersizePkts OBJECT-TYPE
       SYNTAX     Counter64
       MAX-ACCESS read-only
       STATUS     current
       DESCRIPTION
           "Number of undersized frames
           '18446744073709551615' means invalid value."
       ::= { hwEthHistoryStatsEntry 10 }

   hwEthStatsRxOversizePkts OBJECT-TYPE
       SYNTAX     Counter64
       MAX-ACCESS read-only
       STATUS     current
       DESCRIPTION
           "Number of oversized frames.
           '18446744073709551615' means invalid value."
       ::= { hwEthHistoryStatsEntry 11 }

   hwEthStatsRxFragments OBJECT-TYPE
       SYNTAX     Counter64
       MAX-ACCESS read-only
       STATUS     current
       DESCRIPTION
           "Number of fragment frames.
           '18446744073709551615' means invalid value."
       ::= { hwEthHistoryStatsEntry 12 }

   hwEthStatsRxJabbers OBJECT-TYPE
       SYNTAX     Counter64
       MAX-ACCESS read-only
       STATUS     current
       DESCRIPTION
           "Number of Jabber frames.
           '18446744073709551615' means invalid value."
       ::= { hwEthHistoryStatsEntry 13 }

   hwEthStatsRxCollisions OBJECT-TYPE
       SYNTAX     Counter64
       MAX-ACCESS read-only
       STATUS     current
       DESCRIPTION
           "Number of collision frames.
           '18446744073709551615' means invalid value."
       ::= { hwEthHistoryStatsEntry 14 }

   hwEthStatsRxPkts64Octets OBJECT-TYPE
       SYNTAX     Counter64
       MAX-ACCESS read-only
       STATUS     current
       DESCRIPTION
           "Number of packets(64 octets in length).
           '18446744073709551615' means invalid value."
       ::= { hwEthHistoryStatsEntry 15 }

   hwEthStatsRxPkts65to127Octets OBJECT-TYPE
       SYNTAX     Counter64
       MAX-ACCESS read-only
       STATUS     current
       DESCRIPTION
           "Number of packets(65~127 octets in length)
           '18446744073709551615' means invalid value."
       ::= { hwEthHistoryStatsEntry 16 }

   hwEthStatsRxPkts128to255Octets OBJECT-TYPE
       SYNTAX     Counter64
       MAX-ACCESS read-only
       STATUS     current
       DESCRIPTION
           "Number of packets(128~255 octets in length).
           '18446744073709551615' means invalid value."
       ::= { hwEthHistoryStatsEntry 17 }

   hwEthStatsRxPkts256to511Octets OBJECT-TYPE
       SYNTAX     Counter64
       MAX-ACCESS read-only
       STATUS     current
       DESCRIPTION
           "Number of packets(256~511 octets in length).
           '18446744073709551615' means invalid value."
       ::= { hwEthHistoryStatsEntry 18 }

   hwEthStatsRxPkts512to1023Octets OBJECT-TYPE
       SYNTAX     Counter64
       MAX-ACCESS read-only
       STATUS     current
       DESCRIPTION
           "Number of packets(512~1023 octets in length).
           '18446744073709551615' means invalid value."
       ::= { hwEthHistoryStatsEntry 19 }

   hwEthStatsRxPkts1024to1518Octets OBJECT-TYPE
       SYNTAX     Counter64
       MAX-ACCESS read-only
       STATUS     current
       DESCRIPTION
           "Number of packets(1024~1518 octets in length).
           '18446744073709551615' means invalid value."
       ::= { hwEthHistoryStatsEntry 20 }

   hwEthStatsRxPkts1519to2047Octets OBJECT-TYPE
       SYNTAX     Counter64
       MAX-ACCESS read-only
       STATUS     current
       DESCRIPTION
           "Number of packets(1519~2047 octets in length).
           '18446744073709551615' means invalid value."
       ::= { hwEthHistoryStatsEntry 21 }

   hwEthStatsRxPkts2048to4095Octets OBJECT-TYPE
       SYNTAX     Counter64
       MAX-ACCESS read-only
       STATUS     current
       DESCRIPTION
           "Number of packets(2048~4095 octets in length).
           '18446744073709551615' means invalid value."
       ::= { hwEthHistoryStatsEntry 22 }

   hwEthStatsRxPkts4096to9216Octets OBJECT-TYPE
       SYNTAX     Counter64
       MAX-ACCESS read-only
       STATUS     current
       DESCRIPTION
           "Number of packets(4096~9216 octets in length).
           '18446744073709551615' means invalid value."
       ::= { hwEthHistoryStatsEntry 23 }

   hwEthStatsTxOctets OBJECT-TYPE
       SYNTAX     Counter64
       MAX-ACCESS read-only
       STATUS     current
       DESCRIPTION
           "Number of transmitted octets.
           '18446744073709551615' means invalid value."
       ::= { hwEthHistoryStatsEntry 24 }

   hwEthStatsTxPkts OBJECT-TYPE
       SYNTAX     Counter64
       MAX-ACCESS read-only
       STATUS     current
       DESCRIPTION
           "Number of transmitted frames.
           '18446744073709551615' means invalid value."
       ::= { hwEthHistoryStatsEntry 25 }

   hwEthStatsTxBroadcastPkts OBJECT-TYPE
       SYNTAX     Counter64
       MAX-ACCESS read-only
       STATUS     current
       DESCRIPTION
           "Number of transmitted broadcast frames.
           '18446744073709551615' means invalid value."
       ::= { hwEthHistoryStatsEntry 26 }

   hwEthStatsTxMulticastPkts OBJECT-TYPE
       SYNTAX     Counter64
       MAX-ACCESS read-only
       STATUS     current
       DESCRIPTION
           "Number of transmitted multicast frames.
           '18446744073709551615' means invalid value."
       ::= { hwEthHistoryStatsEntry 27 }

   hwEthStatsTxPauseFramePkts OBJECT-TYPE
       SYNTAX     Counter64
       MAX-ACCESS read-only
       STATUS     current
       DESCRIPTION
           "Number of transmitted pause frames.
           '18446744073709551615' means invalid value."
       ::= { hwEthHistoryStatsEntry 28 }

   hwTimeElapsed OBJECT-TYPE
       SYNTAX Integer32
       MAX-ACCESS read-only
       STATUS     current
       DESCRIPTION
           "The elapsed time of the current interval."
       ::= { hwEthHistoryStatsEntry 29 }

   hwValidInterval OBJECT-TYPE
       SYNTAX TruthValue
       MAX-ACCESS read-only
       STATUS     current
       DESCRIPTION
           "whether the interval number is valid."
       ::= { hwEthHistoryStatsEntry 30 }

   hwEthStatsStartTime OBJECT-TYPE
       SYNTAX     OCTET STRING
       MAX-ACCESS read-only
       STATUS     current
       DESCRIPTION
           "Start time of the interval."
       ::= { hwEthHistoryStatsEntry 31 }

   hwEthStatsValidNumber OBJECT-TYPE
       SYNTAX     Integer32
       MAX-ACCESS read-only
       STATUS     current
       DESCRIPTION
           "Number of valid interval.
           '-1' means invalid value."
       ::= { hwEthHistoryStatsEntry 32 }

   hwEthStatsInvalidNumber OBJECT-TYPE
       SYNTAX     Integer32
       MAX-ACCESS read-only
       STATUS     current
       DESCRIPTION
           "Number of invalid interval.
           '-1' means invalid value."
       ::= { hwEthHistoryStatsEntry 33 }

   hwEthStatsStatusChangeTimes OBJECT-TYPE
       SYNTAX     Integer32
       MAX-ACCESS read-only
       STATUS     current
       DESCRIPTION
           "Number of port status changed.
           '-1' means invalid value."
       ::= { hwEthHistoryStatsEntry 34 }

   hwEthStatsRxUnicastPkts OBJECT-TYPE
       SYNTAX     Counter64
       MAX-ACCESS read-only
       STATUS     current
       DESCRIPTION
           "Number of received unicast packets.
           '18446744073709551615' means invalid value."
       ::= { hwEthHistoryStatsEntry 35 }

   hwEthStatsTxUnicastPkts OBJECT-TYPE
       SYNTAX     Counter64
       MAX-ACCESS read-only
       STATUS     current
       DESCRIPTION
           "Number of transmitted unicast packets.
           '18446744073709551615' means invalid value."
       ::= { hwEthHistoryStatsEntry 36 }

   hwEthStatsRxAlignErrors OBJECT-TYPE
       SYNTAX     Counter64
       MAX-ACCESS read-only
       STATUS     current
       DESCRIPTION
           "Number of received alignment error packets.
           '18446744073709551615' means invalid value."
       ::= { hwEthHistoryStatsEntry 37 }

   hwEthStatsTxCollisionPkts OBJECT-TYPE
       SYNTAX     Counter64
       MAX-ACCESS read-only
       STATUS     current
       DESCRIPTION
           "Number of transmitted collision packets.
           '18446744073709551615' means invalid value."
       ::= { hwEthHistoryStatsEntry 38 }

   hwEthStatsTxSingleCollisionPkts OBJECT-TYPE
       SYNTAX     Counter64
       MAX-ACCESS read-only
       STATUS     current
       DESCRIPTION
           "Number of transmitted single collision packets.
           '18446744073709551615' means invalid value."
       ::= { hwEthHistoryStatsEntry 39 }

   hwEthStatsTxMultipleCollisionPkts OBJECT-TYPE
       SYNTAX     Counter64
       MAX-ACCESS read-only
       STATUS     current
       DESCRIPTION
           "Number of transmitted multiple collision packets.
           '18446744073709551615' means invalid value."
       ::= { hwEthHistoryStatsEntry 40 }

   hwEthStatsDiscardedUndersizedPkts OBJECT-TYPE
       SYNTAX     Counter64
       MAX-ACCESS read-only
       STATUS     current
       DESCRIPTION
           "Number of discarded undersized packets.
           '18446744073709551615' means invalid value."
       ::= { hwEthHistoryStatsEntry 41 }

   hwEthStatsTxUnderSizedPkts OBJECT-TYPE
       SYNTAX     Counter64
       MAX-ACCESS read-only
       STATUS     current
       DESCRIPTION
           "Number of transmitted undersized packets.
           '18446744073709551615' means invalid value."
       ::= { hwEthHistoryStatsEntry 42 }

   hwEthStatsTxFragmentsPkts OBJECT-TYPE
       SYNTAX     Counter64
       MAX-ACCESS read-only
       STATUS     current
       DESCRIPTION
           "Number of transmitted fragment packets.
           '18446744073709551615' means invalid value."
       ::= { hwEthHistoryStatsEntry 43 }

   hwEthStatsTxJabbers OBJECT-TYPE
       SYNTAX     Counter64
       MAX-ACCESS read-only
       STATUS     current
       DESCRIPTION
           "Number of transmitted jabbers packets.
           '18446744073709551615' means invalid value."
       ::= { hwEthHistoryStatsEntry 44 }

   hwEthStatsTxOverSizedPkts OBJECT-TYPE
       SYNTAX     Counter64
       MAX-ACCESS read-only
       STATUS     current
       DESCRIPTION
           "Number of transmitted oversized packets.
           '18446744073709551615' means invalid value."
       ::= { hwEthHistoryStatsEntry 45 }

   hwEthStatsTx64OctetsPkts OBJECT-TYPE
       SYNTAX     Counter64
       MAX-ACCESS read-only
       STATUS     current
       DESCRIPTION
           "Number of transmitted packets(64 octets in length).
           '18446744073709551615' means invalid value."
       ::= { hwEthHistoryStatsEntry 46 }

   hwEthStatsTx65to127OctetsPkts OBJECT-TYPE
       SYNTAX     Counter64
       MAX-ACCESS read-only
       STATUS     current
       DESCRIPTION
           "Number of transmitted packets(65~127 octets in length).
           '18446744073709551615' means invalid value."
       ::= { hwEthHistoryStatsEntry 47 }

   hwEthStatsTx128to255OctetsPkts OBJECT-TYPE
       SYNTAX     Counter64
       MAX-ACCESS read-only
       STATUS     current
       DESCRIPTION
           "Number of transmitted packets(128~255 octets in length).
           '18446744073709551615' means invalid value."
       ::= { hwEthHistoryStatsEntry 48 }

   hwEthStatsTx256to511OctetsPkts OBJECT-TYPE
       SYNTAX     Counter64
       MAX-ACCESS read-only
       STATUS     current
       DESCRIPTION
           "Number of transmitted packets(256~511 octets in length).
           '18446744073709551615' means invalid value."
       ::= { hwEthHistoryStatsEntry 49 }

   hwEthStatsTx512to1023OctetsPkts OBJECT-TYPE
       SYNTAX     Counter64
       MAX-ACCESS read-only
       STATUS     current
       DESCRIPTION
           "Number of transmitted packets(512~1023 octets in length).
           '18446744073709551615' means invalid value."
       ::= { hwEthHistoryStatsEntry 50 }

   hwEthStatsTx1024to1518OctetsPkts OBJECT-TYPE
       SYNTAX     Counter64
       MAX-ACCESS read-only
       STATUS     current
       DESCRIPTION
           "Number of transmitted packets(1024~1518 octets in length).
           '18446744073709551615' means invalid value."
       ::= { hwEthHistoryStatsEntry 51 }

   hwEthStatsTxErrorPkts OBJECT-TYPE
       SYNTAX     Counter64
       MAX-ACCESS read-only
       STATUS     current
       DESCRIPTION
           "Number of transmitted error packets.
           '18446744073709551615' means invalid value."
       ::= { hwEthHistoryStatsEntry 52 }

   hwEthStatsRxErrorPkts OBJECT-TYPE
       SYNTAX     Counter64
       MAX-ACCESS read-only
       STATUS     current
       DESCRIPTION
           "Number of received error packets.
           '18446744073709551615' means invalid value."
       ::= { hwEthHistoryStatsEntry 53 }

   hwEthStatsTxDropPkts OBJECT-TYPE
       SYNTAX     Counter64
       MAX-ACCESS read-only
       STATUS     current
       DESCRIPTION
           "Number of transmitted discarded packets.
           '18446744073709551615' means invalid value."
       ::= { hwEthHistoryStatsEntry 54 }

   hwEthStatsTxCRCErrorPkts OBJECT-TYPE
       SYNTAX     Counter64
       MAX-ACCESS read-only
       STATUS     current
       DESCRIPTION
           "Number of transmitted CRC error packets.
           '18446744073709551615' means invalid value."
       ::= { hwEthHistoryStatsEntry 55 }

   hwEthStatsEfmErroredFrameEvents OBJECT-TYPE
       SYNTAX     Unsigned32
       MAX-ACCESS read-only
       STATUS     current
       DESCRIPTION
           "Number of Efm Errored Frame Events.
           '4294967295' means invalid value."
       ::= { hwEthHistoryStatsEntry 56 }

   hwEthStatsEfmErroredFrameSecondSummaryEvents OBJECT-TYPE
       SYNTAX     Unsigned32
       MAX-ACCESS read-only
       STATUS     current
       DESCRIPTION
           "Number of Efm Errored Frame Second Summary Events.
           '4294967295' means invalid value."
       ::= { hwEthHistoryStatsEntry 57 }

   hwEthStatsEfmErroredFramePeriodEvents OBJECT-TYPE
       SYNTAX     Unsigned32
       MAX-ACCESS read-only
       STATUS     current
       DESCRIPTION
           "Number of Efm Errored Frame Period Events.
           '4294967295' means invalid value."
       ::= { hwEthHistoryStatsEntry 58 }


-- hwEthHistoryStatsAlarmProfTable
   hwEthHistoryStatsAlarmProfTable OBJECT-TYPE
       SYNTAX SEQUENCE OF HwEthHistoryStatsAlarmProfEntry
       MAX-ACCESS not-accessible
       STATUS current
       DESCRIPTION
           "Ethernet Alarm Profile.
            The index of this table is alarm-profile's index, hwEthStatsAlarmProfIndex."
       ::= { hwEthHistoryStats 2 }

   hwEthHistoryStatsAlarmProfEntry OBJECT-TYPE
       SYNTAX HwEthHistoryStatsAlarmProfEntry
       MAX-ACCESS not-accessible
       STATUS current
       DESCRIPTION
           "Ethernet Alarm Profile.
            The index of this entry is alarm-profile's index, hwEthStatsAlarmProfIndex."
       INDEX { hwEthStatsAlarmProfIndex }
       ::= { hwEthHistoryStatsAlarmProfTable 1 }

   HwEthHistoryStatsAlarmProfEntry ::=
       SEQUENCE
       {
           hwEthStatsAlarmProfIndex                  Integer32,
           hwEthStatsAlarmProfName                   OCTET STRING,
           hwEthStatsAlarmTableRefNum                Integer32,
           hwEthAlarmProfRowStatus                   RowStatus,
           hwEthStatsTxPktsThresH                    Unsigned32,
           hwEthStatsTxPktsThresL                    Unsigned32,
           hwEthStatsRxPktsThresH                    Unsigned32,
           hwEthStatsRxPktsThresL                    Unsigned32,
           hwEthStatsTxOctetsThresH                  Unsigned32,
           hwEthStatsTxOctetsThresL                  Unsigned32,
           hwEthStatsRxOctetsThresH                  Unsigned32,
           hwEthStatsRxOctetsThresL                  Unsigned32,
           hwEthStatsTxUnicastPktsThresH             Unsigned32,
           hwEthStatsTxUnicastPktsThresL             Unsigned32,
           hwEthStatsRxUnicastPktsThresH             Unsigned32,
           hwEthStatsRxUnicastPktsThresL             Unsigned32,
           hwEthStatsTxMulticastPktsThresH           Unsigned32,
           hwEthStatsTxMulticastPktsThresL           Unsigned32,
           hwEthStatsRxMulticastPktsThresH           Unsigned32,
           hwEthStatsRxMulticastPktsThresL           Unsigned32,
           hwEthStatsTxBroadcastPktsThresH           Unsigned32,
           hwEthStatsTxBroadcastPktsThresL           Unsigned32,
           hwEthStatsRxBroadcastPktsThresH           Unsigned32,
           hwEthStatsRxBroadcastPktsThresL           Unsigned32,
           hwEthStatsTxPausePktsThresH               Unsigned32,
           hwEthStatsTxPausePktsThresL               Unsigned32,
           hwEthStatsRxAlignErrorsThresH             Unsigned32,
           hwEthStatsRxAlignErrorsThresL             Unsigned32,
           hwEthStatsTxDropPktsThresH                Unsigned32,
           hwEthStatsTxDropPktsThresL                Unsigned32,
           hwEthStatsRxDropEventsThresH              Unsigned32,
           hwEthStatsRxDropEventsThresL              Unsigned32,
           hwEthStatsTxCRCErrorPktsThresH            Unsigned32,
           hwEthStatsTxCRCErrorPktsThresL            Unsigned32,
           hwEthStatsRxCRCAlignErrorsThresH          Unsigned32,
           hwEthStatsRxCRCAlignErrorsThresL          Unsigned32,
           hwEthStatsTxCollisionPktsThresH           Unsigned32,
           hwEthStatsTxCollisionPktsThresL           Unsigned32,
           hwEthStatsTxOversizedPktsThresH           Unsigned32,
           hwEthStatsTxOversizedPktsThresL           Unsigned32,
           hwEthStatsRxOversizePktsThresH            Unsigned32,
           hwEthStatsRxOversizePktsThresL            Unsigned32,
           hwEthStatsSingleCollisionPktsThresH       Unsigned32,
           hwEthStatsSingleCollisionPktsThresL       Unsigned32,
           hwEthStatsMulCollisionPktsThresH          Unsigned32,
           hwEthStatsMulCollisionPktsThresL          Unsigned32,
           hwEthStatsTxUndersizedPktsThresH          Unsigned32,
           hwEthStatsTxUndersizedPktsThresL          Unsigned32,
           hwEthStatsRxDiscardedUndersizedPktsThresH Unsigned32,
           hwEthStatsRxDiscardedUndersizedPktsThresL Unsigned32,
           hwEthStatsTxFragmentsPktsThresH           Unsigned32,
           hwEthStatsTxFragmentsPktsThresL           Unsigned32,
           hwEthStatsRxFragmentsPktsThresH           Unsigned32,
           hwEthStatsRxFragmentsPktsThresL           Unsigned32,
           hwEthStatsTxJabbersThresH                 Unsigned32,
           hwEthStatsTxJabbersThresL                 Unsigned32,
           hwEthStatsRxJabbersThresH                 Unsigned32,
           hwEthStatsRxJabbersThresL                 Unsigned32,
           hwEthStatsTxErrorPktsThresH               Unsigned32,
           hwEthStatsTxErrorPktsThresL               Unsigned32,
           hwEthStatsRxErrorPktsThresH               Unsigned32,
           hwEthStatsRxErrorPktsThresL               Unsigned32,
           hwEthStatsStatusChangeTimesThres          Unsigned32
      }

    hwEthStatsAlarmProfIndex  OBJECT-TYPE
            SYNTAX      Integer32(-1 | 1..16)
            MAX-ACCESS  not-accessible
            STATUS      current
            DESCRIPTION
                "This object identifies a row in this table.
                 There are 16 alarm profiles now, numbered 1 to 16.
                 When the value of hwEthStatsAlarmProfIndex is set to -1 for a profile to be added,
                 the system will automatically assign an index to the profile.
                "
            ::= { hwEthHistoryStatsAlarmProfEntry 1 }

     hwEthStatsAlarmProfName  OBJECT-TYPE
            SYNTAX      OCTET STRING (SIZE(1..32))
            MAX-ACCESS  read-create
            STATUS      current
            DESCRIPTION
                "This object identifies the name of alarm profile."
            ::= { hwEthHistoryStatsAlarmProfEntry 2 }

     hwEthStatsAlarmTableRefNum  OBJECT-TYPE
            SYNTAX      Integer32
            MAX-ACCESS  read-only
            STATUS      current
            DESCRIPTION
                "This object identifies the reference times of alarm profile."
            ::= { hwEthHistoryStatsAlarmProfEntry 3 }

     hwEthAlarmProfRowStatus  OBJECT-TYPE
            SYNTAX      RowStatus
            MAX-ACCESS  read-create
            STATUS      current
            DESCRIPTION
                "This object is used to create a new row or to modify or
                 delete an existing row in this table.

                 Before a profile can be deleted, it must be not
                 referenced by all ports.
                 "
            ::= { hwEthHistoryStatsAlarmProfEntry 4 }

     hwEthStatsTxPktsThresH  OBJECT-TYPE
            SYNTAX      Unsigned32
            MAX-ACCESS  read-create
            STATUS      current
            DESCRIPTION
                "Threshold for high byte of Transmitted frames in statistics performance.
                 When the performance value is higher than this threshold,
                 the system should send an alarm."
            ::= { hwEthHistoryStatsAlarmProfEntry 5 }

     hwEthStatsTxPktsThresL  OBJECT-TYPE
            SYNTAX      Unsigned32
            MAX-ACCESS  read-create
            STATUS      current
            DESCRIPTION
                "Threshold for low byte of Transmitted frames in statistics performance.
                 When the performance value is higher than this threshold,
                 the system should send an alarm."
            ::= { hwEthHistoryStatsAlarmProfEntry 6 }

     hwEthStatsRxPktsThresH  OBJECT-TYPE
            SYNTAX      Unsigned32
            MAX-ACCESS  read-create
            STATUS      current
            DESCRIPTION
                "Threshold for high byte of Received frames in statistics performance.
                 When the performance value is higher than this threshold,
                 the system should send an alarm."
            ::= { hwEthHistoryStatsAlarmProfEntry 7 }

     hwEthStatsRxPktsThresL  OBJECT-TYPE
            SYNTAX      Unsigned32
            MAX-ACCESS  read-create
            STATUS      current
            DESCRIPTION
                "Threshold for low byte of Received frames in statistics performance.
                 When the performance value is higher than this threshold,
                 the system should send an alarm."
            ::= { hwEthHistoryStatsAlarmProfEntry 8 }

     hwEthStatsTxOctetsThresH  OBJECT-TYPE
            SYNTAX      Unsigned32
            MAX-ACCESS  read-create
            STATUS      current
            DESCRIPTION
                "Threshold for high byte of Transmitted Octets in statistics performance.
                 When the performance value is higher than this threshold,
                 the system should send an alarm."
            ::= { hwEthHistoryStatsAlarmProfEntry 9 }

     hwEthStatsTxOctetsThresL  OBJECT-TYPE
            SYNTAX      Unsigned32
            MAX-ACCESS  read-create
            STATUS      current
            DESCRIPTION
                "Threshold for low byte of Transmitted Octets in statistics performance.
                 When the performance value is higher than this threshold,
                 the system should send an alarm."
            ::= { hwEthHistoryStatsAlarmProfEntry 10 }

     hwEthStatsRxOctetsThresH  OBJECT-TYPE
            SYNTAX      Unsigned32
            MAX-ACCESS  read-create
            STATUS      current
            DESCRIPTION
                "Threshold for high byte of Received Octets in statistics performance.
                 When the performance value is higher than this threshold,
                 the system should send an alarm."
            ::= { hwEthHistoryStatsAlarmProfEntry 11 }

     hwEthStatsRxOctetsThresL  OBJECT-TYPE
            SYNTAX      Unsigned32
            MAX-ACCESS  read-create
            STATUS      current
            DESCRIPTION
                "Threshold for low byte of Received Octets in statistics performance.
                 When the performance value is higher than this threshold,
                 the system should send an alarm."
            ::= { hwEthHistoryStatsAlarmProfEntry 12 }

     hwEthStatsTxUnicastPktsThresH  OBJECT-TYPE
            SYNTAX      Unsigned32
            MAX-ACCESS  read-create
            STATUS      current
            DESCRIPTION
                "Threshold for high byte of Transmitted Unicast frames in statistics performance.
                 When the performance value is higher than this threshold,
                 the system should send an alarm."
            ::= { hwEthHistoryStatsAlarmProfEntry 13 }

     hwEthStatsTxUnicastPktsThresL  OBJECT-TYPE
            SYNTAX      Unsigned32
            MAX-ACCESS  read-create
            STATUS      current
            DESCRIPTION
                "Threshold for low byte of Transmitted Unicast frames in statistics performance.
                 When the performance value is higher than this threshold,
                 the system should send an alarm."
            ::= { hwEthHistoryStatsAlarmProfEntry 14 }

     hwEthStatsRxUnicastPktsThresH  OBJECT-TYPE
            SYNTAX      Unsigned32
            MAX-ACCESS  read-create
            STATUS      current
            DESCRIPTION
                "Threshold for high byte of Received Unicast frames in statistics performance.
                 When the performance value is higher than this threshold,
                 the system should send an alarm."
            ::= { hwEthHistoryStatsAlarmProfEntry 15 }

     hwEthStatsRxUnicastPktsThresL  OBJECT-TYPE
            SYNTAX      Unsigned32
            MAX-ACCESS  read-create
            STATUS      current
            DESCRIPTION
                "Threshold for low byte of Received Unicast frames in statistics performance.
                 When the performance value is higher than this threshold,
                 the system should send an alarm."
            ::= { hwEthHistoryStatsAlarmProfEntry 16 }

     hwEthStatsTxMulticastPktsThresH  OBJECT-TYPE
            SYNTAX      Unsigned32
            MAX-ACCESS  read-create
            STATUS      current
            DESCRIPTION
                "Threshold for high byte of Transmitted Multicast frames in statistics performance.
                 When the performance value is higher than this threshold,
                 the system should send an alarm."
            ::= { hwEthHistoryStatsAlarmProfEntry 17 }

     hwEthStatsTxMulticastPktsThresL  OBJECT-TYPE
            SYNTAX      Unsigned32
            MAX-ACCESS  read-create
            STATUS      current
            DESCRIPTION
                "Threshold for low byte of Transmitted Multicast frames in statistics performance.
                 When the performance value is higher than this threshold,
                 the system should send an alarm."
            ::= { hwEthHistoryStatsAlarmProfEntry 18 }

     hwEthStatsRxMulticastPktsThresH  OBJECT-TYPE
            SYNTAX      Unsigned32
            MAX-ACCESS  read-create
            STATUS      current
            DESCRIPTION
                "Threshold for high byte of Received Multicast frames in statistics performance.
                 When the performance value is higher than this threshold,
                 the system should send an alarm."
            ::= { hwEthHistoryStatsAlarmProfEntry 19 }

     hwEthStatsRxMulticastPktsThresL  OBJECT-TYPE
            SYNTAX      Unsigned32
            MAX-ACCESS  read-create
            STATUS      current
            DESCRIPTION
                "Threshold for low byte of Received Multicast frames in statistics performance.
                 When the performance value is higher than this threshold,
                 the system should send an alarm."
            ::= { hwEthHistoryStatsAlarmProfEntry 20 }

     hwEthStatsTxBroadcastPktsThresH  OBJECT-TYPE
            SYNTAX      Unsigned32
            MAX-ACCESS  read-create
            STATUS      current
            DESCRIPTION
                "Threshold for high byte of Transmitted Broadcast frames in statistics performance.
                 When the performance value is higher than this threshold,
                 the system should send an alarm."
            ::= { hwEthHistoryStatsAlarmProfEntry 21 }

     hwEthStatsTxBroadcastPktsThresL  OBJECT-TYPE
            SYNTAX      Unsigned32
            MAX-ACCESS  read-create
            STATUS      current
            DESCRIPTION
                "Threshold for low byte of Transmitted Broadcast frames in statistics performance.
                 When the performance value is higher than this threshold,
                 the system should send an alarm."
            ::= { hwEthHistoryStatsAlarmProfEntry 22 }

     hwEthStatsRxBroadcastPktsThresH  OBJECT-TYPE
            SYNTAX      Unsigned32
            MAX-ACCESS  read-create
            STATUS      current
            DESCRIPTION
                "Threshold for high byte of Received Broadcast frames in statistics performance.
                 When the performance value is higher than this threshold,
                 the system should send an alarm."
            ::= { hwEthHistoryStatsAlarmProfEntry 23 }

     hwEthStatsRxBroadcastPktsThresL  OBJECT-TYPE
            SYNTAX      Unsigned32
            MAX-ACCESS  read-create
            STATUS      current
            DESCRIPTION
                "Threshold for low byte of Received Broadcast frames in statistics performance.
                 When the performance value is higher than this threshold,
                 the system should send an alarm."
            ::= { hwEthHistoryStatsAlarmProfEntry 24 }

     hwEthStatsTxPausePktsThresH  OBJECT-TYPE
            SYNTAX      Unsigned32
            MAX-ACCESS  read-create
            STATUS      current
            DESCRIPTION
                "Threshold for high byte of Transmitted Pause frames in statistics performance.
                 When the performance value is higher than this threshold,
                 the system should send an alarm."
            ::= { hwEthHistoryStatsAlarmProfEntry 25 }

     hwEthStatsTxPausePktsThresL  OBJECT-TYPE
            SYNTAX      Unsigned32
            MAX-ACCESS  read-create
            STATUS      current
            DESCRIPTION
                "Threshold for low byte of Transmitted Pause frames in statistics performance.
                 When the performance value is higher than this threshold,
                 the system should send an alarm."
            ::= { hwEthHistoryStatsAlarmProfEntry 26 }

     hwEthStatsRxAlignErrorsThresH  OBJECT-TYPE
            SYNTAX      Unsigned32
            MAX-ACCESS  read-create
            STATUS      current
            DESCRIPTION
                "Threshold for high byte of Received Alignment Error frames in statistics performance.
                 When the performance value is higher than this threshold,
                 the system should send an alarm."
            ::= { hwEthHistoryStatsAlarmProfEntry 27 }

     hwEthStatsRxAlignErrorsThresL  OBJECT-TYPE
            SYNTAX      Unsigned32
            MAX-ACCESS  read-create
            STATUS      current
            DESCRIPTION
                "Threshold for low byte of Received Alignment Error frames in statistics performance.
                 When the performance value is higher than this threshold,
                 the system should send an alarm."
            ::= { hwEthHistoryStatsAlarmProfEntry 28 }

     hwEthStatsTxDropPktsThresH  OBJECT-TYPE
            SYNTAX      Unsigned32
            MAX-ACCESS  read-create
            STATUS      current
            DESCRIPTION
                "Threshold for high byte of Transmitted Discarded frames in statistics performance.
                 When the performance value is higher than this threshold,
                 the system should send an alarm."
            ::= { hwEthHistoryStatsAlarmProfEntry 29 }

     hwEthStatsTxDropPktsThresL  OBJECT-TYPE
            SYNTAX      Unsigned32
            MAX-ACCESS  read-create
            STATUS      current
            DESCRIPTION
                "Threshold for low byte of Transmitted Discarded frames in statistics performance.
                 When the performance value is higher than this threshold,
                 the system should send an alarm."
            ::= { hwEthHistoryStatsAlarmProfEntry 30 }

     hwEthStatsRxDropEventsThresH  OBJECT-TYPE
            SYNTAX      Unsigned32
            MAX-ACCESS  read-create
            STATUS      current
            DESCRIPTION
                "Threshold for high byte of Received Discarded frames in statistics performance.
                 When the performance value is higher than this threshold,
                 the system should send an alarm."
            ::= { hwEthHistoryStatsAlarmProfEntry 31 }

     hwEthStatsRxDropEventsThresL  OBJECT-TYPE
            SYNTAX      Unsigned32
            MAX-ACCESS  read-create
            STATUS      current
            DESCRIPTION
                "Threshold for low byte of Received Discarded frames in statistics performance.
                 When the performance value is higher than this threshold,
                 the system should send an alarm."
            ::= { hwEthHistoryStatsAlarmProfEntry 32 }

     hwEthStatsTxCRCErrorPktsThresH  OBJECT-TYPE
            SYNTAX      Unsigned32
            MAX-ACCESS  read-create
            STATUS      current
            DESCRIPTION
                "Threshold for high byte of Transmitted CRC error frames in statistics performance.
                 When the performance value is higher than this threshold,
                 the system should send an alarm."
            ::= { hwEthHistoryStatsAlarmProfEntry 33 }

     hwEthStatsTxCRCErrorPktsThresL  OBJECT-TYPE
            SYNTAX      Unsigned32
            MAX-ACCESS  read-create
            STATUS      current
            DESCRIPTION
                "Threshold for low byte of Transmitted CRC error frames in statistics performance.
                 When the performance value is higher than this threshold,
                 the system should send an alarm."
            ::= { hwEthHistoryStatsAlarmProfEntry 34 }

     hwEthStatsRxCRCAlignErrorsThresH  OBJECT-TYPE
            SYNTAX      Unsigned32
            MAX-ACCESS  read-create
            STATUS      current
            DESCRIPTION
                "Threshold for high byte of Received CRC error frames in statistics performance.
                 When the performance value is higher than this threshold,
                 the system should send an alarm."
            ::= { hwEthHistoryStatsAlarmProfEntry 35 }

     hwEthStatsRxCRCAlignErrorsThresL  OBJECT-TYPE
            SYNTAX      Unsigned32
            MAX-ACCESS  read-create
            STATUS      current
            DESCRIPTION
                "Threshold for low byte of Received CRC error frames in statistics performance.
                 When the performance value is higher than this threshold,
                 the system should send an alarm."
            ::= { hwEthHistoryStatsAlarmProfEntry 36 }

     hwEthStatsTxCollisionPktsThresH  OBJECT-TYPE
            SYNTAX      Unsigned32
            MAX-ACCESS  read-create
            STATUS      current
            DESCRIPTION
                "Threshold for high byte of Transmitted Collision frames in statistics performance.
                 When the performance value is higher than this threshold,
                 the system should send an alarm."
            ::= { hwEthHistoryStatsAlarmProfEntry 37 }

     hwEthStatsTxCollisionPktsThresL  OBJECT-TYPE
            SYNTAX      Unsigned32
            MAX-ACCESS  read-create
            STATUS      current
            DESCRIPTION
                "Threshold for low byte of Transmitted Collision frames in statistics performance.
                 When the performance value is higher than this threshold,
                 the system should send an alarm."
            ::= { hwEthHistoryStatsAlarmProfEntry 38 }

     hwEthStatsTxOversizedPktsThresH  OBJECT-TYPE
            SYNTAX      Unsigned32
            MAX-ACCESS  read-create
            STATUS      current
            DESCRIPTION
                "Threshold for high byte of Transmitted Oversize frames in statistics performance.
                 When the performance value is higher than this threshold,
                 the system should send an alarm."
            ::= { hwEthHistoryStatsAlarmProfEntry 39 }

     hwEthStatsTxOversizedPktsThresL  OBJECT-TYPE
            SYNTAX      Unsigned32
            MAX-ACCESS  read-create
            STATUS      current
            DESCRIPTION
                "Threshold for low byte of Transmitted Oversize frames in statistics performance.
                 When the performance value is higher than this threshold,
                 the system should send an alarm."
            ::= { hwEthHistoryStatsAlarmProfEntry 40 }

     hwEthStatsRxOversizePktsThresH  OBJECT-TYPE
            SYNTAX      Unsigned32
            MAX-ACCESS  read-create
            STATUS      current
            DESCRIPTION
                "Threshold for high byte of Received Oversize frames in statistics performance.
                 When the performance value is higher than this threshold,
                 the system should send an alarm."
            ::= { hwEthHistoryStatsAlarmProfEntry 41 }

     hwEthStatsRxOversizePktsThresL  OBJECT-TYPE
            SYNTAX      Unsigned32
            MAX-ACCESS  read-create
            STATUS      current
            DESCRIPTION
                "Threshold for low byte of Received Oversize frames in statistics performance.
                 When the performance value is higher than this threshold,
                 the system should send an alarm."
            ::= { hwEthHistoryStatsAlarmProfEntry 42 }

     hwEthStatsSingleCollisionPktsThresH  OBJECT-TYPE
            SYNTAX      Unsigned32
            MAX-ACCESS  read-create
            STATUS      current
            DESCRIPTION
                "Threshold for high byte of Single Collision frames in statistics performance.
                 When the performance value is higher than this threshold,
                 the system should send an alarm."
            ::= { hwEthHistoryStatsAlarmProfEntry 43 }

     hwEthStatsSingleCollisionPktsThresL  OBJECT-TYPE
            SYNTAX      Unsigned32
            MAX-ACCESS  read-create
            STATUS      current
            DESCRIPTION
                "Threshold for low byte of Single Collision frames in statistics performance.
                 When the performance value is higher than this threshold,
                 the system should send an alarm."
            ::= { hwEthHistoryStatsAlarmProfEntry 44 }

     hwEthStatsMulCollisionPktsThresH  OBJECT-TYPE
            SYNTAX      Unsigned32
            MAX-ACCESS  read-create
            STATUS      current
            DESCRIPTION
                "Threshold for high byte of Multiple Collision frames in statistics performance.
                 When the performance value is higher than this threshold,
                 the system should send an alarm."
            ::= { hwEthHistoryStatsAlarmProfEntry 45 }

     hwEthStatsMulCollisionPktsThresL  OBJECT-TYPE
            SYNTAX      Unsigned32
            MAX-ACCESS  read-create
            STATUS      current
            DESCRIPTION
                "Threshold for low byte of Multiple Collision frames in statistics performance.
                 When the performance value is higher than this threshold,
                 the system should send an alarm."
            ::= { hwEthHistoryStatsAlarmProfEntry 46 }

     hwEthStatsTxUndersizedPktsThresH  OBJECT-TYPE
            SYNTAX      Unsigned32
            MAX-ACCESS  read-create
            STATUS      current
            DESCRIPTION
                "Threshold for high byte of Transmitted Undersized frames in statistics performance.
                 When the performance value is higher than this threshold,
                 the system should send an alarm."
            ::= { hwEthHistoryStatsAlarmProfEntry 47 }

     hwEthStatsTxUndersizedPktsThresL  OBJECT-TYPE
            SYNTAX      Unsigned32
            MAX-ACCESS  read-create
            STATUS      current
            DESCRIPTION
                "Threshold for low byte of Transmitted Undersized frames in statistics performance.
                 When the performance value is higher than this threshold,
                 the system should send an alarm."
            ::= { hwEthHistoryStatsAlarmProfEntry 48 }

     hwEthStatsRxDiscardedUndersizedPktsThresH  OBJECT-TYPE
            SYNTAX      Unsigned32
            MAX-ACCESS  read-create
            STATUS      current
            DESCRIPTION
                "Threshold for high byte of Received Undersized frames in statistics performance.
                 When the performance value is higher than this threshold,
                 the system should send an alarm."
            ::= { hwEthHistoryStatsAlarmProfEntry 49 }

     hwEthStatsRxDiscardedUndersizedPktsThresL  OBJECT-TYPE
            SYNTAX      Unsigned32
            MAX-ACCESS  read-create
            STATUS      current
            DESCRIPTION
                "Threshold for low byte of Received Undersized frames in statistics performance.
                 When the performance value is higher than this threshold,
                 the system should send an alarm."
            ::= { hwEthHistoryStatsAlarmProfEntry 50 }

     hwEthStatsTxFragmentsPktsThresH  OBJECT-TYPE
            SYNTAX      Unsigned32
            MAX-ACCESS  read-create
            STATUS      current
            DESCRIPTION
                "Threshold for high byte of Transmitted Fragment frames in statistics performance.
                 When the performance value is higher than this threshold,
                 the system should send an alarm."
            ::= { hwEthHistoryStatsAlarmProfEntry 51 }

     hwEthStatsTxFragmentsPktsThresL  OBJECT-TYPE
            SYNTAX      Unsigned32
            MAX-ACCESS  read-create
            STATUS      current
            DESCRIPTION
                "Threshold for low byte of Transmitted Fragment frames in statistics performance.
                 When the performance value is higher than this threshold,
                 the system should send an alarm."
            ::= { hwEthHistoryStatsAlarmProfEntry 52 }

     hwEthStatsRxFragmentsPktsThresH  OBJECT-TYPE
            SYNTAX      Unsigned32
            MAX-ACCESS  read-create
            STATUS      current
            DESCRIPTION
                "Threshold for high byte of Received Fragment frames in statistics performance.
                 When the performance value is higher than this threshold,
                 the system should send an alarm."
            ::= { hwEthHistoryStatsAlarmProfEntry 53 }

     hwEthStatsRxFragmentsPktsThresL  OBJECT-TYPE
            SYNTAX      Unsigned32
            MAX-ACCESS  read-create
            STATUS      current
            DESCRIPTION
                "Threshold for low byte of Received Fragment frames in statistics performance.
                 When the performance value is higher than this threshold,
                 the system should send an alarm."
            ::= { hwEthHistoryStatsAlarmProfEntry 54 }

     hwEthStatsTxJabbersThresH  OBJECT-TYPE
            SYNTAX      Unsigned32
            MAX-ACCESS  read-create
            STATUS      current
            DESCRIPTION
                "Threshold for high byte of Transmitted Jabbers frames in statistics performance.
                 When the performance value is higher than this threshold,
                 the system should send an alarm."
            ::= { hwEthHistoryStatsAlarmProfEntry 55 }

     hwEthStatsTxJabbersThresL  OBJECT-TYPE
            SYNTAX      Unsigned32
            MAX-ACCESS  read-create
            STATUS      current
            DESCRIPTION
                "Threshold for low byte of Transmitted Jabbers frames in statistics performance.
                 When the performance value is higher than this threshold,
                 the system should send an alarm."
            ::= { hwEthHistoryStatsAlarmProfEntry 56 }

     hwEthStatsRxJabbersThresH  OBJECT-TYPE
            SYNTAX      Unsigned32
            MAX-ACCESS  read-create
            STATUS      current
            DESCRIPTION
                "Threshold for high byte of Received Jabbers frames in statistics performance.
                 When the performance value is higher than this threshold,
                 the system should send an alarm."
            ::= { hwEthHistoryStatsAlarmProfEntry 57 }

     hwEthStatsRxJabbersThresL  OBJECT-TYPE
            SYNTAX      Unsigned32
            MAX-ACCESS  read-create
            STATUS      current
            DESCRIPTION
                "Threshold for low byte of Received Jabbers frames in statistics performance.
                 When the performance value is higher than this threshold,
                 the system should send an alarm."
            ::= { hwEthHistoryStatsAlarmProfEntry 58 }



     hwEthStatsTxErrorPktsThresH  OBJECT-TYPE
            SYNTAX      Unsigned32
            MAX-ACCESS  read-create
            STATUS      current
            DESCRIPTION
                "Threshold for high byte of Transmitted Error frames in statistics performance.
                 When the performance value is higher than this threshold,
                 the system should send an alarm."
            ::= { hwEthHistoryStatsAlarmProfEntry 59 }

     hwEthStatsTxErrorPktsThresL  OBJECT-TYPE
            SYNTAX      Unsigned32
            MAX-ACCESS  read-create
            STATUS      current
            DESCRIPTION
                "Threshold for low byte of Transmitted Error frames in statistics performance.
                 When the performance value is higher than this threshold,
                 the system should send an alarm."
            ::= { hwEthHistoryStatsAlarmProfEntry 60 }

     hwEthStatsRxErrorPktsThresH  OBJECT-TYPE
            SYNTAX      Unsigned32
            MAX-ACCESS  read-create
            STATUS      current
            DESCRIPTION
                "Threshold for high byte of Received Error frames in statistics performance.
                 When the performance value is higher than this threshold,
                 the system should send an alarm."
            ::= { hwEthHistoryStatsAlarmProfEntry 61 }

     hwEthStatsRxErrorPktsThresL  OBJECT-TYPE
            SYNTAX      Unsigned32
            MAX-ACCESS  read-create
            STATUS      current
            DESCRIPTION
                "Threshold for low byte of Received Error frames in statistics performance.
                 When the performance value is higher than this threshold,
                 the system should send an alarm."
            ::= { hwEthHistoryStatsAlarmProfEntry 62 }

     hwEthStatsStatusChangeTimesThres  OBJECT-TYPE
            SYNTAX      Unsigned32
            MAX-ACCESS  read-create
            STATUS      current
            DESCRIPTION
                "Threshold of Status Change times in statistics performance.
                 When the performance value is higher than this threshold,
                 the system should send an alarm."
            ::= { hwEthHistoryStatsAlarmProfEntry 63 }

-- hwDynamicMacQuery
   HwDynamicMacQueryPara ::= TEXTUAL-CONVENTION
       STATUS       current
       DESCRIPTION
       "reserved parameter."
       SYNTAX       Integer32

   HwDynamicMacQueryType ::= TEXTUAL-CONVENTION
       STATUS       current
       DESCRIPTION
           "the value is querying index; if no index, th value is -1."
       SYNTAX INTEGER
           {
           eponOntPortInSpecVlan(1)
           }

   hwDynamicMacQueryTable OBJECT-TYPE
       SYNTAX SEQUENCE OF HwDynamicMacQueryEntry
       MAX-ACCESS not-accessible
       STATUS current
       DESCRIPTION
           "Query Dynamic MAC address.
            The indexes of this table are ifIndex, hwDynamicMacVlanId, hwDynamicMacIndex, hwDynamicMacQueryType,
            hwDynamicMacQueryPara0, hwDynamicMacQueryPara1, hwDynamicMacQueryPara2, hwDynamicMacQueryPara3.
           "
       ::= { hwEthernetPort 17 }

   hwDynamicMacQueryEntry OBJECT-TYPE
       SYNTAX HwDynamicMacQueryEntry
       MAX-ACCESS not-accessible
       STATUS current
       DESCRIPTION
           "Query Dynamic MAC address.
            The indexes of this entry are ifIndex, hwDynamicMacVlanId, hwDynamicMacIndex, hwDynamicMacQueryType,
            hwDynamicMacQueryPara0, hwDynamicMacQueryPara1, hwDynamicMacQueryPara2, hwDynamicMacQueryPara3.
           "
       INDEX { ifIndex, hwDynamicMacVlanId, hwDynamicMacIndex,
                hwDynamicMacQueryType,
                hwDynamicMacQueryPara0,
                hwDynamicMacQueryPara1,
                hwDynamicMacQueryPara2,
                hwDynamicMacQueryPara3
             }
       ::= { hwDynamicMacQueryTable 1 }

   HwDynamicMacQueryEntry ::=
       SEQUENCE {
               hwDynamicMacQueryType
                 HwDynamicMacQueryType,
               hwDynamicMacQueryPara0
                 HwDynamicMacQueryPara,
               hwDynamicMacQueryPara1
                 HwDynamicMacQueryPara,
               hwDynamicMacQueryPara2
                 HwDynamicMacQueryPara,
               hwDynamicMacQueryPara3
                 HwDynamicMacQueryPara,
               hwExtDynamicMacAddr
                 OCTET STRING
       }

   hwDynamicMacQueryType   OBJECT-TYPE
       SYNTAX HwDynamicMacQueryType
       MAX-ACCESS read-only
       STATUS current
       DESCRIPTION
           "query type. "
       ::= { hwDynamicMacQueryEntry 1 }

   hwDynamicMacQueryPara0   OBJECT-TYPE
       SYNTAX HwDynamicMacQueryPara
       MAX-ACCESS read-only
       STATUS current
       DESCRIPTION
           "The First reserved Parameter of HwDynamicMacQueryEntry. "
       ::= { hwDynamicMacQueryEntry 2 }

       hwDynamicMacQueryPara1   OBJECT-TYPE
       SYNTAX HwDynamicMacQueryPara
       MAX-ACCESS read-only
       STATUS current
       DESCRIPTION
           "The Second reserved Parameter of HwDynamicMacQueryEntry. "
       ::= { hwDynamicMacQueryEntry 3 }

   hwDynamicMacQueryPara2   OBJECT-TYPE
       SYNTAX HwDynamicMacQueryPara
       MAX-ACCESS read-only
       STATUS current
       DESCRIPTION
           "The Third reserved Parameter of HwDynamicMacQueryEntry. "
       ::= { hwDynamicMacQueryEntry 4 }

   hwDynamicMacQueryPara3   OBJECT-TYPE
       SYNTAX HwDynamicMacQueryPara
       MAX-ACCESS read-only
       STATUS current
       DESCRIPTION
           "The Fourth reserved Parameter of HwDynamicMacQueryEntry. "
       ::= { hwDynamicMacQueryEntry 5 }

   hwExtDynamicMacAddr   OBJECT-TYPE
       SYNTAX OCTET STRING
       MAX-ACCESS read-only
       STATUS current
       DESCRIPTION
           "Five mac addresses, and its format is (XX-XX-XX-XX-XX-XX)* . "
       ::= { hwDynamicMacQueryEntry 6 }

-- hwUniServiceDataQueryTable
   hwUniServiceDataQueryTable OBJECT-TYPE
       SYNTAX SEQUENCE OF HwUniServiceDataQueryEntry
       MAX-ACCESS not-accessible
       STATUS current
       DESCRIPTION
           "The hwUniServiceDataQueryTable is used for querying the service flow configuration of xDSL port.
            This table supports to query bind IP, static MAC, igmp user and service flow.
            The indexes of this table are ifIndex, hwUniServiceDataType, hwUniServiceDataIndex1 and hwUniServiceDataIndex2.
           "
       ::= { hwEthernetPort 18 }

   hwUniServiceDataQueryEntry OBJECT-TYPE
       SYNTAX HwUniServiceDataQueryEntry
       MAX-ACCESS not-accessible
       STATUS current
       DESCRIPTION
           "The hwUniServiceDataQueryTable is used for querying the service flow configuration of xDSL port.
            This table supports to query bind IP, static MAC, igmp user and service flow.
            The indexes of this entry are ifIndex, hwUniServiceDataType, hwUniServiceDataIndex1 and hwUniServiceDataIndex2.
            "
       INDEX { ifIndex,
               hwUniServiceDataType,
               hwUniServiceDataIndex1,
               hwUniServiceDataIndex2
             }
       ::= { hwUniServiceDataQueryTable 1 }

   HwUniServiceDataQueryEntry ::=
       SEQUENCE {
               hwUniServiceDataType
                 Integer32,
               hwUniServiceDataIndex1
                 Integer32,
               hwUniServiceDataIndex2
                 Integer32,
               hwUniServiceDataEntryStatus
                 RowStatus
       }

   hwUniServiceDataType   OBJECT-TYPE
       SYNTAX Integer32
       MAX-ACCESS not-accessible
       STATUS current
       DESCRIPTION
           "The type of the query information:
            1 means querying static IP which is bound on the service flow.
            2 means querying static MAC which is bound on the service flow.
            3 means querying igmp user which is bound on the service flow.
            4 means querying service flow in the current xDSL port.
           "
       ::= { hwUniServiceDataQueryEntry 1 }

   hwUniServiceDataIndex1   OBJECT-TYPE
       SYNTAX Integer32
       MAX-ACCESS not-accessible
       STATUS current
       DESCRIPTION
           "The meaning is variable with the value of hwUniServiceDataType:
            if hwUniServiceDataType equals 1(querying static IP),
            this parameter indicates the service flow ID of the static IP.
            if hwUniServiceDataType equals 2(querying static MAC),
            this parameter indicates the service flow ID of the static MAC.
            if hwUniServiceDataType equals 3(querying igmp user),
            this parameter indicates the service flow ID of the igmp user ID.
            if hwUniServiceDataType equals 4(querying service flow),
            this parameter indicates the service flow ID.
           "
       ::= { hwUniServiceDataQueryEntry 2 }

   hwUniServiceDataIndex2   OBJECT-TYPE
       SYNTAX Integer32
       MAX-ACCESS not-accessible
       STATUS current
       DESCRIPTION
           "The meaning is variable with the value of hwUniServiceDataType:
            if hwUniServiceDataType equals 1(querying static IP), this parameter indicates the index of the static IP.
            if hwUniServiceDataType equals 2(querying static MAC), this parameter indicates the index of the static MAC.
            if hwUniServiceDataType equals 3(querying igmp user), this parameter indicates the index of the igmp user ID.
            if hwUniServiceDataType equals 4(querying service flow), this parameter is invalid.
           "
       ::= { hwUniServiceDataQueryEntry 3 }

   hwUniServiceDataEntryStatus   OBJECT-TYPE
       SYNTAX RowStatus
       MAX-ACCESS read-create
       STATUS current
       DESCRIPTION
           "Used to query the status of the query operation.
            It is read-only and the value active(1) is always returned.
            Options:
            1. active(1) -indicates the query operation
           "
       ::= { hwUniServiceDataQueryEntry 4 }

   hwVlanIsolateState  OBJECT-TYPE
       SYNTAX INTEGER
           {
           enable(1),disable(2)
           }
       MAX-ACCESS read-write
       STATUS current
       DESCRIPTION
           "VlAN isolate state.
            Options:
            1. enable(1)  -indicates the VLAN isolate state is enable
            2. disable(2) -indicates the VLAN isolate state is disable
           "
       ::= { hwEthernetPort 19 }

-- hwCtpEthAttributeCfgTable
   hwCtpEthAttributeCfgTable  OBJECT-TYPE
       SYNTAX      SEQUENCE  OF  HwCtpEthAttributeCfgEntry
       MAX-ACCESS  not-accessible
       STATUS      current
       DESCRIPTION
           "Indicates the CTP_ETH port attribute configuration. The index of this table is ifIndex.
           "
       ::= { hwEthernetPort 20 }

   hwCtpEthAttributeCfgEntry  OBJECT-TYPE
       SYNTAX      HwCtpEthAttributeCfgEntry
       MAX-ACCESS  not-accessible
       STATUS      current
       DESCRIPTION
           "Indicates the CTP_ETH port attribute configuration. The index of this entry is ifIndex.
           "
       INDEX  { ifIndex }
       ::= { hwCtpEthAttributeCfgTable 1 }

   HwCtpEthAttributeCfgEntry  ::=
       SEQUENCE
           {
           hwTrafficSuppressBroadcast
             Integer32,
           hwTrafficSuppressMulticast
             Integer32,
           hwTrafficSuppressUnknowncast
             Integer32,
           hwCtpEthJumboFrameEnable
             INTEGER,
           hwTrafficSuppressRateBroadcast
             Integer32,
           hwTrafficSuppressRateMulticast
             Integer32,
           hwTrafficSuppressRateUnknowncast
             Integer32
           }

   hwTrafficSuppressBroadcast OBJECT-TYPE
       SYNTAX Integer32 (-1..13)
       MAX-ACCESS read-write
       STATUS current
       DESCRIPTION
           "This object is used to set broadcast traffic suppression on a port.
            Range: -1,0-13
            13 indicates full-suppression of traffic, and 0 indicates no traffic suppression.
            -1 indicates invalid value.
            The suppression levels and corresponding bandwidth ranges are listed as follows:
            ---------------------------------------------------------------
            NO. Min bandwidth(kbps) Max bandwidth(kbps) Package number(pps)
            ---------------------------------------------------------------
              0      Not suppressed      Not suppressed      Not suppressed
              1                   6                 145                  12
              2                  12                 291                  24
              3                  24                 582                  48
              4                  48                1153                  95
              5                  97                2319                 191
              6                 195                4639                 382
              7                 390                9265                 763
              8                 781               18531                1526
              9                1562               37063                3052
             10                3125               74126                6104
             11                6249              148241               12207
             12               12499              296483               24414
             13                   0                   0                   0
            ---------------------------------------------------------------
            Default: 7
           "
       ::= { hwCtpEthAttributeCfgEntry 1 }

   hwTrafficSuppressMulticast OBJECT-TYPE
       SYNTAX Integer32 (-1..13)
       MAX-ACCESS read-write
       STATUS current
       DESCRIPTION
           "This object is used to set unknown multicast traffic suppression on a port.
            Range: -1,0-13
            13 indicates full-suppression of traffic, and 0 indicates no traffic suppression. -1 indicates invalid value.
            The suppression levels and corresponding bandwidth ranges are listed as follows:
            ---------------------------------------------------------------
            NO. Min bandwidth(kbps) Max bandwidth(kbps) Package number(pps)
            ---------------------------------------------------------------
              0      Not suppressed      Not suppressed      Not suppressed
              1                   6                 145                  12
              2                  12                 291                  24
              3                  24                 582                  48
              4                  48                1153                  95
              5                  97                2319                 191
              6                 195                4639                 382
              7                 390                9265                 763
              8                 781               18531                1526
              9                1562               37063                3052
             10                3125               74126                6104
             11                6249              148241               12207
             12               12499              296483               24414
             13                   0                   0                   0
            ---------------------------------------------------------------
            Default: 7
           "
       ::= { hwCtpEthAttributeCfgEntry 2 }

   hwTrafficSuppressUnknowncast OBJECT-TYPE
       SYNTAX Integer32 (-1..13)
       MAX-ACCESS read-write
       STATUS current
       DESCRIPTION
           "This object is used to set unknown unicast traffic suppression on a port.
            Range: -1,0-13
            13 indicates full-suppression of traffic, and 0 indicates no traffic suppression. -1 indicates invalid value.
            The suppression levels and corresponding bandwidth ranges are listed as follows:
            ---------------------------------------------------------------
            NO. Min bandwidth(kbps) Max bandwidth(kbps) Package number(pps)
            ---------------------------------------------------------------
              0      Not suppressed      Not suppressed      Not suppressed
              1                   6                 145                  12
              2                  12                 291                  24
              3                  24                 582                  48
              4                  48                1153                  95
              5                  97                2319                 191
              6                 195                4639                 382
              7                 390                9265                 763
              8                 781               18531                1526
              9                1562               37063                3052
             10                3125               74126                6104
             11                6249              148241               12207
             12               12499              296483               24414
             13                   0                   0                   0
            ---------------------------------------------------------------
            Default: 7
           "
       ::= { hwCtpEthAttributeCfgEntry 3 }

   hwCtpEthJumboFrameEnable OBJECT-TYPE
      SYNTAX INTEGER
          {
          invalid(-1),
          enabled(1),
          disabled(2)
          }
      MAX-ACCESS read-write
      STATUS current
      DESCRIPTION
          "This object is used to enable and disable jumbo frames.
           This object does not support binding and issuance of the entire table.
	       When the carriers' servers need to exchange a large amount of data with their devices,
           operate this object to enable jumbo frames.
           After the operation is executed successfully,
           the corresponding port on the control board can transparently transmit the frames whose size is between 1600 bytes and 9216 bytes.
           By default, the ports disable jumbo frames.
           Options:
           1. invalid(-1) -invalid
           2. enabled(1)  -enable the jumbo frames
           3. disabled(2) -disable the jumbo frames
           Default: disable(2)
          "
       ::= { hwCtpEthAttributeCfgEntry 4 }


   hwTrafficSuppressRateBroadcast OBJECT-TYPE
       SYNTAX Integer32 (-1..24414)
       MAX-ACCESS read-write
       STATUS current
       DESCRIPTION
           "This object is used to set broadcast traffic suppression on a port.
            Range: -1,0-24414
            Unit: pps.
            -1 indicates indicates no configuration.
           "
       ::= { hwCtpEthAttributeCfgEntry 5 }

   hwTrafficSuppressRateMulticast OBJECT-TYPE
       SYNTAX Integer32 (-1..24414)
       MAX-ACCESS read-write
       STATUS current
       DESCRIPTION
           "This object is used to set unknown multicast traffic suppression on a port.
            Range: -1,0-24414
            Unit: pps.
            -1 indicates indicates no configuration.
           "
       ::= { hwCtpEthAttributeCfgEntry 6 }

   hwTrafficSuppressRateUnknowncast OBJECT-TYPE
       SYNTAX Integer32 (-1..24414)
       MAX-ACCESS read-write
       STATUS current
       DESCRIPTION
           "This object is used to set unknown unicast traffic suppression on a port.
            Range: -1,0-24414
            Unit: pps.
            -1 indicates indicates no configuration.
           "
       ::= { hwCtpEthAttributeCfgEntry 7 }

   hwGlobalStatisticOper  OBJECT-TYPE
       SYNTAX INTEGER
           {
           startup(1)
           }
       MAX-ACCESS read-write
       STATUS current
       DESCRIPTION
           "Query global statistics.
            Options:
            1. startup(1)  -enable global statistics
           "
       ::= { hwEthernetPort 21 }


   hwEthernetTrapsVbOids OBJECT IDENTIFIER ::= { hwEthernetPort 22 }

   hwIpdslamQryConditionFlowBundleIndex OBJECT-TYPE
       SYNTAX Integer32
       MAX-ACCESS accessible-for-notify
       STATUS current
       DESCRIPTION
           "Service flow bundle Index"
       ::= {  hwEthernetTrapsVbOids 1 }

   hwActivedXdslPortNum  OBJECT-TYPE
       SYNTAX Counter32
       MAX-ACCESS accessible-for-notify
       STATUS current
       DESCRIPTION
           "port of active XDSL"
       ::= { hwEthernetTrapsVbOids 2 }

   hwActivedOntNum  OBJECT-TYPE
       SYNTAX Counter32
       MAX-ACCESS accessible-for-notify
       STATUS current
       DESCRIPTION
           "Number of active ONTs"
       ::= { hwEthernetTrapsVbOids 3 }


   hwActivedEthPortNum  OBJECT-TYPE
       SYNTAX Counter32
       MAX-ACCESS accessible-for-notify
       STATUS current
       DESCRIPTION
           "online Ethernet port"
       ::= { hwEthernetTrapsVbOids 4 }


   hwUplinkPortUpKbps  OBJECT-TYPE
       SYNTAX Counter32
       MAX-ACCESS accessible-for-notify
       STATUS current
       DESCRIPTION
           "flow quantity of up-port upload"
       ::= { hwEthernetTrapsVbOids 5 }

   hwUplinkPortDownKbps  OBJECT-TYPE
       SYNTAX Counter32
       MAX-ACCESS accessible-for-notify
       STATUS current
       DESCRIPTION
           "flow quantity of up-port download"
       ::= { hwEthernetTrapsVbOids 6 }

   hwUplinkPortUpBandwidthOccupancyRate  OBJECT-TYPE
       SYNTAX Counter32
       MAX-ACCESS accessible-for-notify
       STATUS current
       DESCRIPTION
           "Rate of up-port up bandwidth"
       ::= { hwEthernetTrapsVbOids 7 }

   hwUplinkPortDownBandwidthOccupancyRate  OBJECT-TYPE
       SYNTAX Counter32
       MAX-ACCESS accessible-for-notify
       STATUS current
       DESCRIPTION
           "Rate of up-port down bandwidth"
       ::= { hwEthernetTrapsVbOids 8 }

   hwXponUniPortUpKbps  OBJECT-TYPE
       SYNTAX Counter32
       MAX-ACCESS accessible-for-notify
       STATUS current
       DESCRIPTION
           "Flow quantity of XPON user-port upload"
       ::= { hwEthernetTrapsVbOids 9 }

   hwXponUniPortDownKbps  OBJECT-TYPE
       SYNTAX Counter32
       MAX-ACCESS accessible-for-notify
       STATUS current
       DESCRIPTION
           "Flow quantity of XPON user-port download"
       ::= { hwEthernetTrapsVbOids 10 }

   hwUpLinkPortMCastUpPercent  OBJECT-TYPE
       SYNTAX Counter32
       MAX-ACCESS accessible-for-notify
       STATUS current
       DESCRIPTION
           "Rate of up-port multicast bandwidth."
       ::= { hwEthernetTrapsVbOids 11}

   hwUpLinkPortBCastUpPercent  OBJECT-TYPE
       SYNTAX Counter32
       MAX-ACCESS accessible-for-notify
       STATUS current
       DESCRIPTION
           "Rate of up-port broadcast bandwidth."
       ::= { hwEthernetTrapsVbOids 12 }

   hwUpLinkPortUCastUpPercent  OBJECT-TYPE
       SYNTAX Counter32
       MAX-ACCESS accessible-for-notify
       STATUS current
       DESCRIPTION
           "Rate of up-port up unicast"
       ::= { hwEthernetTrapsVbOids 13 }

   hwUpLinkPortMCastDownPercent  OBJECT-TYPE
       SYNTAX Counter32
       MAX-ACCESS accessible-for-notify
       STATUS current
       DESCRIPTION
           "Rate of up-port down multicast bandwidth"
       ::= { hwEthernetTrapsVbOids 14 }

   hwUpLinkPortBCastDownPercent  OBJECT-TYPE
       SYNTAX Counter32
       MAX-ACCESS accessible-for-notify
       STATUS current
       DESCRIPTION
           "Rate of Up port down broadcast bandwidth "
       ::= { hwEthernetTrapsVbOids 15 }

   hwUpLinkPortUCastDownPercent  OBJECT-TYPE
       SYNTAX Counter32
       MAX-ACCESS accessible-for-notify
       STATUS current
       DESCRIPTION
           "Rate of Up port down unicast bandwidth "
       ::= { hwEthernetTrapsVbOids 16 }

   hwConflictMacAddress OBJECT-TYPE
       SYNTAX MacAddress
       MAX-ACCESS accessible-for-notify
       STATUS current
       DESCRIPTION
           "The source MAC address.
           "
       ::= { hwEthernetTrapsVbOids 17  }

   hwIpTrafficParamChangeCause OBJECT-TYPE
       SYNTAX INTEGER
           {
           addIpTrafficProfile(1),
           modifyIpTrafficProfile(2),
           delIpTrafficProfile(3)
           }
       MAX-ACCESS accessible-for-notify
       STATUS current
       DESCRIPTION
           "The change cause of IP traffic profile change trap.
            Options:
            1. addIpTrafficProfile(1)    -add an IP traffic profile
            2. modifyIpTrafficProfile(2) -modify the IP traffic profile
            3. delIpTrafficProfile(3)    -delete the IP traffic profile
           "
       ::= { hwEthernetTrapsVbOids 18  }

   hwIpTrafficParamPriority OBJECT-TYPE
       SYNTAX Integer32
       MAX-ACCESS accessible-for-notify
       STATUS current
       DESCRIPTION
           "Indicate the outer priority. Equal to the lower 16 bits of the value of hwIpTrafficPriority.
            Range: 0-7
           "
       ::= { hwEthernetTrapsVbOids 19  }

   hwIpTrafficParamPriorityMappingPolicy OBJECT-TYPE
       SYNTAX Integer32
       MAX-ACCESS accessible-for-notify
       STATUS current
       DESCRIPTION
           "Indicate the outer priority mapping policy. Equal to the higher 16 bits of the value of hwIpTrafficPriority.
            Outer priority mapping policy:
            0xFF (specified priority), 0xFE (priority mapped from the outer CoS field on the ingress),
            0xFD (priority copied from the ToS field), 0xFC (priority mapped from the inner CoS field on the ingress),
            0xFB (priority mapped from the packet DSCP field on the ingress).
           "
       ::= { hwEthernetTrapsVbOids 20  }

   hwIpdslamQryConditionPwIndex OBJECT-TYPE
       SYNTAX Unsigned32
       MAX-ACCESS accessible-for-notify
       STATUS current
       DESCRIPTION
           "Pw Index"
       ::= {  hwEthernetTrapsVbOids 21 }

   hwEthPMThresholdItem OBJECT-TYPE
       SYNTAX OCTET STRING (SIZE (0..1024))
       MAX-ACCESS accessible-for-notify
       STATUS current
       DESCRIPTION
           "Indicate the performance statistics threshold item."
       ::= { hwEthernetTrapsVbOids 22 }

   hwEthPMCurrentValue OBJECT-TYPE
       SYNTAX Counter64
       MAX-ACCESS accessible-for-notify
       STATUS current
       DESCRIPTION
           "Indicate the current performance statistics value of the threshold item."
       ::= { hwEthernetTrapsVbOids 23 }

   hwEthPMThresholdValue OBJECT-TYPE
       SYNTAX Counter64
       MAX-ACCESS accessible-for-notify
       STATUS current
       DESCRIPTION
           "Indicate the threshold value."
       ::= { hwEthernetTrapsVbOids 24 }

    hwIpdslamQryConditionOntId OBJECT-TYPE
       SYNTAX Integer32
       MAX-ACCESS accessible-for-notify
       STATUS current
       DESCRIPTION
           "Indicate the ONT ID."
       ::= { hwEthernetTrapsVbOids 25 }

--hwPacketAttackTrap begin

   hwPacketAttackMACAddress OBJECT-TYPE
       SYNTAX OCTET STRING (SIZE (0..17))
       MAX-ACCESS accessible-for-notify
       STATUS current
       DESCRIPTION
           "The MAC address.
           "
       ::= { hwEthernetTrapsVbOids 26  }

    hwPacketNumberOfMACAddress OBJECT-TYPE
       SYNTAX Integer32
       MAX-ACCESS accessible-for-notify
       STATUS current
       DESCRIPTION
           "packet number."
       ::= { hwEthernetTrapsVbOids 27 }

    hwPacketAttackPacketType OBJECT-TYPE
       SYNTAX OCTET STRING (SIZE (0..20))
       MAX-ACCESS accessible-for-notify
       STATUS current
       DESCRIPTION
           "packet type."
       ::= { hwEthernetTrapsVbOids 28 }

    hwPacketNumberOfPacketType OBJECT-TYPE
       SYNTAX Integer32
       MAX-ACCESS accessible-for-notify
       STATUS current
       DESCRIPTION
           "packet number."
       ::= { hwEthernetTrapsVbOids 29 }

--hwPacketAttackTrap end

-- hwExtDefaultPolicy
   hwExtDefaultPolicy OBJECT IDENTIFIER ::= { hwEthernetPort 23 }

   hwExtDefaultFlowUnknownMCast OBJECT-TYPE
       SYNTAX INTEGER
           {
           transparent(1),
           discard(2)
           }
       MAX-ACCESS read-write
       STATUS current
       DESCRIPTION
           "Used for setting or querying the default unknown multicast policy of the service flows.
            Options:
            1. transparent(1)     -Indicates the default unknown multicast packet forwarding policy of service flows is transparent.
            2. discard(2)         -Indicates the default unknown multicast packet forwarding policy of service flows is discard.
            Default: discard(2)
            To set the default unknown multicast packet forwarding policy of service flows, the following
            requirements and restrictions must be met:
            This leaf is used for setting the default control policy of the service flows.
            The set values serve as the default control policy of the newly-created service flows.
            Such settings are valid only for the newly-created service flows, and the control policy of the
            existing service flows in the system is not changed.
            For example, if hwExtDefaultFlowUnknownMCast is set to transparent transmission, the control policy
            of the unknown multicast packets for the newly-created service flow is automatically set the transparent
            transmission, and the existing service flows in the system are not affected.
           "
       ::= { hwExtDefaultPolicy 1 }

   hwExtDefaultFlowDhcpOption82PermitForwarding OBJECT-TYPE
       SYNTAX INTEGER
           {
           enable(1),
           disable(2)
           }
       MAX-ACCESS read-write
       STATUS current
       DESCRIPTION
           "Used for setting and querying the default DHCP option82 transparent transmission switch of the service flow.
            Options:
            1. enable(1)        -Indicates the default DHCP option82 transparent transmission switch is enabled.
            2. disable(2)       -Indicates the default DHCP option82 transparent transmission switch is disabled.
            Default: disable(2)
            The following requirements and restrictions are posed on setting the default option82 transparent transmission
            switch of the DHCP option82 service flow:
            This leaf is used for setting the default control policy of the service flow.
            The set value serves as the default control policy of the newly-created service flow.
            The setting is valid only for the newly-created service flow, and the control policy of the existing service flows
            in the system is not modified.
           "
       ::= { hwExtDefaultPolicy 2 }

   hwExtDefaultPortEfmOamAdminStatus OBJECT-TYPE
       SYNTAX INTEGER
           {
           enable(1),
           disable(2)
           }
       MAX-ACCESS read-write
       STATUS current
       DESCRIPTION
           "Used for setting or querying the default EFM OAM admin status of the port.
            Options:
            1. enable(1)        -Indicates the default EFM OAM admin status is enabled.
            2. disable(2)       -Indicates the default EFM OAM admin status is disabled.
            Default: disable(2)
            This leaf is used for setting the default EFM OAM admin status of the port.
            The set value serves as the default EFM OAM admin status of the newly-created port.
            The setting is valid only for the newly-created port, and the EFM OAM admin status of the existing port
            in the system is not modified.
           "
       ::= { hwExtDefaultPolicy 3 }

-- hwXdslEtherStatsTable
   hwXdslEtherStatsTable OBJECT-TYPE
       SYNTAX SEQUENCE OF HwXdslEtherStatsEntry
       MAX-ACCESS not-accessible
       STATUS current
       DESCRIPTION
           "Statistics of xdsl port query table.
           The index of this table is ifIndex."
       ::= { hwEthernetPort 24 }

   hwXdslEtherStatsEntry OBJECT-TYPE
       SYNTAX HwXdslEtherStatsEntry
       MAX-ACCESS not-accessible
       STATUS current
       DESCRIPTION
           "Statistics of xdsl port query table.
           The index of this entry is ifIndex."
       INDEX { ifIndex                  }
       ::= { hwXdslEtherStatsTable 1 }

   HwXdslEtherStatsEntry ::=
       SEQUENCE {
               hwXdslEtherStatsInAllPkts
                   Counter64,
               hwXdslEtherStatsInUcastPkts
                   Counter64,
               hwXdslEtherStatsInMcastPkts
                   Counter64,
               hwXdslEtherStatsInBcastPkts
                   Counter64,
               hwXdslEtherStatsInAllOctets
                   Counter64,
               hwXdslEtherStatsInUcastOctets
                   Counter64,
               hwXdslEtherStatsInMcastOctets
                   Counter64,
               hwXdslEtherStatsInBcastOctets
                   Counter64,
               hwXdslEtherStatsOutAllPkts
                   Counter64,
               hwXdslEtherStatsOutUcastPkts
                   Counter64,
               hwXdslEtherStatsOutMcastPkts
                   Counter64,
               hwXdslEtherStatsOutBcastPkts
                   Counter64,
               hwXdslEtherStatsOutAllOctets
                   Counter64,
               hwXdslEtherStatsOutUcastOctets
                   Counter64,
               hwXdslEtherStatsOutMcastOctets
                   Counter64,
               hwXdslEtherStatsOutBcastOctets
                   Counter64
       }

   hwXdslEtherStatsInAllPkts   OBJECT-TYPE
       SYNTAX Counter64
       MAX-ACCESS read-only
       STATUS current
       DESCRIPTION
           " Number of received packets. "
       ::= { hwXdslEtherStatsEntry 1 }

   hwXdslEtherStatsInUcastPkts   OBJECT-TYPE
       SYNTAX Counter64
       MAX-ACCESS read-only
       STATUS current
       DESCRIPTION
           " Number of received unicast packets. "
       ::= { hwXdslEtherStatsEntry 2 }

   hwXdslEtherStatsInMcastPkts   OBJECT-TYPE
       SYNTAX Counter64
       MAX-ACCESS read-only
       STATUS current
       DESCRIPTION
           " Number of received multicast packets. "
       ::= { hwXdslEtherStatsEntry 3 }

   hwXdslEtherStatsInBcastPkts   OBJECT-TYPE
       SYNTAX Counter64
       MAX-ACCESS read-only
       STATUS current
       DESCRIPTION
           " Number of received broadcast packets. "
       ::= { hwXdslEtherStatsEntry 4 }

   hwXdslEtherStatsInAllOctets   OBJECT-TYPE
       SYNTAX Counter64
       MAX-ACCESS read-only
       STATUS current
       DESCRIPTION
           " Number of received octet. "
       ::= { hwXdslEtherStatsEntry 5 }

   hwXdslEtherStatsInUcastOctets   OBJECT-TYPE
       SYNTAX Counter64
       MAX-ACCESS read-only
       STATUS current
       DESCRIPTION
           " Number of received unicast octet. "
       ::= { hwXdslEtherStatsEntry 6 }

   hwXdslEtherStatsInMcastOctets   OBJECT-TYPE
       SYNTAX Counter64
       MAX-ACCESS read-only
       STATUS current
       DESCRIPTION
           " Number of received multicast octet. "
       ::= { hwXdslEtherStatsEntry 7 }

   hwXdslEtherStatsInBcastOctets   OBJECT-TYPE
       SYNTAX Counter64
       MAX-ACCESS read-only
       STATUS current
       DESCRIPTION
           " Number of received broadcast octet. "
       ::= { hwXdslEtherStatsEntry 8 }

   hwXdslEtherStatsOutAllPkts   OBJECT-TYPE
      SYNTAX Counter64
      MAX-ACCESS read-only
      STATUS current
      DESCRIPTION
          " Number of transmitted packets. "
      ::= { hwXdslEtherStatsEntry 9 }

        hwXdslEtherStatsOutUcastPkts   OBJECT-TYPE
            SYNTAX Counter64
            MAX-ACCESS read-only
            STATUS current
            DESCRIPTION
                " Number of transmitted unicast packets. "
            ::= { hwXdslEtherStatsEntry 10 }

   hwXdslEtherStatsOutMcastPkts   OBJECT-TYPE
       SYNTAX Counter64
       MAX-ACCESS read-only
       STATUS current
       DESCRIPTION
           " Number of transmitted multicast packets. "
       ::= { hwXdslEtherStatsEntry 11 }

   hwXdslEtherStatsOutBcastPkts   OBJECT-TYPE
       SYNTAX Counter64
       MAX-ACCESS read-only
       STATUS current
       DESCRIPTION
           " Number of transmitted broadcast packets. "
       ::= { hwXdslEtherStatsEntry 12 }

   hwXdslEtherStatsOutAllOctets   OBJECT-TYPE
       SYNTAX Counter64
       MAX-ACCESS read-only
       STATUS current
       DESCRIPTION
           " Number of transmitted octet. "
       ::= { hwXdslEtherStatsEntry 13 }

   hwXdslEtherStatsOutUcastOctets   OBJECT-TYPE
       SYNTAX Counter64
       MAX-ACCESS read-only
       STATUS current
       DESCRIPTION
           " Number of transmitted unicast octet. "
       ::= { hwXdslEtherStatsEntry 14 }

   hwXdslEtherStatsOutMcastOctets   OBJECT-TYPE
       SYNTAX Counter64
       MAX-ACCESS read-only
       STATUS current
       DESCRIPTION
           " Number of transmitted multicast octet. "
       ::= { hwXdslEtherStatsEntry 15 }

   hwXdslEtherStatsOutBcastOctets   OBJECT-TYPE
       SYNTAX Counter64
       MAX-ACCESS read-only
       STATUS current
       DESCRIPTION
           " Number of transmitted broadcast octet. "
       ::= { hwXdslEtherStatsEntry 16 }

-- hwExtProtocolForwardingPolicyTable
   hwExtProtocolForwardingPolicyTable OBJECT IDENTIFIER ::= { hwEthernetPort 25 }

   hwExtEapolPermitForwarding OBJECT-TYPE
       SYNTAX INTEGER
           {
           enable(1),
           disable(2)
           }
       MAX-ACCESS read-write
       STATUS current
       DESCRIPTION
           "Indicates the permission switch of forwarding the EAPoL protocol packet.
            Options:
            1. enable(1)  -indicates that the EAPoL protocol packet can be forwarded.
            2. disable(2) -indicates that the EAPoL protocol packet is discarded.
            Default: enable(1)
           "
       ::= { hwExtProtocolForwardingPolicyTable 1 }

   hwExtEthoamEfmPermitForwarding OBJECT-TYPE
       SYNTAX INTEGER
           {
           enable(1),
           disable(2)
           }
       MAX-ACCESS read-write
       STATUS current
       DESCRIPTION
           "Indicates the permission switch of forwarding the ETHOAM EFM protocol packet.
            Options:
            1. enable(1)  -indicates that the ETHOAM EFM protocol packet can be forwarded.
            2. disable(2) -indicates that the ETHOAM EFM protocol packet is discarded.
            Default: enable(1)
           "
       ::= { hwExtProtocolForwardingPolicyTable 2 }

   hwExtLacpPermitForwarding OBJECT-TYPE
       SYNTAX INTEGER
           {
           enable(1),
           disable(2)
           }
       MAX-ACCESS read-write
       STATUS current
       DESCRIPTION
           "Indicates the permission switch of forwarding the LACP protocol packet.
            Options:
            1. enable(1)  -indicates that the LACP protocol packet can be forwarded.
            2. disable(2) -indicates that the LACP protocol packet is discarded.
            Default: enable(1)
           "
       ::= { hwExtProtocolForwardingPolicyTable 3 }

   hwExtMstpPermitForwarding OBJECT-TYPE
       SYNTAX INTEGER
           {
           enable(1),
           disable(2)
           }
       MAX-ACCESS read-write
       STATUS current
       DESCRIPTION
           "Indicates the permission switch of forwarding the MSTP protocol packet.
            Options:
            1. enable(1)  -indicates that the MSTP protocol packet can be forwarded.
            2. disable(2) -indicates that the MSTP protocol packet is discarded.
            Default: enable(1)
           "
       ::= { hwExtProtocolForwardingPolicyTable 4 }

   --ServiceTypeDetect
   hwServiceTypeDetect OBJECT IDENTIFIER ::= { hwEthernetPort 26 }

   --Service Detect Switch
   hwServiceTypeDetectSwitch OBJECT-TYPE
       SYNTAX INTEGER
           {
           enable(1),
           disable(2)
           }
       MAX-ACCESS read-write
       STATUS current
       DESCRIPTION
           "Indicates service type detect switch.
            Options:
            1. enable(1)  -indicates the service type detect switch is enabled.
            2. disable(2) -indicates the service type detect switch is disabled.
           "
       ::= { hwServiceTypeDetect 1 }

   --Service Detect Table
   hwServiceTypeDetectTable OBJECT-TYPE
       SYNTAX SEQUENCE OF HwServiceTypeDetectEntry
       MAX-ACCESS not-accessible
       STATUS current
       DESCRIPTION
           "Indicates port service detect table.
            The index of this table is ifIndex.
           "
       ::= { hwServiceTypeDetect 2 }

   hwServiceTypeDetectEntry OBJECT-TYPE
       SYNTAX HwServiceTypeDetectEntry
       MAX-ACCESS not-accessible
       STATUS current
       DESCRIPTION
           "Indicates port service detect table.
            The index of this entry is ifIndex."
       INDEX { ifIndex }
       ::= { hwServiceTypeDetectTable 1 }

   HwServiceTypeDetectEntry ::=
       SEQUENCE {
           hwDetectSwitch
               INTEGER,
           hwDetectUserMac
               MacAddress,
           hwDetectUserVlan
               Integer32
           }

   hwDetectSwitch OBJECT-TYPE
       SYNTAX INTEGER
           {
           disable(1),
           detectHSI(2),
           detectMultiService(3)
           }
       MAX-ACCESS read-write
       STATUS current
       DESCRIPTION
           "Indicates the detect service type.
            Options:
            1. disable(1)            -indicates the detect Switch is disabled.
            2. detectHSI(2)          -indicates the HSI detect is enabled.
            3. detectMultiService(3) -indicates the multi-service detect is enabled.

            Default: detectMultiService(3)
           "
       ::= { hwServiceTypeDetectEntry 1 }

   hwDetectUserMac OBJECT-TYPE
       SYNTAX MacAddress
       MAX-ACCESS accessible-for-notify
       STATUS current
       DESCRIPTION
           "The MAC address, and its format is XX-XX-XX-XX-XX-XX."
       ::= { hwServiceTypeDetectEntry 2 }

   hwDetectUserVlan OBJECT-TYPE
       SYNTAX Integer32 (-1 | 0..4095)
       MAX-ACCESS accessible-for-notify
       STATUS current
       DESCRIPTION
           "The user VLAN ID, 0 means untagged, -1 is reserved."
       ::= { hwServiceTypeDetectEntry 3 }

   hwEthernetLine OBJECT IDENTIFIER ::= { hwEthernetPort 27 }

   hwEthernetLineGlobalConfig OBJECT IDENTIFIER ::= { hwEthernetLine 1 }

   hwEthernetLineAlarmRecoverOnShutdown OBJECT-TYPE
       SYNTAX INTEGER
           {
           enable(1),
           disable(2)
           }
       MAX-ACCESS read-write
       STATUS current
       DESCRIPTION
           "Indicates the clear-on-shutdown switch state.
            Options:
            1. enable(1)            -indicates the detect Switch is enabled.
            2. disable(2)           -indicates the the detect Switch is disabled.
            Default: disable(2).
           "
       ::= { hwEthernetLineGlobalConfig 1 }

   hwEthernetLineAlarmSuppressInitial OBJECT-TYPE
       SYNTAX INTEGER
           {
           enable(1),
           disable(2)
           }
       MAX-ACCESS read-write
       STATUS current
       DESCRIPTION
           "Indicates the suppress-initial-alarm switch state.
            Options:
            1. enable(1)            -indicates the detect Switch is enabled.
            2. disable(2)           -indicates the the detect Switch is disabled.
            Default: enable(1).
           "
       ::= { hwEthernetLineGlobalConfig 2 }

    hwEthernetLineOfflineAutoShutdown OBJECT-TYPE
       SYNTAX INTEGER
           {
           enable(1),
           disable(2)
           }
       MAX-ACCESS read-write
       STATUS current
       DESCRIPTION
           "Indicates the Eth port offline auto shutdown switch state.
            Options:
            1. enable(1)            -indicates the Offline ETH port auto shutdown switch is enabled,
                                     when the switch is enabled, the eth port manage state would be shutdown after the port offline.
            2. disable(2)           -indicates the Offline ETH port auto shutdown switch is disabled,
                                     when the switch is disabled, the eth port manage state would note be shutdown after the port offline.
            Default: disable(1).
           "
       ::= { hwEthernetLineGlobalConfig 3 }

    hwOpticsModuleShowMode OBJECT-TYPE
       SYNTAX INTEGER
           {
           standard(1),
           dt(2)
           }
       MAX-ACCESS read-write
       STATUS current
       DESCRIPTION
           "Indicates the show mode of the information about the optical module of an Ethernet port.
            Options:
            1. standard(1)           -indicates the show mode of the information about the optical module of an Ethernet port is standard,
                                     when the mode is standard, the information about the optical module of an Ethernet port is hex string.
            2. dt(2)                 -indicates the show mode of the information about the optical module of an Ethernet port is dt,
                                     when the mode is dt, the information about the optical module of an Ethernet port is ascii string.
            Default: standard(1).
           "
       ::= { hwEthernetLineGlobalConfig 4 }

   --hwDownMcTrafficPolicy
   hwDownMcTrafficPolicy  OBJECT-TYPE
       SYNTAX INTEGER
           {
           noconfig(1),
           vlanConnect(2),
           vlanMac(3)
           }
       MAX-ACCESS read-write
       STATUS current
       DESCRIPTION
           "Indicates the traffic policy of downstream multicast packets.
            Options:
            1. noconfig(1) -indicates no configuration ,the traffic policy of downstream multicast packets is decided by board's default configuration.
            2. vlanConnect(2)  -indicates the traffic policy of downstream multicast packets is S+C priority.
            3. vlanMac(3) -indicates the traffic policy of downstream multicast packets is multicast priority.
            The default value of traffic policy of downstream multicast packets is noconfig(1).
           "
       ::= { hwEthernetPort 28 }

    hwPortPermitForwardTable OBJECT-TYPE
           SYNTAX SEQUENCE OF HwPortPermitForwardEntry
           MAX-ACCESS  not-accessible
           STATUS      current
           DESCRIPTION
               "The indexes of this table are hwExtPermitForwardIfIdex and hwExtPermitForwardSecondIndex.
                This table is used to set or query the forwarding status of the port protocol packet.
                It supports the query and set operations"
           ::= { hwEthernetPort 29 }

        hwPortPermitForwardEntry OBJECT-TYPE
           SYNTAX HwPortPermitForwardEntry
           MAX-ACCESS not-accessible
           STATUS current
           DESCRIPTION
               "The indexes of this entry are hwExtPermitForwardIfIdex and hwExtPermitForwardSecondIndex.
                This table is used to set or query the forwarding status of the port protocol packet.
                It supports the query and set operations"
           INDEX {
                  hwExtPermitForwardIfIdex,
                  hwExtPermitForwardSecondIndex
                 }
           ::= { hwPortPermitForwardTable 1 }

        HwPortPermitForwardEntry ::=
            SEQUENCE {
              hwExtPermitForwardIfIdex
                Integer32,
              hwExtPermitForwardSecondIndex
                Integer32,
              hwExtCfmPermitForwarding
                INTEGER
                   }

        hwExtPermitForwardIfIdex OBJECT-TYPE
              SYNTAX Integer32
              MAX-ACCESS not-accessible
              STATUS current
              DESCRIPTION
                  "Indicates the port index of forwarding the CFM protocol packet."
              ::= { hwPortPermitForwardEntry 1 }

           hwExtPermitForwardSecondIndex OBJECT-TYPE
            SYNTAX Integer32
            MAX-ACCESS not-accessible
            STATUS current
            DESCRIPTION
                "Indicates the second index. The meaning varies with the port type.
                 It must be 0xFFFFFFFF for the DSL or ETH port, and is the ONT ID or 0xFFFFFFFF for the xPON port.
            "
            ::= { hwPortPermitForwardEntry 2 }

           hwExtCfmPermitForwarding OBJECT-TYPE
               SYNTAX INTEGER
               {
               enable(1),
               disable(2)
               }
               MAX-ACCESS read-write
               STATUS current
               DESCRIPTION
                   "Indicates the permission switch of forwarding the CFM protocol packet.
                    Options:
                    1. enable(1)  -indicates that the CFM protocol packet can be forwarded.
                    2. disable(2) -indicates that the CFM protocol packet is discarded.
                Default: enable(1)
                   "
               ::= { hwPortPermitForwardEntry 3 }

    hwResourceOverloadAwareTable OBJECT-TYPE
        SYNTAX SEQUENCE OF HwResourceOverloadAwareEntry
        MAX-ACCESS  not-accessible
        STATUS      current
        DESCRIPTION
            "The index of this table is hwResourceType.
             This table is used to query the configuration of resource overload.
             It supports the query and set operations."
        ::= { hwEthernetPort 30 }

    hwResourceOverloadAwareEntry OBJECT-TYPE
        SYNTAX HwResourceOverloadAwareEntry
        MAX-ACCESS not-accessible
        STATUS current
        DESCRIPTION
            "The index of this entry is hwResourceType.
             This table is used to query the configuration of resource overload.
             It supports the query and set operations."
        INDEX {
               hwResourceType
              }
        ::= { hwResourceOverloadAwareTable 1 }

    HwResourceOverloadAwareEntry ::=
        SEQUENCE {
            hwResourceType
                INTEGER,
            hwResourceOverloadAwareSwitch
                INTEGER,
            hwResourceOverloadAwareUpperThreshold
                Integer32,
            hwResourceOverloadAwareLowerThreshold
                Integer32
                }

    --hwBoardMacAddressLearningVlanConnectTable
   hwBoardMacAddressLearningVlanConnectTable OBJECT-TYPE
       SYNTAX SEQUENCE OF HwBoardMacAddressLearningVlanConnectEntry
       MAX-ACCESS not-accessible
       STATUS current
       DESCRIPTION
           "Used to enable or disable the MAC address learning function on S+C traffic streams.
            The indexes of this table are hwFrameIndex and hwSlotIndex.
           "
       ::= { hwL2IfMibObject 11 }

   hwBoardMacAddressLearningVlanConnectEntry OBJECT-TYPE
       SYNTAX HwBoardMacAddressLearningVlanConnectEntry
       MAX-ACCESS not-accessible
       STATUS current
       DESCRIPTION
           "Used to enable or disable the MAC address learning function on S+C traffic streams.
            The indexes of this entry are hwFrameIndex and hwSlotIndex.
           "
       INDEX { hwFrameIndex,hwSlotIndex }
       ::= { hwBoardMacAddressLearningVlanConnectTable 1 }

   HwBoardMacAddressLearningVlanConnectEntry ::=
       SEQUENCE {
           hwBoardMacAddressLearningVlanConnectCtrl
               INTEGER
                }

   hwBoardMacAddressLearningVlanConnectCtrl OBJECT-TYPE
       SYNTAX INTEGER
           {
           invalid(-1),
           disable(1),
           enable(2),
           noconfig(3)
           }
       MAX-ACCESS read-write
       STATUS current
       DESCRIPTION
           "Indicates the status of the the MAC address learning function on S+C traffic streams.
            Options:
            1. invalid(-1)  -Indicates that the MAC address learning function on S+C traffic streams is unavailable.
            2. disable(1)   -Disables the MAC address learning function on S+C traffic streams.
            3. enable(2)    -Enables the MAC address learning function on S+C traffic streams.
            4. noconfig(3)  -Cancels the MAC address learning function on S+C traffic streams. After the command is successfully executed,
                             the MAC address learning function configured for the specified VLAN takes effect for S+C traffic streams.
            "
       ::= { hwBoardMacAddressLearningVlanConnectEntry 1 }

    hwResourceType OBJECT-TYPE
        SYNTAX INTEGER
        {
        mac(1),
        ipneighbourhardware(2),
        iproutehardware(3),
        iptunnelhardware(4),
        vpnhardware(5),
        srv6tunnelhardware(6)
        }
        MAX-ACCESS not-accessible
        STATUS current
        DESCRIPTION
        "Indicates the resource type.
        Options:
        1. mac(1)  -indicates that the resource is the MAC address.
        2. ipneighbourhardware(2)  -indicates that the resource is the ip neighbour hardware.
        3. iproutehardware(3)  -indicates that the resource is the ip route hardware.
		                        The type only supports the trap of hwIPRouteHardwareOverloadTrap and hwIPRouteHardwareOverloadRestoreTrap.
        4. iptunnelhardware(4)  -indicates that the resource is the ip tunnel hardware.
                            The type only supports the trap of hwIPTunnelHardwareOverloadTrap and hwIPTunnelHardwareOverloadRestoreTrap.
        5. vpnhardware(5)       -indicates that the resource is the VNI PEER hardware.
                            The type only supports the trap of hwVPNHardwareOverloadTrap and hwVPNHardwareOverloadRestoreTrap.
        6. srv6tunnelhardware(6)  -indicates that the resource is the segment-routing ipv6 tunnel hardware.
                            The type only supports the trap of hwSRv6TunnelHardwareOverloadTrap and hwSRv6TunnelHardwareOverloadRestoreTrap.
        "
        ::= { hwResourceOverloadAwareEntry 1 }

    hwResourceOverloadAwareSwitch OBJECT-TYPE
        SYNTAX INTEGER
        {
        enable(1),
        disable(2)
        }
        MAX-ACCESS read-write
        STATUS current
        DESCRIPTION
        "Indicates the switch of resource overload awareness.
        Options:
        1. enable(1)   -indicates that the function of monitoring resources is enabled.
        2. disable(2)  -indicates that the function of monitoring resources is disabled.
        Default: disable(2)
        "
        ::= { hwResourceOverloadAwareEntry 2 }

    hwResourceOverloadAwareUpperThreshold OBJECT-TYPE
        SYNTAX Integer32 (0..100)
        MAX-ACCESS read-write
        STATUS current
        DESCRIPTION
        "Indicates the upper threshold of the resource overload awareness.
        "
        ::= { hwResourceOverloadAwareEntry 3 }

    hwResourceOverloadAwareLowerThreshold OBJECT-TYPE
        SYNTAX Integer32 (0..100)
        MAX-ACCESS read-write
        STATUS current
        DESCRIPTION
        "Indicates the lower threshold of the resource overload awareness.
        "
        ::= { hwResourceOverloadAwareEntry 4 }

  hwInfinibandTable OBJECT-TYPE
        SYNTAX SEQUENCE OF HwInfinibandEntry
        MAX-ACCESS  not-accessible
        STATUS      current
        DESCRIPTION
            "The index of this table is ifIndex.
             This table is used to query the status parameters of infiniband port."
        ::= { hwEthernetPort 31 }

    hwInfinibandEntry OBJECT-TYPE
        SYNTAX HwInfinibandEntry
        MAX-ACCESS not-accessible
        STATUS current
        DESCRIPTION
            "The index of this entry is ifIndex.
             This table is used to query the status parameters of infiniband port."
        INDEX {
               ifIndex
              }
        ::= { hwInfinibandTable 1 }

    HwInfinibandEntry ::=
        SEQUENCE {
            hwInfinibandPortState
                INTEGER
                }

    hwInfinibandPortState OBJECT-TYPE
        SYNTAX INTEGER
        {
        up(1),
        down(2)
        }
          MAX-ACCESS read-only
          STATUS current
          DESCRIPTION
        "The current operational state of the infiniband port.
        Options:
        1. up(1)   -indicates that the operation state is up
        2. down(2) -indicates that the operation state is down
        "
        ::= { hwInfinibandEntry 1 }

  hwInfinibandTraps OBJECT IDENTIFIER ::= { hwEthernetPort 32 }
  hwInfinibandAlarmTraps OBJECT IDENTIFIER ::= { hwInfinibandTraps 1 }
  hwInfinibandAlarmTrapsOids OBJECT IDENTIFIER ::= { hwInfinibandAlarmTraps 0 }

    hwInfinibandPortLinkDown NOTIFICATION-TYPE
       OBJECTS {
                hwFrameIndex,
                hwSlotIndex,
                hwPortIndex
               }
       STATUS current
       DESCRIPTION
           "This trap message is generated when the infiniband port status changes form up to down.
           "
       ::= { hwInfinibandAlarmTrapsOids 1 }

    hwInfinibandPortLinkRecover NOTIFICATION-TYPE
       OBJECTS {
                hwFrameIndex,
                hwSlotIndex,
                hwPortIndex
               }
       STATUS current
       DESCRIPTION
           "This trap message is generated when the infiniband port status changes form down to up.
           "
       ::= { hwInfinibandAlarmTrapsOids 2 }

   --hwPriTagTransDownstream
   hwPriTagTransDownstream  OBJECT-TYPE
       SYNTAX INTEGER
           {
           priorityTagged(1),
           untagged(2)
           }
       MAX-ACCESS read-write
       STATUS current
       DESCRIPTION
           "Indicates the priority-tag switching policy for downstream packets of VLAN priority service ports.
            Options:
            1. priorityTagged(1) -indicates the priority-tag of downstream packets are reserved.
            2. untagged(2)        -indicates the priority-tag of downstream packets are switched to untagged.
            Default: priorityTagged(1)
           "
       ::= { hwEthernetPort 33 }

   hwEthTrafficSuppressDefaultTable OBJECT IDENTIFIER ::= { hwEthernetPort 34 }

       hwEthTrafficSuppressEthPortBroadcastDefaultVaule OBJECT-TYPE
            SYNTAX Integer32 (0..13)
            MAX-ACCESS read-write
            STATUS current
            DESCRIPTION
                "Indicates the default broadcast traffic suppression value for ETH ports.
                 0 indicates no traffic suppression.
                "
            ::= {  hwEthTrafficSuppressDefaultTable 1 }

       hwEthTrafficSuppressEthPortMulticastDefaultVaule OBJECT-TYPE
            SYNTAX Integer32 (0..13)
            MAX-ACCESS read-write
            STATUS current
            DESCRIPTION
                "Indicates the unkown multicast broadcast traffic suppression value for ETH ports.
                 0 indicates no traffic suppression.
                "
            ::= {  hwEthTrafficSuppressDefaultTable 2 }

       hwEthTrafficSuppressEthPortUnicastDefaultVaule OBJECT-TYPE
            SYNTAX Integer32 (0..13)
            MAX-ACCESS read-write
            STATUS current
            DESCRIPTION
                "Indicates the unkown unicast broadcast traffic suppression value for ETH ports.
                 0 indicates no traffic suppression.
                "
            ::= {  hwEthTrafficSuppressDefaultTable 3 }

      hwEthTrafficSuppressBoardBroadcastDefaultVaule OBJECT-TYPE
            SYNTAX Integer32 (0..13)
            MAX-ACCESS read-write
            STATUS current
            DESCRIPTION
                "Indicates the default broadcast traffic suppression value for boards.
                 0 indicates no traffic suppression.
                "
            ::= {  hwEthTrafficSuppressDefaultTable 4 }

     hwEthTrafficSuppressBoardMulticastDefaultVaule OBJECT-TYPE
            SYNTAX Integer32 (0..13)
            MAX-ACCESS read-write
            STATUS current
            DESCRIPTION
                "Indicates the unkown multicast broadcast traffic suppression value for boards.
                 0 indicates no traffic suppression.
                "
            ::= {  hwEthTrafficSuppressDefaultTable 5 }

      hwEthTrafficSuppressBoardUnicastDefaultVaule OBJECT-TYPE
            SYNTAX Integer32 (0..13)
            MAX-ACCESS read-write
            STATUS current
            DESCRIPTION
                "Indicates the unkown unicast broadcast traffic suppression value for boards.
                 0 indicates no traffic suppression.
                "
            ::= {  hwEthTrafficSuppressDefaultTable 6 }

     -- hwPortAutoServiceParaTable
	   hwPortAutoServiceParaTable OBJECT-TYPE
	       SYNTAX SEQUENCE OF HwPortAutoServiceParaEntry
	       MAX-ACCESS not-accessible
	       STATUS current
	       DESCRIPTION
	           "Port auto service para table.
	           The index of this table is ifIndex."
	       ::= { hwEthernetPort 35 }

	   hwPortAutoServiceParaEntry OBJECT-TYPE
	       SYNTAX HwPortAutoServiceParaEntry
	       MAX-ACCESS not-accessible
	       STATUS current
	       DESCRIPTION
	           "Port auto service para table.
	           The index of this entry is ifIndex."
	       INDEX {
	       			ifIndex
	             }
	       ::= { hwPortAutoServiceParaTable 1 }

	   HwPortAutoServiceParaEntry ::=
	       SEQUENCE {
	               hwPortAutoServiceParaRowStatus
	                   RowStatus,
	               hwPortAutoServiceParaType
	                   INTEGER,
	               hwPortAutoServiceParaServiceVlan
	                   Integer32,
	               hwPortAutoServiceParaClientVlanBase
	                   Integer32,
	               hwPortAutoServiceParaOnuVlanNumber
	                   Integer32,
	               hwPortAutoServiceParaReceiveTrafficDescrIndex
	                   Integer32,
	               hwPortAutoServiceParaTransmitTrafficDescrIndex
	                   Integer32,
	               hwPortAutoServiceParaInboundTrafficTableName
	                   OCTET STRING,
	               hwPortAutoServiceParaOutboundTrafficTableName
	                   OCTET STRING
	                }

	   hwPortAutoServiceParaRowStatus   OBJECT-TYPE
	       SYNTAX RowStatus
	       MAX-ACCESS read-create
	       STATUS current
	       DESCRIPTION
	           " This object is used to create a new row or to modify or
                 delete an existing row in this table. "
	       ::= { hwPortAutoServiceParaEntry 1 }

	   hwPortAutoServiceParaType   OBJECT-TYPE
	       SYNTAX INTEGER
	        {
	        singleVlan(1),
	        doubleVlan(2)
	        }
	       MAX-ACCESS read-write
	       STATUS current
	       DESCRIPTION
	           " singleVlan - Creat single service flow
	             doubleVlan - Creat double service flow"
	       ::= { hwPortAutoServiceParaEntry 2 }

	   hwPortAutoServiceParaServiceVlan   OBJECT-TYPE
	       SYNTAX Integer32 (1..4093)
	       MAX-ACCESS read-write
	       STATUS current
	       DESCRIPTION
	           " Number of service vlan. "
	       ::= { hwPortAutoServiceParaEntry 3 }

	   hwPortAutoServiceParaClientVlanBase   OBJECT-TYPE
	       SYNTAX Integer32 (-1|1..4093)
	       MAX-ACCESS read-write
	       STATUS current
	       DESCRIPTION
	           " Number of Client vlan.
	           	 singleVlan mode is not need(-1).
	           	 doubleVlan mode must be define."
	       ::= { hwPortAutoServiceParaEntry 4 }

	   hwPortAutoServiceParaOnuVlanNumber   OBJECT-TYPE
	       SYNTAX Integer32 (1..128)
	       MAX-ACCESS read-write
	       STATUS current
	       DESCRIPTION
	           " Number of ONU max vlan num. "
	       ::= { hwPortAutoServiceParaEntry 5 }

	   hwPortAutoServiceParaReceiveTrafficDescrIndex   OBJECT-TYPE
	       SYNTAX Integer32 (-1|1..1024)
	       MAX-ACCESS read-write
	       STATUS current
	       DESCRIPTION
	           " Indicates the index of the IP traffic table.
                     Range: 1-1024 "
	       ::= { hwPortAutoServiceParaEntry 6 }

	   hwPortAutoServiceParaTransmitTrafficDescrIndex   OBJECT-TYPE
	       SYNTAX Integer32 (-1|1..1024)
	       MAX-ACCESS read-write
	       STATUS current
	       DESCRIPTION
	           " Indicates the index of the IP traffic table.
		     Range: 1-1024"
	       ::= { hwPortAutoServiceParaEntry 7 }

	   hwPortAutoServiceParaInboundTrafficTableName   OBJECT-TYPE
	       SYNTAX OCTET STRING (SIZE (0..32))
	       MAX-ACCESS read-write
	       STATUS current
	       DESCRIPTION
	           " Indicates the name of IP traffic table . "
	       ::= { hwPortAutoServiceParaEntry 8 }

	   hwPortAutoServiceParaOutboundTrafficTableName   OBJECT-TYPE
	      SYNTAX OCTET STRING (SIZE (0..32))
	      MAX-ACCESS read-write
	      STATUS current
	      DESCRIPTION
	          " Indicates the name of IP traffic table . "
	      ::= { hwPortAutoServiceParaEntry 9 }

     --hwMacLimitActionSwitch
     hwMacLimitActionSwitch  OBJECT-TYPE
         SYNTAX INTEGER
             {
             activate(1),
             deactivate(2)
           }
         MAX-ACCESS read-write
         STATUS current
         DESCRIPTION
             "If or not to shutdown the port when the number of MAC addresses of the port reaches an upper limit.
              Options:
              1. activate(1) 	      -not to shutdown the port when the number of MAC addresses of the port reaches an upper limit.
              2. deactivate(2)        -shutdown the port when the number of MAC addresses of the port reaches an upper limit.
              Default: activate(1)
             "
         ::= { hwEthernetPort 36 }

     --hwMacLimitSendEvent
     hwMacLimitSendEvent  OBJECT-TYPE
         SYNTAX INTEGER
             {
             enabled(1),
             disabled(2)
           }
         MAX-ACCESS read-write
         STATUS current
         DESCRIPTION
             "Indicates the priority-tag switching policy for downstream packets of VLAN priority service ports.
              Options:
              1. enabled(1) 	      -not to send event when the number of MAC addresses of the port reaches an upper limit.
              2. disabled(2)          -send event when the number of MAC addresses of the port reaches an upper limit.
              Default: disabled(2)
             "
         ::= { hwEthernetPort 37 }

        hwDslamTrafficUpportMonitor OBJECT IDENTIFIER ::= { hwEthernetPort  38}

        hwDslamTrafficUpportMonitorSwitch OBJECT-TYPE
            SYNTAX INTEGER
                {
                 enable(1),
                 disable(2)
                }
            MAX-ACCESS   read-write
            STATUS       current
            DESCRIPTION
                "Indicates the Echo monitoring function of the uplink port.
                 Options:
                 1. enable(1)               - Indicates that the uplink port is enabled.
                 2. disable(2)              - Indicates that the uplink port is disabled.
                 Default: disable(2)
                "
            ::= { hwDslamTrafficUpportMonitor 1 }

        hwDslamTrafficUpportMonitorPeriod OBJECT-TYPE
            SYNTAX Integer32 (1..60)
            UNITS       "minute"
            MAX-ACCESS   read-write
            STATUS       current
            DESCRIPTION
                "Indicates the monitoring period of the uplink port.
                 Unit: minute
                 Default: 10
                "
            ::= { hwDslamTrafficUpportMonitor 2 }

        hwDslamTrafficUpportMonitorThreshold OBJECT-TYPE
            SYNTAX Integer32 (10 | 20 | 30 | 40 | 50 | 60 | 70 | 80 | 90 )
            MAX-ACCESS   read-write
            STATUS       current
            DESCRIPTION
                "Indicates the Traffic monitoring threshold for the uplink port.
                 Unit: 1/100
                 Default: 50
                "
            ::= { hwDslamTrafficUpportMonitor 3 }

        hwDslamTrafficUpportMonitorMemberTable OBJECT-TYPE
            SYNTAX SEQUENCE OF HwDslamTrafficUpportMonitorMemberEntry
            MAX-ACCESS not-accessible
            STATUS current
            DESCRIPTION
                "Configures the monitoring table of uplink ports.
                 The index of this table is hwDslamTrafficUpportMonitorMemberIfIndex.
                "
            ::= { hwDslamTrafficUpportMonitor 4 }

        hwDslamTrafficUpportMonitorMemberEntry OBJECT-TYPE
            SYNTAX HwDslamTrafficUpportMonitorMemberEntry
            MAX-ACCESS not-accessible
            STATUS current
            DESCRIPTION
                "Configures the monitoring table of uplink ports.
                 The index of this entry is hwDslamTrafficUpportMonitorMemberIfIndex.
                "
            INDEX { hwDslamTrafficUpportMonitorMemberIfIndex }
            ::= { hwDslamTrafficUpportMonitorMemberTable 1 }

        HwDslamTrafficUpportMonitorMemberEntry ::=
            SEQUENCE {
                hwDslamTrafficUpportMonitorMemberIfIndex  Integer32,
                hwDslamTrafficUpportMonitorRowStatus      RowStatus
             }

        hwDslamTrafficUpportMonitorMemberIfIndex OBJECT-TYPE
            SYNTAX Integer32
            MAX-ACCESS not-accessible
            STATUS current
            DESCRIPTION
                "Indicates the index of the monitoring table of uplink ports.
                "
            ::= { hwDslamTrafficUpportMonitorMemberEntry 1 }

        hwDslamTrafficUpportMonitorRowStatus OBJECT-TYPE
            SYNTAX RowStatus
            MAX-ACCESS read-create
            STATUS current
            DESCRIPTION
                "Row status, used to query, create, modify, and delete a monitoring table of uplink ports.
                 It supports the active(1), createAndGo(4), and destroy(6) operations.
                 During query, the value of this leaf is always active(1).
                 During deletion, specify the value of this leaf to destroy(6).
                 During creation, specify the value of this leaf to createAndGo(4).
                 To modify the parameters of a Traffic monitoring table of uplink ports, this leaf need not be issued together.
                Options:
                 1. active(1)               - Indicates the query operation.
                 2. createAndGo(4)          - Indicates the creating operation.
                 3. destroy(6)              - Indicates the deleting operation.
                "
            ::= { hwDslamTrafficUpportMonitorMemberEntry 2 }

        hwDslamTrafficUpportMonitorRecordTable OBJECT-TYPE
            SYNTAX SEQUENCE OF HwDslamTrafficUpportMonitorRecordEntry
            MAX-ACCESS not-accessible
            STATUS current
            DESCRIPTION
                "Indicates the Traffic monitoring table of uplink ports.
                 The index of this table is hwDslamTrafficUpportMonitorRecordIfIndex, hwDslamTrafficUpportMonitorRecordIndex.
                "
            ::= { hwDslamTrafficUpportMonitor 5 }

        hwDslamTrafficUpportMonitorRecordEntry OBJECT-TYPE
            SYNTAX HwDslamTrafficUpportMonitorRecordEntry
            MAX-ACCESS not-accessible
            STATUS current
            DESCRIPTION
                "Indicates the Traffic monitoring table of uplink ports.
                 The index of this entry is hwDslamTrafficUpportMonitorRecordIfIndex, hwDslamTrafficUpportMonitorRecordIndex.
                "
            INDEX { hwDslamTrafficUpportMonitorRecordIfIndex, hwDslamTrafficUpportMonitorRecordIndex}
            ::= { hwDslamTrafficUpportMonitorRecordTable 1 }

        HwDslamTrafficUpportMonitorRecordEntry ::=
            SEQUENCE {
                hwDslamTrafficUpportMonitorRecordIfIndex
                    Integer32,
                hwDslamTrafficUpportMonitorRecordIndex
                    Integer32,
                hwDslamTrafficUpportMonitorRecordTime
                    DateAndTime,
                hwDslamTrafficUpportMonitorUpstream
                    Integer32,
                hwDslamTrafficUpportMonitorDownstream
                    Integer32,
                hwDslamTrafficUpportMonitorUpstreamLast
                    Integer32,
                hwDslamTrafficUpportMonitorDownstreamLast
                    Integer32
             }

        hwDslamTrafficUpportMonitorRecordIfIndex OBJECT-TYPE
            SYNTAX Integer32
            MAX-ACCESS not-accessible
            STATUS current
            DESCRIPTION
               "Indicates the level-1 index of the Traffic monitoring table of uplink ports.
               "
            ::= { hwDslamTrafficUpportMonitorRecordEntry 1 }

        hwDslamTrafficUpportMonitorRecordIndex OBJECT-TYPE
            SYNTAX Integer32
            MAX-ACCESS not-accessible
            STATUS current
            DESCRIPTION
               "Indicates the level-2 index of the Traffic monitoring table of uplink ports.
               "
            ::= { hwDslamTrafficUpportMonitorRecordEntry 2 }

        hwDslamTrafficUpportMonitorRecordTime OBJECT-TYPE
            SYNTAX DateAndTime
            MAX-ACCESS read-only
            STATUS current
            DESCRIPTION
                "Indicates period end time of Traffic packet statistics.
                "
            ::= { hwDslamTrafficUpportMonitorRecordEntry 3 }

        hwDslamTrafficUpportMonitorUpstream OBJECT-TYPE
            SYNTAX Integer32
            MAX-ACCESS read-only
            STATUS current
            DESCRIPTION
                "Indicates upstream uraffic received by the uplink port.
                "
            ::= { hwDslamTrafficUpportMonitorRecordEntry 4 }

        hwDslamTrafficUpportMonitorDownstream OBJECT-TYPE
            SYNTAX Integer32
            MAX-ACCESS read-only
            STATUS current
            DESCRIPTION
                "Indicates downstream traffic received by the uplink port.
                "
            ::= { hwDslamTrafficUpportMonitorRecordEntry 5 }

        hwDslamTrafficUpportMonitorUpstreamLast OBJECT-TYPE
            SYNTAX Integer32
            MAX-ACCESS read-only
            STATUS current
            DESCRIPTION
                "Indicates last upstream traffic received by the uplink port.
                "
            ::= { hwDslamTrafficUpportMonitorRecordEntry 6 }

        hwDslamTrafficUpportMonitorDownstreamLast OBJECT-TYPE
            SYNTAX Integer32
            MAX-ACCESS read-only
            STATUS current
            DESCRIPTION
                "Indicates last downstream traffic received by the uplink port.
                "
            ::= { hwDslamTrafficUpportMonitorRecordEntry 7 }


        hwDslamTrafficUpportMonitorNotifySwitch OBJECT-TYPE
            SYNTAX INTEGER
                {
                 enable(1),
                 disable(2)
                }
            MAX-ACCESS   read-write
            STATUS       current
            DESCRIPTION
                "Indicates the traffic Echo monitoring notify function of the uplink port.
                 Options:
                 1. enable(1)  - Indicates that the traffic monitoring notify function of the uplink port is enabled.
                 2. disable(2) - Indicates that the traffic monitoring notify function of the uplink port is disabled.
                 Default: disable(2)
                "
            ::= { hwDslamTrafficUpportMonitor 6 }

        hwDslamTrafficUpportMonitorActiveThreshold OBJECT-TYPE
            SYNTAX Integer32 (1..100)
            MAX-ACCESS   read-write
            STATUS       current
            DESCRIPTION
                "Indicates the traffic monitoring active threshold for the uplink port.
                 Unit: 1/100
                 Default: 10
                "
            ::= { hwDslamTrafficUpportMonitor 7 }

        hwDslamTrafficUpportMonitorStartTime OBJECT-TYPE
            SYNTAX DateAndTime
            MAX-ACCESS   read-write
            STATUS       current
            DESCRIPTION
                "Indicates the traffic monitoring start time for the uplink port.
                 The start time needs only the hour, minute and second values,
                 and thus only the fifth, sixth and seventh bytes are used, where,
                 the fifth byte indicates the hour value of the
                 start time, the sixth byte indicates the minute value,
                 and the seventh byte indicates the second value.
                 Other bytes are reserved and are filled in 0.
                 For example, if the start time is 08:30:00,
                 the value is presented as 0x00 0x00 0x00 0x00 0x08 0x1E 0x00 0x00.
                 The time must be from 00:00:00 to 23:59:59.
                "
            ::= { hwDslamTrafficUpportMonitor 8 }

        hwDslamTrafficUpportMonitorEndTime OBJECT-TYPE
            SYNTAX DateAndTime
            MAX-ACCESS   read-write
            STATUS       current
            DESCRIPTION
                "Indicates the traffic monitoring end time for the uplink port.
                 The end time needs only the hour, minute and second values,
                 and thus only the fifth, sixth and seventh bytes are used, where,
                 the fifth byte indicates the hour value of the
                 start time, the sixth byte indicates the minute value,
                 and the seventh byte indicates the second value.
                 Other bytes are reserved and are filled in 0.
                 For example, if the start time is 08:30:00,
                 the value is presented as 0x00 0x00 0x00 0x00 0x08 0x1E 0x00 0x00.
                 The time must be from 00:00:00 to 23:59:59.
                "
            ::= { hwDslamTrafficUpportMonitor 9 }

        hwDslamTrafficUpportMonitorPeakRecordTable OBJECT-TYPE
            SYNTAX SEQUENCE OF HwDslamTrafficUpportMonitorPeakRecordEntry
            MAX-ACCESS not-accessible
            STATUS current
            DESCRIPTION
                "Indicates the traffic monitoring peak table of uplink ports.
                 The index of this table is hwDslamTrafficUpportMonitorPeakRecordIfIndex.
                "
            ::= { hwDslamTrafficUpportMonitor 10 }

        hwDslamTrafficUpportMonitorPeakRecordEntry OBJECT-TYPE
            SYNTAX HwDslamTrafficUpportMonitorPeakRecordEntry
            MAX-ACCESS not-accessible
            STATUS current
            DESCRIPTION
                "Indicates the traffic monitoring peak table of uplink ports.
                 The index of this entry is hwDslamTrafficUpportMonitorPeakRecordIfIndex.
                "
            INDEX { hwDslamTrafficUpportMonitorPeakRecordIfIndex }
            ::= { hwDslamTrafficUpportMonitorPeakRecordTable 1 }

        HwDslamTrafficUpportMonitorPeakRecordEntry ::=
            SEQUENCE {
                hwDslamTrafficUpportMonitorPeakRecordIfIndex
                    Integer32,
        hwDslamTrafficUpportMonitorPeakUpstreamRecordTime
                    DateAndTime,
        hwDslamTrafficUpportMonitorPeakUpstream
                    Integer32,
        hwDslamTrafficUpportMonitorPeakDownstreamRecordTime
                    DateAndTime,
        hwDslamTrafficUpportMonitorPeakDownstream
                    Integer32
             }

        hwDslamTrafficUpportMonitorPeakRecordIfIndex OBJECT-TYPE
            SYNTAX Integer32
            MAX-ACCESS not-accessible
            STATUS current
            DESCRIPTION
               "Indicates the index of the traffic monitoring peak table of uplink ports.
               "
            ::= { hwDslamTrafficUpportMonitorPeakRecordEntry 1 }

        hwDslamTrafficUpportMonitorPeakUpstreamRecordTime OBJECT-TYPE
            SYNTAX DateAndTime
            MAX-ACCESS read-only
            STATUS current
            DESCRIPTION
                "Indicates period end time of upstream traffic peak.
                "
            ::= { hwDslamTrafficUpportMonitorPeakRecordEntry 2 }

        hwDslamTrafficUpportMonitorPeakUpstream OBJECT-TYPE
            SYNTAX Integer32
            MAX-ACCESS read-only
            STATUS current
            DESCRIPTION
                "Indicates upstream traffic peak received by the uplink port.
                "
            ::= { hwDslamTrafficUpportMonitorPeakRecordEntry 3 }

       hwDslamTrafficUpportMonitorPeakDownstreamRecordTime OBJECT-TYPE
            SYNTAX DateAndTime
            MAX-ACCESS read-only
            STATUS current
            DESCRIPTION
                "Indicates period end time of downstream traffic peak.
                "
            ::= { hwDslamTrafficUpportMonitorPeakRecordEntry 4 }

        hwDslamTrafficUpportMonitorPeakDownstream OBJECT-TYPE
            SYNTAX Integer32
            MAX-ACCESS read-only
            STATUS current
            DESCRIPTION
                "Indicates downstream traffic peak received by the uplink port.
                "
            ::= { hwDslamTrafficUpportMonitorPeakRecordEntry 5 }

     --hwMacAddressClearForOntPortDownSwitch
     hwMacAddressClearForOntPortDownSwitch  OBJECT-TYPE
         SYNTAX INTEGER
             {
             enabled(1),
             disabled(2)
           }
         MAX-ACCESS read-write
         STATUS current
         DESCRIPTION
             "Indicates the switch of clearing dynamic MAC address for service flows when the ONT port goes offline.
              Options:
              1. enabled(1)  - Indicates that the switch of clearing dynamic MAC address for service flows is enabled.
              2. disabled(2) - Indicates that the switch of clearing dynamic MAC address for service flows is disabled.
              Default: disabled(2)
             "
         ::= { hwEthernetPort 39 }

    --hwDslamNonUnicastUpportMonitor
        hwDslamNonUnicastUpportMonitor OBJECT IDENTIFIER ::= { hwEthernetPort  40}
            hwDslamNonUnicastUpportMonitorSwitch OBJECT-TYPE
                SYNTAX INTEGER
                {
                    enable(1),
                    disable(2)
                }
                MAX-ACCESS   read-write
                STATUS       current
                DESCRIPTION
				    "Indicates the non-uicast monitoring function of the uplink port.
				     Options:
				     1. enable(1)               - Indicates that the non-unicast monitoring function of the uplink port is enabled.
				     2. disable(2)              - Indicates that the non-unicast monitoring function of the uplink port is disabled.
				     Default: enable(1)
				    "
            ::= { hwDslamNonUnicastUpportMonitor 1 }

            hwDslamNonUnicastUpportMonitorPeriod OBJECT-TYPE
                SYNTAX Integer32 (1..60)
                UNITS       "minute"
                MAX-ACCESS   read-write
                STATUS       current
                DESCRIPTION
                    "Indicates the non-unicast monitoring period of the uplink port.
                     Unit: minute
                     Default: 1
                    "
            ::= { hwDslamNonUnicastUpportMonitor 2 }

            hwDslamNonUnicastUpportMonitorBroadcastThdDeftAutoValue OBJECT-TYPE
                SYNTAX Integer32 (1..16)
                MAX-ACCESS   read-write
                STATUS       current
                DESCRIPTION
	                "Indicates the broadcast globally-configured default auto monitoring threshold for the uplink port.
                     When the threshold for monitoring non-unicast packets on the specified port is set to auto,
                     this threshold takes effect 2 levels above the traffic suppression threshold configured on the port
                     (The unknown multicast monitoring threshold for the port on the ETHB board takes effect 2
                     levels above the traffic suppression threshold configured on the board).
                     When no suppression or full suppression is configured on the port,
                     the globally-configured default-auto-value takes effect.
                     For the bandwidth range corresponding to the non-unicast threshold,
                     see hwDslamNonUnicastUpportMonitorBroadcastThdActiveValue description.
                     Default: 12
                    "
            ::= { hwDslamNonUnicastUpportMonitor 3 }

            hwDslamNonUnicastUpportMonitorUnknownUnicastThdDeftAutoValue OBJECT-TYPE
                SYNTAX Integer32 (1..16)
                MAX-ACCESS   read-write
                STATUS       current
                DESCRIPTION
		            "Indicates the unknown unicast globally-configured default auto monitoring threshold for the uplink port.
                     When the threshold for monitoring non-unicast packets on the specified port is set to auto,
                     this threshold takes effect 2 levels above the traffic suppression threshold configured on the port
                     (The unknown multicast monitoring threshold for the port on the ETHB board takes effect 2
                     levels above the traffic suppression threshold configured on the board).
                     When no suppression or full suppression is configured on the port,
                     the globally-configured default-auto-value takes effect.
                     For the bandwidth range corresponding to the non-unicast threshold,
                     see hwDslamNonUnicastUpportMonitorUnknownUnicastThdActiveValue description.
                     Default: 12
                    "
            ::= { hwDslamNonUnicastUpportMonitor 4 }

            hwDslamNonUnicastUpportMonitorUnknownMulticastThdDeftAutoValue OBJECT-TYPE
                SYNTAX Integer32 (1..16)
                MAX-ACCESS   read-write
                STATUS       current
                DESCRIPTION
	                "Indicates the unknown multicast globally-configured default auto monitoring threshold for the uplink port.
                     When the threshold for monitoring non-unicast packets on the specified port is set to auto,
                     this threshold takes effect 2 levels above the traffic suppression threshold configured on the port
                     (The unknown multicast monitoring threshold for the port on the ETHB board takes effect 2
                     levels above the traffic suppression threshold configured on the board).
                     When no suppression or full suppression is configured on the port,
                     the globally-configured default-auto-value takes effect.
                     For the bandwidth range corresponding to the non-unicast threshold,
                     see hwDslamNonUnicastUpportMonitorUnknownMulticastThdActiveValue description.
                     Default: 12
                    "
            ::= { hwDslamNonUnicastUpportMonitor 5 }

            hwDslamNonUnicastUpportMonitorNotifySwitch OBJECT-TYPE
                SYNTAX INTEGER
                {
                    enable(1),
                    disable(2)
                }
                MAX-ACCESS   read-write
                STATUS       current
                DESCRIPTION
                    "Indicates the non-unicast monitoring notification function of the uplink port.
                     Options:
                     1. enable(1)  - Indicates that the non-unicast monitoring notification function of the uplink port is enabled.
                     2. disable(2) - Indicates that the non-unicast monitoring notification function of the uplink port is disabled.
                     Default: disable(2)
                    "
            ::= { hwDslamNonUnicastUpportMonitor 6 }

            hwDslamNonUnicastUpportMonitorStartTime OBJECT-TYPE
                SYNTAX DateAndTime
                MAX-ACCESS   read-write
                STATUS       current
                DESCRIPTION
                    "Indicates the non-unicast monitoring start time for the uplink port.
                     The start time needs only the hour, minute, and second values,
                     and thus only the fifth, sixth, and seventh bytes are used, where,
                     the fifth byte indicates the hour value of the
                     start time, the sixth byte indicates the minute value,
                     and the seventh byte indicates the second value.
                     Other bytes are reserved and are filled in 0.
                     For example, if the start time is 08:30:00,
                     the value is presented as 0x00 0x00 0x00 0x00 0x08 0x1E 0x00 0x00 0x00 0x00 0x00.
                     The time must be from 00:00:00 to 23:59:59.
                    "
            ::= { hwDslamNonUnicastUpportMonitor 7 }

            hwDslamNonUnicastUpportMonitorEndTime OBJECT-TYPE
                SYNTAX DateAndTime
                MAX-ACCESS   read-write
                STATUS       current
                DESCRIPTION
                    "Indicates the non-unicast monitoring end time for the uplink port.
                     The end time needs only the hour, minute, and second values,
                     and thus only the fifth, sixth, and seventh bytes are used, where,
                     the fifth byte indicates the hour value of the
                     start time, the sixth byte indicates the minute value,
                     and the seventh byte indicates the second value.
                     Other bytes are reserved and are filled in 0.
                     For example, if the end time is 23:59:59,
                     the value is presented as 0x00 0x00 0x00 0x00 0x17 0x3B 0x3B 0x00 0x00 0x00 0x00.
                     The time must be from 00:00:00 to 23:59:59.
                    "
            ::= { hwDslamNonUnicastUpportMonitor 8 }

        hwDslamNonUnicastUpportMonitorMemberTable OBJECT-TYPE
            SYNTAX SEQUENCE OF HwDslamNonUnicastUpportMonitorMemberEntry
            MAX-ACCESS not-accessible
            STATUS current
            DESCRIPTION
                "Configures the non-unicast monitoring table of uplink ports.
                 The index of this table is hwDslamNonUnicastUpportMonitorIfIndex.
                "
        ::= { hwDslamNonUnicastUpportMonitor 9 }

        hwDslamNonUnicastUpportMonitorMemberEntry OBJECT-TYPE
            SYNTAX HwDslamNonUnicastUpportMonitorMemberEntry
            MAX-ACCESS not-accessible
            STATUS current
            DESCRIPTION
                "Configures the non-unicast monitoring table of uplink ports.
                 The index of this entry is hwDslamNonUnicastUpportMonitorIfIndex.
                "
            INDEX { hwDslamNonUnicastUpportMonitorIfIndex }
        ::= { hwDslamNonUnicastUpportMonitorMemberTable 1 }

        HwDslamNonUnicastUpportMonitorMemberEntry ::=
            SEQUENCE {
                hwDslamNonUnicastUpportMonitorIfIndex                                   Integer32,
                hwDslamNonUnicastUpportMonitorRowStatus                                 RowStatus,
                hwDslamNonUnicastUpportMonitorBroadcastThd                              Integer32,
                hwDslamNonUnicastUpportMonitorUnknownUnicastThd                         Integer32,
                hwDslamNonUnicastUpportMonitorUnknownMulticastThd                       Integer32,
                hwDslamNonUnicastUpportMonitorBroadcastThdActiveValue                   Integer32,
                hwDslamNonUnicastUpportMonitorUnknownUnicastThdActiveValue              Integer32,
                hwDslamNonUnicastUpportMonitorUnknownMulticastThdActiveValue            Integer32
                }

                hwDslamNonUnicastUpportMonitorIfIndex OBJECT-TYPE
                    SYNTAX Integer32
                    MAX-ACCESS not-accessible
                    STATUS current
                    DESCRIPTION
                        "Indicates the index of the non-unicast monitoring table of uplink ports.
                        "
                ::= { hwDslamNonUnicastUpportMonitorMemberEntry 1 }

                hwDslamNonUnicastUpportMonitorRowStatus OBJECT-TYPE
                    SYNTAX RowStatus
                    MAX-ACCESS read-create
                    STATUS current
                    DESCRIPTION
                        "Row status, used to query, create, modify, and delete a non-unicast monitoring table of uplink ports.
                         It supports the active(1), createAndGo(4), and destroy(6) operations.
                         During query, the value of this leaf is always active(1).
                         During deletion, specify the value of this leaf to destroy(6).
                         During creation, specify the value of this leaf to createAndGo(4).
                         To modify the parameters of a non-unicast monitoring table of uplink ports, this leaf need not be issued together.
                         Options:
                         1. active(1)               - Indicates the query operation.
                         2. createAndGo(4)          - Indicates the creating operation.
                         3. destroy(6)              - Indicates the deleting operation.
                        "
                ::= { hwDslamNonUnicastUpportMonitorMemberEntry 2 }

                hwDslamNonUnicastUpportMonitorBroadcastThd OBJECT-TYPE
                    SYNTAX Integer32 (0..16)
                    MAX-ACCESS   read-write
                    STATUS       current
                    DESCRIPTION
                        "Indicates the broadcast monitoring threshold for the uplink port.
                         When the threshold for monitoring non-unicast packets on the specified port is set to auto,
                         this threshold takes effect 2 levels above the traffic suppression threshold configured on the port
                         (The unknown multicast monitoring threshold for the port on the ETHB board takes effect 2
                         levels above the traffic suppression threshold configured on the board).
                         When no suppression or full suppression is configured on the port,
                         the globally-configured default-auto-value takes effect.0 indicates auto.
                         For the bandwidth range corresponding to the non-unicast threshold,
                         see hwDslamNonUnicastUpportMonitorBroadcastThdActiveValue description.
                         Default: 0
                        "
                ::= { hwDslamNonUnicastUpportMonitorMemberEntry 3 }

                hwDslamNonUnicastUpportMonitorUnknownUnicastThd OBJECT-TYPE
                    SYNTAX Integer32 (0..16)
                    MAX-ACCESS   read-write
                    STATUS       current
                    DESCRIPTION
                        "Indicates the unknown unicast monitoring threshold for the uplink port.
                         When the threshold for monitoring non-unicast packets on the specified port is set to auto,
                         this threshold takes effect 2 levels above the traffic suppression threshold configured on the port
                         (The unknown multicast monitoring threshold for the port on the ETHB board takes effect 2
                         levels above the traffic suppression threshold configured on the board).
                         When no suppression or full suppression is configured on the port,
                         the globally-configured default-auto-value takes effect.0 indicates auto.
                         For the bandwidth range corresponding to the non-unicast threshold,
                         see hwDslamNonUnicastUpportMonitorUnknownUnicastThdActiveValue description.
                         Default: 0
                        "
                ::= { hwDslamNonUnicastUpportMonitorMemberEntry 4 }

                hwDslamNonUnicastUpportMonitorUnknownMulticastThd OBJECT-TYPE
                    SYNTAX Integer32 (0..16)
                    MAX-ACCESS   read-write
                    STATUS       current
                    DESCRIPTION
                        "Indicates the unknown multicast monitoring threshold for the uplink port.
                         When the threshold for monitoring non-unicast packets on the specified port is set to auto,
                         this threshold takes effect 2 levels above the traffic suppression threshold configured on the port
                         (The unknown multicast monitoring threshold for the port on the ETHB board takes effect 2
                         levels above the traffic suppression threshold configured on the board).
                         When no suppression or full suppression is configured on the port,
                         the globally-configured default-auto-value takes effect.0 indicates auto.
                         For the bandwidth range corresponding to the non-unicast threshold,
                         see hwDslamNonUnicastUpportMonitorUnknownMulticastThdActiveValue description.
                         Default: 0
                        "
                ::= { hwDslamNonUnicastUpportMonitorMemberEntry 5 }

                hwDslamNonUnicastUpportMonitorBroadcastThdActiveValue OBJECT-TYPE
                    SYNTAX Integer32 (1..16)
                    MAX-ACCESS   read-only
                    STATUS       current
                    DESCRIPTION
                        "Indicates the broadcast monitoring threshold for the uplink port.
                         When the threshold for monitoring non-unicast packets on the specified port is set to auto,
                         this threshold takes effect 2 levels above the traffic suppression threshold configured on the port
                         (The unknown multicast monitoring threshold for the port on the ETHB board takes effect 2
                         levels above the traffic suppression threshold configured on the board).
                         When no suppression or full suppression is configured on the port,
                         the globally-configured default-auto-value takes effect.
                         The effective broadcast monitoring threshold.
                         The non-unicast threshold definition corresponding bandwidth ranges are listed as follows:
                         ------------------------------------------------------------------------------
                          NO.         Min bandwidth(kbps)         Max bandwidth(kbps)         Packets/s
                         ------------------------------------------------------------------------------
                            1                           6                         145                12
                            2                          12                         291                24
                            3                          24                         582                48
                            4                          48                        1153                95
                            5                          97                        2319               191
                            6                         195                        4639               382
                            7                         390                        9265               763
                            8                         781                       18531              1526
                            9                        1562                       37063              3052
                           10                        3125                       74126              6104
                           11                        6249                      148241             12207
                           12                       12499                      296483             24414
                           13                       24999                      592967             48828
                           14                       49999                     1185934             97656
                           15                       99999                     2371868            195312
                           16                      199999                     4743737            390624
                         ------------------------------------------------------------------------------
                        "
                ::= { hwDslamNonUnicastUpportMonitorMemberEntry 6 }

                hwDslamNonUnicastUpportMonitorUnknownUnicastThdActiveValue OBJECT-TYPE
                    SYNTAX Integer32 (1..16)
                    MAX-ACCESS   read-only
                    STATUS       current
                    DESCRIPTION
                        "Indicates the unknown unicast monitoring threshold for the uplink port.
                         When the threshold for monitoring non-unicast packets on the specified port is set to auto,
                         this threshold takes effect 2 levels above the traffic suppression threshold configured on the port
                         (The unknown multicast monitoring threshold for the port on the ETHB board takes effect 2
                         levels above the traffic suppression threshold configured on the board).
                         When no suppression or full suppression is configured on the port,
                         the globally-configured default-auto-value takes effect.
                         The effective unknown unicast monitoring threshold.
                         The non-unicast threshold definition corresponding bandwidth ranges are listed as follows:
                         ------------------------------------------------------------------------------
                          NO.         Min bandwidth(kbps)         Max bandwidth(kbps)         Packets/s
                         ------------------------------------------------------------------------------
                            1                           6                         145                12
                            2                          12                         291                24
                            3                          24                         582                48
                            4                          48                        1153                95
                            5                          97                        2319               191
                            6                         195                        4639               382
                            7                         390                        9265               763
                            8                         781                       18531              1526
                            9                        1562                       37063              3052
                           10                        3125                       74126              6104
                           11                        6249                      148241             12207
                           12                       12499                      296483             24414
                           13                       24999                      592967             48828
                           14                       49999                     1185934             97656
                           15                       99999                     2371868            195312
                           16                      199999                     4743737            390624
                         ------------------------------------------------------------------------------
                        "
                ::= { hwDslamNonUnicastUpportMonitorMemberEntry 7 }

                hwDslamNonUnicastUpportMonitorUnknownMulticastThdActiveValue OBJECT-TYPE
                    SYNTAX Integer32 (1..16)
                    MAX-ACCESS   read-only
                    STATUS       current
                    DESCRIPTION
                        "Indicates the unknown multicast monitoring threshold for the uplink port.
                         When the threshold for monitoring non-unicast packets on the specified port is set to auto,
                         this threshold takes effect 2 levels above the traffic suppression threshold configured on the port
                         (The unknown multicast monitoring threshold for the port on the ETHB board takes effect 2
                         levels above the traffic suppression threshold configured on the board).
                         When no suppression or full suppression is configured on the port,
                         the globally-configured default-auto-value takes effect.
                         The effective unknown multicast monitoring threshold.
                         The non-unicast threshold definition corresponding bandwidth ranges are listed as follows:
                         ------------------------------------------------------------------------------
                          NO.         Min bandwidth(kbps)         Max bandwidth(kbps)         Packets/s
                         ------------------------------------------------------------------------------
                            1                           6                         145                12
                            2                          12                         291                24
                            3                          24                         582                48
                            4                          48                        1153                95
                            5                          97                        2319               191
                            6                         195                        4639               382
                            7                         390                        9265               763
                            8                         781                       18531              1526
                            9                        1562                       37063              3052
                           10                        3125                       74126              6104
                           11                        6249                      148241             12207
                           12                       12499                      296483             24414
                           13                       24999                      592967             48828
                           14                       49999                     1185934             97656
                           15                       99999                     2371868            195312
                           16                      199999                     4743737            390624
                         ------------------------------------------------------------------------------
                        "
                ::= { hwDslamNonUnicastUpportMonitorMemberEntry 8 }

        hwDslamNonUnicastUpportMonitorRecordTable OBJECT-TYPE
            SYNTAX SEQUENCE OF HwDslamNonUnicastUpportMonitorRecordEntry
            MAX-ACCESS not-accessible
            STATUS current
            DESCRIPTION
                "Indicates the non-unicast monitoring record table of uplink ports.
                 The index of this table is hwDslamNonUnicastUpportMonitorRecordIfIndex, hwDslamNonUnicastUpportMonitorRecordIndex.
                "
            ::= { hwDslamNonUnicastUpportMonitor 10 }

        hwDslamNonUnicastUpportMonitorRecordEntry OBJECT-TYPE
            SYNTAX HwDslamNonUnicastUpportMonitorRecordEntry
            MAX-ACCESS not-accessible
            STATUS current
            DESCRIPTION
                "Indicates the non-unicast monitoring record table of uplink ports.
                 The index of this entry is hwDslamNonUnicastUpportMonitorRecordIfIndex, hwDslamNonUnicastUpportMonitorRecordIndex.
                "
            INDEX { hwDslamNonUnicastUpportMonitorRecordIfIndex, hwDslamNonUnicastUpportMonitorRecordIndex}
            ::= { hwDslamNonUnicastUpportMonitorRecordTable 1 }

        HwDslamNonUnicastUpportMonitorRecordEntry ::=
            SEQUENCE {
                hwDslamNonUnicastUpportMonitorRecordIfIndex
                    Integer32,
                hwDslamNonUnicastUpportMonitorRecordIndex
                    Integer32,
                hwDslamNonUnicastUpportMonitorRecordTime
                    DateAndTime,
                hwDslamNonUnicastUpportMonitorBroadcastRate
                    Counter64,
                hwDslamNonUnicastUpportMonitorUnknownUnicastRate
                    Counter64,
                hwDslamNonUnicastUpportMonitorUnknownMulticastRate
                    Counter64
            }

            hwDslamNonUnicastUpportMonitorRecordIfIndex OBJECT-TYPE
                SYNTAX Integer32
                MAX-ACCESS not-accessible
                STATUS current
                DESCRIPTION
                    "Indicates the level-1 index of the non-unicast monitoring table of uplink ports.
                    "
            ::= { hwDslamNonUnicastUpportMonitorRecordEntry 1 }

            hwDslamNonUnicastUpportMonitorRecordIndex OBJECT-TYPE
                SYNTAX Integer32
                MAX-ACCESS not-accessible
                STATUS current
                DESCRIPTION
                "Indicates the level-2 index of the non-unicast monitoring table of uplink ports.
                "
            ::= { hwDslamNonUnicastUpportMonitorRecordEntry 2 }

            hwDslamNonUnicastUpportMonitorRecordTime OBJECT-TYPE
                SYNTAX DateAndTime
                MAX-ACCESS read-only
                STATUS current
                DESCRIPTION
                    "Indicates period end time of non-unicast packet statistics.
                    "
            ::= { hwDslamNonUnicastUpportMonitorRecordEntry 3 }

            hwDslamNonUnicastUpportMonitorBroadcastRate OBJECT-TYPE
                SYNTAX Counter64
                UNITS  "pps"
                MAX-ACCESS read-only
                STATUS current
                DESCRIPTION
                    "Indicates broadcast packet rate the uplink port.
                     "
            ::= { hwDslamNonUnicastUpportMonitorRecordEntry 4 }

            hwDslamNonUnicastUpportMonitorUnknownUnicastRate OBJECT-TYPE
                SYNTAX Counter64
                UNITS  "pps"
                MAX-ACCESS read-only
                STATUS current
                DESCRIPTION
                    "Indicates unknown unicast packet rate the uplink port.
                    "
            ::= { hwDslamNonUnicastUpportMonitorRecordEntry 5 }

            hwDslamNonUnicastUpportMonitorUnknownMulticastRate OBJECT-TYPE
                SYNTAX Counter64
                UNITS  "pps"
                MAX-ACCESS read-only
                STATUS current
                DESCRIPTION
                    "Indicates unknown multicast packet rate the uplink port.
                    "
            ::= { hwDslamNonUnicastUpportMonitorRecordEntry 6 }

        hwDslamNonUnicastUpportMonitorPeakRecordTable OBJECT-TYPE
            SYNTAX SEQUENCE OF HwDslamNonUnicastUpportMonitorPeakRecordEntry
            MAX-ACCESS not-accessible
            STATUS current
            DESCRIPTION
                "Indicates the table recording the monitored peak non-unicast packets on the uplink port.
                 The index of this table is hwDslamNonUnicastUpportMonitorPeakRecordIfIndex.
                "
            ::= { hwDslamNonUnicastUpportMonitor 11 }

        hwDslamNonUnicastUpportMonitorPeakRecordEntry OBJECT-TYPE
            SYNTAX HwDslamNonUnicastUpportMonitorPeakRecordEntry
            MAX-ACCESS not-accessible
            STATUS current
            DESCRIPTION
                "Indicates the table recording the monitored peak non-unicast packets on the uplink port.
                 The index of this entry is hwDslamNonUnicastUpportMonitorPeakRecordIfIndex.
                "
            INDEX { hwDslamNonUnicastUpportMonitorPeakRecordIfIndex }
            ::= { hwDslamNonUnicastUpportMonitorPeakRecordTable 1 }

        HwDslamNonUnicastUpportMonitorPeakRecordEntry ::=
            SEQUENCE {
                hwDslamNonUnicastUpportMonitorPeakRecordIfIndex
                    Integer32,
                hwDslamNonUnicastUpportMonitorPeakBroadcastRecordTime
                    DateAndTime,
                hwDslamNonUnicastUpportMonitorPeakBroadcastRate
                    Counter64,
                hwDslamNonUnicastUpportMonitorPeakUnknownUnicastRecordTime
                    DateAndTime,
                hwDslamNonUnicastUpportMonitorPeakUnknownUnicastRate
                    Counter64,
                hwDslamNonUnicastUpportMonitorPeakUnknownMulticastRecordTime
                    DateAndTime,
                hwDslamNonUnicastUpportMonitorPeakUnknownMulticastRate
                    Counter64
             }

            hwDslamNonUnicastUpportMonitorPeakRecordIfIndex OBJECT-TYPE
                SYNTAX Integer32
                MAX-ACCESS not-accessible
                STATUS current
                DESCRIPTION
                   "Indicates the index of the table recording the monitored peak non-unicast packets on the uplink port.
                   "
            ::= { hwDslamNonUnicastUpportMonitorPeakRecordEntry 1 }

            hwDslamNonUnicastUpportMonitorPeakBroadcastRecordTime OBJECT-TYPE
                SYNTAX DateAndTime
                MAX-ACCESS read-only
                STATUS current
                DESCRIPTION
                    "Indicates the end time of peak broadcast packet measurement.
                    "
            ::= { hwDslamNonUnicastUpportMonitorPeakRecordEntry 2 }

            hwDslamNonUnicastUpportMonitorPeakBroadcastRate OBJECT-TYPE
                SYNTAX Counter64
                UNITS  "pps"
                MAX-ACCESS read-only
                STATUS current
                DESCRIPTION
                    "Indicates broadcast packet rate the uplink port.
                    "
            ::= { hwDslamNonUnicastUpportMonitorPeakRecordEntry 3 }

            hwDslamNonUnicastUpportMonitorPeakUnknownUnicastRecordTime OBJECT-TYPE
                SYNTAX DateAndTime
                MAX-ACCESS read-only
                STATUS current
                DESCRIPTION
                    "Indicates the end time of peak unknown unicast packet measurement.
                    "
            ::= { hwDslamNonUnicastUpportMonitorPeakRecordEntry 4 }

            hwDslamNonUnicastUpportMonitorPeakUnknownUnicastRate OBJECT-TYPE
                SYNTAX Counter64
                UNITS  "pps"
                MAX-ACCESS read-only
                STATUS current
                DESCRIPTION
                    "Indicates unknow unicast packet rate the uplink port.
                    "
            ::= { hwDslamNonUnicastUpportMonitorPeakRecordEntry 5 }

            hwDslamNonUnicastUpportMonitorPeakUnknownMulticastRecordTime OBJECT-TYPE
                SYNTAX DateAndTime
                MAX-ACCESS read-only
                STATUS current
                DESCRIPTION
                    "Indicates the end time of peak unknow multicast packet measurement.
                    "
            ::= { hwDslamNonUnicastUpportMonitorPeakRecordEntry 6 }

            hwDslamNonUnicastUpportMonitorPeakUnknownMulticastRate OBJECT-TYPE
                SYNTAX Counter64
                UNITS  "pps"
                MAX-ACCESS read-only
                STATUS current
                DESCRIPTION
                    "Indicates unknow multicast packet rate the uplink port.
                    "
            ::= { hwDslamNonUnicastUpportMonitorPeakRecordEntry 7 }

	    hwAggLoadbalancingConfigTable OBJECT-TYPE
	        SYNTAX SEQUENCE OF HwAggLoadbalancingConfigEntry
	        MAX-ACCESS not-accessible
	        STATUS current
	        DESCRIPTION
	            "This table is used to manage the configuration information of an aggregation group loadbalancing.
		     The index of this table is hwAggLBConfigIndex.
	            "
	        ::= { hwExtInterface 13 }

	    hwAggLoadbalancingConfigEntry OBJECT-TYPE
	        SYNTAX HwAggLoadbalancingConfigEntry
	        MAX-ACCESS not-accessible
	        STATUS current
	        DESCRIPTION
	            "This table is used to manage the configuration information of an aggregation group loadbalancing.
		     The index of this entry is hwAggLBConfigIndex.
	            "
	        INDEX { hwAggLBConfigIndex }
	        ::= { hwAggLoadbalancingConfigTable 1 }

	    HwAggLoadbalancingConfigEntry ::=
			SEQUENCE {
			    hwAggLBConfigIndex
					Integer32,
			    hwAggLBSrcMacAddress
			        OCTET STRING,
			    hwAggLBDstMacAddress
			        OCTET STRING,
			    hwAggLBIpAddressType
			        INTEGER,
			    hwAggLBProtocol
			        Integer32,
			    hwAggLBSrcIpAddress
			        IpAddress,
			    hwAggLBDstIpAddress
			        IpAddress,
			    hwAggLBSrcIpv6Address
			        InetAddress,
			    hwAggLBDstIpv6Address
			        InetAddress,
			    hwAggLBSrcPort
			        Integer32,
			    hwAggLBDstPort
	                Integer32,
	          	hwAggLBInportIndex
	              	Unsigned32
	            }

	    hwAggLBConfigIndex OBJECT-TYPE
	        SYNTAX Integer32
	        MAX-ACCESS not-accessible
	        STATUS current
	        DESCRIPTION
	            "IfIndex of the master port in an aggregation group.
	            "
	        ::= { hwAggLoadbalancingConfigEntry 1 }

	    hwAggLBSrcMacAddress OBJECT-TYPE
	        SYNTAX OCTET STRING(SIZE (6..17))
	        MAX-ACCESS read-write
	        STATUS current
	        DESCRIPTION
	            "The source MAC address of the packet.
			      The following is an example of the input format of the MAC address:
			      If the MAC address is 00e0-fc11-0000, enter # 0x00 0xe0 0xfc 0x11 0x00 0x00 or the character string 00-e0-fc-11-00-00.
			      A device may support only one format.
			    "
	        ::= { hwAggLoadbalancingConfigEntry 2 }

	    hwAggLBDstMacAddress OBJECT-TYPE
	        SYNTAX OCTET STRING(SIZE (6..17))
	        MAX-ACCESS read-write
	        STATUS current
	        DESCRIPTION
	            "The destination MAC address of the packet.
		         The following is an example of the input format of the MAC address:
		         If the MAC address is 00e0-fc11-0000, enter # 0x00 0xe0 0xfc 0x11 0x00 0x00 or the character string 00-e0-fc-11-00-00.
		         A device may support only one format.
		        "
	        ::= { hwAggLoadbalancingConfigEntry 3 }

	    hwAggLBIpAddressType OBJECT-TYPE
	        SYNTAX INTEGER
	        {
	         ipv4(1),
	         ipv6(2)
	        }
	        MAX-ACCESS read-write
	        STATUS current
	        DESCRIPTION
	            "Indicates the IP address type.
	             Options:
	             1. ipv4(1)  -indicates that the IP address type is ipv4
	             2. ipv6(2)  -indicates that the IP address type is ipv6
	            "
	        ::= { hwAggLoadbalancingConfigEntry 4 }

	    hwAggLBProtocol OBJECT-TYPE
	        SYNTAX Integer32 (0..255)
	        MAX-ACCESS read-write
	        STATUS current
	        DESCRIPTION
	            "The protocol of the IP packets.
 	             Range: 0-255

			 	 The common types include:
			 	 ICMP: indicates the Internet Control Message Protocol with protocol ID 1
			 	 IGMP: indicates the Internet Group management Protocol with protocol ID 1
			 	 TCP: indicates the Transmission Control Protocol with protocol ID 6
			 	 UDP: indicates the User Datagram Protocol with protocol ID 17
	            "
	        ::= { hwAggLoadbalancingConfigEntry 5 }

	    hwAggLBSrcIpAddress OBJECT-TYPE
	        SYNTAX IpAddress
	        MAX-ACCESS read-write
	        STATUS current
	        DESCRIPTION
	            "The source IPv4 address of the packet.
	            "
	        ::= { hwAggLoadbalancingConfigEntry 6 }


	    hwAggLBDstIpAddress OBJECT-TYPE
	        SYNTAX IpAddress
	        MAX-ACCESS read-write
	        STATUS current
	        DESCRIPTION
	            "The destination IPv4 address of the packet.
	            "
	        ::= { hwAggLoadbalancingConfigEntry 7 }

	    hwAggLBSrcIpv6Address OBJECT-TYPE
	        SYNTAX InetAddress
	        MAX-ACCESS read-write
	        STATUS current
	        DESCRIPTION
	            "The source IPv6 address of the packet.
	            "
	        ::= { hwAggLoadbalancingConfigEntry 8 }


	    hwAggLBDstIpv6Address OBJECT-TYPE
	        SYNTAX InetAddress
	        MAX-ACCESS read-write
	        STATUS current
	        DESCRIPTION
	            "The destination IPv6 address of the packet.
	            "
	        ::= { hwAggLoadbalancingConfigEntry 9 }

	    hwAggLBSrcPort OBJECT-TYPE
	        SYNTAX Integer32 (0..65535)
	        MAX-ACCESS read-write
	        STATUS current
	        DESCRIPTION
	            "The specify source port of the packet.
			     Range: 0-65535
	            "
	        ::= { hwAggLoadbalancingConfigEntry 10 }

	    hwAggLBDstPort OBJECT-TYPE
	        SYNTAX Integer32 (0..65535)
	        MAX-ACCESS read-write
	        STATUS current
	        DESCRIPTION
	            "The specify destination port of the packet.
	             Range: 0-65535
	            "
	        ::= { hwAggLoadbalancingConfigEntry 11 }

		hwAggLBInportIndex OBJECT-TYPE
	      SYNTAX Unsigned32
	      MAX-ACCESS read-write
	      STATUS current
	      DESCRIPTION
	          "IfIndex of the input port.
	          "
	      ::= { hwAggLoadbalancingConfigEntry 12 }

	    hwAggLoadbalancingTable OBJECT-TYPE
	        SYNTAX SEQUENCE OF HwAggLoadbalancingEntry
	        MAX-ACCESS not-accessible
	        STATUS current
	        DESCRIPTION
	            "This table is used to get the result of the packet selection port for an aggregation group.
		     The index of this table is hwAggLBIndex.
				"
	        ::= { hwExtInterface 14 }

	    hwAggLoadbalancingEntry OBJECT-TYPE
	        SYNTAX HwAggLoadbalancingEntry
	        MAX-ACCESS not-accessible
	        STATUS current
	        DESCRIPTION
	            "This table is used to get the result of the packet selection port for an aggregation group.
		     The index of this entry is hwAggLBIndex.
	            "
	        INDEX { hwAggLBIndex }
	        ::= { hwAggLoadbalancingTable 1 }

	    HwAggLoadbalancingEntry ::=
	        SEQUENCE {
			    hwAggLBIndex
					Integer32,
	            hwAggLBSelectIndex
	                Integer32
				}

	    hwAggLBIndex OBJECT-TYPE
	        SYNTAX Integer32
	        MAX-ACCESS not-accessible
	        STATUS current
	        DESCRIPTION
	            "IfIndex of the master port in an aggregation group.
	            "
	        ::= { hwAggLoadbalancingEntry 1 }

	    hwAggLBSelectIndex OBJECT-TYPE
	        SYNTAX Integer32
	        MAX-ACCESS read-only
	        STATUS current
	        DESCRIPTION
	            "The result of the packet selection port for an aggregation group.
	            "
	        ::= { hwAggLoadbalancingEntry 2 }

	--hwPort10GLicControlObjects
        hwPort10GLicControlObjects OBJECT IDENTIFIER ::= { hwEthernetPort  41}
            hwPort10GLicPortNum OBJECT-TYPE
                SYNTAX Integer32
                MAX-ACCESS read-only
                STATUS     current
                DESCRIPTION
				    "Indicates the number of 10G uplink port."
            ::= { hwPort10GLicControlObjects 1 }

            hwPort10GLicRtuAuthSwitch OBJECT-TYPE
                SYNTAX INTEGER
                {
                    enable(1),
                    disable(2)
                }
                MAX-ACCESS   read-write
                STATUS       current
                DESCRIPTION
                    "Indicates 10G uplink port rtu license switch
					 Options:
					 1. enable(1)               - Indicates that the switch of 10G uplink port rtu license is eabled.
					 2. disable(2)              - Indicates that the switch of 10G uplink port rtu license is disabled.
					 Default: disable(2)
                    "
            ::= { hwPort10GLicControlObjects 2 }

   hwExtProtocolForceForwardingPolicyTable OBJECT IDENTIFIER ::= { hwEthernetPort 42 }

   hwExtPimUserForceForwarding OBJECT-TYPE
       SYNTAX INTEGER
           {
           enable(1),
           disable(2)
           }
       MAX-ACCESS read-write
       STATUS current
       DESCRIPTION
           "Indicates the forcible transparent transmission switch of PIM protocol packets on the user side.
            Options:
            1. enable(1)  -Indicates that the forcible transparent transmission of PIM protocol packets on the user side is enabled.
            2. disable(2) -Indicates that the forcible transparent transmission of PIM protocol packets on the user side is disabled.
            Default: enable(1)
           "
       ::= { hwExtProtocolForceForwardingPolicyTable 1 }

   hwExtPimUplinkForceForwarding OBJECT-TYPE
       SYNTAX INTEGER
           {
           enable(1),
           disable(2)
           }
       MAX-ACCESS read-write
       STATUS current
       DESCRIPTION
           "Indicates the forcible transparent transmission switch of PIM protocol packets on the network side.
            Options:
            1. enable(1)  -Indicates that the forcible transparent transmission of PIM protocol packets on the network side is enabled.
            2. disable(2) -Indicates that the forcible transparent transmission of PIM protocol packets on the network side is disabled.
            Default: enable(1)
           "
       ::= { hwExtProtocolForceForwardingPolicyTable 2 }

   hwExtLdpUserForceForwarding OBJECT-TYPE
       SYNTAX INTEGER
           {
           enable(1),
           disable(2)
           }
       MAX-ACCESS read-write
       STATUS current
       DESCRIPTION
           "Indicates the forcible transparent transmission switch of LDP protocol packets on the user side.
            Options:
            1. enable(1)  -Indicates that the forcible transparent transmission of LDP protocol packets on the user side is enabled.
            2. disable(2) -Indicates that the forcible transparent transmission of LDP protocol packets on the user side is disabled.
            Default: enable(1)
           "
       ::= { hwExtProtocolForceForwardingPolicyTable 3 }

   hwExtLdpUplinkForceForwarding OBJECT-TYPE
       SYNTAX INTEGER
           {
           enable(1),
           disable(2)
           }
       MAX-ACCESS read-write
       STATUS current
       DESCRIPTION
           "Indicates the forcible transparent transmission switch of LDP protocol packets on the network side.
            Options:
            1. enable(1)  -Indicates that the forcible transparent transmission of LDP protocol packets on the network side is enabled.
            2. disable(2) -Indicates that the forcible transparent transmission of LDP protocol packets on the network side is disabled.
            Default: enable(1)
           "
       ::= { hwExtProtocolForceForwardingPolicyTable 4 }

   hwExtVrrpUserForceForwarding OBJECT-TYPE
       SYNTAX INTEGER
           {
           enable(1),
           disable(2)
           }
       MAX-ACCESS read-write
       STATUS current
       DESCRIPTION
           "Indicates the forcible transparent transmission switch of VRRP protocol packets on the user side.
            Options:
            1. enable(1)  -Indicates that the forcible transparent transmission of VRRP protocol packets on the user side is enabled.
            2. disable(2) -Indicates that the forcible transparent transmission of VRRP protocol packets on the user side is disabled.
            Default: enable(1)
           "
       ::= { hwExtProtocolForceForwardingPolicyTable 5 }

   hwExtVrrpUplinkForceForwarding OBJECT-TYPE
       SYNTAX INTEGER
           {
           enable(1),
           disable(2)
           }
       MAX-ACCESS read-write
       STATUS current
       DESCRIPTION
           "Indicates the forcible transparent transmission switch of VRRP protocol packets on the network side.
            Options:
            1. enable(1)  -Indicates that the forcible transparent transmission of VRRP protocol packets on the network side is enabled.
            2. disable(2) -Indicates that the forcible transparent transmission of VRRP protocol packets on the network side is disabled.
            Default: enable(1)
           "
       ::= { hwExtProtocolForceForwardingPolicyTable 6 }

   hwExtNtpUserForceForwarding OBJECT-TYPE
       SYNTAX INTEGER
           {
           enable(1),
           disable(2)
           }
       MAX-ACCESS read-write
       STATUS current
       DESCRIPTION
           "Indicates the forcible transparent transmission switch of NTP-multicast protocol packets on the user side.
            Options:
            1. enable(1)  -Indicates that the forcible transparent transmission of NTP-multicast protocol packets on the user side is enabled.
            2. disable(2) -Indicates that the forcible transparent transmission of NTP-multicast protocol packets on the user side is disabled.
            Default: enable(1)
           "
       ::= { hwExtProtocolForceForwardingPolicyTable 7 }

   hwExtNtpUplinkForceForwarding OBJECT-TYPE
       SYNTAX INTEGER
           {
           enable(1),
           disable(2)
           }
       MAX-ACCESS read-write
       STATUS current
       DESCRIPTION
           "Indicates the forcible transparent transmission switch of NTP-multicast protocol packets on the network side.
            Options:
            1. enable(1)  -Indicates that the forcible transparent transmission of NTP-multicast protocol packets on the network side is enabled.
            2. disable(2) -Indicates that the forcible transparent transmission of NTP-multicast protocol packets on the network side is disabled.
            Default: enable(1)
           "
       ::= { hwExtProtocolForceForwardingPolicyTable 8 }

        hwAggregatePortTable OBJECT-TYPE
            SYNTAX SEQUENCE OF HwAggregatePortEntry
            MAX-ACCESS not-accessible
            STATUS current
            DESCRIPTION
            "Indicates the port information of an aggregation group.
            The indexes of this table are hwAggregateIndex and hwAggregatePortIndex.
            "
            ::= { hwExtInterface 15 }

        hwAggregatePortEntry OBJECT-TYPE
            SYNTAX HwAggregatePortEntry
            MAX-ACCESS not-accessible
            STATUS current
            DESCRIPTION
            "Indicates the port information of an aggregation group.
            The indexes of this entry are hwAggregateIndex and hwAggregatePortIndex.
            "
            INDEX { hwAggregateIndex, hwAggregatePortIndex }
            ::= { hwAggregatePortTable 1 }

        HwAggregatePortEntry ::=
        SEQUENCE {
            hwAggregateIndex
                InterfaceIndex,
            hwAggregatePortIndex
                InterfaceIndex,
            hwAggregatePortStatus
                INTEGER
        }

        hwAggregateIndex OBJECT-TYPE
            SYNTAX InterfaceIndex
            MAX-ACCESS not-accessible
            STATUS current
            DESCRIPTION
            "IfIndex of the master port in an aggregation group."
            ::= { hwAggregatePortEntry 1 }

        hwAggregatePortIndex OBJECT-TYPE
            SYNTAX InterfaceIndex
            MAX-ACCESS not-accessible
            STATUS current
            DESCRIPTION
            "IfIndex of the port in an aggregation group."
            ::= { hwAggregatePortEntry 2 }

        hwAggregatePortStatus OBJECT-TYPE
            SYNTAX INTEGER
            {
                forwarding(1),
                block(2)
            }
            MAX-ACCESS read-only
            STATUS current
            DESCRIPTION
            "Indicates the forwarding status of port in an aggregation group.
			Options:
			1. forwarding(1)  -Indicates that the forwarding status of the port in an aggregation group is forwarding.
			2. block(2)       -Indicates that the forwarding status of the port in an aggregation group is blocked."
            ::= { hwAggregatePortEntry 3 }
END
