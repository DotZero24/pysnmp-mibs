-- ===================================================================
-- Copyright (C) 2018 by HUAWEI TECHNOLOGIES. All rights reserved.
-- Description:
-- Reference:
-- Version: V1.02
-- ===================================================================


    HUAWEI-SYS-RES-TRAP-MIB DEFINITIONS ::= BEGIN

        IMPORTS
            OBJECT-GROUP, MODULE-COMPLIANCE, NOTIFICATION-GROUP
                FROM SNMPv2-CONF
            DisplayString, RowStatus
                FROM SNMPv2-TC
            TimeTicks, Integer32, Unsigned32, IpAddress, Counter32, OBJECT-TYPE,
            MODULE-IDENTITY, NOTIFICATION-TYPE
                FROM SNMPv2-SMI
            hwDatacomm
                FROM HUAWEI-MIB;


        hwSysResTrapMIB  MODULE-IDENTITY
            LAST-UPDATED "201812221150Z"
            ORGANIZATION
                  "Huawei Technologies Co.,Ltd."
            CONTACT-INFO
                  "Huawei Industrial Base
                   Bantian, Longgang
                   Shenzhen 518129
                   People's Republic of China
                   Website: http://www.huawei.com
                   Email: support@huawei.com
                  "

            DESCRIPTION
            "This MIB is used to bind system resource traps."

			REVISION "201812221150Z"
            DESCRIPTION
            "Add DESCRIPTION of hwSysSecureRiskWarning at 2020-4-30."

             REVISION "201812221150Z"
            DESCRIPTION
            "Modify  DESCRIPTION  of  hwSysResourceExceedResume  at 2018-12-22."

            REVISION "201811121150Z"		-- Nov 12, 2018 at 11:50 GMT
            DESCRIPTION
            "The initial revision of this MIB module ."
            ::= { hwDatacomm 358 }


   		hwSysResTrapObjects OBJECT IDENTIFIER ::= { hwSysResTrapMIB 1 }

		hwSysResTrapTable OBJECT-TYPE
			SYNTAX SEQUENCE OF HwSysResTrapEntry
			MAX-ACCESS not-accessible
			STATUS current
			DESCRIPTION
				"This table container the objects infomation of public traps. "
			::= { hwSysResTrapObjects 1 }

		hwSysResTrapEntry OBJECT-TYPE
			SYNTAX HwSysResTrapEntry
			MAX-ACCESS not-accessible
			STATUS current
			DESCRIPTION
				"the entry of system resource trap."
			INDEX { hwSysResourceServiceIndex }
			::= { hwSysResTrapTable 1 }

		HwSysResTrapEntry ::=
		    SEQUENCE {
			hwSysResourceServiceID
			INTEGER,
		                   hwSysResourceType
	                                      Unsigned32,
			hwSysResourceServiceIndex
			OCTET STRING
		    }

		hwSysResourceServiceID OBJECT-TYPE
			SYNTAX INTEGER
			{
			    ospf(1)
			}
			MAX-ACCESS accessible-for-notify
			STATUS current
			DESCRIPTION
				"Th service ID of traps."
			::= { hwSysResTrapEntry 1 }

		hwSysResourceType OBJECT-TYPE
			SYNTAX Unsigned32 (0..100)
			MAX-ACCESS accessible-for-notify
			STATUS current
			DESCRIPTION
				"The type of traps."
			::= { hwSysResTrapEntry 2 }

		hwSysResourceServiceIndex OBJECT-TYPE
			SYNTAX OCTET STRING (SIZE (1..127))
			MAX-ACCESS accessible-for-notify
			STATUS current
			DESCRIPTION
				"The service index of traps."
			::= { hwSysResTrapEntry 3 }


	     hwSysResTrapNotifications  OBJECT IDENTIFIER ::= { hwSysResTrapMIB 2 }

	     hwSysResourceExceed  NOTIFICATION-TYPE
	     OBJECTS { hwSysResourceServiceID, hwSysResourceType, hwSysResourceServiceIndex }
	     STATUS current
	     DESCRIPTION
            "The whole device system resource was overloaded."
         ::= { hwSysResTrapNotifications 1 }

	     hwSysResourceExceedResume  NOTIFICATION-TYPE
	     OBJECTS { hwSysResourceServiceID, hwSysResourceType, hwSysResourceServiceIndex }
	     STATUS current
	     DESCRIPTION
            "The whole device system resource overload was recovered."
         ::= { hwSysResTrapNotifications 2 }

	     hwSysResourceThresholdExceed  NOTIFICATION-TYPE
	     OBJECTS { hwSysResourceServiceID, hwSysResourceType, hwSysResourceServiceIndex }
	     STATUS current
	     DESCRIPTION
            "The whole device system resource exceeded the threshold."
         ::= { hwSysResTrapNotifications 3 }

	     hwSysResourceThresholdExceedResume  NOTIFICATION-TYPE
	     OBJECTS { hwSysResourceServiceID, hwSysResourceType, hwSysResourceServiceIndex }
	     STATUS current
	     DESCRIPTION
            "The whole device system resource  fell from the threshold."
         ::= { hwSysResTrapNotifications 4 }

	     hwSysSecureRiskWarning  NOTIFICATION-TYPE
	     STATUS current
	     DESCRIPTION
            "Security risk warning."
         ::= { hwSysResTrapNotifications 5 }

	     hwSysSecureRiskWarningClear  NOTIFICATION-TYPE
	     STATUS current
	     DESCRIPTION
            "Security risk warning clear."
         ::= { hwSysResTrapNotifications 6 }

	     hwSysResTrapCompliances OBJECT IDENTIFIER ::= { hwSysResTrapMIB 3 }
 	     hwSysResTrapObjectsGroup OBJECT-GROUP
		 OBJECTS { hwSysResourceServiceID, hwSysResourceType, hwSysResourceServiceIndex }
		 STATUS current
		 DESCRIPTION
			"Objects group."
		::= { hwSysResTrapCompliances 1 }

        hwSysResTrapNotificationsGroup NOTIFICATION-GROUP
		NOTIFICATIONS { hwSysResourceExceed, hwSysResourceExceedResume, hwSysResourceThresholdExceed, hwSysResourceThresholdExceedResume }
		STATUS current
		DESCRIPTION
			"Notifications group."
		::= { hwSysResTrapCompliances 2 }

	    hwSysResTrapCompliance MODULE-COMPLIANCE
        STATUS current
	    DESCRIPTION
			"The compliance statement for entities which
				implement the Huawei SysResource mib."
	    MODULE -- this module
	    MANDATORY-GROUPS { hwSysResTrapObjectsGroup, hwSysResTrapNotificationsGroup }
	    ::= { hwSysResTrapCompliances 3 }

    END

--
-- HUAWEI-SYS-RES-TRAP-MIB.mib
--
