-- ===================================================================
-- Copyright (C) 2018 by HUAWEI TECHNOLOGIES. All rights reserved.
-- Description:
-- Reference:
-- Version: V1.01
-- ===================================================================


    HUAWEI-VCCHASSIS-MIB DEFINITIONS ::= BEGIN

        IMPORTS
            OBJECT-GROUP, MODULE-COMPLIANCE, NOTIFICATION-GROUP
                FROM SNMPv2-CONF
            DisplayString, RowStatus
                FROM SNMPv2-TC
            TimeTicks, Integer32, Unsigned32, IpAddress, Counter32, OBJECT-TYPE,
            MODULE-IDENTITY, NOTIFICATION-TYPE
                FROM SNMPv2-SMI
            hwDatacomm
                FROM HUAWEI-MIB;


        hwVCCHASSIS MODULE-IDENTITY
            LAST-UPDATED "201804231600Z"
            ORGANIZATION
                  "Huawei Technologies Co.,Ltd."
            CONTACT-INFO
                  "Huawei Industrial Base
  Bantian, Longgang
   Shenzhen 518129
   People's Republic of China
   Website: http://www.huawei.com
   Email: support@huawei.com
 "
            DESCRIPTION
                "Please provide the descritpion."

            REVISION    "201804231600Z"
            DESCRIPTION "V1.01, modify descritption."

            REVISION    "201802251600Z"
            DESCRIPTION "V1.00, initial version."



            ::= { hwDatacomm 185 }

         -- 1.3.6.1.4.1.2011.5.25.185.1
        hwVCCHASSISObjects OBJECT IDENTIFIER ::= { hwVCCHASSIS 1 }
        -- 1.3.6.1.4.1.2011.5.25.185.1.1
        hwVCClusterTopoType OBJECT-TYPE
            SYNTAX OCTET STRING (SIZE (0..12))
            MAX-ACCESS read-only
            STATUS current
            DESCRIPTION
                "This object indicates the topology type of a virtual cluster. "
            ::= { hwVCCHASSISObjects 1 }

        -- 1.3.6.1.4.1.2011.5.25.185.1.2
        hwVCMemberNumber OBJECT-TYPE
            SYNTAX Unsigned32 (0..2)
            MAX-ACCESS read-only
            STATUS current
            DESCRIPTION
                "The vc chassis system's member chassis number. "
            ::= { hwVCCHASSISObjects 2 }

        -- 1.3.6.1.4.1.2011.5.25.185.1.3
        hwVCManageSysoid OBJECT-TYPE
            SYNTAX OBJECT IDENTIFIER
            MAX-ACCESS read-only
            STATUS current
            DESCRIPTION
                "This object indicates the system ID of the virtual cluster management capability."
            ::= { hwVCCHASSISObjects 3 }

        -- 1.3.6.1.4.1.2011.5.25.185.1.5
        hwVCEvents OBJECT IDENTIFIER ::= { hwVCCHASSISObjects 5 }

        -- 1.3.6.1.4.1.2011.5.25.185.1.5.1
        hwVCChassisMemberChange NOTIFICATION-TYPE
            OBJECTS { hwCurrentChassisId }
            STATUS current
            DESCRIPTION
                " This object indicates when a vcc member number change,
                send a SNMP trap to network manager. "
            ::= { hwVCEvents 1 }

        -- 1.3.6.1.4.1.2011.5.25.185.1.10
        hwVCMemberInfoTable OBJECT-TYPE
            SYNTAX SEQUENCE OF HwVCMemberInfoEntry
            MAX-ACCESS not-accessible
            STATUS current
            DESCRIPTION
                "This object indicates the member information list of a virtual cluster."
            ::= { hwVCCHASSISObjects 10 }

        -- 1.3.6.1.4.1.2011.5.25.185.1.10.1
        hwVCMemberInfoEntry OBJECT-TYPE
            SYNTAX HwVCMemberInfoEntry
            MAX-ACCESS not-accessible
            STATUS current
            DESCRIPTION
                "This object indicates the information of vcc member."
            INDEX { hwCurrentChassisId }
            ::= { hwVCMemberInfoTable 1 }

        HwVCMemberInfoEntry ::=
            SEQUENCE {
                hwCurrentChassisId
                    Unsigned32,
                hwChassisRole
                    OCTET STRING,
                hwChassisSysoid
                    OBJECT IDENTIFIER
             }

        -- 1.3.6.1.4.1.2011.5.25.185.1.10.1.1
        hwCurrentChassisId OBJECT-TYPE
            SYNTAX Unsigned32 (1..2)
            MAX-ACCESS read-only

            STATUS current
            DESCRIPTION
                "This object indicates the ID of a member chassis in a virtual cluster."
            ::= { hwVCMemberInfoEntry 1 }

        -- 1.3.6.1.4.1.2011.5.25.185.1.10.1.2
        hwChassisRole OBJECT-TYPE
            SYNTAX OCTET STRING (SIZE (0..12))
            MAX-ACCESS read-only
            STATUS current
            DESCRIPTION
                "This object indicates the role of a member chassis in a virtual cluster."
            ::= { hwVCMemberInfoEntry 2 }

        -- 1.3.6.1.4.1.2011.5.25.185.1.10.1.3
        hwChassisSysoid OBJECT-TYPE
            SYNTAX OBJECT IDENTIFIER
            MAX-ACCESS read-only
            STATUS current
            DESCRIPTION
                "This object indicates the system ID of a member chassis in a virtual cluster. "
            ::= { hwVCMemberInfoEntry 3 }

    END

--
-- HUAWEI-VCCHASSIS-MIB.mib
--
