-- ============================================================================
-- Copyright (C) 2013 by  HUAWEI TECHNOLOGIES. All rights reserved.
-- Description:  This MIB module defines MIB objects which provides voice user management.
-- Reference:
-- Version: V1.34
-- ============================================================================

    HUAWEI-VOICEUSER-MIB DEFINITIONS ::= BEGIN
        IMPORTS
        	MODULE-IDENTITY, OBJECT-TYPE, NOTIFICATION-TYPE, private,Integer32,Unsigned32
        		FROM SNMPv2-SMI
        	MODULE-COMPLIANCE, OBJECT-GROUP, NOTIFICATION-GROUP
        		FROM SNMPv2-CONF
        	TEXTUAL-CONVENTION
        		FROM SNMPv2-TC
        	IpAddress,TimeTicks,Counter32
        		FROM SNMPv2-SMI
        	RowStatus,DisplayString
        		FROM SNMPv2-TC
        	huaweiUtility
        		FROM HUAWEI-MIB
            hwConfigChangeIP
                FROM HUAWEI-DEVICE-MIB;

        hwIASVoiceUser MODULE-IDENTITY
            LAST-UPDATED "201307090000Z"
            ORGANIZATION "Huawei Technologies Co., Ltd."
            CONTACT-INFO
                         "Huawei Industrial Base
                          Bantian, Longgang
                          Shenzhen 518129
                          People's Republic of China
                          Website: http://www.huawei.com
                          Email: support@huawei.com
                         "
            DESCRIPTION
                "This MIB module defines MIB objects which provides voice user management.
                "

        --  Revision history
            REVISION     "201307090000Z"
            DESCRIPTION  "V1.34, modify the value range of hwBraCTPIuaTextIID in hwBraCTPConfigTable, hwPraCTPIuaTextIID in hwPraCTPConfigTable, hwPmbsCTPIuaTextIID in hwPmbsCTPConfigTable"

            REVISION     "201305160000Z"
            DESCRIPTION  "V1.34, added hwPraCTPBChnCallRight to hwPraCTPConfigTable"

            REVISION     "201211120000Z"
            DESCRIPTION  "V1.34, added hwBraCTPRightCliWildcardLen, hwPraCTPRightCliWildcardLen"

            REVISION     "201211140000Z"
            DESCRIPTION  "V1.34, add hwBraCTPConfigCliGroup to hwBraCTPConfigTable
                                 add hwPraCTPConfigCliGroup to hwPraCTPConfigTable"

            REVISION     "201211140000Z"
            DESCRIPTION  "V1.34, added hwBraCTPDspParaTemplate to hwBraCTPConfigTable."

            REVISION     "201210110000Z"
            DESCRIPTION  "V1.34, modify the value range of hwBraCTPConfigCalledPartyNumNationalPrefixFlag in hwBraCTPConfigTable,
        	  										 modify the value range of hwPraCTPConfigDefaultCliMode, hwPraCTPConfigBearCapability, hwPraCTPConfigCalledPartyNumType,
        	  										 hwPraCTPConfigCalledPartyNumInternationalPrefixFlag and hwPraCTPConfigCalledPartyNumNationalPrefixFlag in hwPraCTPConfigTable
        	  										 modify the value range of hwR2CTPRemoteRingFlag in hwR2CTPConfigTable"

            REVISION     "201207310000Z"
            DESCRIPTION  "V1.34, modify the Description of hwPstnCTPFSKAlertInterval and hwPstnCTPRightDisplayName."

            REVISION     "201204260000Z"
            DESCRIPTION  "V1.33, modify the default value of hwPstnCTPDCTime in hwPstnCTPConfigTable from 10 to 80,
                                 added hwPstnCTPEOCTime to hwPstnCTPConfigTable."

            REVISION     "201204060000Z"
            DESCRIPTION  "V1.32, modify the value range of hwPstnCTPFSKAlertInterval in hwPstnCTPConfigTable from 0-100 to -1-100,
                                 modify the value range of hwBraCTPConfigCalledPartyNumType,hwBraCTPConfigDefaultCliMode,hwBraCTPConfigBearCapability,
                                                           hwBraCTPConfigCalledPartyNumInternationalPrefixFlag,hwBraCTPConfigCalledPartyNumNationalPrefixFlag
                                                           in hwBraCTPConfigTable,
                                 modify the description of hwPraCTPConfigDefaultCliMode in hwPraCTPConfigTable"

            REVISION     "201202290000Z"
            DESCRIPTION  "V1.32, modify the value range of hwCTPExternNumberPortBindIndex in hwCTPExternNumberConfigTable from 1-65535 to 1-65534"

            REVISION     "201201160000Z"
            DESCRIPTION  "V1.31, modify the status of hwPstnCTPRightTp, hwPstnCTPRightCd, hwPstnCTPRightUus1, hwPstnCTPRightUus2, hwPstnCTPRightUus3 in hwPstnCTPRightConfigTable"

            REVISION     "201201030000Z"
            DESCRIPTION  "V1.31, added hwPstnCTPConfigDefaultCli,hwSipMgSoftStringConfigParameter39"

            REVISION     "201201020000Z"
            DESCRIPTION  "V1.31, modified hwBraCTPConfigTable"

            REVISION     "201110240000Z"
            DESCRIPTION  "V1.31, add hwPstnCTPFSKAlertInterval,
                                 add the hwBraCTPRightCentrexNo, hwBraCTPRightCentrexPrefix, hwBraCTPRightCentrexFlag, hwBraCTPRightMwiMode ,
	            													 hwBraCTPRightCallHold, hwBraCTPRightThreeParty, hwBraCTPRightConf, hwBraCTPRightCt,
	            		 add the hwPraCTPRightCentrexNo, hwPraCTPRightCentrexPrefix, hwPraCTPRightCentrexFlag, hwPraCTPRightMwiMode
	            		 in the hwPraCTPRightConfigTable
	            		 add table hwR2CTPConfigTable,hwR2CTPOperTable,hwR2CTPRightConfigTable"

            REVISION     "201108230000Z"
            DESCRIPTION  "V1.30, modified the hwPstnUserDataTrapSequence's description "

            REVISION     "201106030000Z"
            DESCRIPTION  "V1.29, added hwPstnCTPRightDc"

            REVISION     "201104130000Z"
            DESCRIPTION  "V1.28, added hwPstnCTPForceSendFsk hwPstnCTPRightHotLine, hwPstnCTPRightPermanentHold,
                                       hwPstnCTPRightCutoffDisconnect, hwPstnCTPRightSccClass, hwPstnCTPRightPermanentHoldMode,
                                       hwPstnCTPRightPermanentHoldTime, hwPstnCTPRightFastDisconnect. modify hwPstnCTPRightDialTone"

            REVISION     "201012210000Z"
            DESCRIPTION  "V1.27, added hwPstnCTPDigitMapGroupName, hwBraCTPDigitMapGroupName, hwPraCTPDigitMapGroupName."

    	    REVISION     "201008030000Z"
            DESCRIPTION  "V1.26, revised the description errors."

            REVISION     "201009030000Z"
            DESCRIPTION  "V1.25, revised the errors. Added trap table hwVoiceUserOperateType, hwVoiceUserPortNum, hwIASVoiceUserPortPstnDataChangeTrap, hwIASVoiceUserPortBraDataChangeTrap, hwIASVoiceUserPortPraDataChangeTrap, hwIASVoiceUserPortPmbsDataChangeTrap"

            REVISION     "201007030000Z"
            DESCRIPTION  "V1.24, revised the errors. Added hwBraCTPRightConfigTable, and hwBraCTPRightConfigTable. Added hwPstnCTPRightAutoReversePolarity."

            REVISION     "201005050000Z"
            DESCRIPTION  "V1.23, revised the errors."

            REVISION     "201004100000Z"
            DESCRIPTION  "V1.22, corrected the enumerate name."

            REVISION     "201003190000Z"
            DESCRIPTION  "V1.21, added configuration of user group. Added hwPstnCTPRightAuthPasswordMode, hwPstnCTPRightAuthHA1, hwCTPExternNumberUserGroupid, hwPstnCTPUserGroupid, hwBraCTPConfigTable, hwBraCTPUserGroupid, and hwPraCTPUserGroupid."

            REVISION     "201001250000Z"
            DESCRIPTION  "V1.19, added trap notification and corrected compile error."

            REVISION     "200912140000Z"
            DESCRIPTION  "V1.18, modified the value range of hwPstnCTPConfigTable to cancel the configuration of Long Distance User."

            ::= { huaweiUtility 112 }



        hwIASVoiceUserObjects OBJECT IDENTIFIER ::= { hwIASVoiceUser 1 }

        hwIASVoiceUserTrapsVbOids OBJECT IDENTIFIER ::= { hwIASVoiceUser 2 }

        hwIASVoiceUserTraps OBJECT IDENTIFIER ::= { hwIASVoiceUser 3 }

        hwIASVoiceUserCommonTraps OBJECT IDENTIFIER ::= { hwIASVoiceUserTraps 1 }

        hwIASVoiceUserAlarmTraps OBJECT IDENTIFIER ::= { hwIASVoiceUserTraps 2 }

        hwIASVoiceUserPortTraps OBJECT IDENTIFIER ::= { hwIASVoiceUserCommonTraps 1 }

        hwIASVoiceUserPortAlarmTraps OBJECT IDENTIFIER ::= { hwIASVoiceUserAlarmTraps 1 }

        hwIASVoiceUserTsnAlarmTraps OBJECT IDENTIFIER ::= { hwIASVoiceUserAlarmTraps 2 }



        hwPstnCTPConfigTable OBJECT-TYPE
            SYNTAX      SEQUENCE OF HwPstnCTPConfigEntry
            MAX-ACCESS  not-accessible
            STATUS      current
            DESCRIPTION
                "This table is used to add, delete, modify, and query the PSTN user.
                The index of this table is hwPstnCTPConfigIndex.
                The service attributes of a PSTN port include the gateway ID, terminal ID, telephone number, whether to support layering configuration, priority flag of the port for the overload control, user type, power-off interval, FSK delay interval, time for issuing the calling number, format for issuing the calling number, and limited pulse dialing. Through the table, you can configure, modify, and query the above-mentioned attributes of the PSTN user.
                "
            ::= { hwIASVoiceUserObjects 1 }

        hwPstnCTPConfigEntry OBJECT-TYPE
            SYNTAX      HwPstnCTPConfigEntry
            MAX-ACCESS  not-accessible
            STATUS      current
            DESCRIPTION
                "This table is used to add, delete, modify, and query the PSTN user.
                The index of this entry is hwPstnCTPConfigIndex.
                The service attributes of a PSTN port include the gateway ID, terminal ID, telephone number, whether to support layering configuration, priority flag of the port for the overload control, user type, power-off interval, FSK delay interval, time for issuing the calling number, format for issuing the calling number, and limited pulse dialing. Through the table, you can configure, modify, and query the above-mentioned attributes of the PSTN user.
                "
            INDEX   {
                        hwPstnCTPConfigIndex
                    }
            ::= { hwPstnCTPConfigTable 1 }

        HwPstnCTPConfigEntry ::=
            SEQUENCE {
                hwPstnCTPConfigIndex	Integer32,
                hwPstnCTPMgId	Integer32,
                hwPstnCTPTerminationID	OCTET STRING,
                hwPstnCTPTelNo	OCTET STRING,
                hwPstnCTPRowStatus	RowStatus,
                hwPstnCTPLayerFlag	INTEGER,
                hwPstnCTPPriorityFlag	INTEGER,
                hwPstnCTPPotsLineType     INTEGER,
                hwPstnCTPDCTime     Integer32,
                hwPstnCTPFSKDelayInterval     Integer32,
                hwPstnCTPCidTransWhen    INTEGER,
                hwPstnCTPCidFormat    INTEGER,
                hwPstnCTPVQEAgc     INTEGER,
                hwPstnCTPVQESns     INTEGER,
                hwPstnCTPVQEAgcLevel    Integer32,
                hwPstnCTPVQESnsLevel    Integer32,
                hwPstnCTPDspInputGain   Integer32,
                hwPstnCTPDspOutputGain  Integer32,
                hwPstnCTPDetectANSbarBySingleToneFlag INTEGER,
                hwPstnCTPBellANSFlag  INTEGER,
                hwPstnCTPDspParaTemplate OCTET STRING,
                hwPstnCTPCidFskMode  INTEGER,
                hwPstnCTPCidTasPattern  INTEGER,
                hwPstnCTPUserGroupid  Integer32,
                hwPstnCTPDigitMapGroupName  OCTET STRING,
                hwPstnCTPForceSendFsk INTEGER,
                hwPstnCTPFSKAlertInterval Integer32,
                hwPstnCTPConfigDefaultCli OCTET STRING,
                hwPstnCTPEOCTime     Integer32,
                hwPstnCTPRemoteBlockPowerDeny INTEGER
               }

        hwPstnCTPConfigIndex OBJECT-TYPE
            SYNTAX      Integer32
            MAX-ACCESS  not-accessible
            STATUS      current
            DESCRIPTION
                "Indicates the frame/slot/port.
                24                                         0
                0011000 | xxxxxxxx | xxxxxx | xxxxxxx | 0000
                port      frame      slot     port      0
                type

                The highest 7 bits indicate the type of port, for PSTN port, must be 0x18
                the next 8 bits indicate the frame ID,
                the next 6 bits indicate the slot ID,
                the next 7 bits indicate the port ID,
                the last 4 bits must be 0.

                The type of port include:
                E1   port = 0x16
                PSTN port = 0x18
                BRA  port = 0x19
                AT0  port = 0x1b
                "
            ::= { hwPstnCTPConfigEntry 1 }

        hwPstnCTPMgId OBJECT-TYPE
            SYNTAX      Integer32(0..16777215)
            MAX-ACCESS  read-create
            STATUS      current
            DESCRIPTION
                "
                Indicates the MG ID.
                "
            ::= { hwPstnCTPConfigEntry 2 }

        hwPstnCTPTerminationID OBJECT-TYPE
            SYNTAX      OCTET STRING(SIZE(0..64))
            MAX-ACCESS  read-create
            STATUS      current
            DESCRIPTION
                "
                Indicates the terminal ID (only the character string of digit type is supported).
                "
            ::= { hwPstnCTPConfigEntry 3 }

        hwPstnCTPTelNo OBJECT-TYPE
          SYNTAX      OCTET STRING(SIZE(0..64))
          MAX-ACCESS  read-create
          STATUS      current
          DESCRIPTION
              "
              Indicates the telephone number.
              "
          ::= { hwPstnCTPConfigEntry 4 }

        hwPstnCTPRowStatus OBJECT-TYPE
          SYNTAX      RowStatus
          MAX-ACCESS  read-write
          STATUS      current
          DESCRIPTION
              "
              Indicates the row status.The operations include activate, shut down, not start, create and register, create and wait, and delete. The operations are not used in the V8R61.
              "
          ::= { hwPstnCTPConfigEntry 5 }

        hwPstnCTPLayerFlag OBJECT-TYPE
          SYNTAX      INTEGER{noLayer(1), -- not to layer
                              layer(2),    -- to layer
                              null(-1)
                              }
          MAX-ACCESS  read-only
          STATUS      current
          DESCRIPTION
              "
              Indicates whether to layer.
              Options:
              1. noLayer(1)       -not to layer
              2. layer(2)         -to layer
              3. null(-1) -invalid value
              "
          ::= { hwPstnCTPConfigEntry 6 }

        hwPstnCTPPriorityFlag OBJECT-TYPE
          SYNTAX      INTEGER{cat1(1), -- the highest priority
                              cat2(2), -- the middle priority
                              cat3(3)  -- the lowest priority
                              }
          MAX-ACCESS  read-create
          STATUS      current
          DESCRIPTION
              "
              Indicates the priority of the terminal.
              Options:
              1. cat1(1) -the highest priority
              2. cat2(2) -the middle priority
              3. cat3(3) -the lowest priority
              "
              DEFVAL      { cat3 }
          ::= { hwPstnCTPConfigEntry 7 }

        hwPstnCTPPotsLineType OBJECT-TYPE
          SYNTAX      INTEGER{del(1),     -- DEL
                              lcPBX(2),   -- loop calling PBX
                              ecPBX(3),   -- earth calling PBX
                              payPhone(4) -- Pay phone
                              }
          MAX-ACCESS  read-create
          STATUS      current
          DESCRIPTION
              "
              Indicates the subscriber type.
              Options:
              1. del(1) -DEL
              2. lcPBX(2) -Loop Calling PBX
              3. ecPBX(3) -earth calling PBX
              4. payPhone(4) -PayPhone
              "
              DEFVAL      { del }
          ::= { hwPstnCTPConfigEntry 8 }

        hwPstnCTPDCTime OBJECT-TYPE
          SYNTAX      Integer32(10..100)
          MAX-ACCESS  read-create
          STATUS      current
          DESCRIPTION
              "
              Indicates the disconnect clear interval.
              Unit: 10ms
              "
              DEFVAL      { 80 }
          ::= { hwPstnCTPConfigEntry 9 }

        hwPstnCTPFSKDelayInterval OBJECT-TYPE
          SYNTAX      Integer32(0..100)
          MAX-ACCESS  read-create
          STATUS      current
          DESCRIPTION
              "
              Indicates the FSK delay interval.
              Unit: 10ms
              "
              DEFVAL      { 80 }
          ::= { hwPstnCTPConfigEntry 10 }

        hwPstnCTPCidTransWhen OBJECT-TYPE
          SYNTAX      INTEGER{afterRing(1),  -- transmit CID after ringing
                              beforeRing(2)  -- transmit CID before ringing
                              }
          MAX-ACCESS  read-create
          STATUS      current
          DESCRIPTION
              "
              Indicates the time for delivering the caller ID.
              Options:
              1. afterRing(1) -transmit CID after ringing
              2. beforeRing(2) -transmit CID before ringing
              "
              DEFVAL      { afterRing }
          ::= { hwPstnCTPConfigEntry 11 }

        hwPstnCTPCidFormat OBJECT-TYPE
          SYNTAX      INTEGER{sdmfFsk(1), -- SDMF FSK format
                              mdmfFsk(2), -- MDMF FSK format
                              dtmf(3),     -- DTMF format
                              russia(4),   -- russia format
                              etsi(5)      -- etsi format
                              }
          MAX-ACCESS  read-create
          STATUS      current
          DESCRIPTION
              "
              Indicates the format of the caller ID.
              Options:
              1. sdmfFsk(1) -SDMF FSK format
              2. mdmfFsk(2) -MDMF FSK format
              3. dtmf(3) -DTMF format
              4. russia(4) -russia format
              5. etsi(5) -etsi format
              "
              DEFVAL      { sdmfFsk }
          ::= { hwPstnCTPConfigEntry 12 }

        hwPstnCTPVQEAgc OBJECT-TYPE
          SYNTAX      INTEGER{enable(1),disable(2)}
          MAX-ACCESS  read-create
          STATUS      current
          DESCRIPTION
              "
              Indicates enable AGC or not.
              Options:
              1. enable(1) -enable AGC
              2. disable(2) -disable AGC
              "
              DEFVAL      { disable }
          ::= { hwPstnCTPConfigEntry 13 }

        hwPstnCTPVQESns OBJECT-TYPE
          SYNTAX      INTEGER{enable(1),disable(2)}
          MAX-ACCESS  read-create
          STATUS      current
          DESCRIPTION
              "
              Indicates enable SNS or not.
              Options:
              1. enable(1) -enable SNS
              2. disable(2) -disable SNS
              "
              DEFVAL      { disable }
          ::= { hwPstnCTPConfigEntry 14 }

        hwPstnCTPVQEAgcLevel OBJECT-TYPE
          SYNTAX      Integer32(-24..-9)
          MAX-ACCESS  read-create
          STATUS      current
          DESCRIPTION
              "
              Indicates set AGC target value.
              Unit: dbm0
              "
              DEFVAL      { -22 }
          ::= { hwPstnCTPConfigEntry 15 }

        hwPstnCTPVQESnsLevel OBJECT-TYPE
          SYNTAX      Integer32(6..20)
          MAX-ACCESS  read-create
          STATUS      current
          DESCRIPTION
              "
              Indicates set VQE noise suppression level.
              Unit: db
              "
              DEFVAL      { 12 }
          ::= { hwPstnCTPConfigEntry 16 }

        hwPstnCTPDspInputGain OBJECT-TYPE
          SYNTAX      Integer32(1..16)
          MAX-ACCESS  read-create
          STATUS      current
          DESCRIPTION
              "
              Dsp input gain.
              1:    -10db
              2:    -9db
              3:    -8db
              4:    -7db
              5:    -6db
              6:    -5db
              7:    -4db
              8:    -3db
              9:    -2db
              10:   -1db
              11:    0db
              12:    1db
              13:    2db
              14:    3db
              15:    4db
              16:    5db
              Unit: db
              "
              DEFVAL      { 11 }
          ::= { hwPstnCTPConfigEntry 17 }

        hwPstnCTPDspOutputGain OBJECT-TYPE
          SYNTAX      Integer32(1..21)
          MAX-ACCESS  read-create
          STATUS      current
          DESCRIPTION
              "
              Dsp output gain.
              1:    -10db
              2:    -9db
              3:    -8db
              4:    -7db
              5:    -6db
              6:    -5db
              7:    -4db
              8:    -3db
              9:    -2db
              10:   -1db
              11:    0db
              12:    1db
              13:    2db
              14:    3db
              15:    4db
              16:    5db
              17:    6db
              18:    7db
              19:    8db
              20:    9db
              21:    10db
              Unit: db
              "
              DEFVAL      { 11 }
          ::= { hwPstnCTPConfigEntry 18 }


        hwPstnCTPDetectANSbarBySingleToneFlag OBJECT-TYPE
          SYNTAX      INTEGER{enable(1),disable(2)}
          MAX-ACCESS  read-create
          STATUS      current
          DESCRIPTION
              "
              It indicates whether the ANSbar signal detected by SingleTone is supported.
              Options:
              1. enable(1) -the ANSbar signal detected by SingleTone is supported
              2. disable(2) -the ANSbar signal detected by SingleTone is not supported
              "
              DEFVAL      { disable }
          ::= { hwPstnCTPConfigEntry 19 }


        hwPstnCTPBellANSFlag OBJECT-TYPE
          SYNTAX      INTEGER{enable(1),disable(2)}
          MAX-ACCESS  read-create
          STATUS      current
          DESCRIPTION
              "
              It indicates whether the Bell ANS is supported.
              Options:
              1. enable(1) -the Bell ANS is supported
              2. disable(2) -the Bell ANS is not supported
              "
              DEFVAL      { disable }
          ::= { hwPstnCTPConfigEntry 20 }

        hwPstnCTPDspParaTemplate OBJECT-TYPE
          SYNTAX      OCTET STRING(SIZE(0..31))
          MAX-ACCESS  read-create
          STATUS      current
          DESCRIPTION
              "
              The index of dsp parameter template name.
              "
          ::= { hwPstnCTPConfigEntry 21 }

        hwPstnCTPCidFskMode OBJECT-TYPE
          SYNTAX      INTEGER{bell202(1),  -- BELL 202
                              ccittv23(2), -- CCITT V23
                              ntt(3)       -- NTT
                              }
          MAX-ACCESS  read-create
          STATUS      current
          DESCRIPTION
              "
              It indicates the mode of fsk.
              Options:
              1. bell202(1) -bell 202
              2. ccittv23(2) -ccitt v23
              3. ntt(3) -ntt
              "
              DEFVAL      { bell202 }
          ::= { hwPstnCTPConfigEntry 22 }


          hwPstnCTPCidTasPattern OBJECT-TYPE
          SYNTAX      INTEGER{noTas(1), -- no tas
                              dtAs(2)   -- DT as
                              }
          MAX-ACCESS  read-create
          STATUS      current
          DESCRIPTION
              "
              It indicates the mode of tas.
              Options:
              1. noTas(1) -no tas
              2. dtAs(2) -DT as
              "
              DEFVAL      { no-tas }
          ::= { hwPstnCTPConfigEntry 23 }

          hwPstnCTPUserGroupid OBJECT-TYPE
          SYNTAX      Integer32(-1..65535)
          MAX-ACCESS  read-write
          STATUS      current
          DESCRIPTION
              "
              It indicates the user group ID.
              -1 indicates clear the user group info.
              "
          ::= { hwPstnCTPConfigEntry 24 }

          hwPstnCTPDigitMapGroupName OBJECT-TYPE
          SYNTAX      OCTET STRING(SIZE(0..32))
          MAX-ACCESS  read-write
          STATUS      current
          DESCRIPTION
              "
              It indicates the digitmap group name.
              "
          ::= { hwPstnCTPConfigEntry 25 }

          hwPstnCTPForceSendFsk OBJECT-TYPE
          SYNTAX      INTEGER{enable(1),disable(2)}
          MAX-ACCESS  read-create
          STATUS      current
          DESCRIPTION
              "
              Indicates enable force send FSK or not.
              Options:
              1. enable(1) -enable force send FSK
              2. disable(2) -disable force send FSK
              "
              DEFVAL      { disable }
          ::= { hwPstnCTPConfigEntry 26 }

          hwPstnCTPFSKAlertInterval OBJECT-TYPE
          SYNTAX      Integer32(0..100|-1)
          MAX-ACCESS  read-write
          STATUS      current
          DESCRIPTION
              "
              It indicates fskend to alert Interval.
              -1 indicate invalid value.
              Unit: 10ms
              "
              DEFVAL      { 40 }
          ::= { hwPstnCTPConfigEntry 27 }

          hwPstnCTPConfigDefaultCli OBJECT-TYPE
          SYNTAX      OCTET STRING(SIZE(0..64))
          MAX-ACCESS  read-write
          STATUS      current
          DESCRIPTION
              "
              It indicates the default cli number of outgoing call.
              "
          ::= { hwPstnCTPConfigEntry 28 }

        hwPstnCTPEOCTime OBJECT-TYPE
          SYNTAX      Integer32(10..100)
          MAX-ACCESS  read-create
          STATUS      current
          DESCRIPTION
              "
              Indicates the end of call interval.
              Unit: 10ms
              "
              DEFVAL      { 10 }
          ::= { hwPstnCTPConfigEntry 29 }

          hwPstnCTPRemoteBlockPowerDeny  OBJECT-TYPE
          SYNTAX      INTEGER{enable(1),disable(2)}
          MAX-ACCESS  read-write
          STATUS      current
          DESCRIPTION
              "
              Indicates the flag of remote block power deny.
              Options:
              1. enable(1) - enable remote block power deny
              2. disable(2) - disable remote block power deny
              "
              DEFVAL      { disable }
          ::= { hwPstnCTPConfigEntry 30 }

      ----------------------------------------------------------------------------------------------------------

        hwPstnCTPOperTable OBJECT-TYPE
          SYNTAX      SEQUENCE OF HwPstnCTPOperEntry
          MAX-ACCESS  not-accessible
          STATUS      current
          DESCRIPTION
            "
            It is used to maintain PSTN ports with the VSP feature.
            The index of this table is hwPstnCTPOperIndex.
            Through the table, you can query the states of PSTN ports, including the running status of the PSTN service, management status of the PSTN service, change time of the running status of the PSTN service, and change time of the management status of the PSTN service.
            Through the table, services on the PSTN port can be terminated, started, and the service status can be queried.
            "
          ::= { hwIASVoiceUserObjects 2 }

        hwPstnCTPOperEntry OBJECT-TYPE
          SYNTAX      HwPstnCTPOperEntry
          MAX-ACCESS  not-accessible
          STATUS      current
          DESCRIPTION
            "
            It is used to maintain PSTN ports with the VSP feature.
            The index of this entry is hwPstnCTPOperIndex.
            Through the table, you can query the states of PSTN ports, including the running status of the PSTN service, management status of the PSTN service, change time of the running status of the PSTN service, and change time of the management status of the PSTN service.
            Through the table, services on the PSTN port can be terminated, started, and the service status can be queried.
            "
          INDEX    {
                    hwPstnCTPOperIndex
                   }
          ::= { hwPstnCTPOperTable 1 }

        HwPstnCTPOperEntry ::=
          SEQUENCE
          {
            hwPstnCTPOperIndex	Integer32,
            hwPstnCTPSrvState	INTEGER,
            hwPstnCTPAdminState	INTEGER,
            hwPstnCTPAdminOper	INTEGER,
            hwPstnCTPSrvStateChange	TimeTicks,
            hwPstnCTPAdminStateChange	TimeTicks,
            hwPstnCTPMaxCobTime      Integer32,
            hwPstnCTPOnexpire        INTEGER,
            hwPstnCTPRegState    INTEGER,
            hwPstnCTPCallState INTEGER,
            hwPstnCTPCallWaitState INTEGER
          }

        hwPstnCTPOperIndex OBJECT-TYPE
          SYNTAX      Integer32
          MAX-ACCESS  not-accessible
          STATUS      current
          DESCRIPTION
              "
              Indicates the frame/slot/port.
              24                                         0
              0011000 | xxxxxxxx | xxxxxx | xxxxxxx | 0000
              port      frame      slot     port      0
              type

              The highest 7 bits indicate the type of port, for PSTN port, must be 0x18
              the next 8 bits indicate the frame ID,
              the next 6 bits indicate the slot ID,
              the next 7 bits indicate the port ID,
              the last 4 bits must be 0.

              The type of port include:
              E1   port = 0x16
              PSTN port = 0x18
              BRA  port = 0x19
              AT0  port = 0x1b
              "
          ::= { hwPstnCTPOperEntry 1 }

        hwPstnCTPSrvState OBJECT-TYPE
          SYNTAX      INTEGER{fault(1),    -- the port is fault
                              idle(2),     -- the user is idle
                              offHook(3), -- the user off-hook
                              lock(4),     -- the user is locked
                              ring(5)      -- the user is ringing
                              }
          MAX-ACCESS  read-only
          STATUS      current
          DESCRIPTION
              "
              Indicates the running status of the service layer of the PSTN port.
              Options:
              1. fault(1)-the port is fault
              2. idle(2) -the user is idle
              3. offHook(3) -the user off-hook
              4. lock(4) -the user is locked
              5. ring(5) -the user is ringing
              "
          ::= { hwPstnCTPOperEntry 2 }

        hwPstnCTPAdminState OBJECT-TYPE
          SYNTAX      INTEGER{blockedLocally(1),  -- the service is blocked cause of the local reason
                              blockedRemotely(2), -- the service is blocked cause of the remote reason
                              inService(3),       -- the service is normal
                              shuttingDown(4),    -- the service is shutting down
                              delayTest(5)        -- the user is waiting for testing
                              }
          MAX-ACCESS  read-only
          STATUS      current
          DESCRIPTION
              "
              Indicates the administration status of the service layer of the PSTN port.
              Options:
              1. blockedLocally(1) -the service is blocked cause of the local reason
              2. blockedRemotely(2) -the service is blocked cause of the remote reason
              3. inService(3) -the service is normal
              4. shuttingDown(4) -the service is shutting down
              5. delayTest(5) -the user is waiting for testing
              "
          ::= { hwPstnCTPOperEntry 3 }

        hwPstnCTPAdminOper OBJECT-TYPE
          SYNTAX      INTEGER{endService(1),         -- stop service
                              startService(2),       -- start service
                              deferEndingService(3) -- stop service gracefully
                              }
          MAX-ACCESS  read-write
          STATUS      current
          DESCRIPTION
              "
              Indicates the maintenance operation of the service layer of the PSTN port.
              Options:
              1. endService(1) -stop service
              2. startService(2) -start service
              3. deferEndingService(3) -stop service gracefully
              "
          ::= { hwPstnCTPOperEntry 4 }

        hwPstnCTPSrvStateChange OBJECT-TYPE
          SYNTAX      TimeTicks
          MAX-ACCESS  read-only
          STATUS      current
          DESCRIPTION
              "
              Indicates the service running status changing time of the PSTN port.
              "
          ::= { hwPstnCTPOperEntry 5 }

        hwPstnCTPAdminStateChange OBJECT-TYPE
          SYNTAX      TimeTicks
          MAX-ACCESS  read-only
          STATUS      current
          DESCRIPTION
              "
              Indicates the service administration status changing time of the PSTN port.
              "
          ::= { hwPstnCTPOperEntry 6 }

          hwPstnCTPMaxCobTime OBJECT-TYPE
          SYNTAX      Integer32(0..1440)
          MAX-ACCESS  read-write
          STATUS      current
          DESCRIPTION
              "
              Length of waiting timer for pstn user defer end service.
              0 is not allowed to set.
              Default: 240
              Unit: minute
              "
          ::= { hwPstnCTPOperEntry 7 }

          hwPstnCTPOnexpire OBJECT-TYPE
          SYNTAX      INTEGER{force(1),cancel(2)}
          MAX-ACCESS  read-write
          STATUS      current
          DESCRIPTION
              "
              Indicates disposal mode when pstn user defer end service timeout.
              Options:
              1. force(1) -force user to end service when end-service timeout
              2. cancel(2) -cancel end service when end-service timeout
              Default: force(1)
              "
          ::= { hwPstnCTPOperEntry 8 }

          hwPstnCTPRegState OBJECT-TYPE
          SYNTAX      INTEGER{initializing(1),  -- the user has not send register request
                              registering(2), --  the user has send register request and is waiting for response
                              failRegistered(3), -- the user received failed response or register timeout
                              unregistering(4),    -- the user is unregistering
                              active(5),       -- the user is actived
                              deactive(6),     -- the user is deactived
                              invalidusertype(7) -- the user is not SIP user
                              }
          MAX-ACCESS  read-only
          STATUS      current
          DESCRIPTION
              "
              Indicates the register status of the PSTN port.
              Options:
              1.initializing(1)  - the user has not send register request
              2.registering(2) -  the user has send register request and is waiting for response
              3.failRegistered(3) - the user received failed response or register timeout
              4.unregistering(4)    - the user is unregistering
              5.active(5) - the user is actived
              6.deactive(6)    - the user is deactived
              7. invalidusertype(7) -- the user is not SIP user
              "
          ::= { hwPstnCTPOperEntry 9 }

          hwPstnCTPCallState OBJECT-TYPE
          SYNTAX      INTEGER{idle(1),-- there is no call on the user
                              offhook(2),--  the user hung up
                              dialing(3),-- the user is dialing
                              establishing(4),-- the call is establishing
                              ringing(5),-- the phone is ringing
                              ringback(6),-- the phone is ringback
                              connecting(7),-- the call is connecting
                              connected(8),-- the call is connected
                              hold(9),-- the call is hold
                              disconnecting(10),-- the call is disconnecting
                              locked(11),     -- the port is locked
                              invalidusertype(12) -- the user is not SIP user
                              }
          MAX-ACCESS  read-only
          STATUS      current
          DESCRIPTION
              "
              Indicates the register status of the PSTN port.
              Options:
              1. idle(1)- there is no call on the user
              2. offhook(2)-  the user hung up
              3. dialing(3)- the user is dialing
              4.establishing(4)- the call is establishing
              5.ringing(5)- the phone is ringing
              6.ringback(6)- the phone is ringback
              7.connecting(7)- the call is connecting
              8.connected(8)- the call is connected
              9.hold(9)- the call is hold
              10.disconnecting(10)- the call is disconnecting
              11.locked(11)- the port is locked
              12. invalidusertype(12) -- the user is not SIP user
              "
          ::= { hwPstnCTPOperEntry 10 }


          hwPstnCTPCallWaitState OBJECT-TYPE
          SYNTAX      INTEGER{disable(1),-- the service is disable
                              idle(2),--  the is no callwaiting services
                              secondaryRinging(3),-- the second part is ringing
                              secondaryConnecting(4),-- the second part is connecting
                              secondaryConnected(5),-- the second part is connected
                              secondaryDisconnecting(6),   -- the second part is disconnecting
                              invalidusertype(7)           -- the user is not SIP user
                              }
          MAX-ACCESS  read-only
          STATUS      current
          DESCRIPTION
              "
              Indicates the register status of the PSTN port.
              Options:
              1. disable(1)- the service is disable
              2. idle(2)-  the is no callwaiting services
              3. secondaryRinging(3)- the second part is ringing
              4. secondaryConnecting(4)- the second part is connecting
              5. secondaryConnected(5)- the second part is connected
              6. secondaryDisconnecting(6)- the second part is disconnecting
              7. invalidusertype(7)           -- the user is not SIP user
              "
          ::= { hwPstnCTPOperEntry 11 }

        hwMgPortStatisticsInfoTable OBJECT-TYPE
          SYNTAX SEQUENCE OF HwMgPortStatisticsInfoEntry
          MAX-ACCESS  not-accessible
          STATUS      current
          DESCRIPTION
            "
            This table is used to query the statistics of the MG service ports.
            The index of this table is hwMgPortStatInfoIndex.
            "
          ::= { hwIASVoiceUserObjects 3 }

        hwMgPortStatisticsInfoEntry OBJECT-TYPE
          SYNTAX HwMgPortStatisticsInfoEntry
          MAX-ACCESS  not-accessible
          STATUS      current
          DESCRIPTION
            "
            This table is used to query the statistics of the MG service ports.
            The index of this entry is hwMgPortStatInfoIndex.
            "
          INDEX    {
                       hwMgPortStatInfoIndex
                   }
          ::= { hwMgPortStatisticsInfoTable 1 }

        HwMgPortStatisticsInfoEntry ::=
          SEQUENCE
          {
            hwMgPortStatInfoIndex	Integer32,
            hwPstnCTPStatTotalNum	Integer32,
            hwPstnCTPStatFaultNum	Integer32,
            hwPstnCTPStatIdleNum	Integer32,
            hwPstnCTPStatOffhookNum	Integer32,
            hwPstnCTPStatParkingNum	Integer32,
            hwPstnCTPStatRingNum	Integer32,
            hwMgPortStatInfoTotalNum     Integer32,
            hwMgPortStatInfoUseableNum   Integer32,
            hwMgPortStatInfoBusyNum      Integer32,
            hwMgPortStatInfoFaultNum     Integer32,
            hwMgPortStatInfoForbiddenNum Integer32
          }

        hwMgPortStatInfoIndex OBJECT-TYPE
          SYNTAX      Integer32
          MAX-ACCESS  not-accessible
          STATUS      current
          DESCRIPTION
              "
              Indicates the frame ID.
              The GetNext (walk) operation is to collect the statistics of each specified shelf of the system.
              In the Get operation, if hwMgPortStatIndex is all F, the operation is to collect the statistics of the entire system; if hwMgPortStatIndex is not all F, the operation is to collect the statistics of the specified shelf.
              "
          ::= { hwMgPortStatisticsInfoEntry 1 }

        hwPstnCTPStatTotalNum OBJECT-TYPE
          SYNTAX      Integer32
          MAX-ACCESS  read-only
          STATUS      current
          DESCRIPTION
              "
              Indicates the total number of the MGPSTN service ports.
              "
          ::= { hwMgPortStatisticsInfoEntry 2 }

        hwPstnCTPStatFaultNum OBJECT-TYPE
          SYNTAX      Integer32
          MAX-ACCESS  read-only
          STATUS      current
          DESCRIPTION
              "
     	 Indicates the number of the MGPSTN faulty ports.
              "
          ::= { hwMgPortStatisticsInfoEntry 3 }

        hwPstnCTPStatIdleNum OBJECT-TYPE
          SYNTAX      Integer32
          MAX-ACCESS  read-only
          STATUS      current
          DESCRIPTION
              "
              Indicates the number of the MGPSTN idle ports.
              "
          ::= { hwMgPortStatisticsInfoEntry 4 }

        hwPstnCTPStatOffhookNum OBJECT-TYPE
          SYNTAX      Integer32
          MAX-ACCESS  read-only
          STATUS      current
          DESCRIPTION
              "
              Indicates the number of the MGPSTN off-hooked ports.
              "
          ::= { hwMgPortStatisticsInfoEntry 5 }

        hwPstnCTPStatParkingNum OBJECT-TYPE
          SYNTAX      Integer32
          MAX-ACCESS  read-only
          STATUS      current
          DESCRIPTION
              "
              Indicates the number of the MGPSTN locked ports.
              "
          ::= { hwMgPortStatisticsInfoEntry 6 }

        hwPstnCTPStatRingNum OBJECT-TYPE
          SYNTAX      Integer32
          MAX-ACCESS  read-only
          STATUS      current
          DESCRIPTION
              "
              Indicates the number of the MGPSTN ringing ports.
              "
          ::= { hwMgPortStatisticsInfoEntry 7 }

        hwMgPortStatInfoTotalNum OBJECT-TYPE
          SYNTAX Integer32
          MAX-ACCESS read-only
          STATUS current
          DESCRIPTION
     	 "
     	 Indicates the total number of the MG service ports.
     	 "
          ::= { hwMgPortStatisticsInfoEntry 8 }

        hwMgPortStatInfoUseableNum OBJECT-TYPE
          SYNTAX Integer32
          MAX-ACCESS read-only
          STATUS current
          DESCRIPTION
              "
              Indicates the number of the MG idle ports.
              "
          ::= { hwMgPortStatisticsInfoEntry 9 }

        hwMgPortStatInfoBusyNum OBJECT-TYPE
          SYNTAX Integer32
          MAX-ACCESS read-only
          STATUS current
          DESCRIPTION
     	 "
              Indicates the number of the MG busy ports.
              "
          ::= { hwMgPortStatisticsInfoEntry 10 }

        hwMgPortStatInfoFaultNum OBJECT-TYPE
          SYNTAX Integer32
          MAX-ACCESS read-only
          STATUS current
          DESCRIPTION
              "
     	 Indicates the number of the MG faulty ports.
     	 "
          ::= { hwMgPortStatisticsInfoEntry 11 }

        hwMgPortStatInfoForbiddenNum OBJECT-TYPE
          SYNTAX Integer32
          MAX-ACCESS read-only
          STATUS current
          DESCRIPTION
     	 "
     	 Indicates the number of the MG blocked ports.
     	 "
          ::= { hwMgPortStatisticsInfoEntry 12 }


        hwBraCTPConfigTable OBJECT-TYPE
         SYNTAX      SEQUENCE OF HwBraCTPConfigEntry
         MAX-ACCESS  not-accessible
         STATUS      current
         DESCRIPTION
           "
           It is used to configure the service attributes of a BRA port. It is used to add, delete, modify, and query the ISDN user with the VoIP feature.
           The index of this table is hwBraCTPConfigIndex.
           The attributes of an ISDN user with the VoIP feature include the gateway ID, terminal ID, IUA link group, interface ID, and telephone number. Through the table, you can configure, modify, and query the above-mentioned attributes of the BRA user.
           "
         ::= { hwIASVoiceUserObjects 4 }

       hwBraCTPConfigEntry OBJECT-TYPE
         SYNTAX      HwBraCTPConfigEntry
         MAX-ACCESS  not-accessible
         STATUS      current
         DESCRIPTION
           "
           It is used to configure the service attributes of a BRA port. It is used to add, delete, modify, and query the ISDN user with the VoIP feature.
           The index of this entry is hwBraCTPConfigIndex.
           The attributes of an ISDN user with the VoIP feature include the gateway ID, terminal ID, IUA link group, interface ID, and telephone number. Through the table, you can configure, modify, and query the above-mentioned attributes of the BRA user.
           "
         INDEX    {
                   hwBraCTPConfigIndex
                  }
         ::= { hwBraCTPConfigTable 1 }

       HwBraCTPConfigEntry ::=
         SEQUENCE
         {
           hwBraCTPConfigIndex	Integer32,
           hwBraCTPMgId	Integer32,
           hwBraCTPTerminationID	OCTET STRING,
           hwBraCTPTelNo	OCTET STRING,
           hwBraCTPLinkSetNo	Integer32,
           hwBraCTPIuaIID	Integer32,
           hwBraCTPRowStatus	RowStatus,
           hwBraCTPPriorityFlag INTEGER,
           hwBraCTPLayerFlag INTEGER,
           hwBraCTPUniErrReport INTEGER,
           hwBraCTPAutoResumeLimit  Integer32,
           hwBraCTPIuaTextIID OCTET STRING,
           hwBraCTPPowerDialerSupport INTEGER,
           hwBraCTPUserGroupid  Integer32,
           hwBraCTPDigitMapGroupName OCTET STRING,
           hwBraCTPConfigIncomingcallChangeName OCTET STRING,
           hwBraCTPConfigOutgoingcallChangeName OCTET STRING,
           hwBraCTPConfigDefaultCli OCTET STRING,
           hwBraCTPConfigDefaultCliMode INTEGER,
           hwBraCTPConfigBearCapability INTEGER,
           hwBraCTPConfigCalledPartyNumType INTEGER,
           hwBraCTPConfigCalledPartyNumInternationalPrefixFlag INTEGER,
           hwBraCTPConfigCalledPartyNumNationalPrefixFlag INTEGER,
           hwBraCTPDspParaTemplate OCTET STRING,
           hwBraCTPConfigCliGroup OCTET STRING
         }

       hwBraCTPConfigIndex OBJECT-TYPE
         SYNTAX      Integer32
         MAX-ACCESS  not-accessible
         STATUS      current
         DESCRIPTION
             "
             Indicates the frame/slot/port.
              25                                         0
              0011001 | xxxxxxxx | xxxxxx | xxxxxxx | 0000
              port      frame      slot     port      0
              type

              The highest 7 bits indicate the type of port, for BRA port, must be 0x19
              the next 8 bits indicate the frame ID,
              the next 6 bits indicate the slot ID,
              the next 7 bits indicate the port ID,
              the last 4 bits must be 0.

              The type of port include:
              E1   port = 0x16
              PSTN port = 0x18
              BRA  port = 0x19
              AT0  port = 0x1b
             "
         ::= { hwBraCTPConfigEntry 1 }

       hwBraCTPMgId OBJECT-TYPE
         SYNTAX      Integer32(0..16777215)
         MAX-ACCESS  read-create
         STATUS      current
         DESCRIPTION
             "
             Indicates the MG ID.
             "
         ::= { hwBraCTPConfigEntry 2 }

       hwBraCTPTerminationID OBJECT-TYPE
         SYNTAX      OCTET STRING(SIZE(0..64))
         MAX-ACCESS  read-create
         STATUS      current
         DESCRIPTION
             "
             Indicates the start terminal ID (only the character string of digit type is supported).
             "
         ::= { hwBraCTPConfigEntry 3 }

       hwBraCTPTelNo OBJECT-TYPE
         SYNTAX      OCTET STRING(SIZE(0..64))
         MAX-ACCESS  read-create
         STATUS      current
         DESCRIPTION
             "
             Indicates the BRA telephone number.
             "
         ::= { hwBraCTPConfigEntry 4 }

       hwBraCTPLinkSetNo OBJECT-TYPE
         SYNTAX      Integer32
         MAX-ACCESS  read-create
         STATUS      current
         DESCRIPTION
             "
             Indicates the link set to which the BRA terminal belongs (the value range depends on the product specifications).
             "
         ::= { hwBraCTPConfigEntry 5 }

       hwBraCTPIuaIID OBJECT-TYPE
         SYNTAX      Integer32(-1|0..65535)
         MAX-ACCESS  read-create
         STATUS      current
         DESCRIPTION
             "
             Indicates the interface ID of the BRA terminal.
             -1 means this parameter is not used.
             "
         ::= { hwBraCTPConfigEntry 6 }

       hwBraCTPRowStatus OBJECT-TYPE
         SYNTAX      RowStatus
         MAX-ACCESS  read-write
         STATUS      current
         DESCRIPTION
             "
             Indicates the row status.
             "
         ::= { hwBraCTPConfigEntry 7 }

       hwBraCTPPriorityFlag OBJECT-TYPE
          SYNTAX      INTEGER{cat1(1), -- the highest priority
                              cat2(2), -- the middle priority
                              cat3(3)  -- the lowest priority
                              }
          MAX-ACCESS  read-create
          STATUS      current
          DESCRIPTION
              "
              Indicates the priority of the terminal.
              Options:
              1. cat1(1) -the highest priority
              2. cat2(2) -the middle priority
              3. cat3(3) -the lowest priority
              Default: cat3(3)"
              DEFVAL      { cat3 }
          ::= { hwBraCTPConfigEntry 8 }

      hwBraCTPLayerFlag OBJECT-TYPE
          SYNTAX      INTEGER{noLayer(1), -- not to layer
                              layer(2),    -- to layer
                              null(-1)
                              }
          MAX-ACCESS  read-only
          STATUS      current
          DESCRIPTION
              "
              Indicates whether to layer.
              Options:
              1. noLayer(1)       -not to layer
              2. layer(2)         -to layer
              3. null(-1)         -invalid value
              "
          ::= { hwBraCTPConfigEntry 9 }

      hwBraCTPUniErrReport OBJECT-TYPE
          SYNTAX      INTEGER{disable(1),enable(2)}
          MAX-ACCESS  read-write
          STATUS      current
          DESCRIPTION
              "
              UNI fault report flag of bra user.
              Options:
              1. disable(1) -disable
              2. enable(2) -enable
              Default: disable(1)
              "
          ::= { hwBraCTPConfigEntry 10 }

      hwBraCTPAutoResumeLimit OBJECT-TYPE
          SYNTAX      Integer32(0..255)
          MAX-ACCESS  read-write
          STATUS      current
          DESCRIPTION
              "
              Indicates auto resume times threshold of bra user.
              Default: 20
              "
          ::= { hwBraCTPConfigEntry 11}

      hwBraCTPIuaTextIID OBJECT-TYPE
         SYNTAX      OCTET STRING(SIZE(0..53))
         MAX-ACCESS  read-create
         STATUS      current
         DESCRIPTION
             "
             Use the text to indicate the interface ID of the BRA terminal. Config area 0~65535. Display area 0~53.
             "
         ::= { hwBraCTPConfigEntry 12 }

      hwBraCTPPowerDialerSupport OBJECT-TYPE
          SYNTAX      INTEGER{enable(1),disable(2)}
          MAX-ACCESS  read-write
          STATUS      current
          DESCRIPTION
              "
              Powerdialer support flag of bra user.
              Options:
              1. enable(1) -enable
              2. disable(2) -disable
              Default: enable(1)
              "
          ::= { hwBraCTPConfigEntry 13 }

      hwBraCTPUserGroupid OBJECT-TYPE
          SYNTAX      Integer32(-1..65535)
          MAX-ACCESS  read-write
          STATUS      current
          DESCRIPTION
              "
              It indicates the user group ID.
              -1 indicates clear the user group info.
              "
          ::= { hwBraCTPConfigEntry 14 }

      hwBraCTPDigitMapGroupName OBJECT-TYPE
          SYNTAX      OCTET STRING(SIZE(0..32))
          MAX-ACCESS  read-write
          STATUS      current
          DESCRIPTION
              "
              It indicates the digitmap group name.
              "
          ::= { hwBraCTPConfigEntry 15 }

       hwBraCTPConfigIncomingcallChangeName OBJECT-TYPE
          SYNTAX      OCTET STRING(SIZE(0..32))
          MAX-ACCESS  read-write
          STATUS      current
          DESCRIPTION
              "
              It indicates the number change of incomging call name.
              "
          ::= { hwBraCTPConfigEntry 16 }

       hwBraCTPConfigOutgoingcallChangeName OBJECT-TYPE
          SYNTAX      OCTET STRING(SIZE(0..32))
          MAX-ACCESS  read-write
          STATUS      current
          DESCRIPTION
              "
              It indicates the number change of outgoing call name.
              "
          ::= { hwBraCTPConfigEntry 17 }

       hwBraCTPConfigDefaultCli OBJECT-TYPE
          SYNTAX      OCTET STRING(SIZE(0..64))
          MAX-ACCESS  read-write
          STATUS      current
          DESCRIPTION
              "
              It indicates the default cli number of outgoing call.
              "
          ::= { hwBraCTPConfigEntry 18 }

      hwBraCTPConfigDefaultCliMode OBJECT-TYPE
          SYNTAX      INTEGER{match(1),
                              overwrite(2),
                              null(-1)}
          MAX-ACCESS  read-write
          STATUS      current
          DESCRIPTION
              "
              Indicates the mode of cli number.
              Options:
              1. match(1) - match
              2. overwrite(2) -overwrite
              3. null(-1) -invalid value
              Default: match(1)
              "
          ::= { hwBraCTPConfigEntry 19 }

      hwBraCTPConfigBearCapability OBJECT-TYPE
          SYNTAX      INTEGER{speech(1),
                              audio(2),
                              speechOraudio(3),
                              null(-1)}
          MAX-ACCESS  read-write
          STATUS      current
          DESCRIPTION
              "
              Indicates the bearCapability of bra user.
              Options:
              1. speech(1)  -speech
              2. audio(2)  -3.1k-audio
              3. speechOraudio(3) -speech or 3.1k-audio
              4. null(-1) -invalid value
              Default: speechOraudio(3)
              "
          ::= { hwBraCTPConfigEntry 20 }

      hwBraCTPConfigCalledPartyNumType OBJECT-TYPE
          SYNTAX      INTEGER{unknown(1),
                              national(2),
                              auto(3),
                              international(4),
                              subscriber(5),
                              null(-1)}
          MAX-ACCESS  read-write
          STATUS      current
          DESCRIPTION
              "
              Indicates the type of called party number.
              Options:
              1. unknown(1) -unknown
              2. national(2) -national
              3. auto(3) -auto
              4. international(4) -international
              5. subscriber(5) -subscriber
              6. null(-1) -invalid value
              Default: unknown(1)
              "
          ::= { hwBraCTPConfigEntry 21 }

      hwBraCTPConfigCalledPartyNumInternationalPrefixFlag OBJECT-TYPE
          SYNTAX      INTEGER{enable(1),
                              disable(2),
                              null(-1)}
          MAX-ACCESS  read-write
          STATUS      current
          DESCRIPTION
              "
              Indicates whether to add prefix on international number.
              Options:
              1. enable(1)  -enable
              2. disable(2)  -disable
              3. null(-1) -invalid value
              Default: disable(2)
              "
          ::= { hwBraCTPConfigEntry 22 }

      hwBraCTPConfigCalledPartyNumNationalPrefixFlag OBJECT-TYPE
          SYNTAX      INTEGER{enable(1),
                              disable(2),
                              null(-1)}
          MAX-ACCESS  read-write
          STATUS      current
          DESCRIPTION
              "
              Indicates whether to add prefix on national number.
              Options:
              1. enable(1)   -enable
              2. disable(2)  -disable
              3. null(-1)    -invalid value
              Default: disable(2)
              "
          ::= { hwBraCTPConfigEntry 23 }

       hwBraCTPDspParaTemplate OBJECT-TYPE
       		SYNTAX      OCTET STRING(SIZE(0..31))
          MAX-ACCESS  read-create
          STATUS      current
          DESCRIPTION
              "
              Indicates the name of DSP parameter template.
              "
          ::= { hwBraCTPConfigEntry 24 }

       hwBraCTPConfigCliGroup OBJECT-TYPE
          SYNTAX      OCTET STRING(SIZE(0..32))
          MAX-ACCESS  read-write
          STATUS      current
          DESCRIPTION
              "
              It indicates the cli-group name of outgoing call.
              "
          ::= { hwBraCTPConfigEntry 25 }


       hwBraCTPOperTable OBJECT-TYPE
         SYNTAX      SEQUENCE OF HwBraCTPOperEntry
         MAX-ACCESS  not-accessible
         STATUS      current
         DESCRIPTION
           "
           It is used to perform operations on service attributes of a BRA port. Through this table, you can perform maintenance operations on an ISDN user with the VSP feature.
           The index of this table is hwBraCTPOperIndex.
           Different from the MG PSTN port, a BRA port contains two B channels and occupies two terminal IDs; however, only one terminal ID needs to be configured and this ID must be an even number. Then, the terminal ID in odd is allocated to the BRA port by default.
           Through this table, you can query the running status of the BRA B1/B2 service, management status of the BRA B1/B2 service, status of the BRA D channel, change time of the running status of the BRA B1/B2 service, and change time of the management status of the BRA B1/B2 service.
           Through the table, services on the BRA port can be terminated, started, and the service status can be queried.
           "
         ::= { hwIASVoiceUserObjects 5 }

       hwBraCTPOperEntry OBJECT-TYPE
         SYNTAX      HwBraCTPOperEntry
         MAX-ACCESS  not-accessible
         STATUS      current
         DESCRIPTION
           "
           It is used to perform operations on service attributes of a BRA port. Through this table, you can perform maintenance operations on an ISDN user with the VSP feature.
           The index of this entry is hwBraCTPOperIndex.
           Different from the MG PSTN port, a BRA port contains two B channels and occupies two terminal IDs; however, only one terminal ID needs to be configured and this ID must be an even number. Then, the terminal ID in odd is allocated to the BRA port by default.
           Through this table, you can query the running status of the BRA B1/B2 service, management status of the BRA B1/B2 service, status of the BRA D channel, change time of the running status of the BRA B1/B2 service, and change time of the management status of the BRA B1/B2 service.
           Through the table, services on the BRA port can be terminated, started, and the service status can be queried.
           "
         INDEX    {
                   hwBraCTPOperIndex
                  }
         ::= { hwBraCTPOperTable 1 }

       HwBraCTPOperEntry ::=
         SEQUENCE
         {
           hwBraCTPOperIndex	        Integer32,
           hwBraCTPB1SrvState	INTEGER,
           hwBraCTPB2SrvState	INTEGER,
           hwBraCTPB1AdminState	INTEGER,
           hwBraCTPB2AdminState	INTEGER,
           hwBraCTPAdminOper	        INTEGER,
           hwBraCTPDState	        INTEGER,
           hwBraCTPB1SrvStateChange	    TimeTicks,
           hwBraCTPB2SrvStateChange	    TimeTicks,
           hwBraCTPB1AdminStateChange	TimeTicks,
           hwBraCTPB2AdminStateChange	TimeTicks,
           hwBraCTPDStateChange	        TimeTicks,
           hwBraCTPMaxCobTime        Integer32,
           hwBraCTPOnexpire          INTEGER,
           hwBraCTPAutoResumeTimes   Integer32
         }

       hwBraCTPOperIndex OBJECT-TYPE
         SYNTAX      Integer32
         MAX-ACCESS  not-accessible
         STATUS      current
         DESCRIPTION
             "
             Indicates the frame/slot/port.
              25                                         0
              0011001 | xxxxxxxx | xxxxxx | xxxxxxx | 0000
              port      frame      slot     port      0
              type

              The highest 7 bits indicate the type of port, for BRA port, must be 0x19
              the next 8 bits indicate the frame ID,
              the next 6 bits indicate the slot ID,
              the next 7 bits indicate the port ID,
              the last 4 bits must be 0.

              The type of port include:
              E1   port = 0x16
              PSTN port = 0x18
              BRA  port = 0x19
              AT0  port = 0x1b
             "
         ::= { hwBraCTPOperEntry 1 }

       hwBraCTPB1SrvState OBJECT-TYPE
         SYNTAX      INTEGER{idle(1),  -- the user is idle
                             busy(2),  -- the user is busy
                             fault(3)  -- the port is fault
                             }
         MAX-ACCESS  read-only
         STATUS      current
         DESCRIPTION
             "
             Indicates the running status of the service layer of the BRA B1 channel.
             Options:
             1. idle(1) -the user is idle
             2. busy(2) -the user is busy
             3. fault(3) -the port is fault
             "
         ::= { hwBraCTPOperEntry 2 }

       hwBraCTPB2SrvState OBJECT-TYPE
         SYNTAX      INTEGER{idle(1), -- the user is idle
                             busy(2), -- the user is busy
                             fault(3) -- the user is fault
                             }
         MAX-ACCESS  read-only
         STATUS      current
         DESCRIPTION
             "
             Indicates the running status of the service layer of the BRA B2 channel.
             Options:
             1. idle(1) -the user is idle
             2. busy(2) -the user is busy
             3. fault(3) -the port is fault
             "
         ::= { hwBraCTPOperEntry 3 }

        hwBraCTPB1AdminState OBJECT-TYPE
         SYNTAX      INTEGER{blockedLocally(1),  -- the service is blocked cause of local reason
                             blockedRemotely(2), -- the service is blocked cause of remote reason
                             inService(3),       -- the service is normal
                             shuttingDown(4)     -- the service is shutting down
                             }
         MAX-ACCESS  read-only
         STATUS      current
         DESCRIPTION
             "
             Indicates the administration status of the service layer of the BRA B1 channel.
             Options:
             1. blockedLocally(1) -the service is blocked cause of local reason
             2. blockedRemotely(2) -the service is blocked cause of remote reason
             3. inService(3) -the service is normal
             4. shuttingDown(4) -the service is shutting down
             "
         ::= { hwBraCTPOperEntry 4 }

         hwBraCTPB2AdminState OBJECT-TYPE
         SYNTAX      INTEGER{blockedLocally(1),   -- the service is blocked cause of local reason
                             blockedRemotely(2),  -- the service is blocked cause of remote reason
                             inService(3),        -- the service is normal
                             shuttingDown(4)      -- the service is shutting down
                             }
         MAX-ACCESS  read-only
         STATUS      current
         DESCRIPTION
             "
             Indicates the administration status of the service layer of the BRA B2 channel.
             Options:
             1. blockedLocally(1) -the service is blocked cause of local reason
             2. blockedRemotely(2) -the service is blocked cause of remote reason
             3. inService(3) -the service is normal
             4. shuttingDown(4) -the service is shutting down
             "
         ::= { hwBraCTPOperEntry 5 }

        hwBraCTPAdminOper OBJECT-TYPE
          SYNTAX      INTEGER{endService(1),          -- stop service
                              startService(2),       -- start service
                              deferEndingService(3) -- stop service gracefully
                              }
          MAX-ACCESS  read-write
          STATUS      current
          DESCRIPTION
              "
              Indicates the maintenance operation of the service layer of the BRA port.
              Options:
              1. endService(1) -stop service
              2. startService(2) -start service
              3. deferEndingService(3) -stop service gracefully
              "
          ::= { hwBraCTPOperEntry 6 }

         hwBraCTPDState OBJECT-TYPE
         SYNTAX      INTEGER{established(1),  -- established
                             block(2),        -- blocked
                             notConstruct(3), -- unestablished
                             teiAlloced(4),   -- TEI is alloced
                             teiNotAlloced(5) -- TEI is not alloced
                             }
         MAX-ACCESS  read-only
         STATUS      current
         DESCRIPTION
             "
             Indicates the status of the BRA D channel.
             Options:
             1. established(1) -established
             2. block(2) -blocked
             3. notConstruct(3) -unestablished
             4. teiAlloced(4) -TEI is alloced
             5. teiNotAlloced(5) -TEI is not alloced
             "
         ::= { hwBraCTPOperEntry 7 }

       hwBraCTPB1SrvStateChange OBJECT-TYPE
         SYNTAX      TimeTicks
         MAX-ACCESS  read-only
         STATUS      current
         DESCRIPTION
             "
             Indicates the service running status changing time of the BRA B1 channel.
             "
         ::= { hwBraCTPOperEntry 8 }

       hwBraCTPB2SrvStateChange OBJECT-TYPE
         SYNTAX      TimeTicks
         MAX-ACCESS  read-only
         STATUS      current
         DESCRIPTION
             "
             Indicates the service running status changing time of the BRA B2 channel.
             "
         ::= { hwBraCTPOperEntry 9 }

       hwBraCTPB1AdminStateChange OBJECT-TYPE
         SYNTAX      TimeTicks
         MAX-ACCESS  read-only
         STATUS      current
         DESCRIPTION
             "
             Indicates the service administration status changing time of the BRA B1 channel.
             "
         ::= { hwBraCTPOperEntry 10 }

       hwBraCTPB2AdminStateChange OBJECT-TYPE
         SYNTAX      TimeTicks
         MAX-ACCESS  read-only
         STATUS      current
         DESCRIPTION
             "
             Indicates the service administration status changing time of the BRA B2 channel.
             "
         ::= { hwBraCTPOperEntry 11 }

       hwBraCTPDStateChange OBJECT-TYPE
         SYNTAX      TimeTicks
         MAX-ACCESS  read-only
         STATUS      current
         DESCRIPTION
             "
             Indicates the status changing time of the BRA D channel.
             "
         ::= { hwBraCTPOperEntry 12 }

       hwBraCTPMaxCobTime OBJECT-TYPE
         SYNTAX      Integer32(0..1440)
         MAX-ACCESS  read-write
         STATUS      current
         DESCRIPTION
             "
             Indicates the length of waiting timer for bra user defer end service. 0 is not allowed to set.
             Default:240
             Unit: minute
             "
         ::= { hwBraCTPOperEntry 13 }

       hwBraCTPOnexpire OBJECT-TYPE
         SYNTAX      INTEGER{force(1),cancel(2)}
         MAX-ACCESS  read-write
         STATUS      current
         DESCRIPTION
             "
             Indicates the disposal mode when bra user defer end service timeout.
             Options:
             1. force(1) -force user to end service
             2. cancel(2) -cancel user's end service
             Default: force(1)
             "
         ::= { hwBraCTPOperEntry 14 }

      hwBraCTPAutoResumeTimes OBJECT-TYPE
          SYNTAX      Integer32(0..255)
          MAX-ACCESS  read-only
          STATUS      current
          DESCRIPTION
              "
              Indicates the auto resume times of bra user.
              "
          ::= { hwBraCTPOperEntry 15}


        hwBraCTPStatisticsTable OBJECT-TYPE
          SYNTAX      SEQUENCE OF HwBraCTPStatisticsEntry
          MAX-ACCESS  not-accessible
          STATUS      current
          DESCRIPTION
            "
            This table is used to query the statistics of the MG-BRA service ports.
            The index of this table is hwBraCTPStatIndex.
            "
          ::= { hwIASVoiceUserObjects 6 }

        hwBraCTPStatisticsEntry OBJECT-TYPE
          SYNTAX      HwBraCTPStatisticsEntry
          MAX-ACCESS  not-accessible
          STATUS      current
          DESCRIPTION
            "
            This table is used to query the statistics of the MG-BRA service ports.
            The index of this entry is hwBraCTPStatIndex.
            "
          INDEX    {
                    hwBraCTPStatIndex
                   }
          ::= { hwBraCTPStatisticsTable 1 }

        HwBraCTPStatisticsEntry ::=
          SEQUENCE
          {
            hwBraCTPStatIndex	Integer32,
            hwBraCTPStatTotalNum	Integer32,
            hwBraCTPStatFaultNum	Integer32,
            hwBraCTPStatIdleNum	Integer32,
            hwBraCTPStatBusyNum	Integer32
          }

        hwBraCTPStatIndex OBJECT-TYPE
          SYNTAX      Integer32
          MAX-ACCESS  not-accessible
          STATUS      current
          DESCRIPTION
              "
              Indicates the frame ID.
              The GetNext (walk) operation is to collect the statistics of each specified shelf of the system.
              In the Get operation, if hwMgPortStatIndex is all F, the operation is to collect the statistics of the entire system; if hwMgPortStatIndex is not all F, the operation is to collect the statistics of the specified shelf.
              "
          ::= { hwBraCTPStatisticsEntry 1 }

        hwBraCTPStatTotalNum OBJECT-TYPE
          SYNTAX      Integer32
          MAX-ACCESS  read-only
          STATUS      current
          DESCRIPTION
              "
              Indicates the total number of the MGBRA service ports.
              "
          ::= { hwBraCTPStatisticsEntry 2 }

        hwBraCTPStatFaultNum OBJECT-TYPE
          SYNTAX      Integer32
          MAX-ACCESS  read-only
          STATUS      current
          DESCRIPTION
              "
              Indicates the number of faulty ports.
              "
          ::= { hwBraCTPStatisticsEntry 3 }

        hwBraCTPStatIdleNum OBJECT-TYPE
          SYNTAX      Integer32
          MAX-ACCESS  read-only
          STATUS      current
          DESCRIPTION
              "
              Indicates the number of idle ports.
              "
          ::= { hwBraCTPStatisticsEntry 4 }

        hwBraCTPStatBusyNum OBJECT-TYPE
          SYNTAX      Integer32
          MAX-ACCESS  read-only
          STATUS      current
          DESCRIPTION
              "
              Indicates the number of busy ports.
              "
          ::= { hwBraCTPStatisticsEntry 5 }



        hwPraCTPConfigTable OBJECT-TYPE
         SYNTAX      SEQUENCE OF HwPraCTPConfigEntry
         MAX-ACCESS  not-accessible
         STATUS      current
         DESCRIPTION
           "
           It is used to configure the service attributes of a PRA port. It is used to add, delete, modify, and query the PRA user with the VSP feature.
           The index of this table is the hwPraCTPConfigIndex.
           The attributes of a PRA user with the VoIP feature include the gateway ID, start terminal ID, IUA link group, and interface ID. Through the table, you can configure, modify, and query the above-mentioned attributes of the PRA user.
           "
         ::= { hwIASVoiceUserObjects 7 }

       hwPraCTPConfigEntry OBJECT-TYPE
         SYNTAX      HwPraCTPConfigEntry
         MAX-ACCESS  not-accessible
         STATUS      current
         DESCRIPTION
           "
           It is used to configure the service attributes of a PRA port. It is used to add, delete, modify, and query the PRA user with the VSP feature.
           The index of this entry is the hwPraCTPConfigIndex.
           The attributes of a PRA user with the VoIP feature include the gateway ID, start terminal ID, IUA link group, and interface ID. Through the table, you can configure, modify, and query the above-mentioned attributes of the PRA user.
           "
         INDEX    {
                   hwPraCTPConfigIndex
                  }
         ::= { hwPraCTPConfigTable 1 }

       HwPraCTPConfigEntry ::=
         SEQUENCE
         {
           hwPraCTPConfigIndex		Integer32,
           hwPraCTPMgId		Integer32,
           hwPraCTPTerminationID	OCTET STRING,
           hwPraCTPLinkSetNo	Integer32,
           hwPraCTPIuaIID	Integer32,
           hwPraCTPRowStatus	RowStatus,
           hwPraCTPLayerFlag   INTEGER,
           hwPraCTPPriorityFlag   INTEGER,
           hwPraCTPUniErrReport INTEGER,
           hwPraCTPSubChnMask   BITS,
           hwPraCTPTelNo   OCTET STRING,
           hwPraCTPAutoResumeLimit   Integer32,
           hwPraCTPIuaTextIID OCTET STRING,
           hwPraCTPPowerDialerSupport INTEGER,
           hwPraCTPUserGroupid  Integer32,
           hwPraCTPDigitMapGroupName OCTET STRING,
           hwPraCTPConfigIncomingcallChangeName OCTET STRING,
           hwPraCTPConfigOutgoingcallChangeName OCTET STRING,
           hwPraCTPConfigDefaultCli OCTET STRING,
           hwPraCTPConfigDefaultCliMode INTEGER,
           hwPraCTPConfigBearCapability INTEGER,
           hwPraCTPConfigCalledPartyNumType INTEGER,
           hwPraCTPConfigCalledPartyNumInternationalPrefixFlag INTEGER,
           hwPraCTPConfigCalledPartyNumNationalPrefixFlag INTEGER,
           hwPraCTPConfigCliGroup OCTET STRING,
           hwPraCTPBChnCallRight OCTET STRING
         }

       hwPraCTPConfigIndex OBJECT-TYPE
         SYNTAX      Integer32
         MAX-ACCESS  not-accessible
         STATUS      current
         DESCRIPTION
             "
             Indicates the frame/slot/port.
              22                                         0
              0010110 | xxxxxxxx | xxxxxx | xxxxxxx | 0000
              port      frame      slot     port      0
              type

              The highest 7 bits indicate the type of port, for E1 port, must be 0x16
              the next 8 bits indicate the frame ID,
              the next 6 bits indicate the slot ID,
              the next 7 bits indicate the port ID,
              the last 4 bits must be 0.

              The type of port include:
              E1   port = 0x16
              PSTN port = 0x18
              BRA  port = 0x19
              AT0  port = 0x1b
             "
         ::= { hwPraCTPConfigEntry 1 }

       hwPraCTPMgId OBJECT-TYPE
         SYNTAX      Integer32(0..16777215)
         MAX-ACCESS  read-create
         STATUS      current
         DESCRIPTION
             "
             Indicates the MG ID.
             "
         ::= { hwPraCTPConfigEntry 2 }

       hwPraCTPTerminationID OBJECT-TYPE
         SYNTAX      OCTET STRING(SIZE(0..64))
         MAX-ACCESS  read-create
         STATUS      current
         DESCRIPTION
             "
             Indicates the start terminal ID (only the character string of digit type is supported).
             "
         ::= { hwPraCTPConfigEntry 3 }

       hwPraCTPLinkSetNo OBJECT-TYPE
         SYNTAX      Integer32
         MAX-ACCESS  read-create
         STATUS      current
         DESCRIPTION
             "
             Indicates the link set to which the PRA terminal belongs (the value range depends on the product specifications).
             "
         ::= { hwPraCTPConfigEntry 4 }

       hwPraCTPIuaIID OBJECT-TYPE
         SYNTAX      Integer32(-1|0..65535)
         MAX-ACCESS  read-create
         STATUS      current
         DESCRIPTION
             "
             Indicates the interface ID of the PRA terminal.
             -1 means this parameter is not used.
             "
         ::= { hwPraCTPConfigEntry 5 }

       hwPraCTPRowStatus OBJECT-TYPE
         SYNTAX      RowStatus
         MAX-ACCESS  read-write
         STATUS      current
         DESCRIPTION
             "
             Indicates the row status.
             "
         ::= { hwPraCTPConfigEntry 6 }

      hwPraCTPLayerFlag OBJECT-TYPE
          SYNTAX      INTEGER{noLayer(1),  -- not to layer
                              layer(2),     -- to layer
                              null(-1)
                              }
          MAX-ACCESS  read-only
          STATUS      current
          DESCRIPTION
              "
              Indicates whether to layer.
              Options:
              1. noLayer(1)       -not to layer
              2. layer(2)         -to layer
              3. null(-1)         -invalid value
              "
          ::= { hwPraCTPConfigEntry 7}

      hwPraCTPPriorityFlag OBJECT-TYPE
          SYNTAX      INTEGER{cat1(1), -- the highest priority
                              cat2(2), -- the middle priority
                              cat3(3)  -- the lowest priority
                              }
          MAX-ACCESS  read-write
          STATUS      current
          DESCRIPTION
              "
              Indicates terminal priority.
              Options:
              1. cat1(1) -the highest priority
              2. cat2(2) -the middle priority
              3. cat3(3) -the lowest priority
              Default: cat3(3)
              "
              DEFVAL      { cat3 }
          ::= { hwPraCTPConfigEntry 8}

      hwPraCTPUniErrReport OBJECT-TYPE
          SYNTAX      INTEGER{disable(1),enable(2)}
          MAX-ACCESS  read-write
          STATUS      current
          DESCRIPTION
              "
              Indicates UNI fault report flag of e1 port.
              Options:
              1. disable(1) -disable UNI fault report of e1 port
              2. enable(2) -enable UNI fault report of e1 port
              Default: disable(1)
              "
              DEFVAL      { disable }
          ::= { hwPraCTPConfigEntry 9}

      hwPraCTPSubChnMask OBJECT-TYPE
          SYNTAX      BITS{bchn0(0),bchn1(1),bchn2(2),bchn3(3),bchn4(4),bchn5(5),bchn6(6),bchn7(7),bchn8(8),bchn9(9),bchn10(10),
                           bchn11(11),bchn12(12),bchn13(13),bchn14(14),bchn15(15),bchn16(16),bchn17(17),bchn18(18),bchn19(19),bchn20(20),
                           bchn21(21),bchn22(22),bchn23(23),bchn24(24),bchn25(25),bchn26(26),bchn27(27),bchn28(28),bchn29(29),bchn30(30),
                           bchn31(31)}
          MAX-ACCESS  read-write
          STATUS      current
          DESCRIPTION
              "
              Indicates from left to right, each bit indicates enable one sub channel(0-31) or not, 0 means disable, 1 means enable, sub channel 0 and 16 must enable.
              Default: 11111111111111111111111111111111
              "
          ::= { hwPraCTPConfigEntry 10}

      hwPraCTPTelNo OBJECT-TYPE
         SYNTAX      OCTET STRING(SIZE(0..64))
         MAX-ACCESS  read-create
         STATUS      current
         DESCRIPTION
             "
             Indicates telphone number.
             "
         ::= { hwPraCTPConfigEntry 11 }

      hwPraCTPAutoResumeLimit OBJECT-TYPE
          SYNTAX      Integer32(0..255)
          MAX-ACCESS  read-write
          STATUS      current
          DESCRIPTION
              "
              Indicates auto resume times threshold of pra user.
              Default: 20
              "
          ::= { hwPraCTPConfigEntry 12}

      hwPraCTPIuaTextIID OBJECT-TYPE
         SYNTAX      OCTET STRING(SIZE(0..53))
         MAX-ACCESS  read-create
         STATUS      current
         DESCRIPTION
             "
             Use the text to indicate the interface ID of the PRA terminal.
             "
         ::= { hwPraCTPConfigEntry 13 }

      hwPraCTPPowerDialerSupport OBJECT-TYPE
          SYNTAX      INTEGER{enable(1),disable(2)}
          MAX-ACCESS  read-write
          STATUS      current
          DESCRIPTION
              "
              Powerdialer support flag of pra user.
              Options:
              1. enable(1)  -support power dialer
              2. disable(2) -not support power dialer
              Default: enable(1)
              "
          ::= { hwPraCTPConfigEntry 14 }

      hwPraCTPUserGroupid OBJECT-TYPE
          SYNTAX      Integer32(-1..65535)
          MAX-ACCESS  read-write
          STATUS      current
          DESCRIPTION
              "
              It indicates the user group ID.
              -1 indicates clear the user group info.
              "
          ::= { hwPraCTPConfigEntry 15 }

      hwPraCTPDigitMapGroupName OBJECT-TYPE
          SYNTAX      OCTET STRING(SIZE(0..32))
          MAX-ACCESS  read-write
          STATUS      current
          DESCRIPTION
              "
              It indicates the digitmap group name.
              "
          ::= { hwPraCTPConfigEntry 16 }

      hwPraCTPConfigIncomingcallChangeName OBJECT-TYPE
          SYNTAX      OCTET STRING(SIZE(0..32))
          MAX-ACCESS  read-write
          STATUS      current
          DESCRIPTION
              "
              It indicates the number change name of incoming call.
              "
          ::= { hwPraCTPConfigEntry 17 }

      hwPraCTPConfigOutgoingcallChangeName OBJECT-TYPE
          SYNTAX      OCTET STRING(SIZE(0..32))
          MAX-ACCESS  read-write
          STATUS      current
          DESCRIPTION
              "
              It indicates the number change name of outgoing call.
              "
          ::= { hwPraCTPConfigEntry 18 }

      hwPraCTPConfigDefaultCli OBJECT-TYPE
          SYNTAX      OCTET STRING(SIZE(0..64))
          MAX-ACCESS  read-write
          STATUS      current
          DESCRIPTION
              "
              It indicates the default cli number of outgoing call.
              "
          ::= { hwPraCTPConfigEntry 19 }

      hwPraCTPConfigDefaultCliMode OBJECT-TYPE
          SYNTAX      INTEGER{match(1),
                              overwrite(2),
                              null(0)}
          MAX-ACCESS  read-write
          STATUS      current
          DESCRIPTION
              "
              Indicates the mode of cli number.
              Options:
              1. match(1)        -match
              2. overwrite(2)    -overwrite
              3. null(0)         -invalid value
              Default: match(1)
              "
          ::= { hwPraCTPConfigEntry 20 }

      hwPraCTPConfigBearCapability OBJECT-TYPE
          SYNTAX      INTEGER{speech(1),
                              audio(2),
                              speechOraudio(3),
                              null(0)}
          MAX-ACCESS  read-write
          STATUS      current
          DESCRIPTION
              "
              Indicates the bearCapability of pra user.
              Options:
              1. speech(1)          -speech
              2. audio(2)           -3.1k-audio
              3. speechOraudio(3)   -speech or 3.1k-audio
              4. null(0)            -invalid value
              Default: speechOraudio(3)
              "
          ::= { hwPraCTPConfigEntry 21 }

      hwPraCTPConfigCalledPartyNumType OBJECT-TYPE
          SYNTAX      INTEGER{unknown(1),
                              national(2),
                              auto(3),
                              international(4),
                              subscriber(5),
                              null(0)}
          MAX-ACCESS  read-write
          STATUS      current
          DESCRIPTION
              "
              Indicates the type of called party number.
              Options:
              1. unknown(1)      -unknown
              2. national(2)     -national
              3. auto(3)         -auto
              4. international(4)    -international
              5. subscriber(5)     -subscriber
              6. null(0)          -invalid value
              Default: unknown(1)
              "
          ::= { hwPraCTPConfigEntry 22 }

      hwPraCTPConfigCalledPartyNumInternationalPrefixFlag OBJECT-TYPE
          SYNTAX      INTEGER{enable(1),
                              disable(2),
                              null(0)}
          MAX-ACCESS  read-write
          STATUS      current
          DESCRIPTION
              "
              Indicates whether to add prefix on international number.
              Options:
              1. enable(1)       -enable
              2. disable(2)      -disable
              3. null(0)        -invalid value
              Default: disable(2)
              "
          ::= { hwPraCTPConfigEntry 23 }

      hwPraCTPConfigCalledPartyNumNationalPrefixFlag OBJECT-TYPE
          SYNTAX      INTEGER{enable(1),
                              disable(2),
                              null(0)}
          MAX-ACCESS  read-write
          STATUS      current
          DESCRIPTION
              "
              Indicates whether to add prefix on national number.
              Options:
              1. enable(1)        -enable
              2. disable(2)       -disable
              3. null(0)          -invalid value
              Default: disable(2)
              "
          ::= { hwPraCTPConfigEntry 24 }

        hwPraCTPConfigCliGroup OBJECT-TYPE
          SYNTAX      OCTET STRING(SIZE(0..32))
          MAX-ACCESS  read-write
          STATUS      current
          DESCRIPTION
              "
              It indicates the cli-group name of outgoing call.
              "
          ::= { hwPraCTPConfigEntry 25 }

        hwPraCTPBChnCallRight OBJECT-TYPE
          SYNTAX      OCTET STRING(SIZE(32..32))
          MAX-ACCESS  read-write
          STATUS      current
          DESCRIPTION
              "
              Indicates the B channel's incoming and outgoing call permissions.
              Indicates the permissions of B channels 0-31 from left to right.
              Meaning of a single byte:
                  0: indicates that the B channel does not have the outgoing or incoming call permission.
                  1: indicates that the B channel has only the outgoing call permission.
                  2: indicates that the B channel has only the incoming call permission.
                  3: indicates that the B channel has the incoming and outgoing call permissions.
              Only 3 can be configured for B channels 0 and 16.
              "
          ::= { hwPraCTPConfigEntry 26 }

        hwPraCTPOperTable OBJECT-TYPE
         SYNTAX      SEQUENCE OF HwPraCTPOperEntry
         MAX-ACCESS  not-accessible
         STATUS      current
         DESCRIPTION
           "
           It is used to perform operations on service attributes of a PRA port. Through this table, you can perform maintenance operations on a PRA user with the VSP feature.
           The index of this table is hwPraCTPOperIndex.
           Through this table, you can query the running status of 32 B channels of the PRA service, management status of 32 B channels of the PRA service, and status of the PRA D channel.
           Through the table, services on the PRA port can be terminated, started, and the service status can be queried.
           "
         ::= { hwIASVoiceUserObjects 8 }

       hwPraCTPOperEntry OBJECT-TYPE
         SYNTAX      HwPraCTPOperEntry
         MAX-ACCESS  not-accessible
         STATUS      current
         DESCRIPTION
           "
           It is used to perform operations on service attributes of a PRA port. Through this table, you can perform maintenance operations on a PRA user with the VSP feature.
           The index of this entry is hwPraCTPOperIndex.
           Through this table, you can query the running status of 32 B channels of the PRA service, management status of 32 B channels of the PRA service, and status of the PRA D channel.
           Through the table, services on the PRA port can be terminated, started, and the service status can be queried.
           "
         INDEX    {
                   hwPraCTPOperIndex
                  }
         ::= { hwPraCTPOperTable 1 }

       HwPraCTPOperEntry ::=
         SEQUENCE
         {
           hwPraCTPOperIndex	      Integer32,
           hwPraCTPBchnSrvState    OCTET STRING,
           hwPraCTPBchnAdminState  OCTET STRING,
           hwPraCTPAdminOper	      INTEGER,
           hwPraCTPDState	      INTEGER,
           hwPraCTPMaxCobTime      Integer32,
           hwPraCTPOnexpire        INTEGER,
           hwPraCTPAutoResumeTimes   Integer32
         }

       hwPraCTPOperIndex OBJECT-TYPE
         SYNTAX      Integer32
         MAX-ACCESS  not-accessible
         STATUS      current
         DESCRIPTION
             "
             Indicates the frame/slot/port.
              22                                         0
              0010110 | xxxxxxxx | xxxxxx | xxxxxxx | 0000
              port      frame      slot     port      0
              type

              The highest 7 bits indicate the type of port, for E1 port, must be 0x16
              the next 8 bits indicate the frame ID,
              the next 6 bits indicate the slot ID,
              the next 7 bits indicate the port ID,
              the last 4 bits must be 0.

              The type of port include:
              E1   port = 0x16
              PSTN port = 0x18
              BRA  port = 0x19
              AT0  port = 0x1b
             "
         ::= { hwPraCTPOperEntry 1 }

       hwPraCTPBchnSrvState OBJECT-TYPE
         SYNTAX      OCTET STRING(SIZE (0..32))
         MAX-ACCESS  read-only
         STATUS      current
         DESCRIPTION
             "
             Indicates the running status of the service layer of the 32 B channels of the PRA. Each character corresponds to a timeslot. The value of the character is as follows: 1-Idle; 2-Busy; 3-Faulty; 4-Unavailable.
             "
         ::= { hwPraCTPOperEntry 2 }

       hwPraCTPBchnAdminState OBJECT-TYPE
         SYNTAX      OCTET STRING(SIZE (0..32))
         MAX-ACCESS  read-only
         STATUS      current
         DESCRIPTION
             "
             Indicates the administration status of the service layer of the 32 B channels of the PRA. Each character corresponds to a timeslot. The value of the character is as follows: 1-blocked-locally; 2-blocked-remotely; 3-in-service;4-shutting-down.
             "
         ::= { hwPraCTPOperEntry 3 }

        hwPraCTPAdminOper OBJECT-TYPE
          SYNTAX      INTEGER{endService(1),         -- stop service
                              startService(2),       -- start service
                              deferEndingService(3) -- stop service gracefully
                              }
          MAX-ACCESS  read-write
          STATUS      current
          DESCRIPTION
              "
              Indicates the service operation.
              Options:
              1. endService(1) -stop service
              2. startService(2) -start service
              3. deferEndingService(3) -stop service gracefully
              "
          ::= { hwPraCTPOperEntry 4 }

       hwPraCTPDState OBJECT-TYPE
         SYNTAX      INTEGER{established(1), -- established
                             block(2),       -- blocked
                             notConstruct(3) -- unestablished
                             }
         MAX-ACCESS  read-only
         STATUS      current
         DESCRIPTION
             "
             Indicates the status of the PRA D channel.
             Options:
             1. established(1) -established
             2. block(2) -blocked
             3. notConstruct(3) -unestablished
             "
         ::= { hwPraCTPOperEntry 5 }

       hwPraCTPMaxCobTime OBJECT-TYPE
         SYNTAX      Integer32(0..1440)
         MAX-ACCESS  read-write
         STATUS      current
         DESCRIPTION
             "
             Indicates length of waiting timer for pra user defer end service.
             0 is not allowed to set.
             Default: 240
             Unit: minute
             "
         ::= { hwPraCTPOperEntry 6 }

       hwPraCTPOnexpire OBJECT-TYPE
         SYNTAX      INTEGER{force(1),cancel(2)}
         MAX-ACCESS  read-write
         STATUS      current
         DESCRIPTION
             "
             Indicates disposal mode when pra user defer end service timeout.
             Options:
             1. force(1)  -force end service
             2. cancel(2) -cancel end service
             Default: force(1)
             "
         ::= { hwPraCTPOperEntry 7 }

       hwPraCTPAutoResumeTimes OBJECT-TYPE
          SYNTAX      Integer32(0..255)
          MAX-ACCESS  read-only
          STATUS      current
          DESCRIPTION
              "
              Indicates auto resume times of pra user.
              "
          ::= { hwPraCTPOperEntry 8}


        hwPortStateTraceOperTable OBJECT-TYPE
          SYNTAX      SEQUENCE OF HwPortStateTraceOperEntry
          MAX-ACCESS  not-accessible
          STATUS      current
          DESCRIPTION
            "
            It is used to trace port status.
            The index of this table is hwPortStateTraceFrameId.
            This table traces states of the MG PSTN ports and MG BRA ports in real time, which contains trace start, trace end, and handshake operations.
            "
          ::= { hwIASVoiceUserObjects 9 }

        hwPortStateTraceOperEntry OBJECT-TYPE
          SYNTAX      HwPortStateTraceOperEntry
          MAX-ACCESS  not-accessible
          STATUS      current
          DESCRIPTION
            "
            It is used to trace port status.
            The index of this entry is hwPortStateTraceFrameId.
            This table traces states of the MG PSTN ports and MG BRA ports in real time, which contains trace start, trace end, and handshake operations.
            "
          INDEX    {
                    hwPortStateTraceOperFrameId
                   }
          ::= { hwPortStateTraceOperTable 1 }

        HwPortStateTraceOperEntry ::=
          SEQUENCE
          {
            hwPortStateTraceOperFrameId	  Integer32,
            hwPortStateTraceOperType    INTEGER,
            hwPortStateTraceOperReportType Integer32
          }

        hwPortStateTraceOperFrameId OBJECT-TYPE
          SYNTAX      Integer32
          MAX-ACCESS  not-accessible
          STATUS      current
          DESCRIPTION
              "
              Indicates the frame ID.
              "
          ::= { hwPortStateTraceOperEntry 1 }

        hwPortStateTraceOperType OBJECT-TYPE
          SYNTAX      INTEGER{stop(1),start(2),handshake(3)}
          MAX-ACCESS  read-write
          STATUS      current
          DESCRIPTION
              "
              Indicates the operation type.
              Options:
              1. stop(1) -stop tracing
              2. start(2) -start tracing
              3. handshake(3) -handshake
              "
          ::= { hwPortStateTraceOperEntry 2 }

        hwPortStateTraceOperReportType OBJECT-TYPE
          SYNTAX      Integer32(0..15)
          MAX-ACCESS  read-write
          STATUS      current
          DESCRIPTION
              "
              Indicates the report type (adopting the bit table):
              Bit0: indicates to report the running status change of the physical layer.
              Bit1: indicates to report the administration status change of the physical layer.
              Bit2: indicates to report the running status change of the service layer.
              Bit3: indicates to report the administration status change of the service layer.
              "
          ::= { hwPortStateTraceOperEntry 3 }

         hwUserDataTrapSequence OBJECT IDENTIFIER ::= { hwIASVoiceUserObjects 10 }

     		hwPstnUserDataTrapSequence OBJECT-TYPE
     			SYNTAX Integer32
     			MAX-ACCESS read-only
     			STATUS current
     			DESCRIPTION
     				"
     				Indicates that the Trap sequence is reported after the PSTN subscriber data changes.
                    "
     			::= { hwUserDataTrapSequence 1 }

     		hwBraUserDataChangeSequence OBJECT-TYPE
     			SYNTAX Integer32
     			MAX-ACCESS read-only
     			STATUS current
     			DESCRIPTION
     				"
     				Indicates that the Trap sequence is reported after the BRA subscriber data changes.
                    "
     			::= { hwUserDataTrapSequence 2 }

     		hwPraUserDataChangeSequence OBJECT-TYPE
     			SYNTAX Integer32
     			MAX-ACCESS read-only
     			STATUS current
     			DESCRIPTION
     				"
     				Indicates that the Trap sequence is reported after the PRA subscriber data changes.
                    "
     			::= { hwUserDataTrapSequence 3 }

     		hwR2UserDataChangeSequence OBJECT-TYPE
     			SYNTAX Integer32
     			MAX-ACCESS read-only
     			STATUS current
     			DESCRIPTION
     				"
     				Indicates that the Trap sequence is reported after the R2 subscriber data changes.
                    "
     			::= { hwUserDataTrapSequence 4 }


       hwPmbsCTPConfigTable OBJECT-TYPE
          SYNTAX      SEQUENCE OF HwPmbsCTPConfigEntry
          MAX-ACCESS  not-accessible
          STATUS      current
          DESCRIPTION
            "
            This table is used to config PMBS user.
            The index of this table is hwPmbsCTPConfigIndex.
            "
          ::= { hwIASVoiceUserObjects 11 }

        hwPmbsCTPConfigEntry OBJECT-TYPE
          SYNTAX      HwPmbsCTPConfigEntry
          MAX-ACCESS  not-accessible
          STATUS      current
          DESCRIPTION
            "
            This table is used to config PMBS user.
            The index of this entry is hwPmbsCTPConfigIndex.
            "
          INDEX    {
                    hwPmbsCTPConfigIndex
                   }
          ::= { hwPmbsCTPConfigTable 1 }

       HwPmbsCTPConfigEntry ::=
          SEQUENCE
          {
            hwPmbsCTPConfigIndex	              Integer32,
            hwPmbsCTPLinkSetNo                  Integer32,
            hwPmbsCTPluaIID                Integer32,
            hwPmbsCTPRowStatus                  RowStatus,
            hwPmbsCTPIuaTextIID             OCTET STRING
          }

       hwPmbsCTPConfigIndex OBJECT-TYPE
          SYNTAX      Integer32
          MAX-ACCESS  not-accessible
          STATUS      current
          DESCRIPTION
              "
              Indicates the frame/slot/port.

              The PMBS user must be configurated on BRA port.

              25                                         0
              0011001 | xxxxxxxx | xxxxxx | xxxxxxx | 0000
              port      frame      slot     port      0
              type

              The highest 7 bits indicate the type of port, for BRA port, must be 0x19
              the next 8 bits indicate the frame ID,
              the next 6 bits indicate the slot ID,
              the next 7 bits indicate the port ID,
              the last 4 bits must be 0.

              The type of port include:
              E1   port = 0x16
              PSTN port = 0x18
              BRA  port = 0x19
              AT0  port = 0x1b
              "
          ::= { hwPmbsCTPConfigEntry 1 }

       hwPmbsCTPLinkSetNo OBJECT-TYPE
          SYNTAX      Integer32
          MAX-ACCESS  read-create
          STATUS      current
          DESCRIPTION
              "
              IUA LinkSetNo.
              "
          ::= { hwPmbsCTPConfigEntry 2 }

       hwPmbsCTPluaIID OBJECT-TYPE
          SYNTAX      Integer32(0..65535 | -1)
          MAX-ACCESS  read-write
          STATUS      current
          DESCRIPTION
              "
              IUA Interface ID.
              "
          ::= { hwPmbsCTPConfigEntry 3 }

       hwPmbsCTPRowStatus OBJECT-TYPE
          SYNTAX      RowStatus
          MAX-ACCESS  read-write
          STATUS      current
          DESCRIPTION
             "
             Row status.
             "
          ::= { hwPmbsCTPConfigEntry 4 }

       hwPmbsCTPIuaTextIID OBJECT-TYPE
         SYNTAX      OCTET STRING(SIZE(0..53))
         MAX-ACCESS  read-create
         STATUS      current
         DESCRIPTION
             "
             Use the text to indicate the interface ID of the PMBS terminal.
             "
         ::= { hwPmbsCTPConfigEntry 5 }

       hwPmbsCTPOperTable OBJECT-TYPE
          SYNTAX      SEQUENCE OF HwPmbsCTPOperEntry
          MAX-ACCESS  not-accessible
          STATUS      current
          DESCRIPTION
            "
            This table is used to operate the PMBS user.
            The index of this table is hwPmbsCTPOperIndex.
            "
          ::= { hwIASVoiceUserObjects 12 }

       hwPmbsCTPOperEntry OBJECT-TYPE
          SYNTAX      HwPmbsCTPOperEntry
          MAX-ACCESS  not-accessible
          STATUS      current
          DESCRIPTION
            "
            This table is used to operate the PMBS user.
            The index of this entry is hwPmbsCTPOperIndex.
            "
          INDEX    {
                    hwPmbsCTPOperIndex
                   }
          ::= { hwPmbsCTPOperTable 1 }

       HwPmbsCTPOperEntry ::=
          SEQUENCE
          {
            hwPmbsCTPOperIndex            Integer32,
            hwPmbsCTPPLinkState           BITS
          }

       hwPmbsCTPOperIndex OBJECT-TYPE
          SYNTAX      Integer32
          MAX-ACCESS  not-accessible
          STATUS      current
          DESCRIPTION
              "
              Indicates the frame/slot/port.
              25                                         0
              0011001 | xxxxxxxx | xxxxxx | xxxxxxx | 0000
              port      frame      slot     port      0
              type

              The highest 7 bits indicate the type of port, for BRA port, must be 0x19
              the next 8 bits indicate the frame ID,
              the next 6 bits indicate the slot ID,
              the next 7 bits indicate the port ID,
              the last 4 bits must be 0.

              The type of port include:
              E1   port = 0x16
              PSTN port = 0x18
              BRA  port = 0x19
              AT0  port = 0x1b
              "
          ::= { hwPmbsCTPOperEntry 1 }

       hwPmbsCTPPLinkState OBJECT-TYPE
          SYNTAX      BITS{ tei1(0),tei2(1),tei3(2),tei4(3),tei5(4),tei6(5),tei7(6),tei8(7),tei9(8),tei10(9),tei11(10),
                            tei12(11),tei13(12),tei14(13),tei15(14),tei16(15),tei17(16),tei18(17),tei19(18),tei20(19),tei21(20),
                            tei22(21),tei23(22),tei24(23),tei25(24),tei26(25),tei27(26),tei28(27),tei29(28),tei30(29),tei31(30),
                            tei32(31),tei33(32),tei34(33),tei35(34),tei36(35),tei37(36),tei38(37),tei39(38),tei40(39),tei41(40),
                            tei42(41),tei43(42),tei44(43),tei45(44),tei46(45),tei47(46),tei48(47),tei49(48),tei50(49),tei51(50),
                            tei52(51),tei53(52),tei54(53),tei55(54),tei56(55),tei57(56),tei58(57),tei59(58),tei60(59),tei61(60),
                            tei62(61),tei63(62) }

          MAX-ACCESS  read-only
          STATUS      current
          DESCRIPTION
              "
              Indicates from left to right, each bit indicates plink status of one TEI(0-62) or not, 0 means plink not established, 1 means plink established.
              "
          ::= { hwPmbsCTPOperEntry 2 }

     hwPstnCTPRightConfigTable OBJECT-TYPE
          SYNTAX      SEQUENCE OF HwPstnCTPRightConfigEntry
          MAX-ACCESS  not-accessible
          STATUS      current
          DESCRIPTION
            "
            This table is used to config PSTN user's right and servicedata.
            The indexes of this table are hwPstnCTPRightConfigIndex, hwPstnCTPRightPortBindIndex.
            "
          ::= { hwIASVoiceUserObjects 13 }

        hwPstnCTPRightConfigEntry OBJECT-TYPE
          SYNTAX      HwPstnCTPRightConfigEntry
          MAX-ACCESS  not-accessible
          STATUS      current
          DESCRIPTION
            "
            This table is used to config PSTN user's right and servicedata.
            The indexes of this entry are hwPstnCTPRightConfigIndex, hwPstnCTPRightPortBindIndex.
            "
          INDEX    {
                    hwPstnCTPRightConfigIndex,
                    hwPstnCTPRightPortBindIndex
                   }
          ::= { hwPstnCTPRightConfigTable 1 }

        HwPstnCTPRightConfigEntry ::=
          SEQUENCE
          {
            hwPstnCTPRightConfigIndex	Integer32,
            hwPstnCTPRightPortBindIndex	Integer32,
            hwPstnCTPRightCallHold	INTEGER,
            hwPstnCTPRightThreeParty	INTEGER,
            hwPstnCTPRightConf	INTEGER,
            hwPstnCTPRightCt 	INTEGER,
            hwPstnCTPRightCw 	INTEGER,
            hwPstnCTPRightMcid       INTEGER,
            hwPstnCTPRightMwi        INTEGER,
            hwPstnCTPRightTp         INTEGER,
            hwPstnCTPRightCd         INTEGER,
            hwPstnCTPRightUus1       INTEGER,
            hwPstnCTPRightUus2     INTEGER,
            hwPstnCTPRightUus3     INTEGER,
            hwPstnCTPRightCentrexNo  Unsigned32,
            hwPstnCTPRightCentrexPrefix OCTET STRING,
            hwPstnCTPRightCentrexFlag INTEGER,
            hwPstnCTPRightMwiMode INTEGER,
            hwPstnCTPRightHotTime Integer32,
            hwPstnCTPRightHotLineNum OCTET STRING,
            hwPstnCTPRightDialTone INTEGER,
            hwPstnCTPRightCfbNum OCTET STRING,
            hwPstnCTPRightCfuNum OCTET STRING,
            hwPstnCTPRightCfnrNum OCTET STRING,
            hwPstnCTPRightCfnrTime Integer32,
            hwPstnCTPRightAnonymousCall INTEGER,
            hwPstnCTPRightAuthName OCTET STRING,
            hwPstnCTPRightAuthPassword OCTET STRING,
            hwPstnCTPRightEndConfigIndex Integer32,
            hwPstnCTPRightAuthPasswordMode INTEGER,
            hwPstnCTPRightAuthHA1  OCTET STRING,
            hwPstnCTPRightAutoReversePolarity INTEGER,
            hwPstnCTPRightDisplayNameMode INTEGER,
            hwPstnCTPRightDisplayName OCTET STRING,
            hwPstnCTPRightHotLine INTEGER,
            hwPstnCTPRightPermanentHold INTEGER,
            hwPstnCTPRightCutoffDisconnect INTEGER,
            hwPstnCTPRightSccClass INTEGER,
            hwPstnCTPRightPermanentHoldMode INTEGER,
            hwPstnCTPRightPermanentHoldTime Integer32,
            hwPstnCTPRightFastDisconnect INTEGER,
            hwPstnCTPRightDc INTEGER
          }

        hwPstnCTPRightConfigIndex OBJECT-TYPE
          SYNTAX      Integer32
          MAX-ACCESS  not-accessible
          STATUS      current
          DESCRIPTION
              "
              Indicates the frame/slot/port.
              31                                         0
              0011000 | xxxxxxxx | xxxxxx | xxxxxxx | 0000
              port      frame      slot     port      0
              type

              The highest 7 bits indicate the type of port, for PSTN port, must be 0x18
              the next 8 bits indicate the frame ID,
              the next 6 bits indicate the slot ID,
              the next 7 bits indicate the port ID,
              the last 4 bits must be 0.

              The type of port include:
              E1   port = 0x16
              PSTN port = 0x18
              BRA  port = 0x19
              AT0  port = 0x1b
              "
          ::= { hwPstnCTPRightConfigEntry 1 }

        hwPstnCTPRightPortBindIndex OBJECT-TYPE
          SYNTAX      Integer32(0..65535)
          MAX-ACCESS  not-accessible
          STATUS      current
          DESCRIPTION
              "
              Indicates the telephone number index.
              "
          ::= { hwPstnCTPRightConfigEntry 2 }

        hwPstnCTPRightCallHold OBJECT-TYPE
          SYNTAX      INTEGER{disable(1),enable(2)}
          MAX-ACCESS  read-write
          STATUS      current
          DESCRIPTION
              "
              Indicates the right flag of callhold.
              Options:
              1. disable(1) -disable
              2. enable(2) -enable
              "
              DEFVAL      { enable }
          ::= { hwPstnCTPRightConfigEntry 3 }

        hwPstnCTPRightThreeParty OBJECT-TYPE
          SYNTAX      INTEGER{disable(1),enable(2)}
          MAX-ACCESS  read-write
          STATUS      current
          DESCRIPTION
              "
              Indicates the right flag of three-party.
              Options:
              1. disable(1) -disable
              2. enable(2) -enable
              "
              DEFVAL      { enable }
          ::= { hwPstnCTPRightConfigEntry 4 }

        hwPstnCTPRightConf OBJECT-TYPE
          SYNTAX      INTEGER{disable(1),enable(2)}
          MAX-ACCESS  read-write
          STATUS      current
          DESCRIPTION
              "
              Indicates the right flag of conf.
              Options:
              1. disable(1) -disable
              2. enable(2) -enable
              "
              DEFVAL      { enable }
          ::= { hwPstnCTPRightConfigEntry 5 }

        hwPstnCTPRightCt OBJECT-TYPE
          SYNTAX      INTEGER{disable(1),enable(2)}
          MAX-ACCESS  read-write
          STATUS      current
          DESCRIPTION
              "
              Indicates the right flag of ct.
              Options:
              1. disable(1) -disable
              2. enable(2) -enable
              "
              DEFVAL      { enable }
          ::= { hwPstnCTPRightConfigEntry 6 }

        hwPstnCTPRightCw OBJECT-TYPE
          SYNTAX      INTEGER{disable(1),enable(2)}
          MAX-ACCESS  read-write
          STATUS      current
          DESCRIPTION
              "
              Indicates the right flag of cw.
              Options:
              1. disable(1) -disable
              2. enable(2) -enable
              "
              DEFVAL      { disable }
          ::= { hwPstnCTPRightConfigEntry 7 }

        hwPstnCTPRightMcid OBJECT-TYPE
          SYNTAX      INTEGER{disable(1),enable(2)}
          MAX-ACCESS  read-write
          STATUS      current
          DESCRIPTION
              "
              Indicates the right flag of mcid.
              Options:
              1. disable(1) -disable
              2. enable(2) -enable
              "
              DEFVAL      { disable }
          ::= { hwPstnCTPRightConfigEntry 8 }

        hwPstnCTPRightMwi OBJECT-TYPE
          SYNTAX      INTEGER{disable(1),enable(2)}
          MAX-ACCESS  read-write
          STATUS      current
          DESCRIPTION
              "
              Indicates the right flag of mwi.
              Options:
              1. disable(1) -disable
              2. enable(2) -enable
              "
              DEFVAL      { disable }
          ::= { hwPstnCTPRightConfigEntry 9 }

        hwPstnCTPRightTp OBJECT-TYPE
          SYNTAX      INTEGER{disable(1),enable(2)}
          MAX-ACCESS  read-write
          STATUS      obsolete
          DESCRIPTION
              "
              Indicates the right flag of tp.
              Options:
              1. disable(1) -disable
              2. enable(2) -enable
              "
              DEFVAL      { disable }
          ::= { hwPstnCTPRightConfigEntry 10 }

        hwPstnCTPRightCd OBJECT-TYPE
          SYNTAX      INTEGER{disable(1),enable(2)}
          MAX-ACCESS  read-write
          STATUS      obsolete
          DESCRIPTION
              "
              Indicates the right flag of cd.
              Options:
              1. disable(1) -disable
              2. enable(2) -enable
              "
              DEFVAL      { disable }
          ::= { hwPstnCTPRightConfigEntry 11 }

        hwPstnCTPRightUus1 OBJECT-TYPE
          SYNTAX      INTEGER{disable(1),enable(2)}
          MAX-ACCESS  read-write
          STATUS      obsolete
          DESCRIPTION
              "
              Indicates the right flag of uus1.
              Options:
              1. disable(1) -disable
              2. enable(2) -enable
              "
              DEFVAL      { disable }
          ::= { hwPstnCTPRightConfigEntry 12 }

        hwPstnCTPRightUus2 OBJECT-TYPE
          SYNTAX      INTEGER{disable(1),enable(2)}
          MAX-ACCESS  read-write
          STATUS      obsolete
          DESCRIPTION
              "
              Indicates the right flag of uus2.
              Options:
              1. disable(1) -disable
              2. enable(2) -enable
              "
              DEFVAL      { disable }
          ::= { hwPstnCTPRightConfigEntry 13 }

        hwPstnCTPRightUus3 OBJECT-TYPE
          SYNTAX      INTEGER{disable(1),enable(2)}
          MAX-ACCESS  read-write
          STATUS      obsolete
          DESCRIPTION
              "
              Indicates the right flag of uus3.
              Options:
              1. disable(1) -disable
              2. enable(2) -enable
              "
              DEFVAL      { disable }
          ::= { hwPstnCTPRightConfigEntry 14 }

        hwPstnCTPRightCentrexNo OBJECT-TYPE
          SYNTAX      Unsigned32(0..4294967295)
          MAX-ACCESS  read-write
          STATUS      current
          DESCRIPTION
              "
              It is used to set centrex NO. of SipPstnUser, 4294967295 means to clear the configuration.
              "
              DEFVAL      { 4294967295 }
          ::= { hwPstnCTPRightConfigEntry 15 }

        hwPstnCTPRightCentrexPrefix OBJECT-TYPE
          SYNTAX      OCTET STRING(SIZE(0..7))
          MAX-ACCESS  read-write
          STATUS      current
          DESCRIPTION
              "
              Indicates the CentrexPrefix of SipPstnUser.
              "
          ::= { hwPstnCTPRightConfigEntry 16 }

        hwPstnCTPRightCentrexFlag OBJECT-TYPE
          SYNTAX      INTEGER{dialDirectly(1), -- dial directly
                              dialSecondary(2) -- dial secondary
                              }
          MAX-ACCESS  read-write
          STATUS      current
          DESCRIPTION
              "
              Indicates the CentrexFlag of SipPstnUser.
              Options:
              1. dialDirectly(1) -dial directly
              2. dialSecondary(2) -dial secondary
              "
              DEFVAL      { dialdirectly }
          ::= { hwPstnCTPRightConfigEntry 17 }

        hwPstnCTPRightMwiMode OBJECT-TYPE
          SYNTAX      INTEGER{deferred(1),  -- deferred
                              immediate(2), -- immediate
                              combine(3)    -- combine
                              }
          MAX-ACCESS  read-write
          STATUS      current
          DESCRIPTION
              "
              Indicates the MwiMode of SipPstnUser.
              Options:
              1. deferred(1) -deferred
              2. immediate(2) -immediate
              3. combine(3) -combine
              "
              DEFVAL      { deferred }
          ::= { hwPstnCTPRightConfigEntry 18 }

        hwPstnCTPRightHotTime OBJECT-TYPE
          SYNTAX      Integer32(0..255)
          MAX-ACCESS  read-write
          STATUS      current
          DESCRIPTION
              "
              Indicates the HotTime of SipPstnUser.
              Unit: second
              "
              DEFVAL      { 5 }
          ::= { hwPstnCTPRightConfigEntry 19 }

        hwPstnCTPRightHotLineNum OBJECT-TYPE
          SYNTAX      OCTET STRING(SIZE(0..64))
          MAX-ACCESS  read-write
          STATUS      current
          DESCRIPTION
              "
              Indicates the HotLineNum of SipPstnUser, the length of hotlinenum mustn't exceed 64.
              "
          ::= { hwPstnCTPRightConfigEntry 20 }

        hwPstnCTPRightDialTone OBJECT-TYPE
          SYNTAX      INTEGER{normal(1),special(2),mw(3),stutter(4)}
          MAX-ACCESS  read-write
          STATUS      current
          DESCRIPTION
              "
              Indicates the DialTone of SipPstnUser.
              Options:
              1. normal(1) -normal tone
              2. special(2) -special tone
              3. mw(3) -message waiting tone
              4. stutter(4) -stutter tone
              "
              DEFVAL      { normal }
          ::= { hwPstnCTPRightConfigEntry 21 }

        hwPstnCTPRightCfbNum OBJECT-TYPE
          SYNTAX      OCTET STRING(SIZE(0..64))
          MAX-ACCESS  read-write
          STATUS      current
          DESCRIPTION
              "
              Indicates the CfbNum of SipPstnUser.
              "
          ::= { hwPstnCTPRightConfigEntry 22 }

        hwPstnCTPRightCfnrNum OBJECT-TYPE
          SYNTAX      OCTET STRING(SIZE(0..64))
          MAX-ACCESS  read-write
          STATUS      current
          DESCRIPTION
              "
              Indicates the CfnrNum of SipPstnUser.
              "
          ::= { hwPstnCTPRightConfigEntry 23 }

        hwPstnCTPRightCfuNum OBJECT-TYPE
          SYNTAX      OCTET STRING(SIZE(0..64))
          MAX-ACCESS  read-write
          STATUS      current
          DESCRIPTION
              "
              Indicates the CfuNum of SipPstnUser.
              "
          ::= { hwPstnCTPRightConfigEntry 24 }

        hwPstnCTPRightCfnrTime OBJECT-TYPE
          SYNTAX      Integer32(0..65535)
          MAX-ACCESS  read-write
          STATUS      current
          DESCRIPTION
              "
              Indicates the CfnrTime of SipPstnUser.
              Unit: second
              "
              DEFVAL  {100}
          ::= { hwPstnCTPRightConfigEntry 25 }

        hwPstnCTPRightAnonymousCall OBJECT-TYPE
          SYNTAX      INTEGER{disable(1),enable(2)}
          MAX-ACCESS  read-write
          STATUS      current
          DESCRIPTION
              "
              Indicates the right flag of anonymous-call.
              Options:
              1. disable(1) -disable anonymous-call
              2. enable(2)  -enable anonymous-call
              "
              DEFVAL   { disable }
          ::= { hwPstnCTPRightConfigEntry 26 }

        hwPstnCTPRightAuthName OBJECT-TYPE
          SYNTAX      OCTET STRING(SIZE(0..64))
          MAX-ACCESS  read-write
          STATUS      current
          DESCRIPTION
              "
              Indicates the authorization username of sippstnuser.
              The character set is unrestricted.
              "
          ::= { hwPstnCTPRightConfigEntry 27 }

        hwPstnCTPRightAuthPassword OBJECT-TYPE
          SYNTAX      OCTET STRING(SIZE(0..64))
          MAX-ACCESS  read-write
          STATUS      current
          DESCRIPTION
              "
              Indicates the authorization password of sippstnuser.
              The character set is unrestricted.
              "
          ::= { hwPstnCTPRightConfigEntry 28 }


        hwPstnCTPRightEndConfigIndex OBJECT-TYPE
          SYNTAX      Integer32
          MAX-ACCESS  read-write
          STATUS      current
          DESCRIPTION
              "
              Indicates the end shelf/slot/port.
              "
          ::= { hwPstnCTPRightConfigEntry 29 }

        hwPstnCTPRightAuthPasswordMode OBJECT-TYPE
          SYNTAX      INTEGER{password(1),ha1(2)}
          MAX-ACCESS  read-write
          STATUS      current
          DESCRIPTION
              "
              Indicates the authorization mode of the password for sippstnuser.
              Options:
              1. password(1) -authorized by password
              2. ha1(2) --authorized by ha1
              "
              DEFVAL   { password }
          ::= { hwPstnCTPRightConfigEntry 30 }

        hwPstnCTPRightAuthHA1  OBJECT-TYPE
          SYNTAX      OCTET STRING(SIZE(0..32))
          MAX-ACCESS  read-write
          STATUS      current
          DESCRIPTION
              "
              Indicates the authorization HA1 value of sippstnuser.
              The character set is unrestricted.
              "
          ::= { hwPstnCTPRightConfigEntry 31 }

        hwPstnCTPRightAutoReversePolarity  OBJECT-TYPE
          SYNTAX      INTEGER{disable(1),enable(2)}
          MAX-ACCESS  read-write
          STATUS      current
          DESCRIPTION
              "
              Indicates the right flag of auto reverse polarity.
              Options:
              1. disable(1) -disable
              2. enable(2) -enable
              "
              DEFVAL   { disable }
          ::= { hwPstnCTPRightConfigEntry 32 }

        hwPstnCTPRightDisplayNameMode  OBJECT-TYPE
          SYNTAX      INTEGER{disable(1),enable(2)}
          MAX-ACCESS  read-write
          STATUS      current
          DESCRIPTION
              "
              Indicates the right flag of display name mode.
              Options:
              1. disable(1) -disable
              2. enable(2) -enable
              "
              DEFVAL   { disable }
          ::= { hwPstnCTPRightConfigEntry 33 }

        hwPstnCTPRightDisplayName  OBJECT-TYPE
          SYNTAX      OCTET STRING(SIZE(0..64))
          MAX-ACCESS  read-write
          STATUS      current
          DESCRIPTION
              "
              Indicates the display name string.
              "
          ::= { hwPstnCTPRightConfigEntry 34 }

        hwPstnCTPRightHotLine OBJECT-TYPE
          SYNTAX      INTEGER{disable(1),enable(2)}
          MAX-ACCESS  read-write
          STATUS      current
          DESCRIPTION
              "
              Indicates the right flag of hotline.
              Options:
              1. disable(1) -disable
              2. enable(2) -enable
              "
              DEFVAL      { disable }
          ::= { hwPstnCTPRightConfigEntry 35 }

        hwPstnCTPRightPermanentHold OBJECT-TYPE
          SYNTAX      INTEGER{disable(1),enable(2)}
          MAX-ACCESS  read-write
          STATUS      current
          DESCRIPTION
              "
              Indicates the right flag of permanent-hold.
              Options:
              1. disable(1) -disable
              2. enable(2) -enable
              "
              DEFVAL      { disable }
          ::= { hwPstnCTPRightConfigEntry 36 }

          hwPstnCTPRightCutoffDisconnect OBJECT-TYPE
          SYNTAX      INTEGER{disable(1),enable(2)}
          MAX-ACCESS  read-write
          STATUS      current
          DESCRIPTION
              "
              Indicates the right flag of cutoff-disconnect.
              Options:
              1. disable(1) -disable
              2. enable(2) -enable
              "
              DEFVAL      { disable }
          ::= { hwPstnCTPRightConfigEntry 37 }

          hwPstnCTPRightSccClass OBJECT-TYPE
          SYNTAX      INTEGER{disable(1),enable(2)}
          MAX-ACCESS  read-write
          STATUS      current
          DESCRIPTION
              "
              Indicates the right flag of SCC class service, for example call-park,  call-pickup,  EBO.
              Options:
              1. disable(1) -disable
              2. enable(2) -enable
              "
              DEFVAL      { disable }
          ::= { hwPstnCTPRightConfigEntry 38 }

          hwPstnCTPRightPermanentHoldMode OBJECT-TYPE
          SYNTAX      INTEGER{norecall(1),  -- norecall
                              reminder(2), -- reminder
                              recall(3)    -- recall
                              }
          MAX-ACCESS  read-write
          STATUS      current
          DESCRIPTION
              "
              Indicates the PermanentHoldMode of SipPstnUser.
              Options:
              1. norecall(1) - no recall
              2. reminder(2) -reminder
              3. recall(3) -recall
              "
              DEFVAL      { norecall }
          ::= { hwPstnCTPRightConfigEntry 39 }

          hwPstnCTPRightPermanentHoldTime OBJECT-TYPE
          SYNTAX      Integer32(12..1023)
          MAX-ACCESS  read-write
          STATUS      current
          DESCRIPTION
              "
              Indicates the PermanentHoldTime of SipPstnUser.
              Unit: second
              "
              DEFVAL  {20}
          ::= { hwPstnCTPRightConfigEntry 40 }

          hwPstnCTPRightFastDisconnect OBJECT-TYPE
          SYNTAX      INTEGER{disable(1),enable(2)}
          MAX-ACCESS  read-write
          STATUS      current
          DESCRIPTION
              "
              Indicates the right flag of fast-disconnect.
              Options:
              1. disable(1) -disable
              2. enable(2) -enable
              "
              DEFVAL      { disable }
          ::= { hwPstnCTPRightConfigEntry 41 }

        hwPstnCTPRightDc OBJECT-TYPE
          SYNTAX      INTEGER{disable(1),enable(2)}
          MAX-ACCESS  read-write
          STATUS      current
          DESCRIPTION
              "
              Indicates the right flag of dual communication.
              Options:
              1. disable(1) -disable
              2. enable(2) -enable
              "
              DEFVAL      { enable }
          ::= { hwPstnCTPRightConfigEntry 42 }

     hwCTPExternNumberConfigTable OBJECT-TYPE
          SYNTAX      SEQUENCE OF HwCTPExternNumberConfigEntry
          MAX-ACCESS  not-accessible
          STATUS      current
          DESCRIPTION
            "
            This table is used to config extern number of the PSTN or ISDN user.
            The indexes of this table are hwCTPExternNumberConfigIndex, hwCTPExternNumberPortBindIndex.
            "
          ::= { hwIASVoiceUserObjects 14 }

        hwCTPExternNumberConfigEntry OBJECT-TYPE
          SYNTAX      HwCTPExternNumberConfigEntry
          MAX-ACCESS  not-accessible
          STATUS      current
          DESCRIPTION
            "
            This table is used to config extern number of the PSTN or ISDN user.
            The indexes of this entry are hwCTPExternNumberConfigIndex, hwCTPExternNumberPortBindIndex.
            "
          INDEX    {
                    hwCTPExternNumberConfigIndex,
                    hwCTPExternNumberPortBindIndex
                   }
          ::= { hwCTPExternNumberConfigTable 1 }

        HwCTPExternNumberConfigEntry ::=
          SEQUENCE
          {
            hwCTPExternNumberConfigIndex	    Integer32,
            hwCTPExternNumberPortBindIndex   Integer32,
            hwCTPExternNumber                OCTET STRING,
            hwCTPExternRowStatus             RowStatus,
            hwCTPExternUserGroupid		Integer32
          }

        hwCTPExternNumberConfigIndex OBJECT-TYPE
          SYNTAX      Integer32
          MAX-ACCESS  not-accessible
          STATUS      current
          DESCRIPTION
              "
              Indicates the frame/slot/port.
              31                                         0
              xxxxxxx | xxxxxxxx | xxxxxx | xxxxxxx | 0000
              port      frame      slot     port      0
              type

              The highest 7 bits indicate the type of port
              the next 8 bits indicate the frame ID,
              the next 6 bits indicate the slot ID,
              the next 7 bits indicate the port ID,
              the last 4 bits must be 0.

              The type of port include:
              E1   port = 0x16
              PSTN port = 0x18
              BRA  port = 0x19
              AT0  port = 0x1b
              "
          ::= { hwCTPExternNumberConfigEntry 1 }

        hwCTPExternNumberPortBindIndex OBJECT-TYPE
          SYNTAX      Integer32(1..65534)
          MAX-ACCESS  not-accessible
          STATUS      current
          DESCRIPTION
              "
              Indicates the extend number index.
              If the value equal -1, then return the idle index of this shelf/slot/port.
              "
          ::= { hwCTPExternNumberConfigEntry 2 }


        hwCTPExternNumber OBJECT-TYPE
          SYNTAX      OCTET STRING(SIZE(1..64))
          MAX-ACCESS  read-write
          STATUS      current
          DESCRIPTION
              "
              Indicates the extend number. - means to delete this extern number.
              "
          ::= { hwCTPExternNumberConfigEntry 3 }

        hwCTPExternRowStatus OBJECT-TYPE
          SYNTAX      RowStatus
          MAX-ACCESS  read-write
          STATUS      current
          DESCRIPTION
              "
              RowStatus
              "
          ::= { hwCTPExternNumberConfigEntry 4 }

       hwCTPExternUserGroupid OBJECT-TYPE
          SYNTAX      Integer32(-1..65535)
          MAX-ACCESS  read-write
          STATUS      current
          DESCRIPTION
              "
              It indicates the user group ID.
              -1 indicates clear the user group info.
              "
          ::= { hwCTPExternNumberConfigEntry 5 }

     hwBraCTPRightConfigTable OBJECT-TYPE
          SYNTAX      SEQUENCE OF HwBraCTPRightConfigEntry
          MAX-ACCESS  not-accessible
          STATUS      current
          DESCRIPTION
            "
            This table is used to config BRA user's right and servicedata.
            The indexes of this table are hwBraCTPRightConfigIndex, hwBraCTPRightPortBindIndex.
            "
          ::= { hwIASVoiceUserObjects 15 }

        hwBraCTPRightConfigEntry OBJECT-TYPE
          SYNTAX      HwBraCTPRightConfigEntry
          MAX-ACCESS  not-accessible
          STATUS      current
          DESCRIPTION
            "
            This table is used to config BRA user's right and servicedata.
            The indexes of this entry are hwBraCTPRightConfigIndex, hwBraCTPRightPortBindIndex.
            "
          INDEX    {
                    hwBraCTPRightConfigIndex,
                    hwBraCTPRightPortBindIndex
                   }
          ::= { hwBraCTPRightConfigTable 1 }

        HwBraCTPRightConfigEntry ::=
          SEQUENCE
          {
            hwBraCTPRightConfigIndex	Integer32,
            hwBraCTPRightPortBindIndex	Integer32,
            hwBraCTPRightAuthName OCTET STRING,
            hwBraCTPRightAuthPassword OCTET STRING,
            hwBraCTPRightEndConfigIndex Integer32,
            hwBraCTPRightAuthPasswordMode INTEGER,
            hwBraCTPRightAuthHA1  OCTET STRING,
            hwBraCTPRightCentrexNo  Unsigned32,
            hwBraCTPRightCentrexPrefix OCTET STRING,
            hwBraCTPRightCentrexFlag INTEGER,
            hwBraCTPRightMwiMode INTEGER,
            hwBraCTPRightCallHold	INTEGER,
            hwBraCTPRightThreeParty	INTEGER,
            hwBraCTPRightConf	INTEGER,
            hwBraCTPRightCt 	INTEGER,
            hwBraCTPRightCw 	INTEGER,
            hwBraCTPRightMcid       INTEGER,
            hwBraCTPRightMwi        INTEGER,
            hwBraCTPRightCliWildcardLen        Integer32
          }

        hwBraCTPRightConfigIndex OBJECT-TYPE
          SYNTAX      Integer32
          MAX-ACCESS  not-accessible
          STATUS      current
          DESCRIPTION
              "
              Indicates the frame/slot/port.
              31                                         0
              0011001 | xxxxxxxx | xxxxxx | xxxxxxx | 0000
              port      frame      slot     port      0
              type

              The highest 7 bits indicate the type of port, for BRA port, must be 0x19
              the next 8 bits indicate the frame ID,
              the next 6 bits indicate the slot ID,
              the next 7 bits indicate the port ID,
              the last 4 bits must be 0.

              The type of port include:
              E1   port = 0x16
              PSTN port = 0x18
              BRA  port = 0x19
              AT0  port = 0x1b
              "
          ::= { hwBraCTPRightConfigEntry 1 }

        hwBraCTPRightPortBindIndex OBJECT-TYPE
          SYNTAX      Integer32(0..65535)
          MAX-ACCESS  not-accessible
          STATUS      current
          DESCRIPTION
              "
              Indicates the telephone number index.
              "
          ::= { hwBraCTPRightConfigEntry 2 }

        hwBraCTPRightAuthName OBJECT-TYPE
          SYNTAX      OCTET STRING(SIZE(0..64))
          MAX-ACCESS  read-write
          STATUS      current
          DESCRIPTION
              "
              Indicates the authorization username of sipbrauser.
              The character set is unrestricted.
              "
          ::= { hwBraCTPRightConfigEntry 3 }

        hwBraCTPRightAuthPassword OBJECT-TYPE
          SYNTAX      OCTET STRING(SIZE(0..64))
          MAX-ACCESS  read-write
          STATUS      current
          DESCRIPTION
              "
              Indicates the authorization password of sipbrauser.
              The character set is unrestricted.
              "
          ::= { hwBraCTPRightConfigEntry 4 }

        hwBraCTPRightEndConfigIndex OBJECT-TYPE
          SYNTAX      Integer32
          MAX-ACCESS  read-write
          STATUS      current
          DESCRIPTION
              "
              Indicates the end shelf/slot/port.
              "
          ::= { hwBraCTPRightConfigEntry 5 }

        hwBraCTPRightAuthPasswordMode OBJECT-TYPE
          SYNTAX      INTEGER{password(1),ha1(2)}
          MAX-ACCESS  read-write
          STATUS      current
          DESCRIPTION
              "
              Indicates the authorization mode of the password for sipbrauser.
              Options:
              1. password(1) -authorized by password
              2. ha1(2) -authorized by ha1
              "
              DEFVAL   { password }
          ::= { hwBraCTPRightConfigEntry 6 }

        hwBraCTPRightAuthHA1  OBJECT-TYPE
          SYNTAX      OCTET STRING(SIZE(0..32))
          MAX-ACCESS  read-write
          STATUS      current
          DESCRIPTION
              "
              Indicates the authorization HA1 value of sipbrauser.
              The character set is unrestricted.
              "
          ::= { hwBraCTPRightConfigEntry 7 }

     hwBraCTPRightCentrexNo OBJECT-TYPE
          SYNTAX      Unsigned32(0..4294967295)
          MAX-ACCESS  read-write
          STATUS      current
          DESCRIPTION
              "
              It is used to set centrex NO. of SipBraUser, 4294967295 means to clear the configuration.
              "
              DEFVAL      { 4294967295 }
          ::= { hwBraCTPRightConfigEntry 8 }

        hwBraCTPRightCentrexPrefix OBJECT-TYPE
          SYNTAX      OCTET STRING(SIZE(0..7))
          MAX-ACCESS  read-write
          STATUS      current
          DESCRIPTION
              "
              Indicates the CentrexPrefix of SipBraUser.
              "
          ::= { hwBraCTPRightConfigEntry 9 }

        hwBraCTPRightCentrexFlag OBJECT-TYPE
          SYNTAX      INTEGER{dialDirectly(1), -- dial directly
                              dialSecondary(2) -- dial secondary
                              }
          MAX-ACCESS  read-write
          STATUS      current
          DESCRIPTION
              "
              Indicates the CentrexFlag of SipBraUser.
              Options:
              1. dialDirectly(1) -dial directly
              2. dialSecondary(2) -dial secondary
              "
              DEFVAL      { dialdirectly }
          ::= { hwBraCTPRightConfigEntry 10 }

        hwBraCTPRightMwiMode OBJECT-TYPE
          SYNTAX      INTEGER{deferred(1),  -- deferred
                              immediate(2), -- immediate
                              combine(3)    -- combine
                              }
          MAX-ACCESS  read-write
          STATUS      current
          DESCRIPTION
              "
              Indicates the MwiMode of SipBraUser.
              Options:
              1. deferred(1) -deferred
              2. immediate(2) -immediate
              3. combine(3) -combine
              "
              DEFVAL      { deferred }
          ::= { hwBraCTPRightConfigEntry 11 }

        hwBraCTPRightCallHold OBJECT-TYPE
          SYNTAX      INTEGER{disable(1),enable(2)}
          MAX-ACCESS  read-write
          STATUS      current
          DESCRIPTION
              "
              Indicates the right flag of callhold.
              Options:
              1. disable(1) -disable
              2. enable(2) -enable
              "
              DEFVAL      { enable }
          ::= { hwBraCTPRightConfigEntry 12 }

        hwBraCTPRightThreeParty OBJECT-TYPE
          SYNTAX      INTEGER{disable(1),enable(2)}
          MAX-ACCESS  read-write
          STATUS      current
          DESCRIPTION
              "
              Indicates the right flag of three-party.
              Options:
              1. disable(1) -disable
              2. enable(2) -enable
              "
              DEFVAL      { enable }
          ::= { hwBraCTPRightConfigEntry 13 }

        hwBraCTPRightConf OBJECT-TYPE
          SYNTAX      INTEGER{disable(1),enable(2)}
          MAX-ACCESS  read-write
          STATUS      current
          DESCRIPTION
              "
              Indicates the right flag of conf.
              Options:
              1. disable(1) -disable
              2. enable(2) -enable
              "
              DEFVAL      { enable }
          ::= { hwBraCTPRightConfigEntry 14 }

        hwBraCTPRightCt OBJECT-TYPE
          SYNTAX      INTEGER{disable(1),enable(2)}
          MAX-ACCESS  read-write
          STATUS      current
          DESCRIPTION
              "
              Indicates the right flag of ct.
              Options:
              1. disable(1) -disable
              2. enable(2) -enable
              "
              DEFVAL      { enable }
          ::= { hwBraCTPRightConfigEntry 15 }

        hwBraCTPRightCw OBJECT-TYPE
          SYNTAX      INTEGER{disable(1),enable(2)}
          MAX-ACCESS  read-write
          STATUS      current
          DESCRIPTION
              "
              Indicates the right flag of cw.
              Options:
              1. disable(1) -disable
              2. enable(2) -enable
              "
              DEFVAL      { disable }
          ::= { hwBraCTPRightConfigEntry 16 }

        hwBraCTPRightMcid OBJECT-TYPE
          SYNTAX      INTEGER{disable(1),enable(2)}
          MAX-ACCESS  read-write
          STATUS      current
          DESCRIPTION
              "
              Indicates the right flag of mcid.
              Options:
              1. disable(1) -disable
              2. enable(2) -enable
              "
              DEFVAL      { disable }
          ::= { hwBraCTPRightConfigEntry 17 }

        hwBraCTPRightMwi OBJECT-TYPE
          SYNTAX      INTEGER{disable(1),enable(2)}
          MAX-ACCESS  read-write
          STATUS      current
          DESCRIPTION
              "
              Indicates the right flag of mwi.
              Options:
              1. disable(1) -disable
              2. enable(2) -enable
              "
              DEFVAL      { disable }
          ::= { hwBraCTPRightConfigEntry 18 }

        hwBraCTPRightCliWildcardLen OBJECT-TYPE
          SYNTAX      Integer32(0..64|255)
          MAX-ACCESS  read-write
          STATUS      current
          DESCRIPTION
              "
              Indicates the wildcard length of CLI number. 255 means to clear the configuration.
              "
              DEFVAL      { 255 }
          ::= { hwBraCTPRightConfigEntry 19 }

     hwPraCTPRightConfigTable OBJECT-TYPE
          SYNTAX      SEQUENCE OF HwPraCTPRightConfigEntry
          MAX-ACCESS  not-accessible
          STATUS      current
          DESCRIPTION
            "
            This table is used to config PRA user's servicedata.
            The indexes of this table are hwPraCTPRightConfigIndex, hwPraCTPRightPortBindIndex.
            "
          ::= { hwIASVoiceUserObjects 16 }

        hwPraCTPRightConfigEntry OBJECT-TYPE
          SYNTAX      HwPraCTPRightConfigEntry
          MAX-ACCESS  not-accessible
          STATUS      current
          DESCRIPTION
            "
            This table is used to config PRA user's servicedata.
            The indexes of this entry are hwPraCTPRightConfigIndex, hwPraCTPRightPortBindIndex.
            "
          INDEX    {
                    hwPraCTPRightConfigIndex,
                    hwPraCTPRightPortBindIndex
                   }
          ::= { hwPraCTPRightConfigTable 1 }

        HwPraCTPRightConfigEntry ::=
          SEQUENCE
          {
            hwPraCTPRightConfigIndex	Integer32,
            hwPraCTPRightPortBindIndex	Integer32,
            hwPraCTPRightAuthName OCTET STRING,
            hwPraCTPRightAuthPassword OCTET STRING,
            hwPraCTPRightEndConfigIndex Integer32,
            hwPraCTPRightAuthPasswordMode INTEGER,
            hwPraCTPRightAuthHA1  OCTET STRING,
            hwPraCTPRightCentrexNo  Unsigned32,
            hwPraCTPRightCentrexPrefix OCTET STRING,
            hwPraCTPRightCentrexFlag INTEGER,
            hwPraCTPRightMwiMode INTEGER,
            hwPraCTPRightCliWildcardLen Integer32
          }

        hwPraCTPRightConfigIndex OBJECT-TYPE
          SYNTAX      Integer32
          MAX-ACCESS  not-accessible
          STATUS      current
          DESCRIPTION
              "
              Indicates the frame/slot/port.
              31                                         0
              0010110 | xxxxxxxx | xxxxxx | xxxxxxx | 0000
              port      frame      slot     port      0
              type

              The highest 7 bits indicate the type of port, for E1 port, must be 0x16
              the next 8 bits indicate the frame ID,
              the next 6 bits indicate the slot ID,
              the next 7 bits indicate the port ID,
              the last 4 bits must be 0.

              The type of port include:
              E1   port = 0x16
              PSTN port = 0x18
              BRA  port = 0x19
              AT0  port = 0x1b
              "
          ::= { hwPraCTPRightConfigEntry 1 }

        hwPraCTPRightPortBindIndex OBJECT-TYPE
          SYNTAX      Integer32(0..65535)
          MAX-ACCESS  not-accessible
          STATUS      current
          DESCRIPTION
              "
              Indicates the telephone number index.
              "
          ::= { hwPraCTPRightConfigEntry 2 }

        hwPraCTPRightAuthName OBJECT-TYPE
          SYNTAX      OCTET STRING(SIZE(0..64))
          MAX-ACCESS  read-write
          STATUS      current
          DESCRIPTION
              "
              Indicates the authorization username of sipprauser.
              The character set is unrestricted.
              "
          ::= { hwPraCTPRightConfigEntry 3 }

        hwPraCTPRightAuthPassword OBJECT-TYPE
          SYNTAX      OCTET STRING(SIZE(0..64))
          MAX-ACCESS  read-write
          STATUS      current
          DESCRIPTION
              "
              Indicates the authorization password of sipprauser.
              The character set is unrestricted.
              "
          ::= { hwPraCTPRightConfigEntry 4 }

        hwPraCTPRightEndConfigIndex OBJECT-TYPE
          SYNTAX      Integer32
          MAX-ACCESS  read-write
          STATUS      current
          DESCRIPTION
              "
              Indicates the end shelf/slot/port.
              "
          ::= { hwPraCTPRightConfigEntry 5 }

        hwPraCTPRightAuthPasswordMode OBJECT-TYPE
          SYNTAX      INTEGER{password(1),ha1(2)}
          MAX-ACCESS  read-write
          STATUS      current
          DESCRIPTION
              "
              Indicates the authorization mode of the password for sipprauser.
              Options:
              1. password(1) -authorized by password
              2. ha1(2) -authorized by ha1
              "
              DEFVAL   { password }
          ::= { hwPraCTPRightConfigEntry 6 }

        hwPraCTPRightAuthHA1  OBJECT-TYPE
          SYNTAX      OCTET STRING(SIZE(0..32))
          MAX-ACCESS  read-write
          STATUS      current
          DESCRIPTION
              "
              Indicates the authorization HA1 value of sipprauser.
              The character set is unrestricted.
              "
          ::= { hwPraCTPRightConfigEntry 7 }

          hwPraCTPRightCentrexNo OBJECT-TYPE
          SYNTAX      Unsigned32(0..4294967295)
          MAX-ACCESS  read-write
          STATUS      current
          DESCRIPTION
              "
              It is used to set centrex NO. of SipPraUser, 4294967295 means to clear the configuration.
              "
              DEFVAL      { 4294967295 }
          ::= { hwPraCTPRightConfigEntry 8 }

        hwPraCTPRightCentrexPrefix OBJECT-TYPE
          SYNTAX      OCTET STRING(SIZE(0..7))
          MAX-ACCESS  read-write
          STATUS      current
          DESCRIPTION
              "
              Indicates the CentrexPrefix of SipPraUser.
              "
          ::= { hwPraCTPRightConfigEntry 9 }

        hwPraCTPRightCentrexFlag OBJECT-TYPE
          SYNTAX      INTEGER{dialDirectly(1), -- dial directly
                              dialSecondary(2) -- dial secondary
                              }
          MAX-ACCESS  read-write
          STATUS      current
          DESCRIPTION
              "
              Indicates the CentrexFlag of SipPraUser.
              Options:
              1. dialDirectly(1) -dial directly
              2. dialSecondary(2) -dial secondary
              "
              DEFVAL      { dialdirectly }
          ::= { hwPraCTPRightConfigEntry 10 }

          hwPraCTPRightMwiMode OBJECT-TYPE
          SYNTAX      INTEGER{deferred(1),  -- deferred
                              immediate(2), -- immediate
                              combine(3)    -- combine
                              }
          MAX-ACCESS  read-write
          STATUS      current
          DESCRIPTION
              "
              Indicates the MwiMode of SipPraUser.
              Options:
              1. deferred(1) -deferred
              2. immediate(2) -immediate
              3. combine(3) -combine
              "
              DEFVAL      { deferred }
          ::= { hwPraCTPRightConfigEntry 11 }

          hwPraCTPRightCliWildcardLen OBJECT-TYPE
          SYNTAX      Integer32(0..64|255)
          MAX-ACCESS  read-write
          STATUS      current
          DESCRIPTION
              "
              Indicates the wildcard length of CLI number. 255 means to clear the configuration.
              "
              DEFVAL      { 255 }
          ::= { hwPraCTPRightConfigEntry 12 }

        hwR2CTPConfigTable OBJECT-TYPE
         SYNTAX      SEQUENCE OF HwR2CTPConfigEntry
         MAX-ACCESS  not-accessible
         STATUS      current
         DESCRIPTION
           "
           It is used to configure the service attributes of a R2 port. It is used to add, delete, modify, and query the R2 user with the VSP feature.
           The index of this table is the hwR2CTPConfigIndex.
           The attributes of a R2 user with the VoIP feature include the gateway ID, terminal ID, R2 profile index. Through the table, you can configure, modify, and query the above-mentioned attributes of the R2 user.
           "
         ::= { hwIASVoiceUserObjects 17 }

       hwR2CTPConfigEntry OBJECT-TYPE
         SYNTAX      HwR2CTPConfigEntry
         MAX-ACCESS  not-accessible
         STATUS      current
         DESCRIPTION
           "
           It is used to configure the service attributes of a R2 port. It is used to add, delete, modify, and query the R2 user with the VSP feature.
           The index of this entry is the hwR2CTPConfigIndex.
           The attributes of a R2 user with the VoIP feature include the gateway ID, terminal ID, R2 profile index. Through the table, you can configure, modify, and query the above-mentioned attributes of the R2 user.
           "
         INDEX    {
                   hwR2CTPConfigIndex
                  }
         ::= { hwR2CTPConfigTable 1 }

       HwR2CTPConfigEntry ::=
         SEQUENCE
         {
           hwR2CTPConfigIndex		Integer32,
           hwR2CTPMgId		Integer32,
           hwR2CTPTerminationID	OCTET STRING,
           hwR2CTPSignalProfileIndex Integer32,
           hwR2CTPSignalProfileName OCTET STRING,
           hwR2CTPRowStatus	RowStatus,
           hwR2CTPPriorityFlag   INTEGER,
           hwR2CTPTelNo   OCTET STRING,
           hwR2CTPUserGroupid  Integer32,
           hwR2CTPDigitMapGroupName OCTET STRING,
           hwR2CTPRemoteRingFlag INTEGER,
           hwR2CTPConfigIncomingcallChangeName OCTET STRING,
           hwR2CTPConfigOutgoingcallChangeName OCTET STRING
         }

       hwR2CTPConfigIndex OBJECT-TYPE
         SYNTAX      Integer32
         MAX-ACCESS  not-accessible
         STATUS      current
         DESCRIPTION
             "
             Indicates the frame/slot/port.
              31                                         0
              0010110 | xxxxxxxx | xxxxxx | xxxxxxx | 0000
              port      frame      slot     port      0
              type

              The highest 7 bits indicate the type of port, for R2 port, must be 0x16
              the next 8 bits indicate the frame ID,
              the next 6 bits indicate the slot ID,
              the next 7 bits indicate the port ID,
              the last 4 bits must be 0.

              The type of port include:
              E1   port = 0x16
              PSTN port = 0x18
              BRA  port = 0x19
              AT0  port = 0x1b
             "
         ::= { hwR2CTPConfigEntry 1 }

       hwR2CTPMgId OBJECT-TYPE
         SYNTAX      Integer32(0..16777215)
         MAX-ACCESS  read-create
         STATUS      current
         DESCRIPTION
             "
             Indicates the MG ID.
             "
         ::= { hwR2CTPConfigEntry 2 }

       hwR2CTPTerminationID OBJECT-TYPE
         SYNTAX      OCTET STRING(SIZE(0..64))
         MAX-ACCESS  read-create
         STATUS      current
         DESCRIPTION
             "
             Indicates the start terminal ID (only the character string of digit type is supported).
             "
         ::= { hwR2CTPConfigEntry 3 }

       hwR2CTPSignalProfileIndex OBJECT-TYPE
         SYNTAX      Integer32(0..15)
         MAX-ACCESS  read-write
         STATUS      current
         DESCRIPTION
             "
             Indicates the R2 signal profile index.
             "
         ::= { hwR2CTPConfigEntry 4 }

       hwR2CTPSignalProfileName OBJECT-TYPE
         SYNTAX      OCTET STRING(SIZE(0..32))
         MAX-ACCESS  read-only
         STATUS      current
         DESCRIPTION
             "
             Indicates the R2 signal profile name.
             "
         ::= { hwR2CTPConfigEntry 5 }

       hwR2CTPRowStatus OBJECT-TYPE
         SYNTAX      RowStatus
         MAX-ACCESS  read-write
         STATUS      current
         DESCRIPTION
             "
             Indicates the row status.
             "
         ::= { hwR2CTPConfigEntry 6 }

      hwR2CTPPriorityFlag OBJECT-TYPE
          SYNTAX      INTEGER{cat1(1), -- the highest priority
                              cat2(2), -- the middle priority
                              cat3(3)  -- the lowest priority
                              }
          MAX-ACCESS  read-write
          STATUS      current
          DESCRIPTION
              "
              Indicates terminal priority.
              Options:
              1. cat1(1) -the highest priority
              2. cat2(2) -the middle priority
              3. cat3(3) -the lowest priority
              "
              DEFVAL      { cat3 }
          ::= { hwR2CTPConfigEntry 7}

      hwR2CTPTelNo OBJECT-TYPE
         SYNTAX      OCTET STRING(SIZE(0..64))
         MAX-ACCESS  read-create
         STATUS      current
         DESCRIPTION
             "
             Indicates telphone number.
             "
         ::= { hwR2CTPConfigEntry 8 }

      hwR2CTPUserGroupid OBJECT-TYPE
          SYNTAX      Integer32(-1..65535)
          MAX-ACCESS  read-write
          STATUS      current
          DESCRIPTION
              "
              It indicates the user group ID.
              -1 indicates clear the user group info.
              "
          ::= { hwR2CTPConfigEntry 9 }

      hwR2CTPDigitMapGroupName OBJECT-TYPE
          SYNTAX      OCTET STRING(SIZE(0..32))
          MAX-ACCESS  read-write
          STATUS      current
          DESCRIPTION
              "
              It indicates the digitmap group name.
              "
          ::= { hwR2CTPConfigEntry 10 }

      hwR2CTPRemoteRingFlag OBJECT-TYPE
          SYNTAX      INTEGER{disable(1),enable(2),null(-1)}
          MAX-ACCESS  read-write
          STATUS      current
          DESCRIPTION
              "
              Indicates RemoteRing.
              Options:
              1. disable(1) -disable receive remote early media
              2. enable(2) -enable receive remote early media
              3. null(-1) -invalid value
              "
              DEFVAL      { disable }
          ::= { hwR2CTPConfigEntry 11}

      hwR2CTPConfigIncomingcallChangeName OBJECT-TYPE
          SYNTAX      OCTET STRING(SIZE(0..32))
          MAX-ACCESS  read-write
          STATUS      current
          DESCRIPTION
              "
              It indicates the number change name of incoming call.
              "
          ::= { hwR2CTPConfigEntry 12 }

     hwR2CTPConfigOutgoingcallChangeName OBJECT-TYPE
          SYNTAX      OCTET STRING(SIZE(0..32))
          MAX-ACCESS  read-write
          STATUS      current
          DESCRIPTION
              "
              It indicates the number change name of outgoing call.
              "
          ::= { hwR2CTPConfigEntry 13 }


        hwR2CTPOperTable OBJECT-TYPE
         SYNTAX      SEQUENCE OF HwR2CTPOperEntry
         MAX-ACCESS  not-accessible
         STATUS      current
         DESCRIPTION
           "
           It is used to perform operations on service attributes of a R2 user port. Through this table, you can perform maintenance operations on a R2 user with the VSP feature.
           The index of this table is hwR2CTPOperIndex.
           Through this table, you can query the running status of 32 B channels of the R2 service, and management status of 32 B channels of the R2 service.
           Through the table, services on the R2 port can be terminated, started, and the service status can be queried.
           "
         ::= { hwIASVoiceUserObjects 18 }

       hwR2CTPOperEntry OBJECT-TYPE
         SYNTAX      HwR2CTPOperEntry
         MAX-ACCESS  not-accessible
         STATUS      current
         DESCRIPTION
           "
            It is used to perform operations on service attributes of a R2 user port. Through this table, you can perform maintenance operations on a R2 user with the VSP feature.
           The index of this entry is hwR2CTPOperIndex.
           Through this table, you can query the running status of 32 B channels of the R2 service, and management status of 32 B channels of the R2 service.
           Through the table, services on the R2 port can be terminated, started, and the service status can be queried.
           "
         INDEX    {
                   hwR2CTPOperIndex
                  }
         ::= { hwR2CTPOperTable 1 }

       HwR2CTPOperEntry ::=
         SEQUENCE
         {
           hwR2CTPOperIndex	      Integer32,
           hwR2CTPBchnSrvState    OCTET STRING,
           hwR2CTPBchnAdminState  OCTET STRING,
           hwR2CTPAdminOper	      INTEGER,
           hwR2CTPMaxCobTime      Integer32,
           hwR2CTPOnexpire        INTEGER
         }

       hwR2CTPOperIndex OBJECT-TYPE
         SYNTAX      Integer32
         MAX-ACCESS  not-accessible
         STATUS      current
         DESCRIPTION
             "
             Indicates the frame/slot/port.
              31                                         0
              0010110 | xxxxxxxx | xxxxxx | xxxxxxx | 0000
              port      frame      slot     port      0
              type

              The highest 7 bits indicate the type of port, for R2 port, must be 0x16
              the next 8 bits indicate the frame ID,
              the next 6 bits indicate the slot ID,
              the next 7 bits indicate the port ID,
              the last 4 bits must be 0.

              The type of port include:
              E1   port = 0x16
              PSTN port = 0x18
              BRA  port = 0x19
              AT0  port = 0x1b
             "
         ::= { hwR2CTPOperEntry 1 }

       hwR2CTPBchnSrvState OBJECT-TYPE
         SYNTAX      OCTET STRING(SIZE (0..32))
         MAX-ACCESS  read-only
         STATUS      current
         DESCRIPTION
             "
             Indicates the running status of the service layer of the 32 B channels of the R2. Each character corresponds to a timeslot. The value of the character is as follows: 1-Idle; 2-Busy; 3-Faulty; 4-Unavailable.
             "
         ::= { hwR2CTPOperEntry 2 }

       hwR2CTPBchnAdminState OBJECT-TYPE
         SYNTAX      OCTET STRING(SIZE (0..32))
         MAX-ACCESS  read-only
         STATUS      current
         DESCRIPTION
             "
             Indicates the administration status of the service layer of the 32 B channels of the R2. Each character corresponds to a timeslot. The value of the character is as follows:
             1-blocked-locally; 2-blocked-remotely; 3-in-service;4-shutting-down;5-MGCblock;6-PBXblock;7-bothblock.
             "
         ::= { hwR2CTPOperEntry 3 }

        hwR2CTPAdminOper OBJECT-TYPE
          SYNTAX      INTEGER{endService(1),         -- stop service
                              startService(2),       -- start service
                              deferEndingService(3) -- stop service gracefully
                              }
          MAX-ACCESS  read-write
          STATUS      current
          DESCRIPTION
              "
              Indicates the service operation.
              Options:
              1. endService(1) -stop service
              2. startService(2) -start service
              3. deferEndingService(3) -stop service gracefully
              "
          ::= { hwR2CTPOperEntry 4 }

       hwR2CTPMaxCobTime OBJECT-TYPE
         SYNTAX      Integer32(0..1440)
         MAX-ACCESS  read-write
         STATUS      current
         DESCRIPTION
             "
             Indicates length of waiting timer for R2 user defer end service.
             0 is not allowed to set.
             Default: 240
             Unit: minute
             "
         ::= { hwR2CTPOperEntry 5 }

       hwR2CTPOnexpire OBJECT-TYPE
         SYNTAX      INTEGER{force(1),cancel(2)}
         MAX-ACCESS  read-write
         STATUS      current
         DESCRIPTION
             "
             Indicates disposal mode when R2 user defer end service timeout.
             Options:
             1. force(1)  -force end service
             2. cancel(2) -cancel end service
             Default: force(1)
             "
         ::= { hwR2CTPOperEntry 6 }

     hwR2CTPRightConfigTable OBJECT-TYPE
          SYNTAX      SEQUENCE OF HwR2CTPRightConfigEntry
          MAX-ACCESS  not-accessible
          STATUS      current
          DESCRIPTION
            "
            This table is used to config R2 user's right.
            The indexes of this table are hwR2CTPRightConfigIndex, hwR2CTPRightPortBindIndex.
            "
          ::= { hwIASVoiceUserObjects 19 }

        hwR2CTPRightConfigEntry OBJECT-TYPE
          SYNTAX      HwR2CTPRightConfigEntry
          MAX-ACCESS  not-accessible
          STATUS      current
          DESCRIPTION
            "
            This table is used to config R2 user's right.
            The indexes of this entry are hwR2CTPRightConfigIndex, hwR2CTPRightPortBindIndex.
            "
          INDEX    {
                    hwR2CTPRightConfigIndex,
                    hwR2CTPRightPortBindIndex
                   }
          ::= { hwR2CTPRightConfigTable 1 }

        HwR2CTPRightConfigEntry ::=
          SEQUENCE
          {
            hwR2CTPRightConfigIndex	Integer32,
            hwR2CTPRightPortBindIndex	Integer32,
            hwR2CTPRightAuthName OCTET STRING,
            hwR2CTPRightAuthPassword OCTET STRING,
            hwR2CTPRightAuthPasswordMode INTEGER,
            hwR2CTPRightAuthHA1  OCTET STRING
          }

        hwR2CTPRightConfigIndex OBJECT-TYPE
          SYNTAX      Integer32
          MAX-ACCESS  not-accessible
          STATUS      current
          DESCRIPTION
              "
              Indicates the frame/slot/port.
              31                                         0
              0011000 | xxxxxxxx | xxxxxx | xxxxxxx | 0000
              port      frame      slot     port      0
              type

              The highest 7 bits indicate the type of port, for PSTN port, must be 0x18
              the next 8 bits indicate the frame ID,
              the next 6 bits indicate the slot ID,
              the next 7 bits indicate the port ID,
              the last 4 bits must be 0.

              The type of port include:
              E1   port = 0x16
              PSTN port = 0x18
              BRA  port = 0x19
              AT0  port = 0x1b
              "
          ::= { hwR2CTPRightConfigEntry 1 }

        hwR2CTPRightPortBindIndex OBJECT-TYPE
          SYNTAX      Integer32(0..65535)
          MAX-ACCESS  not-accessible
          STATUS      current
          DESCRIPTION
              "
              Indicates the telephone number index.
              "
          ::= { hwR2CTPRightConfigEntry 2 }

        hwR2CTPRightAuthName OBJECT-TYPE
          SYNTAX      OCTET STRING(SIZE(0..64))
          MAX-ACCESS  read-write
          STATUS      current
          DESCRIPTION
              "
              Indicates the authorization username of sipR2user.
              The character set is unrestricted.
              "
          ::= { hwR2CTPRightConfigEntry 3 }

        hwR2CTPRightAuthPassword OBJECT-TYPE
          SYNTAX      OCTET STRING(SIZE(0..64))
          MAX-ACCESS  read-write
          STATUS      current
          DESCRIPTION
              "
              Indicates the authorization password of sipR2user.
              The character set is unrestricted.
              "
          ::= { hwR2CTPRightConfigEntry 4 }

        hwR2CTPRightAuthPasswordMode OBJECT-TYPE
          SYNTAX      INTEGER{password(1),ha1(2)}
          MAX-ACCESS  read-write
          STATUS      current
          DESCRIPTION
              "
              Indicates the authorization mode of the password for sipR2user.
              Options:
              1. password(1) -authorized by password
              2. ha1(2) -authorized by ha1
              "
              DEFVAL   { password }
          ::= { hwR2CTPRightConfigEntry 5 }

        hwR2CTPRightAuthHA1  OBJECT-TYPE
          SYNTAX      OCTET STRING(SIZE(0..32))
          MAX-ACCESS  read-write
          STATUS      current
          DESCRIPTION
              "
              Indicates the authorization HA1 value of sipR2user.
              The character set is unrestricted.
              "
          ::= { hwR2CTPRightConfigEntry 6 }

 ------  /* Start hwIASVoiceUserTrapsVbOids */

        hwLightTrapPortNum OBJECT-TYPE
        SYNTAX     Integer32(0..128)
        MAX-ACCESS accessible-for-notify
        STATUS current
        DESCRIPTION
            "
   	        The number of the ports send light state trap.
            "
        ::= { hwIASVoiceUserTrapsVbOids 1 }

        hwLightTrapPortInfo OBJECT-TYPE
        SYNTAX     OCTET STRING(SIZE(0..896))
        MAX-ACCESS accessible-for-notify
        STATUS current
        DESCRIPTION
            "
            The position and state of the ports.
            "
         ::= { hwIASVoiceUserTrapsVbOids 2 }

        hwVoiceUserFrame OBJECT-TYPE
        SYNTAX     Integer32(0..255|-1)
        MAX-ACCESS accessible-for-notify
        STATUS current
        DESCRIPTION
            "
            Indicate the frame that user is configed at.
            -1 indicate invalid value.
            "
         ::= { hwIASVoiceUserTrapsVbOids 3 }

        hwVoiceUserSlot OBJECT-TYPE
        SYNTAX     Integer32(0..255|-1)
        MAX-ACCESS accessible-for-notify
        STATUS current
        DESCRIPTION
            "
            Indicate the slot that user is configed at.
            -1 indicate invalid value.
            "
         ::= { hwIASVoiceUserTrapsVbOids 4 }

        hwVoiceUserPort OBJECT-TYPE
        SYNTAX     Integer32(0..255|-1)
        MAX-ACCESS accessible-for-notify
        STATUS current
        DESCRIPTION
            "
            Indicate the port that user is configed at.
            -1 indicate invalid value.
            "
         ::= { hwIASVoiceUserTrapsVbOids 5 }

        hwVoiceUserOperateType OBJECT-TYPE
        SYNTAX     INTEGER{ user-data-add(1), user-data-delete(2), user-data-modify(3) }
        MAX-ACCESS accessible-for-notify
        STATUS current
        DESCRIPTION
            "
            Indicate the port that user operate type.
            Options:
            1. user-data-add(1) -add user data
            2. user-data-delete(2) -delete user data
            3. user-data-modify(3) -modify user data
            "
         ::= { hwIASVoiceUserTrapsVbOids 6 }

        hwVoiceUserPortNum OBJECT-TYPE
        SYNTAX     Integer32(1..12)
        MAX-ACCESS accessible-for-notify
        STATUS current
        DESCRIPTION
            "
   	        The number of the ports send by user config change trap.
            "
        ::= { hwIASVoiceUserTrapsVbOids 7 }

        hwVoiceUserTsn OBJECT-TYPE
        SYNTAX     Integer32(0..31)
        MAX-ACCESS accessible-for-notify
        STATUS current
        DESCRIPTION
            "
   	        Indicate the time slot ID that user is configed at.
                -1 indicate invalid value.
            "
        ::= { hwIASVoiceUserTrapsVbOids 8 }

 ------  /*  End  hwIASVoiceUserTrapsVbOids */

 ------  /* Start hwIASVoiceUserPortTraps */

        hwIASVoiceUserPortLightTrap NOTIFICATION-TYPE
        OBJECTS { hwLightTrapPortNum, hwLightTrapPortInfo }
        STATUS current
        DESCRIPTION
            "
            This notification indicates that reset result of the SIP media gateway.
            "
        ::= { hwIASVoiceUserPortTraps 0 1 }

        hwIASVoiceUserPortPstnDataChangeTrap NOTIFICATION-TYPE
        OBJECTS { hwConfigChangeIP, hwVoiceUserOperateType, hwVoiceUserPortNum,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort }
        STATUS current
        DESCRIPTION
            "
            This notification indicates that data of pstn user have been changed.
            "
        ::= { hwIASVoiceUserPortTraps 0 2 }

        hwIASVoiceUserPortBraDataChangeTrap NOTIFICATION-TYPE
        OBJECTS { hwConfigChangeIP, hwVoiceUserOperateType, hwVoiceUserPortNum,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort }
        STATUS current
        DESCRIPTION
            "
            This notification indicates that data of bra user have been changed.
            "
        ::= { hwIASVoiceUserPortTraps 0 3 }

        hwIASVoiceUserPortPraDataChangeTrap NOTIFICATION-TYPE
        OBJECTS { hwConfigChangeIP, hwVoiceUserOperateType, hwVoiceUserPortNum,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort }
        STATUS current
        DESCRIPTION
            "
            This notification indicates that data of pra user have been changed.
            "
        ::= { hwIASVoiceUserPortTraps 0 4 }

        hwIASVoiceUserPortPmbsDataChangeTrap NOTIFICATION-TYPE
        OBJECTS { hwConfigChangeIP, hwVoiceUserOperateType, hwVoiceUserPortNum,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort }
        STATUS current
        DESCRIPTION
            "
            This notification indicates that data of pmbs user have been changed.
            "
        ::= { hwIASVoiceUserPortTraps 0 5 }

        hwIASVoiceUserPortR2DataChangeTrap NOTIFICATION-TYPE
        OBJECTS { hwConfigChangeIP, hwVoiceUserOperateType, hwVoiceUserPortNum,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort,
                  hwVoiceUserFrame, hwVoiceUserSlot, hwVoiceUserPort }
        STATUS current
        DESCRIPTION
            "
            This notification indicates that data of R2 user have been changed.
            "
        ::= { hwIASVoiceUserPortTraps 0 6 }

 ------  /*  End  hwIASVoiceUserPortTraps */

 ------  /* Start hwIASVoiceUserPortAlarmTraps */

       hwIASVoiceUserRemoteBlockTrap NOTIFICATION-TYPE
       OBJECTS  { hwVoiceUserFrame, hwVoiceUserSlot, hwVoiceUserPort }
       STATUS      current
       DESCRIPTION
           "
           This notification indicates that the user is remote blocked.
           "
       ::= { hwIASVoiceUserPortAlarmTraps 0 1 }

       hwIASVoiceUserUnblockTrap NOTIFICATION-TYPE
       OBJECTS  { hwVoiceUserFrame, hwVoiceUserSlot, hwVoiceUserPort }
       STATUS      current
       DESCRIPTION
           "
           This notification indicates that the user is unblocked.
           "
       ::= { hwIASVoiceUserPortAlarmTraps 0 2 }

       hwIASVoiceUserlockedTrap NOTIFICATION-TYPE
       OBJECTS  { hwVoiceUserFrame, hwVoiceUserSlot, hwVoiceUserPort }
       STATUS      current
       DESCRIPTION
           "
           This notification indicates that the user is locked.
           "
       ::= { hwIASVoiceUserPortAlarmTraps 0 3 }

       hwIASVoiceUserUnlockedTrap NOTIFICATION-TYPE
       OBJECTS  { hwVoiceUserFrame, hwVoiceUserSlot, hwVoiceUserPort }
       STATUS      current
       DESCRIPTION
           "
           This notification indicates that the user is unlocked.
           "
       ::= { hwIASVoiceUserPortAlarmTraps 0 4 }

 ------  /*  End  hwIASVoiceUserPortAlarmTraps */

 ------  /* Start hwIASVoiceUserTsnAlarmTraps */

       hwIASVoiceUserTsnBlockTrap NOTIFICATION-TYPE
       OBJECTS  { hwVoiceUserFrame, hwVoiceUserSlot, hwVoiceUserPort,hwVoiceUserTsn }
       STATUS      current
       DESCRIPTION
           "
           This notification indicates that the user time slot is blocked.
           "
       ::= { hwIASVoiceUserTsnAlarmTraps 0 1 }

       hwIASVoiceUserTsnUnBlockTrap NOTIFICATION-TYPE
       OBJECTS  { hwVoiceUserFrame, hwVoiceUserSlot, hwVoiceUserPort,hwVoiceUserTsn  }
       STATUS      current
       DESCRIPTION
           "
           This notification indicates that the user time slot is unblocked.
           "
       ::= { hwIASVoiceUserTsnAlarmTraps 0 2 }

 ------  /*  End  hwIASVoiceUserTsnAlarmTraps */

END
