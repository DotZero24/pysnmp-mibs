--
-- HUAWEI-ISOLATE-MIB.my
-- MIB generated by MG-SOFT Visual MIB Builder Version 4.0 Build 347
-- Friday, May 09, 2014 at 11:36:06
--

--  HUAWEI-ISOLATE-MIB.mib
-- MIB generated by MG-SOFT Visual MIB Builder Version 4.0 Build 347
-- Tuesday, May 06, 2014 at 19:22:32
--
--  HUAWEI-ISOLATE-MIB.my
-- MIB generated by MG-SOFT Visual MIB Builder Version 4.0 Build 347
-- Friday, March 14, 2014 at 10:11:33
--
--  HUAWEI-ISOLATE-MIB.my
-- MIB generated by MG-SOFT Visual MIB Builder Version 4.0 Build 347
-- Thursday, March 13, 2014 at 09:22:17
--
--  HUAWEI-ISOLATE-MIB.my
-- MIB generated by MG-SOFT Visual MIB Builder Version 4.0 Build 347
-- Wednesday, March 12, 2014 at 16:03:32
--
-- ==================================================================
-- Copyright (C) 2014 by  HUAWEI TECHNOLOGIES. All rights reserved.
--
-- Description: HUAWEI Layer Two VLAN MIB
-- Reference:
-- Version: V2.00
-- History:
--                 V1.00
-- ==================================================================
-- ==================================================================
--
-- Varibles and types be imported
--
-- ==================================================================

	HUAWEI-ISOLATE-MIB DEFINITIONS ::= BEGIN

		IMPORTS
			hwDatacomm
				FROM HUAWEI-MIB
			InterfaceIndex
				FROM IF-MIB
			OBJECT-GROUP, MODULE-COMPLIANCE
				FROM SNMPv2-CONF
			Integer32, OBJECT-TYPE, MODULE-IDENTITY
				FROM SNMPv2-SMI
			RowStatus
				FROM SNMPv2-TC;


--     1.3.6.1.4.1.2011.5.25.247
-- March 12, 2014 at 15:28 GMT
-- 1.3.6.1.4.1.2011.5.25.247
-- March 12, 2014 at 15:28 GMT
-- 1.3.6.1.4.1.2011.5.25.247
-- March 12, 2014 at 15:28 GMT
-- 1.3.6.1.4.1.2011.5.25.247
-- March 12, 2014 at 15:28 GMT
		-- 1.3.6.1.4.1.2011.5.25.247
		hwIsolateMIB MODULE-IDENTITY
			LAST-UPDATED "201403121528Z"		-- March 12, 2014 at 15:28 GMT
			ORGANIZATION
				"Huawei Technologies Co.,Ltd."
			CONTACT-INFO
				"Huawei Industrial Base
				Bantian, Longgang
				 Shenzhen 518129
				 People's Republic of China
				 Website: http://www.huawei.com
				 Email: support@huawei.com"
			DESCRIPTION
				"This file is an extension of ISOLATE-MIB."
			REVISION "201403121528Z"		-- March 12, 2014 at 15:28 GMT
			DESCRIPTION
				"V2.00, modify node."

			REVISION "201008111600Z"		-- August 11, 2010 at 16:00 GMT
			DESCRIPTION
				"V1.00, initial version."
			::= { hwDatacomm 247 }




--
-- Node definitions
--

--  Node definitions
--
-- Node definitions
--
-- Node definitions
--
-- Node definitions
--
-- 1.3.6.1.4.1.2011.5.25.247.1
-- 1.3.6.1.4.1.2011.5.25.247.1
-- 1.3.6.1.4.1.2011.5.25.247.1
-- 1.3.6.1.4.1.2011.5.25.247.1
		-- 1.3.6.1.4.1.2011.5.25.247.1
		hwIsolateObjects OBJECT IDENTIFIER ::= { hwIsolateMIB 1 }


--     1.3.6.1.4.1.2011.5.25.247.1.2
-- 1.3.6.1.4.1.2011.5.25.247.1.2
-- 1.3.6.1.4.1.2011.5.25.247.1.2
-- 1.3.6.1.4.1.2011.5.25.247.1.2
		-- 1.3.6.1.4.1.2011.5.25.247.1.2
		hwIsolateTable OBJECT IDENTIFIER ::= { hwIsolateObjects 2 }


--     1.3.6.1.4.1.2011.5.25.247.1.1
-- 1.3.6.1.4.1.2011.5.25.247.1.2.1
-- 1.3.6.1.4.1.2011.5.25.247.1.2.1
-- 1.3.6.1.4.1.2011.5.25.247.1.2.1
		-- 1.3.6.1.4.1.2011.5.25.247.1.2.1
		hwPortIsolateMode OBJECT-TYPE
			SYNTAX Integer32
			MAX-ACCESS read-write
			STATUS current
			DESCRIPTION
				"Global Isolation Mode. If the HwPortIsolateMode is 1, mode is layer2. If the HwPortIsolateMode is 2, mode is all.
				By default, mode is layer2."
			::= { hwIsolateTable 1 }


--     1.3.6.1.4.1.2011.5.25.247.1.2.1
-- 1.3.6.1.4.1.2011.5.25.247.1.2.2
-- 1.3.6.1.4.1.2011.5.25.247.1.2.2
-- 1.3.6.1.4.1.2011.5.25.247.1.2.2
		-- 1.3.6.1.4.1.2011.5.25.247.1.2.2
		hwPortIsolateTable OBJECT-TYPE
			SYNTAX SEQUENCE OF HwPortIsolateEntry
			MAX-ACCESS not-accessible
			STATUS current
			DESCRIPTION
				"Port-isolation table."
			::= { hwIsolateTable 2 }


--     1.3.6.1.4.1.2011.5.25.247.1.2.1.1
-- 1.3.6.1.4.1.2011.5.25.247.1.2.2.1
-- 1.3.6.1.4.1.2011.5.25.247.1.2.2.1
-- 1.3.6.1.4.1.2011.5.25.247.1.2.2.1
		-- 1.3.6.1.4.1.2011.5.25.247.1.2.2.1
		hwPortIsolateEntry OBJECT-TYPE
			SYNTAX HwPortIsolateEntry
			MAX-ACCESS not-accessible
			STATUS current
			DESCRIPTION
				"Entries of the Port-isolation table."
			INDEX { hwPortIsolateIfIndex, hwPortIsolateGroupId }
			::= { hwPortIsolateTable 1 }


		HwPortIsolateEntry ::=
			SEQUENCE {
				hwPortIsolateGroupId
					Integer32,
				hwPortIsolateIfIndex
					InterfaceIndex,
				hwPortIsolateRowStatus
					RowStatus
			 }

--     1.3.6.1.4.1.2011.5.25.247.1.2.1.1.1
-- 1.3.6.1.4.1.2011.5.25.247.1.2.2.1.1
-- 1.3.6.1.4.1.2011.5.25.247.1.2.2.1.1
-- 1.3.6.1.4.1.2011.5.25.247.1.2.2.1.1
		-- 1.3.6.1.4.1.2011.5.25.247.1.2.2.1.1
		hwPortIsolateGroupId OBJECT-TYPE
			SYNTAX Integer32 (1..64)
			MAX-ACCESS not-accessible
			STATUS current
			DESCRIPTION
				"Port-isolation GroupId."
			::= { hwPortIsolateEntry 1 }


--     1.3.6.1.4.1.2011.5.25.247.1.2.1.1.2
-- 1.3.6.1.4.1.2011.5.25.247.1.2.2.1.2
-- 1.3.6.1.4.1.2011.5.25.247.1.2.2.1.2
-- 1.3.6.1.4.1.2011.5.25.247.1.2.2.1.2
		-- 1.3.6.1.4.1.2011.5.25.247.1.2.2.1.2
		hwPortIsolateIfIndex OBJECT-TYPE
			SYNTAX InterfaceIndex
			MAX-ACCESS not-accessible
			STATUS current
			DESCRIPTION
				"Port IfIndex."
			::= { hwPortIsolateEntry 2 }


--     1.3.6.1.4.1.2011.5.25.247.1.2.1.1.3
-- 1.3.6.1.4.1.2011.5.25.247.1.2.2.1.3
-- 1.3.6.1.4.1.2011.5.25.247.1.2.2.1.3
-- 1.3.6.1.4.1.2011.5.25.247.1.2.2.1.3
		-- 1.3.6.1.4.1.2011.5.25.247.1.2.2.1.3
		hwPortIsolateRowStatus OBJECT-TYPE
			SYNTAX RowStatus
			MAX-ACCESS read-create
			STATUS current
			DESCRIPTION
				"Operation status."
			::= { hwPortIsolateEntry 3 }


--     1.3.6.1.4.1.2011.5.25.247.1.2.2
-- 1.3.6.1.4.1.2011.5.25.247.1.2.3
-- 1.3.6.1.4.1.2011.5.25.247.1.2.3
-- 1.3.6.1.4.1.2011.5.25.247.1.2.3
		-- 1.3.6.1.4.1.2011.5.25.247.1.2.3
		hwAmIsolateTable OBJECT-TYPE
			SYNTAX SEQUENCE OF HwAmIsolateEntry
			MAX-ACCESS not-accessible
			STATUS current
			DESCRIPTION
				"Am-isolation table."
			::= { hwIsolateTable 3 }


--     1.3.6.1.4.1.2011.5.25.247.1.2.2.1
-- 1.3.6.1.4.1.2011.5.25.247.1.2.3.1
-- 1.3.6.1.4.1.2011.5.25.247.1.2.3.1
-- 1.3.6.1.4.1.2011.5.25.247.1.2.3.1
		-- 1.3.6.1.4.1.2011.5.25.247.1.2.3.1
		hwAmIsolateEntry OBJECT-TYPE
			SYNTAX HwAmIsolateEntry
			MAX-ACCESS not-accessible
			STATUS current
			DESCRIPTION
				"Entries of the Am-isolation table."
			INDEX { hwAmIsolateSrcIfIndex, hwAmIsolateDstIfIndex }
			::= { hwAmIsolateTable 1 }


		HwAmIsolateEntry ::=
			SEQUENCE {
				hwAmIsolateSrcIfIndex
					InterfaceIndex,
				hwAmIsolateDstIfIndex
					InterfaceIndex,
				hwAmIsolateRowStatus
					RowStatus
			 }

--     1.3.6.1.4.1.2011.5.25.247.1.2.2.1.1
-- 1.3.6.1.4.1.2011.5.25.247.1.2.3.1.1
-- 1.3.6.1.4.1.2011.5.25.247.1.2.3.1.1
-- 1.3.6.1.4.1.2011.5.25.247.1.2.3.1.1
		-- 1.3.6.1.4.1.2011.5.25.247.1.2.3.1.1
		hwAmIsolateSrcIfIndex OBJECT-TYPE
			SYNTAX InterfaceIndex
			MAX-ACCESS not-accessible
			STATUS current
			DESCRIPTION
				"Source port IfIndex."
			::= { hwAmIsolateEntry 1 }


--     1.3.6.1.4.1.2011.5.25.247.1.2.2.1.2
-- 1.3.6.1.4.1.2011.5.25.247.1.2.3.1.2
-- 1.3.6.1.4.1.2011.5.25.247.1.2.3.1.2
-- 1.3.6.1.4.1.2011.5.25.247.1.2.3.1.2
		-- 1.3.6.1.4.1.2011.5.25.247.1.2.3.1.2
		hwAmIsolateDstIfIndex OBJECT-TYPE
			SYNTAX InterfaceIndex
			MAX-ACCESS not-accessible
			STATUS current
			DESCRIPTION
				"Destination port IfIndex."
			::= { hwAmIsolateEntry 2 }


--     1.3.6.1.4.1.2011.5.25.247.1.2.2.1.3
-- 1.3.6.1.4.1.2011.5.25.247.1.2.3.1.3
-- 1.3.6.1.4.1.2011.5.25.247.1.2.3.1.3
-- 1.3.6.1.4.1.2011.5.25.247.1.2.3.1.3
		-- 1.3.6.1.4.1.2011.5.25.247.1.2.3.1.3
		hwAmIsolateRowStatus OBJECT-TYPE
			SYNTAX RowStatus
			MAX-ACCESS read-create
			STATUS current
			DESCRIPTION
				"Operation status."
			::= { hwAmIsolateEntry 3 }


--  1.3.6.1.4.1.2011.5.25.247.1.2.4
		-- 1.3.6.1.4.1.2011.5.25.247.1.2.4
		hwIsolateGroup OBJECT-GROUP
			OBJECTS { hwPortIsolateMode, hwPortIsolateRowStatus, hwAmIsolateRowStatus }
			STATUS current
			DESCRIPTION
				"This group is mandatory for agents which implement the Isolation."
			::= { hwIsolateTable 4 }


--  1.3.6.1.4.1.2011.5.25.247.3
-- this module
		-- 1.3.6.1.4.1.2011.5.25.247.3
		hwIsolateComformance MODULE-COMPLIANCE
			STATUS current
			DESCRIPTION
				"Isolate comformance."
			MODULE -- this module
				MANDATORY-GROUPS { hwIsolateGroup }
			::= { hwIsolateMIB 3 }



	END

--
-- HUAWEI-ISOLATE-MIB.my
--
