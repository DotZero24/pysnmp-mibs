-- ====================================================================
-- Copyright (C) 2014 by  HUAWEI TECHNOLOGIES. All rights reserved.
-- Description: Huawei Datacomm OID MIB. This MIB will maintain the MIB OID
--             for router and LAN switch only.
-- Reference:
-- Version: V1.13
-- ====================================================================

HUAWEI-DATACOMM-OID-MIB    DEFINITIONS ::= BEGIN

IMPORTS
    OBJECT-TYPE
        FROM RFC-1212
    enterprises
        FROM RFC1155-SMI
    huaweiMgmt
    	FROM HUAWEI-MIB;

     hwDatacomm MODULE-IDENTITY
        LAST-UPDATED "201406230000Z"
        ORGANIZATION "Huawei Technologies Co.,Ltd."
        CONTACT-INFO
                     "Huawei Industrial Base
                      Bantian, Longgang
                      Shenzhen 518129
                      People's Republic of China
                      Website: http://www.huawei.com
                      Email: support@huawei.com
                     "
        DESCRIPTION  "Huawei Datacomm OID MIB. This MIB will maintain the MIB OID
                      for router and LAN switch only."

         --  Revision history
	REVISION     "201406230000Z"
        DESCRIPTION  "V1.13, Modify the node name hwSystemMan to huaweiSystemManMIB to satisfy for the new OMSYS tool."

        REVISION     "201011200000Z"
        DESCRIPTION  "V1.12, corrected the errors of the MIB file."

        REVISION     "200301210000Z"
        DESCRIPTION  "V1.00, initial version."
        ::= { huaweiMgmt 25  }

--  HUAWEI datacommunication extension mib
voice                   OBJECT IDENTIFIER ::= { hwDatacomm  1 }

-- name: guoxiaojun
-- id: 29157
-- product: R2600,R1700,R3600
-- reason: new mib requirement for voice

hwVoiceGeneralMIB              OBJECT IDENTIFIER ::= { voice 1 }

hwVoiceIfMIB                   OBJECT IDENTIFIER ::= { voice 2 }

hwVoiceAnalogInterfaceMIB      OBJECT IDENTIFIER ::= { voice 3 }

hwVoiceDigitalInterfaceMIB     OBJECT IDENTIFIER ::= { voice 4 }

hwVoiceDialControlMIB          OBJECT IDENTIFIER ::= { voice 5 }

hwVoiceCallActiveMIB           OBJECT IDENTIFIER ::= { voice 6 }

hwVoiceCallHistoryMIB          OBJECT IDENTIFIER ::= { voice 7 }

hwVoiceGKClientMIB	       OBJECT IDENTIFIER ::= { voice 8 }

hwVoiceAAAClientMIB	       OBJECT IDENTIFIER ::= { voice 9 }

hwVoiceH323CallStatMIB	       OBJECT IDENTIFIER ::= { voice 11 }

-- name: guoxiaojun
-- id: 29157
-- product: R2600,R1700,R3600
-- reason: new mib requirement for voice General, voice interface, voice analog interface, voice digital interface, voice dial control, call active, call history, GK client, AAA client, H323 call sataict.

hwIPX	       OBJECT IDENTIFIER ::= { hwDatacomm  2 }

hwFWTP	       OBJECT IDENTIFIER ::= { hwDatacomm  3 }

hwHIIP	       OBJECT IDENTIFIER ::= { hwDatacomm  4 }

hwHRP	       OBJECT IDENTIFIER ::= { hwDatacomm  5 }

-- name: xuqingwei
-- id: 27902
-- product:
-- reason: new mib requirement for hwIPX, hwFWTP, hwHIIP, hwHRP.


hwASPF		OBJECT IDENTIFIER ::= { hwDatacomm  6 }

hwNAT		OBJECT IDENTIFIER ::= { hwDatacomm  7 }

hwBLS		OBJECT IDENTIFIER ::= { hwDatacomm  8 }

hwMACBIND	OBJECT IDENTIFIER ::= { hwDatacomm  9 }

hwATK	        OBJECT IDENTIFIER ::= { hwDatacomm  10 }

hwSECSTAT	OBJECT IDENTIFIER ::= { hwDatacomm  11 }

hwPFLT		OBJECT IDENTIFIER ::= { hwDatacomm  12 }

hwTRNG		OBJECT IDENTIFIER ::= { hwDatacomm  13 }

hwSMAP		OBJECT IDENTIFIER ::= { hwDatacomm  14 }

hwSZONE		OBJECT IDENTIFIER ::= { hwDatacomm  15 }

hwSLOG		OBJECT IDENTIFIER ::= { hwDatacomm  16 }

-- name: xuqingwei
-- id: 27902
-- product:
-- reason: new mib requirement for safety characteristic.

hwSSHMIB	       OBJECT IDENTIFIER ::= { hwDatacomm  17 }

-- name: guoxiaojun
-- id: 29157
-- product: R2600,R1700,R3600
-- reason: new mib requirement for SSH.

hwUserLogMIB	       OBJECT IDENTIFIER ::= { hwDatacomm  18 }

-- name: libingshan
-- id: 22055
-- product: NE05/08/08E/16/16E
-- reason: new mib requirement for user log.

huaweiSystemManMIB    OBJECT IDENTIFIER ::= { hwDatacomm  19 }

-- name: xuqingwei
-- id: 27902
-- product:
-- reason: new mib requirement for system management

hwTACACS    OBJECT IDENTIFIER ::= { hwDatacomm  20 }

-- name: limeng
-- id: 15814
-- product:
-- reason: new mib requirement for hwTACACS (to send Email)

hwNBPortalMIB	       OBJECT IDENTIFIER ::= { hwDatacomm  21 }

-- name: libingshan
-- id: 22055
-- product: NE05/08/08E/16/16E
-- reason: new mib requirement for portal of router narrowband.


END
