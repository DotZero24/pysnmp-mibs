--  ==================================================================
-- Copyright (C) 2018 by  HUAWEI TECHNOLOGIES. All rights reserved.
--
-- Description: HUAWEI-LPT-MIB provides information about LPT
-- Reference:
-- Version: V1.00
-- History:
-- <author>,   <date>,  <contents>
--  HUAWEI   2018-02-28  LPT private MIB
-- ==================================================================
-- ==================================================================
--
-- Variables and types are imported
--
-- ==================================================================

	HUAWEI-LPT-MIB DEFINITIONS ::= BEGIN

        IMPORTS
            hwDatacomm
                FROM HUAWEI-MIB
            ifIndex, ifName
                FROM IF-MIB
            DisplayString, RowStatus
                FROM SNMPv2-TC
            Integer32, MODULE-IDENTITY, OBJECT-TYPE, NOTIFICATION-TYPE
                FROM SNMPv2-SMI
            MODULE-COMPLIANCE, OBJECT-GROUP, NOTIFICATION-GROUP
                FROM SNMPv2-CONF;

--
-- Module Identifier
--
    hwLptMib MODULE-IDENTITY
        LAST-UPDATED "201802281000Z"            -- Feb 28, 2018 at 10:00 GMT
        ORGANIZATION
            "Huawei Technologies Co.,Ltd."
        CONTACT-INFO
            "Huawei Industrial Base
              Bantian, Longgang
               Shenzhen 518129
               People's Republic of China
               Website: http://www.huawei.com
               Email: support@huawei.com
             "
        DESCRIPTION
            "The HUAWEI-LPT-MIB contains objects to
            Manage configuration and Monitor running state
            for LPT feature."
        REVISION "201802281000Z"            -- Feb 28, 2018 at 10:00 GMT
        DESCRIPTION
            "The initial revision of this MIB module."
        ::= { hwDatacomm 355 }
--
-- Objects Identifier
--
    hwLptTraps OBJECT IDENTIFIER ::= { hwLptMib 1 }

--  ******************************************************************
-- NOTIFICATIONS (TRAPS)
-- These notifications will be sent to the management entity
-- whenever LPT closed/opened access port.
-- ******************************************************************

--
-- Notification Identifier
--
    hwLptClosePortAlarm NOTIFICATION-TYPE
        OBJECTS { ifName }
        STATUS current
        DESCRIPTION
            "This object indicates that an hwLptClosePortAlarm notification is sent when LPT closes access port."
        ::= { hwLptTraps 1 }

    hwLptClosePortAlarmResume NOTIFICATION-TYPE
        OBJECTS { ifName }
        STATUS current
        DESCRIPTION
            "This object indicates that an hwLptClosePortAlarmResume notification is sent when LPT opens access port."
        ::= { hwLptTraps 2 }

    hwLPTMIBConformance OBJECT IDENTIFIER ::= { hwLptMib 2 }

    hwLPTMIBCompliances OBJECT IDENTIFIER ::= { hwLPTMIBConformance 1 }

    hwLPTMIBGroups OBJECT IDENTIFIER ::= { hwLPTMIBConformance 2 }

    hwLPTMIBNotificationGroup OBJECT-GROUP
        OBJECTS { hwLptClosePortAlarm, hwLptClosePortAlarmResume}
        STATUS current
        DESCRIPTION
            "The LPT notification collection."
        ::= { hwLPTMIBGroups 1 }

    END
