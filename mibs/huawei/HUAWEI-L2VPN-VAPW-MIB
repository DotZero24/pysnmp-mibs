-- ===================================================================
-- Copyright (C) 2017 by HUAWEI TECHNOLOGIES. All rights reserved.
-- Description: This MIB contains private managed object and notification
--              trap definitions for virtual cluster access.
-- Reference:
-- Version: V1.02
-- ===================================================================


    HUAWEI-L2VPN-VAPW-MIB DEFINITIONS ::= BEGIN

        IMPORTS
            hwDatacomm
                FROM HUAWEI-MIB
            ifIndex, ifName, InterfaceIndex
                FROM IF-MIB
            SnmpAdminString
                FROM SNMP-FRAMEWORK-MIB
            MODULE-COMPLIANCE, OBJECT-GROUP, NOTIFICATION-GROUP
                FROM SNMPv2-CONF
            Integer32, Unsigned32, Counter32, IpAddress, BITS, OBJECT-TYPE,
            MODULE-IDENTITY, NOTIFICATION-TYPE
                FROM SNMPv2-SMI
            InetAddressType, InetAddress
                FROM INET-ADDRESS-MIB;

--
-- Revision history   hwVirtualAccessMib
--
        hwVirtualAccessPw MODULE-IDENTITY
            LAST-UPDATED "201708171653Z"
            ORGANIZATION
                "Huawei Technologies Co.,Ltd."
            CONTACT-INFO
                "Huawei Industrial Base
                 Bantian, Longgang
                 Shenzhen 518129
                 People's Republic of China
                 Website: http://www.huawei.com
                 Email: support@huawei.com"
            DESCRIPTION
        "This MIB contains private network virtual access PW notification trap."

        REVISION    "201708171653Z"
        DESCRIPTION "Modify description of 'hwVirtualAccessPwSourceNodeId', 'hwVirtualAccessPwDestNodeId', 'hwVirtualAccessPwVaTunnelId' at 2017-8-17."

        REVISION    "201403031311Z"
        DESCRIPTION "Modify type of hwVirtualAccessPwReason at 2015-9-29."

        REVISION    "201403031311Z"
        DESCRIPTION "V1.00, initial version."

            ::= { hwVirtualAccessMib 3 }
--
-- Node definitions
--

        hwVirtualAccessMib OBJECT IDENTIFIER ::= { hwDatacomm 343 }

--
-- Node definitions
--
        hwVirtualAccessPwTrapObjects OBJECT IDENTIFIER ::= { hwVirtualAccessPw 1 }

        hwVirtualAccessPwTraps OBJECT IDENTIFIER ::= { hwVirtualAccessPw 2 }


        hwVirtualAccessVaIfIndex OBJECT-TYPE
            SYNTAX InterfaceIndex
            MAX-ACCESS read-only
            STATUS current
            DESCRIPTION
                "Indicates the virtual access interface index of virtual access PW."
            ::= { hwVirtualAccessPwTrapObjects 1 }

        hwVirtualAccessVaIfName OBJECT-TYPE
            SYNTAX OCTET STRING
            MAX-ACCESS read-only
            STATUS current
            DESCRIPTION
                "Indicates the virtual access interface name of virtual access PW."
            ::= { hwVirtualAccessPwTrapObjects 2 }

        hwVirtualAccessApId OBJECT-TYPE
            SYNTAX Integer32
            MAX-ACCESS read-only
            STATUS current
            DESCRIPTION
                "Indicates the AP ID."
            ::= { hwVirtualAccessPwTrapObjects 3 }

         hwVirtualAccessApIfName OBJECT-TYPE
            SYNTAX OCTET STRING
            MAX-ACCESS read-only
            STATUS current
            DESCRIPTION
                "Indicates the AP interface name."
            ::= { hwVirtualAccessPwTrapObjects 4 }

        hwVirtualAccessPwSourceNodeId  OBJECT-TYPE
            SYNTAX IpAddress
            MAX-ACCESS read-only
            STATUS current
            DESCRIPTION
                "Indicates the source node administrative IP address of virtual access tunnel."
            ::= { hwVirtualAccessPwTrapObjects 5 }

        hwVirtualAccessPwDestNodeId  OBJECT-TYPE
            SYNTAX IpAddress
            MAX-ACCESS read-only
            STATUS current
            DESCRIPTION
                "Indicates the destination node administrative IP address of virtual access tunnel."
            ::= { hwVirtualAccessPwTrapObjects 6 }

        hwVirtualAccessPwVaTunnelId OBJECT-TYPE
            SYNTAX Integer32
            MAX-ACCESS read-only
            STATUS current
            DESCRIPTION
                "Indicates the ID of virtual access tunnel."
            ::= { hwVirtualAccessPwTrapObjects 7 }

        hwVirtualAccessPwReason OBJECT-TYPE
            SYNTAX Integer32
            MAX-ACCESS read-only
            STATUS current
            DESCRIPTION
                 "This object indicates the cause that the VirtualAccessPw becomes down.
                 Options:
                 Interface Down  --indicates ac interface was down.
                 Tunnel Down     --indicates virtual access tunnel was down.
                 MTU unmatched   --indicates mtu of VirtualAccessPw not match.
                 Others          --indicates other reason.
                 PW Delete       -- indicates VirtualAccessPw was deleted.
                 PW Up           -- indicates VirtualAccessPw was up.
                 "
            ::= { hwVirtualAccessPwTrapObjects 8 }

        hwVirtualAccessPwDown NOTIFICATION-TYPE
            OBJECTS { hwVirtualAccessVaIfIndex,hwVirtualAccessVaIfName, hwVirtualAccessApId,hwVirtualAccessApIfName, hwVirtualAccessPwSourceNodeId , hwVirtualAccessPwDestNodeId ,
			          hwVirtualAccessPwVaTunnelId, hwVirtualAccessPwReason }
            STATUS current
            DESCRIPTION
                "This notification indicates that virtual access pw changes to down."
            ::= { hwVirtualAccessPwTraps 1 }

        hwVirtualAccessPwDownClear NOTIFICATION-TYPE
            OBJECTS { hwVirtualAccessVaIfIndex,hwVirtualAccessVaIfName, hwVirtualAccessApId,hwVirtualAccessApIfName, hwVirtualAccessPwSourceNodeId , hwVirtualAccessPwDestNodeId ,
			          hwVirtualAccessPwVaTunnelId, hwVirtualAccessPwReason }
            STATUS current
            DESCRIPTION
                "This notification indicates that virtual access pw changes to up."
            ::= { hwVirtualAccessPwTraps 2 }

--  Conformance information
--
        hwVirtualAccessPwMIBConformance OBJECT IDENTIFIER ::= { hwVirtualAccessPw 3 }

        hwVirtualAccessPwMIBCompliances OBJECT IDENTIFIER ::= { hwVirtualAccessPwMIBConformance 1 }

--  this module
        hwVirtualAccessPwMIBCompliance MODULE-COMPLIANCE
            STATUS current
            DESCRIPTION
                "The compliance statement for systems supporting
                the HUAWEI-VirtualAccessPw-MIB."
            MODULE -- this module
                MANDATORY-GROUPS { hwVirtualAccessPwNotificationGroup }
            ::= { hwVirtualAccessPwMIBCompliances 1 }

        hwVirtualAccessPwMIBGroups OBJECT IDENTIFIER ::= { hwVirtualAccessPwMIBConformance 2 }

        hwVirtualAccessPwGroup OBJECT-GROUP
            OBJECTS { hwVirtualAccessVaIfIndex,hwVirtualAccessVaIfName, hwVirtualAccessApId,hwVirtualAccessApIfName, hwVirtualAccessPwSourceNodeId , hwVirtualAccessPwDestNodeId ,
			          hwVirtualAccessPwVaTunnelId, hwVirtualAccessPwReason }
			STATUS current
            DESCRIPTION
                "The virtual access pw group."
            ::= { hwVirtualAccessPwMIBGroups 1 }

        hwVirtualAccessPwNotificationGroup NOTIFICATION-GROUP
            NOTIFICATIONS { hwVirtualAccessPwDown, hwVirtualAccessPwDownClear }
            STATUS current
            DESCRIPTION
                "The virtual access pw Notification group."
            ::= { hwVirtualAccessPwMIBGroups 2 }


    END

--
-- HUAWEI-L2VPN-VAPW-MIB.mib
--
