--
-- HUAWEI-SECURITY-DISK-MIB.mib
-- MIB generated by MG-SOFT Visual MIB Builder Version 6.0  Build 88
-- Monday, July 13, 2015 at 17:27:14
--

	HUAWEI-SECURITY-DISK-MIB DEFINITIONS ::= BEGIN

		IMPORTS
			enterprises
				FROM RFC1155-SMI
			Integer32, OBJECT-TYPE, MODULE-IDENTITY, NOTIFICATION-TYPE
				FROM SNMPv2-SMI;


		-- 1.3.6.1.4.1.2011.6.122.66
		hwDiskMib MODULE-IDENTITY
			LAST-UPDATED "201312190900Z"		-- December 19, 2013 at 09:00 GMT
			ORGANIZATION
				"Huawei Technologies Co.,Ltd."
			CONTACT-INFO
				"Huawei Industrial Base
				Bantian, Longgang
				Shenzhen 518129
				People's Republic of China
				Website: http://www.huawei.com
				Email: support@huawei.com"
			DESCRIPTION
				"The HUAWEI-SECURITY-DISK-MIB contains trap objects to indicate disk status."
			REVISION "201312190900Z"		-- December 19, 2013 at 09:00 GMT
			DESCRIPTION
				"V1.00, completed the first draft."
			::= { hwSecurity 66 }




--
-- Node definitions
--

		-- 1.3.6.1.4.1.2011
		huawei OBJECT IDENTIFIER ::= { enterprises 2011 }


		-- 1.3.6.1.4.1.2011.6
		huaweiUtility OBJECT IDENTIFIER ::= { huawei 6 }


		-- 1.3.6.1.4.1.2011.6.122
		hwSecurity OBJECT IDENTIFIER ::= { huaweiUtility 122 }


		-- 1.3.6.1.4.1.2011.6.122.66.1
		hwSecDiskMibNotification OBJECT IDENTIFIER ::= { hwDiskMib 1 }


		-- 1.3.6.1.4.1.2011.6.122.66.1.1
		hwSecDiskMibTrapObject OBJECT IDENTIFIER ::= { hwSecDiskMibNotification 1 }


		-- 1.3.6.1.4.1.2011.6.122.66.1.1.1
		hwSecDiskSlotNumber OBJECT-TYPE
			SYNTAX Integer32
			MAX-ACCESS accessible-for-notify
			STATUS current
			DESCRIPTION
				"The slot number of the disk."
			::= { hwSecDiskMibTrapObject 1 }


		-- 1.3.6.1.4.1.2011.6.122.66.1.1.2
		hwSecDiskAsc OBJECT-TYPE
			SYNTAX Integer32
			MAX-ACCESS accessible-for-notify
			STATUS current
			DESCRIPTION
				"The first detecting value of the disk."
			::= { hwSecDiskMibTrapObject 2 }


		-- 1.3.6.1.4.1.2011.6.122.66.1.1.3
		hwSecDiskAscq OBJECT-TYPE
			SYNTAX Integer32
			MAX-ACCESS accessible-for-notify
			STATUS current
			DESCRIPTION
				"The second detecting value of the disk."
			::= { hwSecDiskMibTrapObject 3 }


		-- 1.3.6.1.4.1.2011.6.122.66.1.1.4
		hwSecDiskSN OBJECT-TYPE
			SYNTAX OCTET STRING
			MAX-ACCESS accessible-for-notify
			STATUS current
			DESCRIPTION
				"The series number of the disk."
			::= { hwSecDiskMibTrapObject 4 }


		-- 1.3.6.1.4.1.2011.6.122.66.1.2
		hwSecDiskMibTraps OBJECT IDENTIFIER ::= { hwSecDiskMibNotification 2 }


		-- 1.3.6.1.4.1.2011.6.122.66.1.2.1
		hwSecDiskPredictionError NOTIFICATION-TYPE
			OBJECTS { hwSecDiskSlotNumber, hwSecDiskAsc, hwSecDiskAscq, hwSecDiskSN }
			STATUS current
			DESCRIPTION
				" A trap signifies disk failure prediction."
			::= { hwSecDiskMibTraps 1 }


		-- 1.3.6.1.4.1.2011.6.122.66.1.2.2
		hwSecDiskOffline NOTIFICATION-TYPE
			OBJECTS { hwSecDiskSlotNumber }
			STATUS current
			DESCRIPTION
				"Description."
			::= { hwSecDiskMibTraps 2 }


		-- 1.3.6.1.4.1.2011.6.122.66.1.2.3
		hwSecDiskOnline NOTIFICATION-TYPE
			OBJECTS { hwSecDiskSlotNumber }
			STATUS current
			DESCRIPTION
				"Description."
			::= { hwSecDiskMibTraps 3 }



	END

--
-- HUAWEI-SECURITY-DISK-MIB.mib
--
