-- ============================================================================
-- Copyright (C) 2013 by  HUAWEI TECHNOLOGIES. All rights reserved.
-- Description:  This MIB module defines MIB objects which provides VOIP global parameters management.
-- Reference:
-- Version: V1.41
-- ============================================================================

 HUAWEI-VOIP-COMMON-MIB DEFINITIONS ::= BEGIN
      IMPORTS
        	MODULE-IDENTITY, OBJECT-TYPE, NOTIFICATION-TYPE, private,Integer32
        		FROM SNMPv2-SMI
        	MODULE-COMPLIANCE, OBJECT-GROUP, NOTIFICATION-GROUP
        		FROM SNMPv2-CONF
        	TEXTUAL-CONVENTION
        		FROM SNMPv2-TC
        	IpAddress,TimeTicks,Counter32, Unsigned32
        		FROM SNMPv2-SMI
        	RowStatus,DisplayString
        		FROM SNMPv2-TC
        	huaweiUtility
        		FROM HUAWEI-MIB;

      hwVoip MODULE-IDENTITY
                LAST-UPDATED "201304020000Z"
                ORGANIZATION "Huawei Technologies Co., Ltd."
                CONTACT-INFO
                             "Huawei Industrial Base
    	                      Bantian, Longgang
    	                      Shenzhen 518129
    	                      People's Republic of China
    	                      Website: http://www.huawei.com
    	                      Email: support@huawei.com
    	                     "
                DESCRIPTION
                	"
                	This MIB module defines MIB objects which provides VOIP global parameters management.
                	"

            --  Revision history
            REVISION     "201304020000Z"
            DESCRIPTION  "V1.41, modify the Description of node hwDtmfTransfersMode of hwDtmfParametersTable"

            REVISION     "201303160000Z"
            DESCRIPTION  "V1.41, modify the Description of node hwModemTransEvent of hwModemParametersTable"

            REVISION     "201301080000Z"
            DESCRIPTION  "V1.41, modified the value range of hwDspSpecialFlow in hwDspParaTemplateCfgTable"

            REVISION     "201212130000Z"
            DESCRIPTION  "V1.40, modified the OID value of hwMgStreamQosConfigTable"

            REVISION     "201212050000Z"
            DESCRIPTION  "V1.39, modified the hwIASVoipObjects number in hwSRTPParameterTable"

            REVISION     "201211020000Z"
            DESCRIPTION  "V1.39, added hwTranslationRuleSetTable"

            REVISION     "201210120000Z"
            DESCRIPTION  "V1.39, modified the value range of hwVGWNumberChangeChangeLen in hwVGWNumberChangeTable"

            REVISION     "201210110000Z"
            DESCRIPTION  "V1.39, added hwTranslationRuleConfigTable"

            REVISION     "201210090000Z"
            DESCRIPTION  "V1.39, modified the value range and description of hwMgStreamQosCfgProtoType"

            REVISION     "201204280000Z"
            DESCRIPTION  "V1.38, added hwRfcComplied"

            REVISION     "201204280000Z"
            DESCRIPTION  "V1.38, added hwMgStreamQosConfigTable"

            REVISION     "201202250000Z"
            DESCRIPTION  "V1.38, added hwSRTPParameterTable"

            REVISION     "201204260000Z"
            DESCRIPTION  "V1.38, added hwCngLevel to hwDspAttributeTable"

            REVISION     "201110140000Z"
            DESCRIPTION  "V1.37, added hwDspMediaBreakTimer, hwPreDigitMapProtocol, hwDsp2198ForVoice,hwVGWNumberChangeTable,
                          modified hwProtocolActive, hwProtocolConfig, hwDspParaTemplateCfgTable"

            REVISION     "201110130000Z"
            DESCRIPTION  "V1.36, modify the hwFAXTransfersMode's, hwFaxPacketInterval10msGlobal's
                          and hwModemPacketInterval10msGlobal's STATUS"

            REVISION     "201109070000Z"
            DESCRIPTION  "V1.35, added hwMgRingDefaultRingparaTable, hwOnHookDtmfNumStartCode, hwIASVoipResSysDSPAbsentTrap,
                          hwIASVoipResSysDSPAbsentRestoreTrap, hwDspTemplateFixedJbUpImmediately, hwModemParaDtmfFallbackVoice,
                          hwModemDtmfFallbackVoice, hwDspFixedJbUpImmediately."

            REVISION     "201102210000Z"
            DESCRIPTION  "V1.34, added hwDigitMapGroupConfigTable."

            REVISION     "201101200000Z"
            DESCRIPTION  "V1.33, revised the description errors"

            REVISION     "201011150000Z"
            DESCRIPTION  "V1.32, corrected the Description. Added hwTlsRunStateInfoTable, hwIpTrkGrpFaxParaTable,
                          hwIpTrkGrpModemParaTable, hwIpTrkGrpRfc2833Table, hwIpTrkGrpRfc2198Table,
                          hwIpTrkGrpDtmfParaTable, hwRfc2833Dtmf, hwDSPResourceTypeTable, hwTlsParaCfgTable."

            REVISION     "201011090000Z"
            DESCRIPTION  "V1.31, corrected the Description. "
            REVISION     "201007010000Z"
            DESCRIPTION  "V1.30, corrected the Description. Added hwFaxVbdAttributeType, hwFaxRtpInterval, hwModemVbdAttributeType, hwModemRtpInterval
            	          hwOnHookChnSeizure, hwOnHookMarkSignal, hwOnHookSendFskInterval, hwOnHookDtAsDur, hwOffHookMarkSignal,
            	          hwOffHookDetectTeAckInterval, hwOffHookSendFskInterval, hwOffHookDtAsDur, and hwDsp2198ForVbd.
            	          Added hwRfc2833Table,  hwRfc2198Table, hwRfc2198SmartParaTable, and hwDtmfParaTable."

            REVISION     "201006170000Z"
            DESCRIPTION  "V1.29, corrected the description."

            REVISION     "201009060000Z"
            DESCRIPTION  "V1.28, added hwIpTrkGrpFaxParaTable,hwIpTrkGrpModemParaTable,hwIpTrkGrpRfc2833Table,hwIpTrkGrpRfc2198Table,hwIpTrkGrpDtmfParaTable to support PBX"

            REVISION     "201005050000Z"
            DESCRIPTION  "V1.27, revised the errors."

            REVISION     "201004100000Z"
            DESCRIPTION  "V1.26, correct simpletest error. Added hwDsp2198ForVbd."

            REVISION     "201003270000Z"
            DESCRIPTION  "V1.25, added hwDspOverloadResourceCfgTable. Added hwDspInputGain, hwDspOutputGain, hwDspDtmfPara, hwDsp2833ForDataevent, and hwDspSpecialFlow."

            REVISION     "201002250000Z"
            DESCRIPTION  "V1.23, added hwAlarmLoopdelay, hwAlarmPacketlost, and hwAlarmJitterbuffertrap to support new trap"

            REVISION     "201001250000Z"
            DESCRIPTION  "V1.22, added trap notification and corrected compile error"

            REVISION     "200912180000Z"
            DESCRIPTION  "V1.21, added hwVoipDynIPNameTable to support DHCP"

                        ::= { huaweiUtility 36 }


 hwIASVoipAlarmOids OBJECT IDENTIFIER ::= { hwIASVoipTraps 1 }

 hwIASVoipAlarmTraps OBJECT IDENTIFIER ::= { hwIASVoipTraps 0 }
-- cch for stand alone begin
-- hwStandAloneParaTable OBJECT IDENTIFIER ::= { hwIASVoipObjects 24 }
-- cch for standalone end

-- BEGIN: modified by wuguowang 20050722 FOR BT VAG
 --hwDigitmapTable OBJECT IDENTIFIER ::= { hwIASVoipObjects 23 }
-- END: modified by wuguowang 20050722 FOR BT VAG

 hwIASVoipObjects OBJECT IDENTIFIER ::= { hwVoip 1 }

 hwIASVoipTraps OBJECT IDENTIFIER ::= { hwVoip 2 }

 hwIASVoipComTrapsVbOids OBJECT IDENTIFIER ::= { hwVoip 9 }

 hwIASVoipComTraps OBJECT IDENTIFIER ::= { hwVoip 10 }

 hwIASVoipComCommonTraps OBJECT IDENTIFIER ::= { hwIASVoipComTraps 1 }

 hwIASVoipComAlarmTraps OBJECT IDENTIFIER ::= { hwIASVoipComTraps 2 }

 hwIASVoipComResTraps OBJECT IDENTIFIER ::= { hwIASVoipComCommonTraps 1 }

 hwIASVoipComResAlarmTraps OBJECT IDENTIFIER ::= { hwIASVoipComAlarmTraps 1 }

 hwIASVoipComProtocolAlarmTraps OBJECT IDENTIFIER ::= { hwIASVoipComAlarmTraps 2 }

 hwIASVoipComVolcAlarmTraps OBJECT IDENTIFIER ::= { hwIASVoipComAlarmTraps 3 }


 hwVoipCommonObjects OBJECT IDENTIFIER ::= { hwIASVoipObjects 69 }

   hwMgRingTypeMapTable OBJECT-TYPE
     SYNTAX      SEQUENCE OF HwMgRingTypeMapEntry
     MAX-ACCESS  not-accessible
     STATUS      current
     DESCRIPTION
       "
       This table is used to set the ring type mapping.
       The indexes of this table are hwMgRingTypeMapMgId, hwMgRingTypeMapRingId.
       "
     ::= { hwIASVoipObjects 11 }

   hwMgRingTypeMapEntry OBJECT-TYPE
     SYNTAX      HwMgRingTypeMapEntry
     MAX-ACCESS  not-accessible
     STATUS      current
     DESCRIPTION
       "
       This table is used to set the ring type mapping.
       The indexes of this entry are hwMgRingTypeMapMgId, hwMgRingTypeMapRingId.
       "
     INDEX    {
               hwMgRingTypeMapMgId,
               hwMgRingTypeMapRingId
              }
     ::= { hwMgRingTypeMapTable 1 }

   HwMgRingTypeMapEntry ::=
     SEQUENCE
     {
       hwMgRingTypeMapMgId	Integer32,
       hwMgRingTypeMapRingId	Integer32,
       hwMgRingTypeMapCascadeRingType	Integer32,
       hwMgRingTypeMapInitRingType	Integer32,
       hwMgRingTypeMapRowStatus	RowStatus,
       hwMgRingTypeMapName OCTET STRING
     }

   hwMgRingTypeMapMgId OBJECT-TYPE
     SYNTAX      Integer32(0..33554431)
     MAX-ACCESS  not-accessible
     STATUS      current
     DESCRIPTION
         "
         Indicates the MG ID.
         The range of MG ID from 0 to 16777215 is for AG system, value of 33554431 is only for PBX system and the value input from 16777215 to 33554431 is invalid.
         "
     ::= { hwMgRingTypeMapEntry 1 }

   hwMgRingTypeMapRingId OBJECT-TYPE
     SYNTAX      Integer32(0..255)
     MAX-ACCESS  not-accessible
     STATUS      current
     DESCRIPTION
         "
         Indicates the ring ID.
         The range of ring ID from 0 to 15 is for AG system,When  the system is PBX the range of ring ID is  0 to 15,and  255 is also valid.
         When the value is 255 and row status is 4, means the system allocate a valid ring ID from 0 to 15.
         "
     ::= { hwMgRingTypeMapEntry 2 }

   hwMgRingTypeMapCascadeRingType OBJECT-TYPE
     SYNTAX      Integer32(1..31)
     MAX-ACCESS  read-write
     STATUS      current
     DESCRIPTION
         "
         Indicates the cadence ring type.
         Enumerated types:
         1-Null, 2-Normal ring 1:4, 3-Special ring 1:2, 4-Special ring 0.4:0.2:0.4:4, 5-Long ring, 6-Special ring 1.2:2, 7-HK ring 1:3, 8-HK CNTRX 0.4:0.2:0.4:0.2:0.4:3.0,
         9-HK DN-A 0.4:0.2:0.4:3.0, 10-HK ACB 0.4:0.2, 11-HK reminder ring (one tone every 0.4 second; one tone), 12-HK DN-B 1.2:3, 13-CNTRX-IN 0.4:0.2:0.4:0.2:0.4:2.6,
         14-Egypt long-distance ring 2:1, 15-user defined ring mode 0, 16-user defined ring mode 1, 17-user defined ring mode 2, 18-user defined ring mode 3,
         19-user defined ring mode 4, 20-user defined ring mode 5, 21-user defined ring mode 6, 22-user defined ring mode 7, 23-user defined ring mode 8, 24-user defined ring mode 9,
         25-user defined ring mode 10, 26-user defined ring mode 11, 27-user defined ring mode 12, 28-user defined ring mode 13, 29-user defined ring mode 14,
         30-user defined ring mode 15, 31-ETSI RP-AS 0.25
         "
     ::= { hwMgRingTypeMapEntry 3 }

   hwMgRingTypeMapInitRingType OBJECT-TYPE
     SYNTAX      Integer32(1..28)
     MAX-ACCESS  read-write
     STATUS      current
     DESCRIPTION
         "
         Indicates the initial ring type.
         Enumeration type:
         1-Null, 2-Normal ring (FSK) 1:4, 3-Special ring (FSK) 1:2, 4-Special ring (FSK) 0.4:0.2:0.4:4, 5-Special ring (FSK) 1.2:2, 6-HK ring (FSK) 1:3, 7-HK CNTRX (FSK) 0.4:0.2:0.4:0.2:0.4:3.0,
         8-HK DN-A (FSK) 0.4:0.2:0.4:3.0, 9-HK DN-B (FSK) 1.2:3, 10-CNTRX-IN (FSK) 0.4:0.2:0.4:0.2:0.4:2.6, 11-Egypt long-distance ring (FSK) 2:1, 12-user defined FSK ring mode 0,
         13-user defined FSK ring mode 1, 14-user defined FSK ring mode 2, 15-user defined FSK ring mode 3, 16-user defined FSK ring mode 4, 17-user defined FSK ring mode 5,
         18-user defined FSK ring mode 6, 19-user defined FSK ring mode 7, 20-user defined FSK ring mode 8, 21-user defined FSK ring mode 9, 22-user defined FSK ring mode 10,
         23-user defined FSK ring mode 11, 24-user defined FSK ring mode 12, 25-user defined FSK ring mode 13, 26-user defined FSK ring mode 14, 27-user defined FSK ring mode 15, 28-ETSI RP-AS (FSK) 0.25
         "
     ::= { hwMgRingTypeMapEntry 4 }

   hwMgRingTypeMapRowStatus OBJECT-TYPE
     SYNTAX      RowStatus
     MAX-ACCESS  read-write
     STATUS      current
     DESCRIPTION
         "
         Indicates the row status (the SIP supports only 4 and 6).
         "
     ::= { hwMgRingTypeMapEntry 5 }

   hwMgRingTypeMapName OBJECT-TYPE
     SYNTAX      OCTET STRING(SIZE (0..32))
     MAX-ACCESS  read-write
     STATUS      current
     DESCRIPTION
         "
         Indicates the ring type mapping name.
         "
     ::= { hwMgRingTypeMapEntry 6 }

   hwMgCallInfoTable OBJECT-TYPE
     SYNTAX      SEQUENCE OF HwMgCallInfoEntry
     MAX-ACCESS  not-accessible
     STATUS      current
     DESCRIPTION
       "
       This table is use to query the information in the call.
       The index of this table is hwMgCallInfoIndex.
       "
     ::= { hwIASVoipObjects 12 }

   hwMgCallInfoEntry OBJECT-TYPE
     SYNTAX      HwMgCallInfoEntry
     MAX-ACCESS  not-accessible
     STATUS      current
     DESCRIPTION
       "
       This table is use to query the information in the call.
       The index of this entry is hwMgCallInfoIndex.
       "
     INDEX    {
               hwMgCallInfoIndex
              }
     ::= { hwMgCallInfoTable 1 }

   HwMgCallInfoEntry ::=
     SEQUENCE
     {
       hwMgCallInfoIndex	 Integer32,
       hwMgCallInfoRTPPort	 Integer32,
       hwMgCallInfoDSPPlace	 Integer32,
       hwMgCallInfoCodec	 INTEGER,
       hwMgCallInfoPackagTime	 Integer32,
       hwMgCallInfoVAD	         INTEGER,
       hwMgCallInfoEC	         INTEGER,
       hwMgCallInfoJitBuffer	 Integer32,
       hwMgCallInfoTransGain	 Integer32,
       hwMgCallInfoRecvGain	 Integer32,
       hwMgCallInfoRemoteRTPPort Integer32,
       hwMgCallInfoLocalIP       IpAddress,
       hwMgCallInfoRemoteIP      IpAddress,
       hwMgCallInfoDuration	 Integer32,
       hwMgCallInfoRTCPState     INTEGER,
       hwMgCallInfoRmtPackagTime Integer32,
       hwMgCallInfoRcvPackageNum Integer32,
       hwMgCallInfoSndPackageNum Integer32,
       hwMgCallInfoRcvOctsNum    Integer32,
       hwMgCallInfoSndOctsNum    Integer32,
       hwMgCallInfoLoopDelay     Integer32,
       hwMgCallInfoLocalJitter   Integer32,
       hwMgCallInfoRmtJitter     Integer32,
       hwMgCallInfoLocalLossRate Integer32,
       hwMgCallInfoRmtLossRate   Integer32,
       hwMgCallInfoMos           Integer32,
       hwMgCallInfoVlanID        Integer32,
       hwMgCallInfoVlanPriority  Integer32,
       hwMgCallInfoQoSStrategy   Integer32,
       hwMgCallInfoQoSValue     Integer32,
       hwMgCallInfoNplr         Integer32,
       hwMgCallInfoJdr          Integer32,
       hwMgCallInfoRtd          Integer32,
       hwMgCallInfoEsd          Integer32,
       hwMgCallInfoSl           Integer32,
       hwMgCallInfoNl           Integer32,
       hwMgCallInfoRerl         Integer32,
       hwMgCallInfoRFactor      Integer32,
       hwMgCallInfoMoslq        Integer32,
       hwMgCallInfoBld          Integer32,
       hwMgCallInfoGd           Integer32,
       hwMgCallInfoBd           Integer32,
       hwMgCallInfoGld          Integer32
     }

   hwMgCallInfoIndex OBJECT-TYPE
     SYNTAX      Integer32
     MAX-ACCESS  not-accessible
     STATUS      current
     DESCRIPTION
         "
         Indicates the shelf/slot/port.
         "
     ::= { hwMgCallInfoEntry 1 }

   hwMgCallInfoRTPPort OBJECT-TYPE
     SYNTAX      Integer32(0..65535)
     MAX-ACCESS  read-only
     STATUS      current
     DESCRIPTION
         "
         Indicates the local RTP port.
         "
     ::= { hwMgCallInfoEntry 2 }


   hwMgCallInfoDSPPlace OBJECT-TYPE
     SYNTAX      Integer32
     MAX-ACCESS  read-only
     STATUS      current
     DESCRIPTION
         "
         Indicates the DSP channel (the shelf/slot/channel index).
         "
     ::= { hwMgCallInfoEntry 3 }

   hwMgCallInfoCodec OBJECT-TYPE
     SYNTAX      INTEGER{g711U(1),reserved2(2),g72632k(3),reserved4(4),g7231(5),reserved6(6),reserved7(7),reserved8(8),g711A(9),g722(10),reserved11(11),reserved12(12),reserved13(13),silence(14),reserved15(15),g728(16),reserved17(17),reserved18(18),g729(19),reserved20(20),g723LOW(21),reserved22(22),reserved23(23),reserved24(24),reserved25(25),reserved26(26),reserved27(27),reserved28(28),reserved29(29),reserved30(30),reserved31(31),reserved32(32),reserved33(33),reserved34(34),reserved35(35),reserved36(36),reserved37(37),reserved38(38),reserved39(39),reserved40(40),reserved41(41),reserved42(42),reserved43(43),reserved44(44),reserved45(45),reserved46(46),reserved47(47),reserved48(48),reserved49(49),reserved50(50),amr475(51),amr515(52),amr59(53),amr67(54),amr74(55),amr795(56),amr102(57),amr122(58),t38Fax(59),g72616k(60),g72624k(61),g72640k(62)}
     MAX-ACCESS  read-only
     STATUS      current
     DESCRIPTION
         "
         Indicates the enumerated definition of the VoiceCode. Note that several items in the enumerated definition are not consecutive.
         In the definition below, G723Low(16) and G723High(17) need not be distinguished and can be directly presented as G.723.
         Options:
         1. g711U(1) -G711U
         2. reserved2(2) -system reserved
         3. g72632k(3) -G726, 32K
         4. reserved4(4) -system reserved
         5. g7231(5) -G723
         6. reserved6(6) -system reserved
         7. reserved7(7) -system reserved
         8. reserved8(8) -system reserved
         9. g711A(9) -G711A
         10. g722(10) -G722
         11. reserved11(11) -system reserved
         12. reserved12(12) -system reserved
         13. reserved13(13) -system reserved
         14. silence(14) -silence
         15. reserved15(15) -system reserved
         16. g728(16) -G728
         17. reserved17(17) -system reserved
         18. reserved18(18) -system reserved
         19. g729(19) -G729
         20. reserved20(20) -system reserved
         21. g723LOW(21) -G723 low
         22. reserved22(22) -system reserved
         23. reserved23(23) -system reserved
         24. reserved24(24) -system reserved
         25. reserved25(25) -system reserved
         26. reserved26(26) -system reserved
         27. reserved27(27) -system reserved
         28. reserved28(28) -system reserved
         29. reserved29(29) -system reserved
         30. reserved30(30) -system reserved
         31. reserved31(31) -system reserved
         32. reserved32(32) -system reserved
         33. reserved33(33) -system reserved
         34. reserved34(34) -system reserved
         35. reserved35(35) -system reserved
         36. reserved36(36) -system reserved
         37. reserved37(37) -system reserved
         38. reserved38(38) -system reserved
         39. reserved39(39) -system reserved
         40. reserved40(40) -system reserved
         41. reserved41(41) -system reserved
         42. reserved42(42) -system reserved
         43. reserved43(43) -system reserved
         44. reserved44(44) -system reserved
         45. reserved45(45) -system reserved
         46. reserved46(46) -system reserved
         47. reserved47(47) -system reserved
         48. reserved48(48) -system reserved
         49. reserved49(49) -system reserved
         50. reserved50(50) -system reserved
         51. amr475(51) -amr475
         52. amr515(52) -amr515
         53. amr59(53) -amr59
         54. amr67(54) -amr67
         55. amr74(55) -amr74
         56. amr795(56) -amr795
         57. amr102(57) -amr102
         58. amr122(58) -amr122
         59. t38Fax(59) -t38 fax
         60. g72616k(60) -G726, 16K
         61. g72624k(61) -G726, 24K
         62. g72640k(62) -G726, 40K
         "
     ::= { hwMgCallInfoEntry 4 }

   hwMgCallInfoPackagTime OBJECT-TYPE
     SYNTAX      Integer32
     MAX-ACCESS  read-only
     STATUS      current
     DESCRIPTION
         "
         Indicates the codex packetizing duration.
         "
     ::= { hwMgCallInfoEntry 5 }

   hwMgCallInfoVAD OBJECT-TYPE
     SYNTAX      INTEGER{true(1),false(2)}
     MAX-ACCESS  read-only
     STATUS      current
     DESCRIPTION
         "
         Indicates voice activity detection.
         Options:
         1. true(1) -detect voice activity
         2. false(2) -not detect voice activity
         "
     ::= { hwMgCallInfoEntry 6 }

   hwMgCallInfoEC OBJECT-TYPE
     SYNTAX      INTEGER{true(1),false(2)}
     MAX-ACCESS  read-only
     STATUS      current
     DESCRIPTION
         "
         Indicates echo cancel.
         Options:
         1. true(1)  -echo cancel
         2. false(2) -disable echo cancel
         "
     ::= { hwMgCallInfoEntry 7 }

   hwMgCallInfoJitBuffer OBJECT-TYPE
     SYNTAX      Integer32
     MAX-ACCESS  read-only
     STATUS      current
     DESCRIPTION
         "
         Indicates the local JitBuffer value.
         "
     ::= { hwMgCallInfoEntry 8 }

   hwMgCallInfoTransGain OBJECT-TYPE
     SYNTAX      Integer32
     MAX-ACCESS  read-only
     STATUS      current
     DESCRIPTION
         "
         Indicates the transmit gain (0-20 correspond to -10 dB to +10 dB).
         "
     ::= { hwMgCallInfoEntry 9 }

   hwMgCallInfoRecvGain OBJECT-TYPE
     SYNTAX      Integer32
     MAX-ACCESS  read-only
     STATUS      current
     DESCRIPTION
         "
         Indicates the receive gain (0-15 correspond to -10 dB to +5 dB).
         "
     ::= { hwMgCallInfoEntry 10 }

   hwMgCallInfoRemoteRTPPort OBJECT-TYPE
     SYNTAX      Integer32(0..65535)
     MAX-ACCESS  read-only
     STATUS      current
     DESCRIPTION
         "
         Indicates the remote RTP port.
         "
     ::= { hwMgCallInfoEntry 11 }

   hwMgCallInfoLocalIP OBJECT-TYPE
     SYNTAX      IpAddress
     MAX-ACCESS  read-only
     STATUS      current
     DESCRIPTION
         "
         Indicates the local IP address. The value 255.255.255.255 is returned if the entry is invalid.
         "
     ::= { hwMgCallInfoEntry 12 }

   hwMgCallInfoRemoteIP OBJECT-TYPE
     SYNTAX      IpAddress
     MAX-ACCESS  read-only
     STATUS      current
     DESCRIPTION
         "
         Indicates the remote IP address. The value 255.255.255.255 is returned if the entry is invalid.
         "
     ::= { hwMgCallInfoEntry 13 }

   hwMgCallInfoDuration OBJECT-TYPE
     SYNTAX      Integer32
     MAX-ACCESS  read-only
     STATUS      current
     DESCRIPTION
         "
         Indicates the occupied duration.
         Unit: second
         "
     ::= { hwMgCallInfoEntry 14 }

   hwMgCallInfoRTCPState OBJECT-TYPE
     SYNTAX      INTEGER{on(1),         -- enable rtcp
                         off(2),        -- disable rtcp
                         notReported(3) -- not report rtcp
                         }
     MAX-ACCESS  read-only
     STATUS      current
     DESCRIPTION
         "
         Indicates the RTCP status (whether it is enabled).
         Options:
         1. on(1) -enable rtcp
         2. off(2) -disable rtcp
         3. notReported(3) -not report rtcp
         "
     ::= { hwMgCallInfoEntry 15 }

   hwMgCallInfoRmtPackagTime OBJECT-TYPE
     SYNTAX      Integer32
     MAX-ACCESS  read-only
     STATUS      current
     DESCRIPTION
         "
         Indicates the remote packetizing duration.
         "
     ::= { hwMgCallInfoEntry 16 }

   hwMgCallInfoRcvPackageNum OBJECT-TYPE
     SYNTAX      Integer32
     MAX-ACCESS  read-only
     STATUS      current
     DESCRIPTION
         "
         Indicates the count of received packets.
         "
     ::= { hwMgCallInfoEntry 17 }

   hwMgCallInfoSndPackageNum OBJECT-TYPE
     SYNTAX      Integer32
     MAX-ACCESS  read-only
     STATUS      current
     DESCRIPTION
         "
         Indicates the count of sent packets.
         "
     ::= { hwMgCallInfoEntry 18 }

   hwMgCallInfoRcvOctsNum OBJECT-TYPE
     SYNTAX      Integer32
     MAX-ACCESS  read-only
     STATUS      current
     DESCRIPTION
         "
         Indicates the count of received octets.
         "
     ::= { hwMgCallInfoEntry 19 }

   hwMgCallInfoSndOctsNum OBJECT-TYPE
     SYNTAX      Integer32
     MAX-ACCESS  read-only
     STATUS      current
     DESCRIPTION
         "
         Indicates the count of sent octets.
         "
     ::= { hwMgCallInfoEntry 20 }

   hwMgCallInfoLoopDelay OBJECT-TYPE
     SYNTAX      Integer32
     MAX-ACCESS  read-only
     STATUS      current
     DESCRIPTION
         "
         Indicates the loop delay.
         Unit: millisecond
         "
     ::= { hwMgCallInfoEntry 21 }

   hwMgCallInfoLocalJitter OBJECT-TYPE
     SYNTAX      Integer32
     MAX-ACCESS  read-only
     STATUS      current
     DESCRIPTION
         "
         Indicates the local Jitter.
         Unit: millisecond
         "
     ::= { hwMgCallInfoEntry 22 }

   hwMgCallInfoRmtJitter OBJECT-TYPE
     SYNTAX      Integer32
     MAX-ACCESS  read-only
     STATUS      current
     DESCRIPTION
         "
         Indicates the remote Jitter.
         Unit: millisecond
         "
     ::= { hwMgCallInfoEntry 23 }


   hwMgCallInfoLocalLossRate OBJECT-TYPE
     SYNTAX      Integer32
     MAX-ACCESS  read-only
     STATUS      current
     DESCRIPTION
         "
         Indicates the local packet loss rate (%). 1 means 1%.
         "
     ::= { hwMgCallInfoEntry 24 }


   hwMgCallInfoRmtLossRate OBJECT-TYPE
     SYNTAX      Integer32
     MAX-ACCESS  read-only
     STATUS      current
     DESCRIPTION
         "
         Indicates the remote packet loss rate (%). 1 means 1%.
         "
     ::= { hwMgCallInfoEntry 25 }

  hwMgCallInfoMos OBJECT-TYPE
     SYNTAX      Integer32
     MAX-ACCESS  read-only
     STATUS      current
     DESCRIPTION
         "
         MOS(MOS:Mean Opinion Score) value.
         "
     ::= { hwMgCallInfoEntry 26 }

  hwMgCallInfoVlanID OBJECT-TYPE
     SYNTAX      Integer32
     MAX-ACCESS  read-only
     STATUS      current
     DESCRIPTION
         "
         Vlan ID.
         "
     ::= { hwMgCallInfoEntry 27 }

  hwMgCallInfoVlanPriority OBJECT-TYPE
     SYNTAX      Integer32
     MAX-ACCESS  read-only
     STATUS      current
     DESCRIPTION
         "
         Vlan priority.
         "
     ::= { hwMgCallInfoEntry 28 }

  hwMgCallInfoQoSStrategy OBJECT-TYPE
     SYNTAX      Integer32
     MAX-ACCESS  read-only
     STATUS      current
     DESCRIPTION
         "
         QoS strategy.
         "
     ::= { hwMgCallInfoEntry 29 }

  hwMgCallInfoQoSValue OBJECT-TYPE
     SYNTAX      Integer32
     MAX-ACCESS  read-only
     STATUS      current
     DESCRIPTION
         "
         QoS value.
         "
     ::= { hwMgCallInfoEntry 30 }

  hwMgCallInfoNplr OBJECT-TYPE
     SYNTAX      Integer32
     MAX-ACCESS  read-only
     STATUS      current
     DESCRIPTION
         "
         Network Packet Loss Rate(%). 1 means 1%.
         "
     ::= { hwMgCallInfoEntry 31 }

  hwMgCallInfoJdr OBJECT-TYPE
     SYNTAX      Integer32
     MAX-ACCESS  read-only
     STATUS      current
     DESCRIPTION
         "
         Jitter Buffer Discard Rate(%). 1 means 1%.
         "
     ::= { hwMgCallInfoEntry 32 }

  hwMgCallInfoRtd OBJECT-TYPE
     SYNTAX      Integer32
     MAX-ACCESS  read-only
     STATUS      current
     DESCRIPTION
         "
         RTCP Round-Trip Delay.
         Unit: millisecond
         "
     ::= { hwMgCallInfoEntry 33 }

  hwMgCallInfoEsd OBJECT-TYPE
     SYNTAX      Integer32
     MAX-ACCESS  read-only
     STATUS      current
     DESCRIPTION
         "
         End System Delay.
         Unit: millisecond
         "
     ::= { hwMgCallInfoEntry 34 }

  hwMgCallInfoSl OBJECT-TYPE
     SYNTAX      Integer32
     MAX-ACCESS  read-only
     STATUS      current
     DESCRIPTION
         "
         Signal Level.
         Unit: db
         "
     ::= { hwMgCallInfoEntry 35 }

  hwMgCallInfoNl OBJECT-TYPE
     SYNTAX      Integer32
     MAX-ACCESS  read-only
     STATUS      current
     DESCRIPTION
         "
         Noise Level.
         Unit: db
         "
     ::= { hwMgCallInfoEntry 36 }

   hwMgCallInfoRerl OBJECT-TYPE
     SYNTAX      Integer32
     MAX-ACCESS  read-only
     STATUS      current
     DESCRIPTION
         "
         Residual Echo Return Loss.
         Unit: db
         "
     ::= { hwMgCallInfoEntry 37 }

  hwMgCallInfoRFactor OBJECT-TYPE
     SYNTAX      Integer32
     MAX-ACCESS  read-only
     STATUS      current
     DESCRIPTION
         "
         R Factor.
         Range: 0-100
         "
     ::= { hwMgCallInfoEntry 38 }

   hwMgCallInfoMoslq OBJECT-TYPE
     SYNTAX      Integer32
     MAX-ACCESS  read-only
     STATUS      current
     DESCRIPTION
         "
         Estimated MOSLQ(a voice quality metric on a scale from 1 to 5).
         "
     ::= { hwMgCallInfoEntry 39 }

   hwMgCallInfoBld OBJECT-TYPE
     SYNTAX      Integer32
     MAX-ACCESS  read-only
     STATUS      current
     DESCRIPTION
         "
         Burst Loss Density(%). 1 means 1%.
         "
     ::= { hwMgCallInfoEntry 40 }

    hwMgCallInfoGd OBJECT-TYPE
     SYNTAX      Integer32
     MAX-ACCESS  read-only
     STATUS      current
     DESCRIPTION
         "
         Gap Duration.
         Unit: millisecond
         "
     ::= { hwMgCallInfoEntry 41 }

    hwMgCallInfoBd OBJECT-TYPE
     SYNTAX      Integer32
     MAX-ACCESS  read-only
     STATUS      current
     DESCRIPTION
         "
         Burst Duration.
         Unit: millisecond
         "
     ::= { hwMgCallInfoEntry 42 }

    hwMgCallInfoGld OBJECT-TYPE
     SYNTAX      Integer32
     MAX-ACCESS  read-only
     STATUS      current
     DESCRIPTION
         "
         Gap  Loss Density(%). 1 means 1%.
         "
     ::= { hwMgCallInfoEntry 43 }

 hwDspAttributeTable OBJECT IDENTIFIER ::= {  hwIASVoipObjects 25  }

 hwFaxMaxTrainRate OBJECT-TYPE
    SYNTAX      INTEGER{v17(1),v29(2),v27(3)}
    MAX-ACCESS  read-write
    STATUS      current
    DESCRIPTION
      "
      Indicates the maximum fax training rate.
      Options:
      1. v17(1) -V17
      2. v29(2) -V29
      3. v27(3) -V27
      Default: v17(1)
      "
    ::= { hwDspAttributeTable 1 }

 hwFaxTrainMode OBJECT-TYPE
    SYNTAX      INTEGER{remoteTrain(1), -- remote trainning
                        localTrain(2)   -- local trainning
                        }
    MAX-ACCESS  read-write
    STATUS      current
    DESCRIPTION
      "
      Indicates the fax training mode.
      Options:
      1. remoteTrain(1) -remote train
      2. localTrain(2) -local train
      "
    -- DEFVAL      { {remote-Train(1)} }
    ::= { hwDspAttributeTable 2 }

 hwDSPMaxJitterBuffer OBJECT-TYPE
    SYNTAX      Integer32(0..150)
    MAX-ACCESS  read-write
    STATUS      obsolete
    DESCRIPTION
      "
      Indicates the max JitterBuffer value of DSP channel.
      Unit: millisecond
      "
    -- DEFVAL      { 120 }
    ::= { hwDspAttributeTable 3 }

  hwDSPAttrInputGain OBJECT-TYPE
    SYNTAX      Integer32(0..15)
    MAX-ACCESS  read-write
    STATUS      obsolete
    DESCRIPTION
      "
      Indicates the input gain of DSP chip (0-15 correspond to -10 dB to +5 dB).
      "
    -- DEFVAL      { 10 }
    ::= { hwDspAttributeTable 4 }

  hwDSPAttrOutputGain OBJECT-TYPE
    SYNTAX      Integer32(0..20)
    MAX-ACCESS  read-write
    STATUS      obsolete
    DESCRIPTION
      "
      Indicates the output gain of DSP chip (0-20 correspond to -10 dB to +10 dB).
      "
    -- DEFVAL      { 10 }
    ::= { hwDspAttributeTable 5 }

  hwDSPCodeType OBJECT-TYPE
    SYNTAX      INTEGER{g711A(1),    -- G.711A
                        g711u(2),    -- G.711U
                        g723(3),     -- G.723
                        g729(4),     -- G.729
                        g726by16k(5), -- G.726_16K
                        g726by24k(6), -- G.726_24K
                        g726by32k(7), -- G.726_32K
                        g726by40k(8), -- G.726_40K
                        g722(9)      -- G.722
                        }
    MAX-ACCESS  read-write
    STATUS      current
    DESCRIPTION
      "
      Indicates the default coding type of DSP channel.
      It is unavailable in the SIP
      Options:
      1. g711A(1) -G.711A
      2. g711u(2) -G.711U
      3. g723(3) -G.723
      4. g729(4) -G.729
      5. g726by16k(5) -G.726_16K
      6. g726by24k(6) -G.726_24K
      7. g726by32k(7) -G.726_32K
      8. g726by40k(8) -G.726_40K
      9. g722(9) -G722
      "
    -- DEFVAL      { {g711A(1)} }
    ::= { hwDspAttributeTable 6 }

  hwRTCPPackageSendInterval OBJECT-TYPE
    SYNTAX      Integer32(0..65535)
    MAX-ACCESS  read-write
    STATUS      current
    DESCRIPTION
      "
      Indicates the RTCP packet sending interval of DSP channel.
      The valid value must be no less than 500, 0 indicates that the parameter is disabled.
      Unit: millisecond
      "
    -- DEFVAL      { 5000 }
    ::= { hwDspAttributeTable 7 }

  hwDSPRtpPacketInterval OBJECT-TYPE
    SYNTAX      INTEGER{packettime5ms(5),   -- 5ms
                        packettime10ms(10), -- 10ms
                        packettime20ms(20), -- 20ms
                        packettime30ms(30)  -- 30ms
                        }
    MAX-ACCESS  read-write
    STATUS      current
    DESCRIPTION
      "
      Indicates the default RTP packet time of DSP channel.
      Options:
      1. packettime5ms(5)   - 5ms
      2. packettime10ms(10) - 10ms
      3. packettime20ms(20) - 20ms
      4. packettime30ms(30) - 30ms
      "
    -- DEFVAL      { {interval20ms(20)} }
    ::= { hwDspAttributeTable 8 }

  hwDSPEchoCheck OBJECT-TYPE
    SYNTAX      INTEGER{disable(1),enable(2)}
    MAX-ACCESS  read-write
    STATUS      current
    DESCRIPTION
      "
      Indicates the default echo check switch of DSP channel.
      It is unavailable in the SIP.
      Options:
      1. disable(1) -disable
      2. enable(2) -enable
      "
    -- DEFVAL      { {enable(2)} }
    ::= { hwDspAttributeTable 9 }

  hwDSPSilenceReduce OBJECT-TYPE
    SYNTAX      INTEGER{disable(1),enable(2)}
    MAX-ACCESS  read-write
    STATUS      current
    DESCRIPTION
      "
      Indicates the default silence compression switch of DSP channel.
      It is unavailable in the SIP.
      Options:
      1. disable(1) -disable silence compression
      2. enable(2)  -enable silence compression
      "
    -- DEFVAL      { {disable(1)} }
    ::= { hwDspAttributeTable 10 }

  hwDSPNeedStatisOrNot OBJECT-TYPE
    SYNTAX      INTEGER{disable(1),enable(2)}
    MAX-ACCESS  read-write
    STATUS      current
    DESCRIPTION
      "
      Indicate whether DSP channel needs the channel statistics.
      It is unavailable in the SIP.
      Options:
      1. disable(1) -close
      2. enable(2) -open
      "
    -- DEFVAL      { {disable(1)} }
    ::= { hwDspAttributeTable 11 }

  hwDSPClearmodePayload OBJECT-TYPE
    SYNTAX      Integer32(96..127)
    MAX-ACCESS  read-write
    STATUS      current
    DESCRIPTION
      "
      Indicates the default payload type of the DSP channel clearmode (it must not conflict with the payload  used).
      "
    -- DEFVAL      { 100 }
    ::= { hwDspAttributeTable 12 }

  hwSevereDegradethreshold  OBJECT-TYPE
    SYNTAX      Integer32(1..65535)
    MAX-ACCESS  read-write
    STATUS      current
    DESCRIPTION
      "
      Indicates the default threshold of severely packet loss seconds.
      "
    -- DEFVAL      { 400 }
    ::= { hwDspAttributeTable 13 }

  hwBvqm         OBJECT-TYPE
    SYNTAX      INTEGER{disable(1),enable(2)}
    MAX-ACCESS  read-write
    STATUS      current
    DESCRIPTION
      "
      Indicates the VQM switch.
      Options:
      1. disable(1) -disable
      2. enable(2)  -enable
      "
    -- DEFVAL      { Disable }
    ::= { hwDspAttributeTable 14 }

  hwDSPPlc OBJECT-TYPE
    SYNTAX      INTEGER{disable(1),enable(2)}
    MAX-ACCESS  read-write
    STATUS      current
    DESCRIPTION
      "
      Indicates the DSP packet loss compensation algorithm.
      Options:
      1. disable(1) -disable
      2. enable(2) -enable
      "
    -- DEFVAL      { {disable(1)} }
    ::= { hwDspAttributeTable 15 }

    hwDSPMinAdaptJitterBuffer OBJECT-TYPE
    SYNTAX      Integer32(0..150)
    MAX-ACCESS  read-write
    STATUS      current
    DESCRIPTION
      "
      Minimum adapt jitterbuffer of DSP. MinAdaptJitterBuffer<=InitAdaptJitterBuffer<=MaxAdaptJitterBuffer and the MinAdaptJitterBuffer<ThresholdJitterBuffer.
      Unit: millisecond
      "
    -- DEFVAL      { 2 }
    ::= { hwDspAttributeTable 16 }

  hwDSPMaxAdaptJitterBuffer OBJECT-TYPE
    SYNTAX      Integer32(0..150)
    MAX-ACCESS  read-write
    STATUS      current
    DESCRIPTION
      "
      Maximum adapt jitterbuffer of DSP. MinAdaptJitterBuffer<=InitAdaptJitterBuffer<=MaxAdaptJitterBuffer and the MinAdaptJitterBuffer<ThresholdJitterBuffer.
      Unit: millisecond
      "
    -- DEFVAL      { 135 }
    ::= { hwDspAttributeTable 17 }

  hwDSPInitAdaptJitterBuffer OBJECT-TYPE
    SYNTAX      Integer32(0..150)
    MAX-ACCESS  read-write
    STATUS      current
    DESCRIPTION
      "
      Initial adapt jitterbuffer of DSP. MinAdaptJitterBuffer<=InitAdaptJitterBuffer<=MaxAdaptJitterBuffer and the MinAdaptJitterBuffer<ThresholdJitterBuffer.
      Unit: millisecond
      "
    -- DEFVAL      { 2 }
    ::= { hwDspAttributeTable 18 }

  hwDSPMinFixedJitterBuffer OBJECT-TYPE
    SYNTAX      Integer32(0..150)
    MAX-ACCESS  read-write
    STATUS      current
    DESCRIPTION
      "
      Minimum fixed jitterbuffer of DSP. MinFixedJitterBuffer<=NormalFixedJitterBuffer<=MaxFixedJitterBuffer and the MinAdaptJitterBuffer <ThresholdJitterBuffer.
      Unit: millisecond
      "
  -- DEFVAL      { 2 }
    ::= { hwDspAttributeTable 19 }

  hwDSPMaxFixedJitterBuffer OBJECT-TYPE
    SYNTAX      Integer32(0..150)
    MAX-ACCESS  read-write
    STATUS      current
    DESCRIPTION
      "
      Maximum fixed jitterbuffer of DSP. MinFixedJitterBuffer<=NormalFixedJitterBuffer<=MaxFixedJitterBuffer and the MinAdaptJitterBuffer<ThresholdJitterBuffer.
      Unit: millisecond
      "
  -- DEFVAL      { 135 }
    ::= { hwDspAttributeTable 20 }

  hwDSPNormalFixedJitterBuffer OBJECT-TYPE
    SYNTAX      Integer32(0..150)
    MAX-ACCESS  read-write
    STATUS      current
    DESCRIPTION
      "
      Initial fixed jitterbuffer of DSP. MinFixedJitterBuffer<=NormalFixedJitterBuffer<=MaxFixedJitterBuffer and the MinAdaptJitterBuffer<ThresholdJitterBuffer.
      Unit: millisecond
      "
  -- DEFVAL      { 60 }
    ::= { hwDspAttributeTable 21 }

  hw2198Payload OBJECT-TYPE
    SYNTAX      Integer32(96..127)
    MAX-ACCESS  read-write
    STATUS      current
    DESCRIPTION
      "
      Indicates the payload type value of 2198 (it must not conflict with the payload  used).
      "
  -- DEFVAL      { 96 }
    ::= { hwDspAttributeTable 22 }

  hwRedundancyT30 OBJECT-TYPE
    SYNTAX      Integer32(0..7)
    MAX-ACCESS  read-write
    STATUS      current
    DESCRIPTION
      "
      Indicates the T30 redundancy parameter of T38 Fax.
      "
  -- DEFVAL      { 3 }
    ::= { hwDspAttributeTable 23 }

  hwRedundancyT4 OBJECT-TYPE
    SYNTAX      Integer32(0..3)
    MAX-ACCESS  read-write
    STATUS      current
    DESCRIPTION
      "
      Indicates the T4 redundancy parameter of T38 Fax.
      "
  -- DEFVAL      { 3 }
    ::= { hwDspAttributeTable 24 }

  hwDSPRTCPXR OBJECT-TYPE
    SYNTAX      INTEGER{enable(1),disable(2)}
    MAX-ACCESS  read-write
    STATUS      current
    DESCRIPTION
      "
      The switch of RTCP XR.
      Options:
      1. enable(1) -enable RTCP XR
      2. disable(2) -disable RTCP XR
      "
    ::= { hwDspAttributeTable 25 }

  hwG726R32kPayload OBJECT-TYPE
    SYNTAX      Integer32(96..127)
    MAX-ACCESS  read-write
    STATUS      current
    DESCRIPTION
      "
      Indicates the payload type value of G.726-32k (it must not conflict with the payload used).
      "
  -- DEFVAL      { 101 }
    ::= { hwDspAttributeTable 26 }

 hwFaxV8Negotiate OBJECT-TYPE
     SYNTAX      INTEGER{enable(1),disable(2)}
     MAX-ACCESS  read-write
     STATUS      current
     DESCRIPTION
         "
         Indicates the switch of the V8 negotiation of FAX.
         Options:
         1. enable(1) -enable
         2. disable(2) -disable
         "
  -- DEFVAL      { {disable(2)} }
     ::= { hwDspAttributeTable 27 }

hwDSPModeJitterBuffer OBJECT-TYPE
    SYNTAX      INTEGER{adaptive(1),fixed(2)}
    MAX-ACCESS  read-write
    STATUS      current
    DESCRIPTION
      "
      Set JitterBuffer mode of DSP channel.
      Options:
      1. adaptive(1) -adaptive
      2. fixed(2) -fixed
      "
  -- DEFVAL      { {adaptive(1)} }
    ::= { hwDspAttributeTable 28 }

hwVbdPayload OBJECT-TYPE
    SYNTAX      Integer32(96..127)
    MAX-ACCESS  read-write
    STATUS      current
    DESCRIPTION
      "
      Indicates the payload type value of VBD (it must not conflict with the payload used).
      "
  -- DEFVAL      { 102 }
    ::= { hwDspAttributeTable 29 }

hwRfc2833Payload OBJECT-TYPE
    SYNTAX      Integer32(96..127)
    MAX-ACCESS  read-write
    STATUS      current
    DESCRIPTION
      "
      Indicates the payload type value of RFC2833 (it must not conflict with the payload used).
      "
 -- DEFVAL      { 97 }
    ::= { hwDspAttributeTable 30 }

hwG726R16kPayload OBJECT-TYPE
    SYNTAX      Integer32(96..127)
    MAX-ACCESS  read-write
    STATUS      current
    DESCRIPTION
      "
      Indicates the payload type value of G.726-16k (it must not conflict with the payload used).
      "
 -- DEFVAL      { 103 }
    ::= { hwDspAttributeTable 31 }

hwG726R24kPayload OBJECT-TYPE
    SYNTAX      Integer32(96..127)
    MAX-ACCESS  read-write
    STATUS      current
    DESCRIPTION
      "
      Indicates the payload type value of G.726-24k (it must not conflict with the payload used).
      "
 -- DEFVAL      { 104 }
    ::= { hwDspAttributeTable 32 }

hwG726R40kPayload OBJECT-TYPE
    SYNTAX      Integer32(96..127)
    MAX-ACCESS  read-write
    STATUS      current
    DESCRIPTION
      "
      Indicates the payload type value of G.726-40k (it must not conflict with the payload used).
      "
 -- DEFVAL      { 105 }
    ::= { hwDspAttributeTable 33 }

 hwDspAutoVBDSwitchMode OBJECT-TYPE
    SYNTAX      INTEGER{hostControl(1),autoSwitch(2)}
    MAX-ACCESS  read-write
    STATUS      current
    DESCRIPTION
      "
      VBD switch mode.
      Options:
      1. hostControl(1) -host control
      2. autoSwitch(2) -auto switch
      "
 -- DEFVAL      { {hostControl(1)} }
    ::= { hwDspAttributeTable 34 }

 hwDSPAlarmAdaptJitterBuffer OBJECT-TYPE
    SYNTAX      Integer32(0..150)
    MAX-ACCESS  read-write
    STATUS      current
    DESCRIPTION
      "
      Adapt jitterbuffer of DSP alarm threshold.
      Unit: millisecond
      "
 -- DEFVAL      { 150 }
    ::= { hwDspAttributeTable 35 }

    hwDspFixedJbUpImmediately OBJECT-TYPE
    SYNTAX      INTEGER{enable(1),disable(2)}
    MAX-ACCESS  read-write
    STATUS      current
    DESCRIPTION
      "
      Enable DSP fixed JB adjust upward immediately or not.
      Options:
      1. enable(1) -enable
      2. disable(2) -disable
      "
 -- DEFVAL      { 2 }
    ::= { hwDspAttributeTable 36 }

    hwDspMediaBreakTimer OBJECT-TYPE
    SYNTAX      Integer32(0..240)
    MAX-ACCESS  read-write
    STATUS      current
    DESCRIPTION
      "
      Media Break Timer. 0-indicates that the detection is disabled.
      Unit: second
      "
 -- DEFVAL      { 0 }
    ::= { hwDspAttributeTable 37 }

    hwCngLevel  OBJECT-TYPE
    SYNTAX      Integer32(5..90)
    MAX-ACCESS  read-write
    STATUS      current
    DESCRIPTION
      "
      Comfort noise generation level.
      Unit: -dB
      "
 -- DEFVAL      { 64 }
    ::= { hwDspAttributeTable 38 }



   hwProtocolSupportTable OBJECT IDENTIFIER ::= {  hwIASVoipObjects 43  }

   hwProtocolActive OBJECT-TYPE
    SYNTAX      Integer32(1..5)
    MAX-ACCESS  read-only
    STATUS      current
    DESCRIPTION
      "
      The bit table indicates the protocol that is currently used. The bit table from low bit to high bit are H248, MGCP and SIP. For example, the bit table value for sip protocol is 0b00000000000000000000000000000100.
      H248(1)
      MGCP(2)
      SIP(4)
      H248+SIP(5)
      "
    ::= { hwProtocolSupportTable 1 }

  hwProtocolConfig OBJECT-TYPE
    SYNTAX      Integer32(1..5)
    MAX-ACCESS  read-write
    STATUS      current
    DESCRIPTION
      "
      The bit table indicates the protocol supported by the system after the system resets. The bit table from low bit to high bit are H248, MGCP and SIP. For example, the bit table value for sip protocol is 0b00000000000000000000000000000100.
      H248(1)
      MGCP(2)
      SIP(4)
      H248+SIP(5)
      "
    ::= { hwProtocolSupportTable 2 }

  hwFeatureProtocolConfig OBJECT-TYPE
    SYNTAX      Integer32
    MAX-ACCESS  read-write
    STATUS      current
    DESCRIPTION
      "
      Indicates the voice feature supported by the system after the system resets.
      AG+H248(0)
      AG+MGCP(1)
      AG+SIP(2)
      PBX+SIP(3)
      PBX+NONE(4)
      "
    ::= { hwProtocolSupportTable 3 }

  hwFeatureProtocolActive OBJECT-TYPE
    SYNTAX      Integer32
    MAX-ACCESS  read-only
    STATUS      current
    DESCRIPTION
      "
      Indicates the voice feature that is currently used.
      AG+H248(0)
      AG+MGCP(1)
      AG+SIP(2)
      PBX+SIP(3)
      PBX+NONE(4)
      "
    ::= { hwProtocolSupportTable 4 }


  hwFaxParaTable OBJECT-TYPE
     SYNTAX      SEQUENCE OF HwFaxParaEntry
     MAX-ACCESS  not-accessible
     STATUS      current
     DESCRIPTION
       "
       This table is used to config the fax parameter.
       The index of this table is hwFaxParaVgwId.
       "
     ::= { hwVoipCommonObjects 1 }

   hwFaxParaEntry OBJECT-TYPE
     SYNTAX      HwFaxParaEntry
     MAX-ACCESS  not-accessible
     STATUS      current
     DESCRIPTION
       "
       This table is used to config the fax parameter.
       The index of this entry is hwFaxParaVgwId.
       "
     INDEX    {
                hwFaxParaVgwId
              }
     ::= { hwFaxParaTable 1 }

   HwFaxParaEntry ::=
     SEQUENCE
     {
       hwFaxParaVgwId           Integer32,
       hwFaxMode                Integer32,
       hwFaxPacketInterval10ms  INTEGER,
       hwFaxRedundancyFlag      Integer32,
       hwFaxNegoMode            INTEGER,
       hwFaxTransMode           INTEGER,
       hwFaxRfc2198NegoMode     INTEGER,
       hwFaxRfc2198StartMode    INTEGER,
       hwFaxParaVbdCodec  	INTEGER,
       hwFaxParaVbdPtType 	INTEGER,
       hwFaxTransEventType      INTEGER,
       hwFaxVbdAttributeType    INTEGER,
       hwFaxRtpInterval 	INTEGER
     }


   hwFaxParaVgwId OBJECT-TYPE
     SYNTAX      Integer32(0..16777215)
     MAX-ACCESS  not-accessible
     STATUS      current
     DESCRIPTION
         "
         Indicates the interface ID.
         "
     ::= { hwFaxParaEntry 1 }

    hwFaxMode OBJECT-TYPE
     SYNTAX      Integer32
     MAX-ACCESS  read-write
     STATUS      deprecated
     DESCRIPTION
         "
         Indicates the fax transmission mode. 1-Transparent transmission; 2-Auto-negotiation T.38; 3-V3 flow; 4-Stand-alone transparent transmission; 5-V5 flow; 6-Self-switch T.38. To be compatible with the previous versions, the enumerated types remain unchanged. Only 1, 2, 4, and 6 are available in the SIP. In the SIP, the transparent transmission mode is the same as the negotiation transparent transmission mode in the CLI.The default is 5 (V5 flow) for the H.248, 3 (V3 flow) for the MGCP, and 1 (transparent transmission) for the SIP.
         "
     ::= { hwFaxParaEntry 2 }

    hwFaxPacketInterval10ms OBJECT-TYPE
     SYNTAX      INTEGER{enable(1),disable(2)}
     MAX-ACCESS  read-write
     STATUS      current
     DESCRIPTION
       "
       Enable packet interval of fax to use only 10ms or not.
       Options:
       1. enable(1) -enable
       2. disable(2) -disable
       "
 -- DEFVAL      { {disable} }
     ::= { hwFaxParaEntry 3 }

    hwFaxRedundancyFlag OBJECT-TYPE
     SYNTAX      Integer32
     MAX-ACCESS  read-write
     STATUS      deprecated
     DESCRIPTION
         "
         Use fax redundancy parameter or not .1:enable,to use. 2:disable,not to use. This leaf only valid in sip transparent fax.
         "
 -- DEFVAL      { {disable(2)} }
     ::= { hwFaxParaEntry 4 }

    hwFaxNegoMode OBJECT-TYPE
     SYNTAX      INTEGER{negotiate(1), -- negotiate
                         selfswitch(2) -- do not negotiate
                         }
     MAX-ACCESS  read-write
     STATUS      current
     DESCRIPTION
         "
         The negotiate mode of fax.
         Options:
         1. negotiate(1) -negotiate
         2. selfswitch(2) -do not negotiate
         "
 -- DEFVAL      { {negotiate(1)} }
     ::= { hwFaxParaEntry 5 }

    hwFaxTransMode OBJECT-TYPE
     SYNTAX      INTEGER{thoroughly(1), -- use voice codec
                         t38(2)         -- use T.38 codec
                         }
     MAX-ACCESS  read-write
     STATUS      current
     DESCRIPTION
       "
       Indicates the fax transmission mode.
       Options:
       1. thoroughly(1) -use voice codec
       2. t38(2) - use T.38 codec
       Default: thoroughly(1)
       "
 -- DEFVAL      { {thoroughly(1)} }
     ::= { hwFaxParaEntry 6 }

    hwFaxRfc2198NegoMode OBJECT-TYPE
     SYNTAX      INTEGER{negoStart(1),        -- negotiate start
                         fixedStart(2),       -- fixed start
                         noInitiativeStart(3) -- no initiative start
                         }
     MAX-ACCESS  read-write
     STATUS      deprecated
     DESCRIPTION
       "
       Use fax redundancy parameter or not.
       Options:
       1. negoStart(1) -negotiate start
       2. fixedStart(2) -fixed start
       3. noInitiativeStart(3) -no Initiative Start
       "
 -- DEFVAL      { {noInitiativeStart(3)} }
     ::= { hwFaxParaEntry 7 }

    hwFaxRfc2198StartMode OBJECT-TYPE
     SYNTAX      INTEGER{smart2198(1),   -- smart start 2198
                         ordinary2198(2) -- ordinary 2198
                         }
     MAX-ACCESS  read-write
     STATUS      deprecated
     DESCRIPTION
       "
       Whether the fax support the RFC2198 Smart Startup.
       Options:
       1. smart2198(1) -smart start 2198
       2. ordinary2198(2) -ordinary 2198
       "
 -- DEFVAL      { {ordinary2198(2)} }
     ::= { hwFaxParaEntry 8 }

     hwFaxParaVbdCodec OBJECT-TYPE
     SYNTAX      INTEGER{g711A(1),g711U(2)}
     MAX-ACCESS  read-write
     STATUS      current
     DESCRIPTION
       "
       Indicates the codec of VBD.
       Options:
       1. g711A(1) -G.711A
       2. g711U(2) -G.711U
       "
 -- DEFVAL      { {g711A(1)} }
     ::= { hwFaxParaEntry 9 }

     hwFaxParaVbdPtType OBJECT-TYPE
     SYNTAX      INTEGER{static(1),dynamic(2)}
     MAX-ACCESS  read-write
     STATUS      current
     DESCRIPTION
       "
       Indicates the payload type of VBD.
       Options:
       1. static(1) -static payload type
       2. dynamic(2) -dynamic payload type
       "
 -- DEFVAL      { {static(1)} }
     ::= { hwFaxParaEntry 10 }

     hwFaxTransEventType OBJECT-TYPE
     SYNTAX      INTEGER{negoStart(1),fixedStart(2),noInitiativeStart(3)}
     MAX-ACCESS  read-write
     STATUS      deprecated
     DESCRIPTION
       "
       Indicates the mode of sending fax event, whether support the RFC2833.
       Options:
       1. negoStart(1) -negotiation start
       2. fixedStart(2) -fix start
       3. noInitiativeStart(3) -not initiative start
       "
 -- DEFVAL      { {noInitiativeStart(3)} }
     ::= { hwFaxParaEntry 11 }

     hwFaxVbdAttributeType OBJECT-TYPE
     SYNTAX      INTEGER{v152(1),chinatelecom(2),extchinatelecom(3),ietf(4)}
     MAX-ACCESS  read-write
     STATUS      current
     DESCRIPTION
       "
       Indicate the format of session attribute lines when starting fax VBD Negotiation.
       Options:
       1. v152(1) -v.152 format
       2. chinatelecom(2) -chinatelecom format
       3. extchinatelecom(3) -extchinatelecom format
       4. ietf(4) -ietf format
       "
 -- DEFVAL      { {v152(1)} }
     ::= { hwFaxParaEntry 12 }

     hwFaxRtpInterval OBJECT-TYPE
     SYNTAX      INTEGER{packettime5ms(1),packettime10ms(2),packettime20ms(3),packettime30ms(4)}
     MAX-ACCESS  read-write
     STATUS      current
     DESCRIPTION
       "
       Indicates the default RTP packet time of DSP channel.
       Options:
       1. packettime5ms(1) -5ms
       2. packettime10ms(2) -10ms
       3. packettime20ms(3) -20ms
       4. packettime30ms(4) -30ms
       Unit: millisecond
       "
 -- DEFVAL      { {packettime10ms(2)} }
     ::= { hwFaxParaEntry 13 }

  hwModemParaTable OBJECT-TYPE
     SYNTAX      SEQUENCE OF HwModemParaEntry
     MAX-ACCESS  not-accessible
     STATUS      current
     DESCRIPTION
       "
       This table is used to config the modem parameter.
       The index of this table is hwModemParaVgwId.
       "
     ::= { hwVoipCommonObjects 2 }

   hwModemParaEntry OBJECT-TYPE
     SYNTAX      HwModemParaEntry
     MAX-ACCESS  not-accessible
     STATUS      current
     DESCRIPTION
       "
       This table is used to config the modem parameter.
       The index of this entry is hwModemParaVgwId.
       "
     INDEX    {
                hwModemParaVgwId
              }
     ::= { hwModemParaTable 1 }

   HwModemParaEntry ::=
     SEQUENCE
     {
       hwModemParaVgwId           Integer32,
       hwModemMode                Integer32,
       hwModemRedundancyFlag      Integer32,
       hwModemPacketInterval10ms  INTEGER,
       hwModemNegoMode            INTEGER,
       hwModemTransMode           INTEGER,
       hwModemRfc2198NegoMode     INTEGER,
       hwModemRfc2198StartMode    INTEGER,
       hwModemParaVbdCodec        INTEGER,
       hwModemParaVbdPtType       INTEGER,
       hwModemTransEventType      INTEGER,
       hwModemVbdAttributeType    INTEGER,
       hwModemRtpInterval         INTEGER,
       hwModemParaDtmfFallbackVoice INTEGER
     }

   hwModemParaVgwId OBJECT-TYPE
     SYNTAX      Integer32(0..16777215)
     MAX-ACCESS  not-accessible
     STATUS      current
     DESCRIPTION
         "
         Indicates the interface ID.
         "
     ::= { hwModemParaEntry 1 }

    hwModemMode OBJECT-TYPE
     SYNTAX      Integer32
     MAX-ACCESS  read-write
     STATUS      deprecated
     DESCRIPTION
         "
         Indicates the modem transmission mode. 1-Negotiation mode; 2-Stand-alone mode.
         "
 -- DEFVAL      { {negotiate (1)} }
     ::= { hwModemParaEntry 2 }

    hwModemRedundancyFlag OBJECT-TYPE
     SYNTAX      Integer32
     MAX-ACCESS  read-write
     STATUS      deprecated
     DESCRIPTION
         "
         Indicates the flag of using the modem redundancy parameter. 1-enable; 2-disable .
         "
 -- DEFVAL      { {disable (2)} }
     ::= { hwModemParaEntry 3 }

   hwModemPacketInterval10ms OBJECT-TYPE
    SYNTAX      INTEGER{enable(1),disable(2)}
    MAX-ACCESS  read-write
    STATUS      current
    DESCRIPTION
      "
      Enable packet interval of modem to use only 10ms or not.
      Options:
      1. enable(1) -enable
      2. disable(2) -disable
      "
 -- DEFVAL      { {disable} }
    ::= { hwModemParaEntry 4 }

    hwModemNegoMode OBJECT-TYPE
     SYNTAX      INTEGER{negotiate(1), -- negotiate
                         selfswitch(2) -- do not negotiate
                         }
     MAX-ACCESS  read-write
     STATUS      current
     DESCRIPTION
         "
         The negotiate mode of fax.
         Options:
         1. negotiate(1) -negotiate
         2. selfswitch(2) -do not negotiate
         "
 -- DEFVAL      { {negotiate(1)} }
     ::= { hwModemParaEntry 5 }

    hwModemTransMode OBJECT-TYPE
     SYNTAX      INTEGER{thoroughly(1),relay(2)}
     MAX-ACCESS  read-write
     STATUS      current
     DESCRIPTION
       "
       Indicates the fax transmission mode.
       Options:
       1. thoroughly(1) -thoroughly transmission
       2. relay(2) -Relay mode
       Default: thoroughly(1)
       "
 -- DEFVAL      { {thoroughly(1)} }
     ::= { hwModemParaEntry 6 }

    hwModemRfc2198NegoMode OBJECT-TYPE
     SYNTAX      INTEGER{negoStart(1),         -- negotiate start
                         fixedStart(2),        -- fixed start
                         noInitiativeStart(3)  -- no initiative start
                         }
     MAX-ACCESS  read-write
     STATUS      deprecated
     DESCRIPTION
       "
       Use modem redundancy parameter or not.
       Options:
       1. negoStart(1) -negotiate start
       2. fixedStart(2) -fixed start
       3. noInitiativeStart(3) -no initiative start
       "
 -- DEFVAL      { {noInitiativeStart(3)} }
     ::= { hwModemParaEntry 7 }

    hwModemRfc2198StartMode OBJECT-TYPE
     SYNTAX      INTEGER{smart2198(1),   -- smart start 2198
                         ordinary2198(2) -- ordinary 2198
                         }
     MAX-ACCESS  read-write
     STATUS      deprecated
     DESCRIPTION
       "
       whether the modem support the RFC2198 Smart Startup.
       Options:
       1. smart2198(1) -smart 2198
       2. ordinary2198(2) -ordinary 2198
       "
 -- DEFVAL      { {ordinary2198(2)} }
     ::= { hwModemParaEntry 8 }

    hwModemParaVbdCodec OBJECT-TYPE
     SYNTAX      INTEGER{g711A(1),g711U(2)}
     MAX-ACCESS  read-write
     STATUS      current
     DESCRIPTION
       "
       Indicates the codec of VBD.
       Options:
       1. g711A(1) -G.711A
       2. g711U(2) -G.711U
       "
 -- DEFVAL      { {g711A(1)} }
     ::= { hwModemParaEntry 9 }

    hwModemParaVbdPtType OBJECT-TYPE
     SYNTAX      INTEGER{static(1),dynamic(2)}
     MAX-ACCESS  read-write
     STATUS      current
     DESCRIPTION
       "
       Indicates the payload type of VBD.
       Options:
       1. static(1) -static payload type
       2. dynamic(2) -dynamic payload type
       "
 -- DEFVAL      { {static(1)} }
     ::= { hwModemParaEntry 10 }

    hwModemTransEventType OBJECT-TYPE
     SYNTAX      INTEGER{negoStart(1),        -- negotiate start
                         fixedStart(2),       -- fixed start
                         noInitiativeStart(3) -- no initiative start
                         }
     MAX-ACCESS  read-write
     STATUS      deprecated
     DESCRIPTION
       "
       Indicates the mode of sending fax event, whether support the RFC2833.
       Options:
       1. negoStart(1) -negotiate start
       2. fixedStart(2) -fixed start
       3. noInitiativeStart(3) -no initiative start
       "
 -- DEFVAL      { {noInitiativeStart(3)} }
     ::= { hwModemParaEntry 11 }

    hwModemVbdAttributeType OBJECT-TYPE
     SYNTAX      INTEGER{v152(1),             -- V.152
                         chinatelecom(2),     -- chinatelecom
                         extchinatelecom(3),  -- extchinatelecom
                         ietf(4)
                         }
     MAX-ACCESS  read-write
     STATUS      current
     DESCRIPTION
       "
       Indicate the format of session attribute lines when starting modem VBD Negotiation.
       Options:
       1. v152(1) -V.152
       2. chinatelecom(2) -china telecom
       3. extchinatelecom(3) -extend china telecom
       4. ietf(4) -ietf
       "
 -- DEFVAL      { {v152(1)} }
     ::= { hwModemParaEntry 12 }

     hwModemRtpInterval OBJECT-TYPE
     SYNTAX      INTEGER{packettime5ms(1),packettime10ms(2),packettime20ms(3),packettime30ms(4)}
     MAX-ACCESS  read-write
     STATUS      current
     DESCRIPTION
       "
       Indicates the default RTP packet time of DSP channel.
       Options:
       1. packettime5ms(1)  -5ms
       2. packettime10ms(2) -10ms
       3. packettime20ms(3) -20ms
       4. packettime30ms(4) -30ms
       Unit: millisecond
       "
 -- DEFVAL      { {packettime10ms(2)} }
     ::= { hwModemParaEntry 13 }

     hwModemParaDtmfFallbackVoice OBJECT-TYPE
     SYNTAX      INTEGER{enable(1),disable(2)}
     MAX-ACCESS  read-write
     STATUS      current
     DESCRIPTION
       "
       Enable fallback to voice mode or not, when detect DTMF from IP side.
       Options:
       1. enable(1) -enable
       2. disable(2) -disable
       "
 -- DEFVAL      { {disable(2)} }
     ::= { hwModemParaEntry 14 }

   -- hwRfc2833Table (Parameter MIB table)--
    hwRfc2833Table OBJECT-TYPE
     SYNTAX      SEQUENCE OF HwRfc2833Entry
     MAX-ACCESS  not-accessible
     STATUS      current
     DESCRIPTION
       "
       This table is used to config the rfc2833 parameter.
       The index of this table is hwRfc2833VgwId.
       "
     ::= { hwVoipCommonObjects 3 }

   hwRfc2833Entry OBJECT-TYPE
     SYNTAX      HwRfc2833Entry
     MAX-ACCESS  not-accessible
     STATUS      current
     DESCRIPTION
       "
       This table is used to config the rfc2833 parameter.
       The index of this entry is hwRfc2833VgwId.
       "
     INDEX    {
                hwRfc2833VgwId
              }
     ::= { hwRfc2833Table 1 }

   HwRfc2833Entry ::=
     SEQUENCE
     {
       hwRfc2833VgwId       Integer32,
       hwRfc2833NegoMode    INTEGER,
       hwRfc2833FaxModem    INTEGER,
       hwRfc2833FlashHook   INTEGER,
       hwRfc2833Dtmf        INTEGER,
       hwRfcComplied 				INTEGER
     }

   hwRfc2833VgwId OBJECT-TYPE
     SYNTAX      Integer32(0..16777215)
     MAX-ACCESS  not-accessible
     STATUS      current
     DESCRIPTION
         "
         Indicates the interface ID.
         "
     ::= { hwRfc2833Entry 1 }


     hwRfc2833NegoMode OBJECT-TYPE
     SYNTAX      INTEGER{negoStart(1),        -- negotiate start
                         fixedStart(2),       -- fixed start
                         noInitiativeStart(3) -- no initiative start
                         }
     MAX-ACCESS  read-write
     STATUS      current
     DESCRIPTION
       "
       Indicates the start mode of the rfc2833.
       Options:
       1. negoStart(1) -negotiate start
       2. fixedStart(2) -fixed start
       3. noInitiativeStart(3) -no initiative start
       "
     -- DEFVAL      { {noInitiativeStart(3)} }
     ::= { hwRfc2833Entry 2 }

     hwRfc2833FaxModem OBJECT-TYPE
     SYNTAX      INTEGER{enable(1),disable(2)}
     MAX-ACCESS  read-write
     STATUS      current
     DESCRIPTION
      "
      Indicates the flag of fax and modem event using rfc2833 parameter.
      Options:
      1. enable(1) -enable
      2. disable(2) -disable
      Default: enable(1)
      "
     -- DEFVAL      { enable }
     ::= { hwRfc2833Entry 3 }

     hwRfc2833FlashHook OBJECT-TYPE
     SYNTAX      INTEGER{enable(1),disable(2)}
     MAX-ACCESS  read-write
     STATUS      current
     DESCRIPTION
      "
      Indicates the flag of flash hook event using rfc2833 parameter.
      Options:
      1. enable(1) -enable
      2. disable(2) -disable
      Default: disable(2)
      "
     -- DEFVAL      { disable }
     ::= { hwRfc2833Entry 4 }

     hwRfc2833Dtmf OBJECT-TYPE
     SYNTAX      INTEGER{enable(1),disable(2)}
     MAX-ACCESS  read-write
     STATUS      current
     DESCRIPTION
      "
      Indicates the flag of dtmf using rfc2833 parameter.
      Options:
      1. enable(1) -enable
      2. disable(2) -disable
      Default: enable(1)
      "
     -- DEFVAL      { enable }
     ::= { hwRfc2833Entry 5 }

     hwRfcComplied OBJECT-TYPE
     SYNTAX      INTEGER{rfc2833(1),rfc4733(2)}
     MAX-ACCESS  read-write
     STATUS      current
     DESCRIPTION
      "
      Indicates the type of RFC standard compliance.
      Options:
      1. rfc2833(1) - comply with RFC2833
      2. rfc4733(2) - comply with RFC4733
      Default: rfc2833(1)
      "
     -- DEFVAL      { rfc2833 }
     ::= { hwRfc2833Entry 6 }


   -- hwRfc2198Table (Parameter MIB table)--
    hwRfc2198Table OBJECT-TYPE
     SYNTAX      SEQUENCE OF HwRfc2198Entry
     MAX-ACCESS  not-accessible
     STATUS      current
     DESCRIPTION
       "
       This table is used to config the rfc2198 parameter.
       The index of this table is hwRfc2198VgwId.
       "
     ::= { hwVoipCommonObjects 4 }

   hwRfc2198Entry OBJECT-TYPE
     SYNTAX      HwRfc2198Entry
     MAX-ACCESS  not-accessible
     STATUS      current
     DESCRIPTION
       "
       This table is used to config the rfc2198 parameter.
       The index of this entry is hwRfc2198VgwId.
       "
     INDEX    {
                hwRfc2198VgwId
              }
     ::= { hwRfc2198Table 1 }

   HwRfc2198Entry ::=
     SEQUENCE
     {
       hwRfc2198VgwId           Integer32,
       hwRfc2198NegoMode        INTEGER,
       hwRfc2198StartMode       INTEGER,
       hwRfc2198Rfc2833         INTEGER,
       hwRfc2198Vbd             INTEGER,
       hwRfc2198Voice           INTEGER
     }

   hwRfc2198VgwId OBJECT-TYPE
     SYNTAX      Integer32(0..16777215)
     MAX-ACCESS  not-accessible
     STATUS      current
     DESCRIPTION
         "
         Indicates the interface ID.
         "
     ::= { hwRfc2198Entry 1 }


     hwRfc2198NegoMode OBJECT-TYPE
     SYNTAX      INTEGER{negoStart(1),        -- negotiate start
                         fixedStart(2),       -- fixed start
                         noInitiativeStart(3) -- no initiative start
                         }
     MAX-ACCESS  read-write
     STATUS      current
     DESCRIPTION
       "
       Indicates the start mode of the rfc2198.
       Options:
       1. negoStart(1)         -negotiate start
       2. fixedStart(2)        -fixed start
       3. noInitiativeStart(3) -no initiative start
       "
     -- DEFVAL      { {noInitiativeStart(3)} }
     ::= { hwRfc2198Entry 2 }

     hwRfc2198StartMode OBJECT-TYPE
     SYNTAX      INTEGER{smart2198(1),ordinary2198(2)}
     MAX-ACCESS  read-write
     STATUS      current
     DESCRIPTION
      "
      Indicates the start mode of the rfc2198.
      Options:
      1. smart2198(1) -smart start RFC2198
      2. ordinary2198(2) -start RFC2198 ordinary
      "
     -- DEFVAL      { {ordinary2198} }
     ::= { hwRfc2198Entry 3 }

     hwRfc2198Rfc2833 OBJECT-TYPE
     SYNTAX      INTEGER{enable(1),disable(2)}
     MAX-ACCESS  read-write
     STATUS      current
     DESCRIPTION
      "
      Indicates the flag of rfc2833 with using rfc2198.
      Options:
      1. enable(1) -enable
      2. disable(2) -disable
      Default: disable(2)
      "
     -- DEFVAL      { disable }
     ::= { hwRfc2198Entry 4 }

     hwRfc2198Vbd OBJECT-TYPE
     SYNTAX      INTEGER{enable(1),disable(2)}
     MAX-ACCESS  read-write
     STATUS      current
     DESCRIPTION
      "
      Indicates the flag of the VBD using rfc2198.
      Options:
      1. enable(1) -enable
      2. disable(2) -disable
      "
     -- DEFVAL      { {disable} }
     ::= { hwRfc2198Entry 5 }

     hwRfc2198Voice OBJECT-TYPE
     SYNTAX      INTEGER{enable(1),disable(2)}
     MAX-ACCESS  read-write
     STATUS      current
     DESCRIPTION
      "
      Indicates the flag of voice using rfc2198.
      Options:
      1. enable(1) -enable
      2. disable(2) -disable
      "
     -- DEFVAL      { {disable} }
     ::= { hwRfc2198Entry 6 }

  -- hwDtmfParaTable (Parameter MIB table)--
    hwDtmfParaTable OBJECT-TYPE
     SYNTAX      SEQUENCE OF HwDtmfParaEntry
     MAX-ACCESS  not-accessible
     STATUS      current
     DESCRIPTION
       "
       This table is used to config the dtmf parameter.
       The index of this table is hwDtmfVgwId.
       "
     ::= { hwVoipCommonObjects 5 }

   hwDtmfParaEntry OBJECT-TYPE
     SYNTAX      HwDtmfParaEntry
     MAX-ACCESS  not-accessible
     STATUS      current
     DESCRIPTION
       "
       This table is used to config the dtmf parameter.
       The index of this entry is hwDtmfVgwId.
       "
     INDEX    {
                hwDtmfVgwId
              }
     ::= { hwDtmfParaTable 1 }

   HwDtmfParaEntry ::=
     SEQUENCE
     {
       hwDtmfVgwId              Integer32,
       hwDtmfTransMode          INTEGER
     }

   hwDtmfVgwId OBJECT-TYPE
     SYNTAX      Integer32(0..16777215)
     MAX-ACCESS  not-accessible
     STATUS      current
     DESCRIPTION
         "
         Indicates the interface ID.
         "
     ::= { hwDtmfParaEntry 1 }


     hwDtmfTransMode OBJECT-TYPE
     SYNTAX      INTEGER{thoroughly(1),erase(2)}
     MAX-ACCESS  read-write
     STATUS      current
     DESCRIPTION
       "
      Indicates the transmission mode of DTMF.
      Options:
      1. thoroughly(1) -transparent transmission
      2. erase(2) -erase DTMF
      Default: thoroughly(1)
       "
     -- DEFVAL      { {thoroughly(1)} }
     ::= { hwDtmfParaEntry 2 }


 hwDtmfParametersTable OBJECT IDENTIFIER ::= {  hwIASVoipObjects 152  }

 hwDtmfTransfersMode OBJECT-TYPE
    SYNTAX      INTEGER { thoroughly(1),rfc2833(2),erase(3),rfc2833with2198(4) }
    MAX-ACCESS  read-write
    STATUS      current
    DESCRIPTION
      "
      Indicates the transmission mode of DTMF. If protocol is SIP please use hwDtmfTransMode.
      Options:
      1. thoroughly(1) -transparent transmission
      2. rfc2833(2) -2833 transmission
      3. erase(3) -erase DTMF
      4. rfc2833with2198(4) -2833with2198 (this value is currently used by H248)
      Default: thoroughly(1)
      "
    -- DEFVAL      { {thoroughly(1)} }
    ::= { hwDtmfParametersTable 1 }



hwMgDspOperateTable OBJECT-TYPE
     SYNTAX      SEQUENCE OF HwMgDspOperateEntry
     MAX-ACCESS  not-accessible
     STATUS      current
     DESCRIPTION
       "
       This table is used to config the operation of DSP channel.
       The index of this table is hwMgDspOperIndex.
       "
     ::= { hwIASVoipObjects 8 }

   hwMgDspOperateEntry OBJECT-TYPE
     SYNTAX      HwMgDspOperateEntry
     MAX-ACCESS  not-accessible
     STATUS      current
     DESCRIPTION
       "
       This table is used to config the operation of DSP channel.
       The index of this entry is hwMgDspOperIndex.
       "
     INDEX    {
               hwMgDspOperIndex
              }
     ::= { hwMgDspOperateTable 1 }

   HwMgDspOperateEntry ::=
     SEQUENCE
     {
       hwMgDspOperIndex	          Integer32,
       hwMgDspOperChannelState	  INTEGER,
       hwMgDspOperChannelWorkMode INTEGER,
       hwMgDspOperStateChange	  TimeTicks,
       hwMgDspOperAdminStatus	  INTEGER,
       hwMgDspJBInPerCent         Unsigned32
     }

   hwMgDspOperIndex OBJECT-TYPE
     SYNTAX      Integer32
     MAX-ACCESS  not-accessible
     STATUS      current
     DESCRIPTION
         "
         Indicates the shelf/slot/subboard/channel index.
         "
     ::= { hwMgDspOperateEntry 1 }

   hwMgDspOperChannelState OBJECT-TYPE
     SYNTAX      INTEGER{idle(1),g711(2),fault(3),probit(4),pcmLoopback(5),ipLoopback(6),all(7),wastage(8)}
     MAX-ACCESS  read-only
     STATUS      current
     DESCRIPTION
         "
         Indicates the channel status.
         Options:
         1. idle(1) -idle
         2. g711(2) -G.711
         3. fault(3) -faulty
         4. probit(4) -prohibited
         5. pcmLoopback(5) -PCM loopback
         6. ipLoopback(6) -IP loopback
         7. all(7) -full rate
         8. wastage(8) -wastage
         "
     ::= { hwMgDspOperateEntry 2 }

   hwMgDspOperChannelWorkMode OBJECT-TYPE
     SYNTAX      INTEGER{all(1),g711(2),wastage(3)}
     MAX-ACCESS  read-only
     STATUS      current
     DESCRIPTION
         "
         Indicates the channel status.
         The parameter is effective only when the channel status is busy.
         Options:
         1. all(1) -full rate
         2. g711(2) -G.711
         3. wastage(3) -wastage
         "
     ::= { hwMgDspOperateEntry 3 }

   hwMgDspOperStateChange OBJECT-TYPE
     SYNTAX      TimeTicks
     MAX-ACCESS  read-only
     STATUS      current
     DESCRIPTION
         "
         Indicates the channel status changing time.
         "
     ::= { hwMgDspOperateEntry 4 }

   hwMgDspOperAdminStatus OBJECT-TYPE
     SYNTAX      INTEGER{prohibit(1),unprohibit(2),pcmLoopback(3),ipLoopback(4),noLoopback(5)}
     MAX-ACCESS  read-write
     STATUS      current
     DESCRIPTION
         "
         Indicates the operation type.
         Options:
         1. prohibit(1) -prohibit
         2. unprohibit(2) -unprohibit
         3. pcmLoopback(3) -PCM loopback
         4. ipLoopback(4) -IP loopback
         5. noLoopback(5) -cancel loopback.
         "
     ::= { hwMgDspOperateEntry 5 }

   hwMgDspJBInPerCent OBJECT-TYPE
     SYNTAX      Unsigned32(0..100)
     MAX-ACCESS  read-only
     STATUS      current
     DESCRIPTION
         "
         Indicates the current fill level of the jitterbuffer in percent.
         "
     ::= { hwMgDspOperateEntry 6 }


hwMgDspStatisticsTable OBJECT-TYPE
     SYNTAX      SEQUENCE OF HwMgDspStatisticsEntry
     MAX-ACCESS  not-accessible
     STATUS      current
     DESCRIPTION
       "
       This table is used to query the DSP channel statistics.
       The index of this table is hwMgDspStatisticsIndex.
       "
     ::= { hwIASVoipObjects 9}

   hwMgDspStatisticsEntry OBJECT-TYPE
     SYNTAX      HwMgDspStatisticsEntry
     MAX-ACCESS  not-accessible
     STATUS      current
     DESCRIPTION
       "
       This table is used to query the DSP channel statistics.
       The index of this entry is hwMgDspStatisticsIndex.
       "
     INDEX    {
               hwMgDspStatisticsIndex
              }
     ::= { hwMgDspStatisticsTable 1 }

   HwMgDspStatisticsEntry ::=
     SEQUENCE
     {
       hwMgDspStatisticsIndex	        Integer32,
       hwMgDspStatisticsTotalNum	    Integer32,
       hwMgDspStatisticsFreeNum	        Integer32,
       hwMgDspStatisticsG711Num	        Integer32,
       hwMgDspStatisticsAllNum          Integer32,
       hwMgDspStatisticsWastageNum	    Integer32,
       hwMgDspStatisticsFaultNum        Integer32,
       hwMgDspStatisticsLoopNum	        Integer32,
       hwMgDspStatisticsForbiddenNum	Integer32,
       hwMgDspSystemReserved   	        Integer32
     }

   hwMgDspStatisticsIndex OBJECT-TYPE
     SYNTAX      Integer32
     MAX-ACCESS  not-accessible
     STATUS      current
     DESCRIPTION
         "
         Bits 31-26 (six bits): shelf index
         Bits 25-20 (six bits): slot index
         Bits 19-16 (four bits): subboard index
         Bits 15-0 (16 bits): all F
         When the index is all F, it indicates that the statistics of all the channels of the system are queried.
         "
      ::= { hwMgDspStatisticsEntry 1 }


   hwMgDspStatisticsTotalNum OBJECT-TYPE
     SYNTAX      Integer32
     MAX-ACCESS  read-only
     STATUS      current
     DESCRIPTION
         "
         Indicates the total number of DSP channels.
         "
     ::= { hwMgDspStatisticsEntry 2 }

   hwMgDspStatisticsFreeNum OBJECT-TYPE
     SYNTAX      Integer32
     MAX-ACCESS  read-only
     STATUS      current
     DESCRIPTION
         "
         Indicates the number of idle channels.
         "
     ::= { hwMgDspStatisticsEntry 3 }

   hwMgDspStatisticsG711Num OBJECT-TYPE
     SYNTAX      Integer32
     MAX-ACCESS  read-only
     STATUS      current
     DESCRIPTION
         "
         Indicates the number of occupied DSP channels of the G.711.
         "
     ::= { hwMgDspStatisticsEntry 4 }

   hwMgDspStatisticsAllNum OBJECT-TYPE
     SYNTAX      Integer32
     MAX-ACCESS  read-only
     STATUS      current
     DESCRIPTION
         "
         Indicates the number of occupied DSP channels of the full rate.
         "
     ::= { hwMgDspStatisticsEntry 5 }

   hwMgDspStatisticsWastageNum OBJECT-TYPE
     SYNTAX      Integer32
     MAX-ACCESS  read-only
     STATUS      current
     DESCRIPTION
         "
         Indicates the number of DSP channels of the wastage.
         "
     ::= { hwMgDspStatisticsEntry 6 }

   hwMgDspStatisticsFaultNum OBJECT-TYPE
     SYNTAX      Integer32
     MAX-ACCESS  read-only
     STATUS      current
     DESCRIPTION
         "
         Indicates the number of faulty DSP channels.
         "
     ::= { hwMgDspStatisticsEntry 7 }

   hwMgDspStatisticsLoopNum OBJECT-TYPE
     SYNTAX      Integer32
     MAX-ACCESS  read-only
     STATUS      current
     DESCRIPTION
         "
         Indicates the number of DSP channels in the loopback.
         "
     ::= { hwMgDspStatisticsEntry 8 }

   hwMgDspStatisticsForbiddenNum OBJECT-TYPE
     SYNTAX      Integer32
     MAX-ACCESS  read-only
     STATUS      current
     DESCRIPTION
         "
         Indicates the number of prohibited DSP channels.
         "
     ::= { hwMgDspStatisticsEntry 9 }

   hwMgDspSystemReserved OBJECT-TYPE
     SYNTAX      Integer32
     MAX-ACCESS  read-only
     STATUS      deprecated
     DESCRIPTION
         "
         Reserved for the system.
         "
     ::= { hwMgDspStatisticsEntry 10 }

 -- hwFaxParametersTable (Fax parameter MIB table)--
 hwFaxParametersTable OBJECT IDENTIFIER ::= {  hwIASVoipObjects 26  }

 hwFAXTransfersMode OBJECT-TYPE
    SYNTAX      INTEGER{thoroughly(1),selfT38(2),v3Flow(3),selfswitchThoroughly(4),v5Flow(5),selfSwitchT38(6)}
    MAX-ACCESS  read-write
    STATUS      deprecated
    DESCRIPTION
      "
      Indicates the fax transmission mode.
      Options:
      1. thoroughly(1) -transparent transmission
      2. selfT38(2) -auto-negotiation T.38
      3. v3Flow(3) -V3 flow
      4. selfswitchThoroughly(4) -stand-alone transparent transmission
      5. v5Flow(5) -V5 flow
      6. selfSwitchT38(6) -self-switch T.38.
      "
 -- DEFVAL      { {v5Flow(5)} }
    ::= { hwFaxParametersTable 1 }

 hwT38FaxPortAdd2OrNot OBJECT-TYPE
    SYNTAX      INTEGER{rtpPortAdd0(1), -- the udp port of FAX is as same as the voice's
                        rtpPortAdd2(2)  -- the udp port of FAX is the voice's add 2
                        }
    MAX-ACCESS  read-write
    STATUS      current
    DESCRIPTION
      "
      Indicates the T38 fax port.
      Options:
      1. rtpPortAdd0(1) -the udp port of FAX is as same as the voice's
      2. rtpPortAdd2(2) -the udp port of FAX is the voice's add 2
      "
 -- DEFVAL      { {rtpPortAdd0(1)} }
    ::= { hwFaxParametersTable 2 }


 hwFaxPacketInterval10msGlobal OBJECT-TYPE
     SYNTAX      INTEGER{enable(1),disable(2)}
     MAX-ACCESS  read-write
     STATUS      current
     DESCRIPTION
       "
       Enable packet interval of fax to use only 10ms or not.
       Options:
      1. enable(1) -enable
      2. disable(2) -disable
       "
 -- DEFVAL      { {disable} }
     ::= { hwFaxParametersTable 3 }

 hwFaxRFC2198 OBJECT-TYPE
    SYNTAX      Integer32(1..3)
    MAX-ACCESS  read-write
    STATUS      current
    DESCRIPTION
      "
      whether the fax support the RFC2198, 1:DisableRfc2198SmartStartup, 2:EnableRfc2198SmartStartup, 3: ImmediatelyStartupRFC2198
      "
 -- DEFVAL      { 1 }
    ::= { hwFaxParametersTable 4 }

 hwFaxNegotiateMode OBJECT-TYPE
     SYNTAX      INTEGER{selfswitch(1),    -- self switch
                         controledbyMGC(2) -- controled by MGC
                         }
     MAX-ACCESS  read-write
     STATUS      current
     DESCRIPTION
         "
         The negotiate mode of fax.
         Options:
         1. selfswitch(1) -self switch
         2. controledbyMGC(2) -controled by MGC
         "
 -- DEFVAL      { {controled by mGC(2)} }
     ::= { hwFaxParametersTable 5 }

 hwFaxFlow OBJECT-TYPE
     SYNTAX      INTEGER{v2(1),v3(2),v5(3)}
     MAX-ACCESS  read-write
     STATUS      current
     DESCRIPTION
         "
         The negotiate flow of fax.
         Options:
         1. v2(1) -Version 1
         2. v3(2) -Version 2
         3. v5(3) -Version 3
         "
 -- DEFVAL      { {v3(2)} }
     ::= { hwFaxParametersTable 6 }

 hwFaxWorkMode OBJECT-TYPE
     SYNTAX      INTEGER{thoroughly(1),  -- use voice codec
                         t38(2)          -- use T.38 codec
                         }
     MAX-ACCESS  read-write
     STATUS      current
     DESCRIPTION
         "
         Indicates the fax transmission mode.
         Options:
         1. thoroughly(1)   -use voice codec
         2. t38(2)          -use T.38 codec
         Default: thoroughly(1)
         "
 -- DEFVAL      { {thoroughly(1)} }
     ::= { hwFaxParametersTable 7 }

 hwFaxParametersVbdCodec OBJECT-TYPE
     SYNTAX      INTEGER{g711A(1),g711U(2)}
     MAX-ACCESS  read-write
     STATUS      current
     DESCRIPTION
       "
       Indicates the codec of VBD.
       Options:
       1. g711A(1) -G.711A
       2. g711U(2) -G.711U
       "
 -- DEFVAL      { {g711A(1)} }
     ::= { hwFaxParametersTable 8 }

 hwFaxParametersVbdPtType OBJECT-TYPE
     SYNTAX      INTEGER{static(1),dynamic(2)}
     MAX-ACCESS  read-write
     STATUS      current
     DESCRIPTION
       "
       Indicates the payload type of VBD.
       Options:
       1. static(1) -static payload type
       2. dynamic(2) -dynamic payload type
       "
 -- DEFVAL      { {static(1)} }
     ::= { hwFaxParametersTable 9 }

 hwFaxTransEvent OBJECT-TYPE
     SYNTAX      INTEGER{controlledbyMGC(1), -- controled by MGC
                         rfc2833(2)          -- use 2833
                         }
     MAX-ACCESS  read-write
     STATUS      current
     DESCRIPTION
       "
       Indicates the mode of sending fax event.
       In controlled_by_MGC scheme, sending fax event via 2833 depends on the signalling.
       In rfc2833 scheme, the device always sends the fax event via 2833.
       Options:
       1. controlledbyMGC(1) -controled by MGC
       2. rfc2833(2)         -use 2833
       "
 -- DEFVAL      { {controlledbyMGC(1)} }
     ::= { hwFaxParametersTable 10 }

-- hwModemParametersTable (Modem parameter MIB table)--
 hwModemParametersTable OBJECT IDENTIFIER ::= {  hwIASVoipObjects 27  }

 hwModemTransfersMode OBJECT-TYPE
    SYNTAX      INTEGER{thoroughly(1),relay(2)}
    MAX-ACCESS  read-write
    STATUS      current
    DESCRIPTION
      "
      Indicates the modem transmission mode.
      Options:
      1. thoroughly(1) -transparent transmission
      2. relay(2) -relay mode
      "
 -- DEFVAL      { {thoroughly(1)} }
    ::= { hwModemParametersTable 1 }

 hwModemEventMode OBJECT-TYPE
    SYNTAX      INTEGER{delay(1),direct(2),directforhigh-speedsignals(3)}
    MAX-ACCESS  read-write
    STATUS      current
    DESCRIPTION
      "
      Indicates the modem event report mode.
      Options:
      1. delay(1)-delay mode
      2. direct(2) -direct mode
      3. directforhigh-speedsignals(3) -direct for high-speed signals
      "
    ::= { hwModemParametersTable 2 }

 hwModemPacketInterval10msGlobal OBJECT-TYPE
    SYNTAX      INTEGER{enable(1),disable(2)}
    MAX-ACCESS  read-write
    STATUS      current
    DESCRIPTION
      "
      Enable packet interval of modem to use only 10ms or not.
      Options:
      1. enable(1) -enable
      2. disable(2) -disable
      "
 -- DEFVAL      { {disable} }
    ::= { hwModemParametersTable 3 }

 hwModemRFC2198 OBJECT-TYPE
    SYNTAX      Integer32(1..3)
    MAX-ACCESS  read-write
    STATUS      current
    DESCRIPTION
      "
      Whether the modem support RFC2198. 1:DisableRfc2198SmartStartup, 2:EnableRfc2198SmartStartup, 3: ImmediatelyStartupRFC2198
      "
 -- DEFVAL      { 1 }
    ::= { hwModemParametersTable 4 }

 hwModemNegotiateMode OBJECT-TYPE
    SYNTAX      INTEGER{selfswitch(1),    -- self switch
                        controledbyMGC(2) -- controled by MGC
                        }
    MAX-ACCESS  read-write
    STATUS      current
    DESCRIPTION
      "
      The negotiate mode of modem.
      Options:
      1. selfswitch(1) -self switch
      2. controledbyMGC(2) -controled by MGC
      "
 -- DEFVAL      { {controledbyMGC(2)} }
    ::= { hwModemParametersTable 5 }

  hwModemParametersVbdCodec OBJECT-TYPE
     SYNTAX      INTEGER{g711A(1),g711U(2)}
     MAX-ACCESS  read-write
     STATUS      current
     DESCRIPTION
       "
       Indicates the codec of VBD.
       Options:
       1. g711A(1) -G.711A
       2. g711U(2) -G.711U
       "
 -- DEFVAL      { {g711A(1)} }
     ::= { hwModemParametersTable 6 }

 hwModemParametersVbdPtType OBJECT-TYPE
     SYNTAX      INTEGER{static(1),dynamic(2)}
     MAX-ACCESS  read-write
     STATUS      current
     DESCRIPTION
       "
       Indicates the payload type of VBD.
       Options:
       1. static(1) -static payload type
       2. dynamic(2) -dynamic payload type
       "
 -- DEFVAL      { {static(1)} }
     ::= { hwModemParametersTable 7 }

 hwModemTransEvent OBJECT-TYPE
    SYNTAX      INTEGER{controlledbyMGC(1), -- controlled by MGC
                        rfc2833(2)          -- use 2833
                        }
    MAX-ACCESS  read-write
    STATUS      current
    DESCRIPTION
      "
      Indicates the mode of sending modem event.
      In controlled_by_MGC scheme, sending modem event via 2833 depends on the signalling.
      In rfc2833 scheme, the device always sends the modem event via 2833.
      Options:
      1. controlledbyMGC(1) -controlled by MGC
      2. rfc2833(2)         -use 2833
      "
 -- DEFVAL      { {controlledbyMGC(1)} }
    ::= { hwModemParametersTable 8 }

 hwModemDtmfFallbackVoice OBJECT-TYPE
    SYNTAX      INTEGER{enable(1),disable(2)}
    MAX-ACCESS  read-write
    STATUS      current
    DESCRIPTION
      "
      Enable fallback to voice mode or not, when detect DTMF from IP side.
      Options:
      1. enable(1) -enable
      2. disable(2) -disable
      "
 -- DEFVAL      { {disable(2)} }
    ::= { hwModemParametersTable 9 }

   hwMgDspWorkModeTable OBJECT IDENTIFIER ::= { hwIASVoipObjects 33 }

   hwMgDspMode   OBJECT-TYPE
     SYNTAX      Integer32(1..7)
     MAX-ACCESS  read-write
     STATUS      current
     DESCRIPTION
         "
         Indicates the value of the working mode of the DSP channel. 0-0% full rate; 1-10% full rate; 2-20% full rate; 3-30% full rate; 4-40% full rate; 5-50% full rate; 6-100% full rate.
         Default: 6
         "
      ::= { hwMgDspWorkModeTable 1 }

 -- hwBandwidthParaTable (Parameter MIB table)--
 hwBandwidthParaTable OBJECT IDENTIFIER ::= {  hwIASVoipObjects 35  }

        --(Corresponding command line) upward-bandwidth support <yes,no> --
        --(Corresponding command line) upward-bandwidth { max max-upward-bandwidth | reversed reversed-bandwidth }*--

  hwBandwidthSupport OBJECT-TYPE
    SYNTAX      INTEGER{yes(1), no(2)}
    MAX-ACCESS  read-write
    STATUS      current
    DESCRIPTION
      "
      Indicates whether the MG restricts calls in case of insufficient bandwidth.
      Options:
      1. yes(1) -support
      2. no(2)  -not support
      "
 -- DEFVAL      { 2 }
         ::= { hwBandwidthParaTable 1 }

  hwBandwidthMax OBJECT-TYPE
    SYNTAX      Integer32(2..1000)
    MAX-ACCESS  read-write
    STATUS      current
    DESCRIPTION
      "
      Indicates the value of the maximum upstream bandwidth.
      Unit: 100 kbs
      "
 -- DEFVAL      { 1000 }
         ::= { hwBandwidthParaTable 2 }

  hwBandwidthReserved OBJECT-TYPE
    SYNTAX      Integer32(1..999)
    MAX-ACCESS  read-write
    STATUS      current
    DESCRIPTION
      "
      Indicates the value of the bandwidth reserved for emergency calls (%).
      Unit: 100 kbit/s
      "
 -- DEFVAL      { 10 }
    ::= { hwBandwidthParaTable 3 }

 --  hwUserStatisticTable parameters--
    hwUserStatisticTable OBJECT-TYPE
     SYNTAX      SEQUENCE OF HwUserStatisticEntry
     MAX-ACCESS  not-accessible
     STATUS      current
     DESCRIPTION
       "
       This table is used to query the statistics of online subscribers.
       The index of this table is hwUserStatisticMgId.
       "
     ::= { hwIASVoipObjects 36 }

   hwUserStatisticEntry OBJECT-TYPE
     SYNTAX      HwUserStatisticEntry
     MAX-ACCESS  not-accessible
     STATUS      current
     DESCRIPTION
       "
       This table is used to query the statistics of online subscribers.
       The index of this entry is hwUserStatisticMgId.
       "
     INDEX    {
               hwUserStatisticMgId
              }
     ::= { hwUserStatisticTable 1 }

   HwUserStatisticEntry ::=
     SEQUENCE
     {
       hwUserStatisticMgId	   Integer32,
       hwUserStatisticPstn     Integer32,
       hwUserStatisticFax      Integer32,
       hwUserStatisticModem    Integer32,
       hwUserStatisticBra     Integer32,
       hwUserStatisticPra      Integer32,
       hwUserStatisticDpnss    Integer32,
       hwUserStatisticDass2      Integer32,
       hwUserStatisticR2    Integer32
     }

   hwUserStatisticMgId OBJECT-TYPE
     SYNTAX      Integer32(0..16777215)
     MAX-ACCESS  not-accessible
     STATUS      current
     DESCRIPTION
         "
         Indicates the MG ID.
         "
     ::= { hwUserStatisticEntry 1 }

   hwUserStatisticPstn OBJECT-TYPE
     SYNTAX      Integer32
     MAX-ACCESS  read-only
     STATUS      current
     DESCRIPTION
         "
         Indicates the count of online PSTN subscribers.
         "
     ::= { hwUserStatisticEntry 2 }

   hwUserStatisticFax OBJECT-TYPE
     SYNTAX      Integer32
     MAX-ACCESS  read-only
     STATUS      current
     DESCRIPTION
         "
         Indicates the count of online fax subscribers.
         "
     ::= { hwUserStatisticEntry 3 }

   hwUserStatisticModem OBJECT-TYPE
     SYNTAX      Integer32
     MAX-ACCESS  read-only
     STATUS      current
     DESCRIPTION
         "
         Indicates the count of online modem subscribers.
         "
     ::= { hwUserStatisticEntry 4 }

   hwUserStatisticBra OBJECT-TYPE
     SYNTAX      Integer32
     MAX-ACCESS  read-only
     STATUS      current
     DESCRIPTION
         "
         Indicates the count of online BRA subscribers.
         "
     ::= { hwUserStatisticEntry 5 }

   hwUserStatisticPra OBJECT-TYPE
     SYNTAX      Integer32
     MAX-ACCESS  read-only
     STATUS      current
     DESCRIPTION
         "
         Indicates the count of online PRA subscribers.
         "
     ::= { hwUserStatisticEntry 6 }

   hwUserStatisticDpnss OBJECT-TYPE
     SYNTAX      Integer32
     MAX-ACCESS  read-only
     STATUS      current
     DESCRIPTION
         "
         Indicates the count of online DPNSS subscribers.
         "
     ::= { hwUserStatisticEntry 7 }

   hwUserStatisticDass2 OBJECT-TYPE
     SYNTAX      Integer32
     MAX-ACCESS  read-only
     STATUS      current
     DESCRIPTION
         "
         Indicates the count of online DASS2 subscribers.
         "
     ::= { hwUserStatisticEntry 8 }

   hwUserStatisticR2 OBJECT-TYPE
     SYNTAX      Integer32
     MAX-ACCESS  read-only
     STATUS      current
     DESCRIPTION
         "
         Indicates the count of online R2 subscribers.
         "
     ::= { hwUserStatisticEntry 9 }

-- END: modified by wuguowang 20050722 FOR BT VAG




   hwE2ETraceTaskTable OBJECT-TYPE
     SYNTAX      SEQUENCE OF HwE2ETraceTaskEntry
     MAX-ACCESS  not-accessible
     STATUS      current
     DESCRIPTION
       "
       This table is used to config the E2E tracing task.
       The index of this table is hwE2ETraceTaskID.
       "
     ::= { hwIASVoipObjects 45 }

   hwE2ETraceTaskEntry OBJECT-TYPE
     SYNTAX      HwE2ETraceTaskEntry
     MAX-ACCESS  not-accessible
     STATUS      current
     DESCRIPTION
       "
       This table is used to config the E2E tracing task.
       The index of this entry is hwE2ETraceTaskID.
       "
     INDEX    {
               hwE2ETraceTaskID
              }
     ::= { hwE2ETraceTaskTable 1 }

   HwE2ETraceTaskEntry ::=
     SEQUENCE
     {
       hwE2ETraceTaskID	           Integer32,
       hwE2ETraceTaskOperType	   INTEGER,
       hwE2ETraceTaskSessionID	   Integer32,
       hwE2ETraceTaskMsgReptCyc    Integer32,
       hwE2ETraceTaskChkCyc        Integer32,
       hwE2ETraceTaskMsgType       INTEGER,
       hwE2ETraceTaskFTPLnkState   INTEGER,
       hwE2ETraceTaskURLInfoPort   Integer32,
       hwE2ETraceTaskURLInfoIP           IpAddress,
       hwE2ETraceTaskURLInfoPath         OCTET STRING,
       hwE2ETraceTaskURLInfoFileName     OCTET STRING,
       hwE2ETraceTaskUserMgID                Integer32,
       hwE2ETraceTaskUserTerminationID       OCTET STRING
     }

   hwE2ETraceTaskID OBJECT-TYPE
     SYNTAX      Integer32(0..2147483647)
     MAX-ACCESS  not-accessible
     STATUS      current
     DESCRIPTION
         "
         Indicates the tracing task ID.
         Bit 31 (1 bit): 0
         Bit 30 (1 bit): the protocol type (1-H.248; 0-MGCP)
         Bits 29-16 (14 bits): the terminal ID
         Bits 15-0 (16 bits): the RID that is delivered by the softswitch
         "
     ::= { hwE2ETraceTaskEntry 1 }

   hwE2ETraceTaskOperType OBJECT-TYPE
     SYNTAX      INTEGER{delete(1)}
     MAX-ACCESS  read-write
     STATUS      current
     DESCRIPTION
         "
         Indicates the operation type.
         Options:
         1. delete(1) -delete
         "
     ::= { hwE2ETraceTaskEntry 2 }

   hwE2ETraceTaskSessionID OBJECT-TYPE
     SYNTAX      Integer32(0..4294967295)
     MAX-ACCESS  read-only
     STATUS      current
     DESCRIPTION
         "
         Indicates the session ID.
         "
     ::= { hwE2ETraceTaskEntry 3 }

   hwE2ETraceTaskMsgReptCyc OBJECT-TYPE
     SYNTAX      Integer32(30..4294967295)
     MAX-ACCESS  read-only
     STATUS      current
     DESCRIPTION
         "
         Indicates the message reporting period.
         "
     ::= { hwE2ETraceTaskEntry 4 }

   hwE2ETraceTaskChkCyc OBJECT-TYPE
     SYNTAX      Integer32(30..4294967295)
     MAX-ACCESS  read-only
     STATUS      current
     DESCRIPTION
         "
         Indicates the task checking period.
         "
     ::= { hwE2ETraceTaskEntry 5 }

   hwE2ETraceTaskMsgType OBJECT-TYPE
     SYNTAX      INTEGER{ h248(24), mgcp(25) }
     MAX-ACCESS  read-only
     STATUS      current
     DESCRIPTION
         "
         Indicates the message type.
         Options:
         1. h248(24) -H.248
         2. mgcp(25) -MGCP
         "
     ::= { hwE2ETraceTaskEntry 6 }

   hwE2ETraceTaskFTPLnkState OBJECT-TYPE
     SYNTAX      INTEGER{establishing(0),data(1),trying(2),releasing(3),idle(4)}
     MAX-ACCESS  read-only
     STATUS      current
     DESCRIPTION
         "
         Indicates the FTP connection status.
         Options:
         1. establishing(0) -establishing
         2. data(1) -transfering data
         3. trying(2) -trying
         4. releasing(3) -releasing
         5. idle(4) -idle
         "
     ::= { hwE2ETraceTaskEntry 7 }

    hwE2ETraceTaskURLInfoPort OBJECT-TYPE
     SYNTAX      Integer32(0..65535)
     MAX-ACCESS  read-only
     STATUS      current
     DESCRIPTION
         "
         Indicates the port number of the URL message.
         "
     ::= { hwE2ETraceTaskEntry 8 }

   hwE2ETraceTaskURLInfoIP OBJECT-TYPE
     SYNTAX      IpAddress
     MAX-ACCESS  read-only
     STATUS      current
     DESCRIPTION
         "
         Indicates the IP address of the URL message.
         "
     ::= { hwE2ETraceTaskEntry 9 }

   hwE2ETraceTaskURLInfoPath OBJECT-TYPE
     SYNTAX      OCTET STRING(SIZE (1..256))
     MAX-ACCESS  read-only
     STATUS      current
     DESCRIPTION
         "
         Indicates the path of the URL message.
         "
     ::= { hwE2ETraceTaskEntry 10 }

   hwE2ETraceTaskURLInfoFileName OBJECT-TYPE
     SYNTAX      OCTET STRING(SIZE (1..128))
     MAX-ACCESS  read-only
     STATUS      current
     DESCRIPTION
         "
         Indicates the file name of the URL message.
         "
     ::= { hwE2ETraceTaskEntry 11 }

   hwE2ETraceTaskUserMgID OBJECT-TYPE
     SYNTAX      Integer32(0..16777215)
     MAX-ACCESS  read-only
     STATUS      current
     DESCRIPTION
         "
         Indicates the interface ID of the subscriber traced by the tracing task.
         "
     ::= { hwE2ETraceTaskEntry 12 }

   hwE2ETraceTaskUserTerminationID OBJECT-TYPE
     SYNTAX      OCTET STRING(SIZE (1..64))
     MAX-ACCESS  read-only
     STATUS      current
     DESCRIPTION
         "
         Indicates the terminal ID of the tracing task subscriber.
         "
     ::= { hwE2ETraceTaskEntry 13 }


   hwE2ETraceTaskAttrTable OBJECT IDENTIFIER ::= {  hwIASVoipObjects 46  }


   hwE2ETraceTaskAttrTimerLgth OBJECT-TYPE
    SYNTAX      Integer32(0..1800)
    MAX-ACCESS  read-write
    STATUS      current
    DESCRIPTION
      "
      Indicates the value of the tracing task attribute, that is, the timer for reporting the null message.
      Default: 60
      Unit: second
      "
    ::= { hwE2ETraceTaskAttrTable 1 }


--QoS alarm threshold parameter table
hwQosThresholdTable OBJECT IDENTIFIER ::= {  hwIASVoipObjects 59  }

  hwQosThresholdJitter OBJECT-TYPE
    SYNTAX      Integer32(0..1000)
    MAX-ACCESS  read-write
    STATUS      current
    DESCRIPTION
      "Indicates the jitter alarm threshold.
      Unit: millisecond
      "
 -- DEFVAL      { 60 }
         ::= { hwQosThresholdTable 1 }

  hwQosThresholdLoopdelay OBJECT-TYPE
    SYNTAX      Integer32(0..5000)
    MAX-ACCESS  read-write
    STATUS      current
    DESCRIPTION
      "Indicates the loop delay alarm threshold.
      Unit: millisecond
      "
 -- DEFVAL      { 400 }
         ::= { hwQosThresholdTable 2 }

  hwQosThresholdPacketlost OBJECT-TYPE
    SYNTAX      Integer32(0..100)
    MAX-ACCESS  read-write
    STATUS      current
    DESCRIPTION
      "
      Indicates the packet loss rate alarm threshold.
      Unit: 1/100.
      "
 -- DEFVAL      { 5 }
    ::= { hwQosThresholdTable 3 }



--TID Profile Optimization-START-
   hwTidTemplateConfigTable OBJECT-TYPE
     SYNTAX      SEQUENCE OF HwTidTemplateConfigEntry
     MAX-ACCESS  not-accessible
     STATUS      current
     DESCRIPTION
       "
       This table is used to config terminal ID template.
       The index of this table is hwTidTemplateId.
       "
     ::= { hwIASVoipObjects 65 }

   hwTidTemplateConfigEntry OBJECT-TYPE
     SYNTAX      HwTidTemplateConfigEntry
     MAX-ACCESS  not-accessible
     STATUS      current
     DESCRIPTION
       "
       This table is used to config terminal ID template.
       The index of this entry is hwTidTemplateId.
       "
     INDEX    {
               hwTidTemplateId
              }
     ::= { hwTidTemplateConfigTable 1 }

   HwTidTemplateConfigEntry ::=
     SEQUENCE
     {
       hwTidTemplateId	              Integer32,
       hwTidFormat	              OCTET STRING,
       hwTidParameterlist 	      OCTET STRING,
       hwTidTemplateName              OCTET STRING,
       hwTidTemplateRowStatus	      RowStatus,
       hwIsNeedToConfigTID            INTEGER
     }

   hwTidTemplateId OBJECT-TYPE
     SYNTAX      Integer32(0..63)
     MAX-ACCESS  not-accessible
     STATUS      current
     DESCRIPTION
         "
         Indicates the TID profile index.
         TID profiles 0-18 are the default profiles in the system. The default TID profiles can be referenced but can not be added, modified or deleted.
         TID profiles 19-31 are reserved in the system and are not displayed in the query result.
         TID profiles 32-63 are user-defined profiles and can be added, modified or deleted.
         "
     ::= { hwTidTemplateConfigEntry 1 }

   hwTidFormat OBJECT-TYPE
     SYNTAX      OCTET STRING(SIZE (2..64))
     MAX-ACCESS  read-write
     STATUS      current
     DESCRIPTION
         "
         Indicates the format string of the TID profile.
         "
     ::= { hwTidTemplateConfigEntry 2 }

   hwTidParameterlist OBJECT-TYPE
     SYNTAX      OCTET STRING(SIZE (1..64))
     MAX-ACCESS  read-write
     STATUS      current
     DESCRIPTION
         "
         Indicates the parameter list of the TID profile.
         "
     ::= { hwTidTemplateConfigEntry 3 }

   hwTidTemplateName OBJECT-TYPE
     SYNTAX      OCTET STRING(SIZE (1..32))
     MAX-ACCESS  read-write
     STATUS      current
     DESCRIPTION
         "
         Indicates the TID profile name. The profile name must be unique.
         "
     ::= { hwTidTemplateConfigEntry 4 }

   hwTidTemplateRowStatus OBJECT-TYPE
     SYNTAX      RowStatus
     MAX-ACCESS  read-write
     STATUS      current
     DESCRIPTION
         "
         Indicates the row status of the TID profile. Profiles 0-31 cannot be added, deleted, or modified.
         "
     ::= { hwTidTemplateConfigEntry 5 }

   hwIsNeedToConfigTID OBJECT-TYPE
     SYNTAX      INTEGER{no(1),yes(2)}
     MAX-ACCESS  read-only
     STATUS      current
     DESCRIPTION
         "
         Indicates whether the TID needs to be input when adding the subscriber who uses this profile.
         Options:
         1. no(1)  -TID needs not to be input when adding the subscriber
         2. yes(2) -TID must be input when adding the subscriber
         "
     ::= { hwTidTemplateConfigEntry 6 }
--TID profile optimization-END-Add by z66308


  hwClipParametersCfgTable OBJECT IDENTIFIER ::= {  hwIASVoipObjects 62  }

  hwOnHookDualToneAlertLevel OBJECT-TYPE
    SYNTAX      Integer32(1..16)
    MAX-ACCESS  read-write
    STATUS      current
    DESCRIPTION
      "
      Power of Dual Tone Alert in onhook state.
      Support 16 electric:
      1: -5.5dBm0, 2: -6.5dBm0, 3: -7.5dBm0, 4: -8.5dBm0, 5: -9.5dBm0, 6: -10.5dBm0
      7: -11.5dBm0, 8: -12.5dBm0, 9: -13.5dBm0, 10: -14.5dBm0, 11: -15.5dBm0, 12: -16.5dBm0
      13: -17.5dBm0, 14: -18.5dBm0, 15: -19.5dBm0, 16: -20.5dBm0
      "
 -- DEFVAL      { 4 }
         ::= { hwClipParametersCfgTable 1 }

  hwOnHookFSKLevel OBJECT-TYPE
    SYNTAX      Integer32(1..16)
    MAX-ACCESS  read-write
    STATUS      current
    DESCRIPTION
      "
      Power of FSK level in onhook state.
      Support 16 electric:
      1: -5.5dBm0, 2: -6.5dBm0, 3: -7.5dBm0, 4: -8.5dBm0, 5: -9.5dBm0, 6: -10.5dBm0
      7: -11.5dBm0, 8: -12.5dBm0, 9: -13.5dBm0, 10: -14.5dBm0, 11: -15.5dBm0, 12: -16.5dBm0
      13: -17.5dBm0, 14: -18.5dBm0, 15: -19.5dBm0, 16: -20.5dBm0
      "
 -- DEFVAL      { 4 }
         ::= { hwClipParametersCfgTable 2 }

  hwOffHookDualToneAlertLevel OBJECT-TYPE
    SYNTAX      Integer32(1..16)
    MAX-ACCESS  read-write
    STATUS      current
    DESCRIPTION
      "
      Power of Dual Tone Alert in offhook state.
      Support 16 electric:
      1: -5.5dBm0, 2: -6.5dBm0, 3: -7.5dBm0, 4: -8.5dBm0, 5: -9.5dBm0, 6: -10.5dBm0
      7: -11.5dBm0, 8: -12.5dBm0, 9: -13.5dBm0, 10: -14.5dBm0, 11: -15.5dBm0, 12: -16.5dBm0
      13: -17.5dBm0, 14: -18.5dBm0, 15: -19.5dBm0, 16: -20.5dBm0
      "
 -- DEFVAL      { 11 }
    ::= { hwClipParametersCfgTable 3 }

  hwOffHookFSKLevel OBJECT-TYPE
    SYNTAX      Integer32(1..16)
    MAX-ACCESS  read-write
    STATUS      current
    DESCRIPTION
      "
      Power of FSK level in offhook state.
      Support 16 electric:
      1: -5.5dBm0, 2: -6.5dBm0, 3: -7.5dBm0, 4: -8.5dBm0, 5: -9.5dBm0, 6: -10.5dBm0
      7: -11.5dBm0, 8: -12.5dBm0, 9: -13.5dBm0, 10: -14.5dBm0, 11: -15.5dBm0, 12: -16.5dBm0
      13: -17.5dBm0, 14: -18.5dBm0, 15: -19.5dBm0, 16: -20.5dBm0
      "
  -- DEFVAL      { 4 }
    ::= { hwClipParametersCfgTable 4 }

  hwOnHookChnSeizure OBJECT-TYPE
    SYNTAX      Integer32(0..1000)
    MAX-ACCESS  read-write
    STATUS      current
    DESCRIPTION
      "
      Channel seize bits for onhook FSK.
      "
  -- DEFVAL      { 300 }
    ::= { hwClipParametersCfgTable 5 }

  hwOnHookMarkSignal OBJECT-TYPE
    SYNTAX      Integer32(0..1000)
    MAX-ACCESS  read-write
    STATUS      current
    DESCRIPTION
      "
      Mark signal for onhook FSK.
      "
  -- DEFVAL      { 180 }
    ::= { hwClipParametersCfgTable 6 }

  hwOnHookSendFskInterval OBJECT-TYPE
    SYNTAX      Integer32(0..1000)
    MAX-ACCESS  read-write
    STATUS      current
    DESCRIPTION
      "
      The interval between DT-AS and FSK when onhook.
      Unit:  millisecond.
      "
  -- DEFVAL      { 250 }
    ::= { hwClipParametersCfgTable 7 }

  hwOnHookDtAsDur OBJECT-TYPE
    SYNTAX      Integer32(0..1000)
    MAX-ACCESS  read-write
    STATUS      current
    DESCRIPTION
      "
      The duration for DT-AS when onhook.
      Unit:  millisecond.
      "
  -- DEFVAL      { 100 }
    ::= { hwClipParametersCfgTable 8 }

  hwOffHookMarkSignal OBJECT-TYPE
    SYNTAX      Integer32(0..1000)
    MAX-ACCESS  read-write
    STATUS      current
    DESCRIPTION
      "
      Mark signal for offhook FSK.
      "
  -- DEFVAL      { 80 }
    ::= { hwClipParametersCfgTable 9 }

  hwOffHookDetectTeAckInterval OBJECT-TYPE
    SYNTAX      Integer32(0..1000)
    MAX-ACCESS  read-write
    STATUS      current
    DESCRIPTION
      "
      The interval between DT-AS and detecting terminal ack when offhook.
      "
  -- DEFVAL      { 80 }
    ::= { hwClipParametersCfgTable 10 }

  hwOffHookSendFskInterval OBJECT-TYPE
    SYNTAX      Integer32(0..1000)
    MAX-ACCESS  read-write
    STATUS      current
    DESCRIPTION
      "
      The interval between detecting terminal ack and sending FSK when offhook.
      Unit:  millisecond.
      "
  -- DEFVAL      { 50 }
    ::= { hwClipParametersCfgTable 11 }

  hwOffHookDtAsDur OBJECT-TYPE
    SYNTAX      Integer32(0..1000)
    MAX-ACCESS  read-write
    STATUS      current
    DESCRIPTION
      "
      The duration for DT-AS when offhook.
      Unit:  millisecond.
      "
  -- DEFVAL      { 80 }
    ::= { hwClipParametersCfgTable 12 }

  hwOnHookDtmfNumStartCode OBJECT-TYPE
    SYNTAX      Integer32(12..15)
    MAX-ACCESS  read-write
    STATUS      current
    DESCRIPTION
      "
      The DTMF number start code.
      12(A)
      13(B)
      14(C)
      15(D)
      "
  -- DEFVAL      { 15 }
    ::= { hwClipParametersCfgTable 13 }


   hwServiceNumCfgTable OBJECT-TYPE
     SYNTAX      SEQUENCE OF HwServiceNumCfgEntry
     MAX-ACCESS  not-accessible
     STATUS      current
     DESCRIPTION
       "
       This table is used to config the binding between service number and DSP parameters template.
       The index of this table is hwServiceNumMap.
       "
     ::= { hwIASVoipObjects 154 }

   hwServiceNumCfgEntry OBJECT-TYPE
     SYNTAX      HwServiceNumCfgEntry
     MAX-ACCESS  not-accessible
     STATUS      current
     DESCRIPTION
       "
       This table is used to config the binding between service number and DSP parameters template.
       The index of this entry is hwServiceNumMap.
       "
     INDEX    {
               hwServiceNumMap
              }
     ::= { hwServiceNumCfgTable 1 }

   HwServiceNumCfgEntry ::=
     SEQUENCE
     {
       hwServiceNumMap  	OCTET STRING,
       hwDspParaTemplateName	OCTET STRING,
       hwServiceNumRowStatus    RowStatus
     }

   hwServiceNumMap OBJECT-TYPE
     SYNTAX      OCTET STRING(SIZE(1..64))
     MAX-ACCESS  not-accessible
     STATUS      current
     DESCRIPTION
         "
         Indicates the service number digital map.
         "
     ::= { hwServiceNumCfgEntry 1 }

   hwDspParaTemplateName OBJECT-TYPE
     SYNTAX      OCTET STRING(SIZE(1..31))
     MAX-ACCESS  read-write
     STATUS      current
     DESCRIPTION
         "
         Indicates the dsp parameters template name
         "
     ::= { hwServiceNumCfgEntry 2 }

  hwServiceNumRowStatus OBJECT-TYPE
     SYNTAX      RowStatus
     MAX-ACCESS  read-write
     STATUS      current
     DESCRIPTION
         "
         Indicates the row status.
         "
     ::= { hwServiceNumCfgEntry 3 }


   hwDspParaTemplateCfgTable OBJECT-TYPE
     SYNTAX      SEQUENCE OF HwDspParaTemplateCfgEntry
     MAX-ACCESS  not-accessible
     STATUS      current
     DESCRIPTION
       "
       This table is used to config the dsp parameters template.
       The index of this table is hwDspTemplateName.
       "
     ::= { hwIASVoipObjects 155 }

   hwDspParaTemplateCfgEntry OBJECT-TYPE
     SYNTAX      HwDspParaTemplateCfgEntry
     MAX-ACCESS  not-accessible
     STATUS      current
     DESCRIPTION
       "
       This table is used to config the dsp parameters template.
       The index of this entry is hwDspTemplateName.
       "
     INDEX    {
               hwDspTemplateName
              }
     ::= { hwDspParaTemplateCfgTable 1 }

   HwDspParaTemplateCfgEntry ::=
     SEQUENCE
     {
       hwDspTemplateName  	     OCTET STRING,
       hwDspEc                       INTEGER,
       hwDspJbMode                   INTEGER,
       hwDspNlp                      INTEGER,
       hwDspWorkMode                 INTEGER,
       hwDspSc                       INTEGER,
       hwDspTemplateRowStatus        RowStatus,
       hwDspInputGain                Integer32,
       hwDspOutputGain               Integer32,
       hwDspDtmfPara                 INTEGER,
       hwDsp2833ForDataevent         INTEGER,
       hwDspSpecialFlow              Integer32,
       hwDsp2198ForVbd               INTEGER,
       hwDspTemplateFixedJbUpImmediately INTEGER,
       hwDsp2198ForVoice             INTEGER
     }

   hwDspTemplateName OBJECT-TYPE
     SYNTAX      OCTET STRING(SIZE(1..31))
     MAX-ACCESS  not-accessible
     STATUS      current
     DESCRIPTION
         "
         Indicates the dsp parameters template name.
         "
     ::= { hwDspParaTemplateCfgEntry 1 }

  hwDspEc OBJECT-TYPE
     SYNTAX      INTEGER{open(1),close(2),invalid(256)}
     MAX-ACCESS  read-write
     STATUS      current
     DESCRIPTION
         "
         Indicates the echo cotrol.
         Options:
         1. open(1) -open
         2. close(2) -close
         3. invalid(256) -invalid value, use global config
         Default: invalid(256)
         "
     ::= { hwDspParaTemplateCfgEntry 2 }

  hwDspJbMode OBJECT-TYPE
     SYNTAX      INTEGER{adapted(1),fixed(2),invalid(256)}
     MAX-ACCESS  read-write
     STATUS      current
     DESCRIPTION
         "
         Indicates the jitterbuffer mode.
         Options:
         1. adapted(1) -adapted mode
         2. fixed(2) -fixed mode
         3. invalid(256) -invalid value, use global config
         Default: invalid(256)
         "
     ::= { hwDspParaTemplateCfgEntry 3 }

  hwDspNlp OBJECT-TYPE
     SYNTAX      INTEGER{close(1),normal(2),enhanced(3),reduced(4),ecgain(5),dtmfec(6),invalid(256)}
     MAX-ACCESS  read-write
     STATUS      current
     DESCRIPTION
         "
         Indicates the NLP mode.
         Options:
         1. close(1) -close mode
         2. normal(2) -normal mode
         3. enhanced(3) -enhanced mode
         4. reduced(4) -reduced mode
         5. ecgain(5) -ecgain mode
         6. dtmfec(6) -DTMF echo elimination mode
         7. invalid(256) -invalid value, use global config
         Default: invalid(256)
         "
     ::= { hwDspParaTemplateCfgEntry 4 }

  hwDspWorkMode OBJECT-TYPE
     SYNTAX      INTEGER{voice(1),fax(2),modem(3),invalid(256)}
     MAX-ACCESS  read-write
     STATUS      current
     DESCRIPTION
         "
         Indicates the dsp workmode.
         Options:
         1. voice(1) -voice mode
         2. fax(2) -fax mode
         3. modem(3) -modem mode
         4. invalid(256) -invalid value, use global config
         Default: invalid(256)
         "
     ::= { hwDspParaTemplateCfgEntry 5 }

  hwDspSc OBJECT-TYPE
     SYNTAX      INTEGER{open(1),close(2),invalid(256)}
     MAX-ACCESS  read-write
     STATUS      current
     DESCRIPTION
         "
         Indicates the silence cotrol.
         Options:
         1. open(1)-open
         2. close(2) -close
         3. invalid(256)-invalid value, use global config
         Default: invalid(256)
         "
     ::= { hwDspParaTemplateCfgEntry 6 }

  hwDspTemplateRowStatus OBJECT-TYPE
     SYNTAX      RowStatus
     MAX-ACCESS  read-write
     STATUS      current
     DESCRIPTION
         "
         Indicates the row status.
         "
     ::= { hwDspParaTemplateCfgEntry 7 }

  hwDspInputGain OBJECT-TYPE
     SYNTAX      Integer32(-1|0..15)
     MAX-ACCESS  read-write
     STATUS      current
     DESCRIPTION
         "
         Indicates the input gain of DSP chip:
           -1 -- invalid value, use global config
         0-15 -- correspond to -10 dB to +5 dB
         Default: -1
         "
     ::= { hwDspParaTemplateCfgEntry 8 }

  hwDspOutputGain OBJECT-TYPE
     SYNTAX      Integer32(-1|0..20)
     MAX-ACCESS  read-write
     STATUS      current
     DESCRIPTION
         "
         Indicates the output gain of DSP chip:
           -1 -- invalid value, use global config;
         0-20 -- correspond to -10 dB to +10 dB;
         Default: -1
         "
     ::= { hwDspParaTemplateCfgEntry 9 }

  hwDspDtmfPara OBJECT-TYPE
    SYNTAX      INTEGER{globalConfig(1),rfc2833(2),erase(3),rfc2833with2198(4)}
    MAX-ACCESS  read-write
    STATUS      current
    DESCRIPTION
      "
      Indicates the transmission mode of DTMF.
      Options:
      1. globalConfig(1) -global config;
      2. rfc2833(2) -2833 transmission;
      3. erase(3) -erase DTMF;
      4. rfc2833with2198(4) -2833with2198.
      Default: globalConfig(1)
      "
         -- DEFVAL      { {globalConfig(1)} }
    ::= { hwDspParaTemplateCfgEntry 10 }

  hwDsp2833ForDataevent OBJECT-TYPE
    SYNTAX      INTEGER{enable(1),globalConfig(2)}
    MAX-ACCESS  read-write
    STATUS      current
    DESCRIPTION
      "
      Indicates the mode of sending fax/modem event.
      Options:
      1. enable(1) -2833
      2. globalConfig(2) -global config
      Default: globalConfig(2)
      "
         -- DEFVAL      { {disable(2)} }
    ::= { hwDspParaTemplateCfgEntry 11 }

  hwDspSpecialFlow OBJECT-TYPE
    SYNTAX      Integer32(0..255)
    MAX-ACCESS  read-write
    STATUS      current
    DESCRIPTION
      "
      Indicates the dsp special flow.
      0 -- intelligent telephone special flow: filter RTP messages and only processs 2833 messages
      1 -- intelligent telephone special flow: only processs DTMF events in 2833 messages
      2 -- EC special process: enables V.21 flow
      3 -- EC special process: enables V.22 flow
      4 -- EC special process: enables V.23 flow
      5 -- EC special process: enables Bell 103 flow
      6-254 -- reserved values
      255 -- no dsp special flow
      Default: 255
      "
    ::= { hwDspParaTemplateCfgEntry 12 }

  hwDsp2198ForVbd OBJECT-TYPE
    SYNTAX      INTEGER{enable(1),globalConfig(2)}
    MAX-ACCESS  read-write
    STATUS      current
    DESCRIPTION
      "
      Flag of locally starting the 2198 redundancy VBD function.
      Options:
      1. enable(1) -enable 2198 for vbd
      2. globalConfig(2) -global config: use the global config
      "
    ::= { hwDspParaTemplateCfgEntry 13 }

  hwDspTemplateFixedJbUpImmediately OBJECT-TYPE
    SYNTAX      INTEGER{enable(1),disable(2),invalid(256)}
    MAX-ACCESS  read-write
    STATUS      current
    DESCRIPTION
      "
      Enable dsp fixed JB adjust upward immediately or not.
      Options:
      1. enable(1) -enable
      2. disable(2) -disable
      3. invalid(256)-invalid value, use global config
      Default: invalid(256)
      "
    ::= { hwDspParaTemplateCfgEntry 14 }

  hwDsp2198ForVoice OBJECT-TYPE
    SYNTAX      INTEGER{enable(1),globalConfig(2)}
    MAX-ACCESS  read-write
    STATUS      current
    DESCRIPTION
      "
      Flag of locally starting the 2198 redundancy VOICE function.
      Options:
      1. enable(1) -enable 2198 for voice
      2. globalConfig(2) -global config: use the global config
      "
    ::= { hwDspParaTemplateCfgEntry 15 }

hwPreDigitMapConfigTable OBJECT-TYPE
     SYNTAX      SEQUENCE OF HwPreDigitMapConfigEntry
     MAX-ACCESS  not-accessible
     STATUS      current
     DESCRIPTION
       "
       This table is used to config local global digitmap for sip and h248 interface.
       The indexes of this table are hwPreDigitMapName, hwPreDigitMapSliceNo.
       "
     ::= { hwIASVoipObjects 156 }

   hwPreDigitMapConfigEntry OBJECT-TYPE
     SYNTAX      HwPreDigitMapConfigEntry
     MAX-ACCESS  not-accessible
     STATUS      current
     DESCRIPTION
       "
       This table is used to config local global digitmap for sip and h248 interface.
       The indexes of this entry are hwPreDigitMapName, hwPreDigitMapSliceNo.
       "
     INDEX    {
	       hwPreDigitMapName,
	       hwPreDigitMapSliceNo
              }
     ::= { hwPreDigitMapConfigTable 1 }

   HwPreDigitMapConfigEntry ::=
     SEQUENCE
     {
       hwPreDigitMapName        OCTET STRING,
       hwPreDigitMapSliceNo     Unsigned32,
       hwPreDigitMapNewName     OCTET STRING,
       hwPreDigitMapType        INTEGER,
       hwPreDigitMapBody        OCTET STRING,
       hwPreDigitMapRowStatus   RowStatus,
       hwPreDigitMapTotalSlice  Unsigned32,
       hwPreDigitMapProtocol    INTEGER
     }

   hwPreDigitMapName OBJECT-TYPE
     SYNTAX      OCTET STRING(SIZE(1..32))
     MAX-ACCESS  not-accessible
     STATUS      current
     DESCRIPTION
         "
         Indicates the digitmap name.
         "
     ::= { hwPreDigitMapConfigEntry 1 }

   hwPreDigitMapSliceNo OBJECT-TYPE
     SYNTAX      Unsigned32(0..65535)
     MAX-ACCESS  not-accessible
     STATUS      current
     DESCRIPTION
         "
         Serial number for slice.
         High 8 bits for total number of slices, low 8 bits for sequence number of slices.
         "
     ::= { hwPreDigitMapConfigEntry 2 }

   hwPreDigitMapNewName OBJECT-TYPE
     SYNTAX      OCTET STRING(SIZE(1..32))
     MAX-ACCESS  read-write
     STATUS      current
     DESCRIPTION
         "
         Indicates the new digitmap name. used for modifing digitmap name.
         "
     ::= { hwPreDigitMapConfigEntry 3 }

   hwPreDigitMapType OBJECT-TYPE
     SYNTAX      INTEGER{normal(1),emergency(2),scc(3),directCentrex(4),secondCentrex(5)}
     MAX-ACCESS  read-write
     STATUS      current
     DESCRIPTION
         "
         Indicate digit map type.
         For SIP it may be normal(1), emergency(2), scc(3), directCentrex(4), secondCentrex(5).
         For H248 it should only be normal(1).
         Options:
         1. normal(1) -normal
         2. emergency(2) -emergency
         3. scc(3) -scc
         4. directCentrex(4) -direct centrex
         5. secondCentrex(5) -second centrex
         Default: normal(1)
         "
     ::= { hwPreDigitMapConfigEntry 4 }

   hwPreDigitMapBody OBJECT-TYPE
     SYNTAX      OCTET STRING(SIZE(1..256))
     MAX-ACCESS  read-write
     STATUS      current
     DESCRIPTION
         "
         Indicate body of DigitMap, use by add,modify,delete operation.
         "
     ::= { hwPreDigitMapConfigEntry 5 }

   hwPreDigitMapRowStatus OBJECT-TYPE
     SYNTAX      RowStatus
     MAX-ACCESS  read-write
     STATUS      current
     DESCRIPTION
         "
         Indicates the row status of the PreDigitMap.
         "
     ::= { hwPreDigitMapConfigEntry 6 }

   hwPreDigitMapTotalSlice OBJECT-TYPE
     SYNTAX      Unsigned32(0..254)
     MAX-ACCESS  read-only
     STATUS      current
     DESCRIPTION
         "
         Indicates the total slice of the PreDigitMap.
         "
     ::= { hwPreDigitMapConfigEntry 7 }

   hwPreDigitMapProtocol OBJECT-TYPE
     SYNTAX      INTEGER{h248(1),sip(2)}
     MAX-ACCESS  read-write
     STATUS      current
     DESCRIPTION
         "
         Indicates the digitmap protocol.
         Options:
         1. h248(1) -h248 protocol
         2. sip(2) -sip protocol
         "
     ::= { hwPreDigitMapConfigEntry 8 }



   hwVoipDynIPNameTable OBJECT-TYPE
     SYNTAX      SEQUENCE OF HwVoipDynIPNameEntry
     MAX-ACCESS  not-accessible
     STATUS      current
     DESCRIPTION
       "
       This table is used to query the voip dynamic media and signal IP name.
       The indexes of this table are hwVoipDynIPNameType, hwVoipDynIPNameIndex.
       "
     ::= { hwIASVoipObjects 157 }

   hwVoipDynIPNameEntry OBJECT-TYPE
     SYNTAX      HwVoipDynIPNameEntry
     MAX-ACCESS  not-accessible
     STATUS      current
     DESCRIPTION
       "
       This table is used to query the voip dynamic media and signal IP name.
       The indexes of this entry are hwVoipDynIPNameType, hwVoipDynIPNameIndex.
       "
     INDEX    {
               hwVoipDynIPNameType,
               hwVoipDynIPNameIndex
              }
     ::= { hwVoipDynIPNameTable 1 }

   HwVoipDynIPNameEntry ::=
     SEQUENCE
     {
       hwVoipDynIPNameType  	     INTEGER,
       hwVoipDynIPNameIndex          Unsigned32,
       hwVoipDynIPName  	     OCTET STRING
     }


   hwVoipDynIPNameType OBJECT-TYPE
     SYNTAX      INTEGER{mediaIP(1),signalIP(2)}
     MAX-ACCESS  not-accessible
     STATUS      current
     DESCRIPTION
         "
         Indicates dynamic  IP name type.
         Options:
         1. mediaIP(1) -dynamic media IP name
         2. signalIP(2) -dynamic signal IP name
         "
     ::= { hwVoipDynIPNameEntry 1 }


   hwVoipDynIPNameIndex OBJECT-TYPE
     SYNTAX      Unsigned32(0..65535)
     MAX-ACCESS  not-accessible
     STATUS      current
     DESCRIPTION
         "
         Indicates dynamic IP name list index.
         "
     ::= { hwVoipDynIPNameEntry 2 }


   hwVoipDynIPName OBJECT-TYPE
     SYNTAX      OCTET STRING(SIZE(0..64))
     MAX-ACCESS  read-only
     STATUS      current
     DESCRIPTION
         "
         Indicates dynamic media IP name.
         "
     ::= { hwVoipDynIPNameEntry 3 }



 --  /* Start hwIASVoipComTrapsVbOids */

     hwUserFrame OBJECT-TYPE
     SYNTAX Unsigned32(0..255)
     MAX-ACCESS accessible-for-notify
     STATUS current
     DESCRIPTION
         "
	 The frame where mg user is configed.
         "
     ::= { hwIASVoipComTrapsVbOids 1 }

     hwUserSlot OBJECT-TYPE
     SYNTAX Unsigned32(0..255)
     MAX-ACCESS accessible-for-notify
     STATUS current
     DESCRIPTION
         "
	 The slot where mg user is configed.
         "
     ::= { hwIASVoipComTrapsVbOids 2 }

     hwUserPort OBJECT-TYPE
     SYNTAX Unsigned32(0..255)
     MAX-ACCESS accessible-for-notify
     STATUS current
     DESCRIPTION
         "
	 The port where mg user is configed.
         "
     ::= { hwIASVoipComTrapsVbOids 3 }

     hwResDspFrame OBJECT-TYPE
     SYNTAX     Unsigned32(0..255)
     MAX-ACCESS accessible-for-notify
     STATUS current
     DESCRIPTION
         "
         Indicate the frame NO. of a DSP resource board.
         "
     ::= { hwIASVoipComTrapsVbOids 4 }

     hwResDspSlot OBJECT-TYPE
     SYNTAX     Unsigned32(0..255)
     MAX-ACCESS accessible-for-notify
     STATUS current
     DESCRIPTION
         "
         Indicate the slot NO. of a DSP resource board.
         "
     ::= { hwIASVoipComTrapsVbOids 5 }

     hwResDspSub OBJECT-TYPE
     SYNTAX     Unsigned32(0..255)
     MAX-ACCESS accessible-for-notify
     STATUS current
     DESCRIPTION
         "
         The DSP sub-board NO. in a resource board.
         "
     ::= { hwIASVoipComTrapsVbOids 6 }

     hwResDspChannel OBJECT-TYPE
     SYNTAX     Unsigned32(0..65535)
     MAX-ACCESS accessible-for-notify
     STATUS current
     DESCRIPTION
         "
         The DSP inner channel NO. in a subboard.
         "
     ::= { hwIASVoipComTrapsVbOids 7 }

     hwRemoteIPAddr OBJECT-TYPE
     SYNTAX IpAddress
     MAX-ACCESS accessible-for-notify
     STATUS current
     DESCRIPTION
         "
	     The remote ip address.
         "
     ::= { hwIASVoipComTrapsVbOids 8 }

     hwStandbyProtocol OBJECT-TYPE
     SYNTAX INTEGER{ h248(1), mgcp(2), sip(4) }
     MAX-ACCESS accessible-for-notify
     STATUS current
     DESCRIPTION
         "
	     The protocol in standby board.
	     Options:
	     1. h248(1) -H.248
	     2. mgcp(2) -MGCP
	     3. sip(4)  -SIP
         "
     ::= { hwIASVoipComTrapsVbOids 9 }

     hwMgId OBJECT-TYPE
     SYNTAX Unsigned32(0..4294967295)
     MAX-ACCESS accessible-for-notify
     STATUS current
     DESCRIPTION
         "
	     The media gateway ID.
         "
     ::= { hwIASVoipComTrapsVbOids 10 }

     hwRemotePort OBJECT-TYPE
     SYNTAX Unsigned32(1..65535)
     MAX-ACCESS accessible-for-notify
     STATUS current
     DESCRIPTION
         "
	     The remote port.
         "
     ::= { hwIASVoipComTrapsVbOids 11 }

     hwRemoteIpAddr OBJECT-TYPE
     SYNTAX IpAddress
     MAX-ACCESS accessible-for-notify
     STATUS current
     DESCRIPTION
         "
	     The remote ip address.
         "
     ::= { hwIASVoipComTrapsVbOids 12 }

     hwAlarmLoopdelay OBJECT-TYPE
     SYNTAX Unsigned32(0..4294967295)
     MAX-ACCESS accessible-for-notify
     STATUS current
     DESCRIPTION
         "
	     The loop delay.
         "
     ::= { hwIASVoipComTrapsVbOids 13 }

     hwAlarmPacketlost OBJECT-TYPE
     SYNTAX Unsigned32(0..4294967295)
     MAX-ACCESS accessible-for-notify
     STATUS current
     DESCRIPTION
         "
	     The packet loss rate.
         "
     ::= { hwIASVoipComTrapsVbOids 14 }

     hwAlarmJitterbuffer OBJECT-TYPE
     SYNTAX Unsigned32(0..4294967295)
     MAX-ACCESS accessible-for-notify
     STATUS current
     DESCRIPTION
         "
	     The jitter-buffer.
         "
     ::= { hwIASVoipComTrapsVbOids 15 }

 -- /*  End  hwIASVoipComTrapsVbOids */

 --  /* Start hwIASVoipComResAlarmTraps */

    hwIASVoipResUpwardbandwidthTrap NOTIFICATION-TYPE
    OBJECTS  {hwUserFrame}
    STATUS      current
    DESCRIPTION
        "
        This notification indicates that the upstream-bandwidth is insufficient.
        "
    ::= { hwIASVoipComResAlarmTraps 0 1 }

    hwIASVoipResDspAbsentTrap NOTIFICATION-TYPE
    OBJECTS  { hwUserFrame, hwUserSlot, hwUserPort }
    STATUS      current
    DESCRIPTION
        "
        This notification indicates that the DSP resources insufficient.
        "
    ::= { hwIASVoipComResAlarmTraps 0 2 }

    hwIASVoipResDspQosExceedTrap NOTIFICATION-TYPE
    OBJECTS  { hwResDspFrame, hwResDspSlot, hwResDspSub, hwResDspChannel,
               hwRemoteIPAddr, hwAlarmLoopdelay, hwAlarmPacketlost, hwAlarmJitterbuffer }
    STATUS      current
    DESCRIPTION
        "
        This notification indicates that the value of DSP QoS exceeds the threshold.
        "
    ::= { hwIASVoipComResAlarmTraps 0 3 }

    hwIASVoipResDspQosRestoreTrap NOTIFICATION-TYPE
    OBJECTS  { hwResDspFrame, hwResDspSlot, hwResDspSub, hwResDspChannel,
               hwRemoteIPAddr, hwAlarmLoopdelay, hwAlarmPacketlost, hwAlarmJitterbuffer }
    STATUS      current
    DESCRIPTION
        "
        This notification indicates that the value of DSP QoS is normal.
        "
    ::= { hwIASVoipComResAlarmTraps 0 4 }

    hwIASVoipResJbThresholdExceedTrap NOTIFICATION-TYPE
    OBJECTS {hwResDspFrame, hwResDspSlot, hwResDspSub, hwResDspChannel,
             hwRemoteIPAddr, hwAlarmJitterbuffer}
    STATUS current
    DESCRIPTION
    	"
    	This notification indicates that the jitterbuffer exceeds the  preset alarm threshold.
    	"
    ::= { hwIASVoipComResAlarmTraps 0 5 }

    hwIASVoipResJbThresholdRestoreTrap NOTIFICATION-TYPE
    OBJECTS {hwResDspFrame, hwResDspSlot, hwResDspSub, hwResDspChannel,
             hwRemoteIPAddr, hwAlarmJitterbuffer}
    STATUS current
    DESCRIPTION
    	"
    	This notification indicates that the jitterbuffer is restored to below the present alarm threshold.
    	"
    ::= { hwIASVoipComResAlarmTraps 0 6 }

--    hwIASVoipResSysDSPAbsentTrap NOTIFICATION-TYPE
--    OBJECTS {}
--    STATUS current
--    DESCRIPTION
--    	"
--    	This notification indicates that the DSP resources for voice services are insufficient.
--    	"
--    ::= { hwIASVoipComResAlarmTraps 0 7 }

--    hwIASVoipResSysDSPAbsentRestoreTrap NOTIFICATION-TYPE
--    OBJECTS {}
--    STATUS current
--    DESCRIPTION
--    	"
--    	This notification indicates that the system recovers from insufficient DSP resources for voice services.
--    	"
--    ::= { hwIASVoipComResAlarmTraps 0 8 }

--  /*  End  hwIASVoipComResAlarmTraps */

--  /*  Start  hwIASVoipComProtocolAlarmTraps */

    hwIASVoipProtocolDiffTrap NOTIFICATION-TYPE
    OBJECTS  { hwProtocolActive, hwStandbyProtocol }
    STATUS      current
    DESCRIPTION
        "
        This notification indicates that protocol in active Board and standby board are different.
        "
    ::= { hwIASVoipComProtocolAlarmTraps 0 1 }

 --  /*  End  hwIASVoipComProtocolAlarmTraps */

 --  /*  Start  hwIASVoipComVolcAlarmTraps */

    hwIASVoipVolcPowerDialerTrap NOTIFICATION-TYPE
    OBJECTS  { hwUserFrame, hwUserSlot, hwUserPort }
    STATUS      current
    DESCRIPTION
        "
        This notification indicates that user is in PowerDialer state.
        "
    ::= { hwIASVoipComVolcAlarmTraps 0 1 }

    hwIASVoipVolcPotsOverloadTrap NOTIFICATION-TYPE
    OBJECTS  { hwMgId }
    STATUS      current
    DESCRIPTION
        "
        This notification indicates that POTS calling is overloaded.
        "
    ::= { hwIASVoipComVolcAlarmTraps 0 2 }

    hwIASVoipVolcIsdnOverloadTrap NOTIFICATION-TYPE
    OBJECTS  { hwUserFrame, hwUserSlot }
    STATUS      current
    DESCRIPTION
        "
        This notification indicates that ISDN call service is overloaded.
        "
    ::= { hwIASVoipComVolcAlarmTraps 0 3 }

    hwIASVoipMgcOverloadTrap NOTIFICATION-TYPE
    OBJECTS  { hwMgId, hwRemoteIpAddr, hwRemotePort }
    STATUS      current
    DESCRIPTION
        "
        This notification indicates that call events of the VAG exceed the call threshold set on the MGC.
        "
    ::= { hwIASVoipComVolcAlarmTraps 0 4 }

    hwIASVoipVolcPowerDialerRecoverTrap NOTIFICATION-TYPE
    OBJECTS  { hwUserFrame, hwUserSlot, hwUserPort }
    STATUS      current
    DESCRIPTION
        "
        This notification indicates that user is out of PowerDialer state.
        "
    ::= { hwIASVoipComVolcAlarmTraps 0 5 }

    hwIASVoipVolcPotsOverloadRecoverTrap NOTIFICATION-TYPE
    OBJECTS  { hwMgId }
    STATUS      current
    DESCRIPTION
        "
        This notification indicates that POTS calling recovers from overload.
        "
    ::= { hwIASVoipComVolcAlarmTraps 0 6 }

    hwIASVoipVolcIsdnOverloadRecoverTrap NOTIFICATION-TYPE
    OBJECTS  { hwUserFrame, hwUserSlot }
    STATUS      current
    DESCRIPTION
        "
        This notification indicates that ISDN calling recovers from overload.
        "
    ::= { hwIASVoipComVolcAlarmTraps 0 7 }

    hwIASVoipMgcOverloadRecoverTrap NOTIFICATION-TYPE
    OBJECTS  { hwMgId, hwRemoteIpAddr, hwRemotePort }
    STATUS      current
    DESCRIPTION
        "
        This notification indicates that call events of the VAG recover to within the call threshold set on the MGC.
        "
    ::= { hwIASVoipComVolcAlarmTraps 0 8 }

 --  /*  End  hwIASVoipComVolcAlarmTraps */
   -- hwDspOverloadResourceCfgTable (Parameter MIB table)--
 hwDspOverloadResourceCfgTable OBJECT IDENTIFIER ::= {  hwIASVoipObjects 182  }

  hwDspResourceWorkMode OBJECT-TYPE
    SYNTAX      INTEGER{normal(1), priority(2)}
    MAX-ACCESS  read-write
    STATUS      current
    DESCRIPTION
      "
      Indicates whether the AG restricts calls in case of insufficient DSP resource when many call raised.
      Options:
      1. normal(1) -normal
      2. priority(2) -priority
      "
 -- DEFVAL      { 1 }
         ::= { hwDspOverloadResourceCfgTable 1 }

  hwDspResourcethreshold1 OBJECT-TYPE
    SYNTAX      Integer32(0..100)
    MAX-ACCESS  read-write
    STATUS      current
    DESCRIPTION
      "
      Indicates the normal call will use the max threshold of the whole DSP resource.
      The value of hwDspResourcethreshold1 must be smaller than or equal to the hwDspResourcethreshold2.
      Unit: 1/100
      "
 -- DEFVAL      { 100 }
         ::= { hwDspOverloadResourceCfgTable 2 }

  hwDspResourcethreshold2 OBJECT-TYPE
    SYNTAX      Integer32(0..100)
    MAX-ACCESS  read-write
    STATUS      current
    DESCRIPTION
      "
      Indicates the max threshold of the whole DSP resource which used for the prior user.
      The value of hwDspResourcethreshold2 must be smaller than or equal to the hwDspResourcethreshold3.
      Unit: 1/100
      "
 -- DEFVAL      { 100 }
         ::= { hwDspOverloadResourceCfgTable 3 }

  hwDspResourcethreshold3 OBJECT-TYPE
    SYNTAX      Integer32(0..100)
    MAX-ACCESS  read-write
    STATUS      current
    DESCRIPTION
      "
      Indicates the max threshold of the whole DSP resource which used for the high prior user.
      Unit: 1/100
      "
 -- DEFVAL      { 100 }
         ::= { hwDspOverloadResourceCfgTable 4 }

 --  /*  End  hwDspOverloadResourceCfgTable */

 hwRfc2198ParaTable OBJECT IDENTIFIER ::= { hwIASVoipObjects 183 }

 hwRfc2198ForVoice OBJECT-TYPE
    SYNTAX      INTEGER{enable(1), disable(2)}
    MAX-ACCESS  read-write
    STATUS      current
    DESCRIPTION
      "
      Indicates the flag of voice using rfc2198.
      Only for H248 protocol.
      Options:
      1. enable(1) -enable
      2. disable(2) -disable
      "
  -- DEFVAL      { {disable} }
         ::= { hwRfc2198ParaTable 1 }

 hwRfc2198SmartParaTable OBJECT IDENTIFIER ::= { hwIASVoipObjects 184 }

   hwFirstSectionUpThreshold OBJECT-TYPE
     SYNTAX      Integer32(0..1000)
     MAX-ACCESS  read-write
     STATUS      current
     DESCRIPTION
         "
         Indicates the up threshold for packet loss at the first section.
         Default: 5
         Unit: 1/1000
         "
   -- DEFVAL      { 5 }
     ::= { hwRfc2198SmartParaTable 1 }

   hwSecondSectionUpThreshold OBJECT-TYPE
     SYNTAX      Integer32(0..1000)
     MAX-ACCESS  read-write
     STATUS      current
     DESCRIPTION
         "
         Indicates the up threshold for packet loss at the second section.
         Default: 30
         Unit:  1/1000
         "
   -- DEFVAL      { 30 }
     ::= { hwRfc2198SmartParaTable 2 }

  hwThirdSectionUpThreshold OBJECT-TYPE
     SYNTAX      Integer32(0..1000)
     MAX-ACCESS  read-write
     STATUS      current
     DESCRIPTION
         "
         Indicates the up threshold for packet loss at the third section.
         Default: 50
         Unit:  1/1000
         "
    -- DEFVAL      { 50 }
     ::= { hwRfc2198SmartParaTable 3 }

  hwFirstSectionRedundantNum OBJECT-TYPE
     SYNTAX      Integer32(0..3)
     MAX-ACCESS  read-write
     STATUS      current
     DESCRIPTION
         "
         Indicates the redundant number for RFC2198 at the first section.
         Default: 0
         "
  -- DEFVAL      { 0 }
     ::= { hwRfc2198SmartParaTable 4 }
  hwSecondSectionRedundantNum OBJECT-TYPE
     SYNTAX      Integer32(0..3)
     MAX-ACCESS  read-write
     STATUS      current
     DESCRIPTION
         "
         Indicates the redundant number for RFC2198 at the second section.
         Default: 1
         "
  -- DEFVAL      { 1 }
     ::= { hwRfc2198SmartParaTable 5 }

  hwThirdSectionRedundantNum OBJECT-TYPE
     SYNTAX      Integer32(0..3)
     MAX-ACCESS  read-write
     STATUS      current
     DESCRIPTION
         "
         Indicates the redundant number for RFC2198 at the third section.
         Default: 2
         "
   -- DEFVAL      { 2 }
     ::= { hwRfc2198SmartParaTable 6 }

 hwFourthSectionRedundantNum OBJECT-TYPE
     SYNTAX      Integer32(0..3)
     MAX-ACCESS  read-write
     STATUS      current
     DESCRIPTION
         "
         Indicates the redundant number for RFC2198 at the fourth section.
         Default: 3
         "
   -- DEFVAL      { 3 }
     ::= { hwRfc2198SmartParaTable 7 }


   hwTlsParaCfgTable OBJECT-TYPE
     SYNTAX      SEQUENCE OF HwTlsParaCfgEntry
     MAX-ACCESS  not-accessible
     STATUS      current
     DESCRIPTION
       "
       This table is used to set the tls attribute.
       The index of this table is hwTlsParaInterfaceId.
       "
     ::= { hwIASVoipObjects 185 }

   hwTlsParaCfgEntry OBJECT-TYPE
     SYNTAX      HwTlsParaCfgEntry
     MAX-ACCESS  not-accessible
     STATUS      current
     DESCRIPTION
       "
       This table is used to set the tls attribute.
       The index of this entry is hwTlsParaInterfaceId.
       "
     INDEX    {
               hwTlsParaInterfaceId
              }
     ::= { hwTlsParaCfgTable 1 }

   HwTlsParaCfgEntry ::=
     SEQUENCE
     {
       hwTlsParaInterfaceId	Integer32,
       hwTlsParaTlsVersion	INTEGER,
       hwTlsParaAuthMode	INTEGER,
       hwTlsParaRootCA	        OCTET STRING,
       hwTlsParaCert	        OCTET STRING,
       hwTlsParaKey             OCTET STRING
     }

   hwTlsParaInterfaceId OBJECT-TYPE
     SYNTAX      Integer32(0..33554431)
     MAX-ACCESS  not-accessible
     STATUS      current
     DESCRIPTION
         "
         Indicates the MG ID.
         The range of MG ID from 0 to 16777215 is for AG system, value of 33554431 is only for PBX system and the value input from 16777215 to 33554431 is invalid.
         "
     ::= { hwTlsParaCfgEntry 1 }

   hwTlsParaTlsVersion OBJECT-TYPE
     SYNTAX      INTEGER{tlsv10(1),tlsv11(2),auto-negotiate(3)}
     MAX-ACCESS  read-write
     STATUS      current
     DESCRIPTION
         "
         Indicates the version of TLS.
         Options:
         1. tlsv10(1) -TLS v1.0
         2. tlsv11(2) -TLS v1.1
         3. auto-negotiate(3) -auto negotiate
         Default: auto-negotiate(3)
         "
     ::= { hwTlsParaCfgEntry 2 }

   hwTlsParaAuthMode OBJECT-TYPE
     SYNTAX      INTEGER{anonymous(1),server(2),client(3),both(4)}
     MAX-ACCESS  read-write
     STATUS      current
     DESCRIPTION
         "
         Indicates the authentication mode of TLS.
         Options:
         1. anonymous(1) -Anonymous
         2. server(2) -Server
         3. client(3) -Client
         4. both(4) -Both
         Default: anonymous(1)
         "
     ::= { hwTlsParaCfgEntry 3 }

   hwTlsParaRootCA OBJECT-TYPE
     SYNTAX      OCTET STRING(SIZE (0..64))
     MAX-ACCESS  read-write
     STATUS      current
     DESCRIPTION
         "
         Indicates the name of root certificate.
         "
     ::= { hwTlsParaCfgEntry 4 }

   hwTlsParaCert OBJECT-TYPE
     SYNTAX      OCTET STRING(SIZE (0..64))
     MAX-ACCESS  read-write
     STATUS      current
     DESCRIPTION
         "
         Indicates the name of certificate.
         "
     ::= { hwTlsParaCfgEntry 5 }

   hwTlsParaKey OBJECT-TYPE
     SYNTAX      OCTET STRING(SIZE (0..64))
     MAX-ACCESS  read-write
     STATUS      current
     DESCRIPTION
         "
         Indicates the name of key.
         "
     ::= { hwTlsParaCfgEntry 6 }

   hwTlsRunStateInfoTable OBJECT-TYPE
     SYNTAX      SEQUENCE OF HwTlsRunStateInfoEntry
     MAX-ACCESS  not-accessible
     STATUS      current
     DESCRIPTION
       "
       This table is used to display the tls running information.
       The index of this table is hwTlsRunStateInfoSessionID.
       "
     ::= { hwIASVoipObjects 186 }

   hwTlsRunStateInfoEntry OBJECT-TYPE
     SYNTAX      HwTlsRunStateInfoEntry
     MAX-ACCESS  not-accessible
     STATUS      current
     DESCRIPTION
       "
       This table is used to display the tls running information.
       The index of this entry is hwTlsRunStateInfoSessionID.
       "
     INDEX    {
               hwTlsRunStateInfoSessionID
              }
     ::= { hwTlsRunStateInfoTable 1 }

   HwTlsRunStateInfoEntry ::=
     SEQUENCE
     {
       hwTlsRunStateInfoSessionID	Integer32,
       hwTlsRunStateInfoVersion 	INTEGER,
       hwTlsRunStateInfoAuthMode 	INTEGER,
       hwTlsRunStateInfoRootCA	        OCTET STRING,
       hwTlsRunStateInfoCert	        OCTET STRING,
       hwTlsRunStateInfoKey             OCTET STRING,
       hwTlsRunStateInfoState           INTEGER,
       hwTlsRunStateInfoCurrentCipher   OCTET STRING
     }

   hwTlsRunStateInfoSessionID OBJECT-TYPE
     SYNTAX      Integer32
     MAX-ACCESS  not-accessible
     STATUS      current
     DESCRIPTION
         "
         TLS session ID
 	 Constructed by Protocol-Type, Proxy-index, SIP-Interface-ID;
 	 Format:xyzzzzzz(Hex)
 	 a) x for Protocol-Type: SIP(0);
 	 b) y for Proxy-index: SIP Proxy index;
 	 c) z for SIP-Interface-ID: zzzzzz for SIP interface ID;
 	 "
     ::= { hwTlsRunStateInfoEntry 1 }

   hwTlsRunStateInfoVersion OBJECT-TYPE
     SYNTAX      INTEGER{tlsv10(1),tlsv11(2),auto-negotiate(3)}
     MAX-ACCESS  read-only
     STATUS      current
     DESCRIPTION
         "
         Indicates the version of TLS.
         Options:
         1. tlsv10(1) -TLS v1.0
         2. tlsv11(2) -TLS v1.1
         3. auto-negotiate(3) -auto negotiate
         "
    -- DEFVAL      { {auto-negotiate(3)} }
     ::= { hwTlsRunStateInfoEntry 2 }

   hwTlsRunStateInfoAuthMode OBJECT-TYPE
     SYNTAX      INTEGER{anonymous(1),server(2),client(3),both(4)}
     MAX-ACCESS  read-only
     STATUS      current
     DESCRIPTION
         "
         Indicates the authentication mode of TLS.
         Options:
         1. anonymous(1) -Anonymous
         2. server(2) -Server
         3. client(3) -Client
         4. both(4) -Both
         "
    -- DEFVAL      { {anonymous(1)} }
     ::= { hwTlsRunStateInfoEntry 3 }

   hwTlsRunStateInfoRootCA OBJECT-TYPE
     SYNTAX      OCTET STRING(SIZE (0..64))
     MAX-ACCESS  read-only
     STATUS      current
     DESCRIPTION
         "
         Indicates the name of root certificate.
         "
     ::= { hwTlsRunStateInfoEntry 4 }

   hwTlsRunStateInfoCert OBJECT-TYPE
     SYNTAX      OCTET STRING(SIZE (0..64))
     MAX-ACCESS  read-only
     STATUS      current
     DESCRIPTION
         "
         Indicates the name of client certificate.
         "
     ::= { hwTlsRunStateInfoEntry 5 }

   hwTlsRunStateInfoKey OBJECT-TYPE
     SYNTAX      OCTET STRING(SIZE (0..64))
     MAX-ACCESS  read-only
     STATUS      current
     DESCRIPTION
         "
         Indicates the name of client key.
         "
     ::= { hwTlsRunStateInfoEntry 6 }
   hwTlsRunStateInfoState OBJECT-TYPE
     SYNTAX      INTEGER{idle(1),handshaking(2),handshakeSuccess(3),handshakeFailure(4)}
     MAX-ACCESS  read-only
     STATUS      current
     DESCRIPTION
         "
         Indicates the state of handshake.
         Options:
         1. idle(1) -Idle
         2. handshaking(2) -Handshaking
         3. handshakeSuccess(3) -HandshakeSuccess
         4. handshakeFailure(4) -HandshakeFailure
         "
     ::= { hwTlsRunStateInfoEntry 7 }
   hwTlsRunStateInfoCurrentCipher OBJECT-TYPE
     SYNTAX      OCTET STRING(SIZE (0..128))
     MAX-ACCESS  read-only
     STATUS      current
     DESCRIPTION
         "
         Indicates the name of cipher.
         "
     ::= { hwTlsRunStateInfoEntry 8 }

   hwTlsCertificateTable OBJECT-TYPE
     SYNTAX      SEQUENCE OF HwTlsCertificateEntry
     MAX-ACCESS  not-accessible
     STATUS      current
     DESCRIPTION
       "
       This table is used to config and query the certificates in system.
       The indexes of this table are hwTlsCertificateType and hwTlsCertificateIndex.
       "
     ::= { hwIASVoipObjects 187 }

   hwTlsCertificateEntry OBJECT-TYPE
     SYNTAX      HwTlsCertificateEntry
     MAX-ACCESS  not-accessible
     STATUS      current
     DESCRIPTION
       "
       This table is used to config and query the certificates in system.
       The indexes of this entry are hwTlsCertificateType and hwTlsCertificateIndex.
       "
     INDEX    {
               hwTlsCertificateType,
               hwTlsCertificateIndex
              }
     ::= { hwTlsCertificateTable 1 }

   HwTlsCertificateEntry ::=
     SEQUENCE
     {
       hwTlsCertificateType	 Integer32,
       hwTlsCertificateIndex	 Integer32,
       hwTlsParaCertificateName	 OCTET STRING,
       hwTlsCertificateRowStatus RowStatus
     }

   hwTlsCertificateType OBJECT-TYPE
     SYNTAX      Integer32(0..2)
     MAX-ACCESS  not-accessible
     STATUS      current
     DESCRIPTION
         "
         Indicates the type of certificate.
         Options:
         1. 0 -Root certificate
         2. 1 -Certificate
         3. 2 -Key
         "
     ::= { hwTlsCertificateEntry 1 }

   hwTlsCertificateIndex OBJECT-TYPE
     SYNTAX      Integer32(0..255)
     MAX-ACCESS  not-accessible
     STATUS      current
     DESCRIPTION
         "
         Indicates the index of certificate.
         "
     ::= { hwTlsCertificateEntry 2 }

   hwTlsParaCertificateName OBJECT-TYPE
     SYNTAX      OCTET STRING(SIZE (0..64))
     MAX-ACCESS  read-only
     STATUS      current
     DESCRIPTION
         "
         Indicates the name of certificate.
         "
     ::= { hwTlsCertificateEntry 3 }

   hwTlsCertificateRowStatus OBJECT-TYPE
     SYNTAX      RowStatus
     MAX-ACCESS  read-write
     STATUS      current
     DESCRIPTION
         "
         This is used to create new rows in this table, modify existing rows, and delete existing rows.
         "
     ::= { hwTlsCertificateEntry 4 }


  hwIpTrkGrpFaxParaTable OBJECT-TYPE
     SYNTAX      SEQUENCE OF HwIpTrkGrpFaxParaEntry
     MAX-ACCESS  not-accessible
     STATUS      current
     DESCRIPTION
       "
       This table is used to config the fax parameter of a IP truck group.
       The index of this table is hwIpTrkGrpFaxParaGrpName.
       "
     ::= { hwIASVoipObjects 188 }

   hwIpTrkGrpFaxParaEntry OBJECT-TYPE
     SYNTAX      HwIpTrkGrpFaxParaEntry
     MAX-ACCESS  not-accessible
     STATUS      current
     DESCRIPTION
       "
       This table is used to config the fax parameter of a IP truck group.
       The index of this entry is hwIpTrkGrpFaxParaGrpName.
       "
     INDEX    {
                hwIpTrkGrpFaxParaGrpName
              }
     ::= { hwIpTrkGrpFaxParaTable 1 }

   HwIpTrkGrpFaxParaEntry ::=
     SEQUENCE
     {
       hwIpTrkGrpFaxParaGrpName         OCTET STRING,
       hwIpTrkGrpFaxMode                Integer32,
       hwIpTrkGrpFaxRedundancyFlag      Integer32,
       hwIpTrkGrpFaxNegoMode            INTEGER,
       hwIpTrkGrpFaxTransMode           INTEGER,
       hwIpTrkGrpFaxParaVbdCodec  	INTEGER,
       hwIpTrkGrpFaxParaVbdPtType 	INTEGER,
       hwIpTrkGrpFaxVbdAttributeType    INTEGER,
       hwIpTrkGrpFaxRtpInterval 	INTEGER
     }


   hwIpTrkGrpFaxParaGrpName OBJECT-TYPE
     SYNTAX      OCTET STRING(SIZE(0..32))
     MAX-ACCESS  not-accessible
     STATUS      current
     DESCRIPTION
         "
         Indicates the IP truck group name.
         "
     ::= { hwIpTrkGrpFaxParaEntry 1 }

   hwIpTrkGrpFaxMode OBJECT-TYPE
     SYNTAX      Integer32
     MAX-ACCESS  read-write
     STATUS      current
     DESCRIPTION
         "
         Indicates the fax transmission mode. 1-Transparent transmission; 2-Auto-negotiation T.38; 3-V3 flow; 4-Stand-alone transparent transmission; 5-V5 flow; 6-Self-switch T.38. To be compatible with the previous versions, the enumerated types remain unchanged. Only 1, 2, 4, and 6 are available in the SIP. In the SIP, the transparent transmission mode is the same as the negotiation transparent transmission mode in the CLI.The default is 5 (V5 flow) for the H.248, 3 (V3 flow) for the MGCP, and 1 (transparent transmission) for the SIP.
         "
     ::= { hwIpTrkGrpFaxParaEntry 2 }

   hwIpTrkGrpFaxRedundancyFlag OBJECT-TYPE
     SYNTAX      Integer32
     MAX-ACCESS  read-write
     STATUS      current
     DESCRIPTION
         "
         Use fax redundancy parameter or not .1:enable,to use. 2:disable,not to use. This leaf only valid in sip transparent fax.
         "
     ::= { hwIpTrkGrpFaxParaEntry 4 }

   hwIpTrkGrpFaxNegoMode OBJECT-TYPE
     SYNTAX      INTEGER{negotiate(1), -- negotiate
                         selfswitch(2) -- do not negotiate
                         }
     MAX-ACCESS  read-write
     STATUS      current
     DESCRIPTION
         "
         The negotiate mode of fax.
         Options:
         1. negotiate(1) -negotiate
         2. selfswitch(2) -do not negotiate
         "
     ::= { hwIpTrkGrpFaxParaEntry 5 }

   hwIpTrkGrpFaxTransMode OBJECT-TYPE
     SYNTAX      INTEGER{thoroughly(1), -- use voice codec
                         t38(2)         -- use T.38 codec
                         }
     MAX-ACCESS  read-write
     STATUS      current
     DESCRIPTION
       "
       Indicates the fax transmission mode.
       Options:
       1. thoroughly(1) -use voice codec
       2. t38(2) - use T.38 codec
       Default: thoroughly(1)
       "
     ::= { hwIpTrkGrpFaxParaEntry 6 }

   hwIpTrkGrpFaxParaVbdCodec OBJECT-TYPE
     SYNTAX      INTEGER{g711A(1),g711U(2)}
     MAX-ACCESS  read-write
     STATUS      current
     DESCRIPTION
       "
       Indicates the codec of VBD.
       Options:
       1. g711A(1) -G.711A
       2. g711U(2) -G.711U
       "
     ::= { hwIpTrkGrpFaxParaEntry 9 }

   hwIpTrkGrpFaxParaVbdPtType OBJECT-TYPE
     SYNTAX      INTEGER{static(1),dynamic(2)}
     MAX-ACCESS  read-write
     STATUS      current
     DESCRIPTION
       "
       Indicates the payload type of VBD.
       Options:
       1. static(1) -static payload type
       2. dynamic(2) -dynamic payload type
       "
     ::= { hwIpTrkGrpFaxParaEntry 10 }

   hwIpTrkGrpFaxVbdAttributeType OBJECT-TYPE
     SYNTAX      INTEGER{v152(1),chinatelecom(2),extchinatelecom(3),ietf(4)}
     MAX-ACCESS  read-write
     STATUS      current
     DESCRIPTION
       "
       Indicate the format of session attribute lines when starting fax VBD Negotiation.
       Options:
       1. v152(1) -v.152 format
       2. chinatelecom(2) -chinatelecom format
       3. extchinatelecom(3) -extchinatelecom format
       4. ietf(4) -ietf format
       "
     ::= { hwIpTrkGrpFaxParaEntry 12 }

   hwIpTrkGrpFaxRtpInterval OBJECT-TYPE
     SYNTAX      INTEGER{packettime5ms(1),packettime10ms(2),packettime20ms(3),packettime30ms(4)}
     MAX-ACCESS  read-write
     STATUS      current
     DESCRIPTION
       "
       Indicates the default RTP packet time of DSP channel.
       Options:
       1. packettime5ms(1) -5ms
       2. packettime10ms(2) -10ms
       3. packettime20ms(3) -20ms
       4. packettime30ms(4) -30ms
       Unit: millisecond
       "
     ::= { hwIpTrkGrpFaxParaEntry 13 }


  hwIpTrkGrpModemParaTable OBJECT-TYPE
     SYNTAX      SEQUENCE OF HwIpTrkGrpModemParaEntry
     MAX-ACCESS  not-accessible
     STATUS      current
     DESCRIPTION
       "
       This table is used to config the modem parameter of a IP truck group.
       The index of this table is hwIpTrkGrpModemParaGrpName.
       "
     ::= { hwIASVoipObjects 189 }

   hwIpTrkGrpModemParaEntry OBJECT-TYPE
     SYNTAX      HwIpTrkGrpModemParaEntry
     MAX-ACCESS  not-accessible
     STATUS      current
     DESCRIPTION
       "
       This table is used to config the modem parameter of a IP truck group.
       The index of this entry is hwIpTrkGrpModemParaGrpName.
       "
     INDEX    {
                hwIpTrkGrpModemParaGrpName
              }
     ::= { hwIpTrkGrpModemParaTable 1 }

   HwIpTrkGrpModemParaEntry ::=
     SEQUENCE
     {
       hwIpTrkGrpModemParaGrpName         OCTET STRING,
       hwIpTrkGrpModemMode                Integer32,
       hwIpTrkGrpModemRedundancyFlag      Integer32,
       hwIpTrkGrpModemNegoMode            INTEGER,
       hwIpTrkGrpModemTransMode           INTEGER,
       hwIpTrkGrpModemParaVbdCodec        INTEGER,
       hwIpTrkGrpModemParaVbdPtType       INTEGER,
       hwIpTrkGrpModemVbdAttributeType    INTEGER,
       hwIpTrkGrpModemRtpInterval         INTEGER
     }

   hwIpTrkGrpModemParaGrpName OBJECT-TYPE
     SYNTAX      OCTET STRING(SIZE(0..32))
     MAX-ACCESS  not-accessible
     STATUS      current
     DESCRIPTION
         "
         Indicates the IP truck group name.
         "
     ::= { hwIpTrkGrpModemParaEntry 1 }

   hwIpTrkGrpModemMode OBJECT-TYPE
     SYNTAX      Integer32
     MAX-ACCESS  read-write
     STATUS      current
     DESCRIPTION
         "
         Indicates the modem transmission mode. 1-Negotiation mode; 2-Stand-alone mode.
         "
     ::= { hwIpTrkGrpModemParaEntry 2 }

   hwIpTrkGrpModemRedundancyFlag OBJECT-TYPE
     SYNTAX      Integer32
     MAX-ACCESS  read-write
     STATUS      current
     DESCRIPTION
         "
         Indicates the flag of using the modem redundancy parameter. 1-enable; 2-disable .
         "
     ::= { hwIpTrkGrpModemParaEntry 3 }

   hwIpTrkGrpModemNegoMode OBJECT-TYPE
     SYNTAX      INTEGER{negotiate(1), -- negotiate
                         selfswitch(2) -- do not negotiate
                         }
     MAX-ACCESS  read-write
     STATUS      current
     DESCRIPTION
         "
         The negotiate mode of fax.
         Options:
         1. negotiate(1) -negotiate
         2. selfswitch(2) -do not negotiate
         "
     ::= { hwIpTrkGrpModemParaEntry 5 }

   hwIpTrkGrpModemTransMode OBJECT-TYPE
     SYNTAX      INTEGER{thoroughly(1),relay(2)}
     MAX-ACCESS  read-write
     STATUS      current
     DESCRIPTION
       "
       Indicates the fax transmission mode.
       Options:
       1. thoroughly(1) -thoroughly transmission
       2. relay(2) -Relay mode
       Default: thoroughly(1)
       "
     ::= { hwIpTrkGrpModemParaEntry 6 }

   hwIpTrkGrpModemParaVbdCodec OBJECT-TYPE
     SYNTAX      INTEGER{g711A(1),g711U(2)}
     MAX-ACCESS  read-write
     STATUS      current
     DESCRIPTION
       "
       Indicates the codec of VBD.
       Options:
       1. g711A(1) -G.711A
       2. g711U(2) -G.711U
       "
     ::= { hwIpTrkGrpModemParaEntry 9 }

   hwIpTrkGrpModemParaVbdPtType OBJECT-TYPE
     SYNTAX      INTEGER{static(1),dynamic(2)}
     MAX-ACCESS  read-write
     STATUS      current
     DESCRIPTION
       "
       Indicates the payload type of VBD.
       Options:
       1. static(1) -static payload type
       2. dynamic(2) -dynamic payload type
       "
     ::= { hwIpTrkGrpModemParaEntry 10 }

   hwIpTrkGrpModemVbdAttributeType OBJECT-TYPE
     SYNTAX      INTEGER{v152(1),             -- V.152
                         chinatelecom(2),     -- chinatelecom
                         extchinatelecom(3),  -- extchinatelecom
                         ietf(4)
                         }
     MAX-ACCESS  read-write
     STATUS      current
     DESCRIPTION
       "
       Indicate the format of session attribute lines when starting modem VBD Negotiation.
       Options:
       1. v152(1) -V.152
       2. chinatelecom(2) -china telecom
       3. extchinatelecom(3) -extend china telecom
       4. ietf(4) -ietf
       "
     ::= { hwIpTrkGrpModemParaEntry 12 }

   hwIpTrkGrpModemRtpInterval OBJECT-TYPE
     SYNTAX      INTEGER{packettime5ms(1),packettime10ms(2),packettime20ms(3),packettime30ms(4)}
     MAX-ACCESS  read-write
     STATUS      current
     DESCRIPTION
       "
       Indicates the default RTP packet time of DSP channel.
       Options:
       1. packettime5ms(1)  -5ms
       2. packettime10ms(2) -10ms
       3. packettime20ms(3) -20ms
       4. packettime30ms(4) -30ms
       Unit: millisecond
       "
     ::= { hwIpTrkGrpModemParaEntry 13 }

   hwIpTrkGrpRfc2833Table OBJECT-TYPE
     SYNTAX      SEQUENCE OF HwIpTrkGrpRfc2833Entry
     MAX-ACCESS  not-accessible
     STATUS      current
     DESCRIPTION
       "
       This table is used to config the rfc2833 parameter of a IP truck group.
       The index of this table is hwIpTrkGrpRfc2833GrpName.
       "
     ::= { hwIASVoipObjects 190 }

   hwIpTrkGrpRfc2833Entry OBJECT-TYPE
     SYNTAX      HwIpTrkGrpRfc2833Entry
     MAX-ACCESS  not-accessible
     STATUS      current
     DESCRIPTION
       "
       This table is used to config the rfc2833 parameter of a IP truck group.
       The index of this entry is hwIpTrkGrpRfc2833GrpName.
       "
     INDEX    {
                hwIpTrkGrpRfc2833GrpName
              }
     ::= { hwIpTrkGrpRfc2833Table 1 }

   HwIpTrkGrpRfc2833Entry ::=
     SEQUENCE
     {
       hwIpTrkGrpRfc2833GrpName     OCTET STRING,
       hwIpTrkGrpRfc2833NegoMode    INTEGER,
       hwIpTrkGrpRfc2833FaxModem    INTEGER,
       hwIpTrkGrpRfc2833FlashHook   INTEGER,
       hwIpTrkGrpRfc2833Dtmf        INTEGER
     }

   hwIpTrkGrpRfc2833GrpName OBJECT-TYPE
     SYNTAX      OCTET STRING(SIZE(0..32))
     MAX-ACCESS  not-accessible
     STATUS      current
     DESCRIPTION
         "
         Indicates the IP truck group name.
         "
     ::= { hwIpTrkGrpRfc2833Entry 1 }


   hwIpTrkGrpRfc2833NegoMode OBJECT-TYPE
     SYNTAX      INTEGER{negoStart(1),        -- negotiate start
                         fixedStart(2),       -- fixed start
                         noInitiativeStart(3) -- no initiative start
                         }
     MAX-ACCESS  read-write
     STATUS      current
     DESCRIPTION
       "
       Indicates the start mode of the rfc2833.
       Options:
       1. negoStart(1) -negotiate start
       2. fixedStart(2) -fixed start
       3. noInitiativeStart(3) -no initiative start
       "
     ::= { hwIpTrkGrpRfc2833Entry 2 }

   hwIpTrkGrpRfc2833FaxModem OBJECT-TYPE
     SYNTAX      INTEGER{enable(1),disable(2)}
     MAX-ACCESS  read-write
     STATUS      current
     DESCRIPTION
      "
      Indicates the flag of fax and modem event using rfc2833 parameter.
      Options:
      1. enable(1) -enable
      2. disable(2) -disable
      Default: enable(1)
      "
     ::= { hwIpTrkGrpRfc2833Entry 3 }

   hwIpTrkGrpRfc2833FlashHook OBJECT-TYPE
     SYNTAX      INTEGER{enable(1),disable(2)}
     MAX-ACCESS  read-write
     STATUS      current
     DESCRIPTION
      "
      Indicates the flag of flash hook event using rfc2833 parameter.
      Options:
      1. enable(1) -enable
      2. disable(2) -disable
      Default: disable(2)
      "
     ::= { hwIpTrkGrpRfc2833Entry 4 }

   hwIpTrkGrpRfc2833Dtmf OBJECT-TYPE
     SYNTAX      INTEGER{enable(1), disable(2)}
     MAX-ACCESS  read-write
     STATUS      current
     DESCRIPTION
      "
      Indicates the flag of dtmf using rfc2833 parameter.
      Options:
      1. enable(1)  -enable(1)
      2. disable(2) -disable(2)
      Default: enable(1)
      "
     ::= { hwIpTrkGrpRfc2833Entry 5 }


   hwIpTrkGrpRfc2198Table OBJECT-TYPE
     SYNTAX      SEQUENCE OF HwIpTrkGrpRfc2198Entry
     MAX-ACCESS  not-accessible
     STATUS      current
     DESCRIPTION
       "
       This table is used to config the rfc2198 parameter of a IP truck group.
       The index of this table is hwIpTrkGrpRfc2198GrpName.
       "
     ::= { hwIASVoipObjects 191 }

   hwIpTrkGrpRfc2198Entry OBJECT-TYPE
     SYNTAX      HwIpTrkGrpRfc2198Entry
     MAX-ACCESS  not-accessible
     STATUS      current
     DESCRIPTION
       "
       This table is used to config the rfc2198 parameter of a IP truck group.
       The index of this entry is hwIpTrkGrpRfc2198GrpName.
       "
     INDEX    {
                hwIpTrkGrpRfc2198GrpName
              }
     ::= { hwIpTrkGrpRfc2198Table 1 }

   HwIpTrkGrpRfc2198Entry ::=
     SEQUENCE
     {
       hwIpTrkGrpRfc2198GrpName     OCTET STRING,
       hwIpTrkGrpRfc2198NegoMode    INTEGER,
       hwIpTrkGrpRfc2198StartMode   INTEGER,
       hwIpTrkGrpRfc2198Rfc2833     INTEGER,
       hwIpTrkGrpRfc2198Vbd         INTEGER,
       hwIpTrkGrpRfc2198Voice       INTEGER
     }

   hwIpTrkGrpRfc2198GrpName OBJECT-TYPE
     SYNTAX      OCTET STRING(SIZE(0..32))
     MAX-ACCESS  not-accessible
     STATUS      current
     DESCRIPTION
         "
         Indicates the IP truck group name.
         "
     ::= { hwIpTrkGrpRfc2198Entry 1 }


   hwIpTrkGrpRfc2198NegoMode OBJECT-TYPE
     SYNTAX      INTEGER{negoStart(1),        -- negotiate start
                         fixedStart(2),       -- fixed start
                         noInitiativeStart(3) -- no initiative start
                         }
     MAX-ACCESS  read-write
     STATUS      current
     DESCRIPTION
       "
       Indicates the start mode of the rfc2198.
       Options:
       1. negoStart(1)         -negotiate start
       2. fixedStart(2)        -fixed start
       3. noInitiativeStart(3) -no initiative start
       "
     ::= { hwIpTrkGrpRfc2198Entry 2 }

   hwIpTrkGrpRfc2198StartMode OBJECT-TYPE
     SYNTAX      INTEGER{smart2198(1),ordinary2198(2)}
     MAX-ACCESS  read-write
     STATUS      current
     DESCRIPTION
      "
      Indicates the start mode of the rfc2198.
      Options:
      1. smart2198(1) -smart start RFC2198
      2. ordinary2198(2) -start RFC2198 ordinary
      "
     ::= { hwIpTrkGrpRfc2198Entry 3 }

   hwIpTrkGrpRfc2198Rfc2833 OBJECT-TYPE
     SYNTAX      INTEGER{enable(1),disable(2)}
     MAX-ACCESS  read-write
     STATUS      current
     DESCRIPTION
      "
      Indicates the flag of rfc2833 with using rfc2198.
      Options:
      1. enable(1) -enable
      2. disable(2) -disable
      Default: disable(2)
      "
     ::= { hwIpTrkGrpRfc2198Entry 4 }

   hwIpTrkGrpRfc2198Vbd OBJECT-TYPE
     SYNTAX      INTEGER{enable(1),disable(2)}
     MAX-ACCESS  read-write
     STATUS      current
     DESCRIPTION
      "
      Indicates the flag of the VBD using rfc2198.
      Options:
      1. enable(1) -enable
      2. disable(2) -disable
      "
     ::= { hwIpTrkGrpRfc2198Entry 5 }

   hwIpTrkGrpRfc2198Voice OBJECT-TYPE
     SYNTAX      INTEGER{enable(1),disable(2)}
     MAX-ACCESS  read-write
     STATUS      current
     DESCRIPTION
      "
      Indicates the flag of voice using rfc2198.
      Options:
      1. enable(1) -enable
      2. disable(2) -disable
      "
     ::= { hwIpTrkGrpRfc2198Entry 6 }


   hwIpTrkGrpDtmfParaTable OBJECT-TYPE
     SYNTAX      SEQUENCE OF HwIpTrkGrpDtmfParaEntry
     MAX-ACCESS  not-accessible
     STATUS      current
     DESCRIPTION
       "
       This table is used to config the dtmf parameter of a IP truck group.
       The index of this table is hwIpTrkGrpDtmfGrpName.
       "
     ::= { hwIASVoipObjects 192 }

   hwIpTrkGrpDtmfParaEntry OBJECT-TYPE
     SYNTAX      HwIpTrkGrpDtmfParaEntry
     MAX-ACCESS  not-accessible
     STATUS      current
     DESCRIPTION
       "
       This table is used to config the dtmf parameter of a IP truck group.
       The index of this entry is hwIpTrkGrpDtmfGrpName.
       "
     INDEX    {
                hwIpTrkGrpDtmfGrpName
              }
     ::= { hwIpTrkGrpDtmfParaTable 1 }

   HwIpTrkGrpDtmfParaEntry ::=
     SEQUENCE
     {
       hwIpTrkGrpDtmfGrpName   OCTET STRING,
       hwIpTrkGrpDtmfTransMode INTEGER
     }

   hwIpTrkGrpDtmfGrpName OBJECT-TYPE
     SYNTAX      OCTET STRING(SIZE(0..32))
     MAX-ACCESS  not-accessible
     STATUS      current
     DESCRIPTION
         "
         Indicates the IP truck group name.
         "
     ::= { hwIpTrkGrpDtmfParaEntry 1 }

   hwIpTrkGrpDtmfTransMode OBJECT-TYPE
     SYNTAX      INTEGER{thoroughly(1),erase(2)}
     MAX-ACCESS  read-write
     STATUS      current
     DESCRIPTION
       "
      Indicates the transmission mode of DTMF.
      Options:
      1. thoroughly(1) -transparent transmission
      2. erase(2) -erase DTMF
      Default: thoroughly(1)
       "
     ::= { hwIpTrkGrpDtmfParaEntry 2 }

   hwDspResourceTypeTable OBJECT-TYPE
     SYNTAX      SEQUENCE OF HwDspResourceTypeEntry
     MAX-ACCESS  not-accessible
     STATUS      current
     DESCRIPTION
       "
       This table is used to config the DSP resource type.
       The index of this table is hwDspResourceTypeIndex.
       "
     ::= { hwIASVoipObjects 193 }

   hwDspResourceTypeEntry OBJECT-TYPE
     SYNTAX      HwDspResourceTypeEntry
     MAX-ACCESS  not-accessible
     STATUS      current
     DESCRIPTION
       "
       This table is used to config the DSP resource type.
       The index of this entry is hwDspResourceTypeIndex.
       "
     INDEX    {
                hwDspResourceTypeIndex
              }
     ::= { hwDspResourceTypeTable 1 }

   HwDspResourceTypeEntry ::=
     SEQUENCE
     {
       hwDspResourceTypeIndex   Integer32,
       hwDspResourceTypeValue 	INTEGER
     }

   hwDspResourceTypeIndex OBJECT-TYPE
     SYNTAX      Integer32
     MAX-ACCESS  not-accessible
     STATUS      current
     DESCRIPTION
         "
         Bits 31-26 (six bits): shelf index
         Bits 25-20 (six bits): slot index
         Bits 19-16 (four bits): subboard index
         Bits 15-0 (16 bits): chip index
         "
     ::= { hwDspResourceTypeEntry 1 }

   hwDspResourceTypeValue OBJECT-TYPE
     SYNTAX      INTEGER{default(1),instant(2),reserved(3)}
     MAX-ACCESS  read-write
     STATUS      current
     DESCRIPTION
       "
      Indicates the type of resource type.
      Options:
      1. default(1) - default resource
      2. instant(2) - instant conference resource
      3. reserved(3) - reserved conference resource
       "
 -- DEFVAL      { {default(1)} }
     ::= { hwDspResourceTypeEntry 2 }

   hwDigitMapGroupConfigTable OBJECT-TYPE
     SYNTAX      SEQUENCE OF HwDigitMapGroupConfigEntry
     MAX-ACCESS  not-accessible
     STATUS      current
     DESCRIPTION
       "
       This table is used to config the digitmap group.
       The index of this table is hwDigitMapGroupName.
       "
     ::= { hwIASVoipObjects 194 }

   hwDigitMapGroupConfigEntry OBJECT-TYPE
     SYNTAX      HwDigitMapGroupConfigEntry
     MAX-ACCESS  not-accessible
     STATUS      current
     DESCRIPTION
       "
       This table is used to config the digitmap group.
       The index of this entry is hwDigitMapGroupName.
       "
     INDEX    {
                hwDigitMapGroupName
              }
     ::= { hwDigitMapGroupConfigTable 1 }

   HwDigitMapGroupConfigEntry ::=
     SEQUENCE
     {
       hwDigitMapGroupName      OCTET STRING,
       hwDigitMapGroupNewName   OCTET STRING,
       hwDigitMapGroupReferDigitMapNameList   OCTET STRING,
       hwDigitMapGroupRowStatus RowStatus
     }

   hwDigitMapGroupName OBJECT-TYPE
     SYNTAX      OCTET STRING(SIZE(1..32))
     MAX-ACCESS  not-accessible
     STATUS      current
     DESCRIPTION
         "
         Indicates the digitmap group name.
         "
     ::= { hwDigitMapGroupConfigEntry 1 }

   hwDigitMapGroupNewName OBJECT-TYPE
     SYNTAX      OCTET STRING(SIZE(1..32))
     MAX-ACCESS  read-write
     STATUS      current
     DESCRIPTION
         "
         Indicates the new name of digitmap group.
         "
     ::= { hwDigitMapGroupConfigEntry 2 }

   hwDigitMapGroupReferDigitMapNameList OBJECT-TYPE
     SYNTAX      OCTET STRING(SIZE(1..264))
     MAX-ACCESS  read-write
     STATUS      current
     DESCRIPTION
         "
         Indicates the digitmap name list in digitmap group.
         "
     ::= { hwDigitMapGroupConfigEntry 3 }

   hwDigitMapGroupRowStatus OBJECT-TYPE
     SYNTAX      RowStatus
     MAX-ACCESS  read-write
     STATUS      current
     DESCRIPTION
         "
         Indicates the row status of digitmap group.
         "
     ::= { hwDigitMapGroupConfigEntry 4 }

   hwMgRingDefaultMgcParaTable OBJECT-TYPE
     SYNTAX      SEQUENCE OF HwMgRingDefaultMgcParaEntry
     MAX-ACCESS  not-accessible
     STATUS      current
     DESCRIPTION
       "
         This table is used to config the default type for the common ring.
         The index of this table is hwMgRingDefaultMgcParaMgId.
       "
     ::= { hwIASVoipObjects 196 }

   hwMgRingDefaultMgcParaEntry OBJECT-TYPE
     SYNTAX      HwMgRingDefaultMgcParaEntry
     MAX-ACCESS  not-accessible
     STATUS      current
     DESCRIPTION
       "
 	 This table is used to config the default type for the common ring.
         The index of this entry is hwMgRingDefaultMgcParaMgId.
       "
     INDEX    {
               hwMgRingDefaultMgcParaMgId
              }
     ::= { hwMgRingDefaultMgcParaTable 1 }

   HwMgRingDefaultMgcParaEntry ::=
     SEQUENCE
     {
       hwMgRingDefaultMgcParaMgId	Integer32,
       hwMgRingDefaultMgcparaForRing	Integer32,
       hwMgRingDefaultMgcparaForMwi	Integer32
     }

   hwMgRingDefaultMgcParaMgId OBJECT-TYPE
     SYNTAX      Integer32(0..16777215)
     MAX-ACCESS  not-accessible
     STATUS      current
     DESCRIPTION
         "
         Indicates the MG ID.
         "
     ::= { hwMgRingDefaultMgcParaEntry 1 }

   hwMgRingDefaultMgcparaForRing OBJECT-TYPE
     SYNTAX      Integer32(0..15|255)
     MAX-ACCESS  read-write
     STATUS      current
     DESCRIPTION
         "
         Indicates default peer para of the ring.
         Options:
         255. Indicates resume system default config.
         "
     ::= { hwMgRingDefaultMgcParaEntry 2 }

   hwMgRingDefaultMgcparaForMwi OBJECT-TYPE
     SYNTAX      Integer32(0..15|255)
     MAX-ACCESS  read-write
     STATUS      current
     DESCRIPTION
         "
         Indicates default peer para of the mwi ring.
         Options:
         255. Indicates resume system default config.
         "
     ::= { hwMgRingDefaultMgcParaEntry 3 }

   hwIpTrkGrpTlsParaCfgTable OBJECT-TYPE
     SYNTAX      SEQUENCE OF HwIpTrkGrpTlsParaCfgEntry
     MAX-ACCESS  not-accessible
     STATUS      current
     DESCRIPTION
       "
       This table is used to set the tls attribute.
       The index of this table is hwIpTrkGrpTlsParaGrpName.
       "
     ::= { hwIASVoipObjects 197 }

   hwIpTrkGrpTlsParaCfgEntry OBJECT-TYPE
     SYNTAX      HwIpTrkGrpTlsParaCfgEntry
     MAX-ACCESS  not-accessible
     STATUS      current
     DESCRIPTION
       "
       This table is used to set the tls attribute.
       The index of this entry is hwIpTrkGrpTlsParaGrpName.
       "
     INDEX    {
               hwIpTrkGrpTlsParaGrpName
              }
     ::= { hwIpTrkGrpTlsParaCfgTable 1 }

   HwIpTrkGrpTlsParaCfgEntry ::=
     SEQUENCE
     {
       hwIpTrkGrpTlsParaGrpName         OCTET STRING,
       hwIpTrkGrpTlsParaTlsVersion	INTEGER,
       hwIpTrkGrpTlsParaAuthMode	INTEGER,
       hwIpTrkGrpTlsParaRootCA	        OCTET STRING,
       hwIpTrkGrpTlsParaCert	        OCTET STRING,
       hwIpTrkGrpTlsParaKey             OCTET STRING
     }

   hwIpTrkGrpTlsParaGrpName OBJECT-TYPE
     SYNTAX      OCTET STRING(SIZE(0..32))
     MAX-ACCESS  not-accessible
     STATUS      current
     DESCRIPTION
         "
         Indicates the IP truck group name.
         "
     ::= { hwIpTrkGrpTlsParaCfgEntry 1 }

   hwIpTrkGrpTlsParaTlsVersion OBJECT-TYPE
     SYNTAX      INTEGER{tlsv10(1),tlsv11(2),auto-negotiate(3)}
     MAX-ACCESS  read-write
     STATUS      current
     DESCRIPTION
         "
         Indicates the version of TLS.
         Options:
         1. tlsv10(1) -TLS v1.0
         2. tlsv11(2) -TLS v1.1
         3. auto-negotiate(3) -auto negotiate
         Default: auto-negotiate(3)
         "
     ::= { hwIpTrkGrpTlsParaCfgEntry 2 }

   hwIpTrkGrpTlsParaAuthMode OBJECT-TYPE
     SYNTAX      INTEGER{anonymous(1),server(2),client(3),both(4)}
     MAX-ACCESS  read-write
     STATUS      current
     DESCRIPTION
         "
         Indicates the authentication mode of TLS.
         Options:
         1. anonymous(1) -Anonymous
         2. server(2) -Server
         3. client(3) -Client
         4. both(4) -Both
         Default: anonymous(1)
         "
     ::= { hwIpTrkGrpTlsParaCfgEntry 3 }

   hwIpTrkGrpTlsParaRootCA OBJECT-TYPE
     SYNTAX      OCTET STRING(SIZE (0..64))
     MAX-ACCESS  read-write
     STATUS      current
     DESCRIPTION
         "
         Indicates the name of root certificate.
         "
     ::= { hwIpTrkGrpTlsParaCfgEntry 4 }

   hwIpTrkGrpTlsParaCert OBJECT-TYPE
     SYNTAX      OCTET STRING(SIZE (0..64))
     MAX-ACCESS  read-write
     STATUS      current
     DESCRIPTION
         "
         Indicates the name of certificate.
         "
     ::= { hwIpTrkGrpTlsParaCfgEntry 5 }

   hwIpTrkGrpTlsParaKey OBJECT-TYPE
     SYNTAX      OCTET STRING(SIZE (0..64))
     MAX-ACCESS  read-write
     STATUS      current
     DESCRIPTION
         "
         Indicates the name of key.
         "
     ::= { hwIpTrkGrpTlsParaCfgEntry 6 }

      hwMgRingDefaultRingParaTable OBJECT-TYPE
     SYNTAX      SEQUENCE OF HwMgRingDefaultRingParaEntry
     MAX-ACCESS  not-accessible
     STATUS      current
     DESCRIPTION
       "
       This table is used to set the default short ring type and AOCE ring type.
       The index of this table is hwMgRingDefaultRingparaMgId.
       "
     ::= { hwIASVoipObjects 198 }

   hwMgRingDefaultRingParaEntry OBJECT-TYPE
     SYNTAX      HwMgRingDefaultRingParaEntry
     MAX-ACCESS  not-accessible
     STATUS      current
     DESCRIPTION
       "
       This table is used to set the default short ring type and AOCE ring type.
       The index of this entry is hwMgRingDefaultRingparaMgId.
       "
     INDEX    {
               hwMgRingDefaultRingparaMgId
              }
     ::= { hwMgRingDefaultRingParaTable 1 }

   HwMgRingDefaultRingParaEntry ::=
     SEQUENCE
     {
       hwMgRingDefaultRingparaMgId Integer32,
       hwMgShortRingType	       Integer32,
       hwMgAOCERingType	           Integer32
     }

   hwMgRingDefaultRingparaMgId OBJECT-TYPE
     SYNTAX      Integer32(0..16777215)
     MAX-ACCESS  not-accessible
     STATUS      current
     DESCRIPTION
         "
         Indicates the MG ID.
         "
     ::= { hwMgRingDefaultRingParaEntry 1 }

   hwMgShortRingType OBJECT-TYPE
     SYNTAX      Integer32(1..58)
     MAX-ACCESS  read-write
     STATUS      current
     DESCRIPTION
         "
         Indicates the short ring type.
         Enumerated types:
         1-Null, 2-Normal ring 1:4, 3-Special ring 1:2, 4-Special ring 0.4:0.2:0.4:4, 5-Long ring, 6-Special ring 1.2:2, 7-HK ring 1:3, 8-HK CNTRX 0.4:0.2:0.4:0.2:0.4:3.0,
         9-HK DN-A 0.4:0.2:0.4:3.0, 10-HK ACB 0.4:0.2, 11-HK reminder ring (one tone every 0.4 second; one tone), 12-HK DN-B 1.2:3, 13-CNTRX-IN 0.4:0.2:0.4:0.2:0.4:2.6, 14-Egypt long-distance ring 2:1,
         15-user defined ring mode 0, 16-user defined ring mode 1, 17-user defined ring mode 2, 18-user defined ring mode 3, 19-user defined ring mode 4, 20-user defined ring mode 5, 21-user defined ring mode 6,
         22-user defined ring mode 7, 23-user defined ring mode 8, 24-user defined ring mode 9, 25-user defined ring mode 10, 26-user defined ring mode 11, 27-user defined ring mode 12, 28-user defined ring mode 13,
         29-user defined ring mode 14, 30-user defined ring mode 15, 31-ETSI RP-AS 0.25, 32-Normal ring (FSK) 1:4, 33-Special ring (FSK) 1:2, 34-Special ring (FSK) 0.4:0.2:0.4:4, 35-Special ring (FSK) 1.2:2,
         36-HK ring (FSK) 1:3, 37-HK CNTRX (FSK) 0.4:0.2:0.4:0.2:0.4:3.0, 38-HK DN-A (FSK) 0.4:0.2:0.4:3.0, 39-HK DN-B (FSK) 1.2:3, 40-CNTRX-IN (FSK) 0.4:0.2:0.4:0.2:0.4:2.6, 41-Egypt long-distance ring (FSK) 2:1,
         42-user defined FSK ring mode 0, 43-user defined FSK ring mode 1, 44-user defined FSK ring mode 2, 45-user defined FSK ring mode 3, 46-user defined FSK ring mode 4, 47-user defined FSK ring mode 5,
         48-user defined FSK ring mode 6, 49-user defined FSK ring mode 7, 50-user defined FSK ring mode 8, 51-user defined FSK ring mode 9, 52-user defined FSK ring mode 10, 53-user defined FSK ring mode 11,
         54-user defined FSK ring mode 12, 55-user defined FSK ring mode 13, 56-user defined FSK ring mode 14, 57-user defined FSK ring mode 15, 58-ETSI RP-AS (FSK) 0.25
         "
     ::= { hwMgRingDefaultRingParaEntry 2 }

   hwMgAOCERingType OBJECT-TYPE
     SYNTAX      Integer32(1..28)
     MAX-ACCESS  read-write
     STATUS      current
     DESCRIPTION
         "
         Indicates the AOCE ring type.
         Enumeration type:
         1-Null, 2-Normal ring (FSK) 1:4, 3-Special ring (FSK) 1:2, 4-Special ring (FSK) 0.4:0.2:0.4:4, 5-Special ring (FSK) 1.2:2, 6-HK ring (FSK) 1:3, 7-HK CNTRX (FSK) 0.4:0.2:0.4:0.2:0.4:3.0,
         8-HK DN-A (FSK) 0.4:0.2:0.4:3.0, 9-HK DN-B (FSK) 1.2:3, 10-CNTRX-IN (FSK) 0.4:0.2:0.4:0.2:0.4:2.6, 11-Egypt long-distance ring (FSK) 2:1, 12-user defined FSK ring mode 0, 13-user defined FSK ring mode 1,
         14-user defined FSK ring mode 2, 15-user defined FSK ring mode 3, 16-user defined FSK ring mode 4, 17-user defined FSK ring mode 5, 18-user defined FSK ring mode 6, 19-user defined FSK ring mode 7,
         20-user defined FSK ring mode 8, 21-user defined FSK ring mode 9, 22-user defined FSK ring mode 10, 23-user defined FSK ring mode 11, 24-user defined FSK ring mode 12, 25-user defined FSK ring mode 13,
         26-user defined FSK ring mode 14, 27-user defined FSK ring mode 15, 28-ETSI RP-AS (FSK) 0.25
         "
     ::= { hwMgRingDefaultRingParaEntry 3 }

     hwVGWNumberChangeTable OBJECT-TYPE
     SYNTAX      SEQUENCE OF HwVGWNumberChangeEntry
     MAX-ACCESS  not-accessible
     STATUS      current
     DESCRIPTION
       "
       This table is used to set the scheme od number change.
       The index of this table is hwVGWNumberChangeName.
       "
     ::= { hwIASVoipObjects 199 }

   hwVGWNumberChangeEntry OBJECT-TYPE
     SYNTAX      HwVGWNumberChangeEntry
     MAX-ACCESS  not-accessible
     STATUS      current
     DESCRIPTION
       "
       This table is used to set the scheme od number change.
       The index of this entry is hwVGWNumberChangeName.
       "
     INDEX    {
               hwVGWNumberChangeName
              }
     ::= { hwVGWNumberChangeTable 1 }

   HwVGWNumberChangeEntry ::=
     SEQUENCE
     {
       hwVGWNumberChangeName 			 OCTET STRING,
       hwVGWNumberChangeType	     INTEGER,
       hwVGWNumberChangeStartPos	 Integer32,
       hwVGWNumberChangeNewNumber  OCTET STRING,
       hwVGWNumberChangeChangeLen  Integer32,
       hwVGWNumberChangeRowStatus  RowStatus,
       hwVGWNumberChangeTranslationRuleSetName OCTET STRING
     }

   hwVGWNumberChangeName OBJECT-TYPE
     SYNTAX      OCTET STRING(SIZE(1..32))
     MAX-ACCESS  not-accessible
     STATUS      current
     DESCRIPTION
         "
         Indicates the name of number change.
         "
     ::= { hwVGWNumberChangeEntry 1 }

   hwVGWNumberChangeType OBJECT-TYPE
     SYNTAX      INTEGER{insert(1),replace(2),delete(3),translation-rule-set(4)}
     MAX-ACCESS  read-write
     STATUS      current
     DESCRIPTION
         "
         Indicates the change type of number change.
         Options:
         1. insert(1) - insert new number operation
         2. replace(2) - replace number operation
         3. delete(3) - delete number operation
         4. translation-rule-set(4) - translation rule set operation
         "
     ::= { hwVGWNumberChangeEntry 2 }

   hwVGWNumberChangeStartPos OBJECT-TYPE
     SYNTAX      Integer32(1..64|255)
     MAX-ACCESS  read-write
     STATUS      current
     DESCRIPTION
         "
         Indicates the change start position of source number.
         "
     ::= { hwVGWNumberChangeEntry 3 }

   hwVGWNumberChangeNewNumber OBJECT-TYPE
     SYNTAX      OCTET STRING(SIZE(1..32))
     MAX-ACCESS  read-write
     STATUS      current
     DESCRIPTION
         "
         Indicates the modify number of number change.
         "
     ::= { hwVGWNumberChangeEntry 4 }

   hwVGWNumberChangeChangeLen OBJECT-TYPE
     SYNTAX      Integer32(1..64|255)
     MAX-ACCESS  read-write
     STATUS      current
     DESCRIPTION
         "
         Indicates the modify length of number change,255 means to set this value invalid.
         "
     ::= { hwVGWNumberChangeEntry 5 }

   hwVGWNumberChangeRowStatus OBJECT-TYPE
     SYNTAX      RowStatus
     MAX-ACCESS  read-write
     STATUS      current
     DESCRIPTION
         "
         Indicates the row status.
         "
     ::= { hwVGWNumberChangeEntry 6 }

   hwVGWNumberChangeTranslationRuleSetName OBJECT-TYPE
     SYNTAX      OCTET STRING(SIZE(1..32))
     MAX-ACCESS  read-write
     STATUS      current
     DESCRIPTION
         "
         Indicates the translation rule set name of number change.
         "
     ::= { hwVGWNumberChangeEntry 7 }

   hwSRTPParameterTable OBJECT IDENTIFIER ::= {  hwIASVoipObjects 200  }
   hwSrtpSwitch OBJECT-TYPE
     SYNTAX      INTEGER{enable(1),disable(2)}
     MAX-ACCESS  read-write
     STATUS      current
     DESCRIPTION
         "
         Indicates the SRTP enable or disable.
         Options:
         1. enable(1) -enable
         2. disable(2) -disable
         Default: disable(2)
         "
         -- DEFVAL      { disable }
     ::= { hwSRTPParameterTable 1 }

   hwSrtpMode OBJECT-TYPE
     SYNTAX      INTEGER{configuration(1),negotiation(2)}
     MAX-ACCESS  read-write
     STATUS      current
     DESCRIPTION
         "
         Indicates the Master SALT key achieve-mode: configuration or negotiation.
         Options:
         1. configuration(1) - configuration
         2. negotiation(2) - negotiation
         Default: configuration(1)
         "
         -- DEFVAL      { {configuration(1)} }
     ::= { hwSRTPParameterTable 2 }

   hwSrtpKey OBJECT-TYPE
     SYNTAX      OCTET STRING(SIZE(14..32))
     MAX-ACCESS  read-write
     STATUS      current
     DESCRIPTION
         "
         Indicates the Master SALT key.
         "
     ::= { hwSRTPParameterTable 3 }

     hwTranslationRuleConfigTable OBJECT-TYPE
     SYNTAX      SEQUENCE OF HwTranslationRuleConfigEntry
     MAX-ACCESS  not-accessible
     STATUS      current
     DESCRIPTION
       "
       This table is used to set the translation rule.
       The index of this table is hwTranslationRuleName.
       "
     ::= { hwIASVoipObjects 201 }

   hwTranslationRuleConfigEntry OBJECT-TYPE
     SYNTAX      HwTranslationRuleConfigEntry
     MAX-ACCESS  not-accessible
     STATUS      current
     DESCRIPTION
       "
       This table is used to set the translation rule.
       The index of this entry is hwTranslationRuleName.
       "
     INDEX    {
               IMPLIED hwTranslationRuleName
              }
     ::= { hwTranslationRuleConfigTable 1 }

   HwTranslationRuleConfigEntry ::=
     SEQUENCE
     {
       hwTranslationRuleName 		        	 OCTET STRING,
       hwTranslationRuleMatchPattern	     OCTET STRING,
       hwTranslationRuleReplacePattern  	 OCTET STRING,
       hwTranslationRuleRowStatus          RowStatus
     }

   hwTranslationRuleName OBJECT-TYPE
     SYNTAX      OCTET STRING(SIZE(1..32))
     MAX-ACCESS  not-accessible
     STATUS      current
     DESCRIPTION
         "
         Indicates the name of translation rule.
         "
     ::= { hwTranslationRuleConfigEntry 1 }

  hwTranslationRuleMatchPattern OBJECT-TYPE
     SYNTAX      OCTET STRING(SIZE(1..32))
     MAX-ACCESS  read-write
     STATUS      current
     DESCRIPTION
         "
         Indicates the match pattern of translation rule.
         "
     ::= { hwTranslationRuleConfigEntry 2 }

  hwTranslationRuleReplacePattern OBJECT-TYPE
     SYNTAX      OCTET STRING(SIZE(1..64))
     MAX-ACCESS  read-write
     STATUS      current
     DESCRIPTION
         "
         Indicates the replace pattern of translation rule.
         "
     ::= { hwTranslationRuleConfigEntry 3 }

   hwTranslationRuleRowStatus OBJECT-TYPE
     SYNTAX      RowStatus
     MAX-ACCESS  read-write
     STATUS      current
     DESCRIPTION
         "
         Indicates the row status.
         "
     ::= { hwTranslationRuleConfigEntry 4 }

   hwTranslationRuleSetTable OBJECT-TYPE
     SYNTAX      SEQUENCE OF HwTranslationRuleSetEntry
     MAX-ACCESS  not-accessible
     STATUS      current
     DESCRIPTION
       "
       This table is used to config the translation rule set.
       The index of this table is hwTranslationRuleSetName.
       "
     ::= { hwIASVoipObjects 202 }

   hwTranslationRuleSetEntry OBJECT-TYPE
     SYNTAX      HwTranslationRuleSetEntry
     MAX-ACCESS  not-accessible
     STATUS      current
     DESCRIPTION
       "
       This table is used to config the translation rule set.
       The index of this entry is hwTranslationRuleSetName.
       "
     INDEX    {
                IMPLIED hwTranslationRuleSetName
              }
     ::= { hwTranslationRuleSetTable 1 }

   HwTranslationRuleSetEntry ::=
     SEQUENCE
     {
       hwTranslationRuleSetName       OCTET STRING,
       hwTranslationRuleList          OCTET STRING,
       hwTranslationRuleSetRowStatus  RowStatus
     }

   hwTranslationRuleSetName OBJECT-TYPE
     SYNTAX      OCTET STRING(SIZE(1..32))
     MAX-ACCESS  not-accessible
     STATUS      current
     DESCRIPTION
         "
         Indicates the name of translation rule set.
         "
     ::= { hwTranslationRuleSetEntry 1 }

   hwTranslationRuleList OBJECT-TYPE
     SYNTAX      OCTET STRING(SIZE(0..591))
     MAX-ACCESS  read-write
     STATUS      current
     DESCRIPTION
         "
         Indicates the name and the priority of the translation rules in a translation rule set.
         "
     ::= { hwTranslationRuleSetEntry 2 }

   hwTranslationRuleSetRowStatus OBJECT-TYPE
     SYNTAX      RowStatus
     MAX-ACCESS  read-write
     STATUS      current
     DESCRIPTION
         "
         Indicates the row status of translation rule set.
         "
     ::= { hwTranslationRuleSetEntry 3 }

   hwMgStreamQosConfigTable OBJECT-TYPE
     SYNTAX      SEQUENCE OF HwMgStreamQosConfigEntry
     MAX-ACCESS  not-accessible
     STATUS      current
     DESCRIPTION
       "
       This table is used to set the IP stream QOS of different VAG.
       The indexes of this table are hwMgStreamQosCfgProtoType and hwMgStreamQosCfgInterfaceId.
       "
     ::= { hwIASVoipObjects 203 }

   hwMgStreamQosConfigEntry OBJECT-TYPE
     SYNTAX      HwMgStreamQosConfigEntry
     MAX-ACCESS  not-accessible
     STATUS      current
     DESCRIPTION
       "
       This table is used to set the IP stream QOS of different VAG.
       The indexes of this entry are hwMgStreamQosCfgProtoType and hwMgStreamQosCfgInterfaceId.
       "
     INDEX    {
               hwMgStreamQosCfgProtoType,
               hwMgStreamQosCfgInterfaceId
              }
     ::= { hwMgStreamQosConfigTable 1 }

   HwMgStreamQosConfigEntry ::=
     SEQUENCE
     {
       hwMgStreamQosCfgProtoType             INTEGER,
       hwMgStreamQosCfgInterfaceId           Integer32,
       hwMgStreamQosCfgNormalMediaDscp	     Integer32,
       hwMgStreamQosCfgEmergencyMediaDscp    Integer32,
       hwMgStreamQosCfgNormalSignalingDscp     Integer32,
       hwMgStreamQosCfgEmergencySignalingDscp  Integer32
     }

   hwMgStreamQosCfgProtoType OBJECT-TYPE
     SYNTAX      INTEGER{iua(1),h248(2),sip(3)}
     MAX-ACCESS  not-accessible
     STATUS      current
     DESCRIPTION
         "
         Indicates the protocol of the interface to config IP stream QOS.
         Options:
         1. iua(1) - the interface ID is IUA LinkNO.
         2. h248(2) - the interface ID is VAG NO. of H248 interface
         3. sip(3)  - the interface ID is VAG NO. of SIP interface
         "
     ::= { hwMgStreamQosConfigEntry 1 }

   hwMgStreamQosCfgInterfaceId OBJECT-TYPE
     SYNTAX      Integer32(1..16777215)
     MAX-ACCESS  not-accessible
     STATUS      current
     DESCRIPTION
         "
         Indicates the IP stream QOS interface ID.
         if Protocol Type is iua(1), this parameter for IUA LinkNo(0..15);
         if Protocol Type is h248(2), this parameter for H248 interface ID(0..16777215);
         if Protocol Type is sip(3), this parameter for SIP interface ID(0..16777215);
         "
     ::= { hwMgStreamQosConfigEntry 2 }

   hwMgStreamQosCfgNormalMediaDscp OBJECT-TYPE
     SYNTAX      Integer32(0..63|255)
     MAX-ACCESS  read-write
     STATUS      current
     DESCRIPTION
         "
         Indicates the QOS DSCP value of normal call media stream,255 means to set this value invalid.

         "
     ::= { hwMgStreamQosConfigEntry 3 }

   hwMgStreamQosCfgEmergencyMediaDscp OBJECT-TYPE
     SYNTAX      Integer32(0..63|255)
     MAX-ACCESS  read-write
     STATUS      current
     DESCRIPTION
         "
         Indicates the QOS DSCP value of emergency call media stream,255 means to set this value invalid.
         "
     ::= { hwMgStreamQosConfigEntry 4 }

   hwMgStreamQosCfgNormalSignalingDscp OBJECT-TYPE
     SYNTAX      Integer32(0..63|255)
     MAX-ACCESS  read-write
     STATUS      current
     DESCRIPTION
         "
         Indicates the QOS DSCP value of normal call signaling stream,255 means to set this value invalid.
         "
     ::= { hwMgStreamQosConfigEntry 5 }

   hwMgStreamQosCfgEmergencySignalingDscp OBJECT-TYPE
     SYNTAX      Integer32(0..63|255)
     MAX-ACCESS  read-write
     STATUS      current
     DESCRIPTION
         "
         Indicates the QOS DSCP value of emergency call signaling stream,255 means to set this value invalid.
         "
     ::= { hwMgStreamQosConfigEntry 6 }

END
