--
-- HUAWEI-STORAGE-NAS-MIB.mib
-- MIB generated by MG-SOFT Visual MIB Builder Version 4.0 Build 347
-- Wednesday, July 15, 2015 at 17:31:06
--

--  HUAWEI-STORAGE-NAS-MIB.mib
-- MIB generated by MG-SOFT Visual MIB Builder Version 4.0 Build 347
-- Thursday, June 18, 2015 at 16:41:12
--

	HUAWEI-STORAGE-NAS-MIB DEFINITIONS ::= BEGIN

		IMPORTS
			OBJECT-GROUP, MODULE-COMPLIANCE
				FROM SNMPv2-CONF
			enterprises, Unsigned32, Counter32, Counter64,
			OBJECT-TYPE, MODULE-IDENTITY
				FROM SNMPv2-SMI
			TEXTUAL-CONVENTION
				FROM SNMPv2-TC;


		hwStorage MODULE-IDENTITY
			LAST-UPDATED "201008111239Z"		-- August 11, 2010 at 12:39 GMT
			ORGANIZATION
				"Huawei Technologies Co.,Ltd."
			CONTACT-INFO
				"Huawei Industrial Base
				Bantian, Longgang
				Shenzhen 518129
				People's Republic of China
				Website: http://www.huawei.com
				Email: support@huawei.com"
			DESCRIPTION
				"Description.     "
			REVISION "201411061532Z"		-- November 06, 2014 at 15:32 GMT
			DESCRIPTION
				"   "
			::= { huaweistorage 4 }



--
-- Textual conventions
--

--  August 11, 2010 at 12:39 GMT
-- November 06, 2014 at 15:32 GMT
--
-- Textual conventions
--
--  August 11, 2010 at 12:39 GMT
-- April 06, 2013 at 13:54 GMT
--
-- Textual conventions
--
		NodeCodeString ::= TEXTUAL-CONVENTION
			DISPLAY-HINT
				"255a"
			STATUS current
			DESCRIPTION
				"characters in length."
			SYNTAX OCTET STRING (SIZE (15..17))


--
-- Node definitions
--

--  Node definitions
--
		huaweistorage OBJECT IDENTIFIER ::= { enterprises 34774 }


		hwISM OBJECT IDENTIFIER ::= { hwStorage 1 }


		hwStorageDevice OBJECT IDENTIFIER ::= { hwISM 23 }


		hwNasInfo OBJECT IDENTIFIER ::= { hwStorageDevice 7 }


--
		hwInfoShareNFSTable OBJECT-TYPE
			SYNTAX SEQUENCE OF HwInfoShareNFSEntry
			MAX-ACCESS not-accessible
			STATUS current
			DESCRIPTION
				" "
			::= { hwNasInfo 1 }


		hwInfoShareNFSEntry OBJECT-TYPE
			SYNTAX HwInfoShareNFSEntry
			MAX-ACCESS not-accessible
			STATUS current
			DESCRIPTION
				"  "
			INDEX { hwInfoShareNFSShareID }
			::= { hwInfoShareNFSTable 1 }


		HwInfoShareNFSEntry ::=
			SEQUENCE {
				hwInfoShareNFSShareID
					OCTET STRING,
				hwInfoShareNFSFileSystemID
					OCTET STRING,
				hwInfoShareNFSDescription
					OCTET STRING,
				hwInfoShareNFSLocalPath
					OCTET STRING
			 }

--   1.3.6.1.4.1.34774.4.1.23.4.1.1.1
-- 1.3.6.1.4.1.34774.4.1.23.7.1.1.1
		hwInfoShareNFSShareID OBJECT-TYPE
			SYNTAX OCTET STRING
			MAX-ACCESS read-only
			STATUS current
			DESCRIPTION
				"  "
			::= { hwInfoShareNFSEntry 1 }


--   1.3.6.1.4.1.34774.4.1.23.4.1.1.2
-- 1.3.6.1.4.1.34774.4.1.23.7.1.1.2
		hwInfoShareNFSFileSystemID OBJECT-TYPE
			SYNTAX OCTET STRING
			MAX-ACCESS read-only
			STATUS current
			DESCRIPTION
				"  "
			::= { hwInfoShareNFSEntry 2 }


--   1.3.6.1.4.1.34774.4.1.23.4.1.1.3
-- 1.3.6.1.4.1.34774.4.1.23.7.1.1.3
		hwInfoShareNFSDescription OBJECT-TYPE
			SYNTAX OCTET STRING
			MAX-ACCESS read-only
			STATUS current
			DESCRIPTION
				"  "
			::= { hwInfoShareNFSEntry 3 }


--   1.3.6.1.4.1.34774.4.1.23.4.1.1.4
-- 1.3.6.1.4.1.34774.4.1.23.7.1.1.4
		hwInfoShareNFSLocalPath OBJECT-TYPE
			SYNTAX OCTET STRING
			MAX-ACCESS read-only
			STATUS current
			DESCRIPTION
				"  "
			::= { hwInfoShareNFSEntry 4 }


--   1.3.6.1.4.1.34774.4.1.23.4.1
-- 1.3.6.1.4.1.34774.4.1.23.7.2
		hwInfoShareCIFSTable OBJECT-TYPE
			SYNTAX SEQUENCE OF HwInfoShareCIFSEntry
			MAX-ACCESS not-accessible
			STATUS current
			DESCRIPTION
				" "
			::= { hwNasInfo 2 }


--
-- 1.3.6.1.4.1.34774.4.1.23.4.1.1
-- 1.3.6.1.4.1.34774.4.1.23.7.2.1
		hwInfoShareCIFSEntry OBJECT-TYPE
			SYNTAX HwInfoShareCIFSEntry
			MAX-ACCESS not-accessible
			STATUS current
			DESCRIPTION
				"  "
			INDEX { hwInfoShareCIFSID }
			::= { hwInfoShareCIFSTable 1 }


		HwInfoShareCIFSEntry ::=
			SEQUENCE {
				hwInfoShareCIFSID
					OCTET STRING,
				hwInfoShareCIFSName
					OCTET STRING,
				hwInfoShareCIFSFileSystemID
					OCTET STRING,
				hwInfoShareCIFSDescription
					OCTET STRING,
				hwInfoShareCIFSLocalPath
					OCTET STRING,
				hwInfoShareCIFSOplockEnabled
					Unsigned32,
				hwInfoShareCIFSNotifyEnabled
					Unsigned32,
				hwInfoShareCIFSContAvailableEna
					Unsigned32
			 }

--   1.3.6.1.4.1.34774.4.1.23.4.1.1.1
-- 1.3.6.1.4.1.34774.4.1.23.7.2.1.1
		hwInfoShareCIFSID OBJECT-TYPE
			SYNTAX OCTET STRING
			MAX-ACCESS read-only
			STATUS current
			DESCRIPTION
				"  "
			::= { hwInfoShareCIFSEntry 1 }


--   1.3.6.1.4.1.34774.4.1.23.4.1.1.2
-- 1.3.6.1.4.1.34774.4.1.23.7.2.1.2
		hwInfoShareCIFSName OBJECT-TYPE
			SYNTAX OCTET STRING
			MAX-ACCESS read-only
			STATUS current
			DESCRIPTION
				"  "
			::= { hwInfoShareCIFSEntry 2 }


--   1.3.6.1.4.1.34774.4.1.23.4.1.1.3
-- 1.3.6.1.4.1.34774.4.1.23.7.2.1.3
		hwInfoShareCIFSFileSystemID OBJECT-TYPE
			SYNTAX OCTET STRING
			MAX-ACCESS read-only
			STATUS current
			DESCRIPTION
				"  "
			::= { hwInfoShareCIFSEntry 3 }


--   1.3.6.1.4.1.34774.4.1.23.4.1.1.4
-- 1.3.6.1.4.1.34774.4.1.23.7.2.1.4
		hwInfoShareCIFSDescription OBJECT-TYPE
			SYNTAX OCTET STRING
			MAX-ACCESS read-only
			STATUS current
			DESCRIPTION
				"  "
			::= { hwInfoShareCIFSEntry 4 }


--   1.3.6.1.4.1.34774.4.1.23.4.1.1.4
-- 1.3.6.1.4.1.34774.4.1.23.7.2.1.5
		hwInfoShareCIFSLocalPath OBJECT-TYPE
			SYNTAX OCTET STRING
			MAX-ACCESS read-only
			STATUS current
			DESCRIPTION
				"  "
			::= { hwInfoShareCIFSEntry 5 }


--   1.3.6.1.4.1.34774.4.1.23.4.1.1.4
-- 1.3.6.1.4.1.34774.4.1.23.7.2.1.6
		hwInfoShareCIFSOplockEnabled OBJECT-TYPE
			SYNTAX Unsigned32
			MAX-ACCESS read-only
			STATUS current
			DESCRIPTION
				"  "
			::= { hwInfoShareCIFSEntry 6 }


--   1.3.6.1.4.1.34774.4.1.23.4.1.1.4
-- 1.3.6.1.4.1.34774.4.1.23.7.2.1.7
		hwInfoShareCIFSNotifyEnabled OBJECT-TYPE
			SYNTAX Unsigned32
			MAX-ACCESS read-only
			STATUS current
			DESCRIPTION
				"  "
			::= { hwInfoShareCIFSEntry 7 }


--   1.3.6.1.4.1.34774.4.1.23.4.1.1.4
-- 1.3.6.1.4.1.34774.4.1.23.7.2.1.8
		hwInfoShareCIFSContAvailableEna OBJECT-TYPE
			SYNTAX Unsigned32
			MAX-ACCESS read-only
			STATUS current
			DESCRIPTION
				"  "
			::= { hwInfoShareCIFSEntry 8 }


--   1.3.6.1.4.1.34774.4.1.23.4.1
-- 1.3.6.1.4.1.34774.4.1.23.7.3
		hwInfoSharePermsNFSTable OBJECT-TYPE
			SYNTAX SEQUENCE OF HwInfoSharePermsNFSEntry
			MAX-ACCESS not-accessible
			STATUS current
			DESCRIPTION
				" "
			::= { hwNasInfo 3 }


--
-- 1.3.6.1.4.1.34774.4.1.23.4.1.1
-- 1.3.6.1.4.1.34774.4.1.23.7.3.1
		hwInfoSharePermsNFSEntry OBJECT-TYPE
			SYNTAX HwInfoSharePermsNFSEntry
			MAX-ACCESS not-accessible
			STATUS current
			DESCRIPTION
				"  "
			INDEX { hwInfoSharePermsNFSID }
			::= { hwInfoSharePermsNFSTable 1 }


		HwInfoSharePermsNFSEntry ::=
			SEQUENCE {
				hwInfoSharePermsNFSID
					OCTET STRING,
				hwInfoSharePermsNFSAccessName
					OCTET STRING,
				hwInfoSharePermsNFSShareID
					OCTET STRING,
				hwInfoSharePermsNFSAccessType
					Unsigned32,
				hwInfoSharePermsNFSSyncEnabled
					Unsigned32,
				hwInfoSharePermsNFSAllSquashEna
					Unsigned32,
				hwInfoSharePermsNFSRootSquashEna
					Unsigned32
			 }

--   1.3.6.1.4.1.34774.4.1.23.4.1.1.1
-- 1.3.6.1.4.1.34774.4.1.23.7.3.1.1
		hwInfoSharePermsNFSID OBJECT-TYPE
			SYNTAX OCTET STRING
			MAX-ACCESS read-only
			STATUS current
			DESCRIPTION
				"  "
			::= { hwInfoSharePermsNFSEntry 1 }


--   1.3.6.1.4.1.34774.4.1.23.4.1.1.1
-- 1.3.6.1.4.1.34774.4.1.23.7.3.1.2
		hwInfoSharePermsNFSAccessName OBJECT-TYPE
			SYNTAX OCTET STRING
			MAX-ACCESS read-only
			STATUS current
			DESCRIPTION
				"  "
			::= { hwInfoSharePermsNFSEntry 2 }


--   1.3.6.1.4.1.34774.4.1.23.4.1.1.1
-- 1.3.6.1.4.1.34774.4.1.23.7.3.1.3
		hwInfoSharePermsNFSShareID OBJECT-TYPE
			SYNTAX OCTET STRING
			MAX-ACCESS read-only
			STATUS current
			DESCRIPTION
				"  "
			::= { hwInfoSharePermsNFSEntry 3 }


--   1.3.6.1.4.1.34774.4.1.23.4.1.1.1
-- 1.3.6.1.4.1.34774.4.1.23.7.3.1.4
		hwInfoSharePermsNFSAccessType OBJECT-TYPE
			SYNTAX Unsigned32
			MAX-ACCESS read-only
			STATUS current
			DESCRIPTION
				"  "
			::= { hwInfoSharePermsNFSEntry 4 }


--   1.3.6.1.4.1.34774.4.1.23.4.1.1.1
-- 1.3.6.1.4.1.34774.4.1.23.7.3.1.5
		hwInfoSharePermsNFSSyncEnabled OBJECT-TYPE
			SYNTAX Unsigned32
			MAX-ACCESS read-only
			STATUS current
			DESCRIPTION
				"  "
			::= { hwInfoSharePermsNFSEntry 5 }


--   1.3.6.1.4.1.34774.4.1.23.4.1.1.1
-- 1.3.6.1.4.1.34774.4.1.23.7.3.1.6
		hwInfoSharePermsNFSAllSquashEna OBJECT-TYPE
			SYNTAX Unsigned32
			MAX-ACCESS read-only
			STATUS current
			DESCRIPTION
				"  "
			::= { hwInfoSharePermsNFSEntry 6 }


--   1.3.6.1.4.1.34774.4.1.23.4.1.1.1
-- 1.3.6.1.4.1.34774.4.1.23.7.3.1.7
		hwInfoSharePermsNFSRootSquashEna OBJECT-TYPE
			SYNTAX Unsigned32
			MAX-ACCESS read-only
			STATUS current
			DESCRIPTION
				"  "
			::= { hwInfoSharePermsNFSEntry 7 }


--   1.3.6.1.4.1.34774.4.1.23.4.1
-- 1.3.6.1.4.1.34774.4.1.23.7.4
		hwInfoSharePermsCIFSTable OBJECT-TYPE
			SYNTAX SEQUENCE OF HwInfoSharePermsCIFSEntry
			MAX-ACCESS not-accessible
			STATUS current
			DESCRIPTION
				" "
			::= { hwNasInfo 4 }


--
-- 1.3.6.1.4.1.34774.4.1.23.4.1.1
-- 1.3.6.1.4.1.34774.4.1.23.7.4.1
		hwInfoSharePermsCIFSEntry OBJECT-TYPE
			SYNTAX HwInfoSharePermsCIFSEntry
			MAX-ACCESS not-accessible
			STATUS current
			DESCRIPTION
				"  "
			INDEX { hwInfoSharePermsCIFSID }
			::= { hwInfoSharePermsCIFSTable 1 }


		HwInfoSharePermsCIFSEntry ::=
			SEQUENCE {
				hwInfoSharePermsCIFSID
					OCTET STRING,
				hwInfoSharePermsCIFSAccessName
					OCTET STRING,
				hwInfoSharePermsCIFSShareID
					OCTET STRING,
				hwInfoSharePermsCIFSDomainType
					Unsigned32,
				hwInfoSharePermsCIFSPermsType
					Unsigned32
			 }

--   1.3.6.1.4.1.34774.4.1.23.4.1.1.1
-- 1.3.6.1.4.1.34774.4.1.23.7.4.1.1
		hwInfoSharePermsCIFSID OBJECT-TYPE
			SYNTAX OCTET STRING
			MAX-ACCESS read-only
			STATUS current
			DESCRIPTION
				"  "
			::= { hwInfoSharePermsCIFSEntry 1 }


--   1.3.6.1.4.1.34774.4.1.23.4.1.1.1
-- 1.3.6.1.4.1.34774.4.1.23.7.4.1.2
		hwInfoSharePermsCIFSAccessName OBJECT-TYPE
			SYNTAX OCTET STRING
			MAX-ACCESS read-only
			STATUS current
			DESCRIPTION
				"  "
			::= { hwInfoSharePermsCIFSEntry 2 }


--   1.3.6.1.4.1.34774.4.1.23.4.1.1.1
-- 1.3.6.1.4.1.34774.4.1.23.7.4.1.3
		hwInfoSharePermsCIFSShareID OBJECT-TYPE
			SYNTAX OCTET STRING
			MAX-ACCESS read-only
			STATUS current
			DESCRIPTION
				"  "
			::= { hwInfoSharePermsCIFSEntry 3 }


--   1.3.6.1.4.1.34774.4.1.23.4.1.1.1
-- 1.3.6.1.4.1.34774.4.1.23.7.4.1.4
		hwInfoSharePermsCIFSDomainType OBJECT-TYPE
			SYNTAX Unsigned32
			MAX-ACCESS read-only
			STATUS current
			DESCRIPTION
				"  "
			::= { hwInfoSharePermsCIFSEntry 4 }


--   1.3.6.1.4.1.34774.4.1.23.4.1.1.1
-- 1.3.6.1.4.1.34774.4.1.23.7.4.1.5
		hwInfoSharePermsCIFSPermsType OBJECT-TYPE
			SYNTAX Unsigned32
			MAX-ACCESS read-only
			STATUS current
			DESCRIPTION
				"  "
			::= { hwInfoSharePermsCIFSEntry 5 }


--   1.3.6.1.4.1.34774.4.1.23.4.1
-- 1.3.6.1.4.1.34774.4.1.23.7.5
		hwInfoLogicalPortTable OBJECT-TYPE
			SYNTAX SEQUENCE OF HwInfoLogicalPortEntry
			MAX-ACCESS not-accessible
			STATUS current
			DESCRIPTION
				" "
			::= { hwNasInfo 5 }


--
-- 1.3.6.1.4.1.34774.4.1.23.4.1.1
-- 1.3.6.1.4.1.34774.4.1.23.7.5.1
		hwInfoLogicalPortEntry OBJECT-TYPE
			SYNTAX HwInfoLogicalPortEntry
			MAX-ACCESS not-accessible
			STATUS current
			DESCRIPTION
				"  "
			INDEX { hwInfoLogicalPortID }
			::= { hwInfoLogicalPortTable 1 }


		HwInfoLogicalPortEntry ::=
			SEQUENCE {
				hwInfoLogicalPortID
					OCTET STRING,
				hwInfoLogicalPorttName
					OCTET STRING,
				hwInfoLogicalPortRunStatus
					Unsigned32,
				hwInfoLogicalPortIPv4Addr
					OCTET STRING,
				hwInfoLogicalPortIPv4Mask
					OCTET STRING,
				hwInfoLogicalPortIPv4Gateway
					OCTET STRING,
				hwInfoLogicalPortIPv6Addr
					OCTET STRING,
				hwInfoLogicalPortIPv6Mask
					OCTET STRING,
				hwInfoLogicalPortIPv6Gateway
					OCTET STRING,
				hwInfoLogicalPortRole
					Unsigned32,
				hwInfoLogicalPortSupportProt
					Unsigned32,
				hwInfoLogicalPortHomePortType
					Unsigned32,
				hwInfoLogicalPortHomePortID
					OCTET STRING,
				hwInfoLogicalPortOwnerCtrlID
					OCTET STRING,
				hwInfoLogicalPortCurrPortType
					Unsigned32,
				hwInfoLogicalPortCurrPortID
					OCTET STRING,
				hwInfoLogicalPortWorkCtrlID
					OCTET STRING,
				hwInfoLogicalPortActState
					Unsigned32,
				hwInfoLogicalPortAddrFamily
					Unsigned32,
				hwInfoLogicalPortIsPrivate
					Unsigned32,
				hwInfoLogicalPortFailOVGID
					OCTET STRING,
				hwInfoLogicalPortFailOVEnable
					Unsigned32,
				hwInfoLogicalPortFailBackMode
					Unsigned32,
				hwInfoLogicalPortFailOVGName
					OCTET STRING
			 }

--   1.3.6.1.4.1.34774.4.1.23.4.1.1.1
-- 1.3.6.1.4.1.34774.4.1.23.7.5.1.1
		hwInfoLogicalPortID OBJECT-TYPE
			SYNTAX OCTET STRING
			MAX-ACCESS read-only
			STATUS current
			DESCRIPTION
				"  "
			::= { hwInfoLogicalPortEntry 1 }


--   1.3.6.1.4.1.34774.4.1.23.4.1.1.2
-- 1.3.6.1.4.1.34774.4.1.23.7.5.1.2
		hwInfoLogicalPorttName OBJECT-TYPE
			SYNTAX OCTET STRING
			MAX-ACCESS read-only
			STATUS current
			DESCRIPTION
				"  "
			::= { hwInfoLogicalPortEntry 2 }


--   1.3.6.1.4.1.34774.4.1.23.4.1.1.3
-- 1.3.6.1.4.1.34774.4.1.23.7.5.1.3
		hwInfoLogicalPortRunStatus OBJECT-TYPE
			SYNTAX Unsigned32
			MAX-ACCESS read-only
			STATUS current
			DESCRIPTION
				"  "
			::= { hwInfoLogicalPortEntry 3 }


--   1.3.6.1.4.1.34774.4.1.23.4.1.1.4
-- 1.3.6.1.4.1.34774.4.1.23.7.5.1.4
		hwInfoLogicalPortIPv4Addr OBJECT-TYPE
			SYNTAX OCTET STRING
			MAX-ACCESS read-only
			STATUS current
			DESCRIPTION
				"  "
			::= { hwInfoLogicalPortEntry 4 }


--   1.3.6.1.4.1.34774.4.1.23.4.1.1.4
-- 1.3.6.1.4.1.34774.4.1.23.7.5.1.5
		hwInfoLogicalPortIPv4Mask OBJECT-TYPE
			SYNTAX OCTET STRING
			MAX-ACCESS read-only
			STATUS current
			DESCRIPTION
				"  "
			::= { hwInfoLogicalPortEntry 5 }


--   1.3.6.1.4.1.34774.4.1.23.4.1.1.4
-- 1.3.6.1.4.1.34774.4.1.23.7.5.1.6
		hwInfoLogicalPortIPv4Gateway OBJECT-TYPE
			SYNTAX OCTET STRING
			MAX-ACCESS read-only
			STATUS current
			DESCRIPTION
				"  "
			::= { hwInfoLogicalPortEntry 6 }


--   1.3.6.1.4.1.34774.4.1.23.4.1.1.4
-- 1.3.6.1.4.1.34774.4.1.23.7.5.1.7
		hwInfoLogicalPortIPv6Addr OBJECT-TYPE
			SYNTAX OCTET STRING
			MAX-ACCESS read-only
			STATUS current
			DESCRIPTION
				"  "
			::= { hwInfoLogicalPortEntry 7 }


--   1.3.6.1.4.1.34774.4.1.23.4.1.1.4
-- 1.3.6.1.4.1.34774.4.1.23.7.5.1.8
		hwInfoLogicalPortIPv6Mask OBJECT-TYPE
			SYNTAX OCTET STRING
			MAX-ACCESS read-only
			STATUS current
			DESCRIPTION
				"  "
			::= { hwInfoLogicalPortEntry 8 }


--   1.3.6.1.4.1.34774.4.1.23.4.1.1.4
-- 1.3.6.1.4.1.34774.4.1.23.7.5.1.9
		hwInfoLogicalPortIPv6Gateway OBJECT-TYPE
			SYNTAX OCTET STRING
			MAX-ACCESS read-only
			STATUS current
			DESCRIPTION
				"  "
			::= { hwInfoLogicalPortEntry 9 }


--   1.3.6.1.4.1.34774.4.1.23.4.1.1.4
-- 1.3.6.1.4.1.34774.4.1.23.7.5.1.10
		hwInfoLogicalPortRole OBJECT-TYPE
			SYNTAX Unsigned32
			MAX-ACCESS read-only
			STATUS current
			DESCRIPTION
				"  "
			::= { hwInfoLogicalPortEntry 10 }


--   1.3.6.1.4.1.34774.4.1.23.4.1.1.4
-- 1.3.6.1.4.1.34774.4.1.23.7.5.1.11
		hwInfoLogicalPortSupportProt OBJECT-TYPE
			SYNTAX Unsigned32
			MAX-ACCESS read-only
			STATUS current
			DESCRIPTION
				"  "
			::= { hwInfoLogicalPortEntry 11 }


--   1.3.6.1.4.1.34774.4.1.23.4.1.1.4
-- 1.3.6.1.4.1.34774.4.1.23.7.5.1.12
		hwInfoLogicalPortHomePortType OBJECT-TYPE
			SYNTAX Unsigned32
			MAX-ACCESS read-only
			STATUS current
			DESCRIPTION
				"  "
			::= { hwInfoLogicalPortEntry 12 }


--   1.3.6.1.4.1.34774.4.1.23.4.1.1.4
-- 1.3.6.1.4.1.34774.4.1.23.7.5.1.13
		hwInfoLogicalPortHomePortID OBJECT-TYPE
			SYNTAX OCTET STRING
			MAX-ACCESS read-only
			STATUS current
			DESCRIPTION
				"  "
			::= { hwInfoLogicalPortEntry 13 }


--   1.3.6.1.4.1.34774.4.1.23.4.1.1.4
-- 1.3.6.1.4.1.34774.4.1.23.7.5.1.14
		hwInfoLogicalPortOwnerCtrlID OBJECT-TYPE
			SYNTAX OCTET STRING
			MAX-ACCESS read-only
			STATUS current
			DESCRIPTION
				"  "
			::= { hwInfoLogicalPortEntry 14 }


--   1.3.6.1.4.1.34774.4.1.23.4.1.1.4
-- 1.3.6.1.4.1.34774.4.1.23.7.5.1.15
		hwInfoLogicalPortCurrPortType OBJECT-TYPE
			SYNTAX Unsigned32
			MAX-ACCESS read-only
			STATUS current
			DESCRIPTION
				"  "
			::= { hwInfoLogicalPortEntry 15 }


--   1.3.6.1.4.1.34774.4.1.23.4.1.1.4
-- 1.3.6.1.4.1.34774.4.1.23.7.5.1.16
		hwInfoLogicalPortCurrPortID OBJECT-TYPE
			SYNTAX OCTET STRING
			MAX-ACCESS read-only
			STATUS current
			DESCRIPTION
				"  "
			::= { hwInfoLogicalPortEntry 16 }


--   1.3.6.1.4.1.34774.4.1.23.4.1.1.4
-- 1.3.6.1.4.1.34774.4.1.23.7.5.1.17
		hwInfoLogicalPortWorkCtrlID OBJECT-TYPE
			SYNTAX OCTET STRING
			MAX-ACCESS read-only
			STATUS current
			DESCRIPTION
				"  "
			::= { hwInfoLogicalPortEntry 17 }


--   1.3.6.1.4.1.34774.4.1.23.4.1.1.4
-- 1.3.6.1.4.1.34774.4.1.23.7.5.1.18
		hwInfoLogicalPortActState OBJECT-TYPE
			SYNTAX Unsigned32
			MAX-ACCESS read-only
			STATUS current
			DESCRIPTION
				"  "
			::= { hwInfoLogicalPortEntry 18 }


--   1.3.6.1.4.1.34774.4.1.23.4.1.1.4
-- 1.3.6.1.4.1.34774.4.1.23.7.5.1.19
		hwInfoLogicalPortAddrFamily OBJECT-TYPE
			SYNTAX Unsigned32
			MAX-ACCESS read-only
			STATUS current
			DESCRIPTION
				"  "
			::= { hwInfoLogicalPortEntry 19 }


--   1.3.6.1.4.1.34774.4.1.23.4.1.1.4
-- 1.3.6.1.4.1.34774.4.1.23.7.5.1.20
		hwInfoLogicalPortIsPrivate OBJECT-TYPE
			SYNTAX Unsigned32
			MAX-ACCESS read-only
			STATUS current
			DESCRIPTION
				"  "
			::= { hwInfoLogicalPortEntry 20 }


--   1.3.6.1.4.1.34774.4.1.23.4.1.1.4
-- 1.3.6.1.4.1.34774.4.1.23.7.5.1.21
		hwInfoLogicalPortFailOVGID OBJECT-TYPE
			SYNTAX OCTET STRING
			MAX-ACCESS read-only
			STATUS current
			DESCRIPTION
				"  "
			::= { hwInfoLogicalPortEntry 21 }


--   1.3.6.1.4.1.34774.4.1.23.4.1.1.4
-- 1.3.6.1.4.1.34774.4.1.23.7.5.1.22
		hwInfoLogicalPortFailOVEnable OBJECT-TYPE
			SYNTAX Unsigned32
			MAX-ACCESS read-only
			STATUS current
			DESCRIPTION
				"  "
			::= { hwInfoLogicalPortEntry 22 }


--   1.3.6.1.4.1.34774.4.1.23.4.1.1.4
-- 1.3.6.1.4.1.34774.4.1.23.7.5.1.23
		hwInfoLogicalPortFailBackMode OBJECT-TYPE
			SYNTAX Unsigned32
			MAX-ACCESS read-only
			STATUS current
			DESCRIPTION
				"  "
			::= { hwInfoLogicalPortEntry 23 }


--   1.3.6.1.4.1.34774.4.1.23.4.1.1.4
-- 1.3.6.1.4.1.34774.4.1.23.7.5.1.24
		hwInfoLogicalPortFailOVGName OBJECT-TYPE
			SYNTAX OCTET STRING
			MAX-ACCESS read-only
			STATUS current
			DESCRIPTION
				"  "
			::= { hwInfoLogicalPortEntry 24 }


--   1.3.6.1.4.1.34774.4.1.23.4.1
-- 1.3.6.1.4.1.34774.4.1.23.7.6
		hwInfoFileSysTable OBJECT-TYPE
			SYNTAX SEQUENCE OF HwInfoFileSysEntry
			MAX-ACCESS not-accessible
			STATUS current
			DESCRIPTION
				" "
			::= { hwNasInfo 6 }


--
-- 1.3.6.1.4.1.34774.4.1.23.4.1.1
-- 1.3.6.1.4.1.34774.4.1.23.7.6.1
		hwInfoFileSysEntry OBJECT-TYPE
			SYNTAX HwInfoFileSysEntry
			MAX-ACCESS not-accessible
			STATUS current
			DESCRIPTION
				"  "
			INDEX { hwInfoFileSysID }
			::= { hwInfoFileSysTable 1 }


		HwInfoFileSysEntry ::=
			SEQUENCE {
				hwInfoFileSysID
					OCTET STRING,
				hwInfoFileSysName
					OCTET STRING,
				hwInfoFileSysHeathStatus
					Unsigned32,
				hwInfoFileSysRunningStatus
					Unsigned32,
				hwInfoFileSysDescription
					OCTET STRING,
				hwInfoFileSysSubType
					Unsigned32,
				hwInfoFileSysAllocType
					Unsigned32,
				hwInfoFileSysCapacity
					Counter64,
				hwInfoFileSysSnapshotReservePer
					Unsigned32,
				hwInfoFileSysSnapshotUseCapacity
					Counter64,
				hwInfoFileSysSectorSize
					Unsigned32,
				hwInfoFileSysOwningContrller
					OCTET STRING,
				hwInfoFileSysWorkingController
					OCTET STRING,
				hwInfoFileSysIOPriotiry
					Unsigned32,
				hwInfoFileSysEnableCompression
					Unsigned32,
				hwInfoFileSysCompression
					Unsigned32,
				hwInfoFileSysIsShowSnapDir
					Unsigned32,
				hwInfoFileSysAvailableCapacity
					Counter64,
				hwInfoFileSysAvAndAllcCapRatio
					Unsigned32,
				hwInfoFileSysSCCachedSize
					Counter64,
				hwInfoFileSysSCHitRage
					Unsigned32,
				hwInfoFileSysCompressSavedRatio
					Unsigned32
			 }

--   1.3.6.1.4.1.34774.4.1.23.4.1.1.1
-- 1.3.6.1.4.1.34774.4.1.23.7.6.1.1
		hwInfoFileSysID OBJECT-TYPE
			SYNTAX OCTET STRING
			MAX-ACCESS read-only
			STATUS current
			DESCRIPTION
				"  "
			::= { hwInfoFileSysEntry 1 }


--   1.3.6.1.4.1.34774.4.1.23.4.1.1.2
		hwInfoFileSysName OBJECT-TYPE
			SYNTAX OCTET STRING
			MAX-ACCESS read-only
			STATUS current
			DESCRIPTION
				"  "
			::= { hwInfoFileSysEntry 2 }


-- 1.3.6.1.4.1.34774.4.1.23.7.6.1.2
		hwInfoFileSysHeathStatus OBJECT-TYPE
			SYNTAX Unsigned32
			MAX-ACCESS read-only
			STATUS current
			DESCRIPTION
				"  "
			::= { hwInfoFileSysEntry 3 }


--   1.3.6.1.4.1.34774.4.1.23.4.1.1.3
-- 1.3.6.1.4.1.34774.4.1.23.7.6.1.3
		hwInfoFileSysRunningStatus OBJECT-TYPE
			SYNTAX Unsigned32
			MAX-ACCESS read-only
			STATUS current
			DESCRIPTION
				"  "
			::= { hwInfoFileSysEntry 4 }


--   1.3.6.1.4.1.34774.4.1.23.4.1.1.4
-- 1.3.6.1.4.1.34774.4.1.23.7.6.1.4
		hwInfoFileSysDescription OBJECT-TYPE
			SYNTAX OCTET STRING
			MAX-ACCESS read-only
			STATUS current
			DESCRIPTION
				"  "
			::= { hwInfoFileSysEntry 5 }


--   1.3.6.1.4.1.34774.4.1.23.4.1.1.2
-- 1.3.6.1.4.1.34774.4.1.23.7.6.1.5
		hwInfoFileSysSubType OBJECT-TYPE
			SYNTAX Unsigned32
			MAX-ACCESS read-only
			STATUS current
			DESCRIPTION
				"  "
			::= { hwInfoFileSysEntry 6 }


--   1.3.6.1.4.1.34774.4.1.23.4.1.1.2
-- 1.3.6.1.4.1.34774.4.1.23.7.6.1.6
		hwInfoFileSysAllocType OBJECT-TYPE
			SYNTAX Unsigned32
			MAX-ACCESS read-only
			STATUS current
			DESCRIPTION
				"  "
			::= { hwInfoFileSysEntry 7 }


--   1.3.6.1.4.1.34774.4.1.23.4.1.1.2
-- 1.3.6.1.4.1.34774.4.1.23.7.6.1.7
		hwInfoFileSysCapacity OBJECT-TYPE
			SYNTAX Counter64
			MAX-ACCESS read-only
			STATUS current
			DESCRIPTION
				"  "
			::= { hwInfoFileSysEntry 8 }


--   1.3.6.1.4.1.34774.4.1.23.4.1.1.2
-- 1.3.6.1.4.1.34774.4.1.23.7.6.1.8
		hwInfoFileSysSnapshotReservePer OBJECT-TYPE
			SYNTAX Unsigned32
			MAX-ACCESS read-only
			STATUS current
			DESCRIPTION
				"  "
			::= { hwInfoFileSysEntry 9 }


--   1.3.6.1.4.1.34774.4.1.23.4.1.1.2
-- 1.3.6.1.4.1.34774.4.1.23.7.6.1.9
		hwInfoFileSysSnapshotUseCapacity OBJECT-TYPE
			SYNTAX Counter64
			MAX-ACCESS read-only
			STATUS current
			DESCRIPTION
				"  "
			::= { hwInfoFileSysEntry 10 }


--   1.3.6.1.4.1.34774.4.1.23.4.1.1.2
-- 1.3.6.1.4.1.34774.4.1.23.7.6.1.10
		hwInfoFileSysSectorSize OBJECT-TYPE
			SYNTAX Unsigned32
			MAX-ACCESS read-only
			STATUS current
			DESCRIPTION
				"  "
			::= { hwInfoFileSysEntry 11 }


--   1.3.6.1.4.1.34774.4.1.23.4.1.1.1
-- 1.3.6.1.4.1.34774.4.1.23.7.6.1.11
		hwInfoFileSysOwningContrller OBJECT-TYPE
			SYNTAX OCTET STRING
			MAX-ACCESS read-only
			STATUS current
			DESCRIPTION
				"  "
			::= { hwInfoFileSysEntry 12 }


--   1.3.6.1.4.1.34774.4.1.23.4.1.1.1
-- 1.3.6.1.4.1.34774.4.1.23.7.6.1.12
		hwInfoFileSysWorkingController OBJECT-TYPE
			SYNTAX OCTET STRING
			MAX-ACCESS read-only
			STATUS current
			DESCRIPTION
				"  "
			::= { hwInfoFileSysEntry 13 }


--   1.3.6.1.4.1.34774.4.1.23.4.1.1.2
-- 1.3.6.1.4.1.34774.4.1.23.7.6.1.13
		hwInfoFileSysIOPriotiry OBJECT-TYPE
			SYNTAX Unsigned32
			MAX-ACCESS read-only
			STATUS current
			DESCRIPTION
				"  "
			::= { hwInfoFileSysEntry 14 }


--   1.3.6.1.4.1.34774.4.1.23.4.1.1.2
-- 1.3.6.1.4.1.34774.4.1.23.7.6.1.14
		hwInfoFileSysEnableCompression OBJECT-TYPE
			SYNTAX Unsigned32
			MAX-ACCESS read-only
			STATUS current
			DESCRIPTION
				"  "
			::= { hwInfoFileSysEntry 15 }


--   1.3.6.1.4.1.34774.4.1.23.4.1.1.2
-- 1.3.6.1.4.1.34774.4.1.23.7.6.1.15
		hwInfoFileSysCompression OBJECT-TYPE
			SYNTAX Unsigned32
			MAX-ACCESS read-only
			STATUS current
			DESCRIPTION
				"  "
			::= { hwInfoFileSysEntry 16 }


--   1.3.6.1.4.1.34774.4.1.23.4.1.1.2
-- 1.3.6.1.4.1.34774.4.1.23.7.6.1.16
		hwInfoFileSysIsShowSnapDir OBJECT-TYPE
			SYNTAX Unsigned32
			MAX-ACCESS read-only
			STATUS current
			DESCRIPTION
				"  "
			::= { hwInfoFileSysEntry 17 }


--   1.3.6.1.4.1.34774.4.1.23.4.1.1.2
-- 1.3.6.1.4.1.34774.4.1.23.7.6.1.17
		hwInfoFileSysAvailableCapacity OBJECT-TYPE
			SYNTAX Counter64
			MAX-ACCESS read-only
			STATUS current
			DESCRIPTION
				"  "
			::= { hwInfoFileSysEntry 18 }


--   1.3.6.1.4.1.34774.4.1.23.4.1.1.2
-- 1.3.6.1.4.1.34774.4.1.23.7.6.1.18
		hwInfoFileSysAvAndAllcCapRatio OBJECT-TYPE
			SYNTAX Unsigned32
			MAX-ACCESS read-only
			STATUS current
			DESCRIPTION
				"  "
			::= { hwInfoFileSysEntry 19 }


--   1.3.6.1.4.1.34774.4.1.23.4.1.1.2
-- 1.3.6.1.4.1.34774.4.1.23.7.6.1.19
		hwInfoFileSysSCCachedSize OBJECT-TYPE
			SYNTAX Counter64
			MAX-ACCESS read-only
			STATUS current
			DESCRIPTION
				"  "
			::= { hwInfoFileSysEntry 20 }


--   1.3.6.1.4.1.34774.4.1.23.4.1.1.2
-- 1.3.6.1.4.1.34774.4.1.23.7.6.1.20
		hwInfoFileSysSCHitRage OBJECT-TYPE
			SYNTAX Unsigned32
			MAX-ACCESS read-only
			STATUS current
			DESCRIPTION
				"  "
			::= { hwInfoFileSysEntry 21 }


--   1.3.6.1.4.1.34774.4.1.23.4.1.1.2
-- 1.3.6.1.4.1.34774.4.1.23.7.6.1.21
		hwInfoFileSysCompressSavedRatio OBJECT-TYPE
			SYNTAX Unsigned32
			MAX-ACCESS read-only
			STATUS current
			DESCRIPTION
				"  "
			::= { hwInfoFileSysEntry 22 }


--   1.6
-- 1.6
		isoConformance OBJECT IDENTIFIER ::= { iso 6 }


--   1.6.1
-- 1.6.1
		isoGroups OBJECT IDENTIFIER ::= { isoConformance 1 }


--   1.6.1.1
-- 1.6.1.1
		currentObjectGroup OBJECT-GROUP
			OBJECTS { hwInfoShareCIFSContAvailableEna, hwInfoSharePermsNFSID, hwInfoSharePermsNFSAccessName, hwInfoSharePermsNFSShareID, hwInfoSharePermsNFSAccessType,
				hwInfoSharePermsNFSSyncEnabled, hwInfoSharePermsNFSAllSquashEna, hwInfoSharePermsNFSRootSquashEna, hwInfoSharePermsCIFSID, hwInfoSharePermsCIFSAccessName,
				hwInfoSharePermsCIFSShareID, hwInfoSharePermsCIFSDomainType, hwInfoSharePermsCIFSPermsType, hwInfoLogicalPortSupportProt, hwInfoLogicalPortHomePortType,
				hwInfoLogicalPortFailBackMode, hwInfoFileSysID, hwInfoFileSysName, hwInfoFileSysHeathStatus, hwInfoFileSysRunningStatus,
				hwInfoFileSysDescription, hwInfoFileSysSubType, hwInfoFileSysAllocType, hwInfoFileSysCapacity, hwInfoFileSysSnapshotReservePer,
				hwInfoFileSysSnapshotUseCapacity, hwInfoFileSysSectorSize, hwInfoFileSysOwningContrller, hwInfoFileSysWorkingController, hwInfoFileSysIOPriotiry,
				hwInfoFileSysEnableCompression, hwInfoFileSysCompression, hwInfoFileSysIsShowSnapDir, hwInfoFileSysAvailableCapacity, hwInfoFileSysAvAndAllcCapRatio,
				hwInfoFileSysSCCachedSize, hwInfoFileSysSCHitRage, hwInfoFileSysCompressSavedRatio, hwInfoShareNFSShareID, hwInfoShareNFSFileSystemID,
				hwInfoShareNFSDescription, hwInfoShareCIFSID, hwInfoShareCIFSFileSystemID, hwInfoShareCIFSDescription, hwInfoLogicalPortID,
				hwInfoShareNFSLocalPath, hwInfoShareCIFSName, hwInfoShareCIFSLocalPath, hwInfoShareCIFSOplockEnabled, hwInfoShareCIFSNotifyEnabled,
				hwInfoLogicalPorttName, hwInfoLogicalPortRunStatus, hwInfoLogicalPortIPv4Addr, hwInfoLogicalPortIPv4Mask, hwInfoLogicalPortIPv4Gateway,
				hwInfoLogicalPortIPv6Addr, hwInfoLogicalPortIPv6Mask, hwInfoLogicalPortIPv6Gateway, hwInfoLogicalPortRole, hwInfoLogicalPortHomePortID,
				hwInfoLogicalPortOwnerCtrlID, hwInfoLogicalPortCurrPortType, hwInfoLogicalPortCurrPortID, hwInfoLogicalPortWorkCtrlID, hwInfoLogicalPortActState,
				hwInfoLogicalPortAddrFamily, hwInfoLogicalPortIsPrivate, hwInfoLogicalPortFailOVGID, hwInfoLogicalPortFailOVEnable, hwInfoLogicalPortFailOVGName
				 }
			STATUS current
			DESCRIPTION
				"Enter the description of the created OBJECT-GROUP."
			::= { isoGroups 1 }


--   1.6.2
-- 1.6.2
		isoCompliances OBJECT IDENTIFIER ::= { isoConformance 2 }


--    this module
-- 1.6.2.1
-- this module
-- 1.6.2.1
-- this module
		basicCompliance MODULE-COMPLIANCE
			STATUS current
			DESCRIPTION
				"Enter the description of the created MODULE-COMPLIANCE."
			MODULE -- this module
				MANDATORY-GROUPS { currentObjectGroup }
			::= { isoCompliances 1 }



	END

--
-- HUAWEI-STORAGE-NAS-MIB.mib
--
