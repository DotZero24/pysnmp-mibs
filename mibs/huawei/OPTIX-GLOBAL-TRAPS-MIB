--
-- OPTIX-SONET-PER-MIB.mib
-- MIB generated by MG-SOFT Visual MIB Builder Version 3.0 Build 253
-- Monday, March 06, 2006 at 10:26:16
--
            -- =================================================================
--  Copyright (C) 2006 by HUAWEI TECHNOLOGIES. All rights reserved
--
--  Description:This MIB describes the Performance interface of Huawei SONET transmit
--  Reference:
--  Version: V1.00
--  History:
-- 	<author>,<date>,<contents>
-- =================================================================
--

	OPTIX-GLOBAL-TRAPS-MIB DEFINITIONS ::= BEGIN

		IMPORTS
			optixCommonGlobal
				FROM OPTIX-OID-MIB
			PerformanceEventType, ValidflagType, ObjType,AlarmEventType, AlmDataSrvEffType, AlmDataNtfcnCdeType, DataPmEventType
				FROM OPTIX-GLOBAL-TC-MIB
			OBJECT-GROUP, MODULE-COMPLIANCE
				FROM SNMPv2-CONF
			Integer32, Unsigned32, OBJECT-TYPE, MODULE-IDENTITY
				FROM SNMPv2-SMI
			DateAndTime, DisplayString
				FROM SNMPv2-TC;

		optixGlobalTrap MODULE-IDENTITY
			LAST-UPDATED "200805240000Z"
			ORGANIZATION
				"Huawei Technologies co.,Ltd."
			CONTACT-INFO
				"R&D Building
				Huawei Technologies Co., Ltd.
				Bantian, Longgang District
				Shenzhen, P. R. China
				http://www.huawei.com
				Zip:518129
				E-mail:support@huawei.com"
			DESCRIPTION
				"Description."
			REVISION "200805240000Z"
			DESCRIPTION
				"The initial revision of this MIB module."
			::= { optixCommonGlobal 40 }

		optixTrapsCommon OBJECT IDENTIFIER ::= { optixGlobalTrap 10 }
        rptAlmName OBJECT-TYPE
            SYNTAX AlarmEventType
            MAX-ACCESS accessible-for-notify
            STATUS current
            DESCRIPTION
                "Alarm name."
            ::= { optixTrapsCommon 10 }

        -- 1.3.6.1.4.1.2011.2.25.3.20.70.10.40
        rptEvtDateTime OBJECT-TYPE
            SYNTAX DateAndTime
            MAX-ACCESS accessible-for-notify
            STATUS current
            DESCRIPTION
                "Date and time when the triggering event occurred."
            ::= { optixTrapsCommon 40 }

        -- 1.3.6.1.4.1.2011.2.25.3.20.70.10.50
        rptEvtSrvEff OBJECT-TYPE
            SYNTAX AlmDataSrvEffType
            MAX-ACCESS accessible-for-notify
            STATUS current
            DESCRIPTION
                "The effect on service caused by the alarm condition.
                Only NSA(Nonservice-effecting)|SA(Service-effecting) will be represented here."
            ::= { optixTrapsCommon 50 }

        -- 1.3.6.1.4.1.2011.2.25.3.20.70.10.60
        rptEvtNtfcnCde OBJECT-TYPE
            SYNTAX AlmDataNtfcnCdeType
            MAX-ACCESS accessible-for-notify
            STATUS current
            DESCRIPTION
                "The notification code of the alarm.
                Only CR|MJ|MN|IG|NR will be represented here."
            ::= { optixTrapsCommon 60 }

        -- 1.3.6.1.4.1.2011.2.25.3.20.70.10.90
        rptEvtMonValue OBJECT-TYPE
            SYNTAX Counter64
            MAX-ACCESS accessible-for-notify
            STATUS current
            DESCRIPTION
                "Monitored value"
            ::= { optixTrapsCommon 90 }

        -- 1.3.6.1.4.1.2011.2.25.3.20.70.10.100
        rptEvtThValue OBJECT-TYPE
            SYNTAX Counter64
            MAX-ACCESS accessible-for-notify
            STATUS current
            DESCRIPTION
                "Indicates the threshold level."
            ::= { optixTrapsCommon 100 }

        -- 1.3.6.1.4.1.2011.2.25.3.20.70.10.120
        rptEvtNumber OBJECT-TYPE
            SYNTAX Unsigned32
            MAX-ACCESS accessible-for-notify
            STATUS current
            DESCRIPTION
                "The numble of Alarm Message"
            ::= { optixTrapsCommon 120 }

        -- 1.3.6.1.4.1.2011.2.25.3.20.70.10.130
        rptEvtPeriod OBJECT-TYPE
            SYNTAX INTEGER
                {
                null(0),
                period15m(1),
                period1day(2)
                }
            MAX-ACCESS accessible-for-notify
            STATUS current
            DESCRIPTION
                "Specifies the accumulation time period for the PM information.
                Only period15m|period1day|NULL will be represented here."
            ::= { optixTrapsCommon 130 }

        -- 1.3.6.1.4.1.2011.2.25.3.20.70.10.140
        rptEvtVldty OBJECT-TYPE
            SYNTAX ValidflagType
            MAX-ACCESS accessible-for-notify
            STATUS current
            DESCRIPTION
                "It indicates whether the information
                for the specified time period was
                accumulated over the entire time period
                or some portion of it.
                Only INVALID|VALID will be represented here."
            ::= { optixTrapsCommon 140 }

        -- 1.3.6.1.4.1.2011.2.25.3.20.70.10.160
        rptEvtState OBJECT-TYPE
            SYNTAX INTEGER
                {
                start(1),
                clear(3)
                }
            MAX-ACCESS accessible-for-notify
            STATUS current
            DESCRIPTION
                "The state of alarm.
                Only START|CL(Cleared) will be represented here."
            ::= { optixTrapsCommon 160 }
       -- 1.3.6.1.4.1.2011.2.25.3.40.40.10.190
        rptPmName OBJECT-TYPE
        SYNTAX PerformanceEventType
        MAX-ACCESS accessible-for-notify
        STATUS current
        DESCRIPTION
            "Indicates the name of a PM event."
        ::= { optixTrapsCommon 190 }

       -- 1.3.6.1.4.1.2011.2.25.3.40.40.10.210
        rptEvtValue OBJECT-TYPE
            SYNTAX DisplayString
            MAX-ACCESS accessible-for-notify
            STATUS current
            DESCRIPTION
                "Value."
            ::= { optixTrapsCommon 210 }

        -- 1.3.6.1.4.1.2011.2.25.3.20.70.10.20
        rptEvtObjType OBJECT-TYPE
            SYNTAX ObjType
            MAX-ACCESS accessible-for-notify
            STATUS current
            DESCRIPTION
                "objtype."
            ::= { optixTrapsCommon 220}

        rptEvtParaLen OBJECT-TYPE
            SYNTAX Counter32
            MAX-ACCESS accessible-for-notify
            STATUS current
            DESCRIPTION
                "ParaLen"
            ::= { optixTrapsCommon 230}

        -- 1.3.6.1.4.1.2011.2.25.3.20.70.10.30
        rptEvtPara OBJECT-TYPE
            SYNTAX DisplayString
            MAX-ACCESS accessible-for-notify
            STATUS current
            DESCRIPTION
                "para"
            ::= { optixTrapsCommon 240}

        rptEvtStartTime OBJECT-TYPE
            SYNTAX DateAndTime
            MAX-ACCESS accessible-for-notify
            STATUS current
            DESCRIPTION
                "StartTime"
            ::= { optixTrapsCommon 250}

        rptEvtEndTime OBJECT-TYPE
            SYNTAX DateAndTime
            MAX-ACCESS accessible-for-notify
            STATUS current
            DESCRIPTION
                "EndTime"
            ::= { optixTrapsCommon 260}

        rptEvtDataPmName OBJECT-TYPE
            SYNTAX DataPmEventType
            MAX-ACCESS accessible-for-notify
            STATUS current
            DESCRIPTION
                "EndTime"
            ::= { optixTrapsCommon 270}


		optixTrapsPM OBJECT IDENTIFIER ::= { optixGlobalTrap 20 }

           -- 1.3.6.1.4.1.2011.2.25.3.40.40.50
    optixTrapsTrPer OBJECT IDENTIFIER ::= { optixGlobalTrap 50 }





END
--
-- OPTIX-SONET-PER-MIB.mib
--
