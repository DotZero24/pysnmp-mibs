--  ============================================================================
-- Copyright (C) 2015 by  HUAWEI TECHNOLOGIES. All rights reserved.
-- Description:  The mib is used to manage AP on AC, include AP device notify, AP type,
--               AP profile, AP whiltelist, AP region, AP objects etc.
-- Reference:
-- Version: V1.15
--
-- ============================================================================
-- Module definition

	HUAWEI-WLAN-DEVICE-MIB DEFINITIONS ::= BEGIN

		IMPORTS
			hwWlan
				FROM HUAWEI-WLAN-MIB
			hwWlanServiceStaMac, hwWlanServiceStaApId, hwWlanServiceStaRadioId, hwWlanServiceStaEssName, hwWlanServiceStaSsid,
			hwWlanServiceStaOnlineTime, hwWlanServiceStaSnrUs, hwWlanServiceStaRxPowerUs, hwStaWirelessStatTxPkts, hwStaWirelessStatRxPkts,
			hwStaWirelessStatTxBytes, hwStaWirelessStatRxBytes, hwStaWirelessStatTxRate, hwStaWirelessStatRxRate, hwStaAccessChannel,
			hwStaIp, hwStaRssi, hwStaNoise, hwStaVlan, hwStaRecvDropFrames,
			hwStaSendDropFrames, hwStaRecvErrorFrames, hwStaSendErrorFrames, hwStaReSendFrames, hwStaReSendBytes,
			hwStaUsername
				FROM HUAWEI-WLAN-SERVICE-MIB
			OBJECT-GROUP, MODULE-COMPLIANCE, NOTIFICATION-GROUP
				FROM SNMPv2-CONF
			IpAddress, Integer32, Unsigned32, Counter64, OBJECT-TYPE,
			MODULE-IDENTITY, NOTIFICATION-TYPE
				FROM SNMPv2-SMI
			MacAddress, RowStatus, DateAndTime
				FROM SNMPv2-TC;


--       Module identity
		-- 1.3.6.1.4.1.2011.6.139.2
		hwWlanDevice MODULE-IDENTITY
            LAST-UPDATED  "201506182010Z"		-- June  18, 2015 at 19:13 GMT
			ORGANIZATION
				"Huawei Technologies Co.,Ltd."
			CONTACT-INFO
            "Huawei Industrial Base
				   Bantian, Longgang
				   Shenzhen 518129
				   People's Republic of China
				   Website: http://www.huawei.com
				   Email: support@huawei.com
				  "
                                                                   DESCRIPTION
				"Huawei AP device management mib."
			REVISION "201506182010Z"		-- June  18, 2015 at 19:13 GMT
			DESCRIPTION
				"Modify the range of hwApProfileMaxUserNum."
			REVISION "201501202010Z"		-- January  20, 2015 at 20:10 GMT
			DESCRIPTION
				"Huawei AP device management mib."
			REVISION "201412161010Z"		-- December  16, 2014 at 10:10 GMT
			DESCRIPTION
				"Modify the range of hwApHighTemperatureThreshold and hwApLowTemperatureThreshold ."
                        REVISION "201411200910Z"		-- November  20, 2014 at 09:10 GMT
			DESCRIPTION
				"Modify the description of hwApForwardMode and add node hwApLocalAssocResSwitch."
		        REVISION "201409010945Z"		-- September  1, 2014 at 09:45 GMT
			DESCRIPTION
				"Modify the nodes of hwWlanDeviceNotify and hwApRegionEntry."
                        REVISION "201407031551Z"		-- July  3, 2014 at 15:51 GMT
			DESCRIPTION
				"Modify the name of hwEthportUpRate and hwEthportDownRate.The new name is hwApEthportUpRate and hwApEthportDownRate."

                        REVISION "201406161531Z"		-- June  16, 2014 at 15:31 GMT
			DESCRIPTION
				"Modify the name of hwEthportUpRate and hwEthportDownRate.The new name is hwApEthportUpRate and hwApEthportDownRate."
			REVISION "201406041151Z"		-- June  4, 2014 at 11:51 GMT
			DESCRIPTION
				"Modify the name of hwEthportUpRate and hwEthportDownRate.The new name is hwApEthportUpRate and hwApEthportDownRate."
		        REVISION "201404242018Z"		-- April  24, 2014 at 20:18 GMT
			DESCRIPTION
				"Add wids attack detection quiet-time parameter"
			REVISION "201403211628Z"		-- March  21, 2014 at 16:28 GMT
			DESCRIPTION
				"Add object hwAcObjects"

			REVISION "201312040956Z"		-- December  4, 2013 at 9:56 GMT
			DESCRIPTION
				"Add node hwApLedSwitch"
	     	REVISION "201310261056Z"		-- October  26, 2013 at 10:56 GMT
			DESCRIPTION
				"Add calibrate parameter"

			REVISION "201309020000Z"		-- November 04, 2010 at 00:00 GMT
			DESCRIPTION
				"Add calibrate parameter"
            REVISION "201011040000Z"		-- November 04, 2010 at 00:00 GMT
			DESCRIPTION
				"V1.05, Add the ap-blacklist table for the supporting management of ap-blacklist,
				Add hwUnAuthorizedApRecordNumber and hwUnAuthorizedApRecordAdmin for supporting management of
				unauthorized-ap record,
				Modify the Max access read-only of hwApIpAddress to read-write,
				Delete the enum value wlan80211abgn(7) of the hwApTypeRadioType leaf."
			REVISION "201009100000Z"		-- September 10, 2010 at 00:00 GMT
			DESCRIPTION
				"V1.04, Add a leaf hwRadioMaxVAPNum in hwApTypeRadioTable"
			REVISION "201008130000Z"		-- August 13, 2010 at 00:00 GMT
			DESCRIPTION
				"V1.03, Add an enum value unknown(-1) in hwApForwardMode leaf of hwApTable,
				Add an enum value unknown(-1) in hwApRegionForwardMode leaf of hwApRegionTable,
				Add an operation type replaceAp(6) in hwApAdminOper of hwApTable."
			REVISION "201007070000Z"		-- July 07, 2010 at 00:00 GMT
			DESCRIPTION
				"V1.01, Add hwApAntennaMode in hwApTable for the supporting configuration of ap antenna mode."
			REVISION "201005251001Z"		-- May 25, 2010 at 10:01 GMT
			DESCRIPTION
				"V1.00, Initial version"
			::= { hwWlan 2 }


--
-- Node definitions
--

--  Node definitions
--
-- Node definitions
--
-- 1.3.6.1.4.1.2011.6.139.2.1
-- 1.3.6.1.4.1.2011.6.139.2.1
-- 1.3.6.1.4.1.2011.6.139.2.1
		-- 1.3.6.1.4.1.2011.6.139.2.1
		hwWlanDeviceNotifications OBJECT IDENTIFIER ::= { hwWlanDevice 1 }

--    1.3.6.1.4.1.2011.6.139.2.1.1
-- 1.3.6.1.4.1.2011.6.139.2.1.1
-- 1.3.6.1.4.1.2011.6.139.2.1.1
		-- 1.3.6.1.4.1.2011.6.139.2.1.1
		hwWlanDeviceNotify OBJECT IDENTIFIER ::= { hwWlanDeviceNotifications 1 }

--    1.3.6.1.4.1.2011.6.139.2.1.1.1
-- 1.3.6.1.4.1.2011.6.139.2.1.1.1
-- 1.3.6.1.4.1.2011.6.139.2.1.1.1
		-- 1.3.6.1.4.1.2011.6.139.2.1.1.1
		hwApFaultNotify NOTIFICATION-TYPE
			OBJECTS { hwApIndex, hwApUsedType, hwApUsedRegionIndex, hwApSysName, hwApMac,
				hwApFaultTimes }
			STATUS current
			DESCRIPTION
				"This notification occurs when AP become fault because of AP
				off line,reset or shutdown etc.
				hwApIndex: AP ID,
				hwApUsedType: AP type,
				hwApUsedRegionIndex: AP region ID,
				hwApSysName:AP name.
				"
			::= { hwWlanDeviceNotify 1 }

--    1.3.6.1.4.1.2011.6.139.2.1.1.2
-- 1.3.6.1.4.1.2011.6.139.2.1.1.2
-- 1.3.6.1.4.1.2011.6.139.2.1.1.2
		-- 1.3.6.1.4.1.2011.6.139.2.1.1.2
		hwApNormalNotify NOTIFICATION-TYPE
			OBJECTS { hwApIndex, hwApUsedType, hwApUsedRegionIndex, hwApSysName, hwApMac
				 }
			STATUS current
			DESCRIPTION
				"This notification occurs when AP become normal.
				hwApIndex: AP ID,
				hwApUsedType: AP type,
				hwApUsedRegionIndex: AP region ID,
				hwApSysName:AP name.
				"
			::= { hwWlanDeviceNotify 2 }

--    1.3.6.1.4.1.2011.6.139.2.1.1.3
-- 1.3.6.1.4.1.2011.6.139.2.1.1.3
-- 1.3.6.1.4.1.2011.6.139.2.1.1.3
		-- 1.3.6.1.4.1.2011.6.139.2.1.1.3
		hwApTypeNotMatchNotify NOTIFICATION-TYPE
			OBJECTS { hwApIndex, hwApUsedRegionIndex, hwApSysName, hwApUsedType, hwApActualType,
				hwApMac }
			STATUS current
			DESCRIPTION
				"This notification occurs when AP's actual type is not match
				the configured one.
				hwApIndex: AP ID,
				hwApUsedRegionIndex: AP region ID,
				hwApSysName:AP name,
				hwApUsedType: AP type,
				hwApActualType: AP actual type.
				"
			::= { hwWlanDeviceNotify 3 }

--    1.3.6.1.4.1.2011.6.139.2.1.1.4
-- 1.3.6.1.4.1.2011.6.139.2.1.1.4
-- 1.3.6.1.4.1.2011.6.139.2.1.1.4
		-- 1.3.6.1.4.1.2011.6.139.2.1.1.4
		hwApPingResultNotify NOTIFICATION-TYPE
			OBJECTS { hwApIndex, hwApUsedType, hwApUsedRegionIndex, hwApSysName, hwApPingResultSuccessCount,
				hwApPingResultFailureCount, hwApPingResultAverageResponseTime, hwApPingResultMinimumResponseTime, hwApPingResultMaximumResponseTime, hwApMac
				 }
			STATUS current
			DESCRIPTION
				"This notification occurs when AP has accomplished a ping and
				will report the result to user.
				hwApIndex: AP ID,
				hwApUsedType: AP type,
				hwApUsedRegionIndex: AP region ID,
				hwApSysName:AP name,
				hwApPingResultSuccessCount:the successful times of the recent AP ping,
				hwApPingResultFailureCount: the failed times of recent AP ping,
				hwApPingResultAverageResponseTime: the average response time of recent AP ping.
				hwApPingResultMinimumResponseTime: the minimum response time of recent AP ping.
				hwApPingResultMaximumResponseTime: the maximum response time of recent AP ping.
				"
			::= { hwWlanDeviceNotify 4 }

--    1.3.6.1.4.1.2011.6.139.2.1.1.5
-- 1.3.6.1.4.1.2011.6.139.2.1.1.5
-- 1.3.6.1.4.1.2011.6.139.2.1.1.5
		-- 1.3.6.1.4.1.2011.6.139.2.1.1.5
		hwApColdstartNotify NOTIFICATION-TYPE
			OBJECTS { hwApIndex, hwApUsedType, hwApUsedRegionIndex, hwApSysName, hwApMac
				 }
			STATUS current
			DESCRIPTION
				"This notification occurs when AP cold starting.
				hwApIndex: AP ID,
				hwApUsedType: AP type,
				hwApUsedRegionIndex: AP region ID,
				hwApSysName:AP name.
				"
			::= { hwWlanDeviceNotify 5 }

--    1.3.6.1.4.1.2011.6.139.2.1.1.8
-- 1.3.6.1.4.1.2011.6.139.2.1.1.8
-- 1.3.6.1.4.1.2011.6.139.2.1.1.8
		-- 1.3.6.1.4.1.2011.6.139.2.1.1.8
		hwApConfigCommitNotify NOTIFICATION-TYPE
			OBJECTS { hwApIndex, hwApMac }
			STATUS current
			DESCRIPTION
				"This notification occurs when commit AP's configuration successfully.
				hwApIndex: AP ID.
				"
			::= { hwWlanDeviceNotify 8 }

--    1.3.6.1.4.1.2011.6.139.2.1.1.9
-- 1.3.6.1.4.1.2011.6.139.2.1.1.9
-- 1.3.6.1.4.1.2011.6.139.2.1.1.9
		-- 1.3.6.1.4.1.2011.6.139.2.1.1.9
		hwApAddOffLineNotify NOTIFICATION-TYPE
			OBJECTS { hwApIndex, hwApSysName, hwApType, hwApMac, hwApSn
				 }
			STATUS current
			DESCRIPTION
				"This notification occurs when add an AP off line.
				hwApIndex: AP ID,
				hwApSysName:AP name,
				hwApUsedType: AP type,
				hwApUsedRegionIndex: AP region ID,
				hwApMac:AP MAC address,
				hwApSn:AP SN number.
				"
			::= { hwWlanDeviceNotify 9 }

--    1.3.6.1.4.1.2011.6.139.2.1.1.10
-- 1.3.6.1.4.1.2011.6.139.2.1.1.10
-- 1.3.6.1.4.1.2011.6.139.2.1.1.10
		-- 1.3.6.1.4.1.2011.6.139.2.1.1.10
		hwApConfirmNotify NOTIFICATION-TYPE
			OBJECTS { hwApIndex, hwApSysName, hwApUsedType, hwApMac, hwApSn
				 }
			STATUS current
			DESCRIPTION
				"This notification occurs when confirm an AP successfully.
				hwApIndex: AP ID,
				hwApSysName:AP name,
				hwApUsedType: AP type,
				hwApUsedRegionIndex: AP region ID,
				hwApMac:AP MAC address,
				hwApSn:AP SN number.
				"
			::= { hwWlanDeviceNotify 10 }

--   1.3.6.1.4.1.2011.6.139.2.1.1.11
-- 1.3.6.1.4.1.2011.6.139.2.1.1.11
		-- 1.3.6.1.4.1.2011.6.139.2.1.1.11
		hwUnAuthorizedApRecordExistNotify NOTIFICATION-TYPE
			OBJECTS { hwUnAuthorizedApRecordNumber }
			STATUS current
			DESCRIPTION
				"Description."
			::= { hwWlanDeviceNotify 11 }

--   1.3.6.1.4.1.2011.6.139.2.1.1.12
-- 1.3.6.1.4.1.2011.6.139.2.1.1.12
		-- 1.3.6.1.4.1.2011.6.139.2.1.1.12
		hwUnAuthorizedApRecordClearNotify NOTIFICATION-TYPE
			STATUS current
			DESCRIPTION
				"Description."
			::= { hwWlanDeviceNotify 12 }

--   1.3.6.1.4.1.2011.6.139.2.1.1.13
-- 1.3.6.1.4.1.2011.6.139.2.1.1.13
		-- 1.3.6.1.4.1.2011.6.139.2.1.1.13
		hwApCpuOverloadNotify NOTIFICATION-TYPE
			OBJECTS { hwApIndex, hwApMac, hwApCpuOccupancyRate }
			STATUS current
			DESCRIPTION
				"Description."
			::= { hwWlanDeviceNotify 13 }

--   1.3.6.1.4.1.2011.6.139.2.1.1.14
-- 1.3.6.1.4.1.2011.6.139.2.1.1.14
		-- 1.3.6.1.4.1.2011.6.139.2.1.1.14
		hwApCpuOverloadRestoreNotify NOTIFICATION-TYPE
			OBJECTS { hwApIndex, hwApMac, hwApCpuOccupancyRate }
			STATUS current
			DESCRIPTION
				"Description."
			::= { hwWlanDeviceNotify 14 }

--   1.3.6.1.4.1.2011.6.139.2.1.1.15
-- 1.3.6.1.4.1.2011.6.139.2.1.1.15
		-- 1.3.6.1.4.1.2011.6.139.2.1.1.15
		hwApMemoryOverloadNOtify NOTIFICATION-TYPE
			OBJECTS { hwApIndex, hwApMac, hwApMemoryOccupancyRate }
			STATUS current
			DESCRIPTION
				"Description."
			::= { hwWlanDeviceNotify 15 }

--   1.3.6.1.4.1.2011.6.139.2.1.1.16
-- 1.3.6.1.4.1.2011.6.139.2.1.1.16
		-- 1.3.6.1.4.1.2011.6.139.2.1.1.16
		hwApMemoryOverloadRestoreNotify NOTIFICATION-TYPE
			OBJECTS { hwApIndex, hwApMac, hwApMemoryOccupancyRate }
			STATUS current
			DESCRIPTION
				"Description."
			::= { hwWlanDeviceNotify 16 }

--   1.3.6.1.4.1.2011.6.139.2.1.1.17
-- 1.3.6.1.4.1.2011.6.139.2.1.1.17
		-- 1.3.6.1.4.1.2011.6.139.2.1.1.17
		hwAPStaFullNotify NOTIFICATION-TYPE
			OBJECTS { hwApIndex, hwApMac, hwStaAuthFailCause, hwApPermitStaNum }
			STATUS current
			DESCRIPTION
				"Description."
			::= { hwWlanDeviceNotify 17 }

--   1.3.6.1.4.1.2011.6.139.2.1.1.18
-- 1.3.6.1.4.1.2011.6.139.2.1.1.18
		-- 1.3.6.1.4.1.2011.6.139.2.1.1.18
		hwAPStaFullRecoverNotify NOTIFICATION-TYPE
			OBJECTS { hwApIndex, hwApMac, hwStaAuthFailCause, hwApPermitStaNum }
			STATUS current
			DESCRIPTION
				"Description."
			::= { hwWlanDeviceNotify 18 }

--   1.3.6.1.4.1.2011.6.139.2.1.1.19
-- 1.3.6.1.4.1.2011.6.139.2.1.1.19
		-- 1.3.6.1.4.1.2011.6.139.2.1.1.19
		hwAcDevicesSwitchNotify NOTIFICATION-TYPE
			OBJECTS { hwApIndex, hwApMac, hwApSn, hwAcSystemSwitchType }
			STATUS current
			DESCRIPTION
				"Description."
			::= { hwWlanDeviceNotify 19 }

--   1.3.6.1.4.1.2011.6.139.2.1.1.20
-- 1.3.6.1.4.1.2011.6.139.2.1.1.20
		-- 1.3.6.1.4.1.2011.6.139.2.1.1.20
		hwApTimeSynFailNotify NOTIFICATION-TYPE
			OBJECTS { hwApIndex, hwApMac }
			STATUS current
			DESCRIPTION
				"Description."
			::= { hwWlanDeviceNotify 20 }

--   1.3.6.1.4.1.2011.6.139.2.1.1.21
-- 1.3.6.1.4.1.2011.6.139.2.1.1.21
		-- 1.3.6.1.4.1.2011.6.139.2.1.1.21
		hwDyingGaspTrapNotify NOTIFICATION-TYPE
			OBJECTS { hwApIndex, hwApMac }
			STATUS current
			DESCRIPTION
				"Description."
			::= { hwWlanDeviceNotify 21 }

--   1.3.6.1.4.1.2011.6.139.2.1.1.22
-- 1.3.6.1.4.1.2011.6.139.2.1.1.22
		-- 1.3.6.1.4.1.2011.6.139.2.1.1.22
		hwApFaultNotifyFat NOTIFICATION-TYPE
			OBJECTS { hwApIndex, hwApUsedType, hwApSysName }
			STATUS current
			DESCRIPTION
				"Description."
			::= { hwWlanDeviceNotify 22 }

--   1.3.6.1.4.1.2011.6.139.2.1.1.23
-- 1.3.6.1.4.1.2011.6.139.2.1.1.23
		-- 1.3.6.1.4.1.2011.6.139.2.1.1.23
		hwApNormalNotifyFat NOTIFICATION-TYPE
			OBJECTS { hwApIndex, hwApUsedType, hwApSysName }
			STATUS current
			DESCRIPTION
				"Description."
			::= { hwWlanDeviceNotify 23 }

--   1.3.6.1.4.1.2011.6.139.2.1.1.24
-- 1.3.6.1.4.1.2011.6.139.2.1.1.24
		-- 1.3.6.1.4.1.2011.6.139.2.1.1.24
		hwApTemperatureTooLowNotify NOTIFICATION-TYPE
			OBJECTS { hwApIndex, hwApMac, hwApNotifyOrRestoreTemperature }
			STATUS current
			DESCRIPTION
				"Description."
			::= { hwWlanDeviceNotify 24 }

--   1.3.6.1.4.1.2011.6.139.2.1.1.25
-- 1.3.6.1.4.1.2011.6.139.2.1.1.25
		-- 1.3.6.1.4.1.2011.6.139.2.1.1.25
		hwApTemperatureTooLowRestoreNotify NOTIFICATION-TYPE
			OBJECTS { hwApIndex, hwApMac, hwApNotifyOrRestoreTemperature }
			STATUS current
			DESCRIPTION
				"Description."
			::= { hwWlanDeviceNotify 25 }

--   1.3.6.1.4.1.2011.6.139.2.1.1.26
-- 1.3.6.1.4.1.2011.6.139.2.1.1.26
		-- 1.3.6.1.4.1.2011.6.139.2.1.1.26
		hwApTemperatureTooHighNotify NOTIFICATION-TYPE
			OBJECTS { hwApIndex, hwApMac, hwApNotifyOrRestoreTemperature }
			STATUS current
			DESCRIPTION
				"Description."
			::= { hwWlanDeviceNotify 26 }

--   1.3.6.1.4.1.2011.6.139.2.1.1.27
-- 1.3.6.1.4.1.2011.6.139.2.1.1.27
		-- 1.3.6.1.4.1.2011.6.139.2.1.1.27
		hwApTemperatureTooHighRestoreNotify NOTIFICATION-TYPE
			OBJECTS { hwApIndex, hwApMac, hwApNotifyOrRestoreTemperature }
			STATUS current
			DESCRIPTION
				"Description."
			::= { hwWlanDeviceNotify 27 }

		-- 1.3.6.1.4.1.2011.6.139.2.1.1.29
		hwRadioDownNotifyFat NOTIFICATION-TYPE
			OBJECTS { hwApIndex, hwApMac, hwApRadioNotifyPara }
			STATUS current
			DESCRIPTION
				"Description."
			::= { hwWlanDeviceNotify 29 }

		-- 1.3.6.1.4.1.2011.6.139.2.1.1.30
		hwRadioDownRecovNotifyFat NOTIFICATION-TYPE
			OBJECTS { hwApIndex, hwApMac, hwApRadioNotifyPara }
			STATUS current
			DESCRIPTION
				"Description."
			::= { hwWlanDeviceNotify 30 }

--   1.3.6.1.4.1.2011.6.139.2.1.1.27
-- 1.3.6.1.4.1.2011.6.139.2.1.1.31
		-- 1.3.6.1.4.1.2011.6.139.2.1.1.31
		hwApOpticalRxPowerTooHighNotify NOTIFICATION-TYPE
			OBJECTS { hwApIndex, hwApMac, hwApOpticalRxPower }
			STATUS current
			DESCRIPTION
				"Description."
			::= { hwWlanDeviceNotify 31 }

--   1.3.6.1.4.1.2011.6.139.2.1.1.27
-- 1.3.6.1.4.1.2011.6.139.2.1.1.32
		-- 1.3.6.1.4.1.2011.6.139.2.1.1.32
		hwApOpticalRxPowerTooHighRestoreNotify NOTIFICATION-TYPE
			OBJECTS { hwApIndex, hwApMac, hwApOpticalRxPower }
			STATUS current
			DESCRIPTION
				"Description."
			::= { hwWlanDeviceNotify 32 }

--   1.3.6.1.4.1.2011.6.139.2.1.1.27
-- 1.3.6.1.4.1.2011.6.139.2.1.1.33
		-- 1.3.6.1.4.1.2011.6.139.2.1.1.33
		hwApOpticalRxPowerTooLowNotify NOTIFICATION-TYPE
			OBJECTS { hwApIndex, hwApMac, hwApOpticalRxPower }
			STATUS current
			DESCRIPTION
				"Description."
			::= { hwWlanDeviceNotify 33 }

--   1.3.6.1.4.1.2011.6.139.2.1.1.27
-- 1.3.6.1.4.1.2011.6.139.2.1.1.34
		-- 1.3.6.1.4.1.2011.6.139.2.1.1.34
		hwApOpticalRxPowerTooLowRestoreNotify NOTIFICATION-TYPE
			OBJECTS { hwApIndex, hwApMac, hwApOpticalRxPower }
			STATUS current
			DESCRIPTION
				"Description."
			::= { hwWlanDeviceNotify 34 }

--   1.3.6.1.4.1.2011.6.139.2.1.1.27
-- 1.3.6.1.4.1.2011.6.139.2.1.1.35
		-- 1.3.6.1.4.1.2011.6.139.2.1.1.35
		hwApOpticalTemperatureTooHighNotify NOTIFICATION-TYPE
			OBJECTS { hwApIndex, hwApMac, hwApOpticalTemperature }
			STATUS current
			DESCRIPTION
				"Description."
			::= { hwWlanDeviceNotify 35 }

--   1.3.6.1.4.1.2011.6.139.2.1.1.27
-- 1.3.6.1.4.1.2011.6.139.2.1.1.36
		-- 1.3.6.1.4.1.2011.6.139.2.1.1.36
		hwApOpticalTemperatureTooHighRestoreNotify NOTIFICATION-TYPE
			OBJECTS { hwApIndex, hwApMac, hwApOpticalTemperature }
			STATUS current
			DESCRIPTION
				"Description."
			::= { hwWlanDeviceNotify 36 }

--   1.3.6.1.4.1.2011.6.139.2.1.1.27
-- 1.3.6.1.4.1.2011.6.139.2.1.1.37
		-- 1.3.6.1.4.1.2011.6.139.2.1.1.37
		hwApOpticalTemperatureTooLowNotify NOTIFICATION-TYPE
			OBJECTS { hwApIndex, hwApMac, hwApOpticalTemperature }
			STATUS current
			DESCRIPTION
				"Description."
			::= { hwWlanDeviceNotify 37 }

--   1.3.6.1.4.1.2011.6.139.2.1.1.27
-- 1.3.6.1.4.1.2011.6.139.2.1.1.38
		-- 1.3.6.1.4.1.2011.6.139.2.1.1.38
		hwApOpticalTemperatureTooLowRestoreNotify NOTIFICATION-TYPE
			OBJECTS { hwApIndex, hwApMac, hwApOpticalTemperature }
			STATUS current
			DESCRIPTION
				"Description."
			::= { hwWlanDeviceNotify 38 }

--  1.3.6.1.4.1.2011.6.139.2.1.1.39
		-- 1.3.6.1.4.1.2011.6.139.2.1.1.39
		hwApNotSupportCountryCodeNotify NOTIFICATION-TYPE
			OBJECTS { hwApIndex, hwApMac, hwApCfgCountryCode }
			STATUS current
			DESCRIPTION
				"Description."
			::= { hwWlanDeviceNotify 39 }

--  1.3.6.1.4.1.2011.6.139.2.1.1.40
		-- 1.3.6.1.4.1.2011.6.139.2.1.1.40
		hwApReceivedInvalidArpNotify NOTIFICATION-TYPE
			OBJECTS { hwApIndex, hwApMac, hwApNotifyRadioId, hwApNotifyWlanId, hwApArpAttackSrcMac, hwApArpAttackDstMac,
				hwApArpAttackSrcIP }
			STATUS current
			DESCRIPTION
				"Description."
			::= { hwWlanDeviceNotify 40 }

--  1.3.6.1.4.1.2011.6.139.2.1.1.41
		-- 1.3.6.1.4.1.2011.6.139.2.1.1.41
		hwApArpExceedThresholdNotify NOTIFICATION-TYPE
			OBJECTS { hwApIndex, hwApMac, hwApNotifyRadioId, hwApNotifyWlanId, hwApArpActualRate, hwApArpCfgRateThreshold
				 }
			STATUS current
			DESCRIPTION
				"Description."
			::= { hwWlanDeviceNotify 41 }

--  1.3.6.1.4.1.2011.6.139.2.1.1.42
		-- 1.3.6.1.4.1.2011.6.139.2.1.1.42
		hwApColdBootNotify NOTIFICATION-TYPE
			OBJECTS { hwApType, hwApIndex, hwApSysName, hwApMac, hwOccurTime,
				hwApBootNotifyName }
			STATUS current
			DESCRIPTION
				"Description."
			::= { hwWlanDeviceNotify 42 }

--  1.3.6.1.4.1.2011.6.139.2.1.1.43
		-- 1.3.6.1.4.1.2011.6.139.2.1.1.43
		hwApColdBootRestoreNotify NOTIFICATION-TYPE
			OBJECTS { hwApType, hwApIndex, hwApSysName, hwApMac, hwOccurTime,
				hwApBootNotifyName }
			STATUS current
			DESCRIPTION
				"Description."
			::= { hwWlanDeviceNotify 43 }

--  1.3.6.1.4.1.2011.6.139.2.1.1.44
		-- 1.3.6.1.4.1.2011.6.139.2.1.1.44
		hwApHotBootNotify NOTIFICATION-TYPE
			OBJECTS { hwApType, hwApIndex, hwApSysName, hwApMac, hwOccurTime,
				hwApBootNotifyName }
			STATUS current
			DESCRIPTION
				"Description."
			::= { hwWlanDeviceNotify 44 }

--  1.3.6.1.4.1.2011.6.139.2.1.1.45
		-- 1.3.6.1.4.1.2011.6.139.2.1.1.45
		hwApHotBootRestoreNotify NOTIFICATION-TYPE
			OBJECTS { hwApType, hwApIndex, hwApSysName, hwApMac, hwOccurTime,
				hwApBootNotifyName }
			STATUS current
			DESCRIPTION
				"Description."
			::= { hwWlanDeviceNotify 45 }

--  1.3.6.1.4.1.2011.6.139.2.1.1.46
		-- 1.3.6.1.4.1.2011.6.139.2.1.1.46
		hwStationOnlineNotify NOTIFICATION-TYPE
			OBJECTS { hwApIndex, hwApMac, hwWlanServiceStaRadioId, hwWlanServiceStaMac, hwStaAccessChannel,
				hwStaRssi, hwOccurTime }
			STATUS current
			DESCRIPTION
				"Description."
			::= { hwWlanDeviceNotify 46 }

--  1.3.6.1.4.1.2011.6.139.2.1.1.47
		-- 1.3.6.1.4.1.2011.6.139.2.1.1.47
		hwStationOfflineNotify NOTIFICATION-TYPE
			OBJECTS { hwApIndex, hwApMac, hwWlanServiceStaRadioId, hwWlanServiceStaMac, hwStaAccessChannel,
				hwStaRssi, hwOccurTime }
			STATUS current
			DESCRIPTION
				"Description."
			::= { hwWlanDeviceNotify 47 }

--  1.3.6.1.4.1.2011.6.139.2.1.1.48
		-- 1.3.6.1.4.1.2011.6.139.2.1.1.48
		hwStationSignalStrengthLowThanThresholdNotify NOTIFICATION-TYPE
			OBJECTS { hwApIndex, hwApMac, hwWlanServiceStaRadioId, hwWlanServiceStaMac, hwStaRssi,
				hwSignalStrengthThreshold }
			STATUS current
			DESCRIPTION
				"Description."
			::= { hwWlanDeviceNotify 48 }

		-- 1.3.6.1.4.1.2011.6.139.2.1.1.49
		hwAPBroadcastStormDownNotify NOTIFICATION-TYPE
			STATUS current
			DESCRIPTION
				"Description."
			::= { hwWlanDeviceNotify 49 }


		-- 1.3.6.1.4.1.2011.6.139.2.1.1.50
		hwAPBroadcastStormDownRestoreNotify NOTIFICATION-TYPE
			STATUS current
			DESCRIPTION
				"Description."
			::= { hwWlanDeviceNotify 50 }


		-- 1.3.6.1.4.1.2011.6.139.2.1.1.51
		hwAPBroadcastStormUpNotify NOTIFICATION-TYPE
			STATUS current
			DESCRIPTION
				"Description."
			::= { hwWlanDeviceNotify 51 }


		-- 1.3.6.1.4.1.2011.6.139.2.1.1.52
		hwAPBroadcastStormUpRestoreNotify NOTIFICATION-TYPE
			STATUS current
			DESCRIPTION
				"Description."
			::= { hwWlanDeviceNotify 52 }


		-- 1.3.6.1.4.1.2011.6.139.2.1.1.53
		hwApBroadcastRestrainDownNotify NOTIFICATION-TYPE
			STATUS current
			DESCRIPTION
				"Description."
			::= { hwWlanDeviceNotify 53 }


		-- 1.3.6.1.4.1.2011.6.139.2.1.1.54
		hwApBroadcastRestrainDownRestoreNotify NOTIFICATION-TYPE
			STATUS current
			DESCRIPTION
				"Description."
			::= { hwWlanDeviceNotify 54 }


		-- 1.3.6.1.4.1.2011.6.139.2.1.1.55
		hwApBroadcastRestrainUpNotify NOTIFICATION-TYPE
			STATUS current
			DESCRIPTION
				"Description."
			::= { hwWlanDeviceNotify 55 }


		-- 1.3.6.1.4.1.2011.6.139.2.1.1.56
		hwApBroadcastRestrainUpRestoreNotify NOTIFICATION-TYPE
			STATUS current
			DESCRIPTION
				"Description."
			::= { hwWlanDeviceNotify 56 }



		-- 1.3.6.1.4.1.2011.6.139.2.1.1.57
		hwApCRCTooHighNotify NOTIFICATION-TYPE
			OBJECTS { hwApIndex, hwApMac, hwCrcErrActual, hwCrcPortType, hwCrcPortID
				 }
			STATUS current
			DESCRIPTION
				"Description."
			::= { hwWlanDeviceNotify 57 }



		-- 1.3.6.1.4.1.2011.6.139.2.1.1.58
		hwApCRCTooHighRestoreNotify NOTIFICATION-TYPE
			OBJECTS { hwApIndex, hwApMac, hwCrcErrActual, hwCrcPortType, hwCrcPortID
				 }
			STATUS current
			DESCRIPTION
				"Description."
			::= { hwWlanDeviceNotify 58 }


		-- 1.3.6.1.4.1.2011.6.139.2.1.1.59
		hwApConflictApNameNotify NOTIFICATION-TYPE
			OBJECTS { hwApIndex, hwApMac, hwApSysName, hwOccurTime }
			STATUS current
			DESCRIPTION
				"Description."
			::= { hwWlanDeviceNotify 59 }

		-- 1.3.6.1.4.1.2011.6.139.2.1.1.60
		hwApLicenseNotify NOTIFICATION-TYPE
			OBJECTS { hwApLicenseInfo }
			STATUS current
			DESCRIPTION
				"Description."
			::= { hwWlanDeviceNotify 60 }

		-- BEGIN: FMEA alarm from AP 5030DN, 5130DN, 7030DE
		-- 1.3.6.1.4.1.2011.6.139.2.1.1.61
		hwApFmeaIICFaultNotify NOTIFICATION-TYPE
			OBJECTS { hwApIndex, hwApMac }
			STATUS current
			DESCRIPTION
				"AP IIC channel fault."
			::= { hwWlanDeviceNotify 61 }

		-- 1.3.6.1.4.1.2011.6.139.2.1.1.62
		hwApFmeaIICFaultRestoreNotify NOTIFICATION-TYPE
			OBJECTS { hwApIndex, hwApMac }
			STATUS current
			DESCRIPTION
				"AP IIC channel fault clear."
			::= { hwWlanDeviceNotify 62 }

		-- 1.3.6.1.4.1.2011.6.139.2.1.1.63
		hwApFmeaPHYFaultNotify NOTIFICATION-TYPE
			OBJECTS { hwApIndex, hwApMac }
			STATUS current
			DESCRIPTION
				"AP PHY CMOS fault."
			::= { hwWlanDeviceNotify 63 }

		-- 1.3.6.1.4.1.2011.6.139.2.1.1.64
		hwApFmeaPHYFaultRestoreNotify NOTIFICATION-TYPE
			OBJECTS { hwApIndex, hwApMac }
			STATUS current
			DESCRIPTION
				"AP PHY CMOS fault clear."
			::= { hwWlanDeviceNotify 64 }

		-- 1.3.6.1.4.1.2011.6.139.2.1.1.65
		hwApFmeaFaultNotify NOTIFICATION-TYPE
			OBJECTS { hwApIndex, hwApMac, hwApFaultID, hwApIfIndex, hwApFaultInfo }
			STATUS current
			DESCRIPTION
				"AP FMEA fault."
			::= { hwWlanDeviceNotify 65 }

		-- 1.3.6.1.4.1.2011.6.139.2.1.1.66
		hwApFmeaFaultRestoreNotify NOTIFICATION-TYPE
			OBJECTS { hwApIndex, hwApMac, hwApFaultID, hwApIfIndex, hwApFaultInfo }
			STATUS current
			DESCRIPTION
				"AP FMEA fault clear."
			::= { hwWlanDeviceNotify 66 }

		-- 1.3.6.1.4.1.2011.6.139.2.1.1.67
		hwApOpticalInsertNotify NOTIFICATION-TYPE
			OBJECTS { hwApIndex, hwApMac, hwApIfIndex }
			STATUS current
			DESCRIPTION
				"AP optical insert."
			::= { hwWlanDeviceNotify 67 }

		-- 1.3.6.1.4.1.2011.6.139.2.1.1.68
		hwApOpticalRemoveNotify NOTIFICATION-TYPE
			OBJECTS { hwApIndex, hwApMac, hwApIfIndex }
			STATUS current
			DESCRIPTION
				"AP optical remove."
			::= { hwWlanDeviceNotify 68 }

		-- END  : FMEA alarm from AP 5030DN, 5130DN, 7030DE
		-- 1.3.6.1.4.1.2011.6.139.2.1.1.69
		hwApReceivedInvalidArpNewNotify NOTIFICATION-TYPE
			OBJECTS { hwApIndex, hwApMac, hwApNotifyRadioId, hwApNotifyWlanId, hwApArpAttackDropNum }
			STATUS current
			DESCRIPTION
				"Description."
			::= { hwWlanDeviceNotify 69 }

		-- 1.3.6.1.4.1.2011.6.139.2.1.1.70
		hwApVersionMismatchNotify NOTIFICATION-TYPE
			OBJECTS { hwApIndex, hwApMac, hwApActualType, hwApSoftwareVersion }
			STATUS current
			DESCRIPTION
				"Description."
			::= { hwWlanDeviceNotify 70 }


--   1.3.6.1.4.1.2011.6.139.2.1.2
-- 1.3.6.1.4.1.2011.6.139.2.1.3
		-- 1.3.6.1.4.1.2011.6.139.2.1.3
		hwWlanDeviceNotifyObjects OBJECT IDENTIFIER ::= { hwWlanDeviceNotifications 2 }


--    1.3.6.1.4.1.2011.6.139.2.1.2.1
-- 1.3.6.1.4.1.2011.6.139.2.1.2.1
-- 1.3.6.1.4.1.2011.6.139.2.1.2.1
		-- 1.3.6.1.4.1.2011.6.139.2.1.2.1
		hwApActualType OBJECT-TYPE
			SYNTAX OCTET STRING
			MAX-ACCESS read-only
			STATUS current
			DESCRIPTION
				"The actual type of AP. This node is used for describe the actual type
				of an AP tying to get online, which type can't be matched by AC."
			::= { hwWlanDeviceNotifyObjects 1 }

--   1.3.6.1.4.1.2011.6.139.2.1.2.2
-- 1.3.6.1.4.1.2011.6.139.2.1.2.2
		-- 1.3.6.1.4.1.2011.6.139.2.1.2.2
		hwApCpuOccupancyRate OBJECT-TYPE
			SYNTAX Integer32
			MAX-ACCESS read-only
			STATUS current
			DESCRIPTION
				"Description."
			::= { hwWlanDeviceNotifyObjects 2 }

--   1.3.6.1.4.1.2011.6.139.2.1.2.3
-- 1.3.6.1.4.1.2011.6.139.2.1.2.3
		-- 1.3.6.1.4.1.2011.6.139.2.1.2.3
		hwApMemoryOccupancyRate OBJECT-TYPE
			SYNTAX Integer32
			MAX-ACCESS read-only
			STATUS current
			DESCRIPTION
				"Description."
			::= { hwWlanDeviceNotifyObjects 3 }

--   1.3.6.1.4.1.2011.6.139.2.1.2.4
-- 1.3.6.1.4.1.2011.6.139.2.1.2.4
		-- 1.3.6.1.4.1.2011.6.139.2.1.2.4
		hwApPermitStaNum OBJECT-TYPE
			SYNTAX Integer32
			MAX-ACCESS read-only
			STATUS current
			DESCRIPTION
				"Description."
			::= { hwWlanDeviceNotifyObjects 4 }

--   1.3.6.1.4.1.2011.6.139.2.1.2.5
-- 1.3.6.1.4.1.2011.6.139.2.1.2.5
		-- 1.3.6.1.4.1.2011.6.139.2.1.2.5
		hwStaAuthFailCause OBJECT-TYPE
			SYNTAX Integer32
			MAX-ACCESS read-only
			STATUS current
			DESCRIPTION
				"Description."
			::= { hwWlanDeviceNotifyObjects 5 }

--   1.3.6.1.4.1.2011.6.139.2.1.2.6
-- 1.3.6.1.4.1.2011.6.139.2.1.2.6
		-- 1.3.6.1.4.1.2011.6.139.2.1.2.6
		hwAcSystemSwitchType OBJECT-TYPE
			SYNTAX Integer32
			MAX-ACCESS read-only
			STATUS current
			DESCRIPTION
				"Description."
			::= { hwWlanDeviceNotifyObjects 6 }

		-- 1.3.6.1.4.1.2011.6.139.2.1.2.8
		hwApRadioNotifyPara OBJECT-TYPE
			SYNTAX Integer32
			MAX-ACCESS read-only
			STATUS current
			DESCRIPTION
				"Description."
			::= { hwWlanDeviceNotifyObjects 8 }

--   1.3.6.1.4.1.2011.6.139.2.1.2.6
-- 1.3.6.1.4.1.2011.6.139.2.1.2.9
		-- 1.3.6.1.4.1.2011.6.139.2.1.2.9
		hwApOpticalRxPower OBJECT-TYPE
			SYNTAX Integer32
			MAX-ACCESS read-only
			STATUS current
			DESCRIPTION
				"Description."
			::= { hwWlanDeviceNotifyObjects 9 }

--   1.3.6.1.4.1.2011.6.139.2.1.2.6
-- 1.3.6.1.4.1.2011.6.139.2.1.2.10
		-- 1.3.6.1.4.1.2011.6.139.2.1.2.10
		hwApOpticalTemperature OBJECT-TYPE
			SYNTAX Integer32
			MAX-ACCESS read-only
			STATUS current
			DESCRIPTION
				"Description."
			::= { hwWlanDeviceNotifyObjects 10 }

--  1.3.6.1.4.1.2011.6.139.2.1.2.11
		-- 1.3.6.1.4.1.2011.6.139.2.1.2.11
		hwApCfgCountryCode OBJECT-TYPE
			SYNTAX OCTET STRING
			MAX-ACCESS read-only
			STATUS current
			DESCRIPTION
				"Description."
			::= { hwWlanDeviceNotifyObjects 11 }

--  1.3.6.1.4.1.2011.6.139.2.1.2.12
		-- 1.3.6.1.4.1.2011.6.139.2.1.2.12
		hwApArpAttackSrcMac OBJECT-TYPE
			SYNTAX MacAddress
			MAX-ACCESS read-only
			STATUS current
			DESCRIPTION
				"Description."
			::= { hwWlanDeviceNotifyObjects 12 }

--  1.3.6.1.4.1.2011.6.139.2.1.2.13
		-- 1.3.6.1.4.1.2011.6.139.2.1.2.13
		hwApArpAttackDstMac OBJECT-TYPE
			SYNTAX MacAddress
			MAX-ACCESS read-only
			STATUS current
			DESCRIPTION
				"Description."
			::= { hwWlanDeviceNotifyObjects 13 }

--  1.3.6.1.4.1.2011.6.139.2.1.2.14
		-- 1.3.6.1.4.1.2011.6.139.2.1.2.14
		hwApArpAttackSrcIP OBJECT-TYPE
			SYNTAX IpAddress
			MAX-ACCESS read-only
			STATUS current
			DESCRIPTION
				"Description."
			::= { hwWlanDeviceNotifyObjects 14 }

--  1.3.6.1.4.1.2011.6.139.2.1.2.15
		-- 1.3.6.1.4.1.2011.6.139.2.1.2.15
		hwApArpCfgRateThreshold OBJECT-TYPE
			SYNTAX Integer32
			MAX-ACCESS read-only
			STATUS current
			DESCRIPTION
				"Description."
			::= { hwWlanDeviceNotifyObjects 15 }

--  1.3.6.1.4.1.2011.6.139.2.1.2.16
		-- 1.3.6.1.4.1.2011.6.139.2.1.2.16
		hwApArpActualRate OBJECT-TYPE
			SYNTAX Integer32
			MAX-ACCESS read-only
			STATUS current
			DESCRIPTION
				"Description."
			::= { hwWlanDeviceNotifyObjects 16 }

--  1.3.6.1.4.1.2011.6.139.2.1.2.17
		-- 1.3.6.1.4.1.2011.6.139.2.1.2.17
		hwApNotifyRadioId OBJECT-TYPE
			SYNTAX Integer32
			MAX-ACCESS read-only
			STATUS current
			DESCRIPTION
				"Description."
			::= { hwWlanDeviceNotifyObjects 17 }

--  1.3.6.1.4.1.2011.6.139.2.1.2.18
		-- 1.3.6.1.4.1.2011.6.139.2.1.2.18
		hwApNotifyOrRestoreTemperature OBJECT-TYPE
			SYNTAX Integer32
			MAX-ACCESS read-only
			STATUS current
			DESCRIPTION
				"Description."
			::= { hwWlanDeviceNotifyObjects 18 }

--  1.3.6.1.4.1.2011.6.139.2.1.2.19
		-- 1.3.6.1.4.1.2011.6.139.2.1.2.19
		hwOccurTime OBJECT-TYPE
			SYNTAX OCTET STRING
			MAX-ACCESS read-only
			STATUS current
			DESCRIPTION
				"Description."
			::= { hwWlanDeviceNotifyObjects 19 }

--  1.3.6.1.4.1.2011.6.139.2.1.2.20
		-- 1.3.6.1.4.1.2011.6.139.2.1.2.20
		hwApBootNotifyName OBJECT-TYPE
			SYNTAX OCTET STRING
			MAX-ACCESS read-only
			STATUS current
			DESCRIPTION
				"Description."
			::= { hwWlanDeviceNotifyObjects 20 }

--  1.3.6.1.4.1.2011.6.139.2.1.2.21
		-- 1.3.6.1.4.1.2011.6.139.2.1.2.21
		hwApFaultTimes OBJECT-TYPE
			SYNTAX Integer32
			MAX-ACCESS read-only
			STATUS current
			DESCRIPTION
				"Description."
			::= { hwWlanDeviceNotifyObjects 21 }

--  1.3.6.1.4.1.2011.6.139.2.1.2.22
		-- 1.3.6.1.4.1.2011.6.139.2.1.2.22
		hwSignalStrengthThreshold OBJECT-TYPE
			SYNTAX Integer32
			MAX-ACCESS read-write
			STATUS current
			DESCRIPTION
				"Description."
			::= { hwWlanDeviceNotifyObjects 22 }

		-- 1.3.6.1.4.1.2011.6.139.2.1.2.23
		hwStaBroadcastFlux OBJECT-TYPE
			SYNTAX Unsigned32
			MAX-ACCESS read-write
			STATUS current
			DESCRIPTION
				"Description."
			::= { hwWlanDeviceNotifyObjects 23 }


		-- 1.3.6.1.4.1.2011.6.139.2.1.2.24
		hwBroadcastWarnThresholdDown OBJECT-TYPE
			SYNTAX Unsigned32
			MAX-ACCESS read-write
			STATUS current
			DESCRIPTION
				"Description."
			::= { hwWlanDeviceNotifyObjects 24 }


		-- 1.3.6.1.4.1.2011.6.139.2.1.2.25
		hwBroadcastWarnThresholdUp OBJECT-TYPE
			SYNTAX Unsigned32
			MAX-ACCESS read-write
			STATUS current
			DESCRIPTION
				"Description."
			::= { hwWlanDeviceNotifyObjects 25 }


		-- 1.3.6.1.4.1.2011.6.139.2.1.2.26
		hwBroadcastRestrainThresholdDown OBJECT-TYPE
			SYNTAX Unsigned32
			MAX-ACCESS read-write
			STATUS current
			DESCRIPTION
				"Description."
			::= { hwWlanDeviceNotifyObjects 26 }


		-- 1.3.6.1.4.1.2011.6.139.2.1.2.27
		hwBroadcastRestrainThresholdUp OBJECT-TYPE
			SYNTAX Unsigned32
			MAX-ACCESS read-write
			STATUS current
			DESCRIPTION
				"Description."
			::= { hwWlanDeviceNotifyObjects 27 }


		-- 1.3.6.1.4.1.2011.6.139.2.1.2.28
		hwApBroadcastFlux OBJECT-TYPE
			SYNTAX Integer32
			MAX-ACCESS read-write
			STATUS current
			DESCRIPTION
				"Description."
			::= { hwWlanDeviceNotifyObjects 28 }


		-- 1.3.6.1.4.1.2011.6.139.2.1.2.29
		hwCrcErrActual OBJECT-TYPE
			SYNTAX Unsigned32
			MAX-ACCESS read-only
			STATUS current
			DESCRIPTION
				"Description."
			::= { hwWlanDeviceNotifyObjects 29 }

		-- 1.3.6.1.4.1.2011.6.139.2.1.2.30
		hwCrcThreshold OBJECT-TYPE
			SYNTAX Unsigned32
			MAX-ACCESS read-only
			STATUS current
			DESCRIPTION
				"Description."
			::= { hwWlanDeviceNotifyObjects 30 }
	        -- 1.3.6.1.4.1.2011.6.139.2.1.2.31
		hwApNotifyWlanId OBJECT-TYPE
			SYNTAX Integer32
			MAX-ACCESS read-only
			STATUS current
			DESCRIPTION
				"Description."
			::= { hwWlanDeviceNotifyObjects 31 }
		-- 1.3.6.1.4.1.2011.6.139.2.1.2.32
		hwApLicenseInfo OBJECT-TYPE
			SYNTAX OCTET STRING
			MAX-ACCESS read-only
			STATUS current
			DESCRIPTION
				"Description."
			::= { hwWlanDeviceNotifyObjects 32 }


	        -- 1.3.6.1.4.1.2011.6.139.2.1.2.33
		hwCrcPortType OBJECT-TYPE
			SYNTAX OCTET STRING
			MAX-ACCESS read-only
			STATUS current
			DESCRIPTION
				"Description."
			::= { hwWlanDeviceNotifyObjects 33 }
		-- 1.3.6.1.4.1.2011.6.139.2.1.2.34
		hwCrcPortID OBJECT-TYPE
			SYNTAX Integer32
			MAX-ACCESS read-only
			STATUS current
			DESCRIPTION
				"Description."
			::= { hwWlanDeviceNotifyObjects 34 }

		-- 1.3.6.1.4.1.2011.6.139.2.1.2.35
		hwApArpAttackDropNum OBJECT-TYPE
			SYNTAX Integer32
			MAX-ACCESS read-only
			STATUS current
			DESCRIPTION
				"Description."
			::= { hwWlanDeviceNotifyObjects 35 }

		-- 1.3.6.1.4.1.2011.6.139.2.1.2.36
		hwApFaultID OBJECT-TYPE
			SYNTAX INTEGER
				{
				phy(1),
				cpld(2),
				lm75(3),
				sfp(4),
				wifi(5)
				}
			MAX-ACCESS read-only
			STATUS current
			DESCRIPTION
				"AP hardware fault index."
			::= { hwWlanDeviceNotifyObjects 36 }
		-- 1.3.6.1.4.1.2011.6.139.2.1.2.37
                hwApIfIndex OBJECT-TYPE
			SYNTAX Integer32
			MAX-ACCESS read-only
			STATUS current
			DESCRIPTION
				"AP hardware IfIndex."
			::= { hwWlanDeviceNotifyObjects 37 }
		-- 1.3.6.1.4.1.2011.6.139.2.1.2.38
		hwApFaultInfo OBJECT-TYPE
			SYNTAX OCTET STRING
			MAX-ACCESS read-only
			STATUS current
			DESCRIPTION
				"AP hardware fault description."
			::= { hwWlanDeviceNotifyObjects 38 }

--  1.3.6.1.4.1.2011.6.139.2.2
		-- 1.3.6.1.4.1.2011.6.139.2.2
		hwApTypeObjects OBJECT IDENTIFIER ::= { hwWlanDevice 2 }

--    1.3.6.1.4.1.2011.6.139.2.2.1
-- 1.3.6.1.4.1.2011.6.139.2.2.1
-- 1.3.6.1.4.1.2011.6.139.2.2.1
		-- 1.3.6.1.4.1.2011.6.139.2.2.1
		hwApTypeTable OBJECT-TYPE
			SYNTAX SEQUENCE OF HwApTypeEntry
			MAX-ACCESS not-accessible
			STATUS current
			DESCRIPTION
				"Huawei AP type table. The index of this table is hwApType. AP type
				is a string used to represent a kind of AP. AP type table include
				following attribute such as AP's type name, maximum station number,
				maximum SSID number, radio number and type, lineate port number and
				type etc.
				"
			::= { hwApTypeObjects 1 }

--    1.3.6.1.4.1.2011.6.139.2.2.1.1
-- 1.3.6.1.4.1.2011.6.139.2.2.1.1
-- 1.3.6.1.4.1.2011.6.139.2.2.1.1
		-- 1.3.6.1.4.1.2011.6.139.2.2.1.1
		hwApTypeEntry OBJECT-TYPE
			SYNTAX HwApTypeEntry
			MAX-ACCESS not-accessible
			STATUS current
			DESCRIPTION
				"Huawei AP type table entry.The index of this entry is hwApType. AP
				type is a string used to represent a kind of AP. AP type table include
				following attribute such as AP's type name, maximum statio nnumber,
				maximum SSID number, radio number and type, lineate port number and
				type etc.
				"
			INDEX { hwApType }
			::= { hwApTypeTable 1 }

		HwApTypeEntry ::=
			SEQUENCE {
				hwApType
					OCTET STRING,
				hwApTypeDesc
					OCTET STRING,
				hwApTypeLineatePortNum
					Integer32,
				hwApTypeRadioNum
					Integer32,
				hwApTypeMaxStaNum
					Integer32,
				hwApTypeMaxSsidNum
					Integer32,
				hwApTypeAntennaGain
					Integer32,
				hwApTypeRowStatus
					RowStatus,
				hwApTypeReset
					Integer32
			 }

--    1.3.6.1.4.1.2011.6.139.2.2.1.1.1
-- 1.3.6.1.4.1.2011.6.139.2.2.1.1.1
-- 1.3.6.1.4.1.2011.6.139.2.2.1.1.1
		-- 1.3.6.1.4.1.2011.6.139.2.2.1.1.1
		hwApType OBJECT-TYPE
			SYNTAX OCTET STRING
			MAX-ACCESS accessible-for-notify
			STATUS current
			DESCRIPTION
				"AP type is the identification of a kind of AP. "
			::= { hwApTypeEntry 1 }

--    1.3.6.1.4.1.2011.6.139.2.2.1.1.2
-- 1.3.6.1.4.1.2011.6.139.2.2.1.1.2
-- 1.3.6.1.4.1.2011.6.139.2.2.1.1.2
		-- 1.3.6.1.4.1.2011.6.139.2.2.1.1.2
		hwApTypeDesc OBJECT-TYPE
			SYNTAX OCTET STRING
			MAX-ACCESS read-create
			STATUS current
			DESCRIPTION
				"Description of AP type. The maximum string length is 63.
				"
			::= { hwApTypeEntry 2 }

--    1.3.6.1.4.1.2011.6.139.2.2.1.1.3
-- 1.3.6.1.4.1.2011.6.139.2.2.1.1.3
-- 1.3.6.1.4.1.2011.6.139.2.2.1.1.3
		-- 1.3.6.1.4.1.2011.6.139.2.2.1.1.3
		hwApTypeLineatePortNum OBJECT-TYPE
			SYNTAX Integer32
			MAX-ACCESS read-create
			STATUS current
			DESCRIPTION
				"The lineate port number of AP.When add an AP type, its default
				lineateport number is 8."
			::= { hwApTypeEntry 3 }

--    1.3.6.1.4.1.2011.6.139.2.2.1.1.4
-- 1.3.6.1.4.1.2011.6.139.2.2.1.1.4
-- 1.3.6.1.4.1.2011.6.139.2.2.1.1.4
		-- 1.3.6.1.4.1.2011.6.139.2.2.1.1.4
		hwApTypeRadioNum OBJECT-TYPE
			SYNTAX Integer32
			MAX-ACCESS read-create
			STATUS current
			DESCRIPTION
				"The number of radios on the AP.When add an AP type, its default
				radios number is 4."
			::= { hwApTypeEntry 4 }

--    1.3.6.1.4.1.2011.6.139.2.2.1.1.5
-- 1.3.6.1.4.1.2011.6.139.2.2.1.1.5
-- 1.3.6.1.4.1.2011.6.139.2.2.1.1.5
		-- 1.3.6.1.4.1.2011.6.139.2.2.1.1.5
		hwApTypeMaxStaNum OBJECT-TYPE
			SYNTAX Integer32
			MAX-ACCESS read-create
			STATUS current
			DESCRIPTION
				"The maximum of station of AP.When add an AP type, its default
				access station number is 128."
			::= { hwApTypeEntry 5 }

--    1.3.6.1.4.1.2011.6.139.2.2.1.1.6
-- 1.3.6.1.4.1.2011.6.139.2.2.1.1.6
-- 1.3.6.1.4.1.2011.6.139.2.2.1.1.6
		-- 1.3.6.1.4.1.2011.6.139.2.2.1.1.6
		hwApTypeMaxSsidNum OBJECT-TYPE
			SYNTAX Integer32
			MAX-ACCESS read-create
			STATUS current
			DESCRIPTION
				"The maximum of ssid of AP.When add an AP type, its default max-
				imum SSID number is 32."
			::= { hwApTypeEntry 6 }

--    1.3.6.1.4.1.2011.6.139.2.2.1.1.7
-- 1.3.6.1.4.1.2011.6.139.2.2.1.1.7
-- 1.3.6.1.4.1.2011.6.139.2.2.1.1.7
		-- 1.3.6.1.4.1.2011.6.139.2.2.1.1.7
		hwApTypeAntennaGain OBJECT-TYPE
			SYNTAX Integer32
			UNITS "dBi"
			MAX-ACCESS read-create
			STATUS current
			DESCRIPTION
				"The antenna gain of AP. Unit: dBi. Its default antenna gain is
				0."
			::= { hwApTypeEntry 7 }

--    1.3.6.1.4.1.2011.6.139.2.2.1.1.8
-- 1.3.6.1.4.1.2011.6.139.2.2.1.1.8
-- 1.3.6.1.4.1.2011.6.139.2.2.1.1.8
		-- 1.3.6.1.4.1.2011.6.139.2.2.1.1.8
		hwApTypeRowStatus OBJECT-TYPE
			SYNTAX RowStatus
			MAX-ACCESS read-create
			STATUS current
			DESCRIPTION
				"Row status: mainly to support AP type addition and deletion."
			::= { hwApTypeEntry 8 }

--  1.3.6.1.4.1.2011.6.139.2.2.1.1.9
		-- 1.3.6.1.4.1.2011.6.139.2.2.1.1.9
		hwApTypeReset OBJECT-TYPE
			SYNTAX Integer32
			MAX-ACCESS read-write
			STATUS current
			DESCRIPTION
				"Description."
			::= { hwApTypeEntry 9 }

		-- 1.3.6.1.4.1.2011.6.139.2.2.3
		hwApTypeRadioTable OBJECT-TYPE
			SYNTAX SEQUENCE OF HwApTypeRadioEntry
			MAX-ACCESS not-accessible
			STATUS current
			DESCRIPTION
				"Huawei AP type radio table. Each AP type has several radios, gene-
				rally 1 to 4 radios. The index of this table is hwApType in table
				hwApTypeTable and hwApTypeRadioIndex. It describes the following
				attributes of a radio inAP type, radio type, maximal spatial streams,
				maximal antenna number."
			::= { hwApTypeObjects 3 }

--    1.3.6.1.4.1.2011.6.139.2.2.3.1
-- 1.3.6.1.4.1.2011.6.139.2.2.3.1
-- 1.3.6.1.4.1.2011.6.139.2.2.3.1
		-- 1.3.6.1.4.1.2011.6.139.2.2.3.1
		hwApTypeRadioEntry OBJECT-TYPE
			SYNTAX HwApTypeRadioEntry
			MAX-ACCESS not-accessible
			STATUS current
			DESCRIPTION
				"Huawei AP type radio table entry.Each AP type has several radios, gene-
				rally 1 to 4 radios. The index of this entry is hwApType in table
				hwApTypeTable and hwApTypeRadioIndex. It describes the following
				attributes of a radio inAP type, radio type, maximal spatial streams,
				maximal antenna number."
			INDEX { hwApType, hwApTypeRadioIndex }
			::= { hwApTypeRadioTable 1 }

		HwApTypeRadioEntry ::=
			SEQUENCE {
				hwApTypeRadioIndex
					Integer32,
				hwApTypeRadioType
					INTEGER,
				hwRadioMaxSpatialStreamsNum
					Unsigned32,
				hwRadioMaxAntennasNum
					Unsigned32,
				hwRadioMaxVAPNum
					Unsigned32,
				hwApTypeRadioAntennaGain
					Integer32
			 }

--    1.3.6.1.4.1.2011.6.139.2.2.3.1.1
-- 1.3.6.1.4.1.2011.6.139.2.2.3.1.1
-- 1.3.6.1.4.1.2011.6.139.2.2.3.1.1
		-- 1.3.6.1.4.1.2011.6.139.2.2.3.1.1
		hwApTypeRadioIndex OBJECT-TYPE
			SYNTAX Integer32
			MAX-ACCESS not-accessible
			STATUS current
			DESCRIPTION
				"Index of radio in an AP type."
			::= { hwApTypeRadioEntry 1 }

--    1.3.6.1.4.1.2011.6.139.2.2.3.1.2
-- 1.3.6.1.4.1.2011.6.139.2.2.3.1.2
-- 1.3.6.1.4.1.2011.6.139.2.2.3.1.2
		-- 1.3.6.1.4.1.2011.6.139.2.2.3.1.2
		hwApTypeRadioType OBJECT-TYPE
			SYNTAX INTEGER
				{
				wlan80211a(1),
				wlan80211b(2),
				wlan80211g(3),
				wlan80211bg(4),
				wlan80211an(5),
				wlan80211bgn(6)
				}
			MAX-ACCESS read-write
			STATUS current
			DESCRIPTION
				"The type of radio of AP type. When add an AP type ,the default radio type
				is wlan80211a(1).
				"
			::= { hwApTypeRadioEntry 2 }

--    1.3.6.1.4.1.2011.6.139.2.2.3.1.3
-- 1.3.6.1.4.1.2011.6.139.2.2.3.1.3
-- 1.3.6.1.4.1.2011.6.139.2.2.3.1.3
		-- 1.3.6.1.4.1.2011.6.139.2.2.3.1.3
		hwRadioMaxSpatialStreamsNum OBJECT-TYPE
			SYNTAX Unsigned32 (1..4)
			MAX-ACCESS read-write
			STATUS current
			DESCRIPTION
				"Maximum spatial streams number of a radio in an AP type.When add an
				AP type ,its defautl value is 1 ."
			::= { hwApTypeRadioEntry 3 }

--    1.3.6.1.4.1.2011.6.139.2.2.3.1.4
-- 1.3.6.1.4.1.2011.6.139.2.2.3.1.4
-- 1.3.6.1.4.1.2011.6.139.2.2.3.1.4
		-- 1.3.6.1.4.1.2011.6.139.2.2.3.1.4
		hwRadioMaxAntennasNum OBJECT-TYPE
			SYNTAX Unsigned32 (0..254)
			MAX-ACCESS read-write
			STATUS current
			DESCRIPTION
				"Maximum antennas number of a radioin an AP type,defautl is 1 for
				no-80211n type	radio, 0(Smart-Antennas-Array) for 80211n type radio."
			::= { hwApTypeRadioEntry 4 }

--    1.3.6.1.4.1.2011.6.139.2.2.3.1.5
-- 1.3.6.1.4.1.2011.6.139.2.2.3.1.5
-- 1.3.6.1.4.1.2011.6.139.2.2.3.1.5
		-- 1.3.6.1.4.1.2011.6.139.2.2.3.1.5
		hwRadioMaxVAPNum OBJECT-TYPE
			SYNTAX Unsigned32 (1..32)
			MAX-ACCESS read-write
			STATUS current
			DESCRIPTION
				"Maximum VAP number of a radioin an AP type."
			::= { hwApTypeRadioEntry 5 }

--  1.3.6.1.4.1.2011.6.139.2.2.3.1.6
		-- 1.3.6.1.4.1.2011.6.139.2.2.3.1.6
		hwApTypeRadioAntennaGain OBJECT-TYPE
			SYNTAX Integer32 (0..30)
			MAX-ACCESS read-write
			STATUS current
			DESCRIPTION
				"Description."
			::= { hwApTypeRadioEntry 6 }


		-- 1.3.6.1.4.1.2011.6.139.2.2.4
		hwApTypeLineatePortInfoTable OBJECT-TYPE
			SYNTAX SEQUENCE OF HwApTypeLineatePortInfoEntry
			MAX-ACCESS not-accessible
			STATUS current
			DESCRIPTION
				"Huawei AP type lineate port table.Each AP type may have several line-
				ate port.The index of this table is AP type in table hwApTypeTable
				and lineate port ID of AP type. The table describes the lineate port
				type of all AP type."
			::= { hwApTypeObjects 4 }


		-- 1.3.6.1.4.1.2011.6.139.2.2.4.1
		hwApTypeLineatePortInfoEntry OBJECT-TYPE
			SYNTAX HwApTypeLineatePortInfoEntry
			MAX-ACCESS not-accessible
			STATUS current
			DESCRIPTION
				"Huawei AP type lineate port table entry.Each AP type may have several
				lineate port.The index of this table is AP type in table hwApTypeTable
				and lineate port ID of AP type. The table describes the lineate port
				type of all AP type."
			INDEX { hwApType, hwApTypeLineatePortIndex }
			::= { hwApTypeLineatePortInfoTable 1 }

		HwApTypeLineatePortInfoEntry ::=
			SEQUENCE {
				hwApTypeLineatePortIndex
					Integer32,
				hwApTypeLineatePortType
					INTEGER,
				hwApTypeLineatePortName
					OCTET STRING
			 }


		-- 1.3.6.1.4.1.2011.6.139.2.2.4.1.1
		hwApTypeLineatePortIndex OBJECT-TYPE
			SYNTAX Integer32
			MAX-ACCESS not-accessible
			STATUS current
			DESCRIPTION
				"Index of lineate port in an AP type."
			::= { hwApTypeLineatePortInfoEntry 1 }

--      1.3.6.1.4.1.2011.6.139.2.2.2.1.2
-- 1.3.6.1.4.1.2011.6.139.2.2.2.1.2
-- 1.3.6.1.4.1.2011.6.139.2.2.2.1.2
-- 1.3.6.1.4.1.2011.6.139.2.2.2.1.2
-- 1.3.6.1.4.1.2011.6.139.2.2.4.1.2
		-- 1.3.6.1.4.1.2011.6.139.2.2.4.1.2
		hwApTypeLineatePortType OBJECT-TYPE
			SYNTAX INTEGER
				{
				fe(1),
				ge(2),
				gpon(3),
				epon(4),
				adsl2plus(5)
				}
			MAX-ACCESS read-only
			STATUS current
			DESCRIPTION
				"The type of lineate port of AP type.When add a new AP type, its
				default lineate port type is fe(1).
				"
			::= { hwApTypeLineatePortInfoEntry 2 }

--  1.3.6.1.4.1.2011.6.139.2.2.4.1.3
		-- 1.3.6.1.4.1.2011.6.139.2.2.4.1.3
		hwApTypeLineatePortName OBJECT-TYPE
			SYNTAX OCTET STRING
			MAX-ACCESS read-only
			STATUS current
			DESCRIPTION
				"Description."
			::= { hwApTypeLineatePortInfoEntry 3 }

--      1.3.6.1.4.1.2011.6.139.2.3
-- 1.3.6.1.4.1.2011.6.139.2.3
-- 1.3.6.1.4.1.2011.6.139.2.3
		-- 1.3.6.1.4.1.2011.6.139.2.3
		hwApProfileObjects OBJECT IDENTIFIER ::= { hwWlanDevice 3 }

--    1.3.6.1.4.1.2011.6.139.2.3.1
-- 1.3.6.1.4.1.2011.6.139.2.3.1
-- 1.3.6.1.4.1.2011.6.139.2.3.1
		-- 1.3.6.1.4.1.2011.6.139.2.3.1
		hwApProfileTable OBJECT-TYPE
			SYNTAX SEQUENCE OF HwApProfileEntry
			MAX-ACCESS not-accessible
			STATUS current
			DESCRIPTION
				"Huawei AP profile table. The index of this tabel is AP profile name.
				AP profile is aggregate of a group of configuration. Such as, MTU of
				AP's Ethernet, DoS defend switch, working mode of AP, AP log backup
				server configuration, etc.
				"
			::= { hwApProfileObjects 1 }

--    1.3.6.1.4.1.2011.6.139.2.3.1.1
-- 1.3.6.1.4.1.2011.6.139.2.3.1.1
-- 1.3.6.1.4.1.2011.6.139.2.3.1.1
		-- 1.3.6.1.4.1.2011.6.139.2.3.1.1
		hwApProfileEntry OBJECT-TYPE
			SYNTAX HwApProfileEntry
			MAX-ACCESS not-accessible
			STATUS current
			DESCRIPTION
				"Huawei AP profile table entry.The index of this tabel is AP profile
				name. AP profile is aggregate of a group of configuration. Such as, MTU
				of AP's Ethernet, DoS defend switch, working mode of AP, AP log backup
				server configuration, etc."
			INDEX { hwApProfileName }
			::= { hwApProfileTable 1 }

		HwApProfileEntry ::=
			SEQUENCE {
				hwApProfileName
					OCTET STRING,
				hwApEthPortMtu
					Integer32,
				hwApDosDefend
					INTEGER,
				hwApWorkMode
					INTEGER,
				hwApLogBackupServerIp
					IpAddress,
				hwApLogBackupMode
					INTEGER,
				hwApProfileRowStatus
					RowStatus,
				hwApSampleTime
					Integer32,
				hwApStatisticsInterval
					Integer32,
				hwApEapStartMode
					INTEGER,
				hwApEapStartUnicastMac
					MacAddress,
				hwApEapStartTransform
					INTEGER,
				hwApEapResponseMode
					INTEGER,
				hwApEapResponseUnicastMac
					MacAddress,
				hwApEapResponseTransform
					INTEGER,
				hwApOfflineManagement
					INTEGER,
				hwApAlarmRestrictionMode
					INTEGER,
				hwApAlarmRestrictionPeriod
					Integer32,
				hwAp4WayHandshakeRoamPolicy
					INTEGER,
				hwApLogRecordLevel
					INTEGER,
				hwApLogBackupPeriodTime
					Integer32,
				hwApLogRecordFtpMode
					INTEGER,
				hwApLogServerUsername
					OCTET STRING,
				hwApLogServerUserPassword
					OCTET STRING,
				hwApLogServerIp
					IpAddress,
				hwApProfileTelnetSwitch
					INTEGER,
				hwApSshSwitch
					INTEGER,
				hwApProfileDhcpTrustPort
					INTEGER,
				hwApProfileConsoleSwitch
					INTEGER,
				hwApProfileMaxUserNum
					Integer32,
				hwApProfileNdTrustPort
					INTEGER,
				hwApLogBackupServerIpv6Addr
					OCTET STRING,
				hwApLedSwitch
					INTEGER,
				hwApLocalAssocResSwitch
					INTEGER
			 }

--    1.3.6.1.4.1.2011.6.139.2.3.1.1.1
-- 1.3.6.1.4.1.2011.6.139.2.3.1.1.1
-- 1.3.6.1.4.1.2011.6.139.2.3.1.1.1
		-- 1.3.6.1.4.1.2011.6.139.2.3.1.1.1
		hwApProfileName OBJECT-TYPE
			SYNTAX OCTET STRING
			MAX-ACCESS not-accessible
			STATUS current
			DESCRIPTION
				"Ap profile name identifies an AP profile, which include a set of
				AP's configuration."
			::= { hwApProfileEntry 1 }

--    1.3.6.1.4.1.2011.6.139.2.3.1.1.2
-- 1.3.6.1.4.1.2011.6.139.2.3.1.1.2
-- 1.3.6.1.4.1.2011.6.139.2.3.1.1.2
		-- 1.3.6.1.4.1.2011.6.139.2.3.1.1.2
		hwApEthPortMtu OBJECT-TYPE
			SYNTAX Integer32
			MAX-ACCESS read-create
			STATUS current
			DESCRIPTION
				"The maximal packet size of AP Ethernet."
			::= { hwApProfileEntry 2 }

--    1.3.6.1.4.1.2011.6.139.2.3.1.1.3
-- 1.3.6.1.4.1.2011.6.139.2.3.1.1.3
-- 1.3.6.1.4.1.2011.6.139.2.3.1.1.3
		-- 1.3.6.1.4.1.2011.6.139.2.3.1.1.3
		hwApDosDefend OBJECT-TYPE
			SYNTAX INTEGER
				{
				enable(1),
				disable(2)
				}
			MAX-ACCESS read-create
			STATUS current
			DESCRIPTION
				"Not support.
				"
			::= { hwApProfileEntry 3 }

--    1.3.6.1.4.1.2011.6.139.2.3.1.1.4
-- 1.3.6.1.4.1.2011.6.139.2.3.1.1.4
-- 1.3.6.1.4.1.2011.6.139.2.3.1.1.4
		-- 1.3.6.1.4.1.2011.6.139.2.3.1.1.4
		hwApWorkMode OBJECT-TYPE
			SYNTAX INTEGER
				{
				bridge(1),
				routing(2)
				}
			MAX-ACCESS read-create
			STATUS current
			DESCRIPTION
				"Not support.
				"
			::= { hwApProfileEntry 4 }

--    1.3.6.1.4.1.2011.6.139.2.3.1.1.5
-- 1.3.6.1.4.1.2011.6.139.2.3.1.1.5
-- 1.3.6.1.4.1.2011.6.139.2.3.1.1.5
		-- 1.3.6.1.4.1.2011.6.139.2.3.1.1.5
		hwApLogBackupServerIp OBJECT-TYPE
			SYNTAX IpAddress
			MAX-ACCESS read-create
			STATUS current
			DESCRIPTION
				"Ip address of AP's syslog backup server."
			::= { hwApProfileEntry 5 }

--    1.3.6.1.4.1.2011.6.139.2.3.1.1.6
-- 1.3.6.1.4.1.2011.6.139.2.3.1.1.6
-- 1.3.6.1.4.1.2011.6.139.2.3.1.1.6
		-- 1.3.6.1.4.1.2011.6.139.2.3.1.1.6
		hwApLogBackupMode OBJECT-TYPE
			SYNTAX INTEGER
				{
				autoBackup(1),
				manualBackup(2),
				disable(3)
				}
			MAX-ACCESS read-create
			STATUS current
			DESCRIPTION
				"Not support.
				"
			::= { hwApProfileEntry 6 }

--    1.3.6.1.4.1.2011.6.139.2.3.1.1.7
-- 1.3.6.1.4.1.2011.6.139.2.3.1.1.7
-- 1.3.6.1.4.1.2011.6.139.2.3.1.1.7
		-- 1.3.6.1.4.1.2011.6.139.2.3.1.1.7
		hwApProfileRowStatus OBJECT-TYPE
			SYNTAX RowStatus
			MAX-ACCESS read-create
			STATUS current
			DESCRIPTION
				"Row status: mainly to support AP profile addition and deletion."
			::= { hwApProfileEntry 7 }

--    1.3.6.1.4.1.2011.6.139.2.3.1.1.8
-- 1.3.6.1.4.1.2011.6.139.2.3.1.1.8
-- 1.3.6.1.4.1.2011.6.139.2.3.1.1.8
		-- 1.3.6.1.4.1.2011.6.139.2.3.1.1.8
		hwApSampleTime OBJECT-TYPE
			SYNTAX Integer32 (2..300)
			MAX-ACCESS read-write
			STATUS current
			DESCRIPTION
				"Description."
			::= { hwApProfileEntry 8 }

--    1.3.6.1.4.1.2011.6.139.2.3.1.1.9
-- 1.3.6.1.4.1.2011.6.139.2.3.1.1.9
-- 1.3.6.1.4.1.2011.6.139.2.3.1.1.9
		-- 1.3.6.1.4.1.2011.6.139.2.3.1.1.9
		hwApStatisticsInterval OBJECT-TYPE
			SYNTAX Integer32 (60..900)
			MAX-ACCESS read-write
			STATUS current
			DESCRIPTION
				"Description."
			::= { hwApProfileEntry 9 }

--  1.3.6.1.4.1.2011.6.139.2.3.1.1.10
		-- 1.3.6.1.4.1.2011.6.139.2.3.1.1.10
		hwApEapStartMode OBJECT-TYPE
			SYNTAX INTEGER
				{
				broadcast(1),
				multicast(2),
				unicast(3)
				}
			MAX-ACCESS read-create
			STATUS current
			DESCRIPTION
				"Description."
			::= { hwApProfileEntry 10 }

--  1.3.6.1.4.1.2011.6.139.2.3.1.1.11
		-- 1.3.6.1.4.1.2011.6.139.2.3.1.1.11
		hwApEapStartUnicastMac OBJECT-TYPE
			SYNTAX MacAddress
			MAX-ACCESS read-create
			STATUS current
			DESCRIPTION
				"Description."
			::= { hwApProfileEntry 11 }

--  1.3.6.1.4.1.2011.6.139.2.3.1.1.12
		-- 1.3.6.1.4.1.2011.6.139.2.3.1.1.12
		hwApEapStartTransform OBJECT-TYPE
			SYNTAX INTEGER
				{
				specific(1),
				all(2)
				}
			MAX-ACCESS read-create
			STATUS current
			DESCRIPTION
				"Description."
			::= { hwApProfileEntry 12 }

--  1.3.6.1.4.1.2011.6.139.2.3.1.1.13
		-- 1.3.6.1.4.1.2011.6.139.2.3.1.1.13
		hwApEapResponseMode OBJECT-TYPE
			SYNTAX INTEGER
				{
				broadcast(1),
				multicast(2),
				unicastSpecific(3),
				unicastLearning(4)
				}
			MAX-ACCESS read-create
			STATUS current
			DESCRIPTION
				"Description."
			::= { hwApProfileEntry 13 }

--  1.3.6.1.4.1.2011.6.139.2.3.1.1.14
		-- 1.3.6.1.4.1.2011.6.139.2.3.1.1.14
		hwApEapResponseUnicastMac OBJECT-TYPE
			SYNTAX MacAddress
			MAX-ACCESS read-create
			STATUS current
			DESCRIPTION
				"Description."
			::= { hwApProfileEntry 14 }

--  1.3.6.1.4.1.2011.6.139.2.3.1.1.15
		-- 1.3.6.1.4.1.2011.6.139.2.3.1.1.15
		hwApEapResponseTransform OBJECT-TYPE
			SYNTAX INTEGER
				{
				specific(1),
				all(2)
				}
			MAX-ACCESS read-create
			STATUS current
			DESCRIPTION
				"Description."
			::= { hwApProfileEntry 15 }

--  1.3.6.1.4.1.2011.6.139.2.3.1.1.16
		-- 1.3.6.1.4.1.2011.6.139.2.3.1.1.16
		hwApOfflineManagement OBJECT-TYPE
			SYNTAX INTEGER
				{
				disable(1),
				enable(2)
				}
			MAX-ACCESS read-write
			STATUS current
			DESCRIPTION
				"Description."
			::= { hwApProfileEntry 16 }

--  1.3.6.1.4.1.2011.6.139.2.3.1.1.17
		-- 1.3.6.1.4.1.2011.6.139.2.3.1.1.17
		hwApAlarmRestrictionMode OBJECT-TYPE
			SYNTAX INTEGER
				{
				disable(1),
				enable(2)
				}
			MAX-ACCESS read-write
			STATUS current
			DESCRIPTION
				"Description."
			::= { hwApProfileEntry 17 }

--  1.3.6.1.4.1.2011.6.139.2.3.1.1.18
		-- 1.3.6.1.4.1.2011.6.139.2.3.1.1.18
		hwApAlarmRestrictionPeriod OBJECT-TYPE
			SYNTAX Integer32 (10..300)
			MAX-ACCESS read-write
			STATUS current
			DESCRIPTION
				"Description."
			::= { hwApProfileEntry 18 }

--  1.3.6.1.4.1.2011.6.139.2.3.1.1.19
		-- 1.3.6.1.4.1.2011.6.139.2.3.1.1.19
		hwAp4WayHandshakeRoamPolicy OBJECT-TYPE
			SYNTAX INTEGER
				{
				ac(1),
				ap(2)
				}
			MAX-ACCESS read-write
			STATUS current
			DESCRIPTION
				"Not support."
			::= { hwApProfileEntry 19 }

		-- 1.3.6.1.4.1.2011.6.139.2.3.1.1.20
		hwApLogRecordLevel OBJECT-TYPE
			SYNTAX INTEGER
				{
				emergency(1),
				alert(2),
				critical(3),
				error(4),
				warning(5),
				notice(6),
				info(7),
				debug(8)
				}
			MAX-ACCESS read-write
			STATUS current
			DESCRIPTION
				"Description."
			::= { hwApProfileEntry 20 }

--  1.3.6.1.4.1.2011.6.139.2.3.1.1.21
		-- 1.3.6.1.4.1.2011.6.139.2.3.1.1.21
		hwApLogBackupPeriodTime OBJECT-TYPE
			SYNTAX Integer32 (1..24)
			MAX-ACCESS read-write
			STATUS current
			DESCRIPTION
				"Not support."
			::= { hwApProfileEntry 21 }

--  1.3.6.1.4.1.2011.6.139.2.3.1.1.22
		-- 1.3.6.1.4.1.2011.6.139.2.3.1.1.22
		hwApLogRecordFtpMode OBJECT-TYPE
			SYNTAX INTEGER
				{
				disable(1),
				ftp(2),
				sftp(3)
				}
			MAX-ACCESS read-write
			STATUS current
			DESCRIPTION
				"Not support."
			::= { hwApProfileEntry 22 }

--  1.3.6.1.4.1.2011.6.139.2.3.1.1.23
		-- 1.3.6.1.4.1.2011.6.139.2.3.1.1.23
		hwApLogServerUsername OBJECT-TYPE
			SYNTAX OCTET STRING (SIZE (1..32))
			MAX-ACCESS read-write
			STATUS current
			DESCRIPTION
				"Not support."
			::= { hwApProfileEntry 23 }

--  1.3.6.1.4.1.2011.6.139.2.3.1.1.24
		-- 1.3.6.1.4.1.2011.6.139.2.3.1.1.24
		hwApLogServerUserPassword OBJECT-TYPE
			SYNTAX OCTET STRING (SIZE (1..127))
			MAX-ACCESS read-write
			STATUS current
			DESCRIPTION
				"Not support."
			::= { hwApProfileEntry 24 }

--  1.3.6.1.4.1.2011.6.139.2.3.1.1.25
		-- 1.3.6.1.4.1.2011.6.139.2.3.1.1.25
		hwApLogServerIp OBJECT-TYPE
			SYNTAX IpAddress
			MAX-ACCESS read-write
			STATUS current
			DESCRIPTION
				"Not support."
			::= { hwApProfileEntry 25 }

--  1.3.6.1.4.1.2011.6.139.2.3.1.1.26
		-- 1.3.6.1.4.1.2011.6.139.2.3.1.1.26
		hwApProfileTelnetSwitch OBJECT-TYPE
			SYNTAX INTEGER
				{
				disable(1),
				enable(2)
				}
			MAX-ACCESS read-write
			STATUS current
			DESCRIPTION
				"Description."
			::= { hwApProfileEntry 26 }

--  1.3.6.1.4.1.2011.6.139.2.3.1.1.27
		-- 1.3.6.1.4.1.2011.6.139.2.3.1.1.27
		hwApSshSwitch OBJECT-TYPE
			SYNTAX INTEGER
				{
				disable(1),
				enable(2)
				}
			MAX-ACCESS read-write
			STATUS current
			DESCRIPTION
				"Description."
			::= { hwApProfileEntry 27 }

		hwApProfileDhcpTrustPort OBJECT-TYPE
			SYNTAX INTEGER
				{
				disable(1),
				enable(2)
				}
			MAX-ACCESS read-write
			STATUS current
			DESCRIPTION
				"Description."
			::= { hwApProfileEntry 28 }


		-- 1.3.6.1.4.1.2011.6.139.2.3.1.1.29
		hwApProfileConsoleSwitch OBJECT-TYPE
			SYNTAX INTEGER
				{
				disable(1),
				enable(2)
				}
			MAX-ACCESS read-write
			STATUS current
			DESCRIPTION
				"Description."
			::= { hwApProfileEntry 29 }


		-- 1.3.6.1.4.1.2011.6.139.2.3.1.1.30
		hwApProfileMaxUserNum OBJECT-TYPE
			SYNTAX Integer32 (1..256)
			MAX-ACCESS read-create
			STATUS current
			DESCRIPTION
				"Description."
			::= { hwApProfileEntry 30 }


		-- 1.3.6.1.4.1.2011.6.139.2.3.1.1.31
		hwApProfileNdTrustPort OBJECT-TYPE
			SYNTAX INTEGER
				{
				disable(1),
				enable(2)
				}
			MAX-ACCESS read-write
			STATUS current
			DESCRIPTION
				"Description."
			DEFVAL { enable }
			::= { hwApProfileEntry 31 }


		-- 1.3.6.1.4.1.2011.6.139.2.3.1.1.32
		hwApLogBackupServerIpv6Addr OBJECT-TYPE
			SYNTAX OCTET STRING (SIZE (0..46))
			MAX-ACCESS read-write
			STATUS current
			DESCRIPTION
				"Description."
			::= { hwApProfileEntry 32 }

		-- 1.3.6.1.4.1.2011.6.139.2.3.1.1.33
		hwApLedSwitch OBJECT-TYPE
			SYNTAX INTEGER
				{
				off(1),
				on(2)
				}
			MAX-ACCESS read-write
			STATUS current
			DESCRIPTION
				"Description."
			::= { hwApProfileEntry 33 }

		-- 1.3.6.1.4.1.2011.6.139.2.3.1.1.34
		hwApLocalAssocResSwitch OBJECT-TYPE
			SYNTAX INTEGER
				{
				disable(1),
				enable(2)
				}
			MAX-ACCESS read-write
			STATUS current
			DESCRIPTION
				"Description."
			DEFVAL { disable }
			::= { hwApProfileEntry 34 }

--         1.3.6.1.4.1.2011.6.139.2.3.2
-- 1.3.6.1.4.1.2011.6.139.2.3.2
-- 1.3.6.1.4.1.2011.6.139.2.3.2
-- 1.3.6.1.4.1.2011.6.139.2.3.2
-- 1.3.6.1.4.1.2011.6.139.2.3.2
-- 1.3.6.1.4.1.2011.6.139.2.3.2
		-- 1.3.6.1.4.1.2011.6.139.2.3.2
		hwApProfileDefault OBJECT-TYPE
			SYNTAX OCTET STRING
			MAX-ACCESS read-write
			STATUS current
			DESCRIPTION
				"The default profile name. When an AP connect to ac without addition,
				it will be added automatically, and use the default profile."
			::= { hwApProfileObjects 2 }

--    1.3.6.1.4.1.2011.6.139.2.3.3
-- 1.3.6.1.4.1.2011.6.139.2.3.3
-- 1.3.6.1.4.1.2011.6.139.2.3.3
		-- 1.3.6.1.4.1.2011.6.139.2.3.3
		hwApProfileBatchInfo OBJECT IDENTIFIER ::= { hwApProfileObjects 3 }

--    1.3.6.1.4.1.2011.6.139.2.3.3.1
-- 1.3.6.1.4.1.2011.6.139.2.3.3.1
-- 1.3.6.1.4.1.2011.6.139.2.3.3.1
		-- 1.3.6.1.4.1.2011.6.139.2.3.3.1
		hwApProfileBatchStart OBJECT-TYPE
			SYNTAX Integer32
			MAX-ACCESS read-write
			STATUS current
			DESCRIPTION
				"The initiatory AP profile number in batch operation. This node must
				be set in company with the node	hwApProfileBatchNumber. "
			::= { hwApProfileBatchInfo 1 }

--    1.3.6.1.4.1.2011.6.139.2.3.3.2
-- 1.3.6.1.4.1.2011.6.139.2.3.3.2
-- 1.3.6.1.4.1.2011.6.139.2.3.3.2
		-- 1.3.6.1.4.1.2011.6.139.2.3.3.2
		hwApProfileBatchNumber OBJECT-TYPE
			SYNTAX Integer32
			MAX-ACCESS read-write
			STATUS current
			DESCRIPTION
				"The AP profile number in batch operation. This node must be set in
				company with the node hwApProfileBatchStart. "
			::= { hwApProfileBatchInfo 2 }

--    1.3.6.1.4.1.2011.6.139.2.3.3.3
-- 1.3.6.1.4.1.2011.6.139.2.3.3.3
-- 1.3.6.1.4.1.2011.6.139.2.3.3.3
		-- 1.3.6.1.4.1.2011.6.139.2.3.3.3
		hwApProfileBatchReturnNumber OBJECT-TYPE
			SYNTAX Integer32
			MAX-ACCESS read-only
			STATUS current
			DESCRIPTION
				"The actual AP profile number in batch operation. "
			::= { hwApProfileBatchInfo 3 }

--    1.3.6.1.4.1.2011.6.139.2.3.3.4
-- 1.3.6.1.4.1.2011.6.139.2.3.3.4
-- 1.3.6.1.4.1.2011.6.139.2.3.3.4
		-- 1.3.6.1.4.1.2011.6.139.2.3.3.4
		hwApProfileBatchNameList OBJECT-TYPE
			SYNTAX OCTET STRING
			MAX-ACCESS read-only
			STATUS current
			DESCRIPTION
				"The actual AP profile name list in batch operation. Two adjacent
				profile name is divided by '?'. "
			::= { hwApProfileBatchInfo 4 }

--    1.3.6.1.4.1.2011.6.139.2.4
-- 1.3.6.1.4.1.2011.6.139.2.4
-- 1.3.6.1.4.1.2011.6.139.2.4
		-- 1.3.6.1.4.1.2011.6.139.2.4
		hwApAuthListObjects OBJECT IDENTIFIER ::= { hwWlanDevice 4 }

--    1.3.6.1.4.1.2011.6.139.2.4.1
-- 1.3.6.1.4.1.2011.6.139.2.4.1
-- 1.3.6.1.4.1.2011.6.139.2.4.1
		-- 1.3.6.1.4.1.2011.6.139.2.4.1
		hwApMacWhitelistTable OBJECT-TYPE
			SYNTAX SEQUENCE OF HwApMacWhitelistEntry
			MAX-ACCESS not-accessible
			STATUS current
			DESCRIPTION
				"Huawei AP mac address whitelist table. The Index of this table is mac
				address.AP mac address is used to authenticate the AP's validity."
			::= { hwApAuthListObjects 1 }

--    1.3.6.1.4.1.2011.6.139.2.4.1.1
-- 1.3.6.1.4.1.2011.6.139.2.4.1.1
-- 1.3.6.1.4.1.2011.6.139.2.4.1.1
		-- 1.3.6.1.4.1.2011.6.139.2.4.1.1
		hwApMacWhitelistEntry OBJECT-TYPE
			SYNTAX HwApMacWhitelistEntry
			MAX-ACCESS not-accessible
			STATUS current
			DESCRIPTION
				"Huawei AP mac address whitelist table entry. The Index of this table
				is mac address.AP mac address is used to authenticate the AP's validity."
			INDEX { hwApMacWhitelistMacAddr }
			::= { hwApMacWhitelistTable 1 }

		HwApMacWhitelistEntry ::=
			SEQUENCE {
				hwApMacWhitelistMacAddr
					MacAddress,
				hwApMacWhitelistRowStatus
					RowStatus
			 }

--    1.3.6.1.4.1.2011.6.139.2.4.1.1.1
-- 1.3.6.1.4.1.2011.6.139.2.4.1.1.1
-- 1.3.6.1.4.1.2011.6.139.2.4.1.1.1
		-- 1.3.6.1.4.1.2011.6.139.2.4.1.1.1
		hwApMacWhitelistMacAddr OBJECT-TYPE
			SYNTAX MacAddress
			MAX-ACCESS not-accessible
			STATUS current
			DESCRIPTION
				"Ap mac address."
			::= { hwApMacWhitelistEntry 1 }

--    1.3.6.1.4.1.2011.6.139.2.4.1.1.2
-- 1.3.6.1.4.1.2011.6.139.2.4.1.1.2
-- 1.3.6.1.4.1.2011.6.139.2.4.1.1.2
		-- 1.3.6.1.4.1.2011.6.139.2.4.1.1.2
		hwApMacWhitelistRowStatus OBJECT-TYPE
			SYNTAX RowStatus
			MAX-ACCESS read-create
			STATUS current
			DESCRIPTION
				"Row status: mainly to support AP mac whitelist addition and deletion."
			::= { hwApMacWhitelistEntry 2 }

--    1.3.6.1.4.1.2011.6.139.2.4.2
-- 1.3.6.1.4.1.2011.6.139.2.4.2
-- 1.3.6.1.4.1.2011.6.139.2.4.2
		-- 1.3.6.1.4.1.2011.6.139.2.4.2
		hwApSnWhitelistTable OBJECT-TYPE
			SYNTAX SEQUENCE OF HwApSnWhitelistEntry
			MAX-ACCESS not-accessible
			STATUS current
			DESCRIPTION
				"Huawei AP sn whitelist table. The index of this table is AP sn. AP sn
				is used to authenticate the AP's validity."
			::= { hwApAuthListObjects 2 }

--    1.3.6.1.4.1.2011.6.139.2.4.2.1
-- 1.3.6.1.4.1.2011.6.139.2.4.2.1
-- 1.3.6.1.4.1.2011.6.139.2.4.2.1
		-- 1.3.6.1.4.1.2011.6.139.2.4.2.1
		hwApSnWhitelistEntry OBJECT-TYPE
			SYNTAX HwApSnWhitelistEntry
			MAX-ACCESS not-accessible
			STATUS current
			DESCRIPTION
				"Huawei AP sn whitelist table entry.The index of this table is AP sn. AP
				sn is used to authenticate the AP's validity."
			INDEX { hwApSnWhitelistSn }
			::= { hwApSnWhitelistTable 1 }

		HwApSnWhitelistEntry ::=
			SEQUENCE {
				hwApSnWhitelistSn
					OCTET STRING,
				hwApSnWhitelistRowStatus
					RowStatus
			 }

--    1.3.6.1.4.1.2011.6.139.2.4.2.1.1
-- 1.3.6.1.4.1.2011.6.139.2.4.2.1.1
-- 1.3.6.1.4.1.2011.6.139.2.4.2.1.1
		-- 1.3.6.1.4.1.2011.6.139.2.4.2.1.1
		hwApSnWhitelistSn OBJECT-TYPE
			SYNTAX OCTET STRING
			MAX-ACCESS not-accessible
			STATUS current
			DESCRIPTION
				"Ap sn is a string for identifing an AP."
			::= { hwApSnWhitelistEntry 1 }

--    1.3.6.1.4.1.2011.6.139.2.4.2.1.2
-- 1.3.6.1.4.1.2011.6.139.2.4.2.1.2
-- 1.3.6.1.4.1.2011.6.139.2.4.2.1.2
		-- 1.3.6.1.4.1.2011.6.139.2.4.2.1.2
		hwApSnWhitelistRowStatus OBJECT-TYPE
			SYNTAX RowStatus
			MAX-ACCESS read-create
			STATUS current
			DESCRIPTION
				"Row status: mainly to support AP sn whitelist addition and deletion."
			::= { hwApSnWhitelistEntry 2 }

--    1.3.6.1.4.1.2011.6.139.2.4.3
-- 1.3.6.1.4.1.2011.6.139.2.4.3
-- 1.3.6.1.4.1.2011.6.139.2.4.3
		-- 1.3.6.1.4.1.2011.6.139.2.4.3
		hwApAuthMode OBJECT-TYPE
			SYNTAX INTEGER
				{
				macAuth(1),
				snAuth(2),
				noAuth(3)
				}
			MAX-ACCESS read-write
			STATUS current
			DESCRIPTION
				"Ap authentication mode.
				macAuth - AP is authenticated by mac-address.
				snAuth - AP is authenticated by sn.
				noAuth - no authentication. If select this mode, all AP will connect
				to the ac without authentication."
			::= { hwApAuthListObjects 3 }

--    1.3.6.1.4.1.2011.6.139.2.4.4
-- 1.3.6.1.4.1.2011.6.139.2.4.4
-- 1.3.6.1.4.1.2011.6.139.2.4.4
		-- 1.3.6.1.4.1.2011.6.139.2.4.4
		hwApMacWhitelistBatchQueryInfo OBJECT IDENTIFIER ::= { hwApAuthListObjects 4 }

--    1.3.6.1.4.1.2011.6.139.2.4.4.1
-- 1.3.6.1.4.1.2011.6.139.2.4.4.1
-- 1.3.6.1.4.1.2011.6.139.2.4.4.1
		-- 1.3.6.1.4.1.2011.6.139.2.4.4.1
		hwApMacWhitelistBatchQueryStartNumber OBJECT-TYPE
			SYNTAX Integer32
			MAX-ACCESS read-write
			STATUS current
			DESCRIPTION
				"The start valid number of AP mac whitelist when get AP mac whitelist
				in batch. Begin with 0, must less than the specification of whitelist."
			::= { hwApMacWhitelistBatchQueryInfo 1 }

--    1.3.6.1.4.1.2011.6.139.2.4.4.2
-- 1.3.6.1.4.1.2011.6.139.2.4.4.2
-- 1.3.6.1.4.1.2011.6.139.2.4.4.2
		-- 1.3.6.1.4.1.2011.6.139.2.4.4.2
		hwApMacWhitelistBatchQueryNumber OBJECT-TYPE
			SYNTAX Integer32
			MAX-ACCESS read-write
			STATUS current
			DESCRIPTION
				"The query number of AP mac whitelist when query AP mac whitelist in
				batch. The query number must less than or equal the specification of
				mac whitelist."
			::= { hwApMacWhitelistBatchQueryInfo 2 }

--    1.3.6.1.4.1.2011.6.139.2.4.4.3
-- 1.3.6.1.4.1.2011.6.139.2.4.4.3
-- 1.3.6.1.4.1.2011.6.139.2.4.4.3
		-- 1.3.6.1.4.1.2011.6.139.2.4.4.3
		hwApMacWhitelistBatchQueryList OBJECT-TYPE
			SYNTAX OCTET STRING (SIZE (0..768))
			MAX-ACCESS read-only
			STATUS current
			DESCRIPTION
				"The returned AP mac whitelist list when query AP mac whitelist in
				batch. The mac is storaged in the list one by one,and no separator.
				For example, if the start number is 10, and the query number is
				50, then the host will find 50 valid mac whitelists from the 11th
				valid mac whitelist.(Assume there are 100 mac whitelists in host.)
				And each time the SNMP agent can get 128 mac whitelist at most."
			::= { hwApMacWhitelistBatchQueryInfo 3 }

--    1.3.6.1.4.1.2011.6.139.2.4.4.4
-- 1.3.6.1.4.1.2011.6.139.2.4.4.4
-- 1.3.6.1.4.1.2011.6.139.2.4.4.4
		-- 1.3.6.1.4.1.2011.6.139.2.4.4.4
		hwApMacWhitelistBatchQueryReturnNumber OBJECT-TYPE
			SYNTAX Integer32
			MAX-ACCESS read-only
			STATUS current
			DESCRIPTION
				"The actual mac number of returned AP mac whitelist list when query
				AP mac whitelist in batch. "
			::= { hwApMacWhitelistBatchQueryInfo 4 }

--    1.3.6.1.4.1.2011.6.139.2.4.5
-- 1.3.6.1.4.1.2011.6.139.2.4.5
-- 1.3.6.1.4.1.2011.6.139.2.4.5
		-- 1.3.6.1.4.1.2011.6.139.2.4.5
		hwApSnWhitelistBatchQueryInfo OBJECT IDENTIFIER ::= { hwApAuthListObjects 5 }

--    1.3.6.1.4.1.2011.6.139.2.4.5.1
-- 1.3.6.1.4.1.2011.6.139.2.4.5.1
-- 1.3.6.1.4.1.2011.6.139.2.4.5.1
		-- 1.3.6.1.4.1.2011.6.139.2.4.5.1
		hwApSnWhitelistBatchQueryStartNumber OBJECT-TYPE
			SYNTAX Integer32
			MAX-ACCESS read-write
			STATUS current
			DESCRIPTION
				"The start valid number of AP sn whitelist when get AP sn whitelist
				in batch. Begin with 0, must less than the specification of white-
				list."
			::= { hwApSnWhitelistBatchQueryInfo 1 }

--    1.3.6.1.4.1.2011.6.139.2.4.5.2
-- 1.3.6.1.4.1.2011.6.139.2.4.5.2
-- 1.3.6.1.4.1.2011.6.139.2.4.5.2
		-- 1.3.6.1.4.1.2011.6.139.2.4.5.2
		hwApSnWhitelistBatchQueryNumber OBJECT-TYPE
			SYNTAX Integer32
			MAX-ACCESS read-write
			STATUS current
			DESCRIPTION
				"The query number of AP sn whitelist when query AP sn whitelist in
				batch. The query number must less than or equal the specification
				of whitelist."
			::= { hwApSnWhitelistBatchQueryInfo 2 }

--    1.3.6.1.4.1.2011.6.139.2.4.5.3
-- 1.3.6.1.4.1.2011.6.139.2.4.5.3
-- 1.3.6.1.4.1.2011.6.139.2.4.5.3
		-- 1.3.6.1.4.1.2011.6.139.2.4.5.3
		hwApSnWhitelistBatchQueryList OBJECT-TYPE
			SYNTAX OCTET STRING (SIZE (0..8192))
			MAX-ACCESS read-only
			STATUS current
			DESCRIPTION
				"The returned AP sn whitelist list when query AP sn whitelist in
				batch. Two adjacent sn whitelist in the list are divided by '?'.
				   For example, if the start number is 10, and the query number is
				50, then the host will find 50 valid sn whitelists from the 11th
				valid sn whitelist.(Assume there are 100 sn whitelists in host.)
				And each time the SNMP agent can get 128 sn whitelist at most."
			::= { hwApSnWhitelistBatchQueryInfo 3 }

--    1.3.6.1.4.1.2011.6.139.2.4.5.4
-- 1.3.6.1.4.1.2011.6.139.2.4.5.4
-- 1.3.6.1.4.1.2011.6.139.2.4.5.4
		-- 1.3.6.1.4.1.2011.6.139.2.4.5.4
		hwApSnWhitelistBatchQueryReturnNumber OBJECT-TYPE
			SYNTAX Integer32
			MAX-ACCESS read-only
			STATUS current
			DESCRIPTION
				"The actual number of returned AP sn whitelist list when query AP
				sn whitelist in batch."
			::= { hwApSnWhitelistBatchQueryInfo 4 }

--    1.3.6.1.4.1.2011.6.139.2.4.6
-- 1.3.6.1.4.1.2011.6.139.2.4.6
-- 1.3.6.1.4.1.2011.6.139.2.4.6
		-- 1.3.6.1.4.1.2011.6.139.2.4.6
		hwApMacBlacklistTable OBJECT-TYPE
			SYNTAX SEQUENCE OF HwApMacBlacklistEntry
			MAX-ACCESS not-accessible
			STATUS current
			DESCRIPTION
				"Huawei AP mac address blacklist table. The Index of this table is mac
				address.AP mac address is used to authenticate the AP's validity."
			::= { hwApAuthListObjects 6 }

--    1.3.6.1.4.1.2011.6.139.2.4.6.1
-- 1.3.6.1.4.1.2011.6.139.2.4.6.1
-- 1.3.6.1.4.1.2011.6.139.2.4.6.1
		-- 1.3.6.1.4.1.2011.6.139.2.4.6.1
		hwApMacBlacklistEntry OBJECT-TYPE
			SYNTAX HwApMacBlacklistEntry
			MAX-ACCESS not-accessible
			STATUS current
			DESCRIPTION
				"Huawei AP mac address blacklist table entry. The Index of this table
				is mac address.AP mac address is used to authenticate the AP's validity."
			INDEX { hwApMacBlacklistMacAddr }
			::= { hwApMacBlacklistTable 1 }

		HwApMacBlacklistEntry ::=
			SEQUENCE {
				hwApMacBlacklistMacAddr
					MacAddress,
				hwApMacBlacklistRowStatus
					RowStatus
			 }

--    1.3.6.1.4.1.2011.6.139.2.4.6.1.1
-- 1.3.6.1.4.1.2011.6.139.2.4.6.1.1
-- 1.3.6.1.4.1.2011.6.139.2.4.6.1.1
		-- 1.3.6.1.4.1.2011.6.139.2.4.6.1.1
		hwApMacBlacklistMacAddr OBJECT-TYPE
			SYNTAX MacAddress
			MAX-ACCESS not-accessible
			STATUS current
			DESCRIPTION
				"Ap mac address."
			::= { hwApMacBlacklistEntry 1 }

--    1.3.6.1.4.1.2011.6.139.2.4.6.1.2
-- 1.3.6.1.4.1.2011.6.139.2.4.6.1.2
-- 1.3.6.1.4.1.2011.6.139.2.4.6.1.2
		-- 1.3.6.1.4.1.2011.6.139.2.4.6.1.2
		hwApMacBlacklistRowStatus OBJECT-TYPE
			SYNTAX RowStatus
			MAX-ACCESS read-create
			STATUS current
			DESCRIPTION
				"Row status: mainly to support AP mac blacklist addition and deletion."
			::= { hwApMacBlacklistEntry 2 }

--    1.3.6.1.4.1.2011.6.139.2.4.7
-- 1.3.6.1.4.1.2011.6.139.2.4.7
-- 1.3.6.1.4.1.2011.6.139.2.4.7
		-- 1.3.6.1.4.1.2011.6.139.2.4.7
		hwApSnBlacklistTable OBJECT-TYPE
			SYNTAX SEQUENCE OF HwApSnBlacklistEntry
			MAX-ACCESS not-accessible
			STATUS current
			DESCRIPTION
				"Huawei AP sn blacklist table. The index of this table is AP sn. AP sn
				is used to authenticate the AP's validity."
			::= { hwApAuthListObjects 7 }

--    1.3.6.1.4.1.2011.6.139.2.4.7.1
-- 1.3.6.1.4.1.2011.6.139.2.4.7.1
-- 1.3.6.1.4.1.2011.6.139.2.4.7.1
		-- 1.3.6.1.4.1.2011.6.139.2.4.7.1
		hwApSnBlacklistEntry OBJECT-TYPE
			SYNTAX HwApSnBlacklistEntry
			MAX-ACCESS not-accessible
			STATUS current
			DESCRIPTION
				"Huawei AP sn blacklist table entry.The index of this table is AP sn. AP
				sn is used to authenticate the AP's validity."
			INDEX { hwApSnBlacklistSn }
			::= { hwApSnBlacklistTable 1 }

		HwApSnBlacklistEntry ::=
			SEQUENCE {
				hwApSnBlacklistSn
					OCTET STRING,
				hwApSnBlacklistRowStatus
					RowStatus
			 }

--    1.3.6.1.4.1.2011.6.139.2.4.7.1.1
-- 1.3.6.1.4.1.2011.6.139.2.4.7.1.1
-- 1.3.6.1.4.1.2011.6.139.2.4.7.1.1
		-- 1.3.6.1.4.1.2011.6.139.2.4.7.1.1
		hwApSnBlacklistSn OBJECT-TYPE
			SYNTAX OCTET STRING
			MAX-ACCESS not-accessible
			STATUS current
			DESCRIPTION
				"Ap sn is a string for identifing an AP."
			::= { hwApSnBlacklistEntry 1 }

--    1.3.6.1.4.1.2011.6.139.2.4.7.1.2
-- 1.3.6.1.4.1.2011.6.139.2.4.7.1.2
-- 1.3.6.1.4.1.2011.6.139.2.4.7.1.2
		-- 1.3.6.1.4.1.2011.6.139.2.4.7.1.2
		hwApSnBlacklistRowStatus OBJECT-TYPE
			SYNTAX RowStatus
			MAX-ACCESS read-create
			STATUS current
			DESCRIPTION
				"Row status: mainly to support AP sn blacklist addition and deletion."
			::= { hwApSnBlacklistEntry 2 }

--    1.3.6.1.4.1.2011.6.139.2.5
-- 1.3.6.1.4.1.2011.6.139.2.5
-- 1.3.6.1.4.1.2011.6.139.2.5
		-- 1.3.6.1.4.1.2011.6.139.2.5
		hwApRegionObjects OBJECT IDENTIFIER ::= { hwWlanDevice 5 }

--    1.3.6.1.4.1.2011.6.139.2.5.1
-- 1.3.6.1.4.1.2011.6.139.2.5.1
-- 1.3.6.1.4.1.2011.6.139.2.5.1
		-- 1.3.6.1.4.1.2011.6.139.2.5.1
		hwApRegionTable OBJECT-TYPE
			SYNTAX SEQUENCE OF HwApRegionEntry
			MAX-ACCESS not-accessible
			STATUS current
			DESCRIPTION
				"Huawei AP region table. The index of this table is AP region ID. AP
				region is an aggregate of a lot of APs with the same position. Such
				as, all the APs in a building can be compartmentalized into one same
				region."
			::= { hwApRegionObjects 1 }

--    1.3.6.1.4.1.2011.6.139.2.5.1.1
-- 1.3.6.1.4.1.2011.6.139.2.5.1.1
-- 1.3.6.1.4.1.2011.6.139.2.5.1.1
		-- 1.3.6.1.4.1.2011.6.139.2.5.1.1
		hwApRegionEntry OBJECT-TYPE
			SYNTAX HwApRegionEntry
			MAX-ACCESS not-accessible
			STATUS current
			DESCRIPTION
				"Huawei AP region table entry.The index of this table is AP region ID.
				AP region is an aggregate of a lot of APs with the same position. Such
				as, all the APs in a building can be compartmentalized into one same
				region."
			INDEX { hwApRegionIndex }
			::= { hwApRegionTable 1 }

		HwApRegionEntry ::=
			SEQUENCE {
				hwApRegionIndex
					Integer32,
				hwApRegionName
					OCTET STRING,
				hwApRegionDeployMode
					INTEGER,
				hwApRegionApNumber
					Integer32,
				hwApRegionApIndexMask
					OCTET STRING,
				hwApRegionRowStatus
					RowStatus,
				hwApRegionForwardMode
					INTEGER,
				hwApRegionCountryCode
					OCTET STRING,
				hwApRegionScanChannel2G
					OCTET STRING,
				hwApRegionScanChannel5G
					OCTET STRING,
				hwApRegionCalibrateChannel2G
					OCTET STRING,
				hwApRegionCalibrateChannel5G
					OCTET STRING,
				hwApRegionCalibrate5gBandWidth
					INTEGER
			 }

--    1.3.6.1.4.1.2011.6.139.2.5.1.1.1
-- 1.3.6.1.4.1.2011.6.139.2.5.1.1.1
-- 1.3.6.1.4.1.2011.6.139.2.5.1.1.1
		-- 1.3.6.1.4.1.2011.6.139.2.5.1.1.1
		hwApRegionIndex OBJECT-TYPE
			SYNTAX Integer32
			MAX-ACCESS not-accessible
			STATUS current
			DESCRIPTION
				"Ap region index."
			::= { hwApRegionEntry 1 }

--    1.3.6.1.4.1.2011.6.139.2.5.1.1.2
-- 1.3.6.1.4.1.2011.6.139.2.5.1.1.2
-- 1.3.6.1.4.1.2011.6.139.2.5.1.1.2
		-- 1.3.6.1.4.1.2011.6.139.2.5.1.1.2
		hwApRegionName OBJECT-TYPE
			SYNTAX OCTET STRING
			MAX-ACCESS read-create
			STATUS current
			DESCRIPTION
				"The description of the AP region."
			::= { hwApRegionEntry 2 }

--    1.3.6.1.4.1.2011.6.139.2.5.1.1.3
-- 1.3.6.1.4.1.2011.6.139.2.5.1.1.3
-- 1.3.6.1.4.1.2011.6.139.2.5.1.1.3
		-- 1.3.6.1.4.1.2011.6.139.2.5.1.1.3
		hwApRegionDeployMode OBJECT-TYPE
			SYNTAX INTEGER
				{
				discreteDeploy(1),
				normalDeploy(2),
				denselyDeploy(3)
				}
			MAX-ACCESS read-create
			STATUS current
			DESCRIPTION
				"The AP's deploy mode in an AP region.
				discreteDeploy - all the APs in the region is deployed discretely. There
				    is no disturbance between APs. Every AP works at the maximum power.
				normalDeploy - APs in the region is deployed sparsely. Ap works at 50%
				    of the maximum power at least.
				discreteDeploy - APs in the region is deployed densely. Ap works at 25%
				    of the maximum power at least."
			::= { hwApRegionEntry 3 }

--    1.3.6.1.4.1.2011.6.139.2.5.1.1.4
-- 1.3.6.1.4.1.2011.6.139.2.5.1.1.4
-- 1.3.6.1.4.1.2011.6.139.2.5.1.1.4
		-- 1.3.6.1.4.1.2011.6.139.2.5.1.1.4
		hwApRegionApNumber OBJECT-TYPE
			SYNTAX Integer32
			MAX-ACCESS read-only
			STATUS current
			DESCRIPTION
				"Ap number in AP region."
			::= { hwApRegionEntry 4 }

--    1.3.6.1.4.1.2011.6.139.2.5.1.1.5
-- 1.3.6.1.4.1.2011.6.139.2.5.1.1.5
-- 1.3.6.1.4.1.2011.6.139.2.5.1.1.5
		-- 1.3.6.1.4.1.2011.6.139.2.5.1.1.5
		hwApRegionApIndexMask OBJECT-TYPE
			SYNTAX OCTET STRING
			MAX-ACCESS read-only
			STATUS current
			DESCRIPTION
				"All APs's index mask in an AP region.
				Every bit is used to describe an AP is in this region or not. 0 means
				AP is not in this region, and 1 means AP is in this region.The value
				of this node is hexadecimal integer block.
				Each Byte describes 8 APs are in this region or not.
				For example, the first Byte describes AP 0~7 is in this region or not,
				and the second Byte describes AP 8~15 is in this region or not.
				Such as, if only AP 0,4,5,6,7,9 is in this region, the binary number
				is 11110001 and 00000010,the hexadecimal number is 0xF1 and 0x2, so
				the first Byte of this node	is 0xF1,and the second Byte is 0x2."
			::= { hwApRegionEntry 5 }

--    1.3.6.1.4.1.2011.6.139.2.5.1.1.6
-- 1.3.6.1.4.1.2011.6.139.2.5.1.1.6
-- 1.3.6.1.4.1.2011.6.139.2.5.1.1.6
		-- 1.3.6.1.4.1.2011.6.139.2.5.1.1.6
		hwApRegionRowStatus OBJECT-TYPE
			SYNTAX RowStatus
			MAX-ACCESS read-create
			STATUS current
			DESCRIPTION
				"Row status: mainly to support AP region addition and deletion."
			::= { hwApRegionEntry 6 }

--    1.3.6.1.4.1.2011.6.139.2.5.1.1.7
-- 1.3.6.1.4.1.2011.6.139.2.5.1.1.7
-- 1.3.6.1.4.1.2011.6.139.2.5.1.1.7
		-- 1.3.6.1.4.1.2011.6.139.2.5.1.1.7
		hwApRegionForwardMode OBJECT-TYPE
			SYNTAX INTEGER
				{
				directForward(1),
				tunnel(2),
				unknown(-1)
				}
			MAX-ACCESS read-write
			STATUS current
			DESCRIPTION
				"The Ap region based forward mode."
			::= { hwApRegionEntry 7 }

--  1.3.6.1.4.1.2011.6.139.2.5.1.1.8
		-- 1.3.6.1.4.1.2011.6.139.2.5.1.1.8
		hwApRegionCountryCode OBJECT-TYPE
			SYNTAX OCTET STRING
			MAX-ACCESS read-write
			STATUS current
			DESCRIPTION
				"Description."
			::= { hwApRegionEntry 8 }

		-- 1.3.6.1.4.1.2011.6.139.2.5.1.1.9
		hwApRegionScanChannel2G OBJECT-TYPE
			SYNTAX OCTET STRING
			MAX-ACCESS read-write
			STATUS current
			DESCRIPTION
				"Description."
			::= { hwApRegionEntry 9 }


		-- 1.3.6.1.4.1.2011.6.139.2.5.1.1.10
		hwApRegionScanChannel5G OBJECT-TYPE
			SYNTAX OCTET STRING
			MAX-ACCESS read-write
			STATUS current
			DESCRIPTION
				"Description."
			::= { hwApRegionEntry 10 }


		-- 1.3.6.1.4.1.2011.6.139.2.5.1.1.11
		hwApRegionCalibrateChannel2G OBJECT-TYPE
			SYNTAX OCTET STRING
			MAX-ACCESS read-write
			STATUS current
			DESCRIPTION
				"Description."
			::= { hwApRegionEntry 11 }


		-- 1.3.6.1.4.1.2011.6.139.2.5.1.1.12
		hwApRegionCalibrateChannel5G OBJECT-TYPE
			SYNTAX OCTET STRING
			MAX-ACCESS read-write
			STATUS current
			DESCRIPTION
				"Description."
			::= { hwApRegionEntry 12 }


		-- 1.3.6.1.4.1.2011.6.139.2.5.1.1.13
		hwApRegionCalibrate5gBandWidth OBJECT-TYPE
			SYNTAX INTEGER
				{
				ht20(1),
				ht40(2),
				ht80(3),
				unknown(0)
				}
			MAX-ACCESS read-write
			STATUS current
			DESCRIPTION
				"Ap region calibrate 5G band width."
			DEFVAL { 1 }
			::= { hwApRegionEntry 13 }
--    1.3.6.1.4.1.2011.6.139.2.5.2
-- 1.3.6.1.4.1.2011.6.139.2.5.2
-- 1.3.6.1.4.1.2011.6.139.2.5.2
		-- 1.3.6.1.4.1.2011.6.139.2.5.2
		hwApRegionGlobalInfo OBJECT IDENTIFIER ::= { hwApRegionObjects 2 }

--    1.3.6.1.4.1.2011.6.139.2.5.2.1
-- 1.3.6.1.4.1.2011.6.139.2.5.2.1
-- 1.3.6.1.4.1.2011.6.139.2.5.2.1
		-- 1.3.6.1.4.1.2011.6.139.2.5.2.1
		hwApRegionDefault OBJECT-TYPE
			SYNTAX Integer32
			MAX-ACCESS read-write
			STATUS current
			DESCRIPTION
				"The default region index. When an AP connect to ac without addition,
				it will be added automatically, and join the default region."
			::= { hwApRegionGlobalInfo 1 }

--    1.3.6.1.4.1.2011.6.139.2.5.2.2
-- 1.3.6.1.4.1.2011.6.139.2.5.2.2
-- 1.3.6.1.4.1.2011.6.139.2.5.2.2
		-- 1.3.6.1.4.1.2011.6.139.2.5.2.2
		hwApRegionAllExistRegionIndexMask OBJECT-TYPE
			SYNTAX OCTET STRING
			MAX-ACCESS read-only
			STATUS current
			DESCRIPTION
				"All the existent regions' index mask.
				Every bit is used to describe the region is existent or not.
				0 means region is not existent, and 1 means region is existent.
				The value of this node is hexadecimal integer block.
				Each Byte describes 8 APs are existent or not.
				For example, the first Byte describes AP 0~7 is existent or not,
				and the second Byte describes AP 8~15 is existent or not.
				Such as, if only AP 0,4,5,6,7,9 is existent, the binary number is
				11110001 and 00000010,the hexadecimal number is 0xF1 and 0x2, so the
				first Byte of this node is 0xF1,and the second Byte is 0x2."
			::= { hwApRegionGlobalInfo 2 }

--    1.3.6.1.4.1.2011.6.139.2.5.2.3
-- 1.3.6.1.4.1.2011.6.139.2.5.2.3
-- 1.3.6.1.4.1.2011.6.139.2.5.2.3
		-- 1.3.6.1.4.1.2011.6.139.2.5.2.3
		hwApRegionBatchInfo OBJECT IDENTIFIER ::= { hwApRegionGlobalInfo 3 }

--    1.3.6.1.4.1.2011.6.139.2.5.2.3.1
-- 1.3.6.1.4.1.2011.6.139.2.5.2.3.1
-- 1.3.6.1.4.1.2011.6.139.2.5.2.3.1
		-- 1.3.6.1.4.1.2011.6.139.2.5.2.3.1
		hwApRegionBatchStart OBJECT-TYPE
			SYNTAX Integer32
			MAX-ACCESS read-write
			STATUS current
			DESCRIPTION
				"The initiatory AP region number in batch operation. This node must
				be set in company with the node	hwApRegionBatchNumber. "
			::= { hwApRegionBatchInfo 1 }

--    1.3.6.1.4.1.2011.6.139.2.5.2.3.2
-- 1.3.6.1.4.1.2011.6.139.2.5.2.3.2
-- 1.3.6.1.4.1.2011.6.139.2.5.2.3.2
		-- 1.3.6.1.4.1.2011.6.139.2.5.2.3.2
		hwApRegionBatchNumber OBJECT-TYPE
			SYNTAX Integer32
			MAX-ACCESS read-write
			STATUS current
			DESCRIPTION
				"The AP region number in batch operation. This node must be set in
				company with the node hwApRegionBatchStart. "
			::= { hwApRegionBatchInfo 2 }

--    1.3.6.1.4.1.2011.6.139.2.5.2.3.3
-- 1.3.6.1.4.1.2011.6.139.2.5.2.3.3
-- 1.3.6.1.4.1.2011.6.139.2.5.2.3.3
		-- 1.3.6.1.4.1.2011.6.139.2.5.2.3.3
		hwApRegionBatchReturnNumber OBJECT-TYPE
			SYNTAX Integer32
			MAX-ACCESS read-only
			STATUS current
			DESCRIPTION
				"The actual AP region number in batch operation. "
			::= { hwApRegionBatchInfo 3 }

--    1.3.6.1.4.1.2011.6.139.2.5.2.3.4
-- 1.3.6.1.4.1.2011.6.139.2.5.2.3.4
-- 1.3.6.1.4.1.2011.6.139.2.5.2.3.4
		-- 1.3.6.1.4.1.2011.6.139.2.5.2.3.4
		hwApRegionBatchNameList OBJECT-TYPE
			SYNTAX OCTET STRING
			MAX-ACCESS read-only
			STATUS current
			DESCRIPTION
				"The actual AP region names in batch operation. Each profile name
				is divided by '?'. "
			::= { hwApRegionBatchInfo 4 }

--    1.3.6.1.4.1.2011.6.139.2.5.2.3.5
-- 1.3.6.1.4.1.2011.6.139.2.5.2.3.5
-- 1.3.6.1.4.1.2011.6.139.2.5.2.3.5
		-- 1.3.6.1.4.1.2011.6.139.2.5.2.3.5
		hwApRegionBatchDeployMode OBJECT-TYPE
			SYNTAX OCTET STRING
			MAX-ACCESS read-only
			STATUS current
			DESCRIPTION
				"The deploy mode of AP regions in batch operation. The value of this
				node is hexadecimal integer block.Each region's deploy mode occupies
				a Byte.
				For example, if the first operated region's deploy mode is 15,
				and the sencond operated region's deploy mode is 14, so the first Byte
				of this node is 0xF,and the second Byte is 0xE."
			::= { hwApRegionBatchInfo 5 }

--    1.3.6.1.4.1.2011.6.139.2.5.3
-- 1.3.6.1.4.1.2011.6.139.2.5.3
-- 1.3.6.1.4.1.2011.6.139.2.5.3
		-- 1.3.6.1.4.1.2011.6.139.2.5.3
		hwApRegionMerge OBJECT IDENTIFIER ::= { hwApRegionObjects 3 }

--    1.3.6.1.4.1.2011.6.139.2.5.3.1
-- 1.3.6.1.4.1.2011.6.139.2.5.3.1
-- 1.3.6.1.4.1.2011.6.139.2.5.3.1
		-- 1.3.6.1.4.1.2011.6.139.2.5.3.1
		hwApSrcRegionIndex OBJECT-TYPE
			SYNTAX Integer32
			MAX-ACCESS read-write
			STATUS current
			DESCRIPTION
				"The source region index in a merge operation. When a merge operation
				has been done, all the APs in the source region will join the desti-
				nation region,and the source region will become a empty region."
			::= { hwApRegionMerge 1 }

--    1.3.6.1.4.1.2011.6.139.2.5.3.2
-- 1.3.6.1.4.1.2011.6.139.2.5.3.2
-- 1.3.6.1.4.1.2011.6.139.2.5.3.2
		-- 1.3.6.1.4.1.2011.6.139.2.5.3.2
		hwApDestRegionIndex OBJECT-TYPE
			SYNTAX Integer32
			MAX-ACCESS read-write
			STATUS current
			DESCRIPTION
				"The destination region index in a merge operation."
			::= { hwApRegionMerge 2 }

--    1.3.6.1.4.1.2011.6.139.2.6
-- 1.3.6.1.4.1.2011.6.139.2.6
-- 1.3.6.1.4.1.2011.6.139.2.6
		-- 1.3.6.1.4.1.2011.6.139.2.6
		hwApObjects OBJECT IDENTIFIER ::= { hwWlanDevice 6 }

--    1.3.6.1.4.1.2011.6.139.2.6.1
-- 1.3.6.1.4.1.2011.6.139.2.6.1
-- 1.3.6.1.4.1.2011.6.139.2.6.1
		-- 1.3.6.1.4.1.2011.6.139.2.6.1
		hwApTable OBJECT-TYPE
			SYNTAX SEQUENCE OF HwApEntry
			MAX-ACCESS not-accessible
			STATUS current
			DESCRIPTION
				"Huawei AP table. The index of this table is AP ID. The AP table des-
				cribes detailed information of all APs,including the AP's type, the run
				state of the AP, the software of the AP, the hardware version No., etc.
				When add an AP, AP type must be filled in. If current Ap authentication
				mode is MAC or SN, the MAC or SN of AP must be filled in. If current Ap
				authentication mode is noauth, one of the MAC or SN of AP must be filled
				in."
			::= { hwApObjects 1 }

--    1.3.6.1.4.1.2011.6.139.2.6.1.1
-- 1.3.6.1.4.1.2011.6.139.2.6.1.1
-- 1.3.6.1.4.1.2011.6.139.2.6.1.1
		-- 1.3.6.1.4.1.2011.6.139.2.6.1.1
		hwApEntry OBJECT-TYPE
			SYNTAX HwApEntry
			MAX-ACCESS not-accessible
			STATUS current
			DESCRIPTION
				"Huawei AP table entry. The index of this table is AP ID. The AP table
				describes detailed information of all APs,including the AP's type, the
				run state of the AP, the software of the AP, the hardware version No.,etc.
				When add an AP, AP type must be filled in. If current Ap authentication
				mode is MAC or SN, the MAC or SN of AP must be filled in. If current Ap
				authentication mode is noauth, one of the MAC or SN of AP must be filled
				in."
			INDEX { hwApIndex }
			::= { hwApTable 1 }

		HwApEntry ::=
			SEQUENCE {
				hwApIndex
					Integer32,
				hwApUsedType
					OCTET STRING,
				hwApUsedProfileName
					OCTET STRING,
				hwApUsedRegionIndex
					Integer32,
				hwApMac
					MacAddress,
				hwApSn
					OCTET STRING,
				hwApSysName
					OCTET STRING,
				hwApRunState
					INTEGER,
				hwApSoftwareVersion
					OCTET STRING,
				hwApHardwareVersion
					OCTET STRING,
				hwApCpuType
					OCTET STRING,
				hwApCpufrequency
					Integer32,
				hwApMemoryType
					OCTET STRING,
				hwApDomain
					OCTET STRING,
				hwApIpAddress
					IpAddress,
				hwApIpNetMask
					IpAddress,
				hwApGatewayIp
					IpAddress,
				hwApMemorySize
					Integer32,
				hwApFlashSize
					Integer32,
				hwApRunTime
					Unsigned32,
				hwApUpEthPortSpeed
					INTEGER,
				hwApUpEthPortSpeedMode
					INTEGER,
				hwApUpEthPortDuplex
					INTEGER,
				hwApUpEthPortDuplexMode
					INTEGER,
				hwApAdminOper
					INTEGER,
				hwApRowstatus
					RowStatus,
				hwApPerformanceStatCycle
					INTEGER,
				hwApDNS
					IpAddress,
				hwApRunningMode
					INTEGER,
				hwApForwardMode
					INTEGER,
				hwApAntennaMode
					INTEGER,
				hwApCpuThreshold
					Integer32,
				hwApMemThreshold
					Integer32,
				hwApNEnumber
					OCTET STRING,
				hwApOnlineTime
					Unsigned32,
				hwApSysSoftwareDesc
					OCTET STRING,
				hwApSysHardtwareDesc
					OCTET STRING,
				hwApSysManufacture
					OCTET STRING,
				hwApSysSoftwareName
					OCTET STRING,
				hwApSysSoftwareVendor
					OCTET STRING,
				hwApManagementVlanID
					Integer32,
				hwApUsername
					OCTET STRING,
				hwApPassword
					OCTET STRING,
				hwApAcIP1
					IpAddress,
				hwApAcIP2
					IpAddress,
				hwApAcIP3
					IpAddress,
				hwApAcIP4
					IpAddress,
				hwApIpMode
					INTEGER,
				hwApLldpEnable
					INTEGER,
				hwApLldpManageAddr
					INTEGER,
				hwApLldpPortDes
					INTEGER,
				hwApLldpSysCab
					INTEGER,
				hwApLldpSysDes
					INTEGER,
				hwApLldpSysName
					INTEGER,
				hwApLldpDelay
					Integer32,
				hwApLldpHoldMultiplier
					Integer32,
				hwApLldpInterval
					Integer32,
				hwApLldpRestartDelay
					Integer32,
				hwApLldpAdminStatus
					INTEGER,
				hwApLldpReportInterval
					Integer32,
				hwApBomCode
					OCTET STRING,
				hwApSaveMode
					Integer32,
				hwApProtectAcPriority
					Integer32,
				hwApProtectAcIP
					IpAddress,
				hwApOpticalHighRxPowerThreshold
					Integer32,
				hwApOpticalLowRxPowerThreshold
					Integer32,
				hwApOpticalHighTemperatureThreshold
					Integer32,
				hwApOpticalLowTemperatureThreshold
					Integer32,
				hwApKeepService
					INTEGER,
				hwApPriorityAccessMode
					Integer32,
				hwApLineateportMode
					INTEGER,
				hwApLineateportVlanTagged
					OCTET STRING,
				hwApLineateportVlanUntagged
					OCTET STRING,
				hwApLineateportPvidVlan
					Integer32,
				hwApLineateportUserIsolate
					INTEGER,
				hwApLineateportStpEnable
					INTEGER,
				hwApHighTemperatureThreshold
					Integer32,
				hwApLowTemperatureThreshold
					Integer32,
				hwApReset
					Integer32,
				hwApStaticIpAddress
					IpAddress,
				hwApStaticNetMask
					IpAddress,
				hwApStaticGatewayIp
					IpAddress,
				hwApAttackFloodInterval
					Integer32,
				hwApAttackFloodTimes
					Integer32,
				hwApDynamicBlacklistEnable
					Integer32,
				hwApDynamicBlacklistAgingInt
					Integer32,
				hwApAttackPskInterval
					Integer32,
				hwApAttackPskTimes
					Integer32,
				hwApAccessBalanceGap
					Integer32,
				hwApIpv6Address
					OCTET STRING,
				hwApIpv6NetMask
					OCTET STRING,
				hwApGatewayIpv6
					OCTET STRING,
				hwApIpv6DNS
					OCTET STRING,
				hwApProtectAcIPv6Addr
					OCTET STRING,
				hwApLineatePortCfgMtu
					Integer32,
				hwApLineatePortMacAddress
					MacAddress,
				hwApAccessBalanceSwitch
					INTEGER,
				hwApNatIpAddress
					OCTET STRING,
				hwApAttackFloodQuietTime
					Integer32,
				hwApAttackPskQuietTime
					Integer32,
				hwApAttackWeakivQuietTime
					Integer32,
				hwApAttackSpoofQuietTime
					Integer32,
				hwApBootCountTotal
					Integer32,
				hwApBootCountPowerOff
					Integer32,
				hwApBootCountRowStatus
					RowStatus
			 }

--    1.3.6.1.4.1.2011.6.139.2.6.1.1.1
-- 1.3.6.1.4.1.2011.6.139.2.6.1.1.1
-- 1.3.6.1.4.1.2011.6.139.2.6.1.1.1
		-- 1.3.6.1.4.1.2011.6.139.2.6.1.1.1
		hwApIndex OBJECT-TYPE
			SYNTAX Integer32
			MAX-ACCESS accessible-for-notify
			STATUS current
			DESCRIPTION
				"Ap index, is used to identify AP uniquely."
			::= { hwApEntry 1 }

--    1.3.6.1.4.1.2011.6.139.2.6.1.1.2
-- 1.3.6.1.4.1.2011.6.139.2.6.1.1.2
-- 1.3.6.1.4.1.2011.6.139.2.6.1.1.2
		-- 1.3.6.1.4.1.2011.6.139.2.6.1.1.2
		hwApUsedType OBJECT-TYPE
			SYNTAX OCTET STRING
			MAX-ACCESS read-create
			STATUS current
			DESCRIPTION
				"Ap type. For more details, please refer to hwApTypeTable."
			::= { hwApEntry 2 }

--    1.3.6.1.4.1.2011.6.139.2.6.1.1.3
-- 1.3.6.1.4.1.2011.6.139.2.6.1.1.3
-- 1.3.6.1.4.1.2011.6.139.2.6.1.1.3
		-- 1.3.6.1.4.1.2011.6.139.2.6.1.1.3
		hwApUsedProfileName OBJECT-TYPE
			SYNTAX OCTET STRING
			MAX-ACCESS read-create
			STATUS current
			DESCRIPTION
				"Ap profile name. For more details, please refer to hwApProfileTable."
			::= { hwApEntry 3 }

--    1.3.6.1.4.1.2011.6.139.2.6.1.1.4
-- 1.3.6.1.4.1.2011.6.139.2.6.1.1.4
-- 1.3.6.1.4.1.2011.6.139.2.6.1.1.4
		-- 1.3.6.1.4.1.2011.6.139.2.6.1.1.4
		hwApUsedRegionIndex OBJECT-TYPE
			SYNTAX Integer32
			MAX-ACCESS read-create
			STATUS current
			DESCRIPTION
				"Ap region index. For more details, please refer to hwApRegionTable."
			::= { hwApEntry 4 }

--    1.3.6.1.4.1.2011.6.139.2.6.1.1.5
-- 1.3.6.1.4.1.2011.6.139.2.6.1.1.5
-- 1.3.6.1.4.1.2011.6.139.2.6.1.1.5
		-- 1.3.6.1.4.1.2011.6.139.2.6.1.1.5
		hwApMac OBJECT-TYPE
			SYNTAX MacAddress
			MAX-ACCESS read-create
			STATUS current
			DESCRIPTION
				"Ap's mac address."
			::= { hwApEntry 5 }

--    1.3.6.1.4.1.2011.6.139.2.6.1.1.6
-- 1.3.6.1.4.1.2011.6.139.2.6.1.1.6
-- 1.3.6.1.4.1.2011.6.139.2.6.1.1.6
		-- 1.3.6.1.4.1.2011.6.139.2.6.1.1.6
		hwApSn OBJECT-TYPE
			SYNTAX OCTET STRING
			MAX-ACCESS read-create
			STATUS current
			DESCRIPTION
				"Ap's sn."
			::= { hwApEntry 6 }

--    1.3.6.1.4.1.2011.6.139.2.6.1.1.7
-- 1.3.6.1.4.1.2011.6.139.2.6.1.1.7
-- 1.3.6.1.4.1.2011.6.139.2.6.1.1.7
		-- 1.3.6.1.4.1.2011.6.139.2.6.1.1.7
		hwApSysName OBJECT-TYPE
			SYNTAX OCTET STRING
			MAX-ACCESS read-create
			STATUS current
			DESCRIPTION
				"Name of AP."
			::= { hwApEntry 7 }

--    1.3.6.1.4.1.2011.6.139.2.6.1.1.8
-- 1.3.6.1.4.1.2011.6.139.2.6.1.1.8
-- 1.3.6.1.4.1.2011.6.139.2.6.1.1.8
		-- 1.3.6.1.4.1.2011.6.139.2.6.1.1.8
		hwApRunState OBJECT-TYPE
			SYNTAX INTEGER
				{
				idle(1),
				autofind(2),
				typeNotMatch(3),
				fault(4),
				config(5),
				configFailed(6),
				download(7),
				normal(8),
				committing(9),
				commitFailed(10),
				standby(11),
				vermismatch(12)
				}
			MAX-ACCESS read-only
			STATUS current
			DESCRIPTION
				"The run state of AP."
			::= { hwApEntry 8 }

--    1.3.6.1.4.1.2011.6.139.2.6.1.1.9
-- 1.3.6.1.4.1.2011.6.139.2.6.1.1.9
-- 1.3.6.1.4.1.2011.6.139.2.6.1.1.9
		-- 1.3.6.1.4.1.2011.6.139.2.6.1.1.9
		hwApSoftwareVersion OBJECT-TYPE
			SYNTAX OCTET STRING
			MAX-ACCESS read-only
			STATUS current
			DESCRIPTION
				"The software version of AP."
			::= { hwApEntry 9 }

--    1.3.6.1.4.1.2011.6.139.2.6.1.1.10
-- 1.3.6.1.4.1.2011.6.139.2.6.1.1.10
-- 1.3.6.1.4.1.2011.6.139.2.6.1.1.10
		-- 1.3.6.1.4.1.2011.6.139.2.6.1.1.10
		hwApHardwareVersion OBJECT-TYPE
			SYNTAX OCTET STRING
			MAX-ACCESS read-only
			STATUS current
			DESCRIPTION
				"The hardware version of AP."
			::= { hwApEntry 10 }

--    1.3.6.1.4.1.2011.6.139.2.6.1.1.11
-- 1.3.6.1.4.1.2011.6.139.2.6.1.1.11
-- 1.3.6.1.4.1.2011.6.139.2.6.1.1.11
		-- 1.3.6.1.4.1.2011.6.139.2.6.1.1.11
		hwApCpuType OBJECT-TYPE
			SYNTAX OCTET STRING
			MAX-ACCESS read-only
			STATUS current
			DESCRIPTION
				"Cpu type of AP."
			::= { hwApEntry 11 }

--    1.3.6.1.4.1.2011.6.139.2.6.1.1.12
-- 1.3.6.1.4.1.2011.6.139.2.6.1.1.12
-- 1.3.6.1.4.1.2011.6.139.2.6.1.1.12
		-- 1.3.6.1.4.1.2011.6.139.2.6.1.1.12
		hwApCpufrequency OBJECT-TYPE
			SYNTAX Integer32
			UNITS "MHZ"
			MAX-ACCESS read-only
			STATUS current
			DESCRIPTION
				"Cpu frequency of AP. Unit: MHZ."
			::= { hwApEntry 12 }

--    1.3.6.1.4.1.2011.6.139.2.6.1.1.13
-- 1.3.6.1.4.1.2011.6.139.2.6.1.1.13
-- 1.3.6.1.4.1.2011.6.139.2.6.1.1.13
		-- 1.3.6.1.4.1.2011.6.139.2.6.1.1.13
		hwApMemoryType OBJECT-TYPE
			SYNTAX OCTET STRING
			MAX-ACCESS read-only
			STATUS current
			DESCRIPTION
				"Memory type of AP."
			::= { hwApEntry 13 }

--    1.3.6.1.4.1.2011.6.139.2.6.1.1.14
-- 1.3.6.1.4.1.2011.6.139.2.6.1.1.14
-- 1.3.6.1.4.1.2011.6.139.2.6.1.1.14
		-- 1.3.6.1.4.1.2011.6.139.2.6.1.1.14
		hwApDomain OBJECT-TYPE
			SYNTAX OCTET STRING
			MAX-ACCESS read-only
			STATUS current
			DESCRIPTION
				"The domain of AP."
			::= { hwApEntry 14 }

--    1.3.6.1.4.1.2011.6.139.2.6.1.1.15
-- 1.3.6.1.4.1.2011.6.139.2.6.1.1.15
-- 1.3.6.1.4.1.2011.6.139.2.6.1.1.15
		-- 1.3.6.1.4.1.2011.6.139.2.6.1.1.15
		hwApIpAddress OBJECT-TYPE
			SYNTAX IpAddress
			MAX-ACCESS read-write
			STATUS current
			DESCRIPTION
				"The ip address of AP."
			::= { hwApEntry 15 }

--    1.3.6.1.4.1.2011.6.139.2.6.1.1.16
-- 1.3.6.1.4.1.2011.6.139.2.6.1.1.16
-- 1.3.6.1.4.1.2011.6.139.2.6.1.1.16
		-- 1.3.6.1.4.1.2011.6.139.2.6.1.1.16
		hwApIpNetMask OBJECT-TYPE
			SYNTAX IpAddress
			MAX-ACCESS read-only
			STATUS current
			DESCRIPTION
				"The ip net mask of AP."
			::= { hwApEntry 16 }

--    1.3.6.1.4.1.2011.6.139.2.6.1.1.17
-- 1.3.6.1.4.1.2011.6.139.2.6.1.1.17
-- 1.3.6.1.4.1.2011.6.139.2.6.1.1.17
		-- 1.3.6.1.4.1.2011.6.139.2.6.1.1.17
		hwApGatewayIp OBJECT-TYPE
			SYNTAX IpAddress
			MAX-ACCESS read-only
			STATUS current
			DESCRIPTION
				"The gateway's ip address of AP."
			::= { hwApEntry 17 }

--    1.3.6.1.4.1.2011.6.139.2.6.1.1.18
-- 1.3.6.1.4.1.2011.6.139.2.6.1.1.18
-- 1.3.6.1.4.1.2011.6.139.2.6.1.1.18
		-- 1.3.6.1.4.1.2011.6.139.2.6.1.1.18
		hwApMemorySize OBJECT-TYPE
			SYNTAX Integer32
			UNITS "MB"
			MAX-ACCESS read-only
			STATUS current
			DESCRIPTION
				"The memory size of AP. Unit: MB"
			::= { hwApEntry 18 }

--    1.3.6.1.4.1.2011.6.139.2.6.1.1.19
-- 1.3.6.1.4.1.2011.6.139.2.6.1.1.19
-- 1.3.6.1.4.1.2011.6.139.2.6.1.1.19
		-- 1.3.6.1.4.1.2011.6.139.2.6.1.1.19
		hwApFlashSize OBJECT-TYPE
			SYNTAX Integer32
			UNITS "MB"
			MAX-ACCESS read-only
			STATUS current
			DESCRIPTION
				"The flash size of AP. Unit: MB"
			::= { hwApEntry 19 }

--    1.3.6.1.4.1.2011.6.139.2.6.1.1.20
-- 1.3.6.1.4.1.2011.6.139.2.6.1.1.20
-- 1.3.6.1.4.1.2011.6.139.2.6.1.1.20
		-- 1.3.6.1.4.1.2011.6.139.2.6.1.1.20
		hwApRunTime OBJECT-TYPE
			SYNTAX Unsigned32
			MAX-ACCESS read-only
			STATUS current
			DESCRIPTION
				"The working time since AP is started."
			::= { hwApEntry 20 }

--    1.3.6.1.4.1.2011.6.139.2.6.1.1.21
-- 1.3.6.1.4.1.2011.6.139.2.6.1.1.21
-- 1.3.6.1.4.1.2011.6.139.2.6.1.1.21
		-- 1.3.6.1.4.1.2011.6.139.2.6.1.1.21
		hwApUpEthPortSpeed OBJECT-TYPE
			SYNTAX INTEGER
				{
				speed10(1),
				speed100(2),
				speed1000(3),
				speed10000(4)
				}
			UNITS "Mbps"
			MAX-ACCESS read-only
			STATUS current
			DESCRIPTION
				"The up ethernet port speed of AP. Unit: Mbps
				speed10 - 10Mbps,
				speed100 - 100Mbps,
				speed1000 - 1000Mbps,
				speed10000 - 10000Mbps"
			::= { hwApEntry 21 }

--    1.3.6.1.4.1.2011.6.139.2.6.1.1.22
-- 1.3.6.1.4.1.2011.6.139.2.6.1.1.22
-- 1.3.6.1.4.1.2011.6.139.2.6.1.1.22
		-- 1.3.6.1.4.1.2011.6.139.2.6.1.1.22
		hwApUpEthPortSpeedMode OBJECT-TYPE
			SYNTAX INTEGER
				{
				auto(1),
				forced(2)
				}
			MAX-ACCESS read-only
			STATUS current
			DESCRIPTION
				"The up ethernet port speed mode of AP.
				"
			::= { hwApEntry 22 }

--    1.3.6.1.4.1.2011.6.139.2.6.1.1.23
-- 1.3.6.1.4.1.2011.6.139.2.6.1.1.23
-- 1.3.6.1.4.1.2011.6.139.2.6.1.1.23
		-- 1.3.6.1.4.1.2011.6.139.2.6.1.1.23
		hwApUpEthPortDuplex OBJECT-TYPE
			SYNTAX INTEGER
				{
				half(1),
				full(2)
				}
			MAX-ACCESS read-only
			STATUS current
			DESCRIPTION
				"The duplex type of the AP's up ethernet port.
				half(1) - half duplex,
				full(2) - full duplex.
				"
			::= { hwApEntry 23 }

--    1.3.6.1.4.1.2011.6.139.2.6.1.1.24
-- 1.3.6.1.4.1.2011.6.139.2.6.1.1.24
-- 1.3.6.1.4.1.2011.6.139.2.6.1.1.24
		-- 1.3.6.1.4.1.2011.6.139.2.6.1.1.24
		hwApUpEthPortDuplexMode OBJECT-TYPE
			SYNTAX INTEGER
				{
				auto(1),
				forced(2)
				}
			MAX-ACCESS read-only
			STATUS current
			DESCRIPTION
				"The duplex mode of the AP's up ethernet port"
			::= { hwApEntry 24 }

--    1.3.6.1.4.1.2011.6.139.2.6.1.1.25
-- 1.3.6.1.4.1.2011.6.139.2.6.1.1.25
-- 1.3.6.1.4.1.2011.6.139.2.6.1.1.25
		-- 1.3.6.1.4.1.2011.6.139.2.6.1.1.25
		hwApAdminOper OBJECT-TYPE
			SYNTAX INTEGER
				{
				reset(1),
				confirm(2),
				manufacturerConfig(3),
				replaceAp(6)
				}
			MAX-ACCESS read-create
			STATUS current
			DESCRIPTION
				"Ap administration operation.
				reset - reset the AP.
				confirm - when an AP which is not in the white list connects to ac,
				  it will rest on join state. User can confirm it to make it to use.
				manufacturerConfig - reset AP to the manufacturing default config-
				  uration"
			::= { hwApEntry 25 }

--    1.3.6.1.4.1.2011.6.139.2.6.1.1.26
-- 1.3.6.1.4.1.2011.6.139.2.6.1.1.26
-- 1.3.6.1.4.1.2011.6.139.2.6.1.1.26
		-- 1.3.6.1.4.1.2011.6.139.2.6.1.1.26
		hwApRowstatus OBJECT-TYPE
			SYNTAX RowStatus
			MAX-ACCESS read-create
			STATUS current
			DESCRIPTION
				"Row status: mainly to support AP addition and deletion."
			::= { hwApEntry 26 }

--    1.3.6.1.4.1.2011.6.139.2.6.1.1.27
-- 1.3.6.1.4.1.2011.6.139.2.6.1.1.27
-- 1.3.6.1.4.1.2011.6.139.2.6.1.1.27
		-- 1.3.6.1.4.1.2011.6.139.2.6.1.1.27
		hwApPerformanceStatCycle OBJECT-TYPE
			SYNTAX INTEGER
				{
				fiveMinutes(1),
				tenMinutes(2),
				fifteenMinutes(3)
				}
			MAX-ACCESS read-write
			STATUS current
			DESCRIPTION
				"AP's performance Stat Cycle."
			::= { hwApEntry 27 }

--    1.3.6.1.4.1.2011.6.139.2.6.1.1.28
-- 1.3.6.1.4.1.2011.6.139.2.6.1.1.28
-- 1.3.6.1.4.1.2011.6.139.2.6.1.1.28
		-- 1.3.6.1.4.1.2011.6.139.2.6.1.1.28
		hwApDNS OBJECT-TYPE
			SYNTAX IpAddress
			MAX-ACCESS read-only
			STATUS current
			DESCRIPTION
				"AP DNS server address."
			::= { hwApEntry 28 }

--    1.3.6.1.4.1.2011.6.139.2.6.1.1.29
-- 1.3.6.1.4.1.2011.6.139.2.6.1.1.29
-- 1.3.6.1.4.1.2011.6.139.2.6.1.1.29
		-- 1.3.6.1.4.1.2011.6.139.2.6.1.1.29
		hwApRunningMode OBJECT-TYPE
			SYNTAX INTEGER
				{
				auto(1),
				fat(2),
				fit(3)
				}
			MAX-ACCESS read-write
			STATUS current
			DESCRIPTION
				"Running mode of AP.
				auto - If AP connects an AC, it will run in fit mode, or it will
				    run in fat mode.
				fat - Force AP to run in fat mode.
				fit - Force AP to run in fit mode."
			::= { hwApEntry 29 }

--    1.3.6.1.4.1.2011.6.139.2.6.1.1.30
-- 1.3.6.1.4.1.2011.6.139.2.6.1.1.30
-- 1.3.6.1.4.1.2011.6.139.2.6.1.1.30
		-- 1.3.6.1.4.1.2011.6.139.2.6.1.1.30
		hwApForwardMode OBJECT-TYPE
			SYNTAX INTEGER
				{
				directForward(1),
				tunnel(2),
				unknown(-1)
				}
			MAX-ACCESS read-write
			STATUS current
			DESCRIPTION
				"Set AP based forward mode.
				directForward(1) - direct forward mode, station data is direct forward.
				tunnel(2) - CAPWAP tunnel forward mode, station data is forward through
				    the CAPWAP tunnel to ensure	the security.
				"
			::= { hwApEntry 30 }

--    1.3.6.1.4.1.2011.6.139.2.6.1.1.31
-- 1.3.6.1.4.1.2011.6.139.2.6.1.1.31
-- 1.3.6.1.4.1.2011.6.139.2.6.1.1.31
		-- 1.3.6.1.4.1.2011.6.139.2.6.1.1.31
		hwApAntennaMode OBJECT-TYPE
			SYNTAX INTEGER
				{
				autoMode(1),
				leftMode(2),
				rightMode(3)
				}
			MAX-ACCESS read-write
			STATUS current
			DESCRIPTION
				"Ap antenna mode, used to select antenna mode,default is auto mode."
			::= { hwApEntry 31 }

--   1.3.6.1.4.1.2011.6.139.2.6.1.1.32
-- 1.3.6.1.4.1.2011.6.139.2.6.1.1.32
		-- 1.3.6.1.4.1.2011.6.139.2.6.1.1.32
		hwApCpuThreshold OBJECT-TYPE
			SYNTAX Integer32
			MAX-ACCESS read-create
			STATUS current
			DESCRIPTION
				"Description."
			::= { hwApEntry 32 }

--   1.3.6.1.4.1.2011.6.139.2.6.1.1.33
-- 1.3.6.1.4.1.2011.6.139.2.6.1.1.33
		-- 1.3.6.1.4.1.2011.6.139.2.6.1.1.33
		hwApMemThreshold OBJECT-TYPE
			SYNTAX Integer32
			MAX-ACCESS read-create
			STATUS current
			DESCRIPTION
				"Description."
			::= { hwApEntry 33 }

--   1.3.6.1.4.1.2011.6.139.2.6.1.1.34
-- 1.3.6.1.4.1.2011.6.139.2.6.1.1.34
		-- 1.3.6.1.4.1.2011.6.139.2.6.1.1.34
		hwApNEnumber OBJECT-TYPE
			SYNTAX OCTET STRING
			MAX-ACCESS read-write
			STATUS current
			DESCRIPTION
				"Description."
			::= { hwApEntry 34 }

--   1.3.6.1.4.1.2011.6.139.2.6.1.1.35
-- 1.3.6.1.4.1.2011.6.139.2.6.1.1.35
		-- 1.3.6.1.4.1.2011.6.139.2.6.1.1.35
		hwApOnlineTime OBJECT-TYPE
			SYNTAX Unsigned32
			MAX-ACCESS read-only
			STATUS current
			DESCRIPTION
				"Description."
			::= { hwApEntry 35 }

--   1.3.6.1.4.1.2011.6.139.2.6.1.1.36
-- 1.3.6.1.4.1.2011.6.139.2.6.1.1.36
		-- 1.3.6.1.4.1.2011.6.139.2.6.1.1.36
		hwApSysSoftwareDesc OBJECT-TYPE
			SYNTAX OCTET STRING
			MAX-ACCESS read-only
			STATUS current
			DESCRIPTION
				"Description."
			::= { hwApEntry 36 }

--   1.3.6.1.4.1.2011.6.139.2.6.1.1.37
-- 1.3.6.1.4.1.2011.6.139.2.6.1.1.37
		-- 1.3.6.1.4.1.2011.6.139.2.6.1.1.37
		hwApSysHardtwareDesc OBJECT-TYPE
			SYNTAX OCTET STRING
			MAX-ACCESS read-only
			STATUS current
			DESCRIPTION
				"Description."
			::= { hwApEntry 37 }

--   1.3.6.1.4.1.2011.6.139.2.6.1.1.38
-- 1.3.6.1.4.1.2011.6.139.2.6.1.1.38
		-- 1.3.6.1.4.1.2011.6.139.2.6.1.1.38
		hwApSysManufacture OBJECT-TYPE
			SYNTAX OCTET STRING
			MAX-ACCESS read-only
			STATUS current
			DESCRIPTION
				"Description."
			::= { hwApEntry 38 }

--   1.3.6.1.4.1.2011.6.139.2.6.1.1.39
-- 1.3.6.1.4.1.2011.6.139.2.6.1.1.39
		-- 1.3.6.1.4.1.2011.6.139.2.6.1.1.39
		hwApSysSoftwareName OBJECT-TYPE
			SYNTAX OCTET STRING
			MAX-ACCESS read-only
			STATUS current
			DESCRIPTION
				"Description."
			::= { hwApEntry 39 }

--   1.3.6.1.4.1.2011.6.139.2.6.1.1.40
-- 1.3.6.1.4.1.2011.6.139.2.6.1.1.40
		-- 1.3.6.1.4.1.2011.6.139.2.6.1.1.40
		hwApSysSoftwareVendor OBJECT-TYPE
			SYNTAX OCTET STRING
			MAX-ACCESS read-only
			STATUS current
			DESCRIPTION
				"Description."
			::= { hwApEntry 40 }

--   1.3.6.1.4.1.2011.6.139.2.6.1.1.41
-- 1.3.6.1.4.1.2011.6.139.2.6.1.1.41
		-- 1.3.6.1.4.1.2011.6.139.2.6.1.1.41
		hwApManagementVlanID OBJECT-TYPE
			SYNTAX Integer32
			MAX-ACCESS read-write
			STATUS current
			DESCRIPTION
				"Description."
			::= { hwApEntry 41 }

--   1.3.6.1.4.1.2011.6.139.2.6.1.1.42
-- 1.3.6.1.4.1.2011.6.139.2.6.1.1.42
		-- 1.3.6.1.4.1.2011.6.139.2.6.1.1.42
		hwApUsername OBJECT-TYPE
			SYNTAX OCTET STRING (SIZE (0..64))
			MAX-ACCESS read-write
			STATUS current
			DESCRIPTION
				"Description."
			::= { hwApEntry 42 }

--   1.3.6.1.4.1.2011.6.139.2.6.1.1.43
-- 1.3.6.1.4.1.2011.6.139.2.6.1.1.43
		-- 1.3.6.1.4.1.2011.6.139.2.6.1.1.43
		hwApPassword OBJECT-TYPE
			SYNTAX OCTET STRING (SIZE (0..16))
			MAX-ACCESS read-write
			STATUS current
			DESCRIPTION
				"Description."
			::= { hwApEntry 43 }

--   1.3.6.1.4.1.2011.6.139.2.6.1.1.44
-- 1.3.6.1.4.1.2011.6.139.2.6.1.1.44
		-- 1.3.6.1.4.1.2011.6.139.2.6.1.1.44
		hwApAcIP1 OBJECT-TYPE
			SYNTAX IpAddress
			MAX-ACCESS read-write
			STATUS current
			DESCRIPTION
				"Description."
			::= { hwApEntry 44 }

--   1.3.6.1.4.1.2011.6.139.2.6.1.1.45
-- 1.3.6.1.4.1.2011.6.139.2.6.1.1.45
		-- 1.3.6.1.4.1.2011.6.139.2.6.1.1.45
		hwApAcIP2 OBJECT-TYPE
			SYNTAX IpAddress
			MAX-ACCESS read-write
			STATUS current
			DESCRIPTION
				"Description."
			::= { hwApEntry 45 }

--   1.3.6.1.4.1.2011.6.139.2.6.1.1.46
-- 1.3.6.1.4.1.2011.6.139.2.6.1.1.46
		-- 1.3.6.1.4.1.2011.6.139.2.6.1.1.46
		hwApAcIP3 OBJECT-TYPE
			SYNTAX IpAddress
			MAX-ACCESS read-write
			STATUS current
			DESCRIPTION
				"Description."
			::= { hwApEntry 46 }

--   1.3.6.1.4.1.2011.6.139.2.6.1.1.47
-- 1.3.6.1.4.1.2011.6.139.2.6.1.1.47
		-- 1.3.6.1.4.1.2011.6.139.2.6.1.1.47
		hwApAcIP4 OBJECT-TYPE
			SYNTAX IpAddress
			MAX-ACCESS read-write
			STATUS current
			DESCRIPTION
				"Description."
			::= { hwApEntry 47 }

--   1.3.6.1.4.1.2011.6.139.2.6.1.1.48
-- 1.3.6.1.4.1.2011.6.139.2.6.1.1.48
		-- 1.3.6.1.4.1.2011.6.139.2.6.1.1.48
		hwApIpMode OBJECT-TYPE
			SYNTAX INTEGER
				{
				dchp(1),
				pppoe(2),
				static(3)
				}
			MAX-ACCESS read-write
			STATUS current
			DESCRIPTION
				"Description."
			::= { hwApEntry 48 }

--   1.3.6.1.4.1.2011.6.139.2.6.1.1.49
-- 1.3.6.1.4.1.2011.6.139.2.6.1.1.49
		-- 1.3.6.1.4.1.2011.6.139.2.6.1.1.49
		hwApLldpEnable OBJECT-TYPE
			SYNTAX INTEGER
				{
				disable(1),
				enable(2)
				}
			MAX-ACCESS read-create
			STATUS current
			DESCRIPTION
				"Description."
			DEFVAL { enable }
			::= { hwApEntry 49 }

--   1.3.6.1.4.1.2011.6.139.2.6.1.1.50
-- 1.3.6.1.4.1.2011.6.139.2.6.1.1.50
		-- 1.3.6.1.4.1.2011.6.139.2.6.1.1.50
		hwApLldpManageAddr OBJECT-TYPE
			SYNTAX INTEGER
				{
				disable(1),
				enable(2)
				}
			MAX-ACCESS read-create
			STATUS current
			DESCRIPTION
				"Description."
			DEFVAL { enable }
			::= { hwApEntry 50 }

--   1.3.6.1.4.1.2011.6.139.2.6.1.1.51
-- 1.3.6.1.4.1.2011.6.139.2.6.1.1.51
		-- 1.3.6.1.4.1.2011.6.139.2.6.1.1.51
		hwApLldpPortDes OBJECT-TYPE
			SYNTAX INTEGER
				{
				disable(1),
				enable(2)
				}
			MAX-ACCESS read-create
			STATUS current
			DESCRIPTION
				"Description."
			DEFVAL { enable }
			::= { hwApEntry 51 }

--   1.3.6.1.4.1.2011.6.139.2.6.1.1.52
-- 1.3.6.1.4.1.2011.6.139.2.6.1.1.52
		-- 1.3.6.1.4.1.2011.6.139.2.6.1.1.52
		hwApLldpSysCab OBJECT-TYPE
			SYNTAX INTEGER
				{
				disable(1),
				enable(2)
				}
			MAX-ACCESS read-create
			STATUS current
			DESCRIPTION
				"Description."
			DEFVAL { enable }
			::= { hwApEntry 52 }

--   1.3.6.1.4.1.2011.6.139.2.6.1.1.53
-- 1.3.6.1.4.1.2011.6.139.2.6.1.1.53
		-- 1.3.6.1.4.1.2011.6.139.2.6.1.1.53
		hwApLldpSysDes OBJECT-TYPE
			SYNTAX INTEGER
				{
				disable(1),
				enable(2)
				}
			MAX-ACCESS read-create
			STATUS current
			DESCRIPTION
				"Description."
			DEFVAL { enable }
			::= { hwApEntry 53 }

--   1.3.6.1.4.1.2011.6.139.2.6.1.1.54
-- 1.3.6.1.4.1.2011.6.139.2.6.1.1.54
		-- 1.3.6.1.4.1.2011.6.139.2.6.1.1.54
		hwApLldpSysName OBJECT-TYPE
			SYNTAX INTEGER
				{
				disable(1),
				enable(2)
				}
			MAX-ACCESS read-create
			STATUS current
			DESCRIPTION
				"Description."
			DEFVAL { enable }
			::= { hwApEntry 54 }

--   1.3.6.1.4.1.2011.6.139.2.6.1.1.55
-- 1.3.6.1.4.1.2011.6.139.2.6.1.1.55
		-- 1.3.6.1.4.1.2011.6.139.2.6.1.1.55
		hwApLldpDelay OBJECT-TYPE
			SYNTAX Integer32 (1..8192)
			MAX-ACCESS read-create
			STATUS current
			DESCRIPTION
				"Description."
			DEFVAL { 2 }
			::= { hwApEntry 55 }

--   1.3.6.1.4.1.2011.6.139.2.6.1.1.56
-- 1.3.6.1.4.1.2011.6.139.2.6.1.1.56
		-- 1.3.6.1.4.1.2011.6.139.2.6.1.1.56
		hwApLldpHoldMultiplier OBJECT-TYPE
			SYNTAX Integer32 (2..10)
			MAX-ACCESS read-create
			STATUS current
			DESCRIPTION
				"Description."
			DEFVAL { 4 }
			::= { hwApEntry 56 }

--   1.3.6.1.4.1.2011.6.139.2.6.1.1.57
-- 1.3.6.1.4.1.2011.6.139.2.6.1.1.57
		-- 1.3.6.1.4.1.2011.6.139.2.6.1.1.57
		hwApLldpInterval OBJECT-TYPE
			SYNTAX Integer32 (5..32768)
			MAX-ACCESS read-create
			STATUS current
			DESCRIPTION
				"Description."
			DEFVAL { 30 }
			::= { hwApEntry 57 }

--   1.3.6.1.4.1.2011.6.139.2.6.1.1.58
-- 1.3.6.1.4.1.2011.6.139.2.6.1.1.58
		-- 1.3.6.1.4.1.2011.6.139.2.6.1.1.58
		hwApLldpRestartDelay OBJECT-TYPE
			SYNTAX Integer32 (1..10)
			MAX-ACCESS read-create
			STATUS current
			DESCRIPTION
				"Description."
			DEFVAL { 2 }
			::= { hwApEntry 58 }

--   1.3.6.1.4.1.2011.6.139.2.6.1.1.59
-- 1.3.6.1.4.1.2011.6.139.2.6.1.1.59
		-- 1.3.6.1.4.1.2011.6.139.2.6.1.1.59
		hwApLldpAdminStatus OBJECT-TYPE
			SYNTAX INTEGER
				{
				txrx(1),
				rx(2),
				tx(3)
				}
			MAX-ACCESS read-create
			STATUS current
			DESCRIPTION
				"Description."
			DEFVAL { 1 }
			::= { hwApEntry 59 }

--   1.3.6.1.4.1.2011.6.139.2.6.1.1.60
-- 1.3.6.1.4.1.2011.6.139.2.6.1.1.60
		-- 1.3.6.1.4.1.2011.6.139.2.6.1.1.60
		hwApLldpReportInterval OBJECT-TYPE
			SYNTAX Integer32 (5..3600)
			MAX-ACCESS read-create
			STATUS current
			DESCRIPTION
				"Description."
			DEFVAL { 30 }
			::= { hwApEntry 60 }

--   1.3.6.1.4.1.2011.6.139.2.6.1.1.61
-- 1.3.6.1.4.1.2011.6.139.2.6.1.1.61
		-- 1.3.6.1.4.1.2011.6.139.2.6.1.1.61
		hwApBomCode OBJECT-TYPE
			SYNTAX OCTET STRING
			MAX-ACCESS read-only
			STATUS current
			DESCRIPTION
				"Description."
			::= { hwApEntry 61 }

--   1.3.6.1.4.1.2011.6.139.2.6.1.1.62
-- 1.3.6.1.4.1.2011.6.139.2.6.1.1.62
		-- 1.3.6.1.4.1.2011.6.139.2.6.1.1.62
		hwApSaveMode OBJECT-TYPE
			SYNTAX Integer32
			MAX-ACCESS read-create
			STATUS obsolete
			DESCRIPTION
				"Description."
			::= { hwApEntry 62 }

--  1.3.6.1.4.1.2011.6.139.2.6.1.1.63
		-- 1.3.6.1.4.1.2011.6.139.2.6.1.1.63
		hwApProtectAcPriority OBJECT-TYPE
			SYNTAX Integer32
			MAX-ACCESS read-create
			STATUS current
			DESCRIPTION
				"Description."
			::= { hwApEntry 63 }

--  1.3.6.1.4.1.2011.6.139.2.6.1.1.64
		-- 1.3.6.1.4.1.2011.6.139.2.6.1.1.64
		hwApProtectAcIP OBJECT-TYPE
			SYNTAX IpAddress
			MAX-ACCESS read-create
			STATUS current
			DESCRIPTION
				"Description."
			::= { hwApEntry 64 }

--  1.3.6.1.4.1.2011.6.139.2.6.1.1.65
		-- 1.3.6.1.4.1.2011.6.139.2.6.1.1.65
		hwApOpticalHighRxPowerThreshold OBJECT-TYPE
			SYNTAX Integer32 (1000..65535)
			MAX-ACCESS read-create
			STATUS current
			DESCRIPTION
				"range from 1000 to 65535"
			::= { hwApEntry 65 }

--  1.3.6.1.4.1.2011.6.139.2.6.1.1.66
		-- 1.3.6.1.4.1.2011.6.139.2.6.1.1.66
		hwApOpticalLowRxPowerThreshold OBJECT-TYPE
			SYNTAX Integer32 (1..250)
			MAX-ACCESS read-create
			STATUS current
			DESCRIPTION
				"range from 1 to 250"
			::= { hwApEntry 66 }

--  1.3.6.1.4.1.2011.6.139.2.6.1.1.67
		-- 1.3.6.1.4.1.2011.6.139.2.6.1.1.67
		hwApOpticalHighTemperatureThreshold OBJECT-TYPE
			SYNTAX Integer32 (70..125)
			MAX-ACCESS read-create
			STATUS current
			DESCRIPTION
				"range from 70 to 125"
			::= { hwApEntry 67 }

--  1.3.6.1.4.1.2011.6.139.2.6.1.1.68
		-- 1.3.6.1.4.1.2011.6.139.2.6.1.1.68
		hwApOpticalLowTemperatureThreshold OBJECT-TYPE
			SYNTAX Integer32 (-40..-5)
			MAX-ACCESS read-create
			STATUS current
			DESCRIPTION
				"range from -40 to -5"
			::= { hwApEntry 68 }

--  1.3.6.1.4.1.2011.6.139.2.6.1.1.69
		-- 1.3.6.1.4.1.2011.6.139.2.6.1.1.69
		hwApKeepService OBJECT-TYPE
			SYNTAX INTEGER
				{
				enable(1),
				disable(2),
				allowaccess(3)
				}
			MAX-ACCESS read-create
			STATUS current
			DESCRIPTION
				"Description."
			::= { hwApEntry 69 }

--  1.3.6.1.4.1.2011.6.139.2.6.1.1.70
		-- 1.3.6.1.4.1.2011.6.139.2.6.1.1.70
		hwApPriorityAccessMode OBJECT-TYPE
			SYNTAX Integer32 (1..2)
			MAX-ACCESS read-write
			STATUS current
			DESCRIPTION
				"Description."
			::= { hwApEntry 70 }

--  1.3.6.1.4.1.2011.6.139.2.6.1.1.71
		-- 1.3.6.1.4.1.2011.6.139.2.6.1.1.71
		hwApLineateportMode OBJECT-TYPE
			SYNTAX INTEGER
				{
				root(1),
				endpoint(2)
				}
			MAX-ACCESS read-write
			STATUS current
			DESCRIPTION
				"Description."
			::= { hwApEntry 71 }

--  1.3.6.1.4.1.2011.6.139.2.6.1.1.72
		-- 1.3.6.1.4.1.2011.6.139.2.6.1.1.72
		hwApLineateportVlanTagged OBJECT-TYPE
			SYNTAX OCTET STRING (SIZE (0..1024))
			MAX-ACCESS read-write
			STATUS current
			DESCRIPTION
				"Description."
			::= { hwApEntry 72 }

--  1.3.6.1.4.1.2011.6.139.2.6.1.1.73
		-- 1.3.6.1.4.1.2011.6.139.2.6.1.1.73
		hwApLineateportVlanUntagged OBJECT-TYPE
			SYNTAX OCTET STRING (SIZE (0..1024))
			MAX-ACCESS read-write
			STATUS current
			DESCRIPTION
				"Description."
			::= { hwApEntry 73 }

--  1.3.6.1.4.1.2011.6.139.2.6.1.1.74
		-- 1.3.6.1.4.1.2011.6.139.2.6.1.1.74
		hwApLineateportPvidVlan OBJECT-TYPE
			SYNTAX Integer32 (0..4094)
			MAX-ACCESS read-write
			STATUS current
			DESCRIPTION
				"Description."
			::= { hwApEntry 74 }

--  1.3.6.1.4.1.2011.6.139.2.6.1.1.75
		-- 1.3.6.1.4.1.2011.6.139.2.6.1.1.75
		hwApLineateportUserIsolate OBJECT-TYPE
			SYNTAX INTEGER
				{
				disable(1),
				enable(2)
				}
			MAX-ACCESS read-write
			STATUS current
			DESCRIPTION
				"Description."
			::= { hwApEntry 75 }

--  1.3.6.1.4.1.2011.6.139.2.6.1.1.76
		-- 1.3.6.1.4.1.2011.6.139.2.6.1.1.76
		hwApLineateportStpEnable OBJECT-TYPE
			SYNTAX INTEGER
				{
				disable(1),
				enable(2)
				}
			MAX-ACCESS read-write
			STATUS current
			DESCRIPTION
				"Description."
			::= { hwApEntry 76 }

--  1.3.6.1.4.1.2011.6.139.2.6.1.1.77
		-- 1.3.6.1.4.1.2011.6.139.2.6.1.1.77
		hwApHighTemperatureThreshold OBJECT-TYPE
			SYNTAX Integer32 (20..110)
			MAX-ACCESS read-write
			STATUS current
			DESCRIPTION
				"Description."
			::= { hwApEntry 77 }

--  1.3.6.1.4.1.2011.6.139.2.6.1.1.78
		-- 1.3.6.1.4.1.2011.6.139.2.6.1.1.78
		hwApLowTemperatureThreshold OBJECT-TYPE
			SYNTAX Integer32 (-70..10)
			MAX-ACCESS read-write
			STATUS current
			DESCRIPTION
				"Description."
			::= { hwApEntry 78 }

--  1.3.6.1.4.1.2011.6.139.2.6.1.1.79
		-- 1.3.6.1.4.1.2011.6.139.2.6.1.1.79
		hwApReset OBJECT-TYPE
			SYNTAX Integer32
			MAX-ACCESS read-write
			STATUS current
			DESCRIPTION
				"Description."
			::= { hwApEntry 79 }

--  1.3.6.1.4.1.2011.6.139.2.6.1.1.80
		-- 1.3.6.1.4.1.2011.6.139.2.6.1.1.80
		hwApStaticIpAddress OBJECT-TYPE
			SYNTAX IpAddress
			MAX-ACCESS read-create
			STATUS current
			DESCRIPTION
				"Description."
			::= { hwApEntry 80 }

--  1.3.6.1.4.1.2011.6.139.2.6.1.1.81
		-- 1.3.6.1.4.1.2011.6.139.2.6.1.1.81
		hwApStaticNetMask OBJECT-TYPE
			SYNTAX IpAddress
			MAX-ACCESS read-create
			STATUS current
			DESCRIPTION
				"Description."
			::= { hwApEntry 81 }

--  1.3.6.1.4.1.2011.6.139.2.6.1.1.82
		-- 1.3.6.1.4.1.2011.6.139.2.6.1.1.82
		hwApStaticGatewayIp OBJECT-TYPE
			SYNTAX IpAddress
			MAX-ACCESS read-create
			STATUS current
			DESCRIPTION
				"Description."
			::= { hwApEntry 82 }

		-- 1.3.6.1.4.1.2011.6.139.2.6.1.1.83
		hwApAttackFloodInterval OBJECT-TYPE
			SYNTAX Integer32
			MAX-ACCESS read-create
			STATUS current
			DESCRIPTION
				"Description."
			::= { hwApEntry 83 }

 		-- 1.3.6.1.4.1.2011.6.139.2.6.1.1.84
		hwApAttackFloodTimes OBJECT-TYPE
			SYNTAX Integer32
			MAX-ACCESS read-create
			STATUS current
			DESCRIPTION
				"Description."
			::= { hwApEntry 84 }

		-- 1.3.6.1.4.1.2011.6.139.2.6.1.1.85
		hwApDynamicBlacklistEnable OBJECT-TYPE
			SYNTAX Integer32
			MAX-ACCESS read-create
			STATUS current
			DESCRIPTION
				"Description."
			::= { hwApEntry 85 }

		-- 1.3.6.1.4.1.2011.6.139.2.6.1.1.86
		hwApDynamicBlacklistAgingInt OBJECT-TYPE
			SYNTAX Integer32
			MAX-ACCESS read-create
			STATUS current
			DESCRIPTION
				"Description."
			::= { hwApEntry 86 }

		-- 1.3.6.1.4.1.2011.6.139.2.6.1.1.87
		hwApAttackPskInterval OBJECT-TYPE
			SYNTAX Integer32
			MAX-ACCESS read-create
			STATUS current
			DESCRIPTION
				"Description."
			::= { hwApEntry 87 }


		-- 1.3.6.1.4.1.2011.6.139.2.6.1.1.88
		hwApAttackPskTimes OBJECT-TYPE
			SYNTAX Integer32
			MAX-ACCESS read-create
			STATUS current
			DESCRIPTION
				"Description."
			::= { hwApEntry 88 }

		-- 1.3.6.1.4.1.2011.6.139.2.6.1.1.89
		hwApAccessBalanceGap OBJECT-TYPE
			SYNTAX Integer32 (0..100)
			MAX-ACCESS read-write
			STATUS current
			DESCRIPTION
				"Description."
			::= { hwApEntry 89 }

		-- 1.3.6.1.4.1.2011.6.139.2.6.1.1.90
		hwApIpv6Address OBJECT-TYPE
			SYNTAX OCTET STRING (SIZE (0..46))
			MAX-ACCESS read-only
			STATUS current
			DESCRIPTION
				"Description."
			::= { hwApEntry 90 }

		-- 1.3.6.1.4.1.2011.6.139.2.6.1.1.91
		hwApIpv6NetMask OBJECT-TYPE
			SYNTAX OCTET STRING (SIZE (0..46))
			MAX-ACCESS read-only
			STATUS current
			DESCRIPTION
				"Description."
			::= { hwApEntry 91 }

		-- 1.3.6.1.4.1.2011.6.139.2.6.1.1.92
		hwApGatewayIpv6 OBJECT-TYPE
			SYNTAX OCTET STRING (SIZE (0..46))
			MAX-ACCESS read-only
			STATUS current
			DESCRIPTION
				"Description."
			::= { hwApEntry 92 }

		-- 1.3.6.1.4.1.2011.6.139.2.6.1.1.93
		hwApIpv6DNS OBJECT-TYPE
			SYNTAX OCTET STRING (SIZE (0..46))
			MAX-ACCESS read-only
			STATUS current
			DESCRIPTION
				"Description."
			::= { hwApEntry 93 }

		-- 1.3.6.1.4.1.2011.6.139.2.6.1.1.94
		hwApProtectAcIPv6Addr OBJECT-TYPE
			SYNTAX OCTET STRING (SIZE (0..46))
			MAX-ACCESS read-create
			STATUS current
			DESCRIPTION
				"Description."
			::= { hwApEntry 94 }


		-- 1.3.6.1.4.1.2011.6.139.2.6.1.1.95
		hwApLineatePortCfgMtu OBJECT-TYPE
			SYNTAX Integer32
			MAX-ACCESS read-only
			STATUS current
			DESCRIPTION
				"Description."
			::= { hwApEntry 95 }


		-- 1.3.6.1.4.1.2011.6.139.2.6.1.1.96
		hwApLineatePortMacAddress OBJECT-TYPE
			SYNTAX MacAddress
			MAX-ACCESS read-only
			STATUS current
			DESCRIPTION
				"Description."
			::= { hwApEntry 96 }

		-- 1.3.6.1.4.1.2011.6.139.2.6.1.1.97
		hwApAccessBalanceSwitch OBJECT-TYPE
			SYNTAX INTEGER
				{
				disable(1),
				enable(2)
				}
			MAX-ACCESS read-write
			STATUS current
			DESCRIPTION
				"Description."
			::= { hwApEntry 97 }

		-- 1.3.6.1.4.1.2011.6.139.2.6.1.1.98
		hwApNatIpAddress OBJECT-TYPE
			SYNTAX OCTET STRING
			MAX-ACCESS read-only
			STATUS current
			DESCRIPTION
				"Description."
			::= { hwApEntry 98 }

		-- 1.3.6.1.4.1.2011.6.139.2.6.1.1.99
		hwApAttackFloodQuietTime OBJECT-TYPE
			SYNTAX Integer32 (60..36000)
			MAX-ACCESS read-create
			STATUS current
			DESCRIPTION
				"Flood attack quiet time. Range from 60s to 36000s"
			::= { hwApEntry 99 }

		-- 1.3.6.1.4.1.2011.6.139.2.6.1.1.100
		hwApAttackPskQuietTime OBJECT-TYPE
			SYNTAX Integer32 (60..36000)
			MAX-ACCESS read-create
			STATUS current
			DESCRIPTION
				"Psk attack quiet time. Range from 60s to 36000s"
			::= { hwApEntry 100 }

		-- 1.3.6.1.4.1.2011.6.139.2.6.1.1.101
		hwApAttackWeakivQuietTime OBJECT-TYPE
			SYNTAX Integer32 (60..36000)
			MAX-ACCESS read-create
			STATUS current
			DESCRIPTION
				"Weak-iv attack quiet time. Range from 60s to 36000s"
			::= { hwApEntry 101 }

		-- 1.3.6.1.4.1.2011.6.139.2.6.1.1.102
		hwApAttackSpoofQuietTime OBJECT-TYPE
			SYNTAX Integer32 (60..36000)
			MAX-ACCESS read-create
			STATUS current
			DESCRIPTION
				"Spoof attack quiet time. Range from 60s to 36000s"
			::= { hwApEntry 102 }

		-- 1.3.6.1.4.1.2011.6.139.2.6.1.1.103
		hwApBootCountTotal OBJECT-TYPE
			SYNTAX Integer32
			MAX-ACCESS read-create
			STATUS current
			DESCRIPTION
				"Description."
			::= { hwApEntry 103 }

		-- 1.3.6.1.4.1.2011.6.139.2.6.1.1.104
		hwApBootCountPowerOff OBJECT-TYPE
			SYNTAX Integer32
			MAX-ACCESS read-create
			STATUS current
			DESCRIPTION
				"Description."
			::= { hwApEntry 104 }

		-- 1.3.6.1.4.1.2011.6.139.2.6.1.1.105
		hwApBootCountRowStatus OBJECT-TYPE
			SYNTAX RowStatus
			MAX-ACCESS read-create
			STATUS current
			DESCRIPTION
				"Description."
			::= { hwApEntry 105 }

--  1.3.6.1.4.1.2011.6.139.2.6.2
		-- 1.3.6.1.4.1.2011.6.139.2.6.2
		hwApLineatePortTable OBJECT-TYPE
			SYNTAX SEQUENCE OF HwApLineatePortEntry
			MAX-ACCESS not-accessible
			STATUS current
			DESCRIPTION
				"Huawei AP lineate port table. The Index of this table is AP ID and
				lineate port ID."
			::= { hwApObjects 2 }

--    1.3.6.1.4.1.2011.6.139.2.6.2.1
-- 1.3.6.1.4.1.2011.6.139.2.6.2.1
-- 1.3.6.1.4.1.2011.6.139.2.6.2.1
		-- 1.3.6.1.4.1.2011.6.139.2.6.2.1
		hwApLineatePortEntry OBJECT-TYPE
			SYNTAX HwApLineatePortEntry
			MAX-ACCESS not-accessible
			STATUS current
			DESCRIPTION
				"Huawei AP lineate port table entry. The Index of this table is AP ID and
				lineate port ID."
			INDEX { hwApIndex, hwApLineatePortIndex }
			::= { hwApLineatePortTable 1 }

		HwApLineatePortEntry ::=
			SEQUENCE {
				hwApLineatePortIndex
					Integer32,
				hwApLineatePortType
					INTEGER,
				hwApLineatePortDesc
					OCTET STRING,
				hwApLineatePortState
					INTEGER,
				hwApLineatePortSpeed
					Integer32,
				hwApMultiLineatePortDuplex
					INTEGER,
				hwApMultiLineatePortNegotiation
					INTEGER,
				hwApMultiLineatePortMode
					INTEGER,
				hwApMultiLineatePortUserIsolate
					INTEGER,
				hwApMultiLineatePortStpEnable
					INTEGER,
				hwApMultiLineatePortVlanTagged
					OCTET STRING,
				hwApMultiLineatePortVlanUntagged
					OCTET STRING,
				hwApMultiLineatePortPvidVlan
					Integer32,
				hwApMultiLineatePortCRCErrorHighThreshold
					Integer32,
				hwApMultiLineatePortCRCErrorLowThreshold
					Integer32,
				hwApMultiLineatePortCRCErrorSwitch
					INTEGER,
				hwApLineatePortAclNumInbound
					Integer32,
				hwApLineatePortAclNumOutbound
					Integer32,
				hwApLineatePortAclNameInbound
					OCTET STRING,
				hwApLineatePortAclNameOutbound
					OCTET STRING,
				hwApLineatePortAclSwitchInbound
					INTEGER,
				hwApLineatePortAclSwitchOutbound
					INTEGER,
				hwApLineatePortAclNumInboundIPV6
					Integer32,
				hwApLineatePortAclNumOutboundIPV6
					Integer32,
				hwApLineatePortAclNameInboundIPV6
					OCTET STRING,
				hwApLineatePortAclNameOutboundIPV6
					OCTET STRING,
				hwApLineatePortAclSwitchInboundIPV6
					INTEGER,
				hwApLineatePortAclSwitchOutboundIPV6
					INTEGER,
				hwApMultiLineatePortIsAddInTrunk
					INTEGER,
				hwApMultiLineatePortAddedOrExitTrunkID
					Integer32
			 }

--    1.3.6.1.4.1.2011.6.139.2.6.2.1.1
-- 1.3.6.1.4.1.2011.6.139.2.6.2.1.1
-- 1.3.6.1.4.1.2011.6.139.2.6.2.1.1
		-- 1.3.6.1.4.1.2011.6.139.2.6.2.1.1
		hwApLineatePortIndex OBJECT-TYPE
			SYNTAX Integer32
			MAX-ACCESS not-accessible
			STATUS current
			DESCRIPTION
				"Lineate port index on an AP."
			::= { hwApLineatePortEntry 1 }

--    1.3.6.1.4.1.2011.6.139.2.6.2.1.2
-- 1.3.6.1.4.1.2011.6.139.2.6.2.1.2
-- 1.3.6.1.4.1.2011.6.139.2.6.2.1.2
		-- 1.3.6.1.4.1.2011.6.139.2.6.2.1.2
		hwApLineatePortType OBJECT-TYPE
			SYNTAX INTEGER
				{
				fe(1),
				ge(2),
				gpon(3),
				epon(4),
				adsl2plus(5),
				trunk(6)
				}
			MAX-ACCESS read-only
			STATUS current
			DESCRIPTION
				"Lineate port type."
			::= { hwApLineatePortEntry 2 }

--    1.3.6.1.4.1.2011.6.139.2.6.2.1.3
-- 1.3.6.1.4.1.2011.6.139.2.6.2.1.3
-- 1.3.6.1.4.1.2011.6.139.2.6.2.1.3
		-- 1.3.6.1.4.1.2011.6.139.2.6.2.1.3
		hwApLineatePortDesc OBJECT-TYPE
			SYNTAX OCTET STRING
			MAX-ACCESS read-write
			STATUS current
			DESCRIPTION
				"Lineate port description."
			::= { hwApLineatePortEntry 3 }

--    1.3.6.1.4.1.2011.6.139.2.6.2.1.4
-- 1.3.6.1.4.1.2011.6.139.2.6.2.1.4
-- 1.3.6.1.4.1.2011.6.139.2.6.2.1.4
		-- 1.3.6.1.4.1.2011.6.139.2.6.2.1.4
		hwApLineatePortState OBJECT-TYPE
			SYNTAX INTEGER
				{
				down(1),
				up(2),
				unknown(-1)
				}
			MAX-ACCESS read-only
			STATUS current
			DESCRIPTION
				"Lineate port state."
			::= { hwApLineatePortEntry 4 }

--    1.3.6.1.4.1.2011.6.139.2.6.2.1.5
-- 1.3.6.1.4.1.2011.6.139.2.6.2.1.5
-- 1.3.6.1.4.1.2011.6.139.2.6.2.1.5
		-- 1.3.6.1.4.1.2011.6.139.2.6.2.1.5
		hwApLineatePortSpeed OBJECT-TYPE
			SYNTAX Integer32
			UNITS "Mbps"
			MAX-ACCESS read-only
			STATUS current
			DESCRIPTION
				"Lineate port rate. Unit: Mbps"
			::= { hwApLineatePortEntry 5 }


--  1.3.6.1.4.1.2011.6.139.2.6.2.1.9
		-- 1.3.6.1.4.1.2011.6.139.2.6.2.1.6
		hwApMultiLineatePortDuplex OBJECT-TYPE
			SYNTAX INTEGER
				{
				half(1),
				full(2),
				unknown(-1)
				}
			MAX-ACCESS read-write
			STATUS current
			DESCRIPTION
				"Description."
			::= { hwApLineatePortEntry 6 }


--  1.3.6.1.4.1.2011.6.139.2.6.2.1.10
		-- 1.3.6.1.4.1.2011.6.139.2.6.2.1.7
		hwApMultiLineatePortNegotiation OBJECT-TYPE
			SYNTAX INTEGER
				{
				auto(1),
				forced(2),
				unknown(-1)
				}
			MAX-ACCESS read-only
			STATUS current
			DESCRIPTION
				"Description."
			::= { hwApLineatePortEntry 7 }


--  1.3.6.1.4.1.2011.6.139.2.6.2.1.11
		-- 1.3.6.1.4.1.2011.6.139.2.6.2.1.8
		hwApMultiLineatePortMode OBJECT-TYPE
			SYNTAX INTEGER
				{
				root(1),
				endpoint(2)
				}
			MAX-ACCESS read-write
			STATUS current
			DESCRIPTION
				"Description."
			::= { hwApLineatePortEntry 8 }


--  1.3.6.1.4.1.2011.6.139.2.6.2.1.12
		-- 1.3.6.1.4.1.2011.6.139.2.6.2.1.9
		hwApMultiLineatePortUserIsolate OBJECT-TYPE
			SYNTAX INTEGER
				{
				disable(1),
				enable(2)
				}
			MAX-ACCESS read-write
			STATUS current
			DESCRIPTION
				"Description."
			::= { hwApLineatePortEntry 9 }


--  1.3.6.1.4.1.2011.6.139.2.6.2.1.13
		-- 1.3.6.1.4.1.2011.6.139.2.6.2.1.10
		hwApMultiLineatePortStpEnable OBJECT-TYPE
			SYNTAX INTEGER
				{
				disable(1),
				enable(2)
				}
			MAX-ACCESS read-write
			STATUS current
			DESCRIPTION
				"Description."
			::= { hwApLineatePortEntry 10 }


--  1.3.6.1.4.1.2011.6.139.2.6.2.1.14
		-- 1.3.6.1.4.1.2011.6.139.2.6.2.1.11
		hwApMultiLineatePortVlanTagged OBJECT-TYPE
			SYNTAX OCTET STRING (SIZE (0..1024))
			MAX-ACCESS read-write
			STATUS current
			DESCRIPTION
				"Description."
			::= { hwApLineatePortEntry 11 }


--  1.3.6.1.4.1.2011.6.139.2.6.2.1.15
		-- 1.3.6.1.4.1.2011.6.139.2.6.2.1.12
		hwApMultiLineatePortVlanUntagged OBJECT-TYPE
			SYNTAX OCTET STRING (SIZE (0..1024))
			MAX-ACCESS read-write
			STATUS current
			DESCRIPTION
				"Description."
			::= { hwApLineatePortEntry 12 }


--  1.3.6.1.4.1.2011.6.139.2.6.2.1.16
		-- 1.3.6.1.4.1.2011.6.139.2.6.2.1.13
		hwApMultiLineatePortPvidVlan OBJECT-TYPE
			SYNTAX Integer32 (0..4094)
			MAX-ACCESS read-write
			STATUS current
			DESCRIPTION
				"Description."
			::= { hwApLineatePortEntry 13 }


--  1.3.6.1.4.1.2011.6.139.2.6.2.1.17
		-- 1.3.6.1.4.1.2011.6.139.2.6.2.1.14
		hwApMultiLineatePortCRCErrorHighThreshold OBJECT-TYPE
			SYNTAX Integer32
			MAX-ACCESS read-write
			STATUS current
			DESCRIPTION
				"Description."
			::= { hwApLineatePortEntry 14 }


--  1.3.6.1.4.1.2011.6.139.2.6.2.1.18
		-- 1.3.6.1.4.1.2011.6.139.2.6.2.1.15
		hwApMultiLineatePortCRCErrorLowThreshold OBJECT-TYPE
			SYNTAX Integer32
			MAX-ACCESS read-write
			STATUS current
			DESCRIPTION
				"Description."
			::= { hwApLineatePortEntry 15 }


		-- 1.3.6.1.4.1.2011.6.139.2.6.2.1.16
		hwApMultiLineatePortCRCErrorSwitch OBJECT-TYPE
			SYNTAX INTEGER
				{
				disable(1),
				enable(2),
				unknown(-1)
				}
			MAX-ACCESS read-write
			STATUS current
			DESCRIPTION
				"Description."
			::= { hwApLineatePortEntry 16 }


--  1.3.6.1.4.1.2011.6.139.2.6.2.1.19
		-- 1.3.6.1.4.1.2011.6.139.2.6.2.1.17
		hwApLineatePortAclNumInbound OBJECT-TYPE
			SYNTAX Integer32
			MAX-ACCESS read-write
			STATUS current
			DESCRIPTION
				"Description."
			::= { hwApLineatePortEntry 17 }


--  1.3.6.1.4.1.2011.6.139.2.6.2.1.20
		-- 1.3.6.1.4.1.2011.6.139.2.6.2.1.18
		hwApLineatePortAclNumOutbound OBJECT-TYPE
			SYNTAX Integer32
			MAX-ACCESS read-write
			STATUS current
			DESCRIPTION
				"Description."
			::= { hwApLineatePortEntry 18 }


--  1.3.6.1.4.1.2011.6.139.2.6.2.1.21
		-- 1.3.6.1.4.1.2011.6.139.2.6.2.1.19
		hwApLineatePortAclNameInbound OBJECT-TYPE
			SYNTAX OCTET STRING
			MAX-ACCESS read-write
			STATUS current
			DESCRIPTION
				"Description."
			::= { hwApLineatePortEntry 19 }


--  1.3.6.1.4.1.2011.6.139.2.6.2.1.22
		-- 1.3.6.1.4.1.2011.6.139.2.6.2.1.20
		hwApLineatePortAclNameOutbound OBJECT-TYPE
			SYNTAX OCTET STRING
			MAX-ACCESS read-write
			STATUS current
			DESCRIPTION
				"Description."
			::= { hwApLineatePortEntry 20 }


--  1.3.6.1.4.1.2011.6.139.2.6.2.1.23
		-- 1.3.6.1.4.1.2011.6.139.2.6.2.1.21
		hwApLineatePortAclSwitchInbound OBJECT-TYPE
			SYNTAX INTEGER
				{
				disable(1),
				enable(2)
				}
			MAX-ACCESS read-write
			STATUS current
			DESCRIPTION
				"Description."
			::= { hwApLineatePortEntry 21 }


--  1.3.6.1.4.1.2011.6.139.2.6.2.1.24
		-- 1.3.6.1.4.1.2011.6.139.2.6.2.1.22
		hwApLineatePortAclSwitchOutbound OBJECT-TYPE
			SYNTAX INTEGER
				{
				disable(1),
				enable(2)
				}
			MAX-ACCESS read-write
			STATUS current
			DESCRIPTION
				"Description."
			::= { hwApLineatePortEntry 22 }


--  1.3.6.1.4.1.2011.6.139.2.6.2.1.25
		-- 1.3.6.1.4.1.2011.6.139.2.6.2.1.23
		hwApLineatePortAclNumInboundIPV6 OBJECT-TYPE
			SYNTAX Integer32
			MAX-ACCESS read-write
			STATUS current
			DESCRIPTION
				"Description."
			::= { hwApLineatePortEntry 23 }


--  1.3.6.1.4.1.2011.6.139.2.6.2.1.26
		-- 1.3.6.1.4.1.2011.6.139.2.6.2.1.24
		hwApLineatePortAclNumOutboundIPV6 OBJECT-TYPE
			SYNTAX Integer32
			MAX-ACCESS read-write
			STATUS current
			DESCRIPTION
				"Description."
			::= { hwApLineatePortEntry 24 }


--  1.3.6.1.4.1.2011.6.139.2.6.2.1.27
		-- 1.3.6.1.4.1.2011.6.139.2.6.2.1.25
		hwApLineatePortAclNameInboundIPV6 OBJECT-TYPE
			SYNTAX OCTET STRING
			MAX-ACCESS read-write
			STATUS current
			DESCRIPTION
				"Description."
			::= { hwApLineatePortEntry 25 }


--  1.3.6.1.4.1.2011.6.139.2.6.2.1.28
		-- 1.3.6.1.4.1.2011.6.139.2.6.2.1.26
		hwApLineatePortAclNameOutboundIPV6 OBJECT-TYPE
			SYNTAX OCTET STRING
			MAX-ACCESS read-write
			STATUS current
			DESCRIPTION
				"Description."
			::= { hwApLineatePortEntry 26 }


--  1.3.6.1.4.1.2011.6.139.2.6.2.1.29
		-- 1.3.6.1.4.1.2011.6.139.2.6.2.1.27
		hwApLineatePortAclSwitchInboundIPV6 OBJECT-TYPE
			SYNTAX INTEGER
				{
				disable(1),
				enable(2)
				}
			MAX-ACCESS read-write
			STATUS current
			DESCRIPTION
				"Description."
			::= { hwApLineatePortEntry 27 }


--  1.3.6.1.4.1.2011.6.139.2.6.2.1.30
		-- 1.3.6.1.4.1.2011.6.139.2.6.2.1.28
		hwApLineatePortAclSwitchOutboundIPV6 OBJECT-TYPE
			SYNTAX INTEGER
				{
				disable(1),
				enable(2)
				}
			MAX-ACCESS read-write
			STATUS current
			DESCRIPTION
				"Description."
			::= { hwApLineatePortEntry 28 }


		-- 1.3.6.1.4.1.2011.6.139.2.6.2.1.29
		hwApMultiLineatePortIsAddInTrunk OBJECT-TYPE
			SYNTAX INTEGER
				{
				exit(1),
				add(2),
				unknow(-1)
				}
			MAX-ACCESS read-write
			STATUS current
			DESCRIPTION
				"Lineate port is add in trunk. when the value is 1,means not in trunk.
				when the value is 2,means add in trunk."
			::= { hwApLineatePortEntry 29 }


		-- 1.3.6.1.4.1.2011.6.139.2.6.2.1.30
		hwApMultiLineatePortAddedOrExitTrunkID OBJECT-TYPE
			SYNTAX Integer32 (0)
			MAX-ACCESS read-write
			STATUS current
			DESCRIPTION
				"Description."
			::= { hwApLineatePortEntry 30 }



		-- 1.3.6.1.4.1.2011.6.139.2.6.3
		hwApGlobalInfo OBJECT IDENTIFIER ::= { hwApObjects 3 }



		-- 1.3.6.1.4.1.2011.6.139.2.6.3.1
		hwApAllExistApIndexMask OBJECT-TYPE
			SYNTAX OCTET STRING
			MAX-ACCESS read-only
			STATUS current
			DESCRIPTION
				"All the existent APs' index mask.
				Every bit is used to describe the AP is existent or not.0 means AP
				is not existent, and 1 means AP is existent.The value of this node
				is hexadecimal integer block.Each Byte describes 8 APs are existent
				or not.
				For example, the first Byte describes AP 0~7 is existent or not,
				and the second Byte describes AP 8~15 is existent or not.
				Such as, if only AP 0,4,5,6,7,9 is existent, the binary number is
				11110001 and 00000010,the hexadecimal number is 0xF1 and 0x2, so
				the	first Byte of this node is 0xF1,and the second Byte is 0x2."
			::= { hwApGlobalInfo 1 }

--    1.3.6.1.4.1.2011.6.139.2.6.3.2
-- 1.3.6.1.4.1.2011.6.139.2.6.3.2
-- 1.3.6.1.4.1.2011.6.139.2.6.3.2
		-- 1.3.6.1.4.1.2011.6.139.2.6.3.2
		hwUnAuthorizedApRecordNumber OBJECT-TYPE
			SYNTAX Integer32
			MAX-ACCESS read-only
			STATUS current
			DESCRIPTION
				"The number of unauthorized AP records."
			::= { hwApGlobalInfo 2 }

--    1.3.6.1.4.1.2011.6.139.2.6.3.3
-- 1.3.6.1.4.1.2011.6.139.2.6.3.3
-- 1.3.6.1.4.1.2011.6.139.2.6.3.3
		-- 1.3.6.1.4.1.2011.6.139.2.6.3.3
		hwUnAuthorizedApRecordAdmin OBJECT-TYPE
			SYNTAX INTEGER { clear(1) }
			MAX-ACCESS read-write
			STATUS current
			DESCRIPTION
				"Unauthorized AP records administration operation.
				clear: Clear all the records.
				"
			::= { hwApGlobalInfo 3 }

		-- 1.3.6.1.4.1.2011.6.139.2.6.3.4
		hwApResetAllOnlineFailRecord OBJECT-TYPE
			SYNTAX INTEGER {
			                 reset(1),
			                 unknown(-1)
			               }
			MAX-ACCESS read-write
			STATUS current
			DESCRIPTION
				"Reset all ap online-fail records."
			::= { hwApGlobalInfo 4 }

		-- 1.3.6.1.4.1.2011.6.139.2.6.3.5
		hwApResetAllOfflineRecord OBJECT-TYPE
			SYNTAX INTEGER { reset(1) }
			MAX-ACCESS read-write
			STATUS current
			DESCRIPTION
				"Reset all ap offline records."
			::= { hwApGlobalInfo 5 }

		-- 1.3.6.1.4.1.2011.6.139.2.6.3.6
		hwApResetAllBootCountRecord OBJECT-TYPE
			SYNTAX INTEGER { reset(1) }
			MAX-ACCESS read-write
			STATUS current
			DESCRIPTION
				"Reset all ap boot count records."
			::= { hwApGlobalInfo 6 }

--     1.3.6.1.4.1.2011.6.139.2.6.4
-- 1.3.6.1.4.1.2011.6.139.2.6.4
-- 1.3.6.1.4.1.2011.6.139.2.6.4
		-- 1.3.6.1.4.1.2011.6.139.2.6.4
		hwApBatchInfo OBJECT IDENTIFIER ::= { hwApObjects 4 }

--    1.3.6.1.4.1.2011.6.139.2.6.4.1
-- 1.3.6.1.4.1.2011.6.139.2.6.4.1
-- 1.3.6.1.4.1.2011.6.139.2.6.4.1
		-- 1.3.6.1.4.1.2011.6.139.2.6.4.1
		hwApBatchIndexStart OBJECT-TYPE
			SYNTAX Integer32
			MAX-ACCESS read-write
			STATUS current
			DESCRIPTION
				"The initiatory AP number in batch operation. This node must be set
				in company with the node hwApBatchIndexNumber. "
			::= { hwApBatchInfo 1 }

--    1.3.6.1.4.1.2011.6.139.2.6.4.2
-- 1.3.6.1.4.1.2011.6.139.2.6.4.2
-- 1.3.6.1.4.1.2011.6.139.2.6.4.2
		-- 1.3.6.1.4.1.2011.6.139.2.6.4.2
		hwApBatchIndexNumber OBJECT-TYPE
			SYNTAX Integer32
			MAX-ACCESS read-write
			STATUS current
			DESCRIPTION
				"The AP number in batch operation. This node must be set in company
				with the node hwApBatchIndexStart. "
			::= { hwApBatchInfo 2 }

--    1.3.6.1.4.1.2011.6.139.2.6.4.3
-- 1.3.6.1.4.1.2011.6.139.2.6.4.3
-- 1.3.6.1.4.1.2011.6.139.2.6.4.3
		-- 1.3.6.1.4.1.2011.6.139.2.6.4.3
		hwApBatchIndexReturnNumber OBJECT-TYPE
			SYNTAX Integer32
			MAX-ACCESS read-only
			STATUS current
			DESCRIPTION
				"The actual AP number in batch operation. "
			::= { hwApBatchInfo 3 }

--    1.3.6.1.4.1.2011.6.139.2.6.4.4
-- 1.3.6.1.4.1.2011.6.139.2.6.4.4
-- 1.3.6.1.4.1.2011.6.139.2.6.4.4
		-- 1.3.6.1.4.1.2011.6.139.2.6.4.4
		hwApBatchState OBJECT-TYPE
			SYNTAX OCTET STRING
			MAX-ACCESS read-only
			STATUS current
			DESCRIPTION
				"The state of APs in batch operation. The value of this node is
				hexadecimal integer block.Each AP's state occupies a Bytes. For
				example, if the first operated AP's state is 15,and the sencond
				operated AP's state is 14, so the first Byte of this node is 0xF,
				and the second Byte is 0xE."
			::= { hwApBatchInfo 4 }

--    1.3.6.1.4.1.2011.6.139.2.6.4.5
-- 1.3.6.1.4.1.2011.6.139.2.6.4.5
-- 1.3.6.1.4.1.2011.6.139.2.6.4.5
		-- 1.3.6.1.4.1.2011.6.139.2.6.4.5
		hwApBatchNameList OBJECT-TYPE
			SYNTAX OCTET STRING
			MAX-ACCESS read-only
			STATUS current
			DESCRIPTION
				"The actual AP names in batch operation. Each AP name is divided
				by '?'. "
			::= { hwApBatchInfo 5 }

--    1.3.6.1.4.1.2011.6.139.2.6.5
-- 1.3.6.1.4.1.2011.6.139.2.6.5
-- 1.3.6.1.4.1.2011.6.139.2.6.5
		-- 1.3.6.1.4.1.2011.6.139.2.6.5
		hwApPing OBJECT IDENTIFIER ::= { hwApObjects 5 }

--    1.3.6.1.4.1.2011.6.139.2.6.5.1
-- 1.3.6.1.4.1.2011.6.139.2.6.5.1
-- 1.3.6.1.4.1.2011.6.139.2.6.5.1
		-- 1.3.6.1.4.1.2011.6.139.2.6.5.1
		hwApPingIndex OBJECT-TYPE
			SYNTAX Integer32
			MAX-ACCESS read-write
			STATUS current
			DESCRIPTION
				"AP's index in AP ping operation."
			::= { hwApPing 1 }

--    1.3.6.1.4.1.2011.6.139.2.6.5.2
-- 1.3.6.1.4.1.2011.6.139.2.6.5.2
-- 1.3.6.1.4.1.2011.6.139.2.6.5.2
		-- 1.3.6.1.4.1.2011.6.139.2.6.5.2
		hwApPingAddress OBJECT-TYPE
			SYNTAX OCTET STRING
			MAX-ACCESS read-write
			STATUS current
			DESCRIPTION
				"The destination host ip address or domain name."
			::= { hwApPing 2 }

--    1.3.6.1.4.1.2011.6.139.2.6.5.3
-- 1.3.6.1.4.1.2011.6.139.2.6.5.3
-- 1.3.6.1.4.1.2011.6.139.2.6.5.3
		-- 1.3.6.1.4.1.2011.6.139.2.6.5.3
		hwApPingCount OBJECT-TYPE
			SYNTAX Integer32
			MAX-ACCESS read-write
			STATUS current
			DESCRIPTION
				"Number of ping echo requests to send."
			::= { hwApPing 3 }

--    1.3.6.1.4.1.2011.6.139.2.6.5.4
-- 1.3.6.1.4.1.2011.6.139.2.6.5.4
-- 1.3.6.1.4.1.2011.6.139.2.6.5.4
		-- 1.3.6.1.4.1.2011.6.139.2.6.5.4
		hwApPingPacketSize OBJECT-TYPE
			SYNTAX Integer32
			UNITS "Bytes"
			MAX-ACCESS read-write
			STATUS current
			DESCRIPTION
				"Send packet size. Unit: Bytes"
			::= { hwApPing 4 }

--    1.3.6.1.4.1.2011.6.139.2.6.5.5
-- 1.3.6.1.4.1.2011.6.139.2.6.5.5
-- 1.3.6.1.4.1.2011.6.139.2.6.5.5
		-- 1.3.6.1.4.1.2011.6.139.2.6.5.5
		hwApPingWaitTime OBJECT-TYPE
			SYNTAX Integer32
			UNITS "ms"
			MAX-ACCESS read-write
			STATUS current
			DESCRIPTION
				"The waiting time between two packets. Unit: ms"
			::= { hwApPing 5 }

--    1.3.6.1.4.1.2011.6.139.2.6.5.6
-- 1.3.6.1.4.1.2011.6.139.2.6.5.6
-- 1.3.6.1.4.1.2011.6.139.2.6.5.6
		-- 1.3.6.1.4.1.2011.6.139.2.6.5.6
		hwApPingTimeOut OBJECT-TYPE
			SYNTAX Integer32
			UNITS "ms"
			MAX-ACCESS read-write
			STATUS current
			DESCRIPTION
				"Timeout in milliseconds to wait for each reply. Unit: ms"
			::= { hwApPing 6 }

--    1.3.6.1.4.1.2011.6.139.2.6.5.7
-- 1.3.6.1.4.1.2011.6.139.2.6.5.7
-- 1.3.6.1.4.1.2011.6.139.2.6.5.7
		-- 1.3.6.1.4.1.2011.6.139.2.6.5.7
		hwApPingResultSuccessCount OBJECT-TYPE
			SYNTAX Integer32
			MAX-ACCESS read-only
			STATUS current
			DESCRIPTION
				"Success count in the recent ping operation."
			::= { hwApPing 7 }

--    1.3.6.1.4.1.2011.6.139.2.6.5.8
-- 1.3.6.1.4.1.2011.6.139.2.6.5.8
-- 1.3.6.1.4.1.2011.6.139.2.6.5.8
		-- 1.3.6.1.4.1.2011.6.139.2.6.5.8
		hwApPingResultFailureCount OBJECT-TYPE
			SYNTAX Integer32
			MAX-ACCESS read-only
			STATUS current
			DESCRIPTION
				"Failure count in the recent ping operation."
			::= { hwApPing 8 }

--    1.3.6.1.4.1.2011.6.139.2.6.5.9
-- 1.3.6.1.4.1.2011.6.139.2.6.5.9
-- 1.3.6.1.4.1.2011.6.139.2.6.5.9
		-- 1.3.6.1.4.1.2011.6.139.2.6.5.9
		hwApPingResultAverageResponseTime OBJECT-TYPE
			SYNTAX Integer32
			UNITS "ms"
			MAX-ACCESS read-only
			STATUS current
			DESCRIPTION
				"Average response time in the recent ping operation."
			::= { hwApPing 9 }

--    1.3.6.1.4.1.2011.6.139.2.6.5.10
-- 1.3.6.1.4.1.2011.6.139.2.6.5.10
-- 1.3.6.1.4.1.2011.6.139.2.6.5.10
		-- 1.3.6.1.4.1.2011.6.139.2.6.5.10
		hwApPingResultMinimumResponseTime OBJECT-TYPE
			SYNTAX Integer32
			UNITS "ms"
			MAX-ACCESS read-only
			STATUS current
			DESCRIPTION
				"Minimum response time in the recent ping operation."
			::= { hwApPing 10 }

--    1.3.6.1.4.1.2011.6.139.2.6.5.11
-- 1.3.6.1.4.1.2011.6.139.2.6.5.11
-- 1.3.6.1.4.1.2011.6.139.2.6.5.11
		-- 1.3.6.1.4.1.2011.6.139.2.6.5.11
		hwApPingResultMaximumResponseTime OBJECT-TYPE
			SYNTAX Integer32
			UNITS "ms"
			MAX-ACCESS read-only
			STATUS current
			DESCRIPTION
				"Maximum response time in the recent ping operation."
			::= { hwApPing 11 }

--   1.3.6.1.4.1.2011.6.139.2.6.5.12
-- 1.3.6.1.4.1.2011.6.139.2.6.5.12
		-- 1.3.6.1.4.1.2011.6.139.2.6.5.12
		hwApPingApMac OBJECT-TYPE
			SYNTAX MacAddress
			MAX-ACCESS read-write
			STATUS current
			DESCRIPTION
				"Description."
			::= { hwApPing 12 }

		-- 1.3.6.1.4.1.2011.6.139.2.6.5.13
		hwApPingResultFlag OBJECT-TYPE
			SYNTAX INTEGER
				{
				false(1),
				true(2)
				}
			MAX-ACCESS read-only
			STATUS current
			DESCRIPTION
				"Description."
			::= { hwApPing 13 }


--     1.3.6.1.4.1.2011.6.139.2.6.6
-- 1.3.6.1.4.1.2011.6.139.2.6.6
-- 1.3.6.1.4.1.2011.6.139.2.6.6
-- 1.3.6.1.4.1.2011.6.139.2.6.6
		-- 1.3.6.1.4.1.2011.6.139.2.6.6
		hwApPerformanceStatTable OBJECT-TYPE
			SYNTAX SEQUENCE OF HwApPerformanceStatEntry
			MAX-ACCESS not-accessible
			STATUS current
			DESCRIPTION
				"Huawei AP performance statistic table. The index of this table is
				hwApIndex in table hwApTable."
			::= { hwApObjects 6 }

--    1.3.6.1.4.1.2011.6.139.2.6.6.1
-- 1.3.6.1.4.1.2011.6.139.2.6.6.1
-- 1.3.6.1.4.1.2011.6.139.2.6.6.1
		-- 1.3.6.1.4.1.2011.6.139.2.6.6.1
		hwApPerformanceStatEntry OBJECT-TYPE
			SYNTAX HwApPerformanceStatEntry
			MAX-ACCESS not-accessible
			STATUS current
			DESCRIPTION
				"Huawei AP performance statistic table entry.The index of this table
				is hwApIndex in table hwApTable."
			INDEX { hwApIndex }
			::= { hwApPerformanceStatTable 1 }

		HwApPerformanceStatEntry ::=
			SEQUENCE {
				hwApMemoryUseRate
					Integer32,
				hwApCpuUseRate
					Integer32,
				hwApFlashFreeSize
					Integer32,
				hwApTemperature
					Integer32,
				hwApOnlineUserNum
					Integer32,
				hwApUpPortSpeed
					Integer32,
				hwApUpPortRecvFrames
					Unsigned32,
				hwApUpPortRecvRightFrames
					Unsigned32,
				hwApUpPortRecvErrorFrames
					Unsigned32,
				hwApUpPortSendFrames
					Unsigned32,
				hwApUpPortRecvBytes
					Unsigned32,
				hwApUpPortSendBytes
					Unsigned32,
				hwAPUpPortPER
					Integer32,
				hwAPWirelessUpPortTraffic
					Unsigned32,
				hwAPUpPortTraffic
					Unsigned32,
				hwApAirportSendDropFrames
					Unsigned32,
				hwApEthportRecvDropFrames
					Unsigned32,
				hwApAirportUpTraffic
					OCTET STRING,
				hwApAirportDwTraffic
					OCTET STRING,
				hwApEthportDwTraffic
					OCTET STRING,
				hwApEthportUpTraffic
					OCTET STRING,
				hwApAirportRecvDropPacket
					Unsigned32,
				hwApAirportRecvErrorPacket
					Unsigned32,
				hwApEthportRecvUnicastPacket
					Unsigned32,
				hwApEthportRecvNonUnicastPacket
					Unsigned32,
				hwApEthportSendUnicastPacket
					Unsigned32,
				hwApEthportSendNonUnicastPacket
					Unsigned32,
				hwApAvgRCPUUseRate
					Integer32,
				hwApAvgRMemoryUseRate
					Integer32,
				hwEthportSendDropFrames
					Counter64,
				hwEthportSendErrorFrames
					Counter64,
				hwEthportUpDwnTimes
					Unsigned32,
				hwApAirportRecvUnicastFrames
					Counter64,
				hwApEthportRecvUnknownFrames
					Counter64,
				hwApEthportUpRate
					Integer32,
				hwApEthportDownRate
					Integer32,
				hwApUpPortRecvFrames64Bits
					Counter64,
				hwApUpPortRecvRightFrames64Bits
					Counter64,
				hwApUpPortRecvErrorFrames64Bits
					Counter64,
				hwApUpPortSendFrames64Bits
					Counter64,
				hwApUpPortRecvBytes64Bits
					Counter64,
				hwApUpPortSendBytes64Bits
					Counter64,
				hwAPWirelessUpPortTraffic64Bits
					Counter64,
				hwAPUpPortTraffic64Bits
					Counter64,
				hwApAirportSendDropFrames64Bits
					Counter64,
				hwApEthportRecvDropFrames64Bits
					Counter64,
				hwApAirportRecvDropPacket64Bits
					Counter64,
				hwApAirportRecvErrorPacket64Bits
					Counter64,
				hwApEthportRecvUnicastPacket64Bits
					Counter64,
				hwApEthportRecvNonUnicastPacket64Bits
					Counter64,
				hwApEthportSendUnicastPacket64Bits
					Counter64,
				hwApEthportSendNonUnicastPacket64Bits
					Counter64
			 }

--    1.3.6.1.4.1.2011.6.139.2.6.6.1.1
-- 1.3.6.1.4.1.2011.6.139.2.6.6.1.1
-- 1.3.6.1.4.1.2011.6.139.2.6.6.1.1
		-- 1.3.6.1.4.1.2011.6.139.2.6.6.1.1
		hwApMemoryUseRate OBJECT-TYPE
			SYNTAX Integer32
			UNITS "%"
			MAX-ACCESS read-only
			STATUS current
			DESCRIPTION
				"The use rate of AP's memory. Unit: %"
			::= { hwApPerformanceStatEntry 1 }

--    1.3.6.1.4.1.2011.6.139.2.6.6.1.2
-- 1.3.6.1.4.1.2011.6.139.2.6.6.1.2
-- 1.3.6.1.4.1.2011.6.139.2.6.6.1.2
		-- 1.3.6.1.4.1.2011.6.139.2.6.6.1.2
		hwApCpuUseRate OBJECT-TYPE
			SYNTAX Integer32
			UNITS "%"
			MAX-ACCESS read-only
			STATUS current
			DESCRIPTION
				"The use rate of AP's cpu. Unit: %"
			::= { hwApPerformanceStatEntry 2 }

--    1.3.6.1.4.1.2011.6.139.2.6.6.1.3
-- 1.3.6.1.4.1.2011.6.139.2.6.6.1.3
-- 1.3.6.1.4.1.2011.6.139.2.6.6.1.3
		-- 1.3.6.1.4.1.2011.6.139.2.6.6.1.3
		hwApFlashFreeSize OBJECT-TYPE
			SYNTAX Integer32
			UNITS "kb"
			MAX-ACCESS read-only
			STATUS current
			DESCRIPTION
				"The free size of AP's flash. Unit: kb"
			::= { hwApPerformanceStatEntry 3 }

--    1.3.6.1.4.1.2011.6.139.2.6.6.1.4
-- 1.3.6.1.4.1.2011.6.139.2.6.6.1.4
-- 1.3.6.1.4.1.2011.6.139.2.6.6.1.4
		-- 1.3.6.1.4.1.2011.6.139.2.6.6.1.4
		hwApTemperature OBJECT-TYPE
			SYNTAX Integer32
			UNITS "C"
			MAX-ACCESS read-only
			STATUS current
			DESCRIPTION
				"The temperature of AP. Unit: C"
			::= { hwApPerformanceStatEntry 4 }

--    1.3.6.1.4.1.2011.6.139.2.6.6.1.5
-- 1.3.6.1.4.1.2011.6.139.2.6.6.1.5
-- 1.3.6.1.4.1.2011.6.139.2.6.6.1.5
		-- 1.3.6.1.4.1.2011.6.139.2.6.6.1.5
		hwApOnlineUserNum OBJECT-TYPE
			SYNTAX Integer32
			MAX-ACCESS read-only
			STATUS current
			DESCRIPTION
				"The online user number of AP."
			::= { hwApPerformanceStatEntry 5 }

--    1.3.6.1.4.1.2011.6.139.2.6.6.1.6
-- 1.3.6.1.4.1.2011.6.139.2.6.6.1.6
-- 1.3.6.1.4.1.2011.6.139.2.6.6.1.6
		-- 1.3.6.1.4.1.2011.6.139.2.6.6.1.6
		hwApUpPortSpeed OBJECT-TYPE
			SYNTAX Integer32
			UNITS "Mbps"
			MAX-ACCESS read-only
			STATUS current
			DESCRIPTION
				"AP up port's speed. Unit: Mbps."
			::= { hwApPerformanceStatEntry 6 }

--    1.3.6.1.4.1.2011.6.139.2.6.6.1.7
-- 1.3.6.1.4.1.2011.6.139.2.6.6.1.7
-- 1.3.6.1.4.1.2011.6.139.2.6.6.1.7
		-- 1.3.6.1.4.1.2011.6.139.2.6.6.1.7
		hwApUpPortRecvFrames OBJECT-TYPE
			SYNTAX Unsigned32
			MAX-ACCESS read-only
			STATUS current
			DESCRIPTION
				"AP up port received frames."
			::= { hwApPerformanceStatEntry 7 }

--    1.3.6.1.4.1.2011.6.139.2.6.6.1.8
-- 1.3.6.1.4.1.2011.6.139.2.6.6.1.8
-- 1.3.6.1.4.1.2011.6.139.2.6.6.1.8
		-- 1.3.6.1.4.1.2011.6.139.2.6.6.1.8
		hwApUpPortRecvRightFrames OBJECT-TYPE
			SYNTAX Unsigned32
			MAX-ACCESS read-only
			STATUS current
			DESCRIPTION
				"AP up port received correct frames."
			::= { hwApPerformanceStatEntry 8 }

--    1.3.6.1.4.1.2011.6.139.2.6.6.1.9
-- 1.3.6.1.4.1.2011.6.139.2.6.6.1.9
-- 1.3.6.1.4.1.2011.6.139.2.6.6.1.9
		-- 1.3.6.1.4.1.2011.6.139.2.6.6.1.9
		hwApUpPortRecvErrorFrames OBJECT-TYPE
			SYNTAX Unsigned32
			MAX-ACCESS read-only
			STATUS current
			DESCRIPTION
				"AP up port received wrong frames."
			::= { hwApPerformanceStatEntry 9 }

--    1.3.6.1.4.1.2011.6.139.2.6.6.1.10
-- 1.3.6.1.4.1.2011.6.139.2.6.6.1.10
-- 1.3.6.1.4.1.2011.6.139.2.6.6.1.10
		-- 1.3.6.1.4.1.2011.6.139.2.6.6.1.10
		hwApUpPortSendFrames OBJECT-TYPE
			SYNTAX Unsigned32
			MAX-ACCESS read-only
			STATUS current
			DESCRIPTION
				"AP up port side sent frames."
			::= { hwApPerformanceStatEntry 10 }

--    1.3.6.1.4.1.2011.6.139.2.6.6.1.11
-- 1.3.6.1.4.1.2011.6.139.2.6.6.1.11
-- 1.3.6.1.4.1.2011.6.139.2.6.6.1.11
		-- 1.3.6.1.4.1.2011.6.139.2.6.6.1.11
		hwApUpPortRecvBytes OBJECT-TYPE
			SYNTAX Unsigned32
			MAX-ACCESS read-only
			STATUS current
			DESCRIPTION
				"AP up port received Bytes."
			::= { hwApPerformanceStatEntry 11 }

--    1.3.6.1.4.1.2011.6.139.2.6.6.1.12
-- 1.3.6.1.4.1.2011.6.139.2.6.6.1.12
-- 1.3.6.1.4.1.2011.6.139.2.6.6.1.12
		-- 1.3.6.1.4.1.2011.6.139.2.6.6.1.12
		hwApUpPortSendBytes OBJECT-TYPE
			SYNTAX Unsigned32
			MAX-ACCESS read-only
			STATUS current
			DESCRIPTION
				"AP up port sent Bytes."
			::= { hwApPerformanceStatEntry 12 }

--    1.3.6.1.4.1.2011.6.139.2.6.6.1.13
-- 1.3.6.1.4.1.2011.6.139.2.6.6.1.13
-- 1.3.6.1.4.1.2011.6.139.2.6.6.1.13
		-- 1.3.6.1.4.1.2011.6.139.2.6.6.1.13
		hwAPUpPortPER OBJECT-TYPE
			SYNTAX Integer32
			UNITS "%"
			MAX-ACCESS read-only
			STATUS current
			DESCRIPTION
				"The PER of AP's Up-Port.Unit: %
				"
			::= { hwApPerformanceStatEntry 13 }

--    1.3.6.1.4.1.2011.6.139.2.6.6.1.14
-- 1.3.6.1.4.1.2011.6.139.2.6.6.1.14
-- 1.3.6.1.4.1.2011.6.139.2.6.6.1.14
		-- 1.3.6.1.4.1.2011.6.139.2.6.6.1.14
		hwAPWirelessUpPortTraffic OBJECT-TYPE
			SYNTAX Unsigned32
			MAX-ACCESS read-only
			STATUS current
			DESCRIPTION
				"The traffic of AP's Wireless-Up-Port."
			::= { hwApPerformanceStatEntry 14 }

--    1.3.6.1.4.1.2011.6.139.2.6.6.1.15
-- 1.3.6.1.4.1.2011.6.139.2.6.6.1.15
-- 1.3.6.1.4.1.2011.6.139.2.6.6.1.15
		-- 1.3.6.1.4.1.2011.6.139.2.6.6.1.15
		hwAPUpPortTraffic OBJECT-TYPE
			SYNTAX Unsigned32
			MAX-ACCESS read-only
			STATUS current
			DESCRIPTION
				"The traffic of AP's Up-Port."
			::= { hwApPerformanceStatEntry 15 }

--   1.3.6.1.4.1.2011.6.139.2.6.6.1.16
-- 1.3.6.1.4.1.2011.6.139.2.6.6.1.16
		-- 1.3.6.1.4.1.2011.6.139.2.6.6.1.16
		hwApAirportSendDropFrames OBJECT-TYPE
			SYNTAX Unsigned32
			MAX-ACCESS read-only
			STATUS current
			DESCRIPTION
				"Description."
			::= { hwApPerformanceStatEntry 16 }

--   1.3.6.1.4.1.2011.6.139.2.6.6.1.17
-- 1.3.6.1.4.1.2011.6.139.2.6.6.1.17
		-- 1.3.6.1.4.1.2011.6.139.2.6.6.1.17
		hwApEthportRecvDropFrames OBJECT-TYPE
			SYNTAX Unsigned32
			MAX-ACCESS read-only
			STATUS current
			DESCRIPTION
				"Description."
			::= { hwApPerformanceStatEntry 17 }

--   1.3.6.1.4.1.2011.6.139.2.6.6.1.18
-- 1.3.6.1.4.1.2011.6.139.2.6.6.1.18
		-- 1.3.6.1.4.1.2011.6.139.2.6.6.1.18
		hwApAirportUpTraffic OBJECT-TYPE
			SYNTAX OCTET STRING
			MAX-ACCESS read-only
			STATUS current
			DESCRIPTION
				"Description."
			::= { hwApPerformanceStatEntry 18 }

--   1.3.6.1.4.1.2011.6.139.2.6.6.1.19
-- 1.3.6.1.4.1.2011.6.139.2.6.6.1.19
		-- 1.3.6.1.4.1.2011.6.139.2.6.6.1.19
		hwApAirportDwTraffic OBJECT-TYPE
			SYNTAX OCTET STRING
			MAX-ACCESS read-only
			STATUS current
			DESCRIPTION
				"Description."
			::= { hwApPerformanceStatEntry 19 }

--   1.3.6.1.4.1.2011.6.139.2.6.6.1.20
-- 1.3.6.1.4.1.2011.6.139.2.6.6.1.20
		-- 1.3.6.1.4.1.2011.6.139.2.6.6.1.20
		hwApEthportDwTraffic OBJECT-TYPE
			SYNTAX OCTET STRING
			MAX-ACCESS read-only
			STATUS current
			DESCRIPTION
				"Description."
			::= { hwApPerformanceStatEntry 20 }

--   1.3.6.1.4.1.2011.6.139.2.6.6.1.21
-- 1.3.6.1.4.1.2011.6.139.2.6.6.1.21
		-- 1.3.6.1.4.1.2011.6.139.2.6.6.1.21
		hwApEthportUpTraffic OBJECT-TYPE
			SYNTAX OCTET STRING
			MAX-ACCESS read-only
			STATUS current
			DESCRIPTION
				"Description."
			::= { hwApPerformanceStatEntry 21 }

--   1.3.6.1.4.1.2011.6.139.2.6.6.1.22
-- 1.3.6.1.4.1.2011.6.139.2.6.6.1.22
		-- 1.3.6.1.4.1.2011.6.139.2.6.6.1.22
		hwApAirportRecvDropPacket OBJECT-TYPE
			SYNTAX Unsigned32
			MAX-ACCESS read-only
			STATUS current
			DESCRIPTION
				"Description."
			::= { hwApPerformanceStatEntry 22 }

--   1.3.6.1.4.1.2011.6.139.2.6.6.1.23
-- 1.3.6.1.4.1.2011.6.139.2.6.6.1.23
		-- 1.3.6.1.4.1.2011.6.139.2.6.6.1.23
		hwApAirportRecvErrorPacket OBJECT-TYPE
			SYNTAX Unsigned32
			MAX-ACCESS read-only
			STATUS current
			DESCRIPTION
				"Description."
			::= { hwApPerformanceStatEntry 23 }

--   1.3.6.1.4.1.2011.6.139.2.6.6.1.24
-- 1.3.6.1.4.1.2011.6.139.2.6.6.1.24
		-- 1.3.6.1.4.1.2011.6.139.2.6.6.1.24
		hwApEthportRecvUnicastPacket OBJECT-TYPE
			SYNTAX Unsigned32
			MAX-ACCESS read-only
			STATUS current
			DESCRIPTION
				"Description."
			::= { hwApPerformanceStatEntry 24 }

--   1.3.6.1.4.1.2011.6.139.2.6.6.1.25
-- 1.3.6.1.4.1.2011.6.139.2.6.6.1.25
		-- 1.3.6.1.4.1.2011.6.139.2.6.6.1.25
		hwApEthportRecvNonUnicastPacket OBJECT-TYPE
			SYNTAX Unsigned32
			MAX-ACCESS read-only
			STATUS current
			DESCRIPTION
				"Description."
			::= { hwApPerformanceStatEntry 25 }

--   1.3.6.1.4.1.2011.6.139.2.6.6.1.26
-- 1.3.6.1.4.1.2011.6.139.2.6.6.1.26
		-- 1.3.6.1.4.1.2011.6.139.2.6.6.1.26
		hwApEthportSendUnicastPacket OBJECT-TYPE
			SYNTAX Unsigned32
			MAX-ACCESS read-only
			STATUS current
			DESCRIPTION
				"Description."
			::= { hwApPerformanceStatEntry 26 }

--   1.3.6.1.4.1.2011.6.139.2.6.6.1.27
-- 1.3.6.1.4.1.2011.6.139.2.6.6.1.27
		-- 1.3.6.1.4.1.2011.6.139.2.6.6.1.27
		hwApEthportSendNonUnicastPacket OBJECT-TYPE
			SYNTAX Unsigned32
			MAX-ACCESS read-only
			STATUS current
			DESCRIPTION
				"Description."
			::= { hwApPerformanceStatEntry 27 }

--   1.3.6.1.4.1.2011.6.139.2.6.6.1.28
-- 1.3.6.1.4.1.2011.6.139.2.6.6.1.28
		-- 1.3.6.1.4.1.2011.6.139.2.6.6.1.28
		hwApAvgRCPUUseRate OBJECT-TYPE
			SYNTAX Integer32
			MAX-ACCESS read-only
			STATUS current
			DESCRIPTION
				"Description."
			::= { hwApPerformanceStatEntry 28 }

--   1.3.6.1.4.1.2011.6.139.2.6.6.1.29
-- 1.3.6.1.4.1.2011.6.139.2.6.6.1.29
		-- 1.3.6.1.4.1.2011.6.139.2.6.6.1.29
		hwApAvgRMemoryUseRate OBJECT-TYPE
			SYNTAX Integer32
			MAX-ACCESS read-only
			STATUS current
			DESCRIPTION
				"Description."
			::= { hwApPerformanceStatEntry 29 }

--   1.3.6.1.4.1.2011.6.139.2.6.6.1.30
-- 1.3.6.1.4.1.2011.6.139.2.6.6.1.30
		-- 1.3.6.1.4.1.2011.6.139.2.6.6.1.30
		hwEthportSendDropFrames OBJECT-TYPE
			SYNTAX Counter64
			MAX-ACCESS read-only
			STATUS current
			DESCRIPTION
				"Description."
			::= { hwApPerformanceStatEntry 30 }

--   1.3.6.1.4.1.2011.6.139.2.6.6.1.31
-- 1.3.6.1.4.1.2011.6.139.2.6.6.1.31
		-- 1.3.6.1.4.1.2011.6.139.2.6.6.1.31
		hwEthportSendErrorFrames OBJECT-TYPE
			SYNTAX Counter64
			MAX-ACCESS read-only
			STATUS current
			DESCRIPTION
				"Description."
			::= { hwApPerformanceStatEntry 31 }

--   1.3.6.1.4.1.2011.6.139.2.6.6.1.32
-- 1.3.6.1.4.1.2011.6.139.2.6.6.1.32
		-- 1.3.6.1.4.1.2011.6.139.2.6.6.1.32
		hwEthportUpDwnTimes OBJECT-TYPE
			SYNTAX Unsigned32
			MAX-ACCESS read-only
			STATUS current
			DESCRIPTION
				"Description."
			::= { hwApPerformanceStatEntry 32 }

--   1.3.6.1.4.1.2011.6.139.2.6.6.1.33
-- 1.3.6.1.4.1.2011.6.139.2.6.6.1.33
		-- 1.3.6.1.4.1.2011.6.139.2.6.6.1.33
		hwApAirportRecvUnicastFrames OBJECT-TYPE
			SYNTAX Counter64
			MAX-ACCESS read-only
			STATUS current
			DESCRIPTION
				"Description."
			::= { hwApPerformanceStatEntry 33 }

--   1.3.6.1.4.1.2011.6.139.2.6.6.1.34
-- 1.3.6.1.4.1.2011.6.139.2.6.6.1.34
		-- 1.3.6.1.4.1.2011.6.139.2.6.6.1.34
		hwApEthportRecvUnknownFrames OBJECT-TYPE
			SYNTAX Counter64
			MAX-ACCESS read-only
			STATUS current
			DESCRIPTION
				"Description."
			::= { hwApPerformanceStatEntry 34 }

--  1.3.6.1.4.1.2011.6.139.2.6.6.1.35
		-- 1.3.6.1.4.1.2011.6.139.2.6.6.1.35
		hwApEthportUpRate OBJECT-TYPE
			SYNTAX Integer32
			MAX-ACCESS read-only
			STATUS current
			DESCRIPTION
				"Description."
			::= { hwApPerformanceStatEntry 35 }

--  1.3.6.1.4.1.2011.6.139.2.6.6.1.36
		-- 1.3.6.1.4.1.2011.6.139.2.6.6.1.36
		hwApEthportDownRate OBJECT-TYPE
			SYNTAX Integer32
			MAX-ACCESS read-only
			STATUS current
			DESCRIPTION
				"Description."
			::= { hwApPerformanceStatEntry 36 }


		-- 1.3.6.1.4.1.2011.6.139.2.6.6.1.37
		hwApUpPortRecvFrames64Bits OBJECT-TYPE
			SYNTAX Counter64
			MAX-ACCESS read-only
			STATUS current
			DESCRIPTION
				"Description."
			::= { hwApPerformanceStatEntry 37 }


		-- 1.3.6.1.4.1.2011.6.139.2.6.6.1.38
		hwApUpPortRecvRightFrames64Bits OBJECT-TYPE
			SYNTAX Counter64
			MAX-ACCESS read-only
			STATUS current
			DESCRIPTION
				"Description."
			::= { hwApPerformanceStatEntry 38 }


		-- 1.3.6.1.4.1.2011.6.139.2.6.6.1.39
		hwApUpPortRecvErrorFrames64Bits OBJECT-TYPE
			SYNTAX Counter64
			MAX-ACCESS read-only
			STATUS current
			DESCRIPTION
				"Description."
			::= { hwApPerformanceStatEntry 39 }


		-- 1.3.6.1.4.1.2011.6.139.2.6.6.1.40
		hwApUpPortSendFrames64Bits OBJECT-TYPE
			SYNTAX Counter64
			MAX-ACCESS read-only
			STATUS current
			DESCRIPTION
				"Description."
			::= { hwApPerformanceStatEntry 40 }


		-- 1.3.6.1.4.1.2011.6.139.2.6.6.1.41
		hwApUpPortRecvBytes64Bits OBJECT-TYPE
			SYNTAX Counter64
			MAX-ACCESS read-only
			STATUS current
			DESCRIPTION
				"Description."
			::= { hwApPerformanceStatEntry 41 }


		-- 1.3.6.1.4.1.2011.6.139.2.6.6.1.42
		hwApUpPortSendBytes64Bits OBJECT-TYPE
			SYNTAX Counter64
			MAX-ACCESS read-only
			STATUS current
			DESCRIPTION
				"Description."
			::= { hwApPerformanceStatEntry 42 }


		-- 1.3.6.1.4.1.2011.6.139.2.6.6.1.43
		hwAPWirelessUpPortTraffic64Bits OBJECT-TYPE
			SYNTAX Counter64
			MAX-ACCESS read-only
			STATUS current
			DESCRIPTION
				"Description."
			::= { hwApPerformanceStatEntry 43 }


		-- 1.3.6.1.4.1.2011.6.139.2.6.6.1.44
		hwAPUpPortTraffic64Bits OBJECT-TYPE
			SYNTAX Counter64
			MAX-ACCESS read-only
			STATUS current
			DESCRIPTION
				"Description."
			::= { hwApPerformanceStatEntry 44 }


		-- 1.3.6.1.4.1.2011.6.139.2.6.6.1.45
		hwApAirportSendDropFrames64Bits OBJECT-TYPE
			SYNTAX Counter64
			MAX-ACCESS read-only
			STATUS current
			DESCRIPTION
				"Description."
			::= { hwApPerformanceStatEntry 45 }


		-- 1.3.6.1.4.1.2011.6.139.2.6.6.1.46
		hwApEthportRecvDropFrames64Bits OBJECT-TYPE
			SYNTAX Counter64
			MAX-ACCESS read-only
			STATUS current
			DESCRIPTION
				"Description."
			::= { hwApPerformanceStatEntry 46 }


		-- 1.3.6.1.4.1.2011.6.139.2.6.6.1.47
		hwApAirportRecvDropPacket64Bits OBJECT-TYPE
			SYNTAX Counter64
			MAX-ACCESS read-only
			STATUS current
			DESCRIPTION
				"Description."
			::= { hwApPerformanceStatEntry 47 }


		-- 1.3.6.1.4.1.2011.6.139.2.6.6.1.48
		hwApAirportRecvErrorPacket64Bits OBJECT-TYPE
			SYNTAX Counter64
			MAX-ACCESS read-only
			STATUS current
			DESCRIPTION
				"Description."
			::= { hwApPerformanceStatEntry 48 }


		-- 1.3.6.1.4.1.2011.6.139.2.6.6.1.49
		hwApEthportRecvUnicastPacket64Bits OBJECT-TYPE
			SYNTAX Counter64
			MAX-ACCESS read-only
			STATUS current
			DESCRIPTION
				"Description."
			::= { hwApPerformanceStatEntry 49 }


		-- 1.3.6.1.4.1.2011.6.139.2.6.6.1.50
		hwApEthportRecvNonUnicastPacket64Bits OBJECT-TYPE
			SYNTAX Counter64
			MAX-ACCESS read-only
			STATUS current
			DESCRIPTION
				"Description."
			::= { hwApPerformanceStatEntry 50 }


		-- 1.3.6.1.4.1.2011.6.139.2.6.6.1.51
		hwApEthportSendUnicastPacket64Bits OBJECT-TYPE
			SYNTAX Counter64
			MAX-ACCESS read-only
			STATUS current
			DESCRIPTION
				"Description."
			::= { hwApPerformanceStatEntry 51 }


		-- 1.3.6.1.4.1.2011.6.139.2.6.6.1.52
		hwApEthportSendNonUnicastPacket64Bits OBJECT-TYPE
			SYNTAX Counter64
			MAX-ACCESS read-only
			STATUS current
			DESCRIPTION
				"Description."
			::= { hwApPerformanceStatEntry 52 }


--    1.3.6.1.4.1.2011.6.139.2.6.7
-- 1.3.6.1.4.1.2011.6.139.2.6.7
-- 1.3.6.1.4.1.2011.6.139.2.6.7
		-- 1.3.6.1.4.1.2011.6.139.2.6.7
		hwApUnauthorizedApRecordTable OBJECT-TYPE
			SYNTAX SEQUENCE OF HwApUnauthorizedApRecordEntry
			MAX-ACCESS not-accessible
			STATUS current
			DESCRIPTION
				"Huawei unauthorized AP record table. The index of this table is
				unauthorized AP record ID. Unauthorized AP mean that AP's MAC
				address or SN is not in white list,and user doesn't confirm it in
				time."
			::= { hwApObjects 7 }

--    1.3.6.1.4.1.2011.6.139.2.6.7.1
-- 1.3.6.1.4.1.2011.6.139.2.6.7.1
-- 1.3.6.1.4.1.2011.6.139.2.6.7.1
		-- 1.3.6.1.4.1.2011.6.139.2.6.7.1
		hwApUnauthorizedApRecordEntry OBJECT-TYPE
			SYNTAX HwApUnauthorizedApRecordEntry
			MAX-ACCESS not-accessible
			STATUS current
			DESCRIPTION
				"Huawei unauthorized AP record table entry. The index of this table
				is unauthorized AP record ID. Unauthorized AP mean that AP's MAC
				address or SN is not in white list,and user doesn't confirm it in
				time."
			INDEX { hwApUnauthorizedApRecordIndex }
			::= { hwApUnauthorizedApRecordTable 1 }

		HwApUnauthorizedApRecordEntry ::=
			SEQUENCE {
				hwApUnauthorizedApRecordIndex
					Integer32,
				hwApUnauthorizedApType
					OCTET STRING,
				hwApUnauthorizedApMacAddress
					MacAddress,
				hwApUnauthorizedApSn
					OCTET STRING,
				hwApUnauthorizedApIpAddress
					IpAddress,
				hwApUnauthorizedApRecordTime
					DateAndTime
			 }

--    1.3.6.1.4.1.2011.6.139.2.6.7.1.1
-- 1.3.6.1.4.1.2011.6.139.2.6.7.1.1
-- 1.3.6.1.4.1.2011.6.139.2.6.7.1.1
		-- 1.3.6.1.4.1.2011.6.139.2.6.7.1.1
		hwApUnauthorizedApRecordIndex OBJECT-TYPE
			SYNTAX Integer32
			MAX-ACCESS not-accessible
			STATUS current
			DESCRIPTION
				"Unauthorized AP record Index."
			::= { hwApUnauthorizedApRecordEntry 1 }

--    1.3.6.1.4.1.2011.6.139.2.6.7.1.2
-- 1.3.6.1.4.1.2011.6.139.2.6.7.1.2
-- 1.3.6.1.4.1.2011.6.139.2.6.7.1.2
		-- 1.3.6.1.4.1.2011.6.139.2.6.7.1.2
		hwApUnauthorizedApType OBJECT-TYPE
			SYNTAX OCTET STRING
			MAX-ACCESS read-only
			STATUS current
			DESCRIPTION
				"Unauthorized AP's type."
			::= { hwApUnauthorizedApRecordEntry 2 }

--    1.3.6.1.4.1.2011.6.139.2.6.7.1.3
-- 1.3.6.1.4.1.2011.6.139.2.6.7.1.3
-- 1.3.6.1.4.1.2011.6.139.2.6.7.1.3
		-- 1.3.6.1.4.1.2011.6.139.2.6.7.1.3
		hwApUnauthorizedApMacAddress OBJECT-TYPE
			SYNTAX MacAddress
			MAX-ACCESS read-only
			STATUS current
			DESCRIPTION
				"Unauthorized AP's MAC address."
			::= { hwApUnauthorizedApRecordEntry 3 }

--    1.3.6.1.4.1.2011.6.139.2.6.7.1.4
-- 1.3.6.1.4.1.2011.6.139.2.6.7.1.4
-- 1.3.6.1.4.1.2011.6.139.2.6.7.1.4
		-- 1.3.6.1.4.1.2011.6.139.2.6.7.1.4
		hwApUnauthorizedApSn OBJECT-TYPE
			SYNTAX OCTET STRING
			MAX-ACCESS read-only
			STATUS current
			DESCRIPTION
				"Unauthorized AP's SN."
			::= { hwApUnauthorizedApRecordEntry 4 }

--    1.3.6.1.4.1.2011.6.139.2.6.7.1.5
-- 1.3.6.1.4.1.2011.6.139.2.6.7.1.5
-- 1.3.6.1.4.1.2011.6.139.2.6.7.1.5
		-- 1.3.6.1.4.1.2011.6.139.2.6.7.1.5
		hwApUnauthorizedApIpAddress OBJECT-TYPE
			SYNTAX IpAddress
			MAX-ACCESS read-only
			STATUS current
			DESCRIPTION
				"Unauthorized AP's ip address."
			::= { hwApUnauthorizedApRecordEntry 5 }

--    1.3.6.1.4.1.2011.6.139.2.6.7.1.6
-- 1.3.6.1.4.1.2011.6.139.2.6.7.1.6
-- 1.3.6.1.4.1.2011.6.139.2.6.7.1.6
		-- 1.3.6.1.4.1.2011.6.139.2.6.7.1.6
		hwApUnauthorizedApRecordTime OBJECT-TYPE
			SYNTAX DateAndTime
			MAX-ACCESS read-only
			STATUS current
			DESCRIPTION
				"Record's time."
			::= { hwApUnauthorizedApRecordEntry 6 }

--   1.3.6.1.4.1.2011.6.139.2.6.8
-- 1.3.6.1.4.1.2011.6.139.2.6.8
		-- 1.3.6.1.4.1.2011.6.139.2.6.8
		hwApParaStatisticTable OBJECT-TYPE
			SYNTAX SEQUENCE OF HwApParaStatisticEntry
			MAX-ACCESS not-accessible
			STATUS current
			DESCRIPTION
				"Description."
			::= { hwApObjects 8 }

--   1.3.6.1.4.1.2011.6.139.2.6.8.1
-- 1.3.6.1.4.1.2011.6.139.2.6.8.1
		-- 1.3.6.1.4.1.2011.6.139.2.6.8.1
		hwApParaStatisticEntry OBJECT-TYPE
			SYNTAX HwApParaStatisticEntry
			MAX-ACCESS not-accessible
			STATUS current
			DESCRIPTION
				"Description."
			INDEX { hwApMac }
			::= { hwApParaStatisticTable 1 }

		HwApParaStatisticEntry ::=
			SEQUENCE {
				hwApStaAveSignalStrength
					Integer32
			 }

--   1.3.6.1.4.1.2011.6.139.2.6.8.1.1
-- 1.3.6.1.4.1.2011.6.139.2.6.8.1.1
		-- 1.3.6.1.4.1.2011.6.139.2.6.8.1.1
		hwApStaAveSignalStrength OBJECT-TYPE
			SYNTAX Integer32
			MAX-ACCESS read-only
			STATUS current
			DESCRIPTION
				"Description."
			::= { hwApParaStatisticEntry 1 }

--   1.3.6.1.4.1.2011.6.139.2.6.9
-- 1.3.6.1.4.1.2011.6.139.2.6.9
		-- 1.3.6.1.4.1.2011.6.139.2.6.9
		hwMacApTable OBJECT-TYPE
			SYNTAX SEQUENCE OF HwMacApEntry
			MAX-ACCESS not-accessible
			STATUS current
			DESCRIPTION
				"Description."
			::= { hwApObjects 9 }

--   1.3.6.1.4.1.2011.6.139.2.6.9.1
-- 1.3.6.1.4.1.2011.6.139.2.6.9.1
		-- 1.3.6.1.4.1.2011.6.139.2.6.9.1
		hwMacApEntry OBJECT-TYPE
			SYNTAX HwMacApEntry
			MAX-ACCESS not-accessible
			STATUS current
			DESCRIPTION
				"Description."
			INDEX { hwMacApMac }
			::= { hwMacApTable 1 }

		HwMacApEntry ::=
			SEQUENCE {
				hwMacApMac
					MacAddress,
				hwMacApIndex
					Integer32,
				hwMacApUsedType
					OCTET STRING,
				hwMacApUsedProfileName
					OCTET STRING,
				hwMacApUsedRegionIndex
					Integer32,
				hwMacApSn
					OCTET STRING,
				hwMacApSysName
					OCTET STRING,
				hwMacApRunState
					INTEGER,
				hwMacApSoftwareVersion
					OCTET STRING,
				hwMacApHardwareVersion
					OCTET STRING,
				hwMacApCpuType
					OCTET STRING,
				hwMacApCpufrequency
					Integer32,
				hwMacApMemoryType
					OCTET STRING,
				hwMacApDomain
					OCTET STRING,
				hwMacApIpAddress
					IpAddress,
				hwMacApIpNetMask
					IpAddress,
				hwMacApGatewayIp
					IpAddress,
				hwMacApMemorySize
					Integer32,
				hwMacApFlashSize
					Integer32,
				hwMacApRunTime
					Unsigned32,
				hwMacApUpEthPortSpeed
					INTEGER,
				hwMacApUpEthPortSpeedMode
					INTEGER,
				hwMacApUpEthPortDuplex
					INTEGER,
				hwMacApUpEthPortDuplexMode
					INTEGER,
				hwMacApAdminOper
					INTEGER,
				hwMacApRowstatus
					RowStatus,
				hwMacApPerformanceStatCycle
					INTEGER,
				hwMacApDNS
					IpAddress,
				hwMacApRunningMode
					INTEGER,
				hwMacApForwardMode
					INTEGER,
				hwMacApAntennaMode
					INTEGER,
				hwMacApCpuThreshold
					Integer32,
				hwMacApMemThreshold
					Integer32,
				hwMacApNEnumber
					OCTET STRING,
				hwMacApOnlineTime
					Unsigned32,
				hwMacApSysSoftwareDesc
					OCTET STRING,
				hwMacApSysHardtwareDesc
					OCTET STRING,
				hwMacApSysManufacture
					OCTET STRING,
				hwMacApSysSoftwareName
					OCTET STRING,
				hwMacApSysSoftwareVendor
					OCTET STRING,
				hwMacApManagementVlanID
					Integer32,
				hwMacApUsername
					OCTET STRING,
				hwMacApPassword
					OCTET STRING,
				hwMacApAcIP1
					IpAddress,
				hwMacApAcIP2
					IpAddress,
				hwMacApAcIP3
					IpAddress,
				hwMacApAcIP4
					IpAddress,
				hwMacApIpMode
					INTEGER,
				hwMacApLldpEnable
					INTEGER,
				hwMacApLldpManageAddr
					INTEGER,
				hwMacApLldpPortDes
					INTEGER,
				hwMacApLldpSysCab
					INTEGER,
				hwMacApLldpSysDes
					INTEGER,
				hwMacApLldpSysName
					INTEGER,
				hwMacApLldpDelay
					Integer32,
				hwMacApLldpHoldMultiplier
					Integer32,
				hwMacApLldpInterval
					Integer32,
				hwMacApLldpRestartDelay
					Integer32,
				hwMacApLldpAdminStatus
					INTEGER,
				hwMacApLldpReportInterval
					Integer32,
				hwMacApBomCode
					OCTET STRING,
				hwMacApSaveMode
					Integer32,
				hwMacApProtectAcPriority
					Integer32,
				hwMacApProtectAcIP
					IpAddress,
				hwMacApOpticalHighRxPowerThreshold
					Integer32,
				hwMacApOpticalLowRxPowerThreshold
					Integer32,
				hwMacApOpticalHighTemperatureThreshold
					Integer32,
				hwMacApOpticalLowTemperatureThreshold
					Integer32,
				hwMacApKeepService
					INTEGER,
				hwMacApPriorityAccessMode
					Integer32,
				hwMacApLineateportMode
					INTEGER,
				hwMacApLineateportVlanTagged
					OCTET STRING,
				hwMacApLineateportVlanUntagged
					OCTET STRING,
				hwMacApLineateportPvidVlan
					Integer32,
				hwMacApLineateportUserIsolate
					INTEGER,
				hwMacApLineateportStpEnable
					INTEGER,
				hwMacApHighTemperatureThreshold
					Integer32,
				hwMacApLowTemperatureThreshold
					Integer32,
				hwMacApReset
					Integer32,
				hwMacApStaticIpAddress
					IpAddress,
				hwMacApStaticNetMask
					IpAddress,
				hwMacApStaticGatewayIp
					IpAddress,
				hwMacApAttackFloodInterval
					Integer32,
				hwMACApAttackFloodTimes
					Integer32,
				hwMACApDynamicBlacklistEnable
					Integer32,
				hwMACApDynamicBlacklistAgingInt
					Integer32,
				hwMACApAttackPskInterval
					Integer32,
				hwMACApAttackPskTimes
					Integer32,
				hwMACApAccessBalanceGap
					Integer32,
				hwMACApIpv6Address
					OCTET STRING,
				hwMACApIpv6NetMask
					OCTET STRING,
				hwMACApGatewayIpv6
					OCTET STRING,
				hwMACApIpv6DNS
					OCTET STRING,
				hwMACApProtectAcIPv6Addr
					OCTET STRING,
				hwMACApLineatePortCfgMtu
					Integer32,
				hwMACApLineatePortMacAddress
					MacAddress,
				hwMACApAccessBalanceSwitch
					INTEGER,
				hwMACApNatIpAddress
					OCTET STRING,
				hwMACApAttackFloodQuietTime
					Integer32,
				hwMACApAttackPskQuietTime
					Integer32,
				hwMACApAttackWeakivQuietTime
					Integer32,
				hwMACApAttackSpoofQuietTime
					Integer32,
				hwMACApBootCountTotal
					Integer32,
				hwMACApBootCountPowerOff
					Integer32,
				hwMACApBootCountRowStatus
					RowStatus

			 }

-- 1.3.6.1.4.1.2011.6.139.2.6.9.1.1
		-- 1.3.6.1.4.1.2011.6.139.2.6.9.1.1
		hwMacApMac OBJECT-TYPE
			SYNTAX MacAddress
			MAX-ACCESS not-accessible
			STATUS current
			DESCRIPTION
				"Description."
			::= { hwMacApEntry 1 }

--   1.3.6.1.4.1.2011.6.139.2.6.9.1.2
-- 1.3.6.1.4.1.2011.6.139.2.6.9.1.2
		-- 1.3.6.1.4.1.2011.6.139.2.6.9.1.2
		hwMacApIndex OBJECT-TYPE
			SYNTAX Integer32
			MAX-ACCESS read-only
			STATUS current
			DESCRIPTION
				"Description."
			::= { hwMacApEntry 2 }

--   1.3.6.1.4.1.2011.6.139.2.6.9.1.3
-- 1.3.6.1.4.1.2011.6.139.2.6.9.1.3
		-- 1.3.6.1.4.1.2011.6.139.2.6.9.1.3
		hwMacApUsedType OBJECT-TYPE
			SYNTAX OCTET STRING
			MAX-ACCESS read-create
			STATUS current
			DESCRIPTION
				"Description."
			::= { hwMacApEntry 3 }

--   1.3.6.1.4.1.2011.6.139.2.6.9.1.4
-- 1.3.6.1.4.1.2011.6.139.2.6.9.1.4
		-- 1.3.6.1.4.1.2011.6.139.2.6.9.1.4
		hwMacApUsedProfileName OBJECT-TYPE
			SYNTAX OCTET STRING
			MAX-ACCESS read-create
			STATUS current
			DESCRIPTION
				"Description."
			::= { hwMacApEntry 4 }

--   1.3.6.1.4.1.2011.6.139.2.6.9.1.5
-- 1.3.6.1.4.1.2011.6.139.2.6.9.1.5
		-- 1.3.6.1.4.1.2011.6.139.2.6.9.1.5
		hwMacApUsedRegionIndex OBJECT-TYPE
			SYNTAX Integer32
			MAX-ACCESS read-create
			STATUS current
			DESCRIPTION
				"Description."
			::= { hwMacApEntry 5 }

--   1.3.6.1.4.1.2011.6.139.2.6.9.1.6
-- 1.3.6.1.4.1.2011.6.139.2.6.9.1.6
		-- 1.3.6.1.4.1.2011.6.139.2.6.9.1.6
		hwMacApSn OBJECT-TYPE
			SYNTAX OCTET STRING
			MAX-ACCESS read-create
			STATUS current
			DESCRIPTION
				"Description."
			::= { hwMacApEntry 6 }

--   1.3.6.1.4.1.2011.6.139.2.6.9.1.7
-- 1.3.6.1.4.1.2011.6.139.2.6.9.1.7
		-- 1.3.6.1.4.1.2011.6.139.2.6.9.1.7
		hwMacApSysName OBJECT-TYPE
			SYNTAX OCTET STRING
			MAX-ACCESS read-create
			STATUS current
			DESCRIPTION
				"Description."
			::= { hwMacApEntry 7 }

--   1.3.6.1.4.1.2011.6.139.2.6.9.1.8
-- 1.3.6.1.4.1.2011.6.139.2.6.9.1.8
		-- 1.3.6.1.4.1.2011.6.139.2.6.9.1.8
		hwMacApRunState OBJECT-TYPE
			SYNTAX INTEGER
				{
				idle(1),
				autofind(2),
				typeNotMatch(3),
				fault(4),
				config(5),
				configFailed(6),
				download(7),
				normal(8),
				committing(9),
				commitFailed(10),
				standby(11)
				}
			MAX-ACCESS read-only
			STATUS current
			DESCRIPTION
				"Description."
			::= { hwMacApEntry 8 }

--   1.3.6.1.4.1.2011.6.139.2.6.9.1.9
-- 1.3.6.1.4.1.2011.6.139.2.6.9.1.9
		-- 1.3.6.1.4.1.2011.6.139.2.6.9.1.9
		hwMacApSoftwareVersion OBJECT-TYPE
			SYNTAX OCTET STRING
			MAX-ACCESS read-only
			STATUS current
			DESCRIPTION
				"Description."
			::= { hwMacApEntry 9 }

--   1.3.6.1.4.1.2011.6.139.2.6.9.1.10
-- 1.3.6.1.4.1.2011.6.139.2.6.9.1.10
		-- 1.3.6.1.4.1.2011.6.139.2.6.9.1.10
		hwMacApHardwareVersion OBJECT-TYPE
			SYNTAX OCTET STRING
			MAX-ACCESS read-only
			STATUS current
			DESCRIPTION
				"Description."
			::= { hwMacApEntry 10 }

--   1.3.6.1.4.1.2011.6.139.2.6.9.1.11
-- 1.3.6.1.4.1.2011.6.139.2.6.9.1.11
		-- 1.3.6.1.4.1.2011.6.139.2.6.9.1.11
		hwMacApCpuType OBJECT-TYPE
			SYNTAX OCTET STRING
			MAX-ACCESS read-only
			STATUS current
			DESCRIPTION
				"Description."
			::= { hwMacApEntry 11 }

--   1.3.6.1.4.1.2011.6.139.2.6.9.1.12
-- 1.3.6.1.4.1.2011.6.139.2.6.9.1.12
		-- 1.3.6.1.4.1.2011.6.139.2.6.9.1.12
		hwMacApCpufrequency OBJECT-TYPE
			SYNTAX Integer32
			MAX-ACCESS read-only
			STATUS current
			DESCRIPTION
				"Description."
			::= { hwMacApEntry 12 }

--   1.3.6.1.4.1.2011.6.139.2.6.9.1.13
-- 1.3.6.1.4.1.2011.6.139.2.6.9.1.13
		-- 1.3.6.1.4.1.2011.6.139.2.6.9.1.13
		hwMacApMemoryType OBJECT-TYPE
			SYNTAX OCTET STRING
			MAX-ACCESS read-only
			STATUS current
			DESCRIPTION
				"Description."
			::= { hwMacApEntry 13 }

--   1.3.6.1.4.1.2011.6.139.2.6.9.1.14
-- 1.3.6.1.4.1.2011.6.139.2.6.9.1.14
		-- 1.3.6.1.4.1.2011.6.139.2.6.9.1.14
		hwMacApDomain OBJECT-TYPE
			SYNTAX OCTET STRING
			MAX-ACCESS read-only
			STATUS current
			DESCRIPTION
				"Description."
			::= { hwMacApEntry 14 }

--   1.3.6.1.4.1.2011.6.139.2.6.9.1.15
-- 1.3.6.1.4.1.2011.6.139.2.6.9.1.15
		-- 1.3.6.1.4.1.2011.6.139.2.6.9.1.15
		hwMacApIpAddress OBJECT-TYPE
			SYNTAX IpAddress
			MAX-ACCESS read-write
			STATUS current
			DESCRIPTION
				"Description."
			::= { hwMacApEntry 15 }

--   1.3.6.1.4.1.2011.6.139.2.6.9.1.16
-- 1.3.6.1.4.1.2011.6.139.2.6.9.1.16
		-- 1.3.6.1.4.1.2011.6.139.2.6.9.1.16
		hwMacApIpNetMask OBJECT-TYPE
			SYNTAX IpAddress
			MAX-ACCESS read-only
			STATUS current
			DESCRIPTION
				"Description."
			::= { hwMacApEntry 16 }

--   1.3.6.1.4.1.2011.6.139.2.6.9.1.17
-- 1.3.6.1.4.1.2011.6.139.2.6.9.1.17
		-- 1.3.6.1.4.1.2011.6.139.2.6.9.1.17
		hwMacApGatewayIp OBJECT-TYPE
			SYNTAX IpAddress
			MAX-ACCESS read-only
			STATUS current
			DESCRIPTION
				"Description."
			::= { hwMacApEntry 17 }

--   1.3.6.1.4.1.2011.6.139.2.6.9.1.18
-- 1.3.6.1.4.1.2011.6.139.2.6.9.1.18
		-- 1.3.6.1.4.1.2011.6.139.2.6.9.1.18
		hwMacApMemorySize OBJECT-TYPE
			SYNTAX Integer32
			MAX-ACCESS read-only
			STATUS current
			DESCRIPTION
				"Description."
			::= { hwMacApEntry 18 }

--   1.3.6.1.4.1.2011.6.139.2.6.9.1.19
-- 1.3.6.1.4.1.2011.6.139.2.6.9.1.19
		-- 1.3.6.1.4.1.2011.6.139.2.6.9.1.19
		hwMacApFlashSize OBJECT-TYPE
			SYNTAX Integer32
			MAX-ACCESS read-only
			STATUS current
			DESCRIPTION
				"Description."
			::= { hwMacApEntry 19 }

--   1.3.6.1.4.1.2011.6.139.2.6.9.1.20
-- 1.3.6.1.4.1.2011.6.139.2.6.9.1.20
		-- 1.3.6.1.4.1.2011.6.139.2.6.9.1.20
		hwMacApRunTime OBJECT-TYPE
			SYNTAX Unsigned32
			MAX-ACCESS read-only
			STATUS current
			DESCRIPTION
				"Description."
			::= { hwMacApEntry 20 }

--   1.3.6.1.4.1.2011.6.139.2.6.9.1.21
-- 1.3.6.1.4.1.2011.6.139.2.6.9.1.21
		-- 1.3.6.1.4.1.2011.6.139.2.6.9.1.21
		hwMacApUpEthPortSpeed OBJECT-TYPE
			SYNTAX INTEGER
				{
				speed10(1),
				speed100(2),
				speed1000(3),
				speed10000(4)
				}
			MAX-ACCESS read-only
			STATUS current
			DESCRIPTION
				"Description."
			::= { hwMacApEntry 21 }

--   1.3.6.1.4.1.2011.6.139.2.6.9.1.22
-- 1.3.6.1.4.1.2011.6.139.2.6.9.1.22
		-- 1.3.6.1.4.1.2011.6.139.2.6.9.1.22
		hwMacApUpEthPortSpeedMode OBJECT-TYPE
			SYNTAX INTEGER
				{
				auto(1),
				forced(2)
				}
			MAX-ACCESS read-only
			STATUS current
			DESCRIPTION
				"Description."
			::= { hwMacApEntry 22 }

--   1.3.6.1.4.1.2011.6.139.2.6.9.1.23
-- 1.3.6.1.4.1.2011.6.139.2.6.9.1.23
		-- 1.3.6.1.4.1.2011.6.139.2.6.9.1.23
		hwMacApUpEthPortDuplex OBJECT-TYPE
			SYNTAX INTEGER
				{
				half(1),
				full(2)
				}
			MAX-ACCESS read-only
			STATUS current
			DESCRIPTION
				"Description."
			::= { hwMacApEntry 23 }

--   1.3.6.1.4.1.2011.6.139.2.6.9.1.24
-- 1.3.6.1.4.1.2011.6.139.2.6.9.1.24
		-- 1.3.6.1.4.1.2011.6.139.2.6.9.1.24
		hwMacApUpEthPortDuplexMode OBJECT-TYPE
			SYNTAX INTEGER
				{
				auto(1),
				forced(2)
				}
			MAX-ACCESS read-only
			STATUS current
			DESCRIPTION
				"Description."
			::= { hwMacApEntry 24 }

--   1.3.6.1.4.1.2011.6.139.2.6.9.1.25
-- 1.3.6.1.4.1.2011.6.139.2.6.9.1.25
		-- 1.3.6.1.4.1.2011.6.139.2.6.9.1.25
		hwMacApAdminOper OBJECT-TYPE
			SYNTAX INTEGER
				{
				reset(1),
				confirm(2),
				manufacturerConfig(3),
				replaceAp(6)
				}
			MAX-ACCESS read-create
			STATUS current
			DESCRIPTION
				"Description."
			::= { hwMacApEntry 25 }

--   1.3.6.1.4.1.2011.6.139.2.6.9.1.26
-- 1.3.6.1.4.1.2011.6.139.2.6.9.1.26
		-- 1.3.6.1.4.1.2011.6.139.2.6.9.1.26
		hwMacApRowstatus OBJECT-TYPE
			SYNTAX RowStatus
			MAX-ACCESS read-create
			STATUS current
			DESCRIPTION
				"Description."
			::= { hwMacApEntry 26 }

--   1.3.6.1.4.1.2011.6.139.2.6.9.1.27
-- 1.3.6.1.4.1.2011.6.139.2.6.9.1.27
		-- 1.3.6.1.4.1.2011.6.139.2.6.9.1.27
		hwMacApPerformanceStatCycle OBJECT-TYPE
			SYNTAX INTEGER
				{
				fiveMinutes(1),
				tenMinutes(2),
				fifteenMinutes(3)
				}
			MAX-ACCESS read-write
			STATUS current
			DESCRIPTION
				"Description."
			::= { hwMacApEntry 27 }

--   1.3.6.1.4.1.2011.6.139.2.6.9.1.28
-- 1.3.6.1.4.1.2011.6.139.2.6.9.1.28
		-- 1.3.6.1.4.1.2011.6.139.2.6.9.1.28
		hwMacApDNS OBJECT-TYPE
			SYNTAX IpAddress
			MAX-ACCESS read-only
			STATUS current
			DESCRIPTION
				"Description."
			::= { hwMacApEntry 28 }

--   1.3.6.1.4.1.2011.6.139.2.6.9.1.29
-- 1.3.6.1.4.1.2011.6.139.2.6.9.1.29
		-- 1.3.6.1.4.1.2011.6.139.2.6.9.1.29
		hwMacApRunningMode OBJECT-TYPE
			SYNTAX INTEGER
				{
				auto(1),
				fat(2),
				fit(3)
				}
			MAX-ACCESS read-write
			STATUS current
			DESCRIPTION
				"Description."
			::= { hwMacApEntry 29 }

--   1.3.6.1.4.1.2011.6.139.2.6.9.1.30
-- 1.3.6.1.4.1.2011.6.139.2.6.9.1.30
		-- 1.3.6.1.4.1.2011.6.139.2.6.9.1.30
		hwMacApForwardMode OBJECT-TYPE
			SYNTAX INTEGER
				{
				directForward(1),
				tunnel(2),
				unknown(-1)
				}
			MAX-ACCESS read-write
			STATUS current
			DESCRIPTION
				"Description."
			::= { hwMacApEntry 30 }

--   1.3.6.1.4.1.2011.6.139.2.6.9.1.31
-- 1.3.6.1.4.1.2011.6.139.2.6.9.1.31
		-- 1.3.6.1.4.1.2011.6.139.2.6.9.1.31
		hwMacApAntennaMode OBJECT-TYPE
			SYNTAX INTEGER
				{
				autoMode(1),
				leftMode(2),
				rightMode(3)
				}
			MAX-ACCESS read-write
			STATUS current
			DESCRIPTION
				"Description."
			::= { hwMacApEntry 31 }

--   1.3.6.1.4.1.2011.6.139.2.6.9.1.32
-- 1.3.6.1.4.1.2011.6.139.2.6.9.1.32
		-- 1.3.6.1.4.1.2011.6.139.2.6.9.1.32
		hwMacApCpuThreshold OBJECT-TYPE
			SYNTAX Integer32
			MAX-ACCESS read-create
			STATUS current
			DESCRIPTION
				"Description."
			::= { hwMacApEntry 32 }

--   1.3.6.1.4.1.2011.6.139.2.6.9.1.33
-- 1.3.6.1.4.1.2011.6.139.2.6.9.1.33
		-- 1.3.6.1.4.1.2011.6.139.2.6.9.1.33
		hwMacApMemThreshold OBJECT-TYPE
			SYNTAX Integer32
			MAX-ACCESS read-create
			STATUS current
			DESCRIPTION
				"Description."
			::= { hwMacApEntry 33 }

--   1.3.6.1.4.1.2011.6.139.2.6.9.1.34
-- 1.3.6.1.4.1.2011.6.139.2.6.9.1.34
		-- 1.3.6.1.4.1.2011.6.139.2.6.9.1.34
		hwMacApNEnumber OBJECT-TYPE
			SYNTAX OCTET STRING
			MAX-ACCESS read-write
			STATUS current
			DESCRIPTION
				"Description."
			::= { hwMacApEntry 34 }

--   1.3.6.1.4.1.2011.6.139.2.6.9.1.35
-- 1.3.6.1.4.1.2011.6.139.2.6.9.1.35
		-- 1.3.6.1.4.1.2011.6.139.2.6.9.1.35
		hwMacApOnlineTime OBJECT-TYPE
			SYNTAX Unsigned32
			MAX-ACCESS read-only
			STATUS current
			DESCRIPTION
				"Description."
			::= { hwMacApEntry 35 }

--   1.3.6.1.4.1.2011.6.139.2.6.9.1.36
-- 1.3.6.1.4.1.2011.6.139.2.6.9.1.36
		-- 1.3.6.1.4.1.2011.6.139.2.6.9.1.36
		hwMacApSysSoftwareDesc OBJECT-TYPE
			SYNTAX OCTET STRING
			MAX-ACCESS read-only
			STATUS current
			DESCRIPTION
				"Description."
			::= { hwMacApEntry 36 }

--   1.3.6.1.4.1.2011.6.139.2.6.9.1.37
-- 1.3.6.1.4.1.2011.6.139.2.6.9.1.37
		-- 1.3.6.1.4.1.2011.6.139.2.6.9.1.37
		hwMacApSysHardtwareDesc OBJECT-TYPE
			SYNTAX OCTET STRING
			MAX-ACCESS read-only
			STATUS current
			DESCRIPTION
				"Description."
			::= { hwMacApEntry 37 }

--   1.3.6.1.4.1.2011.6.139.2.6.9.1.38
-- 1.3.6.1.4.1.2011.6.139.2.6.9.1.38
		-- 1.3.6.1.4.1.2011.6.139.2.6.9.1.38
		hwMacApSysManufacture OBJECT-TYPE
			SYNTAX OCTET STRING
			MAX-ACCESS read-only
			STATUS current
			DESCRIPTION
				"Description."
			::= { hwMacApEntry 38 }

--   1.3.6.1.4.1.2011.6.139.2.6.9.1.39
-- 1.3.6.1.4.1.2011.6.139.2.6.9.1.39
		-- 1.3.6.1.4.1.2011.6.139.2.6.9.1.39
		hwMacApSysSoftwareName OBJECT-TYPE
			SYNTAX OCTET STRING
			MAX-ACCESS read-only
			STATUS current
			DESCRIPTION
				"Description."
			::= { hwMacApEntry 39 }

--   1.3.6.1.4.1.2011.6.139.2.6.9.1.40
-- 1.3.6.1.4.1.2011.6.139.2.6.9.1.40
		-- 1.3.6.1.4.1.2011.6.139.2.6.9.1.40
		hwMacApSysSoftwareVendor OBJECT-TYPE
			SYNTAX OCTET STRING
			MAX-ACCESS read-only
			STATUS current
			DESCRIPTION
				"Description."
			::= { hwMacApEntry 40 }

--   1.3.6.1.4.1.2011.6.139.2.6.9.1.41
-- 1.3.6.1.4.1.2011.6.139.2.6.9.1.41
		-- 1.3.6.1.4.1.2011.6.139.2.6.9.1.41
		hwMacApManagementVlanID OBJECT-TYPE
			SYNTAX Integer32
			MAX-ACCESS read-write
			STATUS current
			DESCRIPTION
				"Description."
			::= { hwMacApEntry 41 }

--   1.3.6.1.4.1.2011.6.139.2.6.9.1.42
-- 1.3.6.1.4.1.2011.6.139.2.6.9.1.42
		-- 1.3.6.1.4.1.2011.6.139.2.6.9.1.42
		hwMacApUsername OBJECT-TYPE
			SYNTAX OCTET STRING (SIZE (0..64))
			MAX-ACCESS read-write
			STATUS current
			DESCRIPTION
				"Description."
			::= { hwMacApEntry 42 }

--   1.3.6.1.4.1.2011.6.139.2.6.9.1.43
-- 1.3.6.1.4.1.2011.6.139.2.6.9.1.43
		-- 1.3.6.1.4.1.2011.6.139.2.6.9.1.43
		hwMacApPassword OBJECT-TYPE
			SYNTAX OCTET STRING (SIZE (0..16))
			MAX-ACCESS read-write
			STATUS current
			DESCRIPTION
				"Description."
			::= { hwMacApEntry 43 }

--   1.3.6.1.4.1.2011.6.139.2.6.9.1.44
-- 1.3.6.1.4.1.2011.6.139.2.6.9.1.44
		-- 1.3.6.1.4.1.2011.6.139.2.6.9.1.44
		hwMacApAcIP1 OBJECT-TYPE
			SYNTAX IpAddress
			MAX-ACCESS read-write
			STATUS current
			DESCRIPTION
				"Description."
			::= { hwMacApEntry 44 }

--   1.3.6.1.4.1.2011.6.139.2.6.9.1.45
-- 1.3.6.1.4.1.2011.6.139.2.6.9.1.45
		-- 1.3.6.1.4.1.2011.6.139.2.6.9.1.45
		hwMacApAcIP2 OBJECT-TYPE
			SYNTAX IpAddress
			MAX-ACCESS read-write
			STATUS current
			DESCRIPTION
				"Description."
			::= { hwMacApEntry 45 }

--   1.3.6.1.4.1.2011.6.139.2.6.9.1.46
-- 1.3.6.1.4.1.2011.6.139.2.6.9.1.46
		-- 1.3.6.1.4.1.2011.6.139.2.6.9.1.46
		hwMacApAcIP3 OBJECT-TYPE
			SYNTAX IpAddress
			MAX-ACCESS read-write
			STATUS current
			DESCRIPTION
				"Description."
			::= { hwMacApEntry 46 }

--   1.3.6.1.4.1.2011.6.139.2.6.9.1.47
-- 1.3.6.1.4.1.2011.6.139.2.6.9.1.47
		-- 1.3.6.1.4.1.2011.6.139.2.6.9.1.47
		hwMacApAcIP4 OBJECT-TYPE
			SYNTAX IpAddress
			MAX-ACCESS read-write
			STATUS current
			DESCRIPTION
				"Description."
			::= { hwMacApEntry 47 }

--   1.3.6.1.4.1.2011.6.139.2.6.9.1.48
-- 1.3.6.1.4.1.2011.6.139.2.6.9.1.48
		-- 1.3.6.1.4.1.2011.6.139.2.6.9.1.48
		hwMacApIpMode OBJECT-TYPE
			SYNTAX INTEGER
				{
				dhcp(1),
				pppoe(2),
				static(3)
				}
			MAX-ACCESS read-write
			STATUS current
			DESCRIPTION
				"Description."
			::= { hwMacApEntry 48 }

--   1.3.6.1.4.1.2011.6.139.2.6.1.1.49
-- 1.3.6.1.4.1.2011.6.139.2.6.9.1.49
		-- 1.3.6.1.4.1.2011.6.139.2.6.9.1.49
		hwMacApLldpEnable OBJECT-TYPE
			SYNTAX INTEGER
				{
				disable(1),
				enable(2)
				}
			MAX-ACCESS read-create
			STATUS current
			DESCRIPTION
				"Description."
			DEFVAL { disable }
			::= { hwMacApEntry 49 }

--   1.3.6.1.4.1.2011.6.139.2.6.1.1.50
-- 1.3.6.1.4.1.2011.6.139.2.6.9.1.50
		-- 1.3.6.1.4.1.2011.6.139.2.6.9.1.50
		hwMacApLldpManageAddr OBJECT-TYPE
			SYNTAX INTEGER
				{
				disable(1),
				enable(2)
				}
			MAX-ACCESS read-create
			STATUS current
			DESCRIPTION
				"Description."
			DEFVAL { enable }
			::= { hwMacApEntry 50 }

--   1.3.6.1.4.1.2011.6.139.2.6.1.1.51
-- 1.3.6.1.4.1.2011.6.139.2.6.9.1.51
		-- 1.3.6.1.4.1.2011.6.139.2.6.9.1.51
		hwMacApLldpPortDes OBJECT-TYPE
			SYNTAX INTEGER
				{
				disable(1),
				enable(2)
				}
			MAX-ACCESS read-create
			STATUS current
			DESCRIPTION
				"Description."
			DEFVAL { enable }
			::= { hwMacApEntry 51 }

--   1.3.6.1.4.1.2011.6.139.2.6.1.1.52
-- 1.3.6.1.4.1.2011.6.139.2.6.9.1.52
		-- 1.3.6.1.4.1.2011.6.139.2.6.9.1.52
		hwMacApLldpSysCab OBJECT-TYPE
			SYNTAX INTEGER
				{
				disable(1),
				enable(2)
				}
			MAX-ACCESS read-create
			STATUS current
			DESCRIPTION
				"Description."
			DEFVAL { enable }
			::= { hwMacApEntry 52 }

--   1.3.6.1.4.1.2011.6.139.2.6.1.1.53
-- 1.3.6.1.4.1.2011.6.139.2.6.9.1.53
		-- 1.3.6.1.4.1.2011.6.139.2.6.9.1.53
		hwMacApLldpSysDes OBJECT-TYPE
			SYNTAX INTEGER
				{
				disable(1),
				enable(2)
				}
			MAX-ACCESS read-create
			STATUS current
			DESCRIPTION
				"Description."
			DEFVAL { enable }
			::= { hwMacApEntry 53 }

--   1.3.6.1.4.1.2011.6.139.2.6.1.1.54
-- 1.3.6.1.4.1.2011.6.139.2.6.9.1.54
		-- 1.3.6.1.4.1.2011.6.139.2.6.9.1.54
		hwMacApLldpSysName OBJECT-TYPE
			SYNTAX INTEGER
				{
				disable(1),
				enable(2)
				}
			MAX-ACCESS read-create
			STATUS current
			DESCRIPTION
				"Description."
			DEFVAL { enable }
			::= { hwMacApEntry 54 }

--   1.3.6.1.4.1.2011.6.139.2.6.1.1.55
-- 1.3.6.1.4.1.2011.6.139.2.6.9.1.55
		-- 1.3.6.1.4.1.2011.6.139.2.6.9.1.55
		hwMacApLldpDelay OBJECT-TYPE
			SYNTAX Integer32 (1..8192)
			MAX-ACCESS read-create
			STATUS current
			DESCRIPTION
				"Description."
			DEFVAL { 2 }
			::= { hwMacApEntry 55 }

--   1.3.6.1.4.1.2011.6.139.2.6.1.1.56
-- 1.3.6.1.4.1.2011.6.139.2.6.9.1.56
		-- 1.3.6.1.4.1.2011.6.139.2.6.9.1.56
		hwMacApLldpHoldMultiplier OBJECT-TYPE
			SYNTAX Integer32 (2..10)
			MAX-ACCESS read-create
			STATUS current
			DESCRIPTION
				"Description."
			DEFVAL { 4 }
			::= { hwMacApEntry 56 }

--   1.3.6.1.4.1.2011.6.139.2.6.1.1.57
-- 1.3.6.1.4.1.2011.6.139.2.6.9.1.57
		-- 1.3.6.1.4.1.2011.6.139.2.6.9.1.57
		hwMacApLldpInterval OBJECT-TYPE
			SYNTAX Integer32 (5..32768)
			MAX-ACCESS read-create
			STATUS current
			DESCRIPTION
				"Description."
			DEFVAL { 30 }
			::= { hwMacApEntry 57 }

--   1.3.6.1.4.1.2011.6.139.2.6.1.1.58
-- 1.3.6.1.4.1.2011.6.139.2.6.9.1.58
		-- 1.3.6.1.4.1.2011.6.139.2.6.9.1.58
		hwMacApLldpRestartDelay OBJECT-TYPE
			SYNTAX Integer32 (1..10)
			MAX-ACCESS read-create
			STATUS current
			DESCRIPTION
				"Description."
			DEFVAL { 2 }
			::= { hwMacApEntry 58 }

--   1.3.6.1.4.1.2011.6.139.2.6.1.1.59
-- 1.3.6.1.4.1.2011.6.139.2.6.9.1.59
		-- 1.3.6.1.4.1.2011.6.139.2.6.9.1.59
		hwMacApLldpAdminStatus OBJECT-TYPE
			SYNTAX INTEGER
				{
				txrx(1),
				rx(2),
				tx(3)
				}
			MAX-ACCESS read-create
			STATUS current
			DESCRIPTION
				"Description."
			DEFVAL { 1 }
			::= { hwMacApEntry 59 }

--   1.3.6.1.4.1.2011.6.139.2.6.1.1.60
-- 1.3.6.1.4.1.2011.6.139.2.6.9.1.60
		-- 1.3.6.1.4.1.2011.6.139.2.6.9.1.60
		hwMacApLldpReportInterval OBJECT-TYPE
			SYNTAX Integer32 (5..3600)
			MAX-ACCESS read-create
			STATUS current
			DESCRIPTION
				"Description."
			DEFVAL { 30 }
			::= { hwMacApEntry 60 }

--   1.3.6.1.4.1.2011.6.139.2.6.9.1.61
-- 1.3.6.1.4.1.2011.6.139.2.6.9.1.61
		-- 1.3.6.1.4.1.2011.6.139.2.6.9.1.61
		hwMacApBomCode OBJECT-TYPE
			SYNTAX OCTET STRING
			MAX-ACCESS read-only
			STATUS current
			DESCRIPTION
				"Description."
			::= { hwMacApEntry 61 }

--   1.3.6.1.4.1.2011.6.139.2.6.9.1.62
-- 1.3.6.1.4.1.2011.6.139.2.6.9.1.62
		-- 1.3.6.1.4.1.2011.6.139.2.6.9.1.62
		hwMacApSaveMode OBJECT-TYPE
			SYNTAX Integer32
			MAX-ACCESS read-create
			STATUS obsolete
			DESCRIPTION
				"Description."
			::= { hwMacApEntry 62 }

--  1.3.6.1.4.1.2011.6.139.2.6.9.1.63
		-- 1.3.6.1.4.1.2011.6.139.2.6.9.1.63
		hwMacApProtectAcPriority OBJECT-TYPE
			SYNTAX Integer32
			MAX-ACCESS read-create
			STATUS current
			DESCRIPTION
				"Description."
			::= { hwMacApEntry 63 }

--  1.3.6.1.4.1.2011.6.139.2.6.9.1.64
		-- 1.3.6.1.4.1.2011.6.139.2.6.9.1.64
		hwMacApProtectAcIP OBJECT-TYPE
			SYNTAX IpAddress
			MAX-ACCESS read-create
			STATUS current
			DESCRIPTION
				"Description."
			::= { hwMacApEntry 64 }

--  1.3.6.1.4.1.2011.6.139.2.6.9.1.65
		-- 1.3.6.1.4.1.2011.6.139.2.6.9.1.65
		hwMacApOpticalHighRxPowerThreshold OBJECT-TYPE
			SYNTAX Integer32 (1000..65535)
			MAX-ACCESS read-create
			STATUS current
			DESCRIPTION
				"range from 1000 to 65535"
			::= { hwMacApEntry 65 }

--  1.3.6.1.4.1.2011.6.139.2.6.9.1.66
		-- 1.3.6.1.4.1.2011.6.139.2.6.9.1.66
		hwMacApOpticalLowRxPowerThreshold OBJECT-TYPE
			SYNTAX Integer32 (1..25)
			MAX-ACCESS read-create
			STATUS current
			DESCRIPTION
				"range from 1 to 25"
			::= { hwMacApEntry 66 }

--  1.3.6.1.4.1.2011.6.139.2.6.9.1.67
		-- 1.3.6.1.4.1.2011.6.139.2.6.9.1.67
		hwMacApOpticalHighTemperatureThreshold OBJECT-TYPE
			SYNTAX Integer32 (70..125)
			MAX-ACCESS read-create
			STATUS current
			DESCRIPTION
				"range from 70 to 125"
			::= { hwMacApEntry 67 }

--  1.3.6.1.4.1.2011.6.139.2.6.9.1.68
		-- 1.3.6.1.4.1.2011.6.139.2.6.9.1.68
		hwMacApOpticalLowTemperatureThreshold OBJECT-TYPE
			SYNTAX Integer32 (-40..-5)
			MAX-ACCESS read-create
			STATUS current
			DESCRIPTION
				"range from -40 to -5"
			::= { hwMacApEntry 68 }

--  1.3.6.1.4.1.2011.6.139.2.6.9.1.69
		-- 1.3.6.1.4.1.2011.6.139.2.6.9.1.69
		hwMacApKeepService OBJECT-TYPE
			SYNTAX INTEGER
				{
				enable(1),
				disable(2)
				}
			MAX-ACCESS read-create
			STATUS current
			DESCRIPTION
				"Description."
			::= { hwMacApEntry 69 }

--  1.3.6.1.4.1.2011.6.139.2.6.9.1.70
		-- 1.3.6.1.4.1.2011.6.139.2.6.9.1.70
		hwMacApPriorityAccessMode OBJECT-TYPE
			SYNTAX Integer32 (1..2)
			MAX-ACCESS read-write
			STATUS current
			DESCRIPTION
				"Description."
			::= { hwMacApEntry 70 }

--  1.3.6.1.4.1.2011.6.139.2.6.9.1.71
		-- 1.3.6.1.4.1.2011.6.139.2.6.9.1.71
		hwMacApLineateportMode OBJECT-TYPE
			SYNTAX INTEGER
				{
				root(1),
				endpoint(2)
				}
			MAX-ACCESS read-write
			STATUS current
			DESCRIPTION
				"Description."
			::= { hwMacApEntry 71 }

--  1.3.6.1.4.1.2011.6.139.2.6.9.1.72
		-- 1.3.6.1.4.1.2011.6.139.2.6.9.1.72
		hwMacApLineateportVlanTagged OBJECT-TYPE
			SYNTAX OCTET STRING (SIZE (0..1024))
			MAX-ACCESS read-write
			STATUS current
			DESCRIPTION
				"Description."
			::= { hwMacApEntry 72 }

--  1.3.6.1.4.1.2011.6.139.2.6.9.1.73
		-- 1.3.6.1.4.1.2011.6.139.2.6.9.1.73
		hwMacApLineateportVlanUntagged OBJECT-TYPE
			SYNTAX OCTET STRING (SIZE (0..1024))
			MAX-ACCESS read-write
			STATUS current
			DESCRIPTION
				"Description."
			::= { hwMacApEntry 73 }

--  1.3.6.1.4.1.2011.6.139.2.6.9.1.74
		-- 1.3.6.1.4.1.2011.6.139.2.6.9.1.74
		hwMacApLineateportPvidVlan OBJECT-TYPE
			SYNTAX Integer32 (0..4094)
			MAX-ACCESS read-write
			STATUS current
			DESCRIPTION
				"Description."
			::= { hwMacApEntry 74 }

--  1.3.6.1.4.1.2011.6.139.2.6.9.1.75
		-- 1.3.6.1.4.1.2011.6.139.2.6.9.1.75
		hwMacApLineateportUserIsolate OBJECT-TYPE
			SYNTAX INTEGER
				{
				disable(1),
				enable(2)
				}
			MAX-ACCESS read-write
			STATUS current
			DESCRIPTION
				"Description."
			::= { hwMacApEntry 75 }

--  1.3.6.1.4.1.2011.6.139.2.6.9.1.76
		-- 1.3.6.1.4.1.2011.6.139.2.6.9.1.76
		hwMacApLineateportStpEnable OBJECT-TYPE
			SYNTAX INTEGER
				{
				disable(1),
				enable(2)
				}
			MAX-ACCESS read-write
			STATUS current
			DESCRIPTION
				"Description."
			::= { hwMacApEntry 76 }

--  1.3.6.1.4.1.2011.6.139.2.6.9.1.77
		-- 1.3.6.1.4.1.2011.6.139.2.6.9.1.77
		hwMacApHighTemperatureThreshold OBJECT-TYPE
			SYNTAX Integer32 (20..70)
			MAX-ACCESS read-write
			STATUS current
			DESCRIPTION
				"Description."
			::= { hwMacApEntry 77 }

--  1.3.6.1.4.1.2011.6.139.2.6.9.1.78
		-- 1.3.6.1.4.1.2011.6.139.2.6.9.1.78
		hwMacApLowTemperatureThreshold OBJECT-TYPE
			SYNTAX Integer32 (-40..10)
			MAX-ACCESS read-write
			STATUS current
			DESCRIPTION
				"Description."
			::= { hwMacApEntry 78 }

--  1.3.6.1.4.1.2011.6.139.2.6.9.1.79
		-- 1.3.6.1.4.1.2011.6.139.2.6.9.1.79
		hwMacApReset OBJECT-TYPE
			SYNTAX Integer32
			MAX-ACCESS read-write
			STATUS current
			DESCRIPTION
				"Description."
			::= { hwMacApEntry 79 }

--  1.3.6.1.4.1.2011.6.139.2.6.9.1.80
		-- 1.3.6.1.4.1.2011.6.139.2.6.9.1.80
		hwMacApStaticIpAddress OBJECT-TYPE
			SYNTAX IpAddress
			MAX-ACCESS read-create
			STATUS current
			DESCRIPTION
				"Description."
			::= { hwMacApEntry 80 }

--  1.3.6.1.4.1.2011.6.139.2.6.9.1.81
		-- 1.3.6.1.4.1.2011.6.139.2.6.9.1.81
		hwMacApStaticNetMask OBJECT-TYPE
			SYNTAX IpAddress
			MAX-ACCESS read-create
			STATUS current
			DESCRIPTION
				"Description."
			::= { hwMacApEntry 81 }

--  1.3.6.1.4.1.2011.6.139.2.6.9.1.82
		-- 1.3.6.1.4.1.2011.6.139.2.6.9.1.82
		hwMacApStaticGatewayIp OBJECT-TYPE
			SYNTAX IpAddress
			MAX-ACCESS read-create
			STATUS current
			DESCRIPTION
				"Description."
			::= { hwMacApEntry 82 }

		-- 1.3.6.1.4.1.2011.6.139.2.6.9.1.83
		hwMacApAttackFloodInterval OBJECT-TYPE
			SYNTAX Integer32
			MAX-ACCESS read-create
			STATUS current
			DESCRIPTION
				"Description."
			::= { hwMacApEntry 83 }

		-- 1.3.6.1.4.1.2011.6.139.2.6.9.1.84
		hwMACApAttackFloodTimes OBJECT-TYPE
			SYNTAX Integer32
			MAX-ACCESS read-create
			STATUS current
			DESCRIPTION
				"Description."
			::= { hwMacApEntry 84 }

		-- 1.3.6.1.4.1.2011.6.139.2.6.9.1.85
		hwMACApDynamicBlacklistEnable OBJECT-TYPE
			SYNTAX Integer32
			MAX-ACCESS read-create
			STATUS current
			DESCRIPTION
				"Description."
			::= { hwMacApEntry 85 }

		-- 1.3.6.1.4.1.2011.6.139.2.6.9.1.86
		hwMACApDynamicBlacklistAgingInt OBJECT-TYPE
			SYNTAX Integer32
			MAX-ACCESS read-create
			STATUS current
			DESCRIPTION
				"Description."
			::= { hwMacApEntry 86 }

		-- 1.3.6.1.4.1.2011.6.139.2.6.9.1.87
		hwMACApAttackPskInterval OBJECT-TYPE
			SYNTAX Integer32
			MAX-ACCESS read-create
			STATUS current
			DESCRIPTION
				"Description."
			::= { hwMacApEntry 87 }

		-- 1.3.6.1.4.1.2011.6.139.2.6.9.1.88
		hwMACApAttackPskTimes OBJECT-TYPE
			SYNTAX Integer32
			MAX-ACCESS read-create
			STATUS current
			DESCRIPTION
				"Description."
			::= { hwMacApEntry 88 }

		-- 1.3.6.1.4.1.2011.6.139.2.6.9.1.89
		hwMACApAccessBalanceGap OBJECT-TYPE
			SYNTAX Integer32 (1..100)
			MAX-ACCESS read-write
			STATUS current
			DESCRIPTION
				"Description."
			::= { hwMacApEntry 89 }

		-- 1.3.6.1.4.1.2011.6.139.2.6.9.1.90
		hwMACApIpv6Address OBJECT-TYPE
			SYNTAX OCTET STRING (SIZE (0..46))
			MAX-ACCESS read-write
			STATUS current
			DESCRIPTION
				"Description."
			::= { hwMacApEntry 90 }


		-- 1.3.6.1.4.1.2011.6.139.2.6.9.1.91
		hwMACApIpv6NetMask OBJECT-TYPE
			SYNTAX OCTET STRING (SIZE (0..46))
			MAX-ACCESS read-only
			STATUS current
			DESCRIPTION
				"Description."
			::= { hwMacApEntry 91 }


		-- 1.3.6.1.4.1.2011.6.139.2.6.9.1.92
		hwMACApGatewayIpv6 OBJECT-TYPE
			SYNTAX OCTET STRING (SIZE (0..46))
			MAX-ACCESS read-only
			STATUS current
			DESCRIPTION
				"Description."
			::= { hwMacApEntry 92 }


		-- 1.3.6.1.4.1.2011.6.139.2.6.9.1.93
		hwMACApIpv6DNS OBJECT-TYPE
			SYNTAX OCTET STRING (SIZE (0..46))
			MAX-ACCESS read-only
			STATUS current
			DESCRIPTION
				"Description."
			::= { hwMacApEntry 93 }


		-- 1.3.6.1.4.1.2011.6.139.2.6.9.1.94
		hwMACApProtectAcIPv6Addr OBJECT-TYPE
			SYNTAX OCTET STRING (SIZE (0..46))
			MAX-ACCESS read-create
			STATUS current
			DESCRIPTION
				"Description."
			::= { hwMacApEntry 94 }


		-- 1.3.6.1.4.1.2011.6.139.2.6.9.1.95
		hwMACApLineatePortCfgMtu OBJECT-TYPE
			SYNTAX Integer32
			MAX-ACCESS read-only
			STATUS current
			DESCRIPTION
				"Description."
			::= { hwMacApEntry 95 }


		-- 1.3.6.1.4.1.2011.6.139.2.6.9.1.96
		hwMACApLineatePortMacAddress OBJECT-TYPE
			SYNTAX MacAddress
			MAX-ACCESS read-only
			STATUS current
			DESCRIPTION
				"Description."
			::= { hwMacApEntry 96 }

		-- 1.3.6.1.4.1.2011.6.139.2.6.9.1.97
		hwMACApAccessBalanceSwitch OBJECT-TYPE
			SYNTAX INTEGER
				{
				disable(1),
				enable(2)
				}
			MAX-ACCESS read-write
			STATUS current
			DESCRIPTION
				"Description."
			::= { hwMacApEntry 97 }

		-- 1.3.6.1.4.1.2011.6.139.2.6.9.1.98
		hwMACApNatIpAddress OBJECT-TYPE
			SYNTAX OCTET STRING
			MAX-ACCESS read-only
			STATUS current
			DESCRIPTION
				"Description."
			::= { hwMacApEntry 98 }

		-- 1.3.6.1.4.1.2011.6.139.2.6.9.1.99
		hwMACApAttackFloodQuietTime OBJECT-TYPE
			SYNTAX Integer32 (60..36000)
			MAX-ACCESS read-create
			STATUS current
			DESCRIPTION
				"Flood attack quiet time. Range from 60s to 36000s"
			::= { hwMacApEntry 99 }

		-- 1.3.6.1.4.1.2011.6.139.2.6.9.1.100
		hwMACApAttackPskQuietTime OBJECT-TYPE
			SYNTAX Integer32 (60..36000)
			MAX-ACCESS read-create
			STATUS current
			DESCRIPTION
				"Psk attack quiet time. Range from 60s to 36000s"
			::= { hwMacApEntry 100 }

		-- 1.3.6.1.4.1.2011.6.139.2.6.9.1.101
		hwMACApAttackWeakivQuietTime OBJECT-TYPE
			SYNTAX Integer32 (60..36000)
			MAX-ACCESS read-create
			STATUS current
			DESCRIPTION
				"Weak-iv attack quiet time. Range from 60s to 36000s"
			::= { hwMacApEntry 101 }

		-- 1.3.6.1.4.1.2011.6.139.2.6.9.1.102
		hwMACApAttackSpoofQuietTime OBJECT-TYPE
			SYNTAX Integer32 (60..36000)
			MAX-ACCESS read-create
			STATUS current
			DESCRIPTION
				"Spoof attack quiet time. Range from 60s to 36000s"
			::= { hwMacApEntry 102 }


		-- 1.3.6.1.4.1.2011.6.139.2.6.9.1.103
		hwMACApBootCountTotal OBJECT-TYPE
			SYNTAX Integer32
			MAX-ACCESS read-create
			STATUS current
			DESCRIPTION
				"Description."
			::= { hwMacApEntry 103 }

		-- 1.3.6.1.4.1.2011.6.139.2.6.9.1.104
		hwMACApBootCountPowerOff OBJECT-TYPE
			SYNTAX Integer32
			MAX-ACCESS read-create
			STATUS current
			DESCRIPTION
				"Description."
			::= { hwMacApEntry 104 }

		-- 1.3.6.1.4.1.2011.6.139.2.6.9.1.105
		hwMACApBootCountRowStatus OBJECT-TYPE
			SYNTAX RowStatus
			MAX-ACCESS read-create
			STATUS current
			DESCRIPTION
				"Description."
			::= { hwMacApEntry 105 }

--    1.3.6.1.4.1.2011.6.139.2.6.10
-- 1.3.6.1.4.1.2011.6.139.2.6.10
-- 1.3.6.1.4.1.2011.6.139.2.6.10
		-- 1.3.6.1.4.1.2011.6.139.2.6.10
		hwMacApLineatePortTable OBJECT-TYPE
			SYNTAX SEQUENCE OF HwMacApLineatePortEntry
			MAX-ACCESS not-accessible
			STATUS current
			DESCRIPTION
				"Description."
			::= { hwApObjects 10 }

--   1.3.6.1.4.1.2011.6.139.2.6.10.1
-- 1.3.6.1.4.1.2011.6.139.2.6.10.1
		-- 1.3.6.1.4.1.2011.6.139.2.6.10.1
		hwMacApLineatePortEntry OBJECT-TYPE
			SYNTAX HwMacApLineatePortEntry
			MAX-ACCESS not-accessible
			STATUS current
			DESCRIPTION
				"Description."
			INDEX { hwApMac, hwMacApLineatePortIndex }
			::= { hwMacApLineatePortTable 1 }

		HwMacApLineatePortEntry ::=
			SEQUENCE {
				hwMacApLineatePortIndex
					Integer32,
				hwMacApLineatePortType
					INTEGER,
				hwMacApLineatePortDesc
					OCTET STRING,
				hwMacApLineatePortState
					INTEGER,
				hwMacApLineatePortSpeed
					Integer32,
				hwMacApMultiLineatePortDuplex
					INTEGER,
				hwMacApMultiLineatePortNegotiation
					INTEGER,
				hwMacApMultiLineatePortMode
					INTEGER,
				hwMacApMultiLineatePortUserIsolate
					INTEGER,
				hwMacApMultiLineatePortStpEnable
					INTEGER,
				hwMacApMultiLineatePortVlanTagged
					OCTET STRING,
				hwMacApMultiLineatePortVlanUntagged
					OCTET STRING,
				hwMacApMultiLineatePortPvidVlan
					Integer32,
				hwMacApMultiLineatePortCRCErrorHighThreshold
					Integer32,
				hwMacApMultiLineatePortCRCErrorLowThreshold
					Integer32,
				hwMacApMultiLineatePortCRCErrorSwitch
					INTEGER,
				hwMacApLineatePortAclNumInbound
					Integer32,
				hwMacApLineatePortAclNumOutbound
					Integer32,
				hwMacApLineatePortAclNameInbound
					OCTET STRING,
				hwMacApLineatePortAclNameOutbound
					OCTET STRING,
				hwMacApLineatePortAclSwitchInbound
					INTEGER,
				hwMacApLineatePortAclSwitchOutbound
					INTEGER,
				hwMacApLineatePortAclNumInboundIPV6
					Integer32,
				hwMacApLineatePortAclNumOutboundIPV6
					Integer32,
				hwMacApLineatePortAclNameInboundIPV6
					OCTET STRING,
				hwMacApLineatePortAclNameOutboundIPV6
					OCTET STRING,
				hwMacApLineatePortAclSwitchInboundIPV6
					INTEGER,
				hwMacApLineatePortAclSwitchOutboundIPV6
					INTEGER,
				hwMacApMultiLineatePortIsAddInTrunk
					INTEGER,
				hwMacApMultiLineatePortAddedOrExitTrunkID
					Integer32
			 }

--   1.3.6.1.4.1.2011.6.139.2.6.10.1.1
-- 1.3.6.1.4.1.2011.6.139.2.6.10.1.1
		-- 1.3.6.1.4.1.2011.6.139.2.6.10.1.1
		hwMacApLineatePortIndex OBJECT-TYPE
			SYNTAX Integer32
			MAX-ACCESS not-accessible
			STATUS current
			DESCRIPTION
				"Description."
			::= { hwMacApLineatePortEntry 1 }

--   1.3.6.1.4.1.2011.6.139.2.6.10.1.2
-- 1.3.6.1.4.1.2011.6.139.2.6.10.1.2
		-- 1.3.6.1.4.1.2011.6.139.2.6.10.1.2
		hwMacApLineatePortType OBJECT-TYPE
			SYNTAX INTEGER
				{
				fe(1),
				ge(2),
				gpon(3),
				epon(4),
				adsl2plus(5),
				trunk(6)
				}
			MAX-ACCESS read-only
			STATUS current
			DESCRIPTION
				"Description."
			::= { hwMacApLineatePortEntry 2 }

--   1.3.6.1.4.1.2011.6.139.2.6.10.1.3
-- 1.3.6.1.4.1.2011.6.139.2.6.10.1.3
		-- 1.3.6.1.4.1.2011.6.139.2.6.10.1.3
		hwMacApLineatePortDesc OBJECT-TYPE
			SYNTAX OCTET STRING
			MAX-ACCESS read-write
			STATUS current
			DESCRIPTION
				"Description."
			::= { hwMacApLineatePortEntry 3 }

--   1.3.6.1.4.1.2011.6.139.2.6.10.1.4
-- 1.3.6.1.4.1.2011.6.139.2.6.10.1.4
		-- 1.3.6.1.4.1.2011.6.139.2.6.10.1.4
		hwMacApLineatePortState OBJECT-TYPE
			SYNTAX INTEGER
				{
				down(1),
				up(2),
				unknown(-1)
				}
			MAX-ACCESS read-only
			STATUS current
			DESCRIPTION
				"Description."
			::= { hwMacApLineatePortEntry 4 }

--   1.3.6.1.4.1.2011.6.139.2.6.10.1.5
-- 1.3.6.1.4.1.2011.6.139.2.6.10.1.5
		-- 1.3.6.1.4.1.2011.6.139.2.6.10.1.5
		hwMacApLineatePortSpeed OBJECT-TYPE
			SYNTAX Integer32
			MAX-ACCESS read-only
			STATUS current
			DESCRIPTION
				"Description."
			::= { hwMacApLineatePortEntry 5 }


		-- 1.3.6.1.4.1.2011.6.139.2.6.10.1.6
		hwMacApMultiLineatePortDuplex OBJECT-TYPE
			SYNTAX INTEGER
				{
				half(1),
				full(2),
				unknown(-1)
				}
			MAX-ACCESS read-only
			STATUS current
			DESCRIPTION
				"Description."
			::= { hwMacApLineatePortEntry 6 }


		-- 1.3.6.1.4.1.2011.6.139.2.6.10.1.7
		hwMacApMultiLineatePortNegotiation OBJECT-TYPE
			SYNTAX INTEGER
				{
				auto(1),
				forced(2),
				unknown(-1)
				}
			MAX-ACCESS read-only
			STATUS current
			DESCRIPTION
				"Description."
			::= { hwMacApLineatePortEntry 7 }


		-- 1.3.6.1.4.1.2011.6.139.2.6.10.1.8
		hwMacApMultiLineatePortMode OBJECT-TYPE
			SYNTAX INTEGER
				{
				root(1),
				endpoint(2)
				}
			MAX-ACCESS read-write
			STATUS current
			DESCRIPTION
				"Description."
			::= { hwMacApLineatePortEntry 8 }


		-- 1.3.6.1.4.1.2011.6.139.2.6.10.1.9
		hwMacApMultiLineatePortUserIsolate OBJECT-TYPE
			SYNTAX INTEGER
				{
				disable(1),
				enable(2)
				}
			MAX-ACCESS read-write
			STATUS current
			DESCRIPTION
				"Description."
			::= { hwMacApLineatePortEntry 9 }


		-- 1.3.6.1.4.1.2011.6.139.2.6.10.1.10
		hwMacApMultiLineatePortStpEnable OBJECT-TYPE
			SYNTAX INTEGER
				{
				disable(1),
				enable(2)
				}
			MAX-ACCESS read-write
			STATUS current
			DESCRIPTION
				"Description."
			::= { hwMacApLineatePortEntry 10 }


		-- 1.3.6.1.4.1.2011.6.139.2.6.10.1.11
		hwMacApMultiLineatePortVlanTagged OBJECT-TYPE
			SYNTAX OCTET STRING (SIZE (0..1024))
			MAX-ACCESS read-write
			STATUS current
			DESCRIPTION
				"Description."
			::= { hwMacApLineatePortEntry 11 }


		-- 1.3.6.1.4.1.2011.6.139.2.6.10.1.12
		hwMacApMultiLineatePortVlanUntagged OBJECT-TYPE
			SYNTAX OCTET STRING (SIZE (0..1024))
			MAX-ACCESS read-write
			STATUS current
			DESCRIPTION
				"Description."
			::= { hwMacApLineatePortEntry 12 }


		-- 1.3.6.1.4.1.2011.6.139.2.6.10.1.13
		hwMacApMultiLineatePortPvidVlan OBJECT-TYPE
			SYNTAX Integer32 (0..4094)
			MAX-ACCESS read-write
			STATUS current
			DESCRIPTION
				"Description."
			::= { hwMacApLineatePortEntry 13 }


		-- 1.3.6.1.4.1.2011.6.139.2.6.10.1.14
		hwMacApMultiLineatePortCRCErrorHighThreshold OBJECT-TYPE
			SYNTAX Integer32
			MAX-ACCESS read-write
			STATUS current
			DESCRIPTION
				"Description."
			::= { hwMacApLineatePortEntry 14 }


		-- 1.3.6.1.4.1.2011.6.139.2.6.10.1.15
		hwMacApMultiLineatePortCRCErrorLowThreshold OBJECT-TYPE
			SYNTAX Integer32
			MAX-ACCESS read-write
			STATUS current
			DESCRIPTION
				"Description."
			::= { hwMacApLineatePortEntry 15 }


		-- 1.3.6.1.4.1.2011.6.139.2.6.10.1.16
		hwMacApMultiLineatePortCRCErrorSwitch OBJECT-TYPE
			SYNTAX INTEGER
				{
				disable(1),
				enable(2),
				unknown(-1)
				}
			MAX-ACCESS read-write
			STATUS current
			DESCRIPTION
				"Description."
			::= { hwMacApLineatePortEntry 16 }


		-- 1.3.6.1.4.1.2011.6.139.2.6.10.1.17
		hwMacApLineatePortAclNumInbound OBJECT-TYPE
			SYNTAX Integer32
			MAX-ACCESS read-write
			STATUS current
			DESCRIPTION
				"Description."
			::= { hwMacApLineatePortEntry 17 }


		-- 1.3.6.1.4.1.2011.6.139.2.6.10.1.18
		hwMacApLineatePortAclNumOutbound OBJECT-TYPE
			SYNTAX Integer32
			MAX-ACCESS read-write
			STATUS current
			DESCRIPTION
				"Description."
			::= { hwMacApLineatePortEntry 18 }


		-- 1.3.6.1.4.1.2011.6.139.2.6.10.1.19
		hwMacApLineatePortAclNameInbound OBJECT-TYPE
			SYNTAX OCTET STRING
			MAX-ACCESS read-write
			STATUS current
			DESCRIPTION
				"Description."
			::= { hwMacApLineatePortEntry 19 }


		-- 1.3.6.1.4.1.2011.6.139.2.6.10.1.20
		hwMacApLineatePortAclNameOutbound OBJECT-TYPE
			SYNTAX OCTET STRING
			MAX-ACCESS read-write
			STATUS current
			DESCRIPTION
				"Description."
			::= { hwMacApLineatePortEntry 20 }


		-- 1.3.6.1.4.1.2011.6.139.2.6.10.1.21
		hwMacApLineatePortAclSwitchInbound OBJECT-TYPE
			SYNTAX INTEGER
				{
				disable(1),
				enable(2)
				}
			MAX-ACCESS read-write
			STATUS current
			DESCRIPTION
				"Description."
			::= { hwMacApLineatePortEntry 21 }


		-- 1.3.6.1.4.1.2011.6.139.2.6.10.1.22
		hwMacApLineatePortAclSwitchOutbound OBJECT-TYPE
			SYNTAX INTEGER
				{
				disable(1),
				enable(2)
				}
			MAX-ACCESS read-write
			STATUS current
			DESCRIPTION
				"Description."
			::= { hwMacApLineatePortEntry 22 }


		-- 1.3.6.1.4.1.2011.6.139.2.6.10.1.23
		hwMacApLineatePortAclNumInboundIPV6 OBJECT-TYPE
			SYNTAX Integer32
			MAX-ACCESS read-write
			STATUS current
			DESCRIPTION
				"Description."
			::= { hwMacApLineatePortEntry 23 }


		-- 1.3.6.1.4.1.2011.6.139.2.6.10.1.24
		hwMacApLineatePortAclNumOutboundIPV6 OBJECT-TYPE
			SYNTAX Integer32
			MAX-ACCESS read-write
			STATUS current
			DESCRIPTION
				"Description."
			::= { hwMacApLineatePortEntry 24 }


		-- 1.3.6.1.4.1.2011.6.139.2.6.10.1.25
		hwMacApLineatePortAclNameInboundIPV6 OBJECT-TYPE
			SYNTAX OCTET STRING
			MAX-ACCESS read-write
			STATUS current
			DESCRIPTION
				"Description."
			::= { hwMacApLineatePortEntry 25 }


		-- 1.3.6.1.4.1.2011.6.139.2.6.10.1.26
		hwMacApLineatePortAclNameOutboundIPV6 OBJECT-TYPE
			SYNTAX OCTET STRING
			MAX-ACCESS read-write
			STATUS current
			DESCRIPTION
				"Description."
			::= { hwMacApLineatePortEntry 26 }


		-- 1.3.6.1.4.1.2011.6.139.2.6.10.1.27
		hwMacApLineatePortAclSwitchInboundIPV6 OBJECT-TYPE
			SYNTAX INTEGER
				{
				disable(1),
				enable(2)
				}
			MAX-ACCESS read-write
			STATUS current
			DESCRIPTION
				"Description."
			::= { hwMacApLineatePortEntry 27 }


		-- 1.3.6.1.4.1.2011.6.139.2.6.10.1.28
		hwMacApLineatePortAclSwitchOutboundIPV6 OBJECT-TYPE
			SYNTAX INTEGER
				{
				disable(1),
				enable(2)
				}
			MAX-ACCESS read-write
			STATUS current
			DESCRIPTION
				"Description."
			::= { hwMacApLineatePortEntry 28 }


		-- 1.3.6.1.4.1.2011.6.139.2.6.10.1.29
		hwMacApMultiLineatePortIsAddInTrunk OBJECT-TYPE
			SYNTAX INTEGER
				{
				exit(1),
				add(2),
				unknown(-1)
				}
			MAX-ACCESS read-write
			STATUS current
			DESCRIPTION
				"Description."
			::= { hwMacApLineatePortEntry 29 }


		-- 1.3.6.1.4.1.2011.6.139.2.6.10.1.30
		hwMacApMultiLineatePortAddedOrExitTrunkID OBJECT-TYPE
			SYNTAX Integer32
			MAX-ACCESS read-write
			STATUS current
			DESCRIPTION
				"Description."
			::= { hwMacApLineatePortEntry 30 }


--      1.3.6.1.4.1.2011.6.139.2.6.11
-- 1.3.6.1.4.1.2011.6.139.2.6.11
-- 1.3.6.1.4.1.2011.6.139.2.6.11
-- 1.3.6.1.4.1.2011.6.139.2.6.11
-- 1.3.6.1.4.1.2011.6.139.2.6.11
		-- 1.3.6.1.4.1.2011.6.139.2.6.11
		hwMacApPerformanceStatTable OBJECT-TYPE
			SYNTAX SEQUENCE OF HwMacApPerformanceStatEntry
			MAX-ACCESS not-accessible
			STATUS current
			DESCRIPTION
				"Description."
			::= { hwApObjects 11 }

		-- 1.3.6.1.4.1.2011.6.139.2.6.11.1
		hwMacApPerformanceStatEntry OBJECT-TYPE
			SYNTAX HwMacApPerformanceStatEntry
			MAX-ACCESS not-accessible
			STATUS current
			DESCRIPTION
				"Description."
			INDEX { hwApMac }
			::= { hwMacApPerformanceStatTable 1 }

		HwMacApPerformanceStatEntry ::=
			SEQUENCE {
				hwMacApMemoryUseRate
					Integer32,
				hwMacApCpuUseRate
					Integer32,
				hwMacApFlashFreeSize
					Integer32,
				hwMacApTemperature
					Integer32,
				hwMacApOnlineUserNum
					Integer32,
				hwMacApUpPortSpeed
					Integer32,
				hwMacApUpPortRecvFrames
					Unsigned32,
				hwMacApUpPortRecvRightFrames
					Unsigned32,
				hwMacApUpPortRecvErrorFrames
					Unsigned32,
				hwMacApUpPortSendFrames
					Unsigned32,
				hwMacApUpPortRecvBytes
					Unsigned32,
				hwMacApUpPortSendBytes
					Unsigned32,
				hwMacAPUpPortPER
					Integer32,
				hwMacAPWirelessUpPortTraffic
					Unsigned32,
				hwMacAPUpPortTraffic
					Unsigned32,
				hwMacApAirportSendDropFrames
					Unsigned32,
				hwMacApEthportRecvDropFrames
					Unsigned32,
				hwMacApAirportUpTraffic
					OCTET STRING,
				hwMacApAirportDwTraffic
					OCTET STRING,
				hwMacApEthportDwTraffic
					OCTET STRING,
				hwMacApEthportUpTraffic
					OCTET STRING,
				hwMacApAirportRecvDropPacket
					Unsigned32,
				hwMacApAirportRecvErrorPacket
					Unsigned32,
				hwMacApEthportRecvUnicastPacket
					Unsigned32,
				hwMacApEthportRecvNonUnicastPacket
					Unsigned32,
				hwMacApEthportSendUnicastPacket
					Unsigned32,
				hwMacApEthportSendNonUnicastPacket
					Unsigned32,
				hwMacApAvgRCPUUseRate
					Integer32,
				hwMacApAvgRMemoryUseRate
					Integer32,
				hwMacEthportSendDropFrames
					Counter64,
				hwMacEthportSendErrorFrames
					Counter64,
				hwMacEthportUpDwnTimes
					Unsigned32,
				hwMacApAirportRecvUnicastFrames
					Counter64,
				hwMacApEthportRecvUnknownFrames
					Counter64,
				hwMacEthportUpRate
					Integer32,
				hwMacEthportDownRate
					Integer32,
				hwMacApUpPortRecvFrames64Bits
					Counter64,
				hwMacApUpPortRecvRightFrames64Bits
					Counter64,
				hwMacApUpPortRecvErrorFrames64Bits
					Counter64,
				hwMacApUpPortSendFrames64Bits
					Counter64,
				hwMacApUpPortRecvBytes64Bits
					Counter64,
				hwMacApUpPortSendBytes64Bits
					Counter64,
				hwMacAPWirelessUpPortTraffic64Bits
					Counter64,
				hwMacAPUpPortTraffic64Bits
					Counter64,
				hwMacApAirportSendDropFrames64Bits
					Counter64,
				hwMacApEthportRecvDropFrames64Bits
					Counter64,
				hwMacApAirportRecvDropPacket64Bits
					Counter64,
				hwMacApAirportRecvErrorPacket64Bits
					Counter64,
				hwMacApEthportRecvUnicastPacket64Bits
					Counter64,
				hwMacApEthportRecvNonUnicastPacket64Bits
					Counter64,
				hwMacApEthportSendUnicastPacket64Bits
					Counter64,
				hwMacApEthportSendNonUnicastPacket64Bits
					Counter64
			 }

--   1.3.6.1.4.1.2011.6.139.2.6.11.1.1
-- 1.3.6.1.4.1.2011.6.139.2.6.11.1.1
		-- 1.3.6.1.4.1.2011.6.139.2.6.11.1.1
		hwMacApMemoryUseRate OBJECT-TYPE
			SYNTAX Integer32
			MAX-ACCESS read-only
			STATUS current
			DESCRIPTION
				"Description."
			::= { hwMacApPerformanceStatEntry 1 }

--   1.3.6.1.4.1.2011.6.139.2.6.11.1.2
-- 1.3.6.1.4.1.2011.6.139.2.6.11.1.2
		-- 1.3.6.1.4.1.2011.6.139.2.6.11.1.2
		hwMacApCpuUseRate OBJECT-TYPE
			SYNTAX Integer32
			MAX-ACCESS read-only
			STATUS current
			DESCRIPTION
				"Description."
			::= { hwMacApPerformanceStatEntry 2 }

--   1.3.6.1.4.1.2011.6.139.2.6.11.1.3
-- 1.3.6.1.4.1.2011.6.139.2.6.11.1.3
		-- 1.3.6.1.4.1.2011.6.139.2.6.11.1.3
		hwMacApFlashFreeSize OBJECT-TYPE
			SYNTAX Integer32
			MAX-ACCESS read-only
			STATUS current
			DESCRIPTION
				"Description."
			::= { hwMacApPerformanceStatEntry 3 }

--   1.3.6.1.4.1.2011.6.139.2.6.11.1.4
-- 1.3.6.1.4.1.2011.6.139.2.6.11.1.4
		-- 1.3.6.1.4.1.2011.6.139.2.6.11.1.4
		hwMacApTemperature OBJECT-TYPE
			SYNTAX Integer32
			MAX-ACCESS read-only
			STATUS current
			DESCRIPTION
				"Description."
			::= { hwMacApPerformanceStatEntry 4 }

--   1.3.6.1.4.1.2011.6.139.2.6.11.1.5
-- 1.3.6.1.4.1.2011.6.139.2.6.11.1.5
		-- 1.3.6.1.4.1.2011.6.139.2.6.11.1.5
		hwMacApOnlineUserNum OBJECT-TYPE
			SYNTAX Integer32
			MAX-ACCESS read-only
			STATUS current
			DESCRIPTION
				"Description."
			::= { hwMacApPerformanceStatEntry 5 }

--   1.3.6.1.4.1.2011.6.139.2.6.11.1.6
-- 1.3.6.1.4.1.2011.6.139.2.6.11.1.6
		-- 1.3.6.1.4.1.2011.6.139.2.6.11.1.6
		hwMacApUpPortSpeed OBJECT-TYPE
			SYNTAX Integer32
			MAX-ACCESS read-only
			STATUS current
			DESCRIPTION
				"Description."
			::= { hwMacApPerformanceStatEntry 6 }

--   1.3.6.1.4.1.2011.6.139.2.6.11.1.7
-- 1.3.6.1.4.1.2011.6.139.2.6.11.1.7
		-- 1.3.6.1.4.1.2011.6.139.2.6.11.1.7
		hwMacApUpPortRecvFrames OBJECT-TYPE
			SYNTAX Unsigned32
			MAX-ACCESS read-only
			STATUS current
			DESCRIPTION
				"Description."
			::= { hwMacApPerformanceStatEntry 7 }

--   1.3.6.1.4.1.2011.6.139.2.6.11.1.8
-- 1.3.6.1.4.1.2011.6.139.2.6.11.1.8
		-- 1.3.6.1.4.1.2011.6.139.2.6.11.1.8
		hwMacApUpPortRecvRightFrames OBJECT-TYPE
			SYNTAX Unsigned32
			MAX-ACCESS read-only
			STATUS current
			DESCRIPTION
				"Description."
			::= { hwMacApPerformanceStatEntry 8 }

--   1.3.6.1.4.1.2011.6.139.2.6.11.1.9
-- 1.3.6.1.4.1.2011.6.139.2.6.11.1.9
		-- 1.3.6.1.4.1.2011.6.139.2.6.11.1.9
		hwMacApUpPortRecvErrorFrames OBJECT-TYPE
			SYNTAX Unsigned32
			MAX-ACCESS read-only
			STATUS current
			DESCRIPTION
				"Description."
			::= { hwMacApPerformanceStatEntry 9 }

--   1.3.6.1.4.1.2011.6.139.2.6.11.1.10
-- 1.3.6.1.4.1.2011.6.139.2.6.11.1.10
		-- 1.3.6.1.4.1.2011.6.139.2.6.11.1.10
		hwMacApUpPortSendFrames OBJECT-TYPE
			SYNTAX Unsigned32
			MAX-ACCESS read-only
			STATUS current
			DESCRIPTION
				"Description."
			::= { hwMacApPerformanceStatEntry 10 }

--   1.3.6.1.4.1.2011.6.139.2.6.11.1.11
-- 1.3.6.1.4.1.2011.6.139.2.6.11.1.11
		-- 1.3.6.1.4.1.2011.6.139.2.6.11.1.11
		hwMacApUpPortRecvBytes OBJECT-TYPE
			SYNTAX Unsigned32
			MAX-ACCESS read-only
			STATUS current
			DESCRIPTION
				"Description."
			::= { hwMacApPerformanceStatEntry 11 }

--   1.3.6.1.4.1.2011.6.139.2.6.11.1.12
-- 1.3.6.1.4.1.2011.6.139.2.6.11.1.12
		-- 1.3.6.1.4.1.2011.6.139.2.6.11.1.12
		hwMacApUpPortSendBytes OBJECT-TYPE
			SYNTAX Unsigned32
			MAX-ACCESS read-only
			STATUS current
			DESCRIPTION
				"Description."
			::= { hwMacApPerformanceStatEntry 12 }

--   1.3.6.1.4.1.2011.6.139.2.6.11.1.13
-- 1.3.6.1.4.1.2011.6.139.2.6.11.1.13
		-- 1.3.6.1.4.1.2011.6.139.2.6.11.1.13
		hwMacAPUpPortPER OBJECT-TYPE
			SYNTAX Integer32
			MAX-ACCESS read-only
			STATUS current
			DESCRIPTION
				"Description."
			::= { hwMacApPerformanceStatEntry 13 }

--   1.3.6.1.4.1.2011.6.139.2.6.11.1.14
-- 1.3.6.1.4.1.2011.6.139.2.6.11.1.14
		-- 1.3.6.1.4.1.2011.6.139.2.6.11.1.14
		hwMacAPWirelessUpPortTraffic OBJECT-TYPE
			SYNTAX Unsigned32
			MAX-ACCESS read-only
			STATUS current
			DESCRIPTION
				"Description."
			::= { hwMacApPerformanceStatEntry 14 }

--   1.3.6.1.4.1.2011.6.139.2.6.11.1.15
-- 1.3.6.1.4.1.2011.6.139.2.6.11.1.15
		-- 1.3.6.1.4.1.2011.6.139.2.6.11.1.15
		hwMacAPUpPortTraffic OBJECT-TYPE
			SYNTAX Unsigned32
			MAX-ACCESS read-only
			STATUS current
			DESCRIPTION
				"Description."
			::= { hwMacApPerformanceStatEntry 15 }

--   1.3.6.1.4.1.2011.6.139.2.6.11.1.16
-- 1.3.6.1.4.1.2011.6.139.2.6.11.1.16
		-- 1.3.6.1.4.1.2011.6.139.2.6.11.1.16
		hwMacApAirportSendDropFrames OBJECT-TYPE
			SYNTAX Unsigned32
			MAX-ACCESS read-only
			STATUS current
			DESCRIPTION
				"Description."
			::= { hwMacApPerformanceStatEntry 16 }

--   1.3.6.1.4.1.2011.6.139.2.6.11.1.17
-- 1.3.6.1.4.1.2011.6.139.2.6.11.1.17
		-- 1.3.6.1.4.1.2011.6.139.2.6.11.1.17
		hwMacApEthportRecvDropFrames OBJECT-TYPE
			SYNTAX Unsigned32
			MAX-ACCESS read-only
			STATUS current
			DESCRIPTION
				"Description."
			::= { hwMacApPerformanceStatEntry 17 }

--   1.3.6.1.4.1.2011.6.139.2.6.11.1.18
-- 1.3.6.1.4.1.2011.6.139.2.6.11.1.18
		-- 1.3.6.1.4.1.2011.6.139.2.6.11.1.18
		hwMacApAirportUpTraffic OBJECT-TYPE
			SYNTAX OCTET STRING
			MAX-ACCESS read-only
			STATUS current
			DESCRIPTION
				"Description."
			::= { hwMacApPerformanceStatEntry 18 }

--   1.3.6.1.4.1.2011.6.139.2.6.11.1.19
-- 1.3.6.1.4.1.2011.6.139.2.6.11.1.19
		-- 1.3.6.1.4.1.2011.6.139.2.6.11.1.19
		hwMacApAirportDwTraffic OBJECT-TYPE
			SYNTAX OCTET STRING
			MAX-ACCESS read-only
			STATUS current
			DESCRIPTION
				"Description."
			::= { hwMacApPerformanceStatEntry 19 }

--   1.3.6.1.4.1.2011.6.139.2.6.11.1.20
-- 1.3.6.1.4.1.2011.6.139.2.6.11.1.20
		-- 1.3.6.1.4.1.2011.6.139.2.6.11.1.20
		hwMacApEthportDwTraffic OBJECT-TYPE
			SYNTAX OCTET STRING
			MAX-ACCESS read-only
			STATUS current
			DESCRIPTION
				"Description."
			::= { hwMacApPerformanceStatEntry 20 }

--   1.3.6.1.4.1.2011.6.139.2.6.11.1.21
-- 1.3.6.1.4.1.2011.6.139.2.6.11.1.21
		-- 1.3.6.1.4.1.2011.6.139.2.6.11.1.21
		hwMacApEthportUpTraffic OBJECT-TYPE
			SYNTAX OCTET STRING
			MAX-ACCESS read-only
			STATUS current
			DESCRIPTION
				"Description."
			::= { hwMacApPerformanceStatEntry 21 }

--   1.3.6.1.4.1.2011.6.139.2.6.11.1.22
-- 1.3.6.1.4.1.2011.6.139.2.6.11.1.22
		-- 1.3.6.1.4.1.2011.6.139.2.6.11.1.22
		hwMacApAirportRecvDropPacket OBJECT-TYPE
			SYNTAX Unsigned32
			MAX-ACCESS read-only
			STATUS current
			DESCRIPTION
				"Description."
			::= { hwMacApPerformanceStatEntry 22 }

--   1.3.6.1.4.1.2011.6.139.2.6.11.1.23
-- 1.3.6.1.4.1.2011.6.139.2.6.11.1.23
		-- 1.3.6.1.4.1.2011.6.139.2.6.11.1.23
		hwMacApAirportRecvErrorPacket OBJECT-TYPE
			SYNTAX Unsigned32
			MAX-ACCESS read-only
			STATUS current
			DESCRIPTION
				"Description."
			::= { hwMacApPerformanceStatEntry 23 }

--   1.3.6.1.4.1.2011.6.139.2.6.11.1.24
-- 1.3.6.1.4.1.2011.6.139.2.6.11.1.24
		-- 1.3.6.1.4.1.2011.6.139.2.6.11.1.24
		hwMacApEthportRecvUnicastPacket OBJECT-TYPE
			SYNTAX Unsigned32
			MAX-ACCESS read-only
			STATUS current
			DESCRIPTION
				"Description."
			::= { hwMacApPerformanceStatEntry 24 }

--   1.3.6.1.4.1.2011.6.139.2.6.11.1.25
-- 1.3.6.1.4.1.2011.6.139.2.6.11.1.25
		-- 1.3.6.1.4.1.2011.6.139.2.6.11.1.25
		hwMacApEthportRecvNonUnicastPacket OBJECT-TYPE
			SYNTAX Unsigned32
			MAX-ACCESS read-only
			STATUS current
			DESCRIPTION
				"Description."
			::= { hwMacApPerformanceStatEntry 25 }

--   1.3.6.1.4.1.2011.6.139.2.6.11.1.26
-- 1.3.6.1.4.1.2011.6.139.2.6.11.1.26
		-- 1.3.6.1.4.1.2011.6.139.2.6.11.1.26
		hwMacApEthportSendUnicastPacket OBJECT-TYPE
			SYNTAX Unsigned32
			MAX-ACCESS read-only
			STATUS current
			DESCRIPTION
				"Description."
			::= { hwMacApPerformanceStatEntry 26 }

--   1.3.6.1.4.1.2011.6.139.2.6.11.1.27
-- 1.3.6.1.4.1.2011.6.139.2.6.11.1.27
		-- 1.3.6.1.4.1.2011.6.139.2.6.11.1.27
		hwMacApEthportSendNonUnicastPacket OBJECT-TYPE
			SYNTAX Unsigned32
			MAX-ACCESS read-only
			STATUS current
			DESCRIPTION
				"Description."
			::= { hwMacApPerformanceStatEntry 27 }

--   1.3.6.1.4.1.2011.6.139.2.6.11.1.28
-- 1.3.6.1.4.1.2011.6.139.2.6.11.1.28
		-- 1.3.6.1.4.1.2011.6.139.2.6.11.1.28
		hwMacApAvgRCPUUseRate OBJECT-TYPE
			SYNTAX Integer32
			MAX-ACCESS read-only
			STATUS current
			DESCRIPTION
				"Description."
			::= { hwMacApPerformanceStatEntry 28 }

--   1.3.6.1.4.1.2011.6.139.2.6.11.1.29
-- 1.3.6.1.4.1.2011.6.139.2.6.11.1.29
		-- 1.3.6.1.4.1.2011.6.139.2.6.11.1.29
		hwMacApAvgRMemoryUseRate OBJECT-TYPE
			SYNTAX Integer32
			MAX-ACCESS read-only
			STATUS current
			DESCRIPTION
				"Description."
			::= { hwMacApPerformanceStatEntry 29 }

--   1.3.6.1.4.1.2011.6.139.2.6.11.1.30
-- 1.3.6.1.4.1.2011.6.139.2.6.11.1.30
		-- 1.3.6.1.4.1.2011.6.139.2.6.11.1.30
		hwMacEthportSendDropFrames OBJECT-TYPE
			SYNTAX Counter64
			MAX-ACCESS read-only
			STATUS current
			DESCRIPTION
				"Description."
			::= { hwMacApPerformanceStatEntry 30 }

--   1.3.6.1.4.1.2011.6.139.2.6.11.1.31
-- 1.3.6.1.4.1.2011.6.139.2.6.11.1.31
		-- 1.3.6.1.4.1.2011.6.139.2.6.11.1.31
		hwMacEthportSendErrorFrames OBJECT-TYPE
			SYNTAX Counter64
			MAX-ACCESS read-only
			STATUS current
			DESCRIPTION
				"Description."
			::= { hwMacApPerformanceStatEntry 31 }

--   1.3.6.1.4.1.2011.6.139.2.6.11.1.32
-- 1.3.6.1.4.1.2011.6.139.2.6.11.1.32
		-- 1.3.6.1.4.1.2011.6.139.2.6.11.1.32
		hwMacEthportUpDwnTimes OBJECT-TYPE
			SYNTAX Unsigned32
			MAX-ACCESS read-only
			STATUS current
			DESCRIPTION
				"Description."
			::= { hwMacApPerformanceStatEntry 32 }

--   1.3.6.1.4.1.2011.6.139.2.6.11.1.33
-- 1.3.6.1.4.1.2011.6.139.2.6.11.1.33
		-- 1.3.6.1.4.1.2011.6.139.2.6.11.1.33
		hwMacApAirportRecvUnicastFrames OBJECT-TYPE
			SYNTAX Counter64
			MAX-ACCESS read-only
			STATUS current
			DESCRIPTION
				"Description."
			::= { hwMacApPerformanceStatEntry 33 }

--   1.3.6.1.4.1.2011.6.139.2.6.11.1.34
-- 1.3.6.1.4.1.2011.6.139.2.6.11.1.34
		-- 1.3.6.1.4.1.2011.6.139.2.6.11.1.34
		hwMacApEthportRecvUnknownFrames OBJECT-TYPE
			SYNTAX Counter64
			MAX-ACCESS read-only
			STATUS current
			DESCRIPTION
				"Description."
			::= { hwMacApPerformanceStatEntry 34 }

--  1.3.6.1.4.1.2011.6.139.2.6.11.1.35
		-- 1.3.6.1.4.1.2011.6.139.2.6.11.1.35
		hwMacEthportUpRate OBJECT-TYPE
			SYNTAX Integer32
			MAX-ACCESS read-only
			STATUS current
			DESCRIPTION
				"Description."
			::= { hwMacApPerformanceStatEntry 35 }

--  1.3.6.1.4.1.2011.6.139.2.6.11.1.36
		-- 1.3.6.1.4.1.2011.6.139.2.6.11.1.36
		hwMacEthportDownRate OBJECT-TYPE
			SYNTAX Integer32
			MAX-ACCESS read-only
			STATUS current
			DESCRIPTION
				"Description."
			::= { hwMacApPerformanceStatEntry 36 }


		-- 1.3.6.1.4.1.2011.6.139.2.6.11.1.37
		hwMacApUpPortRecvFrames64Bits OBJECT-TYPE
			SYNTAX Counter64
			MAX-ACCESS read-only
			STATUS current
			DESCRIPTION
				"Description."
			::= { hwMacApPerformanceStatEntry 37 }


		-- 1.3.6.1.4.1.2011.6.139.2.6.11.1.38
		hwMacApUpPortRecvRightFrames64Bits OBJECT-TYPE
			SYNTAX Counter64
			MAX-ACCESS read-only
			STATUS current
			DESCRIPTION
				"Description."
			::= { hwMacApPerformanceStatEntry 38 }


		-- 1.3.6.1.4.1.2011.6.139.2.6.11.1.39
		hwMacApUpPortRecvErrorFrames64Bits OBJECT-TYPE
			SYNTAX Counter64
			MAX-ACCESS read-only
			STATUS current
			DESCRIPTION
				"Description."
			::= { hwMacApPerformanceStatEntry 39 }


		-- 1.3.6.1.4.1.2011.6.139.2.6.11.1.40
		hwMacApUpPortSendFrames64Bits OBJECT-TYPE
			SYNTAX Counter64
			MAX-ACCESS read-only
			STATUS current
			DESCRIPTION
				"Description."
			::= { hwMacApPerformanceStatEntry 40 }


		-- 1.3.6.1.4.1.2011.6.139.2.6.11.1.41
		hwMacApUpPortRecvBytes64Bits OBJECT-TYPE
			SYNTAX Counter64
			MAX-ACCESS read-only
			STATUS current
			DESCRIPTION
				"Description."
			::= { hwMacApPerformanceStatEntry 41 }


		-- 1.3.6.1.4.1.2011.6.139.2.6.11.1.42
		hwMacApUpPortSendBytes64Bits OBJECT-TYPE
			SYNTAX Counter64
			MAX-ACCESS read-only
			STATUS current
			DESCRIPTION
				"Description."
			::= { hwMacApPerformanceStatEntry 42 }


		-- 1.3.6.1.4.1.2011.6.139.2.6.11.1.43
		hwMacAPWirelessUpPortTraffic64Bits OBJECT-TYPE
			SYNTAX Counter64
			MAX-ACCESS read-only
			STATUS current
			DESCRIPTION
				"Description."
			::= { hwMacApPerformanceStatEntry 43 }


		-- 1.3.6.1.4.1.2011.6.139.2.6.11.1.44
		hwMacAPUpPortTraffic64Bits OBJECT-TYPE
			SYNTAX Counter64
			MAX-ACCESS read-only
			STATUS current
			DESCRIPTION
				"Description."
			::= { hwMacApPerformanceStatEntry 44 }


		-- 1.3.6.1.4.1.2011.6.139.2.6.11.1.45
		hwMacApAirportSendDropFrames64Bits OBJECT-TYPE
			SYNTAX Counter64
			MAX-ACCESS read-only
			STATUS current
			DESCRIPTION
				"Description."
			::= { hwMacApPerformanceStatEntry 45 }


		-- 1.3.6.1.4.1.2011.6.139.2.6.11.1.46
		hwMacApEthportRecvDropFrames64Bits OBJECT-TYPE
			SYNTAX Counter64
			MAX-ACCESS read-only
			STATUS current
			DESCRIPTION
				"Description."
			::= { hwMacApPerformanceStatEntry 46 }


		-- 1.3.6.1.4.1.2011.6.139.2.6.11.1.47
		hwMacApAirportRecvDropPacket64Bits OBJECT-TYPE
			SYNTAX Counter64
			MAX-ACCESS read-only
			STATUS current
			DESCRIPTION
				"Description."
			::= { hwMacApPerformanceStatEntry 47 }


		-- 1.3.6.1.4.1.2011.6.139.2.6.11.1.48
		hwMacApAirportRecvErrorPacket64Bits OBJECT-TYPE
			SYNTAX Counter64
			MAX-ACCESS read-only
			STATUS current
			DESCRIPTION
				"Description."
			::= { hwMacApPerformanceStatEntry 48 }


		-- 1.3.6.1.4.1.2011.6.139.2.6.11.1.49
		hwMacApEthportRecvUnicastPacket64Bits OBJECT-TYPE
			SYNTAX Counter64
			MAX-ACCESS read-only
			STATUS current
			DESCRIPTION
				"Description."
			::= { hwMacApPerformanceStatEntry 49 }


		-- 1.3.6.1.4.1.2011.6.139.2.6.11.1.50
		hwMacApEthportRecvNonUnicastPacket64Bits OBJECT-TYPE
			SYNTAX Counter64
			MAX-ACCESS read-only
			STATUS current
			DESCRIPTION
				"Description."
			::= { hwMacApPerformanceStatEntry 50 }


		-- 1.3.6.1.4.1.2011.6.139.2.6.11.1.51
		hwMacApEthportSendUnicastPacket64Bits OBJECT-TYPE
			SYNTAX Counter64
			MAX-ACCESS read-only
			STATUS current
			DESCRIPTION
				"Description."
			::= { hwMacApPerformanceStatEntry 51 }


		-- 1.3.6.1.4.1.2011.6.139.2.6.11.1.52
		hwMacApEthportSendNonUnicastPacket64Bits OBJECT-TYPE
			SYNTAX Counter64
			MAX-ACCESS read-only
			STATUS current
			DESCRIPTION
				"Description."
			::= { hwMacApPerformanceStatEntry 52 }


--   1.3.6.1.4.1.2011.6.139.2.6.12
-- 1.3.6.1.4.1.2011.6.139.2.6.12
		-- 1.3.6.1.4.1.2011.6.139.2.6.12
		hwApLineportInfoTable OBJECT-TYPE
			SYNTAX SEQUENCE OF HwApLineportInfoEntry
			MAX-ACCESS not-accessible
			STATUS current
			DESCRIPTION
				"Description."
			::= { hwApObjects 12 }

--   1.3.6.1.4.1.2011.6.139.2.6.12.1
-- 1.3.6.1.4.1.2011.6.139.2.6.12.1
		-- 1.3.6.1.4.1.2011.6.139.2.6.12.1
		hwApLineportInfoEntry OBJECT-TYPE
			SYNTAX HwApLineportInfoEntry
			MAX-ACCESS not-accessible
			STATUS current
			DESCRIPTION
				"Description."
			INDEX { hwApIndex, hwApLineportIndex }
			::= { hwApLineportInfoTable 1 }

		HwApLineportInfoEntry ::=
			SEQUENCE {
				hwApLineportIndex
					Integer32,
				hwApLineportDesc
					OCTET STRING,
				hwApLineportType
					OCTET STRING,
				hwApLineportMtu
					Integer32,
				hwApLineportSpeed
					Integer32,
				hwApLineportMac
					MacAddress,
				hwApLineportAdminStatus
					INTEGER,
				hwApLineportNum
					Integer32
			 }

--   1.3.6.1.4.1.2011.6.139.2.6.12.1.1
-- 1.3.6.1.4.1.2011.6.139.2.6.12.1.1
		-- 1.3.6.1.4.1.2011.6.139.2.6.12.1.1
		hwApLineportIndex OBJECT-TYPE
			SYNTAX Integer32 (0..3)
			MAX-ACCESS not-accessible
			STATUS current
			DESCRIPTION
				"Description."
			::= { hwApLineportInfoEntry 1 }

--   1.3.6.1.4.1.2011.6.139.2.6.12.1.2
-- 1.3.6.1.4.1.2011.6.139.2.6.12.1.2
		-- 1.3.6.1.4.1.2011.6.139.2.6.12.1.2
		hwApLineportDesc OBJECT-TYPE
			SYNTAX OCTET STRING
			MAX-ACCESS read-only
			STATUS current
			DESCRIPTION
				"Description."
			::= { hwApLineportInfoEntry 2 }

--   1.3.6.1.4.1.2011.6.139.2.6.12.1.3
-- 1.3.6.1.4.1.2011.6.139.2.6.12.1.3
		-- 1.3.6.1.4.1.2011.6.139.2.6.12.1.3
		hwApLineportType OBJECT-TYPE
			SYNTAX OCTET STRING
			MAX-ACCESS read-only
			STATUS current
			DESCRIPTION
				"Description."
			::= { hwApLineportInfoEntry 3 }

--   1.3.6.1.4.1.2011.6.139.2.6.12.1.4
-- 1.3.6.1.4.1.2011.6.139.2.6.12.1.4
		-- 1.3.6.1.4.1.2011.6.139.2.6.12.1.4
		hwApLineportMtu OBJECT-TYPE
			SYNTAX Integer32
			MAX-ACCESS read-only
			STATUS current
			DESCRIPTION
				"Description."
			::= { hwApLineportInfoEntry 4 }

--   1.3.6.1.4.1.2011.6.139.2.6.12.1.5
-- 1.3.6.1.4.1.2011.6.139.2.6.12.1.5
		-- 1.3.6.1.4.1.2011.6.139.2.6.12.1.5
		hwApLineportSpeed OBJECT-TYPE
			SYNTAX Integer32
			MAX-ACCESS read-only
			STATUS current
			DESCRIPTION
				"Description."
			::= { hwApLineportInfoEntry 5 }

--   1.3.6.1.4.1.2011.6.139.2.6.12.1.6
-- 1.3.6.1.4.1.2011.6.139.2.6.12.1.6
		-- 1.3.6.1.4.1.2011.6.139.2.6.12.1.6
		hwApLineportMac OBJECT-TYPE
			SYNTAX MacAddress
			MAX-ACCESS read-only
			STATUS current
			DESCRIPTION
				"Description."
			::= { hwApLineportInfoEntry 6 }

--   1.3.6.1.4.1.2011.6.139.2.6.12.1.7
-- 1.3.6.1.4.1.2011.6.139.2.6.12.1.7
		-- 1.3.6.1.4.1.2011.6.139.2.6.12.1.7
		hwApLineportAdminStatus OBJECT-TYPE
			SYNTAX INTEGER
				{
				adminUp(1),
				down(2),
				adminDown(3)
				}
			MAX-ACCESS read-write
			STATUS current
			DESCRIPTION
				"Description."
			::= { hwApLineportInfoEntry 7 }

--   1.3.6.1.4.1.2011.6.139.2.6.12.1.8
-- 1.3.6.1.4.1.2011.6.139.2.6.12.1.8
		-- 1.3.6.1.4.1.2011.6.139.2.6.12.1.8
		hwApLineportNum OBJECT-TYPE
			SYNTAX Integer32
			MAX-ACCESS read-only
			STATUS current
			DESCRIPTION
				"Description."
			::= { hwApLineportInfoEntry 8 }

--   1.3.6.1.4.1.2011.6.139.2.6.13
-- 1.3.6.1.4.1.2011.6.139.2.6.13
		-- 1.3.6.1.4.1.2011.6.139.2.6.13
		hwMacApLineportInfoTable OBJECT-TYPE
			SYNTAX SEQUENCE OF HwMacApLineportInfoEntry
			MAX-ACCESS not-accessible
			STATUS current
			DESCRIPTION
				"Description."
			::= { hwApObjects 13 }

--   1.3.6.1.4.1.2011.6.139.2.6.13.1
-- 1.3.6.1.4.1.2011.6.139.2.6.13.1
		-- 1.3.6.1.4.1.2011.6.139.2.6.13.1
		hwMacApLineportInfoEntry OBJECT-TYPE
			SYNTAX HwMacApLineportInfoEntry
			MAX-ACCESS not-accessible
			STATUS current
			DESCRIPTION
				"Description."
			INDEX { hwMacApMac, hwMacApLineportIndex }
			::= { hwMacApLineportInfoTable 1 }

		HwMacApLineportInfoEntry ::=
			SEQUENCE {
				hwMacApLineportIndex
					Integer32,
				hwMacApLineportDesc
					OCTET STRING,
				hwMacApLineportType
					OCTET STRING,
				hwMacApLineportMtu
					Integer32,
				hwMacApLineportSpeed
					Integer32,
				hwMacApLineportMac
					MacAddress,
				hwMacApLineportAdminStatus
					INTEGER,
				hwMacApLineportNum
					Integer32
			 }

--   1.3.6.1.4.1.2011.6.139.2.6.13.1.1
-- 1.3.6.1.4.1.2011.6.139.2.6.13.1.1
		-- 1.3.6.1.4.1.2011.6.139.2.6.13.1.1
		hwMacApLineportIndex OBJECT-TYPE
			SYNTAX Integer32 (0..3)
			MAX-ACCESS not-accessible
			STATUS current
			DESCRIPTION
				"Description."
			::= { hwMacApLineportInfoEntry 1 }

--   1.3.6.1.4.1.2011.6.139.2.6.13.1.2
-- 1.3.6.1.4.1.2011.6.139.2.6.13.1.2
		-- 1.3.6.1.4.1.2011.6.139.2.6.13.1.2
		hwMacApLineportDesc OBJECT-TYPE
			SYNTAX OCTET STRING
			MAX-ACCESS read-only
			STATUS current
			DESCRIPTION
				"Description."
			::= { hwMacApLineportInfoEntry 2 }

--   1.3.6.1.4.1.2011.6.139.2.6.13.1.3
-- 1.3.6.1.4.1.2011.6.139.2.6.13.1.3
		-- 1.3.6.1.4.1.2011.6.139.2.6.13.1.3
		hwMacApLineportType OBJECT-TYPE
			SYNTAX OCTET STRING
			MAX-ACCESS read-only
			STATUS current
			DESCRIPTION
				"Description."
			::= { hwMacApLineportInfoEntry 3 }

--   1.3.6.1.4.1.2011.6.139.2.6.13.1.4
-- 1.3.6.1.4.1.2011.6.139.2.6.13.1.4
		-- 1.3.6.1.4.1.2011.6.139.2.6.13.1.4
		hwMacApLineportMtu OBJECT-TYPE
			SYNTAX Integer32
			MAX-ACCESS read-only
			STATUS current
			DESCRIPTION
				"Description."
			::= { hwMacApLineportInfoEntry 4 }

--   1.3.6.1.4.1.2011.6.139.2.6.13.1.5
-- 1.3.6.1.4.1.2011.6.139.2.6.13.1.5
		-- 1.3.6.1.4.1.2011.6.139.2.6.13.1.5
		hwMacApLineportSpeed OBJECT-TYPE
			SYNTAX Integer32
			MAX-ACCESS read-only
			STATUS current
			DESCRIPTION
				"Description."
			::= { hwMacApLineportInfoEntry 5 }

--   1.3.6.1.4.1.2011.6.139.2.6.13.1.6
-- 1.3.6.1.4.1.2011.6.139.2.6.13.1.6
		-- 1.3.6.1.4.1.2011.6.139.2.6.13.1.6
		hwMacApLineportMac OBJECT-TYPE
			SYNTAX MacAddress
			MAX-ACCESS read-only
			STATUS current
			DESCRIPTION
				"Description."
			::= { hwMacApLineportInfoEntry 6 }

--   1.3.6.1.4.1.2011.6.139.2.6.13.1.7
-- 1.3.6.1.4.1.2011.6.139.2.6.13.1.7
		-- 1.3.6.1.4.1.2011.6.139.2.6.13.1.7
		hwMacApLineportAdminStatus OBJECT-TYPE
			SYNTAX INTEGER
				{
				adminUp(1),
				down1(2),
				adminDown(3)
				}
			MAX-ACCESS read-write
			STATUS current
			DESCRIPTION
				"Description."
			::= { hwMacApLineportInfoEntry 7 }

--   1.3.6.1.4.1.2011.6.139.2.6.13.1.8
-- 1.3.6.1.4.1.2011.6.139.2.6.13.1.8
		-- 1.3.6.1.4.1.2011.6.139.2.6.13.1.8
		hwMacApLineportNum OBJECT-TYPE
			SYNTAX Integer32
			MAX-ACCESS read-only
			STATUS current
			DESCRIPTION
				"Description."
			::= { hwMacApLineportInfoEntry 8 }

--     1.3.6.1.4.1.2011.6.139.2.6.14
-- 1.3.6.1.4.1.2011.6.139.2.6.14
-- 1.3.6.1.4.1.2011.6.139.2.6.14
-- 1.3.6.1.4.1.2011.6.139.2.6.14
		-- 1.3.6.1.4.1.2011.6.139.2.6.14
		hwApLldpTable OBJECT-TYPE
			SYNTAX SEQUENCE OF HwApLldpEntry
			MAX-ACCESS not-accessible
			STATUS current
			DESCRIPTION
				"Description."
			::= { hwApObjects 14 }

--     1.3.6.1.4.1.2011.6.139.2.6.14.1
-- 1.3.6.1.4.1.2011.6.139.2.6.14.1
-- 1.3.6.1.4.1.2011.6.139.2.6.14.1
-- 1.3.6.1.4.1.2011.6.139.2.6.14.1
		-- 1.3.6.1.4.1.2011.6.139.2.6.14.1
		hwApLldpEntry OBJECT-TYPE
			SYNTAX HwApLldpEntry
			MAX-ACCESS not-accessible
			STATUS current
			DESCRIPTION
				"Description."
			INDEX { hwApIndex, hwApLldpRemLocalPortNum, hwApLldpRemIndex }
			::= { hwApLldpTable 1 }

		HwApLldpEntry ::=
			SEQUENCE {
				hwApLldpRemLocalPortNum
					Integer32,
				hwApLldpRemIndex
					Integer32,
				hwApLldpRemChassisIdSubtype
					Integer32,
				hwApLldpRemChassisId
					OCTET STRING,
				hwApLldpRemPortIdSubtype
					Integer32,
				hwApLldpRemPortId
					OCTET STRING,
				hwApLldpRemPortDesc
					OCTET STRING,
				hwApLldpRemSysName
					OCTET STRING,
				hwApLldpRemSysDesc
					OCTET STRING,
				hwApLldpRemSysCapSupported
					Integer32,
				hwApLldpRemSysCapEnabled
					Integer32
			 }

--     1.3.6.1.4.1.2011.6.139.2.6.14.1.1
-- 1.3.6.1.4.1.2011.6.139.2.6.14.1.1
-- 1.3.6.1.4.1.2011.6.139.2.6.14.1.1
-- 1.3.6.1.4.1.2011.6.139.2.6.14.1.1
		-- 1.3.6.1.4.1.2011.6.139.2.6.14.1.1
		hwApLldpRemLocalPortNum OBJECT-TYPE
			SYNTAX Integer32
			MAX-ACCESS not-accessible
			STATUS current
			DESCRIPTION
				"Description."
			::= { hwApLldpEntry 1 }

--     1.3.6.1.4.1.2011.6.139.2.6.14.1.2
-- 1.3.6.1.4.1.2011.6.139.2.6.14.1.2
-- 1.3.6.1.4.1.2011.6.139.2.6.14.1.2
-- 1.3.6.1.4.1.2011.6.139.2.6.14.1.2
		-- 1.3.6.1.4.1.2011.6.139.2.6.14.1.2
		hwApLldpRemIndex OBJECT-TYPE
			SYNTAX Integer32
			MAX-ACCESS not-accessible
			STATUS current
			DESCRIPTION
				"Description."
			::= { hwApLldpEntry 2 }

--     1.3.6.1.4.1.2011.6.139.2.6.14.1.3
-- 1.3.6.1.4.1.2011.6.139.2.6.14.1.3
-- 1.3.6.1.4.1.2011.6.139.2.6.14.1.3
-- 1.3.6.1.4.1.2011.6.139.2.6.14.1.3
		-- 1.3.6.1.4.1.2011.6.139.2.6.14.1.3
		hwApLldpRemChassisIdSubtype OBJECT-TYPE
			SYNTAX Integer32
			MAX-ACCESS read-only
			STATUS current
			DESCRIPTION
				"Description."
			::= { hwApLldpEntry 3 }

--     1.3.6.1.4.1.2011.6.139.2.6.14.1.4
-- 1.3.6.1.4.1.2011.6.139.2.6.14.1.4
-- 1.3.6.1.4.1.2011.6.139.2.6.14.1.4
-- 1.3.6.1.4.1.2011.6.139.2.6.14.1.4
		-- 1.3.6.1.4.1.2011.6.139.2.6.14.1.4
		hwApLldpRemChassisId OBJECT-TYPE
			SYNTAX OCTET STRING (SIZE (0..255))
			MAX-ACCESS read-only
			STATUS current
			DESCRIPTION
				"Description."
			::= { hwApLldpEntry 4 }



		-- 1.3.6.1.4.1.2011.6.139.2.6.14.1.5
		hwApLldpRemPortIdSubtype OBJECT-TYPE
			SYNTAX Integer32
			MAX-ACCESS read-only
			STATUS current
			DESCRIPTION
				"Description."
			::= { hwApLldpEntry 5 }


		-- 1.3.6.1.4.1.2011.6.139.2.6.14.1.6
		hwApLldpRemPortId OBJECT-TYPE
			SYNTAX OCTET STRING (SIZE (0..255))
			MAX-ACCESS read-only
			STATUS current
			DESCRIPTION
				"Description."
			::= { hwApLldpEntry 6 }

--     1.3.6.1.4.1.2011.6.139.2.6.14.1.7
-- 1.3.6.1.4.1.2011.6.139.2.6.14.1.7
-- 1.3.6.1.4.1.2011.6.139.2.6.14.1.7
-- 1.3.6.1.4.1.2011.6.139.2.6.14.1.7
		-- 1.3.6.1.4.1.2011.6.139.2.6.14.1.7
		hwApLldpRemPortDesc OBJECT-TYPE
			SYNTAX OCTET STRING (SIZE (0..255))
			MAX-ACCESS read-only
			STATUS current
			DESCRIPTION
				"Description."
			::= { hwApLldpEntry 7 }

--     1.3.6.1.4.1.2011.6.139.2.6.14.1.8
-- 1.3.6.1.4.1.2011.6.139.2.6.14.1.8
-- 1.3.6.1.4.1.2011.6.139.2.6.14.1.8
-- 1.3.6.1.4.1.2011.6.139.2.6.14.1.8
		-- 1.3.6.1.4.1.2011.6.139.2.6.14.1.8
		hwApLldpRemSysName OBJECT-TYPE
			SYNTAX OCTET STRING (SIZE (0..255))
			MAX-ACCESS read-only
			STATUS current
			DESCRIPTION
				"Description."
			::= { hwApLldpEntry 8 }

--     1.3.6.1.4.1.2011.6.139.2.6.14.1.9
-- 1.3.6.1.4.1.2011.6.139.2.6.14.1.9
-- 1.3.6.1.4.1.2011.6.139.2.6.14.1.9
-- 1.3.6.1.4.1.2011.6.139.2.6.14.1.9
		-- 1.3.6.1.4.1.2011.6.139.2.6.14.1.9
		hwApLldpRemSysDesc OBJECT-TYPE
			SYNTAX OCTET STRING (SIZE (0..255))
			MAX-ACCESS read-only
			STATUS current
			DESCRIPTION
				"Description."
			::= { hwApLldpEntry 9 }

--     1.3.6.1.4.1.2011.6.139.2.6.14.1.10
-- 1.3.6.1.4.1.2011.6.139.2.6.14.1.10
-- 1.3.6.1.4.1.2011.6.139.2.6.14.1.10
-- 1.3.6.1.4.1.2011.6.139.2.6.14.1.10
		-- 1.3.6.1.4.1.2011.6.139.2.6.14.1.10
		hwApLldpRemSysCapSupported OBJECT-TYPE
			SYNTAX Integer32
			MAX-ACCESS read-only
			STATUS current
			DESCRIPTION
				"Description."
			::= { hwApLldpEntry 10 }

--     1.3.6.1.4.1.2011.6.139.2.6.14.1.11
-- 1.3.6.1.4.1.2011.6.139.2.6.14.1.11
-- 1.3.6.1.4.1.2011.6.139.2.6.14.1.11
-- 1.3.6.1.4.1.2011.6.139.2.6.14.1.11
		-- 1.3.6.1.4.1.2011.6.139.2.6.14.1.11
		hwApLldpRemSysCapEnabled OBJECT-TYPE
			SYNTAX Integer32
			MAX-ACCESS read-only
			STATUS current
			DESCRIPTION
				"Description."
			::= { hwApLldpEntry 11 }

--    1.3.6.1.4.1.2011.6.139.2.6.15
-- 1.3.6.1.4.1.2011.6.139.2.6.15
-- 1.3.6.1.4.1.2011.6.139.2.6.15
		-- 1.3.6.1.4.1.2011.6.139.2.6.15
		hwMacApLldpTable OBJECT-TYPE
			SYNTAX SEQUENCE OF HwMacApLldpEntry
			MAX-ACCESS not-accessible
			STATUS current
			DESCRIPTION
				"Description."
			::= { hwApObjects 15 }

--    1.3.6.1.4.1.2011.6.139.2.6.15.1
-- 1.3.6.1.4.1.2011.6.139.2.6.15.1
-- 1.3.6.1.4.1.2011.6.139.2.6.15.1
		-- 1.3.6.1.4.1.2011.6.139.2.6.15.1
		hwMacApLldpEntry OBJECT-TYPE
			SYNTAX HwMacApLldpEntry
			MAX-ACCESS not-accessible
			STATUS current
			DESCRIPTION
				"Description."
			INDEX { hwMacApMac, hwMacApLldpRemLocalPortNum, hwMacApLldpRemIndex }
			::= { hwMacApLldpTable 1 }

		HwMacApLldpEntry ::=
			SEQUENCE {
				hwMacApLldpRemLocalPortNum
					Integer32,
				hwMacApLldpRemIndex
					Integer32,
				hwMacApLldpRemChassisIdSubtype
					Integer32,
				hwMacApLldpRemChassisId
					OCTET STRING,
				hwMacApLldpRemPortIdSubtype
					Integer32,
				hwMacApLldpRemPortId
					OCTET STRING,
				hwMacApLldpRemPortDesc
					OCTET STRING,
				hwMacApLldpRemSysName
					OCTET STRING,
				hwMacApLldpRemSysDesc
					OCTET STRING,
				hwMacApLldpRemSysCapSupported
					Integer32,
				hwMacApLldpRemSysCapEnabled
					Integer32
			 }

--    1.3.6.1.4.1.2011.6.139.2.6.15.1.1
-- 1.3.6.1.4.1.2011.6.139.2.6.15.1.1
-- 1.3.6.1.4.1.2011.6.139.2.6.15.1.1
		-- 1.3.6.1.4.1.2011.6.139.2.6.15.1.1
		hwMacApLldpRemLocalPortNum OBJECT-TYPE
			SYNTAX Integer32
			MAX-ACCESS not-accessible
			STATUS current
			DESCRIPTION
				"Description."
			::= { hwMacApLldpEntry 1 }

--    1.3.6.1.4.1.2011.6.139.2.6.15.1.2
-- 1.3.6.1.4.1.2011.6.139.2.6.15.1.2
-- 1.3.6.1.4.1.2011.6.139.2.6.15.1.2
		-- 1.3.6.1.4.1.2011.6.139.2.6.15.1.2
		hwMacApLldpRemIndex OBJECT-TYPE
			SYNTAX Integer32
			MAX-ACCESS not-accessible
			STATUS current
			DESCRIPTION
				"Description."
			::= { hwMacApLldpEntry 2 }

--    1.3.6.1.4.1.2011.6.139.2.6.15.1.3
-- 1.3.6.1.4.1.2011.6.139.2.6.15.1.3
-- 1.3.6.1.4.1.2011.6.139.2.6.15.1.3
		-- 1.3.6.1.4.1.2011.6.139.2.6.15.1.3
		hwMacApLldpRemChassisIdSubtype OBJECT-TYPE
			SYNTAX Integer32
			MAX-ACCESS read-only
			STATUS current
			DESCRIPTION
				"Description."
			::= { hwMacApLldpEntry 3 }

--    1.3.6.1.4.1.2011.6.139.2.6.15.1.4
-- 1.3.6.1.4.1.2011.6.139.2.6.15.1.4
-- 1.3.6.1.4.1.2011.6.139.2.6.15.1.4
		-- 1.3.6.1.4.1.2011.6.139.2.6.15.1.4
		hwMacApLldpRemChassisId OBJECT-TYPE
			SYNTAX OCTET STRING (SIZE (0..255))
			MAX-ACCESS read-only
			STATUS current
			DESCRIPTION
				"Description."
			::= { hwMacApLldpEntry 4 }

--    1.3.6.1.4.1.2011.6.139.2.6.15.1.5
-- 1.3.6.1.4.1.2011.6.139.2.6.15.1.5
-- 1.3.6.1.4.1.2011.6.139.2.6.15.1.5
		-- 1.3.6.1.4.1.2011.6.139.2.6.15.1.5
		hwMacApLldpRemPortIdSubtype OBJECT-TYPE
			SYNTAX Integer32
			MAX-ACCESS read-only
			STATUS current
			DESCRIPTION
				"Description."
			::= { hwMacApLldpEntry 5 }

--    1.3.6.1.4.1.2011.6.139.2.6.15.1.6
-- 1.3.6.1.4.1.2011.6.139.2.6.15.1.6
-- 1.3.6.1.4.1.2011.6.139.2.6.15.1.6
		-- 1.3.6.1.4.1.2011.6.139.2.6.15.1.6
		hwMacApLldpRemPortId OBJECT-TYPE
			SYNTAX OCTET STRING (SIZE (0..255))
			MAX-ACCESS read-only
			STATUS current
			DESCRIPTION
				"Description."
			::= { hwMacApLldpEntry 6 }

--    1.3.6.1.4.1.2011.6.139.2.6.15.1.7
-- 1.3.6.1.4.1.2011.6.139.2.6.15.1.7
-- 1.3.6.1.4.1.2011.6.139.2.6.15.1.7
		-- 1.3.6.1.4.1.2011.6.139.2.6.15.1.7
		hwMacApLldpRemPortDesc OBJECT-TYPE
			SYNTAX OCTET STRING (SIZE (0..255))
			MAX-ACCESS read-only
			STATUS current
			DESCRIPTION
				"Description."
			::= { hwMacApLldpEntry 7 }

--    1.3.6.1.4.1.2011.6.139.2.6.15.1.8
-- 1.3.6.1.4.1.2011.6.139.2.6.15.1.8
-- 1.3.6.1.4.1.2011.6.139.2.6.15.1.8
		-- 1.3.6.1.4.1.2011.6.139.2.6.15.1.8
		hwMacApLldpRemSysName OBJECT-TYPE
			SYNTAX OCTET STRING (SIZE (0..255))
			MAX-ACCESS read-only
			STATUS current
			DESCRIPTION
				"Description."
			::= { hwMacApLldpEntry 8 }

--    1.3.6.1.4.1.2011.6.139.2.6.15.1.9
-- 1.3.6.1.4.1.2011.6.139.2.6.15.1.9
-- 1.3.6.1.4.1.2011.6.139.2.6.15.1.9
		-- 1.3.6.1.4.1.2011.6.139.2.6.15.1.9
		hwMacApLldpRemSysDesc OBJECT-TYPE
			SYNTAX OCTET STRING (SIZE (0..255))
			MAX-ACCESS read-only
			STATUS current
			DESCRIPTION
				"Description."
			::= { hwMacApLldpEntry 9 }

--    1.3.6.1.4.1.2011.6.139.2.6.15.1.10
-- 1.3.6.1.4.1.2011.6.139.2.6.15.1.10
-- 1.3.6.1.4.1.2011.6.139.2.6.15.1.10
		-- 1.3.6.1.4.1.2011.6.139.2.6.15.1.10
		hwMacApLldpRemSysCapSupported OBJECT-TYPE
			SYNTAX Integer32
			MAX-ACCESS read-only
			STATUS current
			DESCRIPTION
				"Description."
			::= { hwMacApLldpEntry 10 }

--    1.3.6.1.4.1.2011.6.139.2.6.15.1.11
-- 1.3.6.1.4.1.2011.6.139.2.6.15.1.11
-- 1.3.6.1.4.1.2011.6.139.2.6.15.1.11
		-- 1.3.6.1.4.1.2011.6.139.2.6.15.1.11
		hwMacApLldpRemSysCapEnabled OBJECT-TYPE
			SYNTAX Integer32
			MAX-ACCESS read-only
			STATUS current
			DESCRIPTION
				"Description."
			::= { hwMacApLldpEntry 11 }

--    1.3.6.1.4.1.2011.6.139.2.6.16
-- 1.3.6.1.4.1.2011.6.139.2.6.16
-- 1.3.6.1.4.1.2011.6.139.2.6.16
		-- 1.3.6.1.4.1.2011.6.139.2.6.16
		hwAplldpRemManAddrTable OBJECT-TYPE
			SYNTAX SEQUENCE OF HwAplldpRemManAddrEntry
			MAX-ACCESS not-accessible
			STATUS current
			DESCRIPTION
				"Description."
			::= { hwApObjects 16 }

--    1.3.6.1.4.1.2011.6.139.2.6.16.1
-- 1.3.6.1.4.1.2011.6.139.2.6.16.1
-- 1.3.6.1.4.1.2011.6.139.2.6.16.1
		-- 1.3.6.1.4.1.2011.6.139.2.6.16.1
		hwAplldpRemManAddrEntry OBJECT-TYPE
			SYNTAX HwAplldpRemManAddrEntry
			MAX-ACCESS not-accessible
			STATUS current
			DESCRIPTION
				"Description."
			INDEX { hwApIndex, hwApLldpRemLocalPortNum, hwApLldpRemIndex, hwApLldpRemManAddrSubtype, hwApLldpRemManAddr
				 }
			::= { hwAplldpRemManAddrTable 1 }

		HwAplldpRemManAddrEntry ::=
			SEQUENCE {
				hwApLldpRemManAddrSubtype
					Integer32,
				hwApLldpRemManAddr
					OCTET STRING,
				hwApLldpRemManAddrIfSubtype
					Integer32,
				hwApLldpRemManAddrIfId
					Integer32,
				hwApLldpRemManAddrOID
					OCTET STRING
			 }

--    1.3.6.1.4.1.2011.6.139.2.6.16.1.1
-- 1.3.6.1.4.1.2011.6.139.2.6.16.1.1
-- 1.3.6.1.4.1.2011.6.139.2.6.16.1.1
		-- 1.3.6.1.4.1.2011.6.139.2.6.16.1.1
		hwApLldpRemManAddrSubtype OBJECT-TYPE
			SYNTAX Integer32
			MAX-ACCESS not-accessible
			STATUS current
			DESCRIPTION
				"Description."
			::= { hwAplldpRemManAddrEntry 1 }

--    1.3.6.1.4.1.2011.6.139.2.6.16.1.2
-- 1.3.6.1.4.1.2011.6.139.2.6.16.1.2
-- 1.3.6.1.4.1.2011.6.139.2.6.16.1.2
		-- 1.3.6.1.4.1.2011.6.139.2.6.16.1.2
		hwApLldpRemManAddr OBJECT-TYPE
			SYNTAX OCTET STRING (SIZE (0..31))
			MAX-ACCESS not-accessible
			STATUS current
			DESCRIPTION
				"Description."
			::= { hwAplldpRemManAddrEntry 2 }

--    1.3.6.1.4.1.2011.6.139.2.6.16.1.3
-- 1.3.6.1.4.1.2011.6.139.2.6.16.1.3
-- 1.3.6.1.4.1.2011.6.139.2.6.16.1.3
		-- 1.3.6.1.4.1.2011.6.139.2.6.16.1.3
		hwApLldpRemManAddrIfSubtype OBJECT-TYPE
			SYNTAX Integer32
			MAX-ACCESS read-only
			STATUS current
			DESCRIPTION
				"Description."
			::= { hwAplldpRemManAddrEntry 3 }

--    1.3.6.1.4.1.2011.6.139.2.6.16.1.4
-- 1.3.6.1.4.1.2011.6.139.2.6.16.1.4
-- 1.3.6.1.4.1.2011.6.139.2.6.16.1.4
		-- 1.3.6.1.4.1.2011.6.139.2.6.16.1.4
		hwApLldpRemManAddrIfId OBJECT-TYPE
			SYNTAX Integer32
			MAX-ACCESS read-only
			STATUS current
			DESCRIPTION
				"Description."
			::= { hwAplldpRemManAddrEntry 4 }

--    1.3.6.1.4.1.2011.6.139.2.6.16.1.5
-- 1.3.6.1.4.1.2011.6.139.2.6.16.1.5
-- 1.3.6.1.4.1.2011.6.139.2.6.16.1.5
		-- 1.3.6.1.4.1.2011.6.139.2.6.16.1.5
		hwApLldpRemManAddrOID OBJECT-TYPE
			SYNTAX OCTET STRING (SIZE (0..128))
			MAX-ACCESS read-only
			STATUS current
			DESCRIPTION
				"Description."
			::= { hwAplldpRemManAddrEntry 5 }

--    1.3.6.1.4.1.2011.6.139.2.6.17
-- 1.3.6.1.4.1.2011.6.139.2.6.17
-- 1.3.6.1.4.1.2011.6.139.2.6.17
		-- 1.3.6.1.4.1.2011.6.139.2.6.17
		hwMacAplldpRemManAddrTable OBJECT-TYPE
			SYNTAX SEQUENCE OF HwMacAplldpRemManAddrEntry
			MAX-ACCESS not-accessible
			STATUS current
			DESCRIPTION
				"Description."
			::= { hwApObjects 17 }

--    1.3.6.1.4.1.2011.6.139.2.6.17.1
-- 1.3.6.1.4.1.2011.6.139.2.6.17.1
-- 1.3.6.1.4.1.2011.6.139.2.6.17.1
		-- 1.3.6.1.4.1.2011.6.139.2.6.17.1
		hwMacAplldpRemManAddrEntry OBJECT-TYPE
			SYNTAX HwMacAplldpRemManAddrEntry
			MAX-ACCESS not-accessible
			STATUS current
			DESCRIPTION
				"Description."
			INDEX { hwMacApMac, hwMacApLldpRemLocalPortNum, hwMacApLldpRemIndex, hwMACApLldpRemManAddrSubtype, hwMACApLldpRemManAddr
				 }
			::= { hwMacAplldpRemManAddrTable 1 }

		HwMacAplldpRemManAddrEntry ::=
			SEQUENCE {
				hwMACApLldpRemManAddrSubtype
					Integer32,
				hwMACApLldpRemManAddr
					OCTET STRING,
				hwMACApLldpRemManAddrIfSubtype
					Integer32,
				hwMACApLldpRemManAddrIfId
					Integer32,
				hwMACApLldpRemManAddrOID
					OCTET STRING
			 }

--    1.3.6.1.4.1.2011.6.139.2.6.17.1.1
-- 1.3.6.1.4.1.2011.6.139.2.6.17.1.1
-- 1.3.6.1.4.1.2011.6.139.2.6.17.1.1
		-- 1.3.6.1.4.1.2011.6.139.2.6.17.1.1
		hwMACApLldpRemManAddrSubtype OBJECT-TYPE
			SYNTAX Integer32
			MAX-ACCESS not-accessible
			STATUS current
			DESCRIPTION
				"Description."
			::= { hwMacAplldpRemManAddrEntry 1 }

--    1.3.6.1.4.1.2011.6.139.2.6.17.1.2
-- 1.3.6.1.4.1.2011.6.139.2.6.17.1.2
-- 1.3.6.1.4.1.2011.6.139.2.6.17.1.2
		-- 1.3.6.1.4.1.2011.6.139.2.6.17.1.2
		hwMACApLldpRemManAddr OBJECT-TYPE
			SYNTAX OCTET STRING (SIZE (0..31))
			MAX-ACCESS not-accessible
			STATUS current
			DESCRIPTION
				"Description."
			::= { hwMacAplldpRemManAddrEntry 2 }

--    1.3.6.1.4.1.2011.6.139.2.6.17.1.3
-- 1.3.6.1.4.1.2011.6.139.2.6.17.1.3
-- 1.3.6.1.4.1.2011.6.139.2.6.17.1.3
		-- 1.3.6.1.4.1.2011.6.139.2.6.17.1.3
		hwMACApLldpRemManAddrIfSubtype OBJECT-TYPE
			SYNTAX Integer32
			MAX-ACCESS read-only
			STATUS current
			DESCRIPTION
				"Description."
			::= { hwMacAplldpRemManAddrEntry 3 }

--    1.3.6.1.4.1.2011.6.139.2.6.17.1.4
-- 1.3.6.1.4.1.2011.6.139.2.6.17.1.4
-- 1.3.6.1.4.1.2011.6.139.2.6.17.1.4
		-- 1.3.6.1.4.1.2011.6.139.2.6.17.1.4
		hwMACApLldpRemManAddrIfId OBJECT-TYPE
			SYNTAX Integer32
			MAX-ACCESS read-only
			STATUS current
			DESCRIPTION
				"Description."
			::= { hwMacAplldpRemManAddrEntry 4 }

--    1.3.6.1.4.1.2011.6.139.2.6.17.1.5
-- 1.3.6.1.4.1.2011.6.139.2.6.17.1.5
-- 1.3.6.1.4.1.2011.6.139.2.6.17.1.5
		-- 1.3.6.1.4.1.2011.6.139.2.6.17.1.5
		hwMACApLldpRemManAddrOID OBJECT-TYPE
			SYNTAX OCTET STRING (SIZE (0..128))
			MAX-ACCESS read-only
			STATUS current
			DESCRIPTION
				"Description."
			::= { hwMacAplldpRemManAddrEntry 5 }

--   1.3.6.1.4.1.2011.6.139.2.6.18
-- 1.3.6.1.4.1.2011.6.139.2.6.18
		-- 1.3.6.1.4.1.2011.6.139.2.6.18
		hwApOpticalInfoTable OBJECT-TYPE
			SYNTAX SEQUENCE OF HwApOpticalInfoEntry
			MAX-ACCESS not-accessible
			STATUS current
			DESCRIPTION
				"Description."
			::= { hwApObjects 18 }

--   1.3.6.1.4.1.2011.6.139.2.6.18.1
-- 1.3.6.1.4.1.2011.6.139.2.6.18.1
		-- 1.3.6.1.4.1.2011.6.139.2.6.18.1
		hwApOpticalInfoEntry OBJECT-TYPE
			SYNTAX HwApOpticalInfoEntry
			MAX-ACCESS not-accessible
			STATUS current
			DESCRIPTION
				"Description."
			INDEX { hwApIndex }
			::= { hwApOpticalInfoTable 1 }

		HwApOpticalInfoEntry ::=
			SEQUENCE {
				hwApOpticalNominalBitRate
					Integer32,
				hwApOpticalLinkLen9X125km
					Integer32,
				hwApOpticalLinkLen50X125X100m
					Integer32,
				hwApOpticalLinkLen62p5X125X10m
					Integer32,
				hwApOpticalLinkLenCopper
					Integer32,
				hwApOpticalSfpConnector
					OCTET STRING,
				hwApOpticalDdmVoltage
					Integer32,
				hwApOpticalDdmTxBiasCurrent
					Integer32,
				hwApOpticalDdmTxPower
					Integer32,
				hwApOpticalDdmRxPower
					Integer32,
				hwApOpticalDdmTemperature
					Integer32,
				hwApOpticalVdndorOui
					Integer32,
				hwApOpticalVendorName
					OCTET STRING,
				hwApOpticalVendorPn
					OCTET STRING,
				hwApOpticalVendorRev
					OCTET STRING,
				hwApOpticalVendorSn
					OCTET STRING
			 }

--   1.3.6.1.4.1.2011.6.139.2.6.18.1.1
-- 1.3.6.1.4.1.2011.6.139.2.6.18.1.1
		-- 1.3.6.1.4.1.2011.6.139.2.6.18.1.1
		hwApOpticalNominalBitRate OBJECT-TYPE
			SYNTAX Integer32
			MAX-ACCESS read-only
			STATUS current
			DESCRIPTION
				"Description."
			::= { hwApOpticalInfoEntry 1 }

--   1.3.6.1.4.1.2011.6.139.2.6.18.1.2
-- 1.3.6.1.4.1.2011.6.139.2.6.18.1.2
		-- 1.3.6.1.4.1.2011.6.139.2.6.18.1.2
		hwApOpticalLinkLen9X125km OBJECT-TYPE
			SYNTAX Integer32
			MAX-ACCESS read-only
			STATUS current
			DESCRIPTION
				"Description."
			::= { hwApOpticalInfoEntry 2 }

--   1.3.6.1.4.1.2011.6.139.2.6.18.1.3
-- 1.3.6.1.4.1.2011.6.139.2.6.18.1.3
		-- 1.3.6.1.4.1.2011.6.139.2.6.18.1.3
		hwApOpticalLinkLen50X125X100m OBJECT-TYPE
			SYNTAX Integer32
			MAX-ACCESS read-only
			STATUS current
			DESCRIPTION
				"Description."
			::= { hwApOpticalInfoEntry 3 }

--   1.3.6.1.4.1.2011.6.139.2.6.18.1.4
-- 1.3.6.1.4.1.2011.6.139.2.6.18.1.4
		-- 1.3.6.1.4.1.2011.6.139.2.6.18.1.4
		hwApOpticalLinkLen62p5X125X10m OBJECT-TYPE
			SYNTAX Integer32
			MAX-ACCESS read-only
			STATUS current
			DESCRIPTION
				"Description."
			::= { hwApOpticalInfoEntry 4 }

--   1.3.6.1.4.1.2011.6.139.2.6.18.1.5
-- 1.3.6.1.4.1.2011.6.139.2.6.18.1.5
		-- 1.3.6.1.4.1.2011.6.139.2.6.18.1.5
		hwApOpticalLinkLenCopper OBJECT-TYPE
			SYNTAX Integer32
			MAX-ACCESS read-only
			STATUS current
			DESCRIPTION
				"Description."
			::= { hwApOpticalInfoEntry 5 }

--   1.3.6.1.4.1.2011.6.139.2.6.18.1.6
-- 1.3.6.1.4.1.2011.6.139.2.6.18.1.6
		-- 1.3.6.1.4.1.2011.6.139.2.6.18.1.6
		hwApOpticalSfpConnector OBJECT-TYPE
			SYNTAX OCTET STRING
			MAX-ACCESS read-only
			STATUS current
			DESCRIPTION
				"Description."
			::= { hwApOpticalInfoEntry 6 }

--   1.3.6.1.4.1.2011.6.139.2.6.18.1.7
-- 1.3.6.1.4.1.2011.6.139.2.6.18.1.7
		-- 1.3.6.1.4.1.2011.6.139.2.6.18.1.7
		hwApOpticalDdmVoltage OBJECT-TYPE
			SYNTAX Integer32
			MAX-ACCESS read-only
			STATUS current
			DESCRIPTION
				"Description."
			::= { hwApOpticalInfoEntry 7 }

--   1.3.6.1.4.1.2011.6.139.2.6.18.1.8
-- 1.3.6.1.4.1.2011.6.139.2.6.18.1.8
		-- 1.3.6.1.4.1.2011.6.139.2.6.18.1.8
		hwApOpticalDdmTxBiasCurrent OBJECT-TYPE
			SYNTAX Integer32
			MAX-ACCESS read-only
			STATUS current
			DESCRIPTION
				"Description."
			::= { hwApOpticalInfoEntry 8 }

--   1.3.6.1.4.1.2011.6.139.2.6.18.1.9
-- 1.3.6.1.4.1.2011.6.139.2.6.18.1.9
		-- 1.3.6.1.4.1.2011.6.139.2.6.18.1.9
		hwApOpticalDdmTxPower OBJECT-TYPE
			SYNTAX Integer32
			MAX-ACCESS read-only
			STATUS current
			DESCRIPTION
				"Description."
			::= { hwApOpticalInfoEntry 9 }

--   1.3.6.1.4.1.2011.6.139.2.6.18.1.10
-- 1.3.6.1.4.1.2011.6.139.2.6.18.1.10
		-- 1.3.6.1.4.1.2011.6.139.2.6.18.1.10
		hwApOpticalDdmRxPower OBJECT-TYPE
			SYNTAX Integer32
			MAX-ACCESS read-only
			STATUS current
			DESCRIPTION
				"Description."
			::= { hwApOpticalInfoEntry 10 }

--   1.3.6.1.4.1.2011.6.139.2.6.18.1.11
-- 1.3.6.1.4.1.2011.6.139.2.6.18.1.11
		-- 1.3.6.1.4.1.2011.6.139.2.6.18.1.11
		hwApOpticalDdmTemperature OBJECT-TYPE
			SYNTAX Integer32
			MAX-ACCESS read-only
			STATUS current
			DESCRIPTION
				"Description."
			::= { hwApOpticalInfoEntry 11 }

--   1.3.6.1.4.1.2011.6.139.2.6.18.1.12
-- 1.3.6.1.4.1.2011.6.139.2.6.18.1.12
		-- 1.3.6.1.4.1.2011.6.139.2.6.18.1.12
		hwApOpticalVdndorOui OBJECT-TYPE
			SYNTAX Integer32
			MAX-ACCESS read-only
			STATUS current
			DESCRIPTION
				"Description."
			::= { hwApOpticalInfoEntry 12 }

--   1.3.6.1.4.1.2011.6.139.2.6.18.1.13
-- 1.3.6.1.4.1.2011.6.139.2.6.18.1.13
		-- 1.3.6.1.4.1.2011.6.139.2.6.18.1.13
		hwApOpticalVendorName OBJECT-TYPE
			SYNTAX OCTET STRING
			MAX-ACCESS read-only
			STATUS current
			DESCRIPTION
				"Description."
			::= { hwApOpticalInfoEntry 13 }

--   1.3.6.1.4.1.2011.6.139.2.6.18.1.14
-- 1.3.6.1.4.1.2011.6.139.2.6.18.1.14
		-- 1.3.6.1.4.1.2011.6.139.2.6.18.1.14
		hwApOpticalVendorPn OBJECT-TYPE
			SYNTAX OCTET STRING
			MAX-ACCESS read-only
			STATUS current
			DESCRIPTION
				"Description."
			::= { hwApOpticalInfoEntry 14 }

--   1.3.6.1.4.1.2011.6.139.2.6.18.1.15
-- 1.3.6.1.4.1.2011.6.139.2.6.18.1.15
		-- 1.3.6.1.4.1.2011.6.139.2.6.18.1.15
		hwApOpticalVendorRev OBJECT-TYPE
			SYNTAX OCTET STRING
			MAX-ACCESS read-only
			STATUS current
			DESCRIPTION
				"Description."
			::= { hwApOpticalInfoEntry 15 }

--   1.3.6.1.4.1.2011.6.139.2.6.18.1.16
-- 1.3.6.1.4.1.2011.6.139.2.6.18.1.16
		-- 1.3.6.1.4.1.2011.6.139.2.6.18.1.16
		hwApOpticalVendorSn OBJECT-TYPE
			SYNTAX OCTET STRING
			MAX-ACCESS read-only
			STATUS current
			DESCRIPTION
				"Description."
			::= { hwApOpticalInfoEntry 16 }

--   1.3.6.1.4.1.2011.6.139.2.6.19
-- 1.3.6.1.4.1.2011.6.139.2.6.19
		-- 1.3.6.1.4.1.2011.6.139.2.6.19
		hwMacApOpticalInfoTable OBJECT-TYPE
			SYNTAX SEQUENCE OF HwMacApOpticalInfoEntry
			MAX-ACCESS not-accessible
			STATUS current
			DESCRIPTION
				"Description."
			::= { hwApObjects 19 }

--   1.3.6.1.4.1.2011.6.139.2.6.19.1
-- 1.3.6.1.4.1.2011.6.139.2.6.19.1
		-- 1.3.6.1.4.1.2011.6.139.2.6.19.1
		hwMacApOpticalInfoEntry OBJECT-TYPE
			SYNTAX HwMacApOpticalInfoEntry
			MAX-ACCESS not-accessible
			STATUS current
			DESCRIPTION
				"Description."
			INDEX { hwMacApMac }
			::= { hwMacApOpticalInfoTable 1 }

		HwMacApOpticalInfoEntry ::=
			SEQUENCE {
				hwMacApOpticalNominalBitRate
					Integer32,
				hwMacApOpticalLinkLen9X125km
					Integer32,
				hwMacApOpticalLinkLen50X125X100m
					Integer32,
				hwMacApOpticalLinkLen62p5X125X10m
					Integer32,
				hwMacApOpticalLinkLenCopper
					Integer32,
				hwMacApOpticalSfpConnector
					OCTET STRING,
				hwMacApOpticalDdmVoltage
					Integer32,
				hwMacApOpticalDdmTxBiasCurrent
					Integer32,
				hwMacApOpticalDdmTxPower
					Integer32,
				hwMacApOpticalDdmRxPower
					Integer32,
				hwMacApOpticalDdmTemperature
					Integer32,
				hwMacApOpticalVdndorOui
					Integer32,
				hwMacApOpticalVendorName
					OCTET STRING,
				hwMacApOpticalVendorPn
					OCTET STRING,
				hwMacApOpticalVendorRev
					OCTET STRING,
				hwMacApOpticalVendorSn
					OCTET STRING
			 }

--   1.3.6.1.4.1.2011.6.139.2.6.19.1.1
-- 1.3.6.1.4.1.2011.6.139.2.6.19.1.1
		-- 1.3.6.1.4.1.2011.6.139.2.6.19.1.1
		hwMacApOpticalNominalBitRate OBJECT-TYPE
			SYNTAX Integer32
			MAX-ACCESS read-only
			STATUS current
			DESCRIPTION
				"Description."
			::= { hwMacApOpticalInfoEntry 1 }

--   1.3.6.1.4.1.2011.6.139.2.6.19.1.2
-- 1.3.6.1.4.1.2011.6.139.2.6.19.1.2
		-- 1.3.6.1.4.1.2011.6.139.2.6.19.1.2
		hwMacApOpticalLinkLen9X125km OBJECT-TYPE
			SYNTAX Integer32
			MAX-ACCESS read-only
			STATUS current
			DESCRIPTION
				"Description."
			::= { hwMacApOpticalInfoEntry 2 }

--   1.3.6.1.4.1.2011.6.139.2.6.19.1.3
-- 1.3.6.1.4.1.2011.6.139.2.6.19.1.3
		-- 1.3.6.1.4.1.2011.6.139.2.6.19.1.3
		hwMacApOpticalLinkLen50X125X100m OBJECT-TYPE
			SYNTAX Integer32
			MAX-ACCESS read-only
			STATUS current
			DESCRIPTION
				"Description."
			::= { hwMacApOpticalInfoEntry 3 }

--   1.3.6.1.4.1.2011.6.139.2.6.19.1.4
-- 1.3.6.1.4.1.2011.6.139.2.6.19.1.4
		-- 1.3.6.1.4.1.2011.6.139.2.6.19.1.4
		hwMacApOpticalLinkLen62p5X125X10m OBJECT-TYPE
			SYNTAX Integer32
			MAX-ACCESS read-only
			STATUS current
			DESCRIPTION
				"Description."
			::= { hwMacApOpticalInfoEntry 4 }

--   1.3.6.1.4.1.2011.6.139.2.6.19.1.5
-- 1.3.6.1.4.1.2011.6.139.2.6.19.1.5
		-- 1.3.6.1.4.1.2011.6.139.2.6.19.1.5
		hwMacApOpticalLinkLenCopper OBJECT-TYPE
			SYNTAX Integer32
			MAX-ACCESS read-only
			STATUS current
			DESCRIPTION
				"Description."
			::= { hwMacApOpticalInfoEntry 5 }

--   1.3.6.1.4.1.2011.6.139.2.6.19.1.6
-- 1.3.6.1.4.1.2011.6.139.2.6.19.1.6
		-- 1.3.6.1.4.1.2011.6.139.2.6.19.1.6
		hwMacApOpticalSfpConnector OBJECT-TYPE
			SYNTAX OCTET STRING
			MAX-ACCESS read-only
			STATUS current
			DESCRIPTION
				"Description."
			::= { hwMacApOpticalInfoEntry 6 }

--   1.3.6.1.4.1.2011.6.139.2.6.19.1.7
-- 1.3.6.1.4.1.2011.6.139.2.6.19.1.7
		-- 1.3.6.1.4.1.2011.6.139.2.6.19.1.7
		hwMacApOpticalDdmVoltage OBJECT-TYPE
			SYNTAX Integer32
			MAX-ACCESS read-only
			STATUS current
			DESCRIPTION
				"Description."
			::= { hwMacApOpticalInfoEntry 7 }

--   1.3.6.1.4.1.2011.6.139.2.6.19.1.8
-- 1.3.6.1.4.1.2011.6.139.2.6.19.1.8
		-- 1.3.6.1.4.1.2011.6.139.2.6.19.1.8
		hwMacApOpticalDdmTxBiasCurrent OBJECT-TYPE
			SYNTAX Integer32
			MAX-ACCESS read-only
			STATUS current
			DESCRIPTION
				"Description."
			::= { hwMacApOpticalInfoEntry 8 }

--   1.3.6.1.4.1.2011.6.139.2.6.19.1.9
-- 1.3.6.1.4.1.2011.6.139.2.6.19.1.9
		-- 1.3.6.1.4.1.2011.6.139.2.6.19.1.9
		hwMacApOpticalDdmTxPower OBJECT-TYPE
			SYNTAX Integer32
			MAX-ACCESS read-only
			STATUS current
			DESCRIPTION
				"Description."
			::= { hwMacApOpticalInfoEntry 9 }

--   1.3.6.1.4.1.2011.6.139.2.6.19.1.10
-- 1.3.6.1.4.1.2011.6.139.2.6.19.1.10
		-- 1.3.6.1.4.1.2011.6.139.2.6.19.1.10
		hwMacApOpticalDdmRxPower OBJECT-TYPE
			SYNTAX Integer32
			MAX-ACCESS read-only
			STATUS current
			DESCRIPTION
				"Description."
			::= { hwMacApOpticalInfoEntry 10 }

--   1.3.6.1.4.1.2011.6.139.2.6.19.1.11
-- 1.3.6.1.4.1.2011.6.139.2.6.19.1.11
		-- 1.3.6.1.4.1.2011.6.139.2.6.19.1.11
		hwMacApOpticalDdmTemperature OBJECT-TYPE
			SYNTAX Integer32
			MAX-ACCESS read-only
			STATUS current
			DESCRIPTION
				"Description."
			::= { hwMacApOpticalInfoEntry 11 }

--   1.3.6.1.4.1.2011.6.139.2.6.19.1.12
-- 1.3.6.1.4.1.2011.6.139.2.6.19.1.12
		-- 1.3.6.1.4.1.2011.6.139.2.6.19.1.12
		hwMacApOpticalVdndorOui OBJECT-TYPE
			SYNTAX Integer32
			MAX-ACCESS read-only
			STATUS current
			DESCRIPTION
				"Description."
			::= { hwMacApOpticalInfoEntry 12 }

--   1.3.6.1.4.1.2011.6.139.2.6.19.1.13
-- 1.3.6.1.4.1.2011.6.139.2.6.19.1.13
		-- 1.3.6.1.4.1.2011.6.139.2.6.19.1.13
		hwMacApOpticalVendorName OBJECT-TYPE
			SYNTAX OCTET STRING
			MAX-ACCESS read-only
			STATUS current
			DESCRIPTION
				"Description."
			::= { hwMacApOpticalInfoEntry 13 }

--   1.3.6.1.4.1.2011.6.139.2.6.19.1.14
-- 1.3.6.1.4.1.2011.6.139.2.6.19.1.14
		-- 1.3.6.1.4.1.2011.6.139.2.6.19.1.14
		hwMacApOpticalVendorPn OBJECT-TYPE
			SYNTAX OCTET STRING
			MAX-ACCESS read-only
			STATUS current
			DESCRIPTION
				"Description."
			::= { hwMacApOpticalInfoEntry 14 }

--   1.3.6.1.4.1.2011.6.139.2.6.19.1.15
-- 1.3.6.1.4.1.2011.6.139.2.6.19.1.15
		-- 1.3.6.1.4.1.2011.6.139.2.6.19.1.15
		hwMacApOpticalVendorRev OBJECT-TYPE
			SYNTAX OCTET STRING
			MAX-ACCESS read-only
			STATUS current
			DESCRIPTION
				"Description."
			::= { hwMacApOpticalInfoEntry 15 }

--   1.3.6.1.4.1.2011.6.139.2.6.19.1.16
-- 1.3.6.1.4.1.2011.6.139.2.6.19.1.16
		-- 1.3.6.1.4.1.2011.6.139.2.6.19.1.16
		hwMacApOpticalVendorSn OBJECT-TYPE
			SYNTAX OCTET STRING
			MAX-ACCESS read-only
			STATUS current
			DESCRIPTION
				"Description."
			::= { hwMacApOpticalInfoEntry 16 }

--  1.3.6.1.4.1.2011.6.139.2.6.20
		-- 1.3.6.1.4.1.2011.6.139.2.6.20
		hwApSysnameTable OBJECT-TYPE
			SYNTAX SEQUENCE OF HwApSysnameEntry
			MAX-ACCESS not-accessible
			STATUS current
			DESCRIPTION
				"Description."
			::= { hwApObjects 20 }

--  1.3.6.1.4.1.2011.6.139.2.6.20.1
		-- 1.3.6.1.4.1.2011.6.139.2.6.20.1
		hwApSysnameEntry OBJECT-TYPE
			SYNTAX HwApSysnameEntry
			MAX-ACCESS not-accessible
			STATUS current
			DESCRIPTION
				"Description."
			INDEX { hwApSysName }
			::= { hwApSysnameTable 1 }

		HwApSysnameEntry ::=
			SEQUENCE {
				hwApSysnameApId
					Integer32,
				hwApSysnameApMac
					MacAddress
			 }

--  1.3.6.1.4.1.2011.6.139.2.6.20.1.1
		-- 1.3.6.1.4.1.2011.6.139.2.6.20.1.1
		hwApSysnameApId OBJECT-TYPE
			SYNTAX Integer32
			MAX-ACCESS read-only
			STATUS current
			DESCRIPTION
				"Description."
			::= { hwApSysnameEntry 1 }

--  1.3.6.1.4.1.2011.6.139.2.6.20.1.2
		-- 1.3.6.1.4.1.2011.6.139.2.6.20.1.2
		hwApSysnameApMac OBJECT-TYPE
			SYNTAX MacAddress
			MAX-ACCESS read-only
			STATUS current
			DESCRIPTION
				"Description."
			::= { hwApSysnameEntry 2 }

--  1.3.6.1.4.1.2011.6.139.2.6.21
		-- 1.3.6.1.4.1.2011.6.139.2.6.21
		hwApPhysicalAttrTable OBJECT-TYPE
			SYNTAX SEQUENCE OF HwApPhysicalAttrEntry
			MAX-ACCESS not-accessible
			STATUS current
			DESCRIPTION
				"Description."
			::= { hwApObjects 21 }

--  1.3.6.1.4.1.2011.6.139.2.6.21.1
		-- 1.3.6.1.4.1.2011.6.139.2.6.21.1
		hwApPhysicalAttrEntry OBJECT-TYPE
			SYNTAX HwApPhysicalAttrEntry
			MAX-ACCESS not-accessible
			STATUS current
			DESCRIPTION
				"Description."
			INDEX { hwApIndex }
			::= { hwApPhysicalAttrTable 1 }

		HwApPhysicalAttrEntry ::=
			SEQUENCE {
				hwApElectronicLabel
					OCTET STRING
			 }

--  1.3.6.1.4.1.2011.6.139.2.6.21.1.1
		-- 1.3.6.1.4.1.2011.6.139.2.6.21.1.1
		hwApElectronicLabel OBJECT-TYPE
			SYNTAX OCTET STRING (SIZE (0..1025))
			MAX-ACCESS read-only
			STATUS current
			DESCRIPTION
				"Description."
			::= { hwApPhysicalAttrEntry 1 }

--  1.3.6.1.4.1.2011.6.139.2.6.22
		-- 1.3.6.1.4.1.2011.6.139.2.6.22
		hwMacApPhysicalAttrTable OBJECT-TYPE
			SYNTAX SEQUENCE OF HwMacApPhysicalAttrEntry
			MAX-ACCESS not-accessible
			STATUS current
			DESCRIPTION
				"Description."
			::= { hwApObjects 22 }

--  1.3.6.1.4.1.2011.6.139.2.6.22.1
		-- 1.3.6.1.4.1.2011.6.139.2.6.22.1
		hwMacApPhysicalAttrEntry OBJECT-TYPE
			SYNTAX HwMacApPhysicalAttrEntry
			MAX-ACCESS not-accessible
			STATUS current
			DESCRIPTION
				"Description."
			INDEX { hwMacApMac }
			::= { hwMacApPhysicalAttrTable 1 }

		HwMacApPhysicalAttrEntry ::=
			SEQUENCE {
				hwMacApElectronicLabel
					OCTET STRING
			 }

--  1.3.6.1.4.1.2011.6.139.2.6.22.1.1
		-- 1.3.6.1.4.1.2011.6.139.2.6.22.1.1
		hwMacApElectronicLabel OBJECT-TYPE
			SYNTAX OCTET STRING (SIZE (0..1025))
			MAX-ACCESS read-only
			STATUS current
			DESCRIPTION
				"Description."
			::= { hwMacApPhysicalAttrEntry 1 }

		-- 1.3.6.1.4.1.2011.6.139.2.6.23
		hwApLineportStatTable OBJECT-TYPE
			SYNTAX SEQUENCE OF HwApLineportStatEntry
			MAX-ACCESS not-accessible
			STATUS current
			DESCRIPTION
				"Description."
			::= { hwApObjects 23 }

		-- 1.3.6.1.4.1.2011.6.139.2.6.23.1
		hwApLineportStatEntry OBJECT-TYPE
			SYNTAX HwApLineportStatEntry
			MAX-ACCESS not-accessible
			STATUS current
			DESCRIPTION
				"Description."
			INDEX { hwApIndex, hwApLineatePortIndex }
			::= { hwApLineportStatTable 1 }

		HwApLineportStatEntry ::=
			SEQUENCE {
				hwApLinePortStatClear
					Integer32,
				hwApLinePortUpDwnTimes
					Unsigned32,
				hwApLinePortInPkts
					Counter64,
				hwApLinePortInUnicastPkts
					Counter64,
				hwApLinePortInNonUnicastPkts
					Counter64,
				hwApLinePortInBytes
					Counter64,
				hwApLinePortInErrorPkts
					Counter64,
				hwApLinePortInDiscardPkts
					Counter64,
				hwApLinePortOutPkts
					Counter64,
				hwApLinePortOutUnicastPkts
					Counter64,
				hwApLinePortOutNonUnicastPkts
					Counter64,
				hwApLinePortOutBytes
					Counter64,
				hwApLinePortOutErrorsPkts
					Counter64,
				hwApLinePortOutDiscardPkts
					Counter64
			 }

		-- 1.3.6.1.4.1.2011.6.139.2.6.23.1.1
		hwApLinePortStatClear OBJECT-TYPE
			SYNTAX Integer32
			MAX-ACCESS read-write
			STATUS current
			DESCRIPTION
				"Description."
			::= { hwApLineportStatEntry 1 }

		-- 1.3.6.1.4.1.2011.6.139.2.6.23.1.2
		hwApLinePortUpDwnTimes OBJECT-TYPE
			SYNTAX Unsigned32
			MAX-ACCESS read-only
			STATUS current
			DESCRIPTION
				"Description."
			::= { hwApLineportStatEntry 2 }

		-- 1.3.6.1.4.1.2011.6.139.2.6.23.1.3
		hwApLinePortInPkts OBJECT-TYPE
			SYNTAX Counter64
			MAX-ACCESS read-only
			STATUS current
			DESCRIPTION
				"Description."
			::= { hwApLineportStatEntry 3 }

		-- 1.3.6.1.4.1.2011.6.139.2.6.23.1.4
		hwApLinePortInUnicastPkts OBJECT-TYPE
			SYNTAX Counter64
			MAX-ACCESS read-only
			STATUS current
			DESCRIPTION
				"Description."
			::= { hwApLineportStatEntry 4 }

		-- 1.3.6.1.4.1.2011.6.139.2.6.23.1.5
		hwApLinePortInNonUnicastPkts OBJECT-TYPE
			SYNTAX Counter64
			MAX-ACCESS read-only
			STATUS current
			DESCRIPTION
				"Description."
			::= { hwApLineportStatEntry 5 }

		-- 1.3.6.1.4.1.2011.6.139.2.6.23.1.6
		hwApLinePortInBytes OBJECT-TYPE
			SYNTAX Counter64
			MAX-ACCESS read-only
			STATUS current
			DESCRIPTION
				"Description."
			::= { hwApLineportStatEntry 6 }

		-- 1.3.6.1.4.1.2011.6.139.2.6.23.1.7
		hwApLinePortInErrorPkts OBJECT-TYPE
			SYNTAX Counter64
			MAX-ACCESS read-only
			STATUS current
			DESCRIPTION
				"Description."
			::= { hwApLineportStatEntry 7 }

		-- 1.3.6.1.4.1.2011.6.139.2.6.23.1.8
		hwApLinePortInDiscardPkts OBJECT-TYPE
			SYNTAX Counter64
			MAX-ACCESS read-only
			STATUS current
			DESCRIPTION
				"Description."
			::= { hwApLineportStatEntry 8 }

		-- 1.3.6.1.4.1.2011.6.139.2.6.23.1.9
		hwApLinePortOutPkts OBJECT-TYPE
			SYNTAX Counter64
			MAX-ACCESS read-only
			STATUS current
			DESCRIPTION
				"Description."
			::= { hwApLineportStatEntry 9 }

		-- 1.3.6.1.4.1.2011.6.139.2.6.23.1.10
		hwApLinePortOutUnicastPkts OBJECT-TYPE
			SYNTAX Counter64
			MAX-ACCESS read-only
			STATUS current
			DESCRIPTION
				"Description."
			::= { hwApLineportStatEntry 10 }

		-- 1.3.6.1.4.1.2011.6.139.2.6.23.1.11
		hwApLinePortOutNonUnicastPkts OBJECT-TYPE
			SYNTAX Counter64
			MAX-ACCESS read-only
			STATUS current
			DESCRIPTION
				"Description."
			::= { hwApLineportStatEntry 11 }

		-- 1.3.6.1.4.1.2011.6.139.2.6.23.1.12
		hwApLinePortOutBytes OBJECT-TYPE
			SYNTAX Counter64
			MAX-ACCESS read-only
			STATUS current
			DESCRIPTION
				"Description."
			::= { hwApLineportStatEntry 12 }

		-- 1.3.6.1.4.1.2011.6.139.2.6.23.1.13
		hwApLinePortOutErrorsPkts OBJECT-TYPE
			SYNTAX Counter64
			MAX-ACCESS read-only
			STATUS current
			DESCRIPTION
				"Description."
			::= { hwApLineportStatEntry 13 }

		-- 1.3.6.1.4.1.2011.6.139.2.6.23.1.14
		hwApLinePortOutDiscardPkts OBJECT-TYPE
			SYNTAX Counter64
			MAX-ACCESS read-only
			STATUS current
			DESCRIPTION
				"Description."
			::= { hwApLineportStatEntry 14 }

		-- 1.3.6.1.4.1.2011.6.139.2.6.24
		hwMacApLineportStatTable OBJECT-TYPE
			SYNTAX SEQUENCE OF HwMacApLineportStatEntry
			MAX-ACCESS not-accessible
			STATUS current
			DESCRIPTION
				"Description."
			::= { hwApObjects 24 }

		-- 1.3.6.1.4.1.2011.6.139.2.6.24.1
		hwMacApLineportStatEntry OBJECT-TYPE
			SYNTAX HwMacApLineportStatEntry
			MAX-ACCESS not-accessible
			STATUS current
			DESCRIPTION
				"Description."
			INDEX { hwMacApMac, hwMacApLineatePortIndex }
			::= { hwMacApLineportStatTable 1 }

		HwMacApLineportStatEntry ::=
			SEQUENCE {
				hwMacApLinePortStatClear
					Integer32,
				hwMacApLinePortUpDwnTimes
					Unsigned32,
				hwMacApLinePortInPkts
					Counter64,
				hwMacApLinePortInUnicastPkts
					Counter64,
				hwMacApLinePortInNonUnicastPkts
					Counter64,
				hwMacApLinePortInBytes
					Counter64,
				hwMacApLinePortInErrorPkts
					Counter64,
				hwMacApLinePortInDiscardPkts
					Counter64,
				hwMacApLinePortOutPkts
					Counter64,
				hwMacApLinePortOutUnicastPkts
					Counter64,
				hwMacApLinePortOutNonUnicastPkts
					Counter64,
				hwMacApLinePortOutBytes
					Counter64,
				hwMacApLinePortOutErrorsPkts
					Counter64,
				hwMacApLinePortOutDiscardPkts
					Counter64
			 }

		-- 1.3.6.1.4.1.2011.6.139.2.6.24.1.1
		hwMacApLinePortStatClear OBJECT-TYPE
			SYNTAX Integer32
			MAX-ACCESS read-write
			STATUS current
			DESCRIPTION
				"Description."
			::= { hwMacApLineportStatEntry 1 }

		-- 1.3.6.1.4.1.2011.6.139.2.6.24.1.2
		hwMacApLinePortUpDwnTimes OBJECT-TYPE
			SYNTAX Unsigned32
			MAX-ACCESS read-only
			STATUS current
			DESCRIPTION
				"Description."
			::= { hwMacApLineportStatEntry 2 }

		-- 1.3.6.1.4.1.2011.6.139.2.6.24.1.3
		hwMacApLinePortInPkts OBJECT-TYPE
			SYNTAX Counter64
			MAX-ACCESS read-only
			STATUS current
			DESCRIPTION
				"Description."
			::= { hwMacApLineportStatEntry 3 }

		-- 1.3.6.1.4.1.2011.6.139.2.6.24.1.4
		hwMacApLinePortInUnicastPkts OBJECT-TYPE
			SYNTAX Counter64
			MAX-ACCESS read-only
			STATUS current
			DESCRIPTION
				"Description."
			::= { hwMacApLineportStatEntry 4 }

		-- 1.3.6.1.4.1.2011.6.139.2.6.24.1.5
		hwMacApLinePortInNonUnicastPkts OBJECT-TYPE
			SYNTAX Counter64
			MAX-ACCESS read-only
			STATUS current
			DESCRIPTION
				"Description."
			::= { hwMacApLineportStatEntry 5 }

		-- 1.3.6.1.4.1.2011.6.139.2.6.24.1.6
		hwMacApLinePortInBytes OBJECT-TYPE
			SYNTAX Counter64
			MAX-ACCESS read-only
			STATUS current
			DESCRIPTION
				"Description."
			::= { hwMacApLineportStatEntry 6 }

		-- 1.3.6.1.4.1.2011.6.139.2.6.24.1.7
		hwMacApLinePortInErrorPkts OBJECT-TYPE
			SYNTAX Counter64
			MAX-ACCESS read-only
			STATUS current
			DESCRIPTION
				"Description."
			::= { hwMacApLineportStatEntry 7 }

		-- 1.3.6.1.4.1.2011.6.139.2.6.24.1.8
		hwMacApLinePortInDiscardPkts OBJECT-TYPE
			SYNTAX Counter64
			MAX-ACCESS read-only
			STATUS current
			DESCRIPTION
				"Description."
			::= { hwMacApLineportStatEntry 8 }

		-- 1.3.6.1.4.1.2011.6.139.2.6.24.1.9
		hwMacApLinePortOutPkts OBJECT-TYPE
			SYNTAX Counter64
			MAX-ACCESS read-only
			STATUS current
			DESCRIPTION
				"Description."
			::= { hwMacApLineportStatEntry 9 }

		-- 1.3.6.1.4.1.2011.6.139.2.6.24.1.10
		hwMacApLinePortOutUnicastPkts OBJECT-TYPE
			SYNTAX Counter64
			MAX-ACCESS read-only
			STATUS current
			DESCRIPTION
				"Description."
			::= { hwMacApLineportStatEntry 10 }

		-- 1.3.6.1.4.1.2011.6.139.2.6.24.1.11
		hwMacApLinePortOutNonUnicastPkts OBJECT-TYPE
			SYNTAX Counter64
			MAX-ACCESS read-only
			STATUS current
			DESCRIPTION
				"Description."
			::= { hwMacApLineportStatEntry 11 }

		-- 1.3.6.1.4.1.2011.6.139.2.6.24.1.12
		hwMacApLinePortOutBytes OBJECT-TYPE
			SYNTAX Counter64
			MAX-ACCESS read-only
			STATUS current
			DESCRIPTION
				"Description."
			::= { hwMacApLineportStatEntry 12 }

		-- 1.3.6.1.4.1.2011.6.139.2.6.24.1.13
		hwMacApLinePortOutErrorsPkts OBJECT-TYPE
			SYNTAX Counter64
			MAX-ACCESS read-only
			STATUS current
			DESCRIPTION
				"Description."
			::= { hwMacApLineportStatEntry 13 }

		-- 1.3.6.1.4.1.2011.6.139.2.6.24.1.14
		hwMacApLinePortOutDiscardPkts OBJECT-TYPE
			SYNTAX Counter64
			MAX-ACCESS read-only
			STATUS current
			DESCRIPTION
				"Description."
			::= { hwMacApLineportStatEntry 14 }

--          1.3.6.1.4.1.2011.6.139.2.6.25
-- 1.3.6.1.4.1.2011.6.139.2.6.25
-- 1.3.6.1.4.1.2011.6.139.2.6.25
-- 1.3.6.1.4.1.2011.6.139.2.6.25
-- 1.3.6.1.4.1.2011.6.139.2.6.25
-- 1.3.6.1.4.1.2011.6.139.2.6.25
-- 1.3.6.1.4.1.2011.6.139.2.6.25
-- 1.3.6.1.4.1.2011.6.139.2.6.25
-- 1.3.6.1.4.1.2011.6.139.2.6.25
		-- 1.3.6.1.4.1.2011.6.139.2.6.25
		hwApLineatePortLldpCfgTable OBJECT-TYPE
			SYNTAX SEQUENCE OF HwApLineatePortLldpCfgEntry
			MAX-ACCESS not-accessible
			STATUS current
			DESCRIPTION
				"Description."
			::= { hwApObjects 25 }


--          1.3.6.1.4.1.2011.6.139.2.6.25.1
-- 1.3.6.1.4.1.2011.6.139.2.6.25.1
-- 1.3.6.1.4.1.2011.6.139.2.6.25.1
-- 1.3.6.1.4.1.2011.6.139.2.6.25.1
-- 1.3.6.1.4.1.2011.6.139.2.6.25.1
-- 1.3.6.1.4.1.2011.6.139.2.6.25.1
-- 1.3.6.1.4.1.2011.6.139.2.6.25.1
-- 1.3.6.1.4.1.2011.6.139.2.6.25.1
-- 1.3.6.1.4.1.2011.6.139.2.6.25.1
		-- 1.3.6.1.4.1.2011.6.139.2.6.25.1
		hwApLineatePortLldpCfgEntry OBJECT-TYPE
			SYNTAX HwApLineatePortLldpCfgEntry
			MAX-ACCESS not-accessible
			STATUS current
			DESCRIPTION
				"Description."
			INDEX { hwApIndex, hwApLldpRemLocalPortNum, hwApLineatePortLldpIndex }
			::= { hwApLineatePortLldpCfgTable 1 }


		HwApLineatePortLldpCfgEntry ::=
			SEQUENCE {
				hwApLineatePortLldpIndex
					Integer32,
				hwApLineatePortLldpEnable
					Integer32,
				hwApLineatePortLldpManageAddr
					Integer32,
				hwApLineatePortLldpPortDes
					Integer32,
				hwApLineatePortLldpSysCab
					Integer32,
				hwApLineatePortLldpSysDes
					Integer32,
				hwApLineatePortLldpSysName
					Integer32,
				hwApLineatePortLldpDelay
					Integer32,
				hwApLineatePortLldpHoldMultiplier
					Integer32,
				hwApLineatePortLldpInterval
					Integer32,
				hwApLineatePortLldpRestartDelay
					Integer32,
				hwApLineatePortLldpAdminStatus
					Integer32,
				hwApLineatePortLldpReportInterval
					Unsigned32
			 }

--          1.3.6.1.4.1.2011.6.139.2.6.25.1.1
-- 1.3.6.1.4.1.2011.6.139.2.6.25.1.1
-- 1.3.6.1.4.1.2011.6.139.2.6.25.1.1
-- 1.3.6.1.4.1.2011.6.139.2.6.25.1.1
-- 1.3.6.1.4.1.2011.6.139.2.6.25.1.1
-- 1.3.6.1.4.1.2011.6.139.2.6.25.1.1
-- 1.3.6.1.4.1.2011.6.139.2.6.25.1.1
-- 1.3.6.1.4.1.2011.6.139.2.6.25.1.1
-- 1.3.6.1.4.1.2011.6.139.2.6.25.1.1
		-- 1.3.6.1.4.1.2011.6.139.2.6.25.1.1
		hwApLineatePortLldpIndex OBJECT-TYPE
			SYNTAX Integer32
			MAX-ACCESS not-accessible
			STATUS current
			DESCRIPTION
				"Description."
			::= { hwApLineatePortLldpCfgEntry 1 }


--          1.3.6.1.4.1.2011.6.139.2.6.25.1.2
-- 1.3.6.1.4.1.2011.6.139.2.6.25.1.2
-- 1.3.6.1.4.1.2011.6.139.2.6.25.1.2
-- 1.3.6.1.4.1.2011.6.139.2.6.25.1.2
-- 1.3.6.1.4.1.2011.6.139.2.6.25.1.2
-- 1.3.6.1.4.1.2011.6.139.2.6.25.1.2
-- 1.3.6.1.4.1.2011.6.139.2.6.25.1.2
-- 1.3.6.1.4.1.2011.6.139.2.6.25.1.2
-- 1.3.6.1.4.1.2011.6.139.2.6.25.1.2
		-- 1.3.6.1.4.1.2011.6.139.2.6.25.1.2
		hwApLineatePortLldpEnable OBJECT-TYPE
			SYNTAX Integer32 (0..1)
			MAX-ACCESS read-write
			STATUS current
			DESCRIPTION
				"Description."
			::= { hwApLineatePortLldpCfgEntry 2 }


--          1.3.6.1.4.1.2011.6.139.2.6.25.1.3
-- 1.3.6.1.4.1.2011.6.139.2.6.25.1.3
-- 1.3.6.1.4.1.2011.6.139.2.6.25.1.3
-- 1.3.6.1.4.1.2011.6.139.2.6.25.1.3
-- 1.3.6.1.4.1.2011.6.139.2.6.25.1.3
-- 1.3.6.1.4.1.2011.6.139.2.6.25.1.3
-- 1.3.6.1.4.1.2011.6.139.2.6.25.1.3
-- 1.3.6.1.4.1.2011.6.139.2.6.25.1.3
-- 1.3.6.1.4.1.2011.6.139.2.6.25.1.3
		-- 1.3.6.1.4.1.2011.6.139.2.6.25.1.3
		hwApLineatePortLldpManageAddr OBJECT-TYPE
			SYNTAX Integer32 (0..1)
			MAX-ACCESS read-write
			STATUS current
			DESCRIPTION
				"Description."
			::= { hwApLineatePortLldpCfgEntry 3 }


--          1.3.6.1.4.1.2011.6.139.2.6.25.1.4
-- 1.3.6.1.4.1.2011.6.139.2.6.25.1.4
-- 1.3.6.1.4.1.2011.6.139.2.6.25.1.4
-- 1.3.6.1.4.1.2011.6.139.2.6.25.1.4
-- 1.3.6.1.4.1.2011.6.139.2.6.25.1.4
-- 1.3.6.1.4.1.2011.6.139.2.6.25.1.4
-- 1.3.6.1.4.1.2011.6.139.2.6.25.1.4
-- 1.3.6.1.4.1.2011.6.139.2.6.25.1.4
-- 1.3.6.1.4.1.2011.6.139.2.6.25.1.4
		-- 1.3.6.1.4.1.2011.6.139.2.6.25.1.4
		hwApLineatePortLldpPortDes OBJECT-TYPE
			SYNTAX Integer32 (0..1)
			MAX-ACCESS read-write
			STATUS current
			DESCRIPTION
				"Description."
			::= { hwApLineatePortLldpCfgEntry 4 }


--          1.3.6.1.4.1.2011.6.139.2.6.25.1.5
-- 1.3.6.1.4.1.2011.6.139.2.6.25.1.5
-- 1.3.6.1.4.1.2011.6.139.2.6.25.1.5
-- 1.3.6.1.4.1.2011.6.139.2.6.25.1.5
-- 1.3.6.1.4.1.2011.6.139.2.6.25.1.5
-- 1.3.6.1.4.1.2011.6.139.2.6.25.1.5
-- 1.3.6.1.4.1.2011.6.139.2.6.25.1.5
-- 1.3.6.1.4.1.2011.6.139.2.6.25.1.5
-- 1.3.6.1.4.1.2011.6.139.2.6.25.1.5
		-- 1.3.6.1.4.1.2011.6.139.2.6.25.1.5
		hwApLineatePortLldpSysCab OBJECT-TYPE
			SYNTAX Integer32 (0..1)
			MAX-ACCESS read-write
			STATUS current
			DESCRIPTION
				"Description."
			::= { hwApLineatePortLldpCfgEntry 5 }


--          1.3.6.1.4.1.2011.6.139.2.6.25.1.6
-- 1.3.6.1.4.1.2011.6.139.2.6.25.1.6
-- 1.3.6.1.4.1.2011.6.139.2.6.25.1.6
-- 1.3.6.1.4.1.2011.6.139.2.6.25.1.6
-- 1.3.6.1.4.1.2011.6.139.2.6.25.1.6
-- 1.3.6.1.4.1.2011.6.139.2.6.25.1.6
-- 1.3.6.1.4.1.2011.6.139.2.6.25.1.6
-- 1.3.6.1.4.1.2011.6.139.2.6.25.1.6
-- 1.3.6.1.4.1.2011.6.139.2.6.25.1.6
		-- 1.3.6.1.4.1.2011.6.139.2.6.25.1.6
		hwApLineatePortLldpSysDes OBJECT-TYPE
			SYNTAX Integer32 (0..1)
			MAX-ACCESS read-write
			STATUS current
			DESCRIPTION
				"Description."
			::= { hwApLineatePortLldpCfgEntry 6 }


--          1.3.6.1.4.1.2011.6.139.2.6.25.1.7
-- 1.3.6.1.4.1.2011.6.139.2.6.25.1.7
-- 1.3.6.1.4.1.2011.6.139.2.6.25.1.7
-- 1.3.6.1.4.1.2011.6.139.2.6.25.1.7
-- 1.3.6.1.4.1.2011.6.139.2.6.25.1.7
-- 1.3.6.1.4.1.2011.6.139.2.6.25.1.7
-- 1.3.6.1.4.1.2011.6.139.2.6.25.1.7
-- 1.3.6.1.4.1.2011.6.139.2.6.25.1.7
-- 1.3.6.1.4.1.2011.6.139.2.6.25.1.7
		-- 1.3.6.1.4.1.2011.6.139.2.6.25.1.7
		hwApLineatePortLldpSysName OBJECT-TYPE
			SYNTAX Integer32 (0..1)
			MAX-ACCESS read-write
			STATUS current
			DESCRIPTION
				"Description."
			::= { hwApLineatePortLldpCfgEntry 7 }


--          1.3.6.1.4.1.2011.6.139.2.6.25.1.8
-- 1.3.6.1.4.1.2011.6.139.2.6.25.1.8
-- 1.3.6.1.4.1.2011.6.139.2.6.25.1.8
-- 1.3.6.1.4.1.2011.6.139.2.6.25.1.8
-- 1.3.6.1.4.1.2011.6.139.2.6.25.1.8
-- 1.3.6.1.4.1.2011.6.139.2.6.25.1.8
-- 1.3.6.1.4.1.2011.6.139.2.6.25.1.8
-- 1.3.6.1.4.1.2011.6.139.2.6.25.1.8
-- 1.3.6.1.4.1.2011.6.139.2.6.25.1.8
		-- 1.3.6.1.4.1.2011.6.139.2.6.23.1.8
		hwApLineatePortLldpDelay OBJECT-TYPE
			SYNTAX Integer32
			MAX-ACCESS read-write
			STATUS current
			DESCRIPTION
				"Description."
			::= { hwApLineatePortLldpCfgEntry 8 }


--          1.3.6.1.4.1.2011.6.139.2.6.25.1.9
-- 1.3.6.1.4.1.2011.6.139.2.6.25.1.9
-- 1.3.6.1.4.1.2011.6.139.2.6.25.1.9
-- 1.3.6.1.4.1.2011.6.139.2.6.25.1.9
-- 1.3.6.1.4.1.2011.6.139.2.6.25.1.9
-- 1.3.6.1.4.1.2011.6.139.2.6.25.1.9
-- 1.3.6.1.4.1.2011.6.139.2.6.25.1.9
-- 1.3.6.1.4.1.2011.6.139.2.6.25.1.9
-- 1.3.6.1.4.1.2011.6.139.2.6.25.1.9
		-- 1.3.6.1.4.1.2011.6.139.2.6.25.1.9
		hwApLineatePortLldpHoldMultiplier OBJECT-TYPE
			SYNTAX Integer32
			MAX-ACCESS read-write
			STATUS current
			DESCRIPTION
				"Description."
			::= { hwApLineatePortLldpCfgEntry 9 }


--          1.3.6.1.4.1.2011.6.139.2.6.25.1.10
-- 1.3.6.1.4.1.2011.6.139.2.6.25.1.10
-- 1.3.6.1.4.1.2011.6.139.2.6.25.1.10
-- 1.3.6.1.4.1.2011.6.139.2.6.25.1.10
-- 1.3.6.1.4.1.2011.6.139.2.6.25.1.10
-- 1.3.6.1.4.1.2011.6.139.2.6.25.1.10
-- 1.3.6.1.4.1.2011.6.139.2.6.25.1.10
-- 1.3.6.1.4.1.2011.6.139.2.6.25.1.10
-- 1.3.6.1.4.1.2011.6.139.2.6.25.1.10
		-- 1.3.6.1.4.1.2011.6.139.2.6.25.1.10
		hwApLineatePortLldpInterval OBJECT-TYPE
			SYNTAX Integer32
			MAX-ACCESS read-write
			STATUS current
			DESCRIPTION
				"Description."
			::= { hwApLineatePortLldpCfgEntry 10 }


--          1.3.6.1.4.1.2011.6.139.2.6.25.1.11
-- 1.3.6.1.4.1.2011.6.139.2.6.25.1.11
-- 1.3.6.1.4.1.2011.6.139.2.6.25.1.11
-- 1.3.6.1.4.1.2011.6.139.2.6.25.1.11
-- 1.3.6.1.4.1.2011.6.139.2.6.25.1.11
-- 1.3.6.1.4.1.2011.6.139.2.6.25.1.11
-- 1.3.6.1.4.1.2011.6.139.2.6.25.1.11
-- 1.3.6.1.4.1.2011.6.139.2.6.25.1.11
-- 1.3.6.1.4.1.2011.6.139.2.6.25.1.11
		-- 1.3.6.1.4.1.2011.6.139.2.6.25.1.11
		hwApLineatePortLldpRestartDelay OBJECT-TYPE
			SYNTAX Integer32
			MAX-ACCESS read-write
			STATUS current
			DESCRIPTION
				"Description."
			::= { hwApLineatePortLldpCfgEntry 11 }


--          1.3.6.1.4.1.2011.6.139.2.6.25.1.12
-- 1.3.6.1.4.1.2011.6.139.2.6.25.1.12
-- 1.3.6.1.4.1.2011.6.139.2.6.25.1.12
-- 1.3.6.1.4.1.2011.6.139.2.6.25.1.12
-- 1.3.6.1.4.1.2011.6.139.2.6.25.1.12
-- 1.3.6.1.4.1.2011.6.139.2.6.25.1.12
-- 1.3.6.1.4.1.2011.6.139.2.6.25.1.12
-- 1.3.6.1.4.1.2011.6.139.2.6.25.1.12
-- 1.3.6.1.4.1.2011.6.139.2.6.25.1.12
		-- 1.3.6.1.4.1.2011.6.139.2.6.25.1.12
		hwApLineatePortLldpAdminStatus OBJECT-TYPE
			SYNTAX Integer32 (0..2)
			MAX-ACCESS read-write
			STATUS current
			DESCRIPTION
				"Description."
			::= { hwApLineatePortLldpCfgEntry 12 }


--          1.3.6.1.4.1.2011.6.139.2.6.25.1.13
-- 1.3.6.1.4.1.2011.6.139.2.6.25.1.13
-- 1.3.6.1.4.1.2011.6.139.2.6.25.1.13
-- 1.3.6.1.4.1.2011.6.139.2.6.25.1.13
-- 1.3.6.1.4.1.2011.6.139.2.6.25.1.13
-- 1.3.6.1.4.1.2011.6.139.2.6.25.1.13
-- 1.3.6.1.4.1.2011.6.139.2.6.25.1.13
-- 1.3.6.1.4.1.2011.6.139.2.6.25.1.13
-- 1.3.6.1.4.1.2011.6.139.2.6.25.1.13
		-- 1.3.6.1.4.1.2011.6.139.2.6.25.1.13
		hwApLineatePortLldpReportInterval OBJECT-TYPE
			SYNTAX Unsigned32
			MAX-ACCESS read-write
			STATUS current
			DESCRIPTION
				"Description."
			::= { hwApLineatePortLldpCfgEntry 13 }


--      1.3.6.1.4.1.2011.6.139.2.6.26
-- 1.3.6.1.4.1.2011.6.139.2.6.26
-- 1.3.6.1.4.1.2011.6.139.2.6.26
-- 1.3.6.1.4.1.2011.6.139.2.6.26
-- 1.3.6.1.4.1.2011.6.139.2.6.26
		-- 1.3.6.1.4.1.2011.6.139.2.6.26
		hwMacApLineatePortLldpCfgTable OBJECT-TYPE
			SYNTAX SEQUENCE OF HwMacApLineatePortLldpCfgEntry
			MAX-ACCESS not-accessible
			STATUS current
			DESCRIPTION
				"Description."
			::= { hwApObjects 26 }


--      1.3.6.1.4.1.2011.6.139.2.6.26.1
-- 1.3.6.1.4.1.2011.6.139.2.6.26.1
-- 1.3.6.1.4.1.2011.6.139.2.6.26.1
-- 1.3.6.1.4.1.2011.6.139.2.6.26.1
-- 1.3.6.1.4.1.2011.6.139.2.6.26.1
		-- 1.3.6.1.4.1.2011.6.139.2.6.26.1
		hwMacApLineatePortLldpCfgEntry OBJECT-TYPE
			SYNTAX HwMacApLineatePortLldpCfgEntry
			MAX-ACCESS not-accessible
			STATUS current
			DESCRIPTION
				"Description."
			INDEX { hwMacApLineatePortLldpIndex, hwMacApMac }
			::= { hwMacApLineatePortLldpCfgTable 1 }


		HwMacApLineatePortLldpCfgEntry ::=
			SEQUENCE {
				hwMacApLineatePortLldpIndex
					Integer32,
				hwMacApLineatePortLldpEnable
					Integer32,
				hwMacApLineatePortLldpManageAddr
					Integer32,
				hwMacApLineatePortLldpPortDes
					Integer32,
				hwMacApLineatePortLldpSysCab
					Integer32,
				hwMacApLineatePortLldpSysDes
					Integer32,
				hwMacApLineatePortLldpSysName
					Integer32,
				hwMacApLineatePortLldpDelay
					Integer32,
				hwMacApLineatePortLldpHoldMultiplier
					Integer32,
				hwMacApLineatePortLldpInterval
					Integer32,
				hwMacApLineatePortLldpRestartDelay
					Integer32,
				hwMacApLineatePortLldpAdminStatus
					Integer32,
				hwMacApLineatePortLldpReportInterval
					Integer32
			 }

--      1.3.6.1.4.1.2011.6.139.2.6.26.1.1
-- 1.3.6.1.4.1.2011.6.139.2.6.26.1.1
-- 1.3.6.1.4.1.2011.6.139.2.6.26.1.1
-- 1.3.6.1.4.1.2011.6.139.2.6.26.1.1
-- 1.3.6.1.4.1.2011.6.139.2.6.26.1.1
		-- 1.3.6.1.4.1.2011.6.139.2.6.26.1.1
		hwMacApLineatePortLldpIndex OBJECT-TYPE
			SYNTAX Integer32
			MAX-ACCESS not-accessible
			STATUS current
			DESCRIPTION
				"Description."
			::= { hwMacApLineatePortLldpCfgEntry 1 }


--      1.3.6.1.4.1.2011.6.139.2.6.26.1.2
-- 1.3.6.1.4.1.2011.6.139.2.6.26.1.2
-- 1.3.6.1.4.1.2011.6.139.2.6.26.1.2
-- 1.3.6.1.4.1.2011.6.139.2.6.26.1.2
-- 1.3.6.1.4.1.2011.6.139.2.6.26.1.2
		-- 1.3.6.1.4.1.2011.6.139.2.6.26.1.2
		hwMacApLineatePortLldpEnable OBJECT-TYPE
			SYNTAX Integer32 (0..1)
			MAX-ACCESS read-write
			STATUS current
			DESCRIPTION
				"Description."
			::= { hwMacApLineatePortLldpCfgEntry 2 }


--      1.3.6.1.4.1.2011.6.139.2.6.26.1.3
-- 1.3.6.1.4.1.2011.6.139.2.6.26.1.3
-- 1.3.6.1.4.1.2011.6.139.2.6.26.1.3
-- 1.3.6.1.4.1.2011.6.139.2.6.26.1.3
-- 1.3.6.1.4.1.2011.6.139.2.6.26.1.3
		-- 1.3.6.1.4.1.2011.6.139.2.6.26.1.3
		hwMacApLineatePortLldpManageAddr OBJECT-TYPE
			SYNTAX Integer32 (0..1)
			MAX-ACCESS read-write
			STATUS current
			DESCRIPTION
				"Description."
			::= { hwMacApLineatePortLldpCfgEntry 3 }


--      1.3.6.1.4.1.2011.6.139.2.6.26.1.4
-- 1.3.6.1.4.1.2011.6.139.2.6.26.1.4
-- 1.3.6.1.4.1.2011.6.139.2.6.26.1.4
-- 1.3.6.1.4.1.2011.6.139.2.6.26.1.4
-- 1.3.6.1.4.1.2011.6.139.2.6.26.1.4
		-- 1.3.6.1.4.1.2011.6.139.2.6.26.1.4
		hwMacApLineatePortLldpPortDes OBJECT-TYPE
			SYNTAX Integer32 (0..1)
			MAX-ACCESS read-write
			STATUS current
			DESCRIPTION
				"Description."
			::= { hwMacApLineatePortLldpCfgEntry 4 }


--      1.3.6.1.4.1.2011.6.139.2.6.26.1.5
-- 1.3.6.1.4.1.2011.6.139.2.6.26.1.5
-- 1.3.6.1.4.1.2011.6.139.2.6.26.1.5
-- 1.3.6.1.4.1.2011.6.139.2.6.26.1.5
-- 1.3.6.1.4.1.2011.6.139.2.6.26.1.5
		-- 1.3.6.1.4.1.2011.6.139.2.6.26.1.5
		hwMacApLineatePortLldpSysCab OBJECT-TYPE
			SYNTAX Integer32 (0..1)
			MAX-ACCESS read-write
			STATUS current
			DESCRIPTION
				"Description."
			::= { hwMacApLineatePortLldpCfgEntry 5 }


--      1.3.6.1.4.1.2011.6.139.2.6.26.1.6
-- 1.3.6.1.4.1.2011.6.139.2.6.26.1.6
-- 1.3.6.1.4.1.2011.6.139.2.6.26.1.6
-- 1.3.6.1.4.1.2011.6.139.2.6.26.1.6
-- 1.3.6.1.4.1.2011.6.139.2.6.26.1.6
		-- 1.3.6.1.4.1.2011.6.139.2.6.26.1.6
		hwMacApLineatePortLldpSysDes OBJECT-TYPE
			SYNTAX Integer32 (0..1)
			MAX-ACCESS read-write
			STATUS current
			DESCRIPTION
				"Description."
			::= { hwMacApLineatePortLldpCfgEntry 6 }


--      1.3.6.1.4.1.2011.6.139.2.6.26.1.7
-- 1.3.6.1.4.1.2011.6.139.2.6.26.1.7
-- 1.3.6.1.4.1.2011.6.139.2.6.26.1.7
-- 1.3.6.1.4.1.2011.6.139.2.6.26.1.7
-- 1.3.6.1.4.1.2011.6.139.2.6.26.1.7
		-- 1.3.6.1.4.1.2011.6.139.2.6.26.1.7
		hwMacApLineatePortLldpSysName OBJECT-TYPE
			SYNTAX Integer32 (0..1)
			MAX-ACCESS read-write
			STATUS current
			DESCRIPTION
				"Description."
			::= { hwMacApLineatePortLldpCfgEntry 7 }


--      1.3.6.1.4.1.2011.6.139.2.6.26.1.8
-- 1.3.6.1.4.1.2011.6.139.2.6.26.1.8
-- 1.3.6.1.4.1.2011.6.139.2.6.26.1.8
-- 1.3.6.1.4.1.2011.6.139.2.6.26.1.8
-- 1.3.6.1.4.1.2011.6.139.2.6.26.1.8
		-- 1.3.6.1.4.1.2011.6.139.2.6.26.1.8
		hwMacApLineatePortLldpDelay OBJECT-TYPE
			SYNTAX Integer32
			MAX-ACCESS read-write
			STATUS current
			DESCRIPTION
				"Description."
			::= { hwMacApLineatePortLldpCfgEntry 8 }


--      1.3.6.1.4.1.2011.6.139.2.6.26.1.9
-- 1.3.6.1.4.1.2011.6.139.2.6.26.1.9
-- 1.3.6.1.4.1.2011.6.139.2.6.26.1.9
-- 1.3.6.1.4.1.2011.6.139.2.6.26.1.9
-- 1.3.6.1.4.1.2011.6.139.2.6.26.1.9
		-- 1.3.6.1.4.1.2011.6.139.2.6.26.1.9
		hwMacApLineatePortLldpHoldMultiplier OBJECT-TYPE
			SYNTAX Integer32
			MAX-ACCESS read-write
			STATUS current
			DESCRIPTION
				"Description."
			::= { hwMacApLineatePortLldpCfgEntry 9 }


--      1.3.6.1.4.1.2011.6.139.2.6.26.1.10
-- 1.3.6.1.4.1.2011.6.139.2.6.26.1.10
-- 1.3.6.1.4.1.2011.6.139.2.6.26.1.10
-- 1.3.6.1.4.1.2011.6.139.2.6.26.1.10
-- 1.3.6.1.4.1.2011.6.139.2.6.26.1.10
		-- 1.3.6.1.4.1.2011.6.139.2.6.26.1.10
		hwMacApLineatePortLldpInterval OBJECT-TYPE
			SYNTAX Integer32
			MAX-ACCESS read-write
			STATUS current
			DESCRIPTION
				"Description."
			::= { hwMacApLineatePortLldpCfgEntry 10 }


--      1.3.6.1.4.1.2011.6.139.2.6.26.1.11
-- 1.3.6.1.4.1.2011.6.139.2.6.26.1.11
-- 1.3.6.1.4.1.2011.6.139.2.6.26.1.11
-- 1.3.6.1.4.1.2011.6.139.2.6.26.1.11
-- 1.3.6.1.4.1.2011.6.139.2.6.26.1.11
		-- 1.3.6.1.4.1.2011.6.139.2.6.26.1.11
		hwMacApLineatePortLldpRestartDelay OBJECT-TYPE
			SYNTAX Integer32
			MAX-ACCESS read-write
			STATUS current
			DESCRIPTION
				"Description."
			::= { hwMacApLineatePortLldpCfgEntry 11 }


--      1.3.6.1.4.1.2011.6.139.2.6.26.1.12
-- 1.3.6.1.4.1.2011.6.139.2.6.26.1.12
-- 1.3.6.1.4.1.2011.6.139.2.6.26.1.12
-- 1.3.6.1.4.1.2011.6.139.2.6.26.1.12
-- 1.3.6.1.4.1.2011.6.139.2.6.26.1.12
		-- 1.3.6.1.4.1.2011.6.139.2.6.26.1.12
		hwMacApLineatePortLldpAdminStatus OBJECT-TYPE
			SYNTAX Integer32 (0..2)
			MAX-ACCESS read-write
			STATUS current
			DESCRIPTION
				"Description."
			::= { hwMacApLineatePortLldpCfgEntry 12 }


--      1.3.6.1.4.1.2011.6.139.2.6.26.1.13
-- 1.3.6.1.4.1.2011.6.139.2.6.26.1.13
-- 1.3.6.1.4.1.2011.6.139.2.6.26.1.13
-- 1.3.6.1.4.1.2011.6.139.2.6.26.1.13
-- 1.3.6.1.4.1.2011.6.139.2.6.26.1.13
		-- 1.3.6.1.4.1.2011.6.139.2.6.26.1.13
		hwMacApLineatePortLldpReportInterval OBJECT-TYPE
			SYNTAX Integer32
			MAX-ACCESS read-write
			STATUS current
			DESCRIPTION
				"Description."
			::= { hwMacApLineatePortLldpCfgEntry 13 }


--     1.3.6.1.4.1.2011.6.139.2.6.27
-- 1.3.6.1.4.1.2011.6.139.2.6.27
-- 1.3.6.1.4.1.2011.6.139.2.6.27
-- 1.3.6.1.4.1.2011.6.139.2.6.27
		-- 1.3.6.1.4.1.2011.6.139.2.6.27
		hwApLineatePortLldpTable OBJECT-TYPE
			SYNTAX SEQUENCE OF HwApLineatePortLldpEntry
			MAX-ACCESS not-accessible
			STATUS current
			DESCRIPTION
				"Description."
			::= { hwApObjects 27 }


--     1.3.6.1.4.1.2011.6.139.2.6.27.1
-- 1.3.6.1.4.1.2011.6.139.2.6.27.1
-- 1.3.6.1.4.1.2011.6.139.2.6.27.1
-- 1.3.6.1.4.1.2011.6.139.2.6.27.1
		-- 1.3.6.1.4.1.2011.6.139.2.6.27.1
		hwApLineatePortLldpEntry OBJECT-TYPE
			SYNTAX HwApLineatePortLldpEntry
			MAX-ACCESS not-accessible
			STATUS current
			DESCRIPTION
				"Description."
			INDEX { hwApIndex, hwApLineatePortLldpRemLocalPortNum, hwApLineatePortLldpRemIndex }
			::= { hwApLineatePortLldpTable 1 }


		HwApLineatePortLldpEntry ::=
			SEQUENCE {
				hwApLineatePortLldpRemLocalPortNum
					Integer32,
				hwApLineatePortLldpRemIndex
					Integer32,
				hwApLineatePortLldpRemChassisIdSubtype
					Integer32,
				hwApLineatePortLldpRemChassisId
					OCTET STRING,
				hwApLineatePortLldpRemPortIdSubtype
					Integer32,
				hwApLineatePortLldpRemPortId
					OCTET STRING,
				hwApLineatePortLldpRemPortDesc
					OCTET STRING,
				hwApLineatePortLldpRemSysName
					OCTET STRING,
				hwApLineatePortLldpRemSysDesc
					OCTET STRING,
				hwApLineatePortLldpRemSysCapSupported
					Integer32,
				hwApLineatePortLldpRemSysCapEnabled
					Integer32
			 }

--     1.3.6.1.4.1.2011.6.139.2.6.27.1.1
-- 1.3.6.1.4.1.2011.6.139.2.6.27.1.1
-- 1.3.6.1.4.1.2011.6.139.2.6.27.1.1
-- 1.3.6.1.4.1.2011.6.139.2.6.27.1.1
		-- 1.3.6.1.4.1.2011.6.139.2.6.27.1.1
		hwApLineatePortLldpRemLocalPortNum OBJECT-TYPE
			SYNTAX Integer32
			MAX-ACCESS not-accessible
			STATUS current
			DESCRIPTION
				"Description."
			::= { hwApLineatePortLldpEntry 1 }


--     1.3.6.1.4.1.2011.6.139.2.6.27.1.2
-- 1.3.6.1.4.1.2011.6.139.2.6.27.1.2
-- 1.3.6.1.4.1.2011.6.139.2.6.27.1.2
-- 1.3.6.1.4.1.2011.6.139.2.6.27.1.2
		-- 1.3.6.1.4.1.2011.6.139.2.6.27.1.2
		hwApLineatePortLldpRemIndex OBJECT-TYPE
			SYNTAX Integer32
			MAX-ACCESS not-accessible
			STATUS current
			DESCRIPTION
				"Description."
			::= { hwApLineatePortLldpEntry 2 }


--     1.3.6.1.4.1.2011.6.139.2.6.27.1.3
-- 1.3.6.1.4.1.2011.6.139.2.6.27.1.3
-- 1.3.6.1.4.1.2011.6.139.2.6.27.1.3
-- 1.3.6.1.4.1.2011.6.139.2.6.27.1.3
		-- 1.3.6.1.4.1.2011.6.139.2.6.27.1.3
		hwApLineatePortLldpRemChassisIdSubtype OBJECT-TYPE
			SYNTAX Integer32
			MAX-ACCESS read-only
			STATUS current
			DESCRIPTION
				"Description."
			::= { hwApLineatePortLldpEntry 3 }


--     1.3.6.1.4.1.2011.6.139.2.6.27.1.4
-- 1.3.6.1.4.1.2011.6.139.2.6.27.1.4
-- 1.3.6.1.4.1.2011.6.139.2.6.27.1.4
-- 1.3.6.1.4.1.2011.6.139.2.6.27.1.4
		-- 1.3.6.1.4.1.2011.6.139.2.6.27.1.4
		hwApLineatePortLldpRemChassisId OBJECT-TYPE
			SYNTAX OCTET STRING (SIZE (0..255))
			MAX-ACCESS read-only
			STATUS current
			DESCRIPTION
				"Description."
			::= { hwApLineatePortLldpEntry 4 }


--     1.3.6.1.4.1.2011.6.139.2.6.27.1.5
-- 1.3.6.1.4.1.2011.6.139.2.6.27.1.5
-- 1.3.6.1.4.1.2011.6.139.2.6.27.1.5
-- 1.3.6.1.4.1.2011.6.139.2.6.27.1.5
		-- 1.3.6.1.4.1.2011.6.139.2.6.27.1.5
		hwApLineatePortLldpRemPortIdSubtype OBJECT-TYPE
			SYNTAX Integer32
			MAX-ACCESS read-only
			STATUS current
			DESCRIPTION
				"Description."
			::= { hwApLineatePortLldpEntry 5 }


--     1.3.6.1.4.1.2011.6.139.2.6.27.1.6
-- 1.3.6.1.4.1.2011.6.139.2.6.27.1.6
-- 1.3.6.1.4.1.2011.6.139.2.6.27.1.6
-- 1.3.6.1.4.1.2011.6.139.2.6.27.1.6
		-- 1.3.6.1.4.1.2011.6.139.2.6.27.1.6
		hwApLineatePortLldpRemPortId OBJECT-TYPE
			SYNTAX OCTET STRING (SIZE (0..255))
			MAX-ACCESS read-only
			STATUS current
			DESCRIPTION
				"Description."
			::= { hwApLineatePortLldpEntry 6 }


--     1.3.6.1.4.1.2011.6.139.2.6.27.1.7
-- 1.3.6.1.4.1.2011.6.139.2.6.27.1.7
-- 1.3.6.1.4.1.2011.6.139.2.6.27.1.7
-- 1.3.6.1.4.1.2011.6.139.2.6.27.1.7
		-- 1.3.6.1.4.1.2011.6.139.2.6.27.1.7
		hwApLineatePortLldpRemPortDesc OBJECT-TYPE
			SYNTAX OCTET STRING (SIZE (0..255))
			MAX-ACCESS read-only
			STATUS current
			DESCRIPTION
				"Description."
			::= { hwApLineatePortLldpEntry 7 }


--     1.3.6.1.4.1.2011.6.139.2.6.27.1.8
-- 1.3.6.1.4.1.2011.6.139.2.6.27.1.8
-- 1.3.6.1.4.1.2011.6.139.2.6.27.1.8
-- 1.3.6.1.4.1.2011.6.139.2.6.27.1.8
		-- 1.3.6.1.4.1.2011.6.139.2.6.27.1.8
		hwApLineatePortLldpRemSysName OBJECT-TYPE
			SYNTAX OCTET STRING (SIZE (0..255))
			MAX-ACCESS read-only
			STATUS current
			DESCRIPTION
				"Description."
			::= { hwApLineatePortLldpEntry 8 }


--     1.3.6.1.4.1.2011.6.139.2.6.27.1.9
-- 1.3.6.1.4.1.2011.6.139.2.6.27.1.9
-- 1.3.6.1.4.1.2011.6.139.2.6.27.1.9
-- 1.3.6.1.4.1.2011.6.139.2.6.27.1.9
		-- 1.3.6.1.4.1.2011.6.139.2.6.27.1.9
		hwApLineatePortLldpRemSysDesc OBJECT-TYPE
			SYNTAX OCTET STRING (SIZE (0..255))
			MAX-ACCESS read-only
			STATUS current
			DESCRIPTION
				"Description."
			::= { hwApLineatePortLldpEntry 9 }


--     1.3.6.1.4.1.2011.6.139.2.6.27.1.10
-- 1.3.6.1.4.1.2011.6.139.2.6.27.1.10
-- 1.3.6.1.4.1.2011.6.139.2.6.27.1.10
-- 1.3.6.1.4.1.2011.6.139.2.6.27.1.10
		-- 1.3.6.1.4.1.2011.6.139.2.6.27.1.10
		hwApLineatePortLldpRemSysCapSupported OBJECT-TYPE
			SYNTAX Integer32
			MAX-ACCESS read-only
			STATUS current
			DESCRIPTION
				"Description."
			::= { hwApLineatePortLldpEntry 10 }


--     1.3.6.1.4.1.2011.6.139.2.6.27.1.11
-- 1.3.6.1.4.1.2011.6.139.2.6.27.1.11
-- 1.3.6.1.4.1.2011.6.139.2.6.27.1.11
-- 1.3.6.1.4.1.2011.6.139.2.6.27.1.11
		-- 1.3.6.1.4.1.2011.6.139.2.6.27.1.11
		hwApLineatePortLldpRemSysCapEnabled OBJECT-TYPE
			SYNTAX Integer32
			MAX-ACCESS read-only
			STATUS current
			DESCRIPTION
				"Description."
			::= { hwApLineatePortLldpEntry 11 }


--    1.3.6.1.4.1.2011.6.139.2.6.28
-- 1.3.6.1.4.1.2011.6.139.2.6.28
-- 1.3.6.1.4.1.2011.6.139.2.6.28
		-- 1.3.6.1.4.1.2011.6.139.2.6.28
		hwMacApLineatePortLldpTable OBJECT-TYPE
			SYNTAX SEQUENCE OF HwMacApLineatePortLldpEntry
			MAX-ACCESS not-accessible
			STATUS current
			DESCRIPTION
				"Description."
			::= { hwApObjects 28 }


--    1.3.6.1.4.1.2011.6.139.2.6.28.1
-- 1.3.6.1.4.1.2011.6.139.2.6.28.1
-- 1.3.6.1.4.1.2011.6.139.2.6.28.1
		-- 1.3.6.1.4.1.2011.6.139.2.6.28.1
		hwMacApLineatePortLldpEntry OBJECT-TYPE
			SYNTAX HwMacApLineatePortLldpEntry
			MAX-ACCESS not-accessible
			STATUS current
			DESCRIPTION
				"Description."
			INDEX { hwMacApMac, hwMacApLineatePortLldpRemLocalPortNum, hwMacApLineatePortLldpRemIndex }
			::= { hwMacApLineatePortLldpTable 1 }


		HwMacApLineatePortLldpEntry ::=
			SEQUENCE {
				hwMacApLineatePortLldpRemLocalPortNum
					Integer32,
				hwMacApLineatePortLldpRemIndex
					Integer32,
				hwMacApLineatePortLldpRemChassisIdSubtype
					Integer32,
				hwMacApLineatePortLldpRemChassisId
					OCTET STRING,
				hwMacApLineatePortLldpRemPortIdSubtype
					Integer32,
				hwMacApLineatePortLldpRemPortId
					OCTET STRING,
				hwMacApLineatePortLldpRemPortDesc
					OCTET STRING,
				hwMacApLineatePortLldpRemSysName
					OCTET STRING,
				hwMacApLineatePortLldpRemSysDesc
					OCTET STRING,
				hwMacApLineatePortLldpRemSysCapSupported
					Integer32,
				hwMacApLineatePortLldpRemSysCapEnabled
					Integer32
			 }

--    1.3.6.1.4.1.2011.6.139.2.6.28.1.1
-- 1.3.6.1.4.1.2011.6.139.2.6.28.1.1
-- 1.3.6.1.4.1.2011.6.139.2.6.28.1.1
		-- 1.3.6.1.4.1.2011.6.139.2.6.28.1.1
		hwMacApLineatePortLldpRemLocalPortNum OBJECT-TYPE
			SYNTAX Integer32
			MAX-ACCESS not-accessible
			STATUS current
			DESCRIPTION
				"Description."
			::= { hwMacApLineatePortLldpEntry 1 }


--    1.3.6.1.4.1.2011.6.139.2.6.28.1.2
-- 1.3.6.1.4.1.2011.6.139.2.6.28.1.2
-- 1.3.6.1.4.1.2011.6.139.2.6.28.1.2
		-- 1.3.6.1.4.1.2011.6.139.2.6.28.1.2
		hwMacApLineatePortLldpRemIndex OBJECT-TYPE
			SYNTAX Integer32
			MAX-ACCESS not-accessible
			STATUS current
			DESCRIPTION
				"Description."
			::= { hwMacApLineatePortLldpEntry 2 }


--    1.3.6.1.4.1.2011.6.139.2.6.28.1.3
-- 1.3.6.1.4.1.2011.6.139.2.6.28.1.3
-- 1.3.6.1.4.1.2011.6.139.2.6.28.1.3
		-- 1.3.6.1.4.1.2011.6.139.2.6.28.1.3
		hwMacApLineatePortLldpRemChassisIdSubtype OBJECT-TYPE
			SYNTAX Integer32
			MAX-ACCESS read-only
			STATUS current
			DESCRIPTION
				"Description."
			::= { hwMacApLineatePortLldpEntry 3 }


--    1.3.6.1.4.1.2011.6.139.2.6.28.1.4
-- 1.3.6.1.4.1.2011.6.139.2.6.28.1.4
-- 1.3.6.1.4.1.2011.6.139.2.6.28.1.4
		-- 1.3.6.1.4.1.2011.6.139.2.6.28.1.4
		hwMacApLineatePortLldpRemChassisId OBJECT-TYPE
			SYNTAX OCTET STRING (SIZE (0..255))
			MAX-ACCESS read-only
			STATUS current
			DESCRIPTION
				"Description."
			::= { hwMacApLineatePortLldpEntry 4 }


--    1.3.6.1.4.1.2011.6.139.2.6.28.1.5
-- 1.3.6.1.4.1.2011.6.139.2.6.28.1.5
-- 1.3.6.1.4.1.2011.6.139.2.6.28.1.5
		-- 1.3.6.1.4.1.2011.6.139.2.6.28.1.5
		hwMacApLineatePortLldpRemPortIdSubtype OBJECT-TYPE
			SYNTAX Integer32
			MAX-ACCESS read-only
			STATUS current
			DESCRIPTION
				"Description."
			::= { hwMacApLineatePortLldpEntry 5 }


--    1.3.6.1.4.1.2011.6.139.2.6.28.1.6
-- 1.3.6.1.4.1.2011.6.139.2.6.28.1.6
-- 1.3.6.1.4.1.2011.6.139.2.6.28.1.6
		-- 1.3.6.1.4.1.2011.6.139.2.6.28.1.6
		hwMacApLineatePortLldpRemPortId OBJECT-TYPE
			SYNTAX OCTET STRING (SIZE (0..255))
			MAX-ACCESS read-only
			STATUS current
			DESCRIPTION
				"Description."
			::= { hwMacApLineatePortLldpEntry 6 }


--    1.3.6.1.4.1.2011.6.139.2.6.28.1.7
-- 1.3.6.1.4.1.2011.6.139.2.6.28.1.7
-- 1.3.6.1.4.1.2011.6.139.2.6.28.1.7
		-- 1.3.6.1.4.1.2011.6.139.2.6.28.1.7
		hwMacApLineatePortLldpRemPortDesc OBJECT-TYPE
			SYNTAX OCTET STRING (SIZE (0..255))
			MAX-ACCESS read-only
			STATUS current
			DESCRIPTION
				"Description."
			::= { hwMacApLineatePortLldpEntry 7 }


--    1.3.6.1.4.1.2011.6.139.2.6.28.1.8
-- 1.3.6.1.4.1.2011.6.139.2.6.28.1.8
-- 1.3.6.1.4.1.2011.6.139.2.6.28.1.8
		-- 1.3.6.1.4.1.2011.6.139.2.6.28.1.8
		hwMacApLineatePortLldpRemSysName OBJECT-TYPE
			SYNTAX OCTET STRING (SIZE (0..255))
			MAX-ACCESS read-only
			STATUS current
			DESCRIPTION
				"Description."
			::= { hwMacApLineatePortLldpEntry 8 }


--    1.3.6.1.4.1.2011.6.139.2.6.28.1.9
-- 1.3.6.1.4.1.2011.6.139.2.6.28.1.9
-- 1.3.6.1.4.1.2011.6.139.2.6.28.1.9
		-- 1.3.6.1.4.1.2011.6.139.2.6.28.1.9
		hwMacApLineatePortLldpRemSysDesc OBJECT-TYPE
			SYNTAX OCTET STRING (SIZE (0..255))
			MAX-ACCESS read-only
			STATUS current
			DESCRIPTION
				"Description."
			::= { hwMacApLineatePortLldpEntry 9 }


--    1.3.6.1.4.1.2011.6.139.2.6.28.1.10
-- 1.3.6.1.4.1.2011.6.139.2.6.28.1.10
-- 1.3.6.1.4.1.2011.6.139.2.6.28.1.10
		-- 1.3.6.1.4.1.2011.6.139.2.6.28.1.10
		hwMacApLineatePortLldpRemSysCapSupported OBJECT-TYPE
			SYNTAX Integer32
			MAX-ACCESS read-only
			STATUS current
			DESCRIPTION
				"Description."
			::= { hwMacApLineatePortLldpEntry 10 }


--    1.3.6.1.4.1.2011.6.139.2.6.28.1.11
-- 1.3.6.1.4.1.2011.6.139.2.6.28.1.11
-- 1.3.6.1.4.1.2011.6.139.2.6.28.1.11
		-- 1.3.6.1.4.1.2011.6.139.2.6.28.1.11
		hwMacApLineatePortLldpRemSysCapEnabled OBJECT-TYPE
			SYNTAX Integer32
			MAX-ACCESS read-only
			STATUS current
			DESCRIPTION
				"Description."
			::= { hwMacApLineatePortLldpEntry 11 }


--   1.3.6.1.4.1.2011.6.139.2.6.29
-- 1.3.6.1.4.1.2011.6.139.2.6.29
		-- 1.3.6.1.4.1.2011.6.139.2.6.29
		hwApLineatePortLldpRemManAddrTable OBJECT-TYPE
			SYNTAX SEQUENCE OF HwApLineatePortLldpRemManAddrEntry
			MAX-ACCESS not-accessible
			STATUS current
			DESCRIPTION
				"Description."
			::= { hwApObjects 29 }


--   1.3.6.1.4.1.2011.6.139.2.6.29.1
-- 1.3.6.1.4.1.2011.6.139.2.6.29.1
		-- 1.3.6.1.4.1.2011.6.139.2.6.29.1
		hwApLineatePortLldpRemManAddrEntry OBJECT-TYPE
			SYNTAX HwApLineatePortLldpRemManAddrEntry
			MAX-ACCESS not-accessible
			STATUS current
			DESCRIPTION
				"Description."
			INDEX { hwApIndex, hwApLineatePortLldpRemLocalPortNum, hwApLineatePortLldpRemIndex, hwApLineatePortLldpRemManAddrSubtype, hwApLineatePortLldpRemManAddr
				 }
			::= { hwApLineatePortLldpRemManAddrTable 1 }


		HwApLineatePortLldpRemManAddrEntry ::=
			SEQUENCE {
				hwApLineatePortLldpRemManAddrSubtype
					Integer32,
				hwApLineatePortLldpRemManAddr
					OCTET STRING,
				hwApLineatePortLldpRemManAddrIfSubtype
					Integer32,
				hwApLineatePortLldpRemManAddrIfId
					Integer32,
				hwApLineatePortLldpRemManAddrOID
					OCTET STRING
			 }

--   1.3.6.1.4.1.2011.6.139.2.6.29.1.1
-- 1.3.6.1.4.1.2011.6.139.2.6.29.1.1
		-- 1.3.6.1.4.1.2011.6.139.2.6.29.1.1
		hwApLineatePortLldpRemManAddrSubtype OBJECT-TYPE
			SYNTAX Integer32
			MAX-ACCESS not-accessible
			STATUS current
			DESCRIPTION
				"Description."
			::= { hwApLineatePortLldpRemManAddrEntry 1 }


--   1.3.6.1.4.1.2011.6.139.2.6.29.1.2
-- 1.3.6.1.4.1.2011.6.139.2.6.29.1.2
		-- 1.3.6.1.4.1.2011.6.139.2.6.29.1.2
		hwApLineatePortLldpRemManAddr OBJECT-TYPE
			SYNTAX OCTET STRING (SIZE (0..31))
			MAX-ACCESS not-accessible
			STATUS current
			DESCRIPTION
				"Description."
			::= { hwApLineatePortLldpRemManAddrEntry 2 }


--   1.3.6.1.4.1.2011.6.139.2.6.29.1.3
-- 1.3.6.1.4.1.2011.6.139.2.6.29.1.3
		-- 1.3.6.1.4.1.2011.6.139.2.6.29.1.3
		hwApLineatePortLldpRemManAddrIfSubtype OBJECT-TYPE
			SYNTAX Integer32
			MAX-ACCESS read-only
			STATUS current
			DESCRIPTION
				"Description."
			::= { hwApLineatePortLldpRemManAddrEntry 3 }


--   1.3.6.1.4.1.2011.6.139.2.6.29.1.4
-- 1.3.6.1.4.1.2011.6.139.2.6.29.1.4
		-- 1.3.6.1.4.1.2011.6.139.2.6.29.1.4
		hwApLineatePortLldpRemManAddrIfId OBJECT-TYPE
			SYNTAX Integer32
			MAX-ACCESS read-only
			STATUS current
			DESCRIPTION
				"Description."
			::= { hwApLineatePortLldpRemManAddrEntry 4 }


--   1.3.6.1.4.1.2011.6.139.2.6.29.1.5
-- 1.3.6.1.4.1.2011.6.139.2.6.29.1.5
		-- 1.3.6.1.4.1.2011.6.139.2.6.29.1.5
		hwApLineatePortLldpRemManAddrOID OBJECT-TYPE
			SYNTAX OCTET STRING (SIZE (0..128))
			MAX-ACCESS read-only
			STATUS current
			DESCRIPTION
				"Description."
			::= { hwApLineatePortLldpRemManAddrEntry 5 }


--   1.3.6.1.4.1.2011.6.139.2.6.30
-- 1.3.6.1.4.1.2011.6.139.2.6.30
		-- 1.3.6.1.4.1.2011.6.139.2.6.30
		hwMacApLineatePortLldpRemManAddrTable OBJECT-TYPE
			SYNTAX SEQUENCE OF HwMacApLineatePortLldpRemManAddrEntry
			MAX-ACCESS not-accessible
			STATUS current
			DESCRIPTION
				"Description."
			::= { hwApObjects 30 }


--   1.3.6.1.4.1.2011.6.139.2.6.30.1
-- 1.3.6.1.4.1.2011.6.139.2.6.30.1
		-- 1.3.6.1.4.1.2011.6.139.2.6.30.1
		hwMacApLineatePortLldpRemManAddrEntry OBJECT-TYPE
			SYNTAX HwMacApLineatePortLldpRemManAddrEntry
			MAX-ACCESS not-accessible
			STATUS current
			DESCRIPTION
				"Description."
			INDEX { hwMacApMac, hwMacApLineatePortLldpRemLocalPortNum, hwMacApLineatePortLldpRemIndex, hwMACApLineatePortLldpRemManAddrSubtype, hwMACApLineatePortLldpRemManAddr
				 }
			::= { hwMacApLineatePortLldpRemManAddrTable 1 }


		HwMacApLineatePortLldpRemManAddrEntry ::=
			SEQUENCE {
				hwMACApLineatePortLldpRemManAddrSubtype
					Integer32,
				hwMACApLineatePortLldpRemManAddr
					OCTET STRING,
				hwMACApLineatePortLldpRemManAddrIfSubtype
					Integer32,
				hwMACApLineatePortLldpRemManAddrIfId
					Integer32,
				hwMACApLineatePortLldpRemManAddrOID
					OCTET STRING
			 }

--   1.3.6.1.4.1.2011.6.139.2.6.30.1.1
-- 1.3.6.1.4.1.2011.6.139.2.6.30.1.1
		-- 1.3.6.1.4.1.2011.6.139.2.6.30.1.1
		hwMACApLineatePortLldpRemManAddrSubtype OBJECT-TYPE
			SYNTAX Integer32
			MAX-ACCESS not-accessible
			STATUS current
			DESCRIPTION
				"Description."
			::= { hwMacApLineatePortLldpRemManAddrEntry 1 }


--   1.3.6.1.4.1.2011.6.139.2.6.30.1.2
-- 1.3.6.1.4.1.2011.6.139.2.6.30.1.2
		-- 1.3.6.1.4.1.2011.6.139.2.6.30.1.2
		hwMACApLineatePortLldpRemManAddr OBJECT-TYPE
			SYNTAX OCTET STRING (SIZE (0..31))
			MAX-ACCESS not-accessible
			STATUS current
			DESCRIPTION
				"Description."
			::= { hwMacApLineatePortLldpRemManAddrEntry 2 }


--   1.3.6.1.4.1.2011.6.139.2.6.30.1.3
-- 1.3.6.1.4.1.2011.6.139.2.6.30.1.3
		-- 1.3.6.1.4.1.2011.6.139.2.6.30.1.3
		hwMACApLineatePortLldpRemManAddrIfSubtype OBJECT-TYPE
			SYNTAX Integer32
			MAX-ACCESS read-only
			STATUS current
			DESCRIPTION
				"Description."
			::= { hwMacApLineatePortLldpRemManAddrEntry 3 }


--   1.3.6.1.4.1.2011.6.139.2.6.30.1.4
-- 1.3.6.1.4.1.2011.6.139.2.6.30.1.4
		-- 1.3.6.1.4.1.2011.6.139.2.6.30.1.4
		hwMACApLineatePortLldpRemManAddrIfId OBJECT-TYPE
			SYNTAX Integer32
			MAX-ACCESS read-only
			STATUS current
			DESCRIPTION
				"Description."
			::= { hwMacApLineatePortLldpRemManAddrEntry 4 }


--   1.3.6.1.4.1.2011.6.139.2.6.30.1.5
-- 1.3.6.1.4.1.2011.6.139.2.6.30.1.5
		-- 1.3.6.1.4.1.2011.6.139.2.6.30.1.5
		hwMACApLineatePortLldpRemManAddrOID OBJECT-TYPE
			SYNTAX OCTET STRING (SIZE (0..128))
			MAX-ACCESS read-only
			STATUS current
			DESCRIPTION
				"Description."
			::= { hwMacApLineatePortLldpRemManAddrEntry 5 }


		-- 1.3.6.1.4.1.2011.6.139.2.6.31
		hwApOnlineFailTable OBJECT-TYPE
			SYNTAX SEQUENCE OF HwApOnlineFailEntry
			MAX-ACCESS not-accessible
			STATUS current
			DESCRIPTION
				"Description."
			::= { hwApObjects 31 }


		-- 1.3.6.1.4.1.2011.6.139.2.6.31.1
		hwApOnlineFailEntry OBJECT-TYPE
			SYNTAX HwApOnlineFailEntry
			MAX-ACCESS not-accessible
			STATUS current
			DESCRIPTION
				"Description."
			INDEX { hwApOnlineFailMac }
			::= { hwApOnlineFailTable 1 }


		HwApOnlineFailEntry ::=
			SEQUENCE {
				hwApOnlineFailMac
					MacAddress,
				hwMacApOnlineFailTime
					OCTET STRING,
				hwMacApOnlineFailReason
					OCTET STRING,
				hwMacApOnlineFailRowStatus
					RowStatus
			 }

		-- 1.3.6.1.4.1.2011.6.139.2.6.31.1.1
		hwApOnlineFailMac OBJECT-TYPE
			SYNTAX MacAddress
			MAX-ACCESS not-accessible
			STATUS current
			DESCRIPTION
				"The mac of AP."
			::= { hwApOnlineFailEntry 1 }


		-- 1.3.6.1.4.1.2011.6.139.2.6.31.1.2
		hwMacApOnlineFailTime OBJECT-TYPE
			SYNTAX OCTET STRING
			MAX-ACCESS read-only
			STATUS current
			DESCRIPTION
				"The last time of ap online fail."
			::= { hwApOnlineFailEntry 2 }


		-- 1.3.6.1.4.1.2011.6.139.2.6.31.1.3
		hwMacApOnlineFailReason OBJECT-TYPE
			SYNTAX OCTET STRING (SIZE (0..64))
			MAX-ACCESS read-only
			STATUS current
			DESCRIPTION
				"The last reason of ap online fail."
			::= { hwApOnlineFailEntry 3 }


		-- 1.3.6.1.4.1.2011.6.139.2.6.31.1.4
		hwMacApOnlineFailRowStatus OBJECT-TYPE
			SYNTAX RowStatus
			MAX-ACCESS read-write
			STATUS current
			DESCRIPTION
				"Delete a record."
			::= { hwApOnlineFailEntry 4 }


		-- 1.3.6.1.4.1.2011.6.139.2.6.32
		hwApOfflineTable OBJECT-TYPE
			SYNTAX SEQUENCE OF HwApOfflineEntry
			MAX-ACCESS not-accessible
			STATUS current
			DESCRIPTION
				"Description."
			::= { hwApObjects 32 }


		-- 1.3.6.1.4.1.2011.6.139.2.6.32.1
		hwApOfflineEntry OBJECT-TYPE
			SYNTAX HwApOfflineEntry
			MAX-ACCESS not-accessible
			STATUS current
			DESCRIPTION
				"Description."
			INDEX { hwApOfflineMac }
			::= { hwApOfflineTable 1 }


		HwApOfflineEntry ::=
			SEQUENCE {
				hwApOfflineMac
					MacAddress,
				hwMacApOfflineTime
					OCTET STRING,
				hwMacApOfflineReason
					OCTET STRING,
				hwMacApOfflineRowStatus
					RowStatus
			 }

		-- 1.3.6.1.4.1.2011.6.139.2.6.32.1.1
		hwApOfflineMac OBJECT-TYPE
			SYNTAX MacAddress
			MAX-ACCESS not-accessible
			STATUS current
			DESCRIPTION
				"The mac of AP."
			::= { hwApOfflineEntry 1 }


		-- 1.3.6.1.4.1.2011.6.139.2.6.32.1.2
		hwMacApOfflineTime OBJECT-TYPE
			SYNTAX OCTET STRING
			MAX-ACCESS read-only
			STATUS current
			DESCRIPTION
				"The last time of ap offline."
			::= { hwApOfflineEntry 2 }


		-- 1.3.6.1.4.1.2011.6.139.2.6.32.1.3
		hwMacApOfflineReason OBJECT-TYPE
			SYNTAX OCTET STRING (SIZE (0..64))
			MAX-ACCESS read-only
			STATUS current
			DESCRIPTION
				"The last reason of ap offline."
			::= { hwApOfflineEntry 3 }


		-- 1.3.6.1.4.1.2011.6.139.2.6.32.1.4
		hwMacApOfflineRowStatus OBJECT-TYPE
			SYNTAX RowStatus
			MAX-ACCESS read-create
			STATUS current
			DESCRIPTION
				"Delete a record."
			::= { hwApOfflineEntry 4 }



--   1.3.6.1.4.1.2011.6.139.2.8
-- 1.3.6.1.4.1.2011.6.139.2.7
		-- 1.3.6.1.4.1.2011.6.139.2.8
		hwAcObjects OBJECT IDENTIFIER ::= { hwWlanDevice 7 }


--  1.3.6.1.4.1.2011.6.139.2.8.1
		-- 1.3.6.1.4.1.2011.6.139.2.7.1
		hwAcTable OBJECT-TYPE
			SYNTAX SEQUENCE OF HwAcEntry
			MAX-ACCESS not-accessible
			STATUS current
			DESCRIPTION
				"Description."
			::= { hwAcObjects 1 }


--  1.3.6.1.4.1.2011.6.139.2.8.1.1
		-- 1.3.6.1.4.1.2011.6.139.2.7.1.1
		hwAcEntry OBJECT-TYPE
			SYNTAX HwAcEntry
			MAX-ACCESS not-accessible
			STATUS current
			DESCRIPTION
				"Description."
			INDEX { hwMemAcIndex }
			::= { hwAcTable 1 }


		HwAcEntry ::=
			SEQUENCE {
				hwMemAcIndex
					Integer32,
				hwAcIpVersion
					INTEGER,
				hwAcIPv4Address
					IpAddress,
				hwAcIPv6Address
					OCTET STRING,
				hwAcState
					INTEGER,
				hwAcRowStatus
					RowStatus
			 }

--  1.3.6.1.4.1.2011.6.139.2.8.1.1.1
		-- 1.3.6.1.4.1.2011.6.139.2.7.1.1.1
		hwMemAcIndex OBJECT-TYPE
			SYNTAX Integer32
			MAX-ACCESS not-accessible
			STATUS current
			DESCRIPTION
				"Description."
			::= { hwAcEntry 1 }


--  1.3.6.1.4.1.2011.6.139.2.8.1.1.2
		-- 1.3.6.1.4.1.2011.6.139.2.7.1.1.2
		hwAcIpVersion OBJECT-TYPE
			SYNTAX INTEGER
				{
				ipv4(1),
				ipv6(2)
				}
			MAX-ACCESS read-write
			STATUS current
			DESCRIPTION
				"Description."
			::= { hwAcEntry 2 }


--  1.3.6.1.4.1.2011.6.139.2.8.1.1.3
		-- 1.3.6.1.4.1.2011.6.139.2.7.1.1.3
		hwAcIPv4Address OBJECT-TYPE
			SYNTAX IpAddress
			MAX-ACCESS read-write
			STATUS current
			DESCRIPTION
				"Description."
			::= { hwAcEntry 3 }


--  1.3.6.1.4.1.2011.6.139.2.8.1.1.4
		-- 1.3.6.1.4.1.2011.6.139.2.7.1.1.4
		hwAcIPv6Address OBJECT-TYPE
			SYNTAX OCTET STRING
			MAX-ACCESS read-write
			STATUS current
			DESCRIPTION
				"Description."
			::= { hwAcEntry 4 }


--  1.3.6.1.4.1.2011.6.139.2.8.1.1.5
		-- 1.3.6.1.4.1.2011.6.139.2.7.1.1.5
		hwAcState OBJECT-TYPE
			SYNTAX INTEGER
				{
				normal(1),
				fault(2)
				}
			MAX-ACCESS read-only
			STATUS current
			DESCRIPTION
				"Description."
			::= { hwAcEntry 5 }


--  1.3.6.1.4.1.2011.6.139.2.8.1.1.6
		-- 1.3.6.1.4.1.2011.6.139.2.7.1.1.6
		hwAcRowStatus OBJECT-TYPE
			SYNTAX RowStatus
			MAX-ACCESS read-write
			STATUS current
			DESCRIPTION
				"Description."
			::= { hwAcEntry 6 }


--  1.3.6.1.4.1.2011.6.139.2.8.2
		-- 1.3.6.1.4.1.2011.6.139.2.7.2
		hwMobilityGroupTable OBJECT-TYPE
			SYNTAX SEQUENCE OF HwMobilityGroupEntry
			MAX-ACCESS not-accessible
			STATUS current
			DESCRIPTION
				"Description."
			::= { hwAcObjects 2 }


--  1.3.6.1.4.1.2011.6.139.2.8.2.1
		-- 1.3.6.1.4.1.2011.6.139.2.7.2.1
		hwMobilityGroupEntry OBJECT-TYPE
			SYNTAX HwMobilityGroupEntry
			MAX-ACCESS not-accessible
			STATUS current
			DESCRIPTION
				"Description."
			INDEX { hwMobilityGroupName }
			::= { hwMobilityGroupTable 1 }


		HwMobilityGroupEntry ::=
			SEQUENCE {
				hwMobilityGroupName
					OCTET STRING,
				hwMobilityGroupMemberList
					OCTET STRING,
				hwMobilityGroupStatus
					RowStatus,
				hwMobilityGroupMemberOpcode
					INTEGER,
				hwMobilityGroupMemberIndex
					Integer32
			 }

--  1.3.6.1.4.1.2011.6.139.2.8.2.1.1
		-- 1.3.6.1.4.1.2011.6.139.2.7.2.1.1
		hwMobilityGroupName OBJECT-TYPE
			SYNTAX OCTET STRING
			MAX-ACCESS not-accessible
			STATUS current
			DESCRIPTION
				"Description."
			::= { hwMobilityGroupEntry 1 }


--  1.3.6.1.4.1.2011.6.139.2.8.2.1.2
		-- 1.3.6.1.4.1.2011.6.139.2.7.2.1.2
		hwMobilityGroupMemberList OBJECT-TYPE
			SYNTAX OCTET STRING
			MAX-ACCESS read-only
			STATUS current
			DESCRIPTION
				"Description."
			::= { hwMobilityGroupEntry 2 }


--  1.3.6.1.4.1.2011.6.139.2.8.2.1.3
		-- 1.3.6.1.4.1.2011.6.139.2.7.2.1.3
		hwMobilityGroupStatus OBJECT-TYPE
			SYNTAX RowStatus
			MAX-ACCESS read-write
			STATUS current
			DESCRIPTION
				"Description."
			::= { hwMobilityGroupEntry 3 }


--  1.3.6.1.4.1.2011.6.139.2.8.2.1.4
		-- 1.3.6.1.4.1.2011.6.139.2.7.2.1.4
		hwMobilityGroupMemberOpcode OBJECT-TYPE
			SYNTAX INTEGER
				{
				add(1),
				del(2)
				}
			MAX-ACCESS read-write
			STATUS current
			DESCRIPTION
				"Description."
			::= { hwMobilityGroupEntry 4 }


--  1.3.6.1.4.1.2011.6.139.2.8.2.1.5
		-- 1.3.6.1.4.1.2011.6.139.2.7.2.1.5
		hwMobilityGroupMemberIndex OBJECT-TYPE
			SYNTAX Integer32 (0..63)
			MAX-ACCESS read-write
			STATUS current
			DESCRIPTION
				"Description."
			::= { hwMobilityGroupEntry 5 }


--        1.3.6.1.4.1.2011.6.139.2.7
-- 1.3.6.1.4.1.2011.6.139.2.7
-- 1.3.6.1.4.1.2011.6.139.2.7
		-- 1.3.6.1.4.1.2011.6.139.2.7
		hwWlanDeviceObjects OBJECT IDENTIFIER ::= { hwWlanDevice 8 }


--    1.3.6.1.4.1.2011.6.139.2.8
-- 1.3.6.1.4.1.2011.6.139.2.8
-- 1.3.6.1.4.1.2011.6.139.2.8
		-- 1.3.6.1.4.1.2011.6.139.2.8
		hwWlanDeviceConformance OBJECT IDENTIFIER ::= { hwWlanDevice 9 }


--   1.3.6.1.4.1.2011.6.139.2.8.1
-- 1.3.6.1.4.1.2011.6.139.2.8.1
		-- 1.3.6.1.4.1.2011.6.139.2.8.1
		hwWlanDeviceCompliances OBJECT IDENTIFIER ::= { hwWlanDeviceConformance 1 }


--   1.3.6.1.4.1.2011.6.139.2.8.1.1
-- 1.3.6.1.4.1.2011.6.139.2.8.1.1
		-- 1.3.6.1.4.1.2011.6.139.2.8.1.1
		hwWlanDeviceCompliance MODULE-COMPLIANCE
			STATUS current
			DESCRIPTION
				"Description."
			MODULE -- this module
					MANDATORY-GROUPS { hwWlanDeviceNotifyGroup, hwWlanDeviceNotifyObjectsGroup, hwApTypeGroup, hwApProfileGroup, hwApAuthListGroup,
			hwApRegionGroup, hwApGroup, hwAcGroup }
			::= { hwWlanDeviceCompliances 1 }


--   1.3.6.1.4.1.2011.6.139.2.8.2
-- 1.3.6.1.4.1.2011.6.139.2.8.2
		-- 1.3.6.1.4.1.2011.6.139.2.8.2
		hwWlanDeviceObjectGroups OBJECT IDENTIFIER ::= { hwWlanDeviceConformance 2 }


--   1.3.6.1.4.1.2011.6.139.2.8.2.1
-- 1.3.6.1.4.1.2011.6.139.2.8.2.1
		-- 1.3.6.1.4.1.2011.6.139.2.8.2.1
		hwWlanDeviceNotifyGroup NOTIFICATION-GROUP
			NOTIFICATIONS { hwApFaultNotify, hwApNormalNotify, hwApTypeNotMatchNotify, hwApPingResultNotify, hwApColdstartNotify,
				hwApConfigCommitNotify, hwApAddOffLineNotify, hwApConfirmNotify, hwUnAuthorizedApRecordExistNotify, hwUnAuthorizedApRecordClearNotify,
				hwApCpuOverloadNotify, hwApCpuOverloadRestoreNotify, hwApMemoryOverloadNOtify, hwApMemoryOverloadRestoreNotify, hwAPStaFullNotify,
				hwAPStaFullRecoverNotify, hwAcDevicesSwitchNotify, hwApTimeSynFailNotify, hwDyingGaspTrapNotify, hwApFaultNotifyFat,
				hwApNormalNotifyFat, hwApTemperatureTooLowNotify, hwApTemperatureTooLowRestoreNotify, hwApTemperatureTooHighNotify, hwApTemperatureTooHighRestoreNotify,
				hwRadioDownNotifyFat, hwRadioDownRecovNotifyFat, hwApOpticalRxPowerTooHighNotify, hwApOpticalRxPowerTooHighRestoreNotify, hwApOpticalRxPowerTooLowNotify,
				hwApOpticalRxPowerTooLowRestoreNotify, hwApOpticalTemperatureTooHighNotify, hwApOpticalTemperatureTooHighRestoreNotify, hwApOpticalTemperatureTooLowNotify, hwApOpticalTemperatureTooLowRestoreNotify,
				hwApNotSupportCountryCodeNotify, hwApReceivedInvalidArpNotify, hwApArpExceedThresholdNotify, hwApColdBootNotify, hwApColdBootRestoreNotify,
				hwApHotBootNotify, hwApHotBootRestoreNotify, hwStationOnlineNotify, hwStationOfflineNotify, hwStationSignalStrengthLowThanThresholdNotify,
				hwAPBroadcastStormDownNotify, hwAPBroadcastStormDownRestoreNotify, hwAPBroadcastStormUpNotify, hwAPBroadcastStormUpRestoreNotify, hwApBroadcastRestrainDownNotify,
				hwApBroadcastRestrainDownRestoreNotify, hwApBroadcastRestrainUpNotify, hwApBroadcastRestrainUpRestoreNotify, hwApCRCTooHighNotify, hwApCRCTooHighRestoreNotify, hwApConflictApNameNotify, hwApLicenseNotify,
				hwApFmeaIICFaultNotify, hwApFmeaIICFaultRestoreNotify,
				hwApFmeaPHYFaultNotify, hwApFmeaPHYFaultRestoreNotify,
				hwApFmeaFaultNotify,hwApFmeaFaultRestoreNotify,hwApOpticalInsertNotify,hwApOpticalRemoveNotify,
				hwApReceivedInvalidArpNewNotify,hwApVersionMismatchNotify
				 }
			STATUS current
			DESCRIPTION
				"Description."
			::= { hwWlanDeviceObjectGroups 1 }


--  1.3.6.1.4.1.2011.6.139.2.8.2.2
		-- 1.3.6.1.4.1.2011.6.139.2.8.2.2
		hwWlanDeviceNotifyObjectsGroup OBJECT-GROUP
			OBJECTS { hwApActualType, hwApCpuOccupancyRate, hwApMemoryOccupancyRate, hwApPermitStaNum, hwStaAuthFailCause,
				hwAcSystemSwitchType, hwApRadioNotifyPara, hwApOpticalRxPower, hwApOpticalTemperature, hwApCfgCountryCode,
				hwApArpAttackSrcMac, hwApArpAttackDstMac, hwApArpAttackSrcIP, hwApArpCfgRateThreshold, hwApArpActualRate,
				hwApNotifyRadioId, hwApNotifyOrRestoreTemperature, hwOccurTime, hwApBootNotifyName, hwApFaultTimes,
				hwSignalStrengthThreshold, hwStaBroadcastFlux, hwBroadcastWarnThresholdDown, hwBroadcastWarnThresholdUp, hwBroadcastRestrainThresholdDown,
				hwBroadcastRestrainThresholdUp, hwApBroadcastFlux, hwCrcErrActual, hwCrcThreshold, hwApNotifyWlanId, hwApLicenseInfo, hwCrcPortType, hwCrcPortID,
				hwApArpAttackDropNum,hwApFaultID,hwApIfIndex,hwApFaultInfo }
			STATUS current
			DESCRIPTION
				"Description."
			::= { hwWlanDeviceObjectGroups 2 }


--  1.3.6.1.4.1.2011.6.139.2.8.2.3
		-- 1.3.6.1.4.1.2011.6.139.2.8.2.3
		hwApTypeGroup OBJECT-GROUP
			OBJECTS { hwApTypeDesc, hwApTypeLineatePortNum, hwApTypeRadioNum, hwApTypeMaxStaNum, hwApTypeMaxSsidNum,
				hwApTypeAntennaGain, hwApTypeRowStatus, hwApTypeReset, hwApTypeLineatePortType, hwApTypeRadioType,
				hwRadioMaxSpatialStreamsNum, hwRadioMaxAntennasNum, hwRadioMaxVAPNum, hwApTypeRadioAntennaGain, hwApLocalAssocResSwitch }
			STATUS current
			DESCRIPTION
				"Description."
			::= { hwWlanDeviceObjectGroups 3 }


--  1.3.6.1.4.1.2011.6.139.2.8.2.4
		-- 1.3.6.1.4.1.2011.6.139.2.8.2.4
		hwApProfileGroup OBJECT-GROUP
			OBJECTS { hwApEthPortMtu, hwApDosDefend, hwApWorkMode, hwApLogBackupServerIp, hwApLogBackupMode,
				hwApProfileRowStatus, hwApSampleTime, hwApStatisticsInterval, hwApEapStartMode, hwApEapStartUnicastMac,
				hwApEapStartTransform, hwApEapResponseMode, hwApEapResponseUnicastMac, hwApEapResponseTransform, hwApOfflineManagement,
				hwApAlarmRestrictionMode, hwApAlarmRestrictionPeriod, hwAp4WayHandshakeRoamPolicy, hwApLogRecordLevel, hwApLogBackupPeriodTime,
				hwApLogRecordFtpMode, hwApLogServerUsername, hwApLogServerUserPassword, hwApLogServerIp, hwApProfileTelnetSwitch,
				hwApSshSwitch, hwApProfileDhcpTrustPort, hwApProfileConsoleSwitch,hwApProfileMaxUserNum, hwApProfileNdTrustPort,
				hwApLedSwitch, hwApProfileDefault, hwApProfileBatchStart, hwApProfileBatchNumber, hwApProfileBatchReturnNumber, hwApProfileBatchNameList
				}
			STATUS current
			DESCRIPTION
				"Description."
			::= { hwWlanDeviceObjectGroups 4 }


--  1.3.6.1.4.1.2011.6.139.2.8.2.5
		-- 1.3.6.1.4.1.2011.6.139.2.8.2.5
		hwApAuthListGroup OBJECT-GROUP
			OBJECTS { hwApMacWhitelistRowStatus, hwApSnWhitelistRowStatus, hwApAuthMode, hwApMacWhitelistBatchQueryStartNumber, hwApMacWhitelistBatchQueryNumber,
				hwApMacWhitelistBatchQueryList, hwApMacWhitelistBatchQueryReturnNumber, hwApSnWhitelistBatchQueryStartNumber, hwApSnWhitelistBatchQueryNumber, hwApSnWhitelistBatchQueryList,
				hwApSnWhitelistBatchQueryReturnNumber, hwApMacBlacklistRowStatus, hwApSnBlacklistRowStatus }
			STATUS current
			DESCRIPTION
				"Description."
			::= { hwWlanDeviceObjectGroups 5 }


--  1.3.6.1.4.1.2011.6.139.2.8.2.6
		-- 1.3.6.1.4.1.2011.6.139.2.8.2.6
		hwApRegionGroup OBJECT-GROUP
			OBJECTS { hwApRegionName, hwApRegionDeployMode, hwApRegionApNumber, hwApRegionApIndexMask, hwApRegionRowStatus,
				hwApRegionForwardMode, hwApRegionCountryCode, hwApRegionDefault, hwApRegionAllExistRegionIndexMask, hwApRegionBatchStart,
				hwApRegionBatchNumber, hwApRegionBatchReturnNumber, hwApRegionBatchNameList, hwApRegionBatchDeployMode, hwApSrcRegionIndex,
				hwApDestRegionIndex, hwApRegionScanChannel2G, hwApRegionScanChannel5G,hwApRegionCalibrateChannel2G,hwApRegionCalibrateChannel5G,
				hwApRegionCalibrate5gBandWidth }
			STATUS current
			DESCRIPTION
				"Description."
			::= { hwWlanDeviceObjectGroups 6 }


--   1.3.6.1.4.1.2011.6.139.2.8.2.2
-- 1.3.6.1.4.1.2011.6.139.2.8.2.7
		-- 1.3.6.1.4.1.2011.6.139.2.8.2.7
		hwApGroup OBJECT-GROUP
			OBJECTS { hwApUsedType, hwApUsedProfileName, hwApUsedRegionIndex, hwApMac, hwApSn,
				hwApSysName, hwApRunState, hwApSoftwareVersion, hwApHardwareVersion, hwApCpuType,
				hwApCpufrequency, hwApMemoryType, hwApDomain, hwApIpAddress, hwApIpNetMask,
				hwApGatewayIp, hwApMemorySize, hwApFlashSize, hwApRunTime, hwApUpEthPortSpeed,
				hwApUpEthPortSpeedMode, hwApUpEthPortDuplex, hwApUpEthPortDuplexMode, hwApAdminOper, hwApRowstatus,
				hwApPerformanceStatCycle, hwApDNS, hwApRunningMode, hwApForwardMode, hwApAntennaMode,
				hwApCpuThreshold, hwApMemThreshold, hwApNEnumber, hwApOnlineTime, hwApSysSoftwareDesc,
				hwApSysHardtwareDesc, hwApSysManufacture, hwApSysSoftwareName, hwApSysSoftwareVendor, hwApManagementVlanID,
				hwApUsername, hwApPassword, hwApAcIP1, hwApAcIP2, hwApAcIP3,
				hwApAcIP4, hwApIpMode, hwApLldpEnable, hwApLldpManageAddr, hwApLldpPortDes,
				hwApLldpSysCab, hwApLldpSysDes, hwApLldpSysName, hwApLldpDelay, hwApLldpHoldMultiplier,
				hwApLldpInterval, hwApLldpRestartDelay, hwApLldpAdminStatus, hwApLldpReportInterval, hwApBomCode,
				hwApProtectAcPriority, hwApProtectAcIP, hwApOpticalHighRxPowerThreshold, hwApOpticalLowRxPowerThreshold, hwApOpticalHighTemperatureThreshold,
				hwApOpticalLowTemperatureThreshold, hwApKeepService, hwApPriorityAccessMode, hwApLineateportMode, hwApLineateportVlanTagged,
				hwApLineateportVlanUntagged, hwApLineateportPvidVlan, hwApLineateportUserIsolate, hwApLineateportStpEnable, hwApHighTemperatureThreshold,
				hwApLowTemperatureThreshold, hwApReset, hwApStaticIpAddress, hwApStaticNetMask, hwApStaticGatewayIp,
				hwApAttackFloodInterval, hwApAttackFloodTimes, hwApDynamicBlacklistEnable, hwApDynamicBlacklistAgingInt, hwApAttackPskInterval,
				hwApAttackPskTimes, hwApAccessBalanceGap, hwApIpv6Address, hwApIpv6NetMask, hwApGatewayIpv6, hwApIpv6DNS, hwApProtectAcIPv6Addr,
				hwApLineatePortCfgMtu, hwApLineatePortMacAddress, hwApAccessBalanceSwitch, hwApNatIpAddress, hwApAttackFloodQuietTime, hwApAttackPskQuietTime, hwApAttackWeakivQuietTime, hwApAttackSpoofQuietTime, hwApBootCountTotal, hwApBootCountPowerOff, hwApBootCountRowStatus, hwApLineatePortType, hwApLineatePortDesc, hwApLineatePortState, hwApLineatePortSpeed,
				hwApMultiLineatePortDuplex, hwApMultiLineatePortNegotiation,hwApMultiLineatePortMode, hwApMultiLineatePortUserIsolate,
				hwApMultiLineatePortStpEnable, hwApMultiLineatePortVlanTagged, hwApMultiLineatePortVlanUntagged, hwApMultiLineatePortPvidVlan,
				 hwApMultiLineatePortCRCErrorHighThreshold, hwApMultiLineatePortCRCErrorLowThreshold, hwApMultiLineatePortCRCErrorSwitch,
                                hwApLineatePortAclNumInbound, hwApLineatePortAclNumOutbound, hwApLineatePortAclNameInbound, hwApLineatePortAclNameOutbound, hwApLineatePortAclSwitchInbound,
				hwApLineatePortAclSwitchOutbound, hwApLineatePortAclNumInboundIPV6, hwApLineatePortAclNumOutboundIPV6, hwApLineatePortAclNameInboundIPV6, hwApLineatePortAclNameOutboundIPV6,
				hwApLineatePortAclSwitchInboundIPV6, hwApLineatePortAclSwitchOutboundIPV6, hwApMultiLineatePortIsAddInTrunk, hwApMultiLineatePortAddedOrExitTrunkID,
				hwApAllExistApIndexMask, hwUnAuthorizedApRecordNumber, hwUnAuthorizedApRecordAdmin,
				hwApBatchIndexStart, hwApBatchIndexNumber, hwApBatchIndexReturnNumber, hwApBatchState, hwApBatchNameList,
				hwApPingIndex, hwApPingAddress, hwApPingCount, hwApPingPacketSize, hwApPingWaitTime,
				hwApPingTimeOut, hwApPingResultSuccessCount, hwApPingResultFailureCount, hwApPingResultAverageResponseTime, hwApPingResultMinimumResponseTime,
				hwApPingResultMaximumResponseTime, hwApPingApMac, hwApPingResultFlag, hwApMemoryUseRate, hwApCpuUseRate, hwApFlashFreeSize,
				hwApTemperature, hwApOnlineUserNum, hwApUpPortSpeed, hwApUpPortRecvFrames, hwApUpPortRecvRightFrames,
				hwApUpPortRecvErrorFrames, hwApUpPortSendFrames, hwApUpPortRecvBytes, hwApUpPortSendBytes, hwAPUpPortPER,
				hwAPWirelessUpPortTraffic, hwAPUpPortTraffic, hwApAirportSendDropFrames, hwApEthportRecvDropFrames, hwApAirportUpTraffic,
				hwApAirportDwTraffic, hwApEthportDwTraffic, hwApEthportUpTraffic, hwApAirportRecvDropPacket, hwApAirportRecvErrorPacket,
				hwApEthportRecvUnicastPacket, hwApEthportRecvNonUnicastPacket, hwApEthportSendUnicastPacket, hwApEthportSendNonUnicastPacket, hwApAvgRCPUUseRate,
				hwApAvgRMemoryUseRate, hwEthportSendDropFrames, hwEthportSendErrorFrames, hwEthportUpDwnTimes, hwApAirportRecvUnicastFrames,
				hwApEthportRecvUnknownFrames, hwApEthportUpRate, hwApEthportDownRate, hwApUnauthorizedApType, hwApUnauthorizedApMacAddress,
				hwApUnauthorizedApSn, hwApUnauthorizedApIpAddress, hwApUnauthorizedApRecordTime, hwApStaAveSignalStrength, hwMacApIndex,
				hwMacApUsedType, hwMacApUsedProfileName, hwMacApUsedRegionIndex, hwMacApSn, hwMacApSysName,
				hwMacApRunState, hwMacApSoftwareVersion, hwMacApHardwareVersion, hwMacApCpuType, hwMacApCpufrequency,
				hwMacApMemoryType, hwMacApDomain, hwMacApIpAddress, hwMacApIpNetMask, hwMacApGatewayIp,
				hwMacApMemorySize, hwMacApFlashSize, hwMacApRunTime, hwMacApUpEthPortSpeed, hwMacApUpEthPortSpeedMode,
				hwMacApUpEthPortDuplex, hwMacApUpEthPortDuplexMode, hwMacApAdminOper, hwMacApRowstatus, hwMacApPerformanceStatCycle,
				hwMacApDNS, hwMacApRunningMode, hwMacApForwardMode, hwMacApAntennaMode, hwMacApCpuThreshold,
				hwMacApMemThreshold, hwMacApNEnumber, hwMacApOnlineTime, hwMacApSysSoftwareDesc, hwMacApSysHardtwareDesc,
				hwMacApSysManufacture, hwMacApSysSoftwareName, hwMacApSysSoftwareVendor, hwMacApManagementVlanID, hwMacApUsername,
				hwMacApPassword, hwMacApAcIP1, hwMacApAcIP2, hwMacApAcIP3, hwMacApAcIP4,
				hwMacApIpMode, hwMacApLldpEnable, hwMacApLldpManageAddr, hwMacApLldpPortDes, hwMacApLldpSysCab,
				hwMacApLldpSysDes, hwMacApLldpSysName, hwMacApLldpDelay, hwMacApLldpHoldMultiplier, hwMacApLldpInterval,
				hwMacApLldpRestartDelay, hwMacApLldpAdminStatus, hwMacApLldpReportInterval, hwMacApBomCode, hwMacApProtectAcPriority,
				hwMacApProtectAcIP, hwMacApOpticalHighRxPowerThreshold, hwMacApOpticalLowRxPowerThreshold, hwMacApOpticalHighTemperatureThreshold, hwMacApOpticalLowTemperatureThreshold,
				hwMacApKeepService, hwMacApPriorityAccessMode, hwMacApLineateportMode, hwMacApLineateportVlanTagged, hwMacApLineateportVlanUntagged,
				hwMacApLineateportPvidVlan, hwMacApLineateportUserIsolate, hwMacApLineateportStpEnable, hwMacApHighTemperatureThreshold, hwMacApLowTemperatureThreshold,
				hwMacApReset, hwMacApStaticIpAddress, hwMacApStaticNetMask, hwMacApStaticGatewayIp, hwMacApAttackFloodInterval,
				hwMACApAttackFloodTimes, hwMACApDynamicBlacklistEnable, hwMACApDynamicBlacklistAgingInt, hwMACApAttackPskInterval, hwMACApAttackPskTimes, hwMACApAccessBalanceGap,
				hwMACApIpv6Address, hwMACApIpv6NetMask, hwMACApGatewayIpv6, hwMACApIpv6DNS, hwMACApProtectAcIPv6Addr, hwMACApLineatePortCfgMtu, hwMACApLineatePortMacAddress, hwMACApAccessBalanceSwitch,
				hwMACApNatIpAddress, hwMACApAttackFloodQuietTime, hwMACApAttackPskQuietTime, hwMACApAttackWeakivQuietTime, hwMACApAttackSpoofQuietTime, hwMACApBootCountTotal, hwMACApBootCountPowerOff, hwMACApBootCountRowStatus, hwMacApLineatePortType, hwMacApLineatePortDesc, hwMacApLineatePortState, hwMacApLineatePortSpeed, hwMacApMultiLineatePortDuplex, hwMacApMultiLineatePortNegotiation,
				hwMacApMultiLineatePortMode, hwMacApMultiLineatePortUserIsolate, hwMacApMultiLineatePortStpEnable, hwMacApMultiLineatePortVlanTagged, hwMacApMultiLineatePortVlanUntagged,
				hwMacApMultiLineatePortPvidVlan, hwMacApMultiLineatePortCRCErrorHighThreshold, hwMacApMultiLineatePortCRCErrorLowThreshold, hwMacApMultiLineatePortCRCErrorSwitch, hwMacApLineatePortAclNumInbound,
				hwMacApLineatePortAclNumOutbound, hwMacApLineatePortAclNameInbound, hwMacApLineatePortAclNameOutbound, hwMacApLineatePortAclSwitchInbound, hwMacApLineatePortAclSwitchOutbound, hwMacApLineatePortAclNumInboundIPV6,
				hwMacApLineatePortAclNumOutboundIPV6, hwMacApLineatePortAclNameInboundIPV6, hwMacApLineatePortAclNameOutboundIPV6, hwMacApLineatePortAclSwitchInboundIPV6, hwMacApLineatePortAclSwitchOutboundIPV6,hwMacApMultiLineatePortIsAddInTrunk, hwMacApMultiLineatePortAddedOrExitTrunkID,
                                hwMacApMemoryUseRate, hwMacApCpuUseRate, hwMacApFlashFreeSize, hwMacApTemperature,
				hwMacApOnlineUserNum, hwMacApUpPortSpeed, hwMacApUpPortRecvFrames, hwMacApUpPortRecvRightFrames, hwMacApUpPortRecvErrorFrames,
				hwMacApUpPortSendFrames, hwMacApUpPortRecvBytes, hwMacApUpPortSendBytes, hwMacAPUpPortPER, hwMacAPWirelessUpPortTraffic,
				hwMacAPUpPortTraffic, hwMacApAirportSendDropFrames, hwMacApEthportRecvDropFrames, hwMacApAirportUpTraffic, hwMacApAirportDwTraffic,
				hwMacApEthportDwTraffic, hwMacApEthportUpTraffic, hwMacApAirportRecvDropPacket, hwMacApAirportRecvErrorPacket, hwMacApEthportRecvUnicastPacket,
				hwMacApEthportRecvNonUnicastPacket, hwMacApEthportSendUnicastPacket, hwMacApEthportSendNonUnicastPacket, hwMacApAvgRCPUUseRate, hwMacApAvgRMemoryUseRate,
				hwMacEthportSendDropFrames, hwMacEthportSendErrorFrames, hwMacEthportUpDwnTimes, hwMacApAirportRecvUnicastFrames, hwMacApEthportRecvUnknownFrames,
				hwMacEthportUpRate, hwMacEthportDownRate, hwApLineportDesc, hwApLineportType, hwApLineportMtu,
				hwApLineportSpeed, hwApLineportMac, hwApLineportAdminStatus, hwApLineportNum, hwMacApLineportDesc,
				hwMacApLineportType, hwMacApLineportMtu, hwMacApLineportSpeed, hwMacApLineportMac, hwMacApLineportAdminStatus,
				hwMacApLineportNum, hwApLldpRemChassisIdSubtype, hwApLldpRemChassisId, hwApLldpRemPortIdSubtype, hwApLldpRemPortId,
				hwApLldpRemPortDesc, hwApLldpRemSysName, hwApLldpRemSysDesc, hwApLldpRemSysCapSupported, hwApLldpRemSysCapEnabled,
				hwMacApLldpRemChassisIdSubtype, hwMacApLldpRemChassisId, hwMacApLldpRemPortIdSubtype, hwMacApLldpRemPortId, hwMacApLldpRemPortDesc,
				hwMacApLldpRemSysName, hwMacApLldpRemSysDesc, hwMacApLldpRemSysCapSupported, hwMacApLldpRemSysCapEnabled, hwApLldpRemManAddrIfSubtype,
				hwApLldpRemManAddrIfId, hwApLldpRemManAddrOID, hwMACApLldpRemManAddrIfSubtype, hwMACApLldpRemManAddrIfId, hwMACApLldpRemManAddrOID,
				hwApOpticalNominalBitRate, hwApOpticalLinkLen9X125km, hwApOpticalLinkLen50X125X100m, hwApOpticalLinkLen62p5X125X10m, hwApOpticalLinkLenCopper,
				hwApOpticalSfpConnector, hwApOpticalDdmVoltage, hwApOpticalDdmTxBiasCurrent, hwApOpticalDdmTxPower, hwApOpticalDdmRxPower,
				hwApOpticalDdmTemperature, hwApOpticalVdndorOui, hwApOpticalVendorName, hwApOpticalVendorPn, hwApOpticalVendorRev,
				hwApOpticalVendorSn, hwMacApOpticalNominalBitRate, hwMacApOpticalLinkLen9X125km, hwMacApOpticalLinkLen50X125X100m, hwMacApOpticalLinkLen62p5X125X10m,
				hwMacApOpticalLinkLenCopper, hwMacApOpticalSfpConnector, hwMacApOpticalDdmVoltage, hwMacApOpticalDdmTxBiasCurrent, hwMacApOpticalDdmTxPower,
				hwMacApOpticalDdmRxPower, hwMacApOpticalDdmTemperature, hwMacApOpticalVdndorOui, hwMacApOpticalVendorName, hwMacApOpticalVendorPn,
				hwMacApOpticalVendorRev, hwMacApOpticalVendorSn, hwApSysnameApId, hwApSysnameApMac, hwApElectronicLabel,
				hwMacApElectronicLabel }
			STATUS current
			DESCRIPTION
				"Description."
			::= { hwWlanDeviceObjectGroups 7 }

                 hwAcGroup OBJECT-GROUP
			OBJECTS { hwAcIpVersion, hwAcIPv4Address, hwAcIPv6Address, hwAcState,
				hwAcRowStatus, hwMobilityGroupMemberList, hwMobilityGroupStatus,hwMobilityGroupMemberOpcode,
				hwMobilityGroupMemberIndex}
			STATUS current
			DESCRIPTION
				"Description."
			::= { hwWlanDeviceObjectGroups 8 }


	END

--
-- HUAWEI-WLAN-DEVICE-MIB.mib
--
