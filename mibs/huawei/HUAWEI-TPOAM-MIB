-- =================================================================
-- Copyright (C) 2014 by  HUAWEI TECHNOLOGIES. All rights reserved.
--
-- Description: HUAWEI-TPOAM-MIB
-- Reference:
-- Version:     V2.23
-- History:
--     <YaoShuran>, <2011-05-20>, <V1.01 publish>
--     <LiuLihua>, <2012-03-06>, <V1.02 publish>
-- ==================================================================

    HUAWEI-TPOAM-MIB DEFINITIONS ::= BEGIN

        IMPORTS
            CounterBasedGauge64
                FROM HCNUM-TC
            hwDatacomm
                FROM HUAWEI-MIB
            EnabledStatus
                FROM P-BRIDGE-MIB
            OBJECT-GROUP, MODULE-COMPLIANCE, NOTIFICATION-GROUP
                FROM SNMPv2-CONF
            Integer32, Unsigned32, Counter32, BITS, OBJECT-TYPE,
            MODULE-IDENTITY, NOTIFICATION-TYPE, IpAddress
                FROM SNMPv2-SMI
            MacAddress, TruthValue, RowStatus, TimeInterval, TimeStamp, DateAndTime,
            TEXTUAL-CONVENTION, PhysAddress
                FROM SNMPv2-TC
            HWL2VpnVcEncapsType
                FROM HUAWEI-VPLS-EXT-MIB
              ;

        hwMplsTpOamMib MODULE-IDENTITY
            LAST-UPDATED "201412170000Z"
            ORGANIZATION
               "Huawei Technologies Co.,Ltd."
            CONTACT-INFO
                "Huawei Industrial Base
                  Bantian, Longgang
                   Shenzhen 518129
                   People's Republic of China
                   Website: http://www.huawei.com
                   Email: support@huawei.com
                 "
            DESCRIPTION
                "MPLS-TP OAM MIB"

            -- Revision history
            REVISION     "201412170000Z"
            DESCRIPTION  "V2.23, update description of hwMplsTpOamMeL3vpnName, hwMplsTpOamMeL2vpnNetgateMac.
                          "

            REVISION     "201310140000Z"
            DESCRIPTION  "V2.22, update description of hwMplsTpOamIpMegPingMinDelay, hwMplsTpOamIpMegPingMaxDelay, hwMplsTpOamIpMegPingAverDelay, hwMplsTpOamIpMegTracertRespTable.
                          "

           REVISION     "201309250000Z"
            DESCRIPTION  "V2.21, added hwMplsTpOamIpMegPingTrap, hwMplsTpOamIpMegTracertTrap in trap.
                          added hwMplsTpOamMeL3vpnName, hwMplsTpOamMeL2vpnNetgateMac, hwMplsTpOamMeSourceip, hwMplsTpOamIpUni in HwMplsTpOamMeEntry.
                          added hwMplsTpOamIpMegObject.
                         "

            REVISION     "201105200000Z"
            DESCRIPTION  "V1.01, added hwMplsTpOamLockEnable, hwMplsTpOamLockInterval, hwMplsTpOamLockExp, hwMplsTpOamCsfEnable, hwMplsTpOamCsfInterval, hwMplsTpOamCsfExp, hwMplsTpOamTstResetResult, hwMplsTpOamMegLevel in HwMplsTpOamMegEntry.
                          added hwMplsTpOamMeLspName,hwMplsTpOamMeVsiName in HwMplsTpOamMeEntry.
                          added tables hwMplsTpOamMeasureStatisticTestTable, hwMplsTpOamMegSectionLookupTable, hwMplsTpOamMegLspLookupTable, hwMplsTpOamMegVsiLookupTable
                         "

            REVISION     "201009120000Z"
            DESCRIPTION  "V1.00, initial version."
            ::= { hwMplsTpOam 1 }



--
-- Textual conventions
--


-- Node definitions
--

        hwMplsTpOam OBJECT IDENTIFIER ::= { hwDatacomm 235 }


        hwMplsTpOamMegObject OBJECT IDENTIFIER ::= { hwMplsTpOamMib 1 }
        hwMplsTpOamMegTable OBJECT-TYPE
            SYNTAX SEQUENCE OF HwMplsTpOamMegEntry
            MAX-ACCESS not-accessible
            STATUS current
            DESCRIPTION
                "
                This table is used to create a MPLS-TP Maintenance Entity Group Object (MEG).
                "
            ::= { hwMplsTpOamMegObject 1 }


        hwMplsTpOamMegEntry OBJECT-TYPE
            SYNTAX HwMplsTpOamMegEntry
            MAX-ACCESS not-accessible
            STATUS current
            DESCRIPTION
                "The MEG table entry."
            INDEX { hwMplsTpOamMegId }
            ::= { hwMplsTpOamMegTable 1 }


        HwMplsTpOamMegEntry ::=
            SEQUENCE {
                hwMplsTpOamMegId
                    OCTET STRING,
                hwMplsTpOamCCSendEnable
                    EnabledStatus,
                hwMplsTpOamCCReceiveEnable
                    EnabledStatus,
                hwMplsTpOamCCInterval
                    INTEGER,
                hwMplsTpOamCCExp
                    Integer32,
                hwMplsTpOamSingleLossReceiveEnable
                    EnabledStatus,
                hwMplsTpOamSingleLossEnable
                    EnabledStatus,
                hwMplsTpOamSingleLossCount
                    Integer32,
                hwMplsTpOamSingleLossInterval
                    INTEGER,
                hwMplsTpOamSingleLossExp
                    Integer32,
                hwMplsTpOamDualLossEnable
                    EnabledStatus,
                hwMplsTpOamDualLossInterval
                    INTEGER,
                hwMplsTpOamDualLossSD1Threshold
                    Integer32,
                hwMplsTpOamDualLossSD2Threshold
                    Integer32,
                hwMplsTpOamOneWayDelayMeasureEnable
                    EnabledStatus,
                hwMplsTpOamOneWayDelayMeasureInterval
                    INTEGER,
                hwMplsTpOamOneWayDelayMeasureCount
                    Integer32,
                hwMplsTpOamOneWayDelayMeasureExp
                    Integer32,
                hwMplsTpOamOneWayDelayMeasureResetResult
                    EnabledStatus,
                hwMplsTpOamTwoWayDelayMeasureEnable
                    EnabledStatus,
                hwMplsTpOamTwoWayDelayMeasureInterval
                    INTEGER,
                hwMplsTpOamTwoWayDelayMeasureCount
                    Integer32,
                hwMplsTpOamTwoWayDelayMeasureExp
                    Integer32,
                hwMplsTpOamAisEnable
                    EnabledStatus,
                hwMplsTpOamAisInterval
                    INTEGER,
                hwMplsTpOamAisExp
                    Integer32,
                hwMplsTpOamSingleLossResetResult
                    EnabledStatus,
                hwMplsTpOamTwoWayDelayMeasureResetResult
                    EnabledStatus,
                hwMplsTpOamTwoWayDelayMeasureTwoStamp
                    EnabledStatus,
                hwMplsTpOamLockEnable
                    EnabledStatus,
                hwMplsTpOamLockInterval
                    INTEGER,
                hwMplsTpOamLockExp
                    Integer32,
                hwMplsTpOamCsfEnable
                    EnabledStatus,
                hwMplsTpOamCsfInterval
                    INTEGER,
                hwMplsTpOamCsfExp
                    Integer32,
                hwMplsTpOamTstResetResult
                    EnabledStatus,
                hwMplsTpOamMegLevel
                    Integer32,
                hwMplsTpOamRDIEnable
                    EnabledStatus,
                hwMplsTpOamSingleLossProactiveSD1Threshold
                    Integer32,
                hwMplsTpOamSingleLossProactiveSD2Threshold
                    Integer32,
                hwMplsTpOamSingleLossProactiveEnable
                    EnabledStatus,
                hwMplsTpOamOneWayDelayMeasureProactiveEnable
                    EnabledStatus,
                hwMplsTpOamTwoWayDelayMeasureProactiveEnable
                    EnabledStatus,
                hwMplsTpOneWayDelayMeasurePaddingValue
                    Integer32,
                hwMplsTpOneWayDelayMeasurePacketSize
                    Integer32,
                hwMplsTpTwoWayDelayMeasurePaddingValue
                    Integer32,
                hwMplsTpTwoWayDelayMeasurePacketSize
                    Integer32,
                hwMplsTpOamBitErrorDetectionSD1Threshold
                    Integer32,
                hwMplsTpOamBitErrorDetectionSD2Threshold
                    Integer32,
                hwMplsTpOamMegRowStatus
                    RowStatus,
                hwMplsTpOamSingleLossProactiveSD1ContinuousPeriod
                    Integer32,
                hwMplsTpOamSingleLossProactiveSD2ContinuousPeriod
                    Integer32,
                hwMplsTpOamSingleLossProactiveSD1Period
                    Integer32,
                hwMplsTpOamSingleLossProactiveSD1Count
                    Integer32,
                hwMplsTpOamSingleLossProactiveSD2Period
                    Integer32,
                hwMplsTpOamSingleLossProactiveSD2Count
                    Integer32,
                hwMplsTpOamSingleLossProactiveRevertivePeriod
                    Integer32,
                hwMplsTpOamOneWayDelayMeasureReceiveEnable
                    EnabledStatus
             }

        hwMplsTpOamMegId OBJECT-TYPE
            SYNTAX OCTET STRING (SIZE (1..48))
            MAX-ACCESS accessible-for-notify
            STATUS current
            DESCRIPTION
                "
                This object indicates the ID of the MEG.
                "
            ::= { hwMplsTpOamMegEntry 1 }

        hwMplsTpOamCCSendEnable OBJECT-TYPE
            SYNTAX EnabledStatus
            MAX-ACCESS read-create
            STATUS current
            DESCRIPTION
                "
                This object indicates whether CCM sending is enabled on the ME in a MEG.
                "
            ::= { hwMplsTpOamMegEntry 2 }

        hwMplsTpOamCCReceiveEnable OBJECT-TYPE
            SYNTAX EnabledStatus
            MAX-ACCESS read-create
            STATUS current
            DESCRIPTION
                "
                This object indicates whether CCM receiving is enabled on the ME in a MEG.
                "
             ::= { hwMplsTpOamMegEntry 3 }

        hwMplsTpOamCCInterval OBJECT-TYPE
            SYNTAX INTEGER{
                interval3ms       (1),
                interval10ms      (2),
                interval100ms     (3),
                interval1000ms    (4),
                interval10000ms   (5),
                interval60000ms   (6),
                interval600000ms  (7)
                }
            MAX-ACCESS read-create
            STATUS current
            DESCRIPTION
                "
                This object indicates the interval for MEs in the MEG to send
                or probe CCMs. The value of this object can be:
                1:  3.3 milliseconds
                2:  10 milliseconds
                3:  100 milliseconds
                4:  1 second
                5:  10 seconds
                6:  1 minute
                7:  10 minutes
                By default, the value is 1 second.
        "
            DEFVAL { 4 }
            ::= { hwMplsTpOamMegEntry 4 }

        hwMplsTpOamCCExp OBJECT-TYPE
            SYNTAX Integer32 (0..7)
             MAX-ACCESS read-create
            STATUS current
            DESCRIPTION
                "
                This object indicates the packet EXP for MEs in the MEG to send
                or probe CCMs.
                "
            DEFVAL { 7 }
            ::= { hwMplsTpOamMegEntry 5 }

        hwMplsTpOamSingleLossReceiveEnable OBJECT-TYPE
            SYNTAX EnabledStatus
             MAX-ACCESS read-create
            STATUS current
            DESCRIPTION
                "
                This object indicates the receive flag for packet single loss statistics in the MEG.
                "
            ::= { hwMplsTpOamMegEntry 6 }

        hwMplsTpOamSingleLossEnable OBJECT-TYPE
            SYNTAX EnabledStatus
            MAX-ACCESS read-create
            STATUS current
            DESCRIPTION
                "
                This object indicates the packet single loss statistics is enabled in the MEG.
                "
            ::= { hwMplsTpOamMegEntry 7 }

        hwMplsTpOamSingleLossCount OBJECT-TYPE
            SYNTAX Integer32(1..60)
            MAX-ACCESS read-create
            STATUS current
            DESCRIPTION
                "
                This object indicates the count for packet single loss statistics.
                "
            DEFVAL { 5 }
            ::= { hwMplsTpOamMegEntry 8 }

        hwMplsTpOamSingleLossInterval OBJECT-TYPE
            SYNTAX INTEGER
            {
              interval1000ms(4),
              interval10000ms(5)
            }
            MAX-ACCESS read-create
            STATUS current
            DESCRIPTION
                "
                This object indicates the interval for packet single loss statistics in the MEG.
                "
            DEFVAL { 4 }
            ::= { hwMplsTpOamMegEntry 9 }

        hwMplsTpOamSingleLossExp OBJECT-TYPE
            SYNTAX Integer32 (0..7)
            MAX-ACCESS read-create
            STATUS current
            DESCRIPTION
                "
                This object indicates the packet EXP for packet single loss statistics in the MEG.
                "
            DEFVAL { 7 }
            ::= { hwMplsTpOamMegEntry 10 }

        hwMplsTpOamDualLossEnable OBJECT-TYPE
            SYNTAX EnabledStatus
            MAX-ACCESS read-create
            STATUS current
            DESCRIPTION
                "
                This object indicates the dual loss statistics is enabled in the MEG.
                "
            ::= { hwMplsTpOamMegEntry 11 }

        hwMplsTpOamDualLossInterval OBJECT-TYPE
            SYNTAX INTEGER{
                interval1000ms     (4),
                interval10000ms    (5)
                }
            MAX-ACCESS read-create
            STATUS current
            DESCRIPTION
                "
                This object indicates the interval for packet dual loss statistics in the MEG.
                "
            DEFVAL { 4 }
            ::= { hwMplsTpOamMegEntry 12 }

        hwMplsTpOamDualLossSD1Threshold OBJECT-TYPE
            SYNTAX Integer32(1..1000000)
            MAX-ACCESS read-create
            STATUS current
            DESCRIPTION
                "
                This object indicates the signal degrade threshold for packet dual loss statistics in the MEG.
                "
            ::= { hwMplsTpOamMegEntry 13 }

        hwMplsTpOamDualLossSD2Threshold OBJECT-TYPE
            SYNTAX Integer32(1..1000000)
            MAX-ACCESS read-create
            STATUS current
            DESCRIPTION
                "
                This object indicates the signal fault threshold for packet dual loss statistics in the MEG.
                "
            ::= { hwMplsTpOamMegEntry 14 }


        hwMplsTpOamOneWayDelayMeasureEnable OBJECT-TYPE
            SYNTAX EnabledStatus
            MAX-ACCESS read-create
            STATUS current
            DESCRIPTION
                "
                This object indicates the one-way delay statistics is enabled in the MEG.
                "
            ::= { hwMplsTpOamMegEntry 15 }

        hwMplsTpOamOneWayDelayMeasureInterval OBJECT-TYPE
            SYNTAX INTEGER{
                interval1000ms    (4),
                interval10000ms   (5)
                }
            MAX-ACCESS read-create
            STATUS current
            DESCRIPTION
                "
                This object indicates the interval for one-way delay statistics in the MEG.
                "
            DEFVAL { 4 }
            ::= { hwMplsTpOamMegEntry 16 }

        hwMplsTpOamOneWayDelayMeasureCount OBJECT-TYPE
            SYNTAX Integer32(1..60)
            MAX-ACCESS read-create
            STATUS current
            DESCRIPTION
                "
                This object indicates the count for one-way delay statistics in the MEG.
                "
            DEFVAL { 5 }
            ::= { hwMplsTpOamMegEntry 17 }

        hwMplsTpOamOneWayDelayMeasureExp OBJECT-TYPE
            SYNTAX Integer32 (0..7)
            MAX-ACCESS read-create
            STATUS current
            DESCRIPTION
                "
                This object indicates the packet EXP for one-way delay statistics in the MEG.
                "
            DEFVAL { 7 }
            ::= { hwMplsTpOamMegEntry 18 }

        hwMplsTpOamOneWayDelayMeasureResetResult OBJECT-TYPE
            SYNTAX EnabledStatus
            MAX-ACCESS read-create
            STATUS current
            DESCRIPTION
                "
                This object indicates the result for one-way delay statistics in the MEG.
                "
            ::= { hwMplsTpOamMegEntry 19 }

        hwMplsTpOamTwoWayDelayMeasureEnable OBJECT-TYPE
            SYNTAX EnabledStatus
            MAX-ACCESS read-create
            STATUS current
            DESCRIPTION
                "
                This object indicates the two-way delay statistics is enabled in the MEG.
                "
            ::= { hwMplsTpOamMegEntry 20 }

        hwMplsTpOamTwoWayDelayMeasureInterval OBJECT-TYPE
            SYNTAX INTEGER{
                interval1000ms    (4),
                interval10000ms   (5)
                }
            MAX-ACCESS read-create
            STATUS current
            DESCRIPTION
                "
                This object indicates the interval for two-way delay statistics in the MEG.
                "
            DEFVAL { 4 }
            ::= { hwMplsTpOamMegEntry 21 }

        hwMplsTpOamTwoWayDelayMeasureCount OBJECT-TYPE
            SYNTAX Integer32(1..60)
            MAX-ACCESS read-create
            STATUS current
            DESCRIPTION
                "
                This object indicates the count for two-way delay statistics in the MEG.
                "
            DEFVAL { 5 }
            ::= { hwMplsTpOamMegEntry 22 }

        hwMplsTpOamTwoWayDelayMeasureExp OBJECT-TYPE
            SYNTAX Integer32 (0..7)
            MAX-ACCESS read-create
            STATUS current
            DESCRIPTION
                "
                This object indicates the packet EXP for two-way delay statistics in the MEG.
                "
            DEFVAL { 7 }
            ::= { hwMplsTpOamMegEntry 23 }

        hwMplsTpOamAisEnable OBJECT-TYPE
            SYNTAX EnabledStatus
            MAX-ACCESS read-create
            STATUS current
            DESCRIPTION
                "
                This object indicates the AIS(Alarm Indication Signal) is enabled in the MEG.
                "
            ::= { hwMplsTpOamMegEntry 24 }

        hwMplsTpOamAisInterval OBJECT-TYPE
            SYNTAX INTEGER{
                interval1000ms      (4),
                interval60000ms     (6)
                }
            MAX-ACCESS read-create
            STATUS current
            DESCRIPTION
                "
                This object indicates the interval of AIS(Alarm Indication Signal) in the MEG.
                "
            DEFVAL { 4 }
            ::= { hwMplsTpOamMegEntry 25 }

        hwMplsTpOamAisExp OBJECT-TYPE
            SYNTAX Integer32 (0..7)
            MAX-ACCESS read-create
            STATUS current
            DESCRIPTION
                "
                This object indicates the packet EXP of AIS(Alarm Indication Signal) in the MEG.
                "
            DEFVAL { 7 }
            ::= { hwMplsTpOamMegEntry 26 }

        hwMplsTpOamSingleLossResetResult OBJECT-TYPE
            SYNTAX EnabledStatus
            MAX-ACCESS read-create
            STATUS current
            DESCRIPTION
                "
                This object indicates the result for single loss statistics in the MEG.
                "
            ::= { hwMplsTpOamMegEntry 27 }

        hwMplsTpOamTwoWayDelayMeasureResetResult OBJECT-TYPE
            SYNTAX EnabledStatus
            MAX-ACCESS read-create
            STATUS current
            DESCRIPTION
                "
                This object indicates the result for two-way delay statistics in the MEG.
                "
            ::= { hwMplsTpOamMegEntry 28 }

        hwMplsTpOamTwoWayDelayMeasureTwoStamp OBJECT-TYPE
            SYNTAX EnabledStatus
            MAX-ACCESS read-create
            STATUS current
            DESCRIPTION
                "
                This object indicates the result for two-way delay statistics in the MEG.
                "
            ::= { hwMplsTpOamMegEntry 29 }
        hwMplsTpOamLockEnable OBJECT-TYPE
            SYNTAX EnabledStatus
            MAX-ACCESS read-create
            STATUS current
            DESCRIPTION
                "
                This object indicates the LOCK is enabled in the MEG.
                "
            ::= { hwMplsTpOamMegEntry 30 }

        hwMplsTpOamLockInterval OBJECT-TYPE
            SYNTAX INTEGER
            {
              interval1000ms(4),
              interval60000ms(6)
            }
            MAX-ACCESS read-create
            STATUS current
            DESCRIPTION
                "
                This object indicates the interval of LOCK in the MEG.
                "
            DEFVAL { 4 }
            ::= { hwMplsTpOamMegEntry 31 }

        hwMplsTpOamLockExp OBJECT-TYPE
            SYNTAX Integer32 (0..7)
            MAX-ACCESS read-create
            STATUS current
            DESCRIPTION
                "
                This object indicates the packet EXP of LOCK in the MEG.
                "
            DEFVAL { 7 }
            ::= { hwMplsTpOamMegEntry 32 }


        hwMplsTpOamCsfEnable OBJECT-TYPE
            SYNTAX EnabledStatus
            MAX-ACCESS read-create
            STATUS current
            DESCRIPTION
                "
                This object indicates the CSF(client signal fail) is enabled in the MEG.
                "
            ::= { hwMplsTpOamMegEntry 33 }

        hwMplsTpOamCsfInterval OBJECT-TYPE
            SYNTAX INTEGER
            {
              interval1000ms(4),
              interval60000ms(6)
            }
            MAX-ACCESS read-create
            STATUS current
            DESCRIPTION
                "
                This object indicates the interval of CSF(client signal fail) in the MEG.
                "
            DEFVAL { 4 }
            ::= { hwMplsTpOamMegEntry 34 }

        hwMplsTpOamCsfExp OBJECT-TYPE
            SYNTAX Integer32 (0..7)
            MAX-ACCESS read-create
            STATUS current
            DESCRIPTION
                "
                This object indicates the packet EXP of CSF(client signal fail) in the MEG.
                "
            DEFVAL { 7 }
            ::= { hwMplsTpOamMegEntry 35 }

        hwMplsTpOamTstResetResult OBJECT-TYPE
            SYNTAX EnabledStatus
            MAX-ACCESS read-create
            STATUS current
            DESCRIPTION
                "
                This object indicates the result for test statistics in the MEG.
                "
            ::= { hwMplsTpOamMegEntry 36 }

        hwMplsTpOamMegLevel OBJECT-TYPE
            SYNTAX Integer32 (0..7)
            MAX-ACCESS read-create
            STATUS current
            DESCRIPTION
                "
                This object indicates the level for the MEG.
                "
            DEFVAL { 7 }
            ::= { hwMplsTpOamMegEntry 37 }

         hwMplsTpOamRDIEnable OBJECT-TYPE
            SYNTAX EnabledStatus
            MAX-ACCESS read-create
            STATUS current
            DESCRIPTION
                "
                This object indicates whether RDI is enabled in the MEG.
                "
            ::= { hwMplsTpOamMegEntry 38 }

        hwMplsTpOamSingleLossProactiveSD1Threshold OBJECT-TYPE
            SYNTAX Integer32(1..1000000)
            MAX-ACCESS read-create
            STATUS current
            DESCRIPTION
                "
                This object indicates the signal degrade threshold for proactive single-end packet loss statistics in the MEG.
                "
            ::= { hwMplsTpOamMegEntry 39 }

        hwMplsTpOamSingleLossProactiveSD2Threshold OBJECT-TYPE
            SYNTAX Integer32(1..1000000)
            MAX-ACCESS read-create
            STATUS current
            DESCRIPTION
                "
                This object indicates the signal degrade threshold for proactive single-end packet loss statistics in the MEG.
                "
            ::= { hwMplsTpOamMegEntry 40 }

        hwMplsTpOamSingleLossProactiveEnable OBJECT-TYPE
            SYNTAX EnabledStatus
            MAX-ACCESS read-create
            STATUS current
            DESCRIPTION
                "
                This object indicates whether proactive SLM statistics is enabled in the MEG.
                "
            ::= { hwMplsTpOamMegEntry 41 }

        hwMplsTpOamOneWayDelayMeasureProactiveEnable OBJECT-TYPE
            SYNTAX EnabledStatus
            MAX-ACCESS read-create
            STATUS current
            DESCRIPTION
                "
                This object indicates whether proactive 1DM statistics is enabled in the MEG.
                "
            ::= { hwMplsTpOamMegEntry 42 }

        hwMplsTpOamTwoWayDelayMeasureProactiveEnable OBJECT-TYPE
            SYNTAX EnabledStatus
            MAX-ACCESS read-create
            STATUS current
            DESCRIPTION
                "
                This object indicates whether proactive 2DM statistics is enabled in the MEG.
                "
            ::= { hwMplsTpOamMegEntry 43 }

        hwMplsTpOneWayDelayMeasurePaddingValue OBJECT-TYPE
            SYNTAX Integer32 (0|1)
            MAX-ACCESS read-create
            STATUS current
            DESCRIPTION
                "
                This object indicates the padding bit for 1DM packet in the MEG.
                   1. 0 -the padding bit of 1DM padding packet is 0
                   2. 1 -the padding bit of 1DM padding packet is 1
                "
            ::= { hwMplsTpOamMegEntry 44 }

        hwMplsTpOneWayDelayMeasurePacketSize OBJECT-TYPE
            SYNTAX Integer32 (29 | 64..1518)
            MAX-ACCESS read-create
            STATUS current
            DESCRIPTION
                "
                This object indicates the size of a 1DM packet transmitted in a MEG.
                "
            ::= { hwMplsTpOamMegEntry 45 }

        hwMplsTpTwoWayDelayMeasurePaddingValue OBJECT-TYPE
            SYNTAX Integer32 (0|1)
            MAX-ACCESS read-create
            STATUS current
            DESCRIPTION
                "
                This object indicates the padding bit for 2DM packet in the MEG.
                   1. 0 -the padding bit of DMM padding packet is 0
                   2. 1 -the padding bit of DMM padding packet is 1
                "
            ::= { hwMplsTpOamMegEntry 46 }

        hwMplsTpTwoWayDelayMeasurePacketSize OBJECT-TYPE
            SYNTAX Integer32 (45 | 64..1518)
            MAX-ACCESS read-create
            STATUS current
            DESCRIPTION
                "
                This object indicates the size of a DMM packet transmitted in a MEG.
                "
            ::= { hwMplsTpOamMegEntry 47 }

        hwMplsTpOamBitErrorDetectionSD1Threshold OBJECT-TYPE
            SYNTAX Integer32(0..100)
            MAX-ACCESS read-create
            STATUS current
            DESCRIPTION
                "
                This object indicates the signal degrade threshold for bit error detection statistics in the MEG.
                "
            ::= { hwMplsTpOamMegEntry 48 }

        hwMplsTpOamBitErrorDetectionSD2Threshold OBJECT-TYPE
            SYNTAX Integer32(0..100)
            MAX-ACCESS read-create
            STATUS current
            DESCRIPTION
                "
                This object indicates the signal degrade threshold for bit error detection statistics in the MEG.
                "
            ::= { hwMplsTpOamMegEntry 49 }

        hwMplsTpOamMegRowStatus OBJECT-TYPE
            SYNTAX RowStatus
            MAX-ACCESS read-create
            STATUS current
            DESCRIPTION
                "
                This object indicates the row status of this table.
                "
            ::= { hwMplsTpOamMegEntry 50 }

        hwMplsTpOamSingleLossProactiveSD1ContinuousPeriod OBJECT-TYPE
            SYNTAX Integer32(0..60)
            MAX-ACCESS read-create
            STATUS current
            DESCRIPTION
                "
                This is SD cause APS period.
                "
            ::= { hwMplsTpOamMegEntry 51 }

        hwMplsTpOamSingleLossProactiveSD2ContinuousPeriod OBJECT-TYPE
            SYNTAX Integer32(0..60)
            MAX-ACCESS read-create
            STATUS current
            DESCRIPTION
                "
                This is SD cause APS period.
                "
            ::= { hwMplsTpOamMegEntry 52 }

        hwMplsTpOamSingleLossProactiveSD1Period OBJECT-TYPE
            SYNTAX Integer32(0..60)
            MAX-ACCESS read-create
            STATUS current
            DESCRIPTION
                "
                This is SD cause APS period.
                "
            ::= { hwMplsTpOamMegEntry 53 }

        hwMplsTpOamSingleLossProactiveSD1Count OBJECT-TYPE
            SYNTAX Integer32(0..60)
            MAX-ACCESS read-create
            STATUS current
            DESCRIPTION
                "
                This is SD cause APS period.
                "
            ::= { hwMplsTpOamMegEntry 54 }

        hwMplsTpOamSingleLossProactiveSD2Period OBJECT-TYPE
            SYNTAX Integer32(0..60)
            MAX-ACCESS read-create
            STATUS current
            DESCRIPTION
                "
                This is SD cause APS period.
                "
            ::= { hwMplsTpOamMegEntry 55 }

        hwMplsTpOamSingleLossProactiveSD2Count OBJECT-TYPE
            SYNTAX Integer32(0..60)
            MAX-ACCESS read-create
            STATUS current
            DESCRIPTION
                "
                This is SD cause APS period.
                "
            ::= { hwMplsTpOamMegEntry 56 }

        hwMplsTpOamSingleLossProactiveRevertivePeriod OBJECT-TYPE
            SYNTAX Integer32(0..60)
            MAX-ACCESS read-create
            STATUS current
            DESCRIPTION
                "
                This is SD cause APS reswitch period.
                "
            ::= { hwMplsTpOamMegEntry 57 }

        hwMplsTpOamOneWayDelayMeasureReceiveEnable OBJECT-TYPE
            SYNTAX EnabledStatus
            MAX-ACCESS read-create
            STATUS current
            DESCRIPTION
                "
                This object indicates whether proactive 1DM statistics is enabled in the MEG.
                "
            ::= { hwMplsTpOamMegEntry 58 }

        hwMplsTpOamMeObject OBJECT IDENTIFIER ::= { hwMplsTpOamMib 2 }


        hwMplsTpOamMeTable OBJECT-TYPE
            SYNTAX SEQUENCE OF HwMplsTpOamMeEntry
            MAX-ACCESS not-accessible
            STATUS current
            DESCRIPTION
                "This table is used to create a MPLS-TP Maintenance Entity Object (ME)."
            ::= { hwMplsTpOamMeObject 1 }


        hwMplsTpOamMeEntry OBJECT-TYPE
            SYNTAX HwMplsTpOamMeEntry
            MAX-ACCESS not-accessible
            STATUS current
            DESCRIPTION
                "
                The ME table entry.
                "
            INDEX { hwMplsTpOamMegId,hwMplsTpOamMeIndex }
            ::= { hwMplsTpOamMeTable 1 }


        HwMplsTpOamMeEntry ::=
            SEQUENCE {
                hwMplsTpOamMeIndex
                    Unsigned32,
                hwMplsTpOamMeType
                    INTEGER,
                hwMplsTpOamMeDirection
                    INTEGER,
                hwMplsTpOamMeIfName
                    OCTET STRING,
                hwMplsTpOamMePeerip
                    IpAddress,
                hwMplsTpOamMeVcId
                    Unsigned32,
                hwMplsTpOamMeVcType
                    HWL2VpnVcEncapsType,
                hwMplsTpOamMeVllRemotePeerIp
                    IpAddress,
                hwMplsTpOamMEVllTTL
                    Integer32,
                hwMplsTpOamMeMepId
                    Integer32,
                hwMplsTpOamMeRemoteMepId
                    Integer32,
                hwMplsTpOamMeState
                    INTEGER,
                hwMplsTpOamMeLspName
                    OCTET STRING,
                hwMplsTpOamMeVsiName
                    OCTET STRING,
                hwMplsTpOamMeFarEndState
                    INTEGER,
                hwMplsTpOamMeNearEndState
                    INTEGER,
                hwMplsTpOamMeGal
                    Integer32,
                hwMplsTpOamRingId
                    Integer32,
                hwMplsTpOamRingDirection
                    INTEGER,
                hwMplsTpOamMeRowStatus
                    RowStatus,
                hwMplsTpOamMeSwitchPeerIp
                    IpAddress,
                hwMplsTpOamMeSwitchVcId
                    Unsigned32,
                hwMplsTpOamError
                    Unsigned32,
                hwMplsTpOamMeMipId
                    Integer32,
                hwMplsTpOamMeL3vpnName
                    OCTET STRING,
                hwMplsTpOamMeL2vpnNetgateMac
                    PhysAddress,
                hwMplsTpOamMeSourceip
                    IpAddress,
                hwMplsTpOamIpUni
                    INTEGER
             }


        hwMplsTpOamMeIndex OBJECT-TYPE
            SYNTAX Unsigned32
            MAX-ACCESS accessible-for-notify
            STATUS current
            DESCRIPTION
                "
                The index to the ME table.
                "
            ::= { hwMplsTpOamMeEntry 1 }

        hwMplsTpOamMeType OBJECT-TYPE
            SYNTAX INTEGER
                {
                vll(1),
                vsi(2),
                te(3),
                section(4),
                associate(5),
                ring(6),
                vllMip(7),
                teMip(8),
                ip(9)
                }
            MAX-ACCESS read-create
            STATUS current
            DESCRIPTION
                "
                The type to the ME table.
                "
             ::= { hwMplsTpOamMeEntry 2 }

         hwMplsTpOamMeDirection OBJECT-TYPE
            SYNTAX INTEGER
                {
                ingress(1),
                egress(2),
                dual(3)
                }
            MAX-ACCESS read-only
            STATUS current
            DESCRIPTION
                "
                The direction to the ME table.
                Default is dual.
                This node only be seted by associate LSP.
                "
            ::= { hwMplsTpOamMeEntry 3 }

        hwMplsTpOamMeIfName OBJECT-TYPE
            SYNTAX OCTET STRING (SIZE (0..63))
            MAX-ACCESS read-create
            STATUS current
            DESCRIPTION
                "
                This object indicates the interfacename of the ME.
                "
            DEFVAL { "" }
            ::= { hwMplsTpOamMeEntry 4 }


        hwMplsTpOamMePeerip OBJECT-TYPE
            SYNTAX IpAddress
            MAX-ACCESS read-create
            STATUS current
            DESCRIPTION
                "
                This object indicates the peer IP address.
                "
            ::= { hwMplsTpOamMeEntry 5 }


        hwMplsTpOamMeVcId OBJECT-TYPE
            SYNTAX Unsigned32
            MAX-ACCESS read-create
            STATUS current
            DESCRIPTION
                "
                This object indicates the vc id of PW type ME.
                "
            ::= { hwMplsTpOamMeEntry 6 }


        hwMplsTpOamMeVcType OBJECT-TYPE
            SYNTAX HWL2VpnVcEncapsType
            MAX-ACCESS read-create
            STATUS current
            DESCRIPTION
                "
                This object indicates the vc type of PW type ME.
                "
            ::= { hwMplsTpOamMeEntry 7 }

        hwMplsTpOamMeVllRemotePeerIp OBJECT-TYPE
            SYNTAX IpAddress
            MAX-ACCESS read-create
            STATUS current
            DESCRIPTION
                "
                This object indicates the remote peer IP of PW type ME.
                "
            ::= { hwMplsTpOamMeEntry 8 }

        hwMplsTpOamMEVllTTL OBJECT-TYPE
            SYNTAX Integer32 (1..255)
             MAX-ACCESS read-create
            STATUS current
            DESCRIPTION
                "
                This object indicates the VLL ttl of PW type ME, it uses for TTL Hops in SPE or TPE.
                "
            ::= { hwMplsTpOamMeEntry 9 }

         hwMplsTpOamMeMepId OBJECT-TYPE
            SYNTAX Integer32 (0|1..8191)
            MAX-ACCESS read-create
            STATUS current
            DESCRIPTION
                "
                This object indicates the MEP Id of local.
                "
            ::= { hwMplsTpOamMeEntry 10 }

        hwMplsTpOamMeRemoteMepId OBJECT-TYPE
            SYNTAX Integer32 (0|1..8191)
            MAX-ACCESS read-create
            STATUS current
            DESCRIPTION
                "
                This object indicates the MEP Id of remote.
                "
            ::= { hwMplsTpOamMeEntry 11 }

        hwMplsTpOamMeState OBJECT-TYPE
            SYNTAX INTEGER
                {
                init(1),
                up(2),
                down(3)
                }
            MAX-ACCESS read-only
            STATUS current
            DESCRIPTION
                "
                This object indicates the state of the ME.
                "
            ::= { hwMplsTpOamMeEntry 12 }

        hwMplsTpOamMeLspName OBJECT-TYPE
            SYNTAX OCTET STRING (SIZE (0..19))
            MAX-ACCESS read-create
            STATUS current
            DESCRIPTION
                "
                This object indicates the LSP name of the ME.
                "
            DEFVAL { "" }
            ::= { hwMplsTpOamMeEntry 13 }

        hwMplsTpOamMeVsiName OBJECT-TYPE
            SYNTAX OCTET STRING (SIZE (0..31))
            MAX-ACCESS read-create
            STATUS current
            DESCRIPTION
                "
                This object indicates the VSI name of the ME.
                "
            DEFVAL { "" }
            ::= { hwMplsTpOamMeEntry 14 }

        hwMplsTpOamMeFarEndState OBJECT-TYPE
            SYNTAX INTEGER
                {
                available(1),
                defectUnavailable(2)
                }
            MAX-ACCESS read-only
            STATUS current
            DESCRIPTION
                "
                This object indicates the far-end state of the ME.
                "
            ::= { hwMplsTpOamMeEntry 15 }

        hwMplsTpOamMeNearEndState OBJECT-TYPE
            SYNTAX INTEGER
                {
                available(1),
                defectUnavailable(2)
                }
            MAX-ACCESS read-only
            STATUS current
            DESCRIPTION
                "
                This object indicates the near-end state of the ME.
                "
            ::= { hwMplsTpOamMeEntry 16 }

        hwMplsTpOamMeGal OBJECT-TYPE
            SYNTAX Integer32 (0|13|14)
            MAX-ACCESS read-create
            STATUS current
            DESCRIPTION
                "
                 This object indicates the value of GAL.
                "
            ::= { hwMplsTpOamMeEntry 17 }

        hwMplsTpOamRingId OBJECT-TYPE
            SYNTAX Integer32 (0|1..65535)
            MAX-ACCESS read-create
            STATUS current
            DESCRIPTION
                "
                This object indicates the ring id of the ME.
                "
            ::= { hwMplsTpOamMeEntry 18 }

        hwMplsTpOamRingDirection OBJECT-TYPE
            SYNTAX INTEGER
                {
                invalid(1),
                east(2),
                west(3)
                }
            MAX-ACCESS read-create
            STATUS current
            DESCRIPTION
                "
                This object indicates the ring direction of the ME.
                "
            ::= { hwMplsTpOamMeEntry 19 }

        hwMplsTpOamMeRowStatus OBJECT-TYPE
            SYNTAX RowStatus
            MAX-ACCESS read-create
            STATUS current
            DESCRIPTION
                "
                This object indicates the row status of this table.
                "
            ::= { hwMplsTpOamMeEntry 20 }

        hwMplsTpOamMeSwitchPeerIp OBJECT-TYPE
            SYNTAX IpAddress
            MAX-ACCESS read-create
            STATUS current
            DESCRIPTION
                "
                This object indicates the peer IP address of PW switch node.
                "
            ::= { hwMplsTpOamMeEntry 21 }


        hwMplsTpOamMeSwitchVcId OBJECT-TYPE
            SYNTAX Unsigned32
            MAX-ACCESS read-create
            STATUS current
            DESCRIPTION
                "
                This object indicates the vc id of PW switch node.
                "
            ::= { hwMplsTpOamMeEntry 22 }

       hwMplsTpOamError OBJECT-TYPE
            SYNTAX Unsigned32 (0..4294967295)
            MAX-ACCESS read-only
            STATUS current
            DESCRIPTION
                "
                This object indicates the error for the status.
                "
            DEFVAL { 0 }
            ::= { hwMplsTpOamMeEntry 23 }

       hwMplsTpOamMeMipId OBJECT-TYPE
            SYNTAX Integer32 (0..8191)
            MAX-ACCESS read-create
            STATUS current
            DESCRIPTION
                "
                This object indicates the mip id of the ME.
                "
            DEFVAL { 0 }
            ::= { hwMplsTpOamMeEntry 24 }

        hwMplsTpOamMeL3vpnName OBJECT-TYPE
            SYNTAX OCTET STRING (SIZE (0..31))
            MAX-ACCESS read-create
            STATUS current
            DESCRIPTION
                "
                This object indicates the L3vpn name of the ME.
                "
            DEFVAL { "" }
            ::= { hwMplsTpOamMeEntry 25 }

        hwMplsTpOamMeL2vpnNetgateMac OBJECT-TYPE
            SYNTAX PhysAddress
            MAX-ACCESS read-create
            STATUS current
            DESCRIPTION
                "
                This object indicates the L2vpn Netgate Mac of the ME.
                "
            DEFVAL { "" }
            ::= { hwMplsTpOamMeEntry 26 }

        hwMplsTpOamMeSourceip OBJECT-TYPE
            SYNTAX IpAddress
            MAX-ACCESS read-create
            STATUS current
            DESCRIPTION
                "
                This object indicates the Source Ip of the ME.
                "
            DEFVAL { "" }
            ::= { hwMplsTpOamMeEntry 27 }

        hwMplsTpOamIpUni OBJECT-TYPE
            SYNTAX INTEGER
                {
                invalid(0),
                l2uni(1),
                l3uni(2)
                }
            MAX-ACCESS read-create
            STATUS current
            DESCRIPTION
                "
                This object indicates the  ip meg type of the ME.
                "
            ::= { hwMplsTpOamMeEntry 28 }


        hwMplsTpOamLBObject OBJECT IDENTIFIER ::= { hwMplsTpOamMib 3 }


        hwMplsTpOamLBTable OBJECT-TYPE
            SYNTAX SEQUENCE OF HwMplsTpOamLBEntry
            MAX-ACCESS not-accessible
            STATUS current
            DESCRIPTION
                "
                The entries related to the MEG Ping include the parameters input
                by users and the returned results.
                "
            ::= { hwMplsTpOamLBObject 1 }


        hwMplsTpOamLBEntry OBJECT-TYPE
            SYNTAX HwMplsTpOamLBEntry
            MAX-ACCESS not-accessible
            STATUS current
            DESCRIPTION
                "
                The entry related to the MEG Ping.
                "
            INDEX { hwMplsTpOamMegId }
            ::= { hwMplsTpOamLBTable 1 }


        HwMplsTpOamLBEntry ::=
            SEQUENCE {
                hwMplsTpOamLBState
                    INTEGER,
                hwMplsTpOamLBTimeOut
                    Unsigned32,
                hwMplsTpOamLBCount
                    Unsigned32,
                hwMplsTpOamLBPacketSize
                    Integer32,
                hwMplsTpOamLBSendPacketNum
                    Counter32,
                hwMplsTpOamLBRecvPacketNum
                    Counter32,
                hwMplsTpOamLBPacketLossRatio
                    Unsigned32,
                hwMplsTpOamLBRecvTimeDelayMin
                    Unsigned32,
                hwMplsTpOamLBRecvTimeDelayMax
                    Unsigned32,
                hwMplsTpOamLBRecvTimeDelayAvg
                    Unsigned32,
                hwMplsTpOamLBDestNodeType
                    INTEGER,
                hwMplsTpOamLBTTL
                    Integer32,
                hwMplsTpOamLBNodeID
                    IpAddress,
                hwMplsTpOamLBIFNum
                    Unsigned32,
                hwMplsTpOamLBIsWithRequest
                    TruthValue,
                hwMplsTpOamLBDestMipId
                    Integer32
             }

        hwMplsTpOamLBState OBJECT-TYPE
            SYNTAX INTEGER
                {
                disable(1),
                enable(2)
                }
            MAX-ACCESS read-create
            STATUS current
            DESCRIPTION
                "
                This object indicates whether the LB function is enable.
               The value can be:
           1:disable
           2:enable
         By default, the value is disable.
         "
            DEFVAL { 1 }
            ::= { hwMplsTpOamLBEntry 1 }

        hwMplsTpOamLBTimeOut OBJECT-TYPE
            SYNTAX Unsigned32 (1..65535)
            MAX-ACCESS read-create
            STATUS current
            DESCRIPTION
                "
                This object indicates the timeout period for waiting for the LBR.
                The value ranges from 1 to 65535, in milliseconds.
                By default, the value is 2000.
                "
            DEFVAL { 2000 }
            ::= { hwMplsTpOamLBEntry 2 }


        hwMplsTpOamLBCount OBJECT-TYPE
            SYNTAX Unsigned32 (1..268435455)
            MAX-ACCESS read-create
            STATUS current
            DESCRIPTION
                "
                This object indicates the number of ping operation times.
                The value ranges from 1 to 268435455.
                By default, the value is 5.
                "
            DEFVAL { 5 }
            ::= { hwMplsTpOamLBEntry 3 }


        hwMplsTpOamLBPacketSize OBJECT-TYPE
            SYNTAX Integer32 (64..1500)
            MAX-ACCESS read-create
            STATUS current
            DESCRIPTION
                "
                This object indicates the size of an LBM packet.
                The value ranges from 64 to 1500 in bytes.
                "
            ::= { hwMplsTpOamLBEntry 4 }


        hwMplsTpOamLBSendPacketNum OBJECT-TYPE
            SYNTAX Counter32
            MAX-ACCESS read-only
            STATUS current
            DESCRIPTION
                "
                This object indicates the number of sent LBMs.
                "
            ::= { hwMplsTpOamLBEntry 5 }


        hwMplsTpOamLBRecvPacketNum OBJECT-TYPE
            SYNTAX Counter32
            MAX-ACCESS read-only
            STATUS current
            DESCRIPTION
                "
                This object indicates the number of received LBRs.
                "
            ::= { hwMplsTpOamLBEntry 6 }


        hwMplsTpOamLBPacketLossRatio OBJECT-TYPE
            SYNTAX Unsigned32 (0..100)
            MAX-ACCESS read-only
            STATUS current
            DESCRIPTION
                "
                This object indicates the frame loss ratio on the physical link.
                The value ranges from 0 to 100.
                "
            ::= { hwMplsTpOamLBEntry 7 }


        hwMplsTpOamLBRecvTimeDelayMin OBJECT-TYPE
            SYNTAX Unsigned32
            MAX-ACCESS read-only
            STATUS current
            DESCRIPTION
                "
                This object indicates the minimum delay in receiving the LBM.
                "
            ::= { hwMplsTpOamLBEntry 8 }


        hwMplsTpOamLBRecvTimeDelayMax OBJECT-TYPE
            SYNTAX Unsigned32
            MAX-ACCESS read-only
            STATUS current
            DESCRIPTION
                "
                This object indicates the maximum delay in receiving the LBM.
                "
            ::= { hwMplsTpOamLBEntry 9 }


        hwMplsTpOamLBRecvTimeDelayAvg OBJECT-TYPE
            SYNTAX Unsigned32
            MAX-ACCESS read-only
            STATUS current
            DESCRIPTION
                "
                This object indicates the average delay in receiving the LBM.
                "
            ::= { hwMplsTpOamLBEntry 10 }

        hwMplsTpOamLBDestNodeType OBJECT-TYPE
            SYNTAX INTEGER
                {
                mep(1),
                mip(2)
                }
            MAX-ACCESS read-create
            STATUS current
            DESCRIPTION
                "
                This object indicates LB node is MIP node or MEP node.
                "
            DEFVAL { 1 }
            ::= { hwMplsTpOamLBEntry 11 }


        hwMplsTpOamLBTTL OBJECT-TYPE
            SYNTAX Integer32 (0..255)
             MAX-ACCESS read-create
            STATUS current
            DESCRIPTION
                "
                This object indicates the TTL of LB.
                "
            ::= { hwMplsTpOamLBEntry 12 }


        hwMplsTpOamLBNodeID OBJECT-TYPE
            SYNTAX IpAddress
            MAX-ACCESS read-create
            STATUS current
            DESCRIPTION
                "
                This object indicates the Node-ID of LB.
                "
            ::= { hwMplsTpOamLBEntry 13 }


        hwMplsTpOamLBIFNum OBJECT-TYPE
            SYNTAX Unsigned32 (0..4294967295)
            MAX-ACCESS read-create
            STATUS current
            DESCRIPTION
                "
                This object indicates the IF-NUM of LB.
                "
            ::= { hwMplsTpOamLBEntry 14 }


        hwMplsTpOamLBIsWithRequest OBJECT-TYPE
            SYNTAX     TruthValue
            MAX-ACCESS read-create
            STATUS current
            DESCRIPTION
                "
                This object indicates whether  LB is with request-tlv or not.
                "
            ::= { hwMplsTpOamLBEntry 15 }

        hwMplsTpOamLBDestMipId OBJECT-TYPE
            SYNTAX Integer32 (0..8191)
            MAX-ACCESS read-create
            STATUS current
            DESCRIPTION
                "
                This object indicates the Node-ID of LB. The Node-ID is the mip id.
                "
            DEFVAL { 0 }
            ::= { hwMplsTpOamLBEntry 16 }

--
-- The Leaf Nodes of hwMplsTpOamObject
--
        hwMplsTpOamDualLossLossRatio OBJECT-TYPE
            SYNTAX Unsigned32
            MAX-ACCESS accessible-for-notify
            STATUS current
            DESCRIPTION
                "This object indicates the value of near loss ratio."
            ::= { hwMplsTpOamMib 4 }






        hwMplsTpOamTraps OBJECT IDENTIFIER ::= { hwMplsTpOamMib 5 }


--  ******************************************************************
-- NOTIFICATIONS (TRAPS)
-- These notifications will be sent to the management entity
-- whenever a MeP loses/restores contact with one or more other MePs.
-- ******************************************************************
        hwMplsTpOamLossOfConnection NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamMeLspName,
                hwMplsTpOamMeVsiName
                }
            STATUS current
            DESCRIPTION
                "
                This object is used to indicates the connectivity fault of the link.
                "
            ::= { hwMplsTpOamTraps 1 }

        hwMplsTpOamLossOfConnectionRecovery NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamMeLspName,
                hwMplsTpOamMeVsiName
                }
            STATUS current
            DESCRIPTION
                "
                This object indicates that the link recovers from a connectivity fault.
                "
            ::= { hwMplsTpOamTraps 2 }

        hwMplsTpOamRemoteDefectIndication NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamMeLspName,
                hwMplsTpOamMeVsiName
             }
            STATUS current
            DESCRIPTION
                "
                This object is used to indicates the remote defect of the link.
                "
            ::= { hwMplsTpOamTraps 3 }

        hwMplsTpOamRemoteDefectIndicationRecovery NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamMeLspName,
                hwMplsTpOamMeVsiName
            }
            STATUS current
            DESCRIPTION
                "
                This object indicates that the link recovers from a remote defect.
                "
            ::= { hwMplsTpOamTraps 4 }

        hwMplsTpOamUnExpectMeg NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamMeLspName,
                hwMplsTpOamMeVsiName
            }
            STATUS current
            DESCRIPTION
                "
                This object indicates the link receivs an unexpect MEG-ID defect.
                "
            ::= { hwMplsTpOamTraps 5 }

        hwMplsTpOamUnExpectMegRecovery NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId ,
                hwMplsTpOamMeLspName,
                hwMplsTpOamMeVsiName
            }
            STATUS current
            DESCRIPTION
                "
                This object indicates that the link recovers from an unexpect MEG-ID defect.
                "
            ::= { hwMplsTpOamTraps 6 }

        hwMplsTpOamUnExpectMep NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamMeLspName,
                hwMplsTpOamMeVsiName
            }
            STATUS current
            DESCRIPTION
                "
                This object indicates the link receivs an unexpect MEP-ID defect.
                "
            ::= { hwMplsTpOamTraps 7 }

        hwMplsTpOamUnExpectMepRecovery NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamMeLspName,
                hwMplsTpOamMeVsiName
        }
            STATUS current
            DESCRIPTION
                "
                This object indicates that the link recovers from an unexpect MEP-ID defect.
                "
            ::= { hwMplsTpOamTraps 8 }

        hwMplsTpOamUnExpectPeriod NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamMeLspName,
                hwMplsTpOamMeVsiName
            }
            STATUS current
            DESCRIPTION
                "
                This object indicates the link receivs an unexpect period defect.
                "
            ::= { hwMplsTpOamTraps 9 }

        hwMplsTpOamUnExpectPeriodRecovery NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamMeLspName,
                hwMplsTpOamMeVsiName
            }
            STATUS current
            DESCRIPTION
                "
                This object indicates that the link recovers from an unexpect period defect.
                "
            ::= { hwMplsTpOamTraps 10 }

        hwMplsTpOamUnExpectPhb NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamMeLspName,
                hwMplsTpOamMeVsiName
            }
            STATUS current
            DESCRIPTION
                "
                This object indicates the link receivs an unexpect PHB defect.
                "
            ::= { hwMplsTpOamTraps 11 }

        hwMplsTpOamUnExpectPhbRecovery NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamMeLspName,
                hwMplsTpOamMeVsiName
            }
            STATUS current
            DESCRIPTION
                "
                This object indicates that the link recovers from an unexpect PHB defect.
                "
            ::= { hwMplsTpOamTraps 12 }

        hwMplsTpOamAlarmIndicationSignal NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamMeLspName,
                hwMplsTpOamMeVsiName
            }
            STATUS current
            DESCRIPTION
                "
                This object indicates the link receivs an alarm indication signal defect.
                "
            ::= { hwMplsTpOamTraps 13 }

        hwMplsTpOamAlarmIndicationSignalRecovery NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamMeLspName,
                hwMplsTpOamMeVsiName
            }
            STATUS current
            DESCRIPTION
                "
                This object indicates that the link recovers from an alarm indication signal defect.
                "
            ::= { hwMplsTpOamTraps 14 }

        hwMplsTpOamNearDualLossSD1 NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamDualLossLossRatio,
                hwMplsTpOamDualLossSD1Threshold,
                hwMplsTpOamMeLspName,
                hwMplsTpOamMeVsiName
            }
            STATUS current
            DESCRIPTION
                "
                This object indicates the link receivs a packet lost exceed
                signal degrade threshold defect.
                "
            ::= { hwMplsTpOamTraps 15 }

        hwMplsTpOamNearDualLossSD1Recovery NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamDualLossLossRatio,
                hwMplsTpOamDualLossSD1Threshold,
                hwMplsTpOamMeLspName,
                hwMplsTpOamMeVsiName
            }
            STATUS current
            DESCRIPTION
                "
                This object indicates that the link recovers from a packet
                lost exceed signal degrade threshold defect.
                "
            ::= { hwMplsTpOamTraps 16 }

        hwMplsTpOamFarDualLossSD1 NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamDualLossLossRatio,
                hwMplsTpOamDualLossSD1Threshold,
                hwMplsTpOamMeLspName,
                hwMplsTpOamMeVsiName
            }
            STATUS current
            DESCRIPTION
                "
                This object indicates the link receivs a packet lost exceed signal
                degrade threshold defect from the remote link.
                "
            ::= { hwMplsTpOamTraps 17 }

        hwMplsTpOamFarDualLossSD1Recovery NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamDualLossLossRatio,
                hwMplsTpOamDualLossSD1Threshold,
                hwMplsTpOamMeLspName,
                hwMplsTpOamMeVsiName
            }
            STATUS current
            DESCRIPTION
                "
                This object indicates that the link recovers from a packet lost
                exceed signal degrade threshold defect from the remote link.
                "
            ::= { hwMplsTpOamTraps 18 }

        hwMplsTpOamNearDualLossSD2 NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamDualLossLossRatio,
                hwMplsTpOamDualLossSD2Threshold,
                hwMplsTpOamMeLspName,
                hwMplsTpOamMeVsiName
            }
            STATUS current
            DESCRIPTION
                "
                This object indicates the link receivs a packet lost
                exceed signal degrade threshold defect.
                "
            ::= { hwMplsTpOamTraps 19 }

        hwMplsTpOamNearDualLossSD2Recovery NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamDualLossLossRatio,
                hwMplsTpOamDualLossSD2Threshold,
                hwMplsTpOamMeLspName,
                hwMplsTpOamMeVsiName
            }
            STATUS current
            DESCRIPTION
                "
                This object indicates that the link recovers from a packet
                lost exceed signal degrade threshold.
                "
            ::= { hwMplsTpOamTraps 20 }

        hwMplsTpOamFarDualLossSD2 NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamDualLossLossRatio,
                hwMplsTpOamDualLossSD2Threshold,
                hwMplsTpOamMeLspName,
                hwMplsTpOamMeVsiName
            }
            STATUS current
            DESCRIPTION
                "
                This object indicates the link receivs a packet lost exceed
                signal degrade threshold defect from the remote link.
                "
            ::= { hwMplsTpOamTraps 21 }

        hwMplsTpOamFarDualLossSD2Recovery NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamDualLossLossRatio,
                hwMplsTpOamDualLossSD2Threshold,
                hwMplsTpOamMeLspName,
                hwMplsTpOamMeVsiName
            }
            STATUS current
            DESCRIPTION
                "
                This object indicates that the link recovers from a packet lost
                exceed signal degrade threshold defect from the remote link.
                "
            ::= { hwMplsTpOamTraps 22 }

        hwMplsTpOamLCK NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamMeLspName,
                hwMplsTpOamMeVsiName
            }
            STATUS current
            DESCRIPTION
                "
                This object indicates that the client level detected lock signal from the service level.
                "
            ::= { hwMplsTpOamTraps 23 }

        hwMplsTpOamLCKRecovery NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamMeLspName,
                hwMplsTpOamMeVsiName
            }
            STATUS current
            DESCRIPTION
                "
                This object indicates that the client level can not detect lock signal from the service level.
                "
            ::= { hwMplsTpOamTraps 24 }

        hwMplsTpOamCSF NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamMeLspName,
                hwMplsTpOamMeVsiName
            }
            STATUS current
            DESCRIPTION
                "
                This object is used to indicates client failed signal degrade in the AC.
                "
            ::= { hwMplsTpOamTraps 25 }

        hwMplsTpOamCSFRecovery NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamMeLspName,
                hwMplsTpOamMeVsiName
            }
            STATUS current
            DESCRIPTION
                "
                This object indicates that the link recovers from a client failed signal in the AC.
                "
            ::= { hwMplsTpOamTraps 26 }

        hwMplsTpOamUnExpectMegLevel NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamMeLspName,
                hwMplsTpOamMeVsiName
            }
            STATUS current
            DESCRIPTION
                "
                This object is used to indicates receiving an unexpect MEG-LEVEL defect of the link.
                "
            ::= { hwMplsTpOamTraps 27 }

        hwMplsTpOamUnExpectMegLevelRecovery NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamMeLspName,
                hwMplsTpOamMeVsiName
            }
            STATUS current
            DESCRIPTION
                "
                This object indicates that the link recovers from an unexpect MEG-LEVEL defect.
                "
            ::= { hwMplsTpOamTraps 28 }

        hwMplsTpOamSectionLossOfConnection NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId
            }
            STATUS current
            DESCRIPTION
                "
                This object is used to indicates the connectivity fault of the link.
                "
            ::= { hwMplsTpOamTraps 29 }

        hwMplsTpOamSectionLossOfConnectionRecovery NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId
                }
            STATUS current
            DESCRIPTION
                "
                This object indicates that the link recovers from a connectivity fault.
                "
            ::= { hwMplsTpOamTraps 30 }

        hwMplsTpOamSectionRemoteDefectIndication NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId
             }
            STATUS current
            DESCRIPTION
                "
                This object is used to indicates the remote defect of the link.
                "
            ::= { hwMplsTpOamTraps 31 }

        hwMplsTpOamSectionRemoteDefectIndicationRecovery NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId
            }
            STATUS current
            DESCRIPTION
                "
                This object indicates that the link recovers from a remote defect.
                "
            ::= { hwMplsTpOamTraps 32 }

        hwMplsTpOamSectionUnExpectMeg NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId
            }
            STATUS current
            DESCRIPTION
                "
                This object is used to indicates receiving an unexpect MEG-ID defect of the link.
                "
            ::= { hwMplsTpOamTraps 33 }

        hwMplsTpOamSectionUnExpectMegRecovery NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId
            }
            STATUS current
            DESCRIPTION
                "
                This object indicates that the link recovers from an unexpect MEG-ID defect.
                "
            ::= { hwMplsTpOamTraps 34 }

        hwMplsTpOamSectionUnExpectMep NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId
            }
            STATUS current
            DESCRIPTION
                "
                This object is used to indicates receiving an unexpect MEP-ID defect of the link.
                "
            ::= { hwMplsTpOamTraps 35 }

        hwMplsTpOamSectionUnExpectMepRecovery NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId
        }
            STATUS current
            DESCRIPTION
                "
                This object indicates that the link recovers from an unexpect MEP-ID defect.
                "
            ::= { hwMplsTpOamTraps 36 }

        hwMplsTpOamSectionUnExpectPeriod NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId
            }
            STATUS current
            DESCRIPTION
                "
                This object is used to indicates receiving an unexpect period defect of the link.
                "
            ::= { hwMplsTpOamTraps 37 }

        hwMplsTpOamSectionUnExpectPeriodRecovery NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId
            }
            STATUS current
            DESCRIPTION
                "
                This object indicates that the link recovers from an unexpect period defect.
                "
            ::= { hwMplsTpOamTraps 38 }

        hwMplsTpOamSectionUnExpectPhb NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId
            }
            STATUS current
            DESCRIPTION
                "
                This object is used to indicates receiving an unexpect PHB defect of the link.
                "
            ::= { hwMplsTpOamTraps 39 }

        hwMplsTpOamSectionUnExpectPhbRecovery NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId
            }
            STATUS current
            DESCRIPTION
                "
                This object indicates that the link recovers from an unexpect PHB defect.
                "
            ::= { hwMplsTpOamTraps 40 }

        hwMplsTpOamSectionNearDualLossSD1 NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId,
                hwMplsTpOamDualLossLossRatio,
                hwMplsTpOamDualLossSD1Threshold
            }
            STATUS current
            DESCRIPTION
                "
                This object is used to indicates packet lost exceed signal degrade threshold in the local link.
                "
            ::= { hwMplsTpOamTraps 41 }

        hwMplsTpOamSectionNearDualLossSD1Recovery NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId,
                hwMplsTpOamDualLossLossRatio,
                hwMplsTpOamDualLossSD1Threshold
            }
            STATUS current
            DESCRIPTION
                "
                This object indicates that the link recovers from a packet lost exceed signal degrade threshold.
                "
            ::= { hwMplsTpOamTraps 42 }

        hwMplsTpOamSectionFarDualLossSD1 NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId,
                hwMplsTpOamDualLossLossRatio,
                hwMplsTpOamDualLossSD1Threshold
            }
            STATUS current
            DESCRIPTION
                "
                This object is used to indicates packet lost exceed signal
                degrade threshold in the remote link.
                "
            ::= { hwMplsTpOamTraps 43 }

        hwMplsTpOamSectionFarDualLossSD1Recovery NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId,
                hwMplsTpOamDualLossLossRatio,
                hwMplsTpOamDualLossSD1Threshold
            }
            STATUS current
            DESCRIPTION
                "
                This object indicates that the link recovers from a packet lost
                exceed signal degrade threshold in the remote link.
                "
            ::= { hwMplsTpOamTraps 44 }

        hwMplsTpOamSectionNearDualLossSD2 NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId,
                hwMplsTpOamDualLossLossRatio,
                hwMplsTpOamDualLossSD2Threshold
            }
            STATUS current
            DESCRIPTION
                "
                This object is used to indicates packet lost exceed signal
                degrade threshold in the local link.
                "
            ::= { hwMplsTpOamTraps 45 }

        hwMplsTpOamSectionNearDualLossSD2Recovery NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId,
                hwMplsTpOamDualLossLossRatio,
                hwMplsTpOamDualLossSD2Threshold
            }
            STATUS current
            DESCRIPTION
                "
                This object indicates that the link recovers from a packet
                lost exceed signal degrade threshold.
                "
            ::= { hwMplsTpOamTraps 46 }

        hwMplsTpOamSectionFarDualLossSD2 NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId,
                hwMplsTpOamDualLossLossRatio,
                hwMplsTpOamDualLossSD2Threshold
            }
            STATUS current
            DESCRIPTION
                "
                This object is used to indicates packet lost exceed signal
                degrade threshold in the remote link.
                "
            ::= { hwMplsTpOamTraps 47 }

        hwMplsTpOamSectionFarDualLossSD2Recovery NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId,
                hwMplsTpOamDualLossLossRatio,
                hwMplsTpOamDualLossSD2Threshold
            }
            STATUS current
            DESCRIPTION
                "
                This object indicates that the link recovers from a packet lost
                exceed signal degrade threshold in the remote link.
                "
            ::= { hwMplsTpOamTraps 48}

        hwMplsTpOamSectionLCK NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId
            }
            STATUS current
            DESCRIPTION
                "
                This object indicates that the link detected lock signal from the service level.
                "
            ::= { hwMplsTpOamTraps 49 }

        hwMplsTpOamSectionLCKRecovery NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId
            }
            STATUS current
            DESCRIPTION
                "
                This object indicates that the link can not detect lock signal from the service level.
                "
            ::= { hwMplsTpOamTraps 50 }

        hwMplsTpOamSectionUnExpectMegLevel NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId
            }
            STATUS current
            DESCRIPTION
                "
                This object is used to indicates receiving an unexpect MEG-LEVEL defect of the link.
                "
            ::= { hwMplsTpOamTraps 51 }

        hwMplsTpOamSectionUnExpectMegLevelRecovery NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId
            }
            STATUS current
            DESCRIPTION
                "
                This object indicates that the link recovers from an unexpect MEG-LEVEL defect.
                "
            ::= { hwMplsTpOamTraps 52 }

        hwMplsTpOamSectionLocalLock NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId
            }
            STATUS current
            DESCRIPTION
                "
                This object indicates that the link has been locked by user.
                "
            ::= { hwMplsTpOamTraps 53 }

        hwMplsTpOamSectionLocalLockRecovery NOTIFICATION-TYPE
            OBJECTS {
                hwMplsTpOamMegId,
                hwMplsTpOamMeType,
                hwMplsTpOamMeDirection,
                hwMplsTpOamMeIfName,
                hwMplsTpOamMePeerip,
                hwMplsTpOamMeMepId,
                hwMplsTpOamMeRemoteMepId
            }
            STATUS current
            DESCRIPTION
                "
                This object indicates that the user cancelled lock signal of the link.
                "
            ::= { hwMplsTpOamTraps 54 }

        hwMplsTpOamLocalLock NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamMeLspName,
                hwMplsTpOamMeVsiName
            }
            STATUS current
            DESCRIPTION
                "
                This object indicates that the service has been locked by user.
                "
            ::= { hwMplsTpOamTraps 55 }

        hwMplsTpOamLocalLockRecovery NOTIFICATION-TYPE
            OBJECTS {
                hwMplsTpOamMegId,
                hwMplsTpOamMeType,
                hwMplsTpOamMeDirection,
                hwMplsTpOamMeIfName,
                hwMplsTpOamMePeerip,
                hwMplsTpOamMeVcId,
                hwMplsTpOamMeVcType,
                hwMplsTpOamMeVllRemotePeerIp,
                hwMplsTpOamMEVllTTL,
                hwMplsTpOamMeMepId,
                hwMplsTpOamMeRemoteMepId,
                hwMplsTpOamMeLspName,
                hwMplsTpOamMeVsiName
            }
            STATUS current
            DESCRIPTION
                "
                This object indicates that the user cancelled lock signal of the service.
                "
            ::= { hwMplsTpOamTraps 56 }

	hwMplsTpOamIpMegPingTrap NOTIFICATION-TYPE
            OBJECTS {
                hwMplsTpOamMegId,
                hwMplsTpOamMeIndex,
                hwMplsTpOamMeMepId,
                hwMplsTpOamIpMegPingNum,
                hwMplsTpOamIpMegPingSeqNum,
                hwMplsTpOamIpMegPingMepId,
                hwMplsTpOamIpMegPingLsrId,
                hwMplsTpOamIpMegPingTtl,
                hwMplsTpOamIpMegPingServiceType,
                hwMplsTpOamIpMegPingIfIndex,
                hwMplsTpOamIpMegPingVpnName
            }
            STATUS current
            DESCRIPTION
            	"
            	This object indicates that the ip-meg ping info.
            	"
            ::= { hwMplsTpOamTraps 57 }

	hwMplsTpOamIpMegTracertTrap NOTIFICATION-TYPE
            OBJECTS {
                hwMplsTpOamMegId,
                hwMplsTpOamMeIndex,
                hwMplsTpOamMeMepId,
                hwMplsTpOamIpMegTracertSeqNum,
                hwMplsTpOamIpMegTracertMepId,
                hwMplsTpOamIpMegTracertLsrId,
                hwMplsTpOamIpMegTracertTtl,
                hwMplsTpOamIpMegTracertServiceType,
                hwMplsTpOamIpMegTracertIfIndex,
                hwMplsTpOamIpMegTracertVpnName
            }
            STATUS current
            DESCRIPTION
            	"
            	This object indicates that the ip-meg tracert info.
  		"
		::= { hwMplsTpOamTraps 58 }

        hwMplsTpOamStatistic OBJECT IDENTIFIER ::= { hwMplsTpOamMib 6 }
        hwMplsTpOamStatisticObject OBJECT IDENTIFIER ::= { hwMplsTpOamStatistic 1 }
        hwMplsTpOamSingleLossStatisticTable OBJECT-TYPE
            SYNTAX      SEQUENCE OF HwMplsTpOamSingleLossStatisticEntry
            MAX-ACCESS  not-accessible
            STATUS current
            DESCRIPTION
              "
              This table contains statistics for the OAM function on a
                particular MPLS-TP environment.
              "
            ::= { hwMplsTpOamStatisticObject 1 }
        hwMplsTpOamSingleLossStatisticEntry OBJECT-TYPE
            SYNTAX      HwMplsTpOamSingleLossStatisticEntry
            MAX-ACCESS  not-accessible
            STATUS current
            DESCRIPTION
              "
              An entry in the table, containing statistics information on
                the MPLS-TP OAM function for the ME in MPLS-TP environment.
              "
            INDEX       { hwMplsTpOamMegId }
            ::= { hwMplsTpOamSingleLossStatisticTable 1 }

         HwMplsTpOamSingleLossStatisticEntry ::=
            SEQUENCE {
              hwMplsTpOamSingleLossStatisticLocal
                 OCTET STRING,
              hwMplsTpOamSingleLossStatisticLocalRate
                 OCTET STRING,
              hwMplsTpOamSingleLossStatisticRemote
                 OCTET STRING,
              hwMplsTpOamSingleLossStatisticRemoteRate
                 OCTET STRING,
              hwMplsTpOamSingleLossStatisticLocalMin
                 Unsigned32,
              hwMplsTpOamSingleLossStatisticLocalMax
                 Unsigned32,
              hwMplsTpOamSingleLossStatisticLocalAverage
                 Unsigned32,
              hwMplsTpOamSingleLossStatisticLocallRateMin
                 Integer32,
              hwMplsTpOamSingleLossStatisticLocallRateMax
                 Integer32,
              hwMplsTpOamSingleLossStatisticLocallRateAverage
                 Integer32,
              hwMplsTpOamSingleLossStatisticRemoteMin
                 Unsigned32,
              hwMplsTpOamSingleLossStatisticRemoteMax
                 Unsigned32,
              hwMplsTpOamSingleLossStatisticRemoteAverage
                 Unsigned32,
              hwMplsTpOamSingleLossStatisticRemoteRateMin
                 Integer32,
              hwMplsTpOamSingleLossStatisticRemoteRateMax
                 Integer32,
              hwMplsTpOamSingleLossStatisticRemoteRateAverage
                 Integer32
            }


         hwMplsTpOamSingleLossStatisticLocal OBJECT-TYPE
            SYNTAX OCTET STRING (SIZE(0..1024))
            MAX-ACCESS read-only
            STATUS current
            DESCRIPTION
                "
                Indicates the packet loss statistics that are collected on a local end.
                "
            ::= { hwMplsTpOamSingleLossStatisticEntry 1 }

         hwMplsTpOamSingleLossStatisticLocalRate OBJECT-TYPE
            SYNTAX OCTET STRING (SIZE(0..1024))
            MAX-ACCESS read-only
            STATUS current
            DESCRIPTION
                "
                Indicates the packet loss rate statistics that are collected on a local end.
                "
            ::= { hwMplsTpOamSingleLossStatisticEntry 2 }

         hwMplsTpOamSingleLossStatisticRemote OBJECT-TYPE
            SYNTAX OCTET STRING (SIZE(0..1024))
            MAX-ACCESS read-only
            STATUS current
            DESCRIPTION
                "
                Indicates the packet loss statistics that are collected on a remote end.
                "
            ::= { hwMplsTpOamSingleLossStatisticEntry 3 }

         hwMplsTpOamSingleLossStatisticRemoteRate OBJECT-TYPE
            SYNTAX OCTET STRING (SIZE(0..1024))
            MAX-ACCESS read-only
            STATUS current
            DESCRIPTION
                "
                Indicates the packet loss rate statistics that are collected on a remote end.
                "
            ::= { hwMplsTpOamSingleLossStatisticEntry 4 }

    hwMplsTpOamSingleLossStatisticLocalMin OBJECT-TYPE
        SYNTAX Unsigned32
            MAX-ACCESS read-only
            STATUS current
            DESCRIPTION
                "
                Indicates the minimal packet loss rate statistics that are collected on a local end.
                "
            ::= { hwMplsTpOamSingleLossStatisticEntry 5 }

    hwMplsTpOamSingleLossStatisticLocalMax OBJECT-TYPE
        SYNTAX Unsigned32
            MAX-ACCESS read-only
            STATUS current
            DESCRIPTION
                "
                Indicates the maximal packet loss rate statistics that are collected on a local end.
                "
            ::= { hwMplsTpOamSingleLossStatisticEntry 6 }

    hwMplsTpOamSingleLossStatisticLocalAverage OBJECT-TYPE
        SYNTAX Unsigned32
            MAX-ACCESS read-only
            STATUS current
            DESCRIPTION
                "
                Indicates the average packet loss statistics that are collected on a local end.
                "
            ::= { hwMplsTpOamSingleLossStatisticEntry 7 }

    hwMplsTpOamSingleLossStatisticLocallRateMin OBJECT-TYPE
        SYNTAX Integer32(0..10000)
            MAX-ACCESS read-only
            STATUS current
            DESCRIPTION
                "
                Indicates the minimal packet loss rate statistics that are collected on a local end.
                "
            ::= { hwMplsTpOamSingleLossStatisticEntry 8 }

    hwMplsTpOamSingleLossStatisticLocallRateMax OBJECT-TYPE
        SYNTAX Integer32(0..10000)
            MAX-ACCESS read-only
            STATUS current
            DESCRIPTION
                "
                Indicates the maximal packet loss rate statistics that are collected on a local end.
                "
            ::= { hwMplsTpOamSingleLossStatisticEntry 9 }

    hwMplsTpOamSingleLossStatisticLocallRateAverage OBJECT-TYPE
        SYNTAX Integer32(0..10000)
            MAX-ACCESS read-only
            STATUS current
            DESCRIPTION
                "
                Indicates the average packet loss rate statistics that are collected on a local end.
                "
            ::= { hwMplsTpOamSingleLossStatisticEntry 10 }

    hwMplsTpOamSingleLossStatisticRemoteMin OBJECT-TYPE
        SYNTAX Unsigned32
            MAX-ACCESS read-only
            STATUS current
            DESCRIPTION
                "
                Indicates the minimal packet loss statistics that are collected on a remote end.
                "
            ::= { hwMplsTpOamSingleLossStatisticEntry 11 }

    hwMplsTpOamSingleLossStatisticRemoteMax OBJECT-TYPE
        SYNTAX Unsigned32
            MAX-ACCESS read-only
            STATUS current
            DESCRIPTION
                "
                Indicates the maximal packet loss statistics that are collected on a remote end.
                "
            ::= { hwMplsTpOamSingleLossStatisticEntry 12 }

    hwMplsTpOamSingleLossStatisticRemoteAverage OBJECT-TYPE
        SYNTAX Unsigned32
            MAX-ACCESS read-only
            STATUS current
            DESCRIPTION
                "
                Indicates the average packet loss statistics that are collected on a remote end.
                "
            ::= { hwMplsTpOamSingleLossStatisticEntry 13 }

    hwMplsTpOamSingleLossStatisticRemoteRateMin OBJECT-TYPE
        SYNTAX Integer32(0..10000)
            MAX-ACCESS read-only
            STATUS current
            DESCRIPTION
                "
                Indicates the minimal packet loss rate statistics that are collected on a remote end.
                "
            ::= { hwMplsTpOamSingleLossStatisticEntry 14 }

    hwMplsTpOamSingleLossStatisticRemoteRateMax OBJECT-TYPE
        SYNTAX Integer32(0..10000)
            MAX-ACCESS read-only
            STATUS current
            DESCRIPTION
                "
                Indicates the maximal packet loss rate statistics that are collected on a remote end.
                "
            ::= { hwMplsTpOamSingleLossStatisticEntry 15 }

    hwMplsTpOamSingleLossStatisticRemoteRateAverage OBJECT-TYPE
        SYNTAX Integer32(0..10000)
            MAX-ACCESS read-only
            STATUS current
            DESCRIPTION
                "
                Indicates the average packet loss rate statistics that are collected on a remote end.
                "
            ::= { hwMplsTpOamSingleLossStatisticEntry 16 }



        hwMplsTpOamDelayMeasureStatisticOneWayTable OBJECT-TYPE
            SYNTAX SEQUENCE OF HwMplsTpOamDelayMeasureStatisticOneWayEntry
            MAX-ACCESS  not-accessible
            STATUS current
            DESCRIPTION
              "
              This table contains information about the MPLS-TP OAM
               one-way delay statistic for MEG.
              "
            ::= { hwMplsTpOamStatisticObject 2 }
        hwMplsTpOamDelayMeasureStatisticOneWayEntry OBJECT-TYPE
            SYNTAX      HwMplsTpOamDelayMeasureStatisticOneWayEntry
            MAX-ACCESS  not-accessible
            STATUS current
            DESCRIPTION
              "
              An entry in the table, containing information on the OAM
              one-way delay statistic entity for MEG.
              "
            INDEX       { hwMplsTpOamMegId }
            ::= { hwMplsTpOamDelayMeasureStatisticOneWayTable 1 }

        HwMplsTpOamDelayMeasureStatisticOneWayEntry ::=
            SEQUENCE {
              hwMplsTpOamDelayMeasureStatisticOneWayAndVar
                OCTET STRING,
              hwMplsTpOamDelayMeasureStatisticOneWayDelayMin
                Unsigned32,
              hwMplsTpOamDelayMeasureStatisticOneWayDelayMax
                Unsigned32,
              hwMplsTpOamDelayMeasureStatisticOneWayDelayAverage
                Unsigned32,
              hwMplsTpOamDelayMeasureStatisticOneWayVariationMin
                Unsigned32,
              hwMplsTpOamDelayMeasureStatisticOneWayVariationMax
                Unsigned32,
              hwMplsTpOamDelayMeasureStatisticOneWayVariationAverage
                Unsigned32
            }


        hwMplsTpOamDelayMeasureStatisticOneWayAndVar OBJECT-TYPE
            SYNTAX OCTET STRING (SIZE (0..1024))
            MAX-ACCESS  read-only
            STATUS current
            DESCRIPTION
              "
              This object indicates the statistics about the one-way delay in the MEG.
              "
            ::= { hwMplsTpOamDelayMeasureStatisticOneWayEntry 1 }

        hwMplsTpOamDelayMeasureStatisticOneWayDelayMin OBJECT-TYPE
            SYNTAX Unsigned32
            MAX-ACCESS  read-only
            STATUS current
            DESCRIPTION
              "
              This object indicates the minimal delay statistics about the one-way delay in the MEG.
              "
            ::= { hwMplsTpOamDelayMeasureStatisticOneWayEntry 2 }

        hwMplsTpOamDelayMeasureStatisticOneWayDelayMax OBJECT-TYPE
            SYNTAX Unsigned32
            MAX-ACCESS  read-only
            STATUS current
            DESCRIPTION
              "
              This object indicates the maximal delay statistics about the one-way delay in the MEG.
              "
            ::= { hwMplsTpOamDelayMeasureStatisticOneWayEntry 3 }

        hwMplsTpOamDelayMeasureStatisticOneWayDelayAverage OBJECT-TYPE
            SYNTAX Unsigned32
            MAX-ACCESS  read-only
            STATUS current
            DESCRIPTION
              "
              This object indicates the average delay statistics about the one-way delay in the MEG.
              "
            ::= { hwMplsTpOamDelayMeasureStatisticOneWayEntry 4 }

        hwMplsTpOamDelayMeasureStatisticOneWayVariationMin OBJECT-TYPE
            SYNTAX Unsigned32
            MAX-ACCESS  read-only
            STATUS current
            DESCRIPTION
              "
              This object indicates the minimal delay variation statistics about the one-way delay in the MEG.
              "
            ::= { hwMplsTpOamDelayMeasureStatisticOneWayEntry 5 }

        hwMplsTpOamDelayMeasureStatisticOneWayVariationMax OBJECT-TYPE
            SYNTAX Unsigned32
            MAX-ACCESS  read-only
            STATUS current
            DESCRIPTION
              "
              This object indicates the maximal delay variation statistics about the one-way delay in the MEG.
              "
            ::= { hwMplsTpOamDelayMeasureStatisticOneWayEntry 6 }

        hwMplsTpOamDelayMeasureStatisticOneWayVariationAverage OBJECT-TYPE
            SYNTAX Unsigned32
            MAX-ACCESS  read-only
            STATUS current
            DESCRIPTION
              "
              This object indicates the average delay variation statistics about the one-way delay in the MEG.
              "
            ::= { hwMplsTpOamDelayMeasureStatisticOneWayEntry 7 }


        hwMplsTpOamDelayMeasureStatisticTwoWayTable OBJECT-TYPE
            SYNTAX SEQUENCE OF HwMplsTpOamDelayMeasureStatisticTwoWayEntry
            MAX-ACCESS  not-accessible
            STATUS current
            DESCRIPTION
              "
              This table contains information about the MPLS-TP OAM
               two-way delay statistic for MEG.
              "
            ::= { hwMplsTpOamStatisticObject 3 }
        hwMplsTpOamDelayMeasureStatisticTwoWayEntry OBJECT-TYPE
            SYNTAX      HwMplsTpOamDelayMeasureStatisticTwoWayEntry
            MAX-ACCESS  not-accessible
            STATUS current
            DESCRIPTION
              "
              An entry in the table, containing information on the OAM
              two-way delay statistic entity for MEG.
              "
            INDEX   { hwMplsTpOamMegId }
            ::= { hwMplsTpOamDelayMeasureStatisticTwoWayTable 1 }

        HwMplsTpOamDelayMeasureStatisticTwoWayEntry ::=
            SEQUENCE {
              hwMplsTpOamDelayMeasureStatisticTwoWayAndVar
                 OCTET STRING,
              hwMplsTpOamDelayMeasureStatisticTwoWayDelayMin
                Unsigned32,
              hwMplsTpOamDelayMeasureStatisticTwoWayDelayMax
                Unsigned32,
              hwMplsTpOamDelayMeasureStatisticTwoWayDelayAverage
                Unsigned32,
              hwMplsTpOamDelayMeasureStatisticTwoWayVariationMin
                Unsigned32,
              hwMplsTpOamDelayMeasureStatisticTwoWayVariationMax
                Unsigned32,
              hwMplsTpOamDelayMeasureStatisticTwoWayVariationAverage
                Unsigned32

            }

        hwMplsTpOamDelayMeasureStatisticTwoWayAndVar OBJECT-TYPE
            SYNTAX OCTET STRING (SIZE (0..1024))
            MAX-ACCESS  read-only
            STATUS current
            DESCRIPTION
              "
              This object indicates the statistics about the two-way delay in the MEG.
              "
            ::= { hwMplsTpOamDelayMeasureStatisticTwoWayEntry 1 }

        hwMplsTpOamDelayMeasureStatisticTwoWayDelayMin OBJECT-TYPE
            SYNTAX Unsigned32
            MAX-ACCESS  read-only
            STATUS current
            DESCRIPTION
              "
              This object indicates the minimal delay statistics about the two-way delay in the MEG.
              "
            ::= { hwMplsTpOamDelayMeasureStatisticTwoWayEntry 2 }

        hwMplsTpOamDelayMeasureStatisticTwoWayDelayMax OBJECT-TYPE
            SYNTAX Unsigned32
            MAX-ACCESS  read-only
            STATUS current
            DESCRIPTION
              "
              This object indicates the maximal delay statistics about the two-way delay in the MEG.
              "
            ::= { hwMplsTpOamDelayMeasureStatisticTwoWayEntry 3 }

        hwMplsTpOamDelayMeasureStatisticTwoWayDelayAverage OBJECT-TYPE
            SYNTAX Unsigned32
            MAX-ACCESS  read-only
            STATUS current
            DESCRIPTION
              "
              This object indicates the average delay statistics about the two-way delay in the MEG.
              "
            ::= { hwMplsTpOamDelayMeasureStatisticTwoWayEntry 4 }

        hwMplsTpOamDelayMeasureStatisticTwoWayVariationMin OBJECT-TYPE
            SYNTAX Unsigned32
            MAX-ACCESS  read-only
            STATUS current
            DESCRIPTION
              "
              This object indicates the minimal delay variation statistics about the two-way delay in the MEG.
              "
            ::= { hwMplsTpOamDelayMeasureStatisticTwoWayEntry 5 }

        hwMplsTpOamDelayMeasureStatisticTwoWayVariationMax OBJECT-TYPE
            SYNTAX Unsigned32
            MAX-ACCESS  read-only
            STATUS current
            DESCRIPTION
              "
              This object indicates the maximal delay variation statistics about the two-way delay in the MEG.
              "
            ::= { hwMplsTpOamDelayMeasureStatisticTwoWayEntry 6 }

        hwMplsTpOamDelayMeasureStatisticTwoWayVariationAverage OBJECT-TYPE
            SYNTAX Unsigned32
            MAX-ACCESS  read-only
            STATUS current
            DESCRIPTION
              "
              This object indicates the average delay variation statistics about the two-way delay in the MEG.
              "
            ::= { hwMplsTpOamDelayMeasureStatisticTwoWayEntry 7 }

        hwMplsTpOamMeasureStatisticTestTable OBJECT-TYPE
            SYNTAX SEQUENCE OF HwMplsTpOamMeasureStatisticTestEntry
            MAX-ACCESS  not-accessible
            STATUS current
            DESCRIPTION
              "
              This table contains information about the MPLS-TP OAM
               test statistic for MEG.
              "
            ::= { hwMplsTpOamStatisticObject 4 }

        hwMplsTpOamMeasureStatisticTestEntry OBJECT-TYPE
            SYNTAX      HwMplsTpOamMeasureStatisticTestEntry
            MAX-ACCESS  not-accessible
            STATUS current
            DESCRIPTION
              "
              An entry in the table, containing information on the OAM
              test statistic entity for MEG.
              "
            INDEX       { hwMplsTpOamMegId }
            ::= { hwMplsTpOamMeasureStatisticTestTable 1 }

        HwMplsTpOamMeasureStatisticTestEntry ::=
            SEQUENCE {
              hwMplsTpOamMeasureStatisticTestPacketNum
                Unsigned32
            }

        hwMplsTpOamMeasureStatisticTestPacketNum OBJECT-TYPE
            SYNTAX Unsigned32
            MAX-ACCESS  read-only
            STATUS current
            DESCRIPTION
              "
              This object indicates the number about sending/received packet in the MEG.
              edge of sending: send number
              edge of receiving: received number
              "
            ::= { hwMplsTpOamMeasureStatisticTestEntry 1 }

        hwMplsTpOamInterfaceAis OBJECT IDENTIFIER ::= { hwMplsTpOamMib 7 }
        hwMplsTpOamInterfaceAisObject OBJECT IDENTIFIER ::= { hwMplsTpOamInterfaceAis 1 }
        hwMplsTpOamInterfaceAisTable OBJECT-TYPE
            SYNTAX      SEQUENCE OF HwMplsTpOamInterfaceAisEntry
            MAX-ACCESS  not-accessible
            STATUS current
            DESCRIPTION
              "
              This table is used to configure the Alarm Indication Signal (AIS)
                function in the interface to suppress alarms.
              "
            ::= { hwMplsTpOamInterfaceAisObject 1 }

        hwMplsTpOamInterfaceAisEntry OBJECT-TYPE
            SYNTAX HwMplsTpOamInterfaceAisEntry
            MAX-ACCESS not-accessible
            STATUS current
            DESCRIPTION
                "
                The entry of alarm indication signal in the interface.
                "
            INDEX { hwMplsTpOamInterfaceAisInterfaceName }
            ::= { hwMplsTpOamInterfaceAisTable 1 }


        HwMplsTpOamInterfaceAisEntry ::=
            SEQUENCE {
                hwMplsTpOamInterfaceAisInterfaceName
                    OCTET STRING,
                hwMplsTpOamInterfaceAisEnable
                    EnabledStatus,
                hwMplsTpOamInterfaceAisInterval
                    INTEGER,
                hwMplsTpOamInterfaceAisExp
                    Integer32,
                hwMplsTpOamInterfaceAisRowStatus
                    RowStatus
             }

        hwMplsTpOamInterfaceAisInterfaceName OBJECT-TYPE
            SYNTAX OCTET STRING (SIZE (0..63))
            MAX-ACCESS not-accessible
            STATUS current
            DESCRIPTION
                "
                This object indicates the interface for AIS function.
                "
            ::= { hwMplsTpOamInterfaceAisEntry 1 }

        hwMplsTpOamInterfaceAisEnable OBJECT-TYPE
            SYNTAX EnabledStatus
            MAX-ACCESS read-create
            STATUS current
            DESCRIPTION
                "
                This object indicates whether the AIS function is enabled in the interface.
                "
            ::= { hwMplsTpOamInterfaceAisEntry 2 }

        hwMplsTpOamInterfaceAisInterval OBJECT-TYPE
            SYNTAX INTEGER{
                interval1000ms      (4),
                interval60000ms     (6)
                }
            MAX-ACCESS read-create
            STATUS current
            DESCRIPTION
                "
                This object indicates the interval for sending AIS frames.
                "
            DEFVAL { 4 }
            ::= { hwMplsTpOamInterfaceAisEntry 3 }

        hwMplsTpOamInterfaceAisExp OBJECT-TYPE
            SYNTAX Integer32 (0..7)
            MAX-ACCESS read-create
            STATUS current
            DESCRIPTION
                "
                This object indicates the packet EXP for sending AIS frames.
                "
            DEFVAL { 7 }
            ::= { hwMplsTpOamInterfaceAisEntry 4 }

        hwMplsTpOamInterfaceAisRowStatus OBJECT-TYPE
            SYNTAX RowStatus
            MAX-ACCESS read-create
            STATUS current
            DESCRIPTION
                "
                This object indicates the row status of this table.
                "
            ::= { hwMplsTpOamInterfaceAisEntry 50 }


        hwMplsTpOamMegLookup OBJECT IDENTIFIER ::= { hwMplsTpOamMib 8 }
        hwMplsTpOamMegLookupObject OBJECT IDENTIFIER ::= { hwMplsTpOamMegLookup 1 }
        hwMplsTpOamMegTeLookupTable OBJECT-TYPE
            SYNTAX      SEQUENCE OF HwMplsTpOamMegTeLookupEntry
            MAX-ACCESS  not-accessible
            STATUS current
            DESCRIPTION
              "
              This table is used to lookup MEG for special parameters in MPLS TE scenario.
              "
            ::= { hwMplsTpOamMegLookupObject 1 }

        hwMplsTpOamMegTeLookupEntry OBJECT-TYPE
            SYNTAX HwMplsTpOamMegTeLookupEntry
            MAX-ACCESS not-accessible
            STATUS current
            DESCRIPTION
                "
                The entry for MPLS TE MEG.
                "
            INDEX { hwMplsTpOamMegTeInterfaceName }
            ::= { hwMplsTpOamMegTeLookupTable 1 }


        HwMplsTpOamMegTeLookupEntry ::=
            SEQUENCE {
                hwMplsTpOamMegTeInterfaceName
                    OCTET STRING,
                hwMplsTpOamTeMegId
                    OCTET STRING,
                hwMplsTpOamTeMeIndex
                    Unsigned32
             }

        hwMplsTpOamMegTeInterfaceName OBJECT-TYPE
            SYNTAX OCTET STRING (SIZE (0..63))
            MAX-ACCESS not-accessible
            STATUS current
            DESCRIPTION
                "
                This object indicates the associate interface in MEG.
                "
            ::= { hwMplsTpOamMegTeLookupEntry 1 }

        hwMplsTpOamTeMegId OBJECT-TYPE
            SYNTAX OCTET STRING (SIZE (1..48))
            MAX-ACCESS read-only
            STATUS current
            DESCRIPTION
                "
                This object indicates the MEG ID in MEG.
                "
            ::= { hwMplsTpOamMegTeLookupEntry 2 }

        hwMplsTpOamTeMeIndex OBJECT-TYPE
            SYNTAX Unsigned32
            MAX-ACCESS read-only
            STATUS current
            DESCRIPTION
                "
                This object indicates the ME index in MEG.
                "
            ::= { hwMplsTpOamMegTeLookupEntry 3 }

        hwMplsTpOamMegVllLookupTable OBJECT-TYPE
            SYNTAX      SEQUENCE OF HwMplsTpOamMegVllLookupEntry
            MAX-ACCESS  not-accessible
            STATUS current
            DESCRIPTION
              "
              This table is used to lookup MEG for special parameters in pwe3 scenario.
              "
            ::= { hwMplsTpOamMegLookupObject 2 }

        hwMplsTpOamMegVllLookupEntry OBJECT-TYPE
            SYNTAX HwMplsTpOamMegVllLookupEntry
            MAX-ACCESS not-accessible
            STATUS current
            DESCRIPTION
                "
                The entry for VLL MEG.
                "
            INDEX { hwMplsTpOamMegVllPeerip,hwMplsTpOamMegVcType,hwMplsTpOamMegVcId }
            ::= { hwMplsTpOamMegVllLookupTable 1 }


        HwMplsTpOamMegVllLookupEntry ::=
            SEQUENCE {
                hwMplsTpOamMegVllPeerip
                    IpAddress,
                hwMplsTpOamMegVcType
                    HWL2VpnVcEncapsType,
                hwMplsTpOamMegVcId
                    Unsigned32,
                hwMplsTpOamVllMegId
                    OCTET STRING,
                hwMplsTpOamVllMeIndex
                    Unsigned32
             }

        hwMplsTpOamMegVllPeerip OBJECT-TYPE
            SYNTAX IpAddress
            MAX-ACCESS not-accessible
            STATUS current
            DESCRIPTION
                "
                This object indicates the peer IP of PW type ME.
                "
            ::= { hwMplsTpOamMegVllLookupEntry 1 }

        hwMplsTpOamMegVcType OBJECT-TYPE
            SYNTAX HWL2VpnVcEncapsType
            MAX-ACCESS not-accessible
            STATUS current
            DESCRIPTION
                "
                This object indicates the vc type of PW type ME.
                "
            ::= { hwMplsTpOamMegVllLookupEntry 2 }

        hwMplsTpOamMegVcId OBJECT-TYPE
            SYNTAX Unsigned32
            MAX-ACCESS not-accessible
            STATUS current
            DESCRIPTION
                "
                This object indicates the vc id of PW type ME.
                "
            ::= { hwMplsTpOamMegVllLookupEntry 3 }

         hwMplsTpOamVllMegId OBJECT-TYPE
            SYNTAX OCTET STRING (SIZE (1..48))
            MAX-ACCESS read-only
            STATUS current
            DESCRIPTION
                "
                This object indicates the MEG Id in MEG.
                "
            ::= { hwMplsTpOamMegVllLookupEntry 4 }

        hwMplsTpOamVllMeIndex OBJECT-TYPE
            SYNTAX Unsigned32
            MAX-ACCESS read-only
            STATUS current
            DESCRIPTION
                "
                This object indicates the ME index in MEG.
                "
            ::= { hwMplsTpOamMegVllLookupEntry 5 }

       hwMplsTpOamMegSectionLookupTable OBJECT-TYPE
            SYNTAX      SEQUENCE OF HwMplsTpOamMegSectionLookupEntry
            MAX-ACCESS  not-accessible
            STATUS current
            DESCRIPTION
              "
              This table is used to lookup MEG for special parameters in section scenario.
              "
            ::= { hwMplsTpOamMegLookupObject 3 }

        hwMplsTpOamMegSectionLookupEntry OBJECT-TYPE
            SYNTAX HwMplsTpOamMegSectionLookupEntry
            MAX-ACCESS not-accessible
            STATUS current
            DESCRIPTION
                "
                The entry for SECTION MEG.
                "
            INDEX { hwMplsTpOamMegSectionInterfaceName }
            ::= { hwMplsTpOamMegSectionLookupTable 1 }


        HwMplsTpOamMegSectionLookupEntry ::=
            SEQUENCE {
                hwMplsTpOamMegSectionInterfaceName
                    OCTET STRING,
                hwMplsTpOamSectionMegId
                    OCTET STRING,
                hwMplsTpOamSectionMeIndex
                    Unsigned32
             }

        hwMplsTpOamMegSectionInterfaceName OBJECT-TYPE
            SYNTAX OCTET STRING (SIZE (0..63))
            MAX-ACCESS not-accessible
            STATUS current
            DESCRIPTION
                "
                This object indicates the associate interface in MEG.
                "
            ::= { hwMplsTpOamMegSectionLookupEntry 1 }

        hwMplsTpOamSectionMegId OBJECT-TYPE
            SYNTAX OCTET STRING (SIZE(1..48))
            MAX-ACCESS read-only
            STATUS current
            DESCRIPTION
                "
                This object indicates the meg id of section type ME.
                "
            ::= { hwMplsTpOamMegSectionLookupEntry 2 }

        hwMplsTpOamSectionMeIndex OBJECT-TYPE
            SYNTAX Unsigned32
            MAX-ACCESS read-only
            STATUS current
            DESCRIPTION
                "
                This object indicates the ME index in MEG.
                "
            ::= { hwMplsTpOamMegSectionLookupEntry 3 }

        hwMplsTpOamMegLspLookupTable OBJECT-TYPE
            SYNTAX SEQUENCE OF HwMplsTpOamMegLspLookupEntry
            MAX-ACCESS  not-accessible
            STATUS current
            DESCRIPTION
              "
              This table is used to lookup LSP.
              "
            ::= { hwMplsTpOamMegLookupObject 4 }

        hwMplsTpOamMegLspLookupEntry OBJECT-TYPE
            SYNTAX HwMplsTpOamMegLspLookupEntry
            MAX-ACCESS not-accessible
            STATUS current
            DESCRIPTION
                "
                The entry for MPLS LSP MEG.
                "
            INDEX { hwMplsTpOamMegLspName }
            ::= { hwMplsTpOamMegLspLookupTable 1 }


        HwMplsTpOamMegLspLookupEntry ::=
            SEQUENCE {
                hwMplsTpOamMegLspName
                    OCTET STRING,
                hwMplsTpOamLspMegId
                    OCTET STRING,
                hwMplsTpOamLspMeIndex
                    Unsigned32
             }

        hwMplsTpOamMegLspName OBJECT-TYPE
            SYNTAX OCTET STRING (SIZE (0..19))
            MAX-ACCESS not-accessible
            STATUS current
            DESCRIPTION
                "
                This object indicates the associate LSP in MEG.
                "
            ::= { hwMplsTpOamMegLspLookupEntry 1 }

        hwMplsTpOamLspMegId OBJECT-TYPE
            SYNTAX OCTET STRING (SIZE (1..48))
            MAX-ACCESS read-only
            STATUS current
            DESCRIPTION
                "
                This object indicates the MEG ID in MEG.
                "
            ::= { hwMplsTpOamMegLspLookupEntry 2 }

        hwMplsTpOamLspMeIndex OBJECT-TYPE
            SYNTAX Unsigned32
            MAX-ACCESS read-only
            STATUS current
            DESCRIPTION
                "
                This object indicates the ME index in MEG.
                "
            ::= { hwMplsTpOamMegLspLookupEntry 3 }

        hwMplsTpOamMegVsiLookupTable OBJECT-TYPE
            SYNTAX SEQUENCE OF HwMplsTpOamMegVsiLookupEntry
            MAX-ACCESS  not-accessible
            STATUS current
            DESCRIPTION
              "
              This table is used to lookup MEG for special parameters in pwe3 scenario.
              "
            ::= { hwMplsTpOamMegLookupObject 5 }

        hwMplsTpOamMegVsiLookupEntry OBJECT-TYPE
            SYNTAX HwMplsTpOamMegVsiLookupEntry
            MAX-ACCESS not-accessible
            STATUS current
            DESCRIPTION
                "
                The entry for VSI MEG.
                "
            INDEX { hwMplsTpOamMegVsiName,hwMplsTpOamMegVsiPeerip,hwMplsTpOamMegVsiPwId }
            ::= { hwMplsTpOamMegVsiLookupTable 1 }


        HwMplsTpOamMegVsiLookupEntry ::=
            SEQUENCE {
                hwMplsTpOamMegVsiName
                    OCTET STRING,
                hwMplsTpOamMegVsiPeerip
                    IpAddress,
                hwMplsTpOamMegVsiPwId
                    Unsigned32,
                hwMplsTpOamVsiMegId
                    OCTET STRING,
                hwMplsTpOamVsiMeIndex
                    Unsigned32
             }

        hwMplsTpOamMegVsiName OBJECT-TYPE
            SYNTAX OCTET STRING (SIZE (0..31))
            MAX-ACCESS not-accessible
            STATUS current
            DESCRIPTION
                "
                This object indicates the VSI name of PW type ME.
                "
            ::= { hwMplsTpOamMegVsiLookupEntry 1 }

        hwMplsTpOamMegVsiPeerip OBJECT-TYPE
            SYNTAX IpAddress
            MAX-ACCESS not-accessible
            STATUS current
            DESCRIPTION
                "
                This object indicates the peer IP of PW type ME.
                "
            ::= { hwMplsTpOamMegVsiLookupEntry 2 }

        hwMplsTpOamMegVsiPwId OBJECT-TYPE
            SYNTAX Unsigned32
            MAX-ACCESS not-accessible
            STATUS current
            DESCRIPTION
                "
                This object indicates the VSI id of PW type ME.
                "
            ::= { hwMplsTpOamMegVsiLookupEntry 3 }

         hwMplsTpOamVsiMegId OBJECT-TYPE
            SYNTAX OCTET STRING (SIZE (1..48))
            MAX-ACCESS read-only
            STATUS current
            DESCRIPTION
                "
                This object indicates the MEG Id in MEG.
                "
            ::= { hwMplsTpOamMegVsiLookupEntry 4 }

        hwMplsTpOamVsiMeIndex OBJECT-TYPE
            SYNTAX Unsigned32
            MAX-ACCESS read-only
            STATUS current
            DESCRIPTION
                "
                This object indicates the ME index in MEG.
                "
            ::= { hwMplsTpOamMegVsiLookupEntry 5 }


        hwMplsTpOamTstObject OBJECT IDENTIFIER ::= { hwMplsTpOamMib 9 }

        hwMplsTpOamTstTable OBJECT-TYPE
            SYNTAX SEQUENCE OF HwMplsTpOamTstEntry
            MAX-ACCESS not-accessible
            STATUS current
            DESCRIPTION
                "
                The entries related to the MEG test include the parameters input
                by users and the returned results.
                "
            ::= { hwMplsTpOamTstObject 1 }


        hwMplsTpOamTstEntry OBJECT-TYPE
            SYNTAX HwMplsTpOamTstEntry
            MAX-ACCESS not-accessible
            STATUS current
            DESCRIPTION
                " "
            INDEX { hwMplsTpOamMegId }
            ::= { hwMplsTpOamTstTable 1 }


        HwMplsTpOamTstEntry ::=
            SEQUENCE {
                hwMplsTpOamTstState
                    INTEGER,
                hwMplsTpOamTstCount
                    Unsigned32,
                hwMplsTpOamTstExp
                    Integer32,
                hwMplsTpOamTstInterval
                    INTEGER,
                hwMplsTpOamTstHardwareBasedEnable
                    EnabledStatus,
                hwMplsTpOamTstRate
                    Unsigned32,
                hwMplsTpOamTstBlockFlowEnable
                    EnabledStatus
             }

        hwMplsTpOamTstState OBJECT-TYPE
            SYNTAX INTEGER
                {
                disable(1),
                enable(2)
                }
            MAX-ACCESS read-create
            STATUS current
            DESCRIPTION
                "
                This object indicates whether the TEST function is enable.
                   The value can be:
                   1:disable
                   2:enable
                 By default, the value is disable.
                 "
            DEFVAL { 1 }
            ::= { hwMplsTpOamTstEntry 1 }

        hwMplsTpOamTstCount OBJECT-TYPE
            SYNTAX Unsigned32 (1..4294967295)
            MAX-ACCESS read-create
            STATUS current
            DESCRIPTION
                "
                This object indicates the number of test operation times.
                The value ranges from 1 to 4294967295.
                By default, the value is 5.
                "
            DEFVAL { 5 }
            ::= { hwMplsTpOamTstEntry 2 }

        hwMplsTpOamTstExp OBJECT-TYPE
            SYNTAX Integer32 (0..7)
            MAX-ACCESS read-create
            STATUS current
            DESCRIPTION
                "
                This object indicates the exp of test.
                The value ranges from 0 to 7.
                By default, the value is 7.
                "
            DEFVAL { 7 }
            ::= { hwMplsTpOamTstEntry 3 }

        hwMplsTpOamTstInterval OBJECT-TYPE
            SYNTAX INTEGER
            {
                interval1000ms    (4),
                interval10000ms   (5),
                interval60000ms   (6),
                interval600000ms  (7)
            }
            MAX-ACCESS read-create
            STATUS current
            DESCRIPTION
                "
                This object indicates the interval of test.
                The value of this object can be:
                  (1) 1  second
                  (2) 10 seconds
                  (3) 1  minute
                  (4) 10 minutes
                By default, the value is 1 second.
                "
            DEFVAL { 4 }
            ::= { hwMplsTpOamTstEntry 4 }

        hwMplsTpOamTstHardwareBasedEnable OBJECT-TYPE
            SYNTAX EnabledStatus
            MAX-ACCESS read-create
            STATUS current
            DESCRIPTION
                "
                This object indicates whether hardware is enabled for sending test packets or not.
                The default value is disable.
                "
            ::= { hwMplsTpOamTstEntry 5 }

        hwMplsTpOamTstRate OBJECT-TYPE
            SYNTAX Unsigned32 (0 | 1..10485760)
            MAX-ACCESS read-create
            STATUS current
            DESCRIPTION
                "
                This object indicates the rate of test.
                The value ranges from 1 to 10485760 in kbps.
                "
             ::= { hwMplsTpOamTstEntry 6 }

        hwMplsTpOamTstBlockFlowEnable OBJECT-TYPE
            SYNTAX EnabledStatus
            MAX-ACCESS read-create
            STATUS current
            DESCRIPTION
                "
                This object indicates whether block data flow is enabled for sending test packets or not.
                The default value is disable
                "
            ::= { hwMplsTpOamTstEntry 7 }

       hwMplsTpOamScalarsObjects OBJECT IDENTIFIER ::= { hwMplsTpOamMib 10 }

       hwMplsTpOamMode OBJECT-TYPE
            SYNTAX INTEGER{
                private  (0),
                standard (1)
                }
            MAX-ACCESS read-write
            STATUS current
            DESCRIPTION
                "
                This object indicates the mode of mpls-tp oam.
                "
            ::= { hwMplsTpOamScalarsObjects 1 }


	hwMplsTpOamIpMegObject OBJECT IDENTIFIER ::= { hwMplsTpOamMib 11 }

	hwMplsTpOamIpMegPingRespTable OBJECT-TYPE
		SYNTAX SEQUENCE OF HwMplsTpOamIpMegPingRespEntry
		MAX-ACCESS not-accessible
		STATUS current
		DESCRIPTION
			"
			The response of the MEG ip ping.
			"
		::= { hwMplsTpOamIpMegObject 1 }

	hwMplsTpOamIpMegPingRespEntry OBJECT-TYPE
		SYNTAX HwMplsTpOamIpMegPingRespEntry
		MAX-ACCESS not-accessible
		STATUS current
		DESCRIPTION
			" "
		INDEX { hwMplsTpOamMegId, hwMplsTpOamIpMegPingNum }
		::= { hwMplsTpOamIpMegPingRespTable 1 }

	HwMplsTpOamIpMegPingRespEntry ::=
		SEQUENCE {
			hwMplsTpOamIpMegPingNum
				Integer32,
			hwMplsTpOamIpMegPingSeqNum
				Integer32,
			hwMplsTpOamIpMegPingResult
				INTEGER,
			hwMplsTpOamIpMegPingMepId
				Integer32,
			hwMplsTpOamIpMegPingLsrId
				IpAddress,
			hwMplsTpOamIpMegPingPktLen
				Integer32,
			hwMplsTpOamIpMegPingDelay
				Integer32,
			hwMplsTpOamIpMegPingTtl
				Integer32,
			hwMplsTpOamIpMegPingServiceType
				INTEGER,
			hwMplsTpOamIpMegPingServiceIndex
				Integer32,
			hwMplsTpOamIpMegPingIfIndex
				Integer32,
			hwMplsTpOamIpMegPingVpnName
				OCTET STRING,
			hwMplsTpOamIpMegPingReturnCode
				INTEGER
		 }

	hwMplsTpOamIpMegPingNum OBJECT-TYPE
		SYNTAX Integer32
		MAX-ACCESS accessible-for-notify
		STATUS current
		DESCRIPTION
			"
			This object indicates the return num of ip meg ping packet.
			 "
		::= { hwMplsTpOamIpMegPingRespEntry 1 }

	hwMplsTpOamIpMegPingSeqNum OBJECT-TYPE
		SYNTAX Integer32
		MAX-ACCESS read-only
		STATUS current
		DESCRIPTION
			"
			This object indicates the send sequence num of ip meg ping packet.
			"
		::= { hwMplsTpOamIpMegPingRespEntry 2 }

	hwMplsTpOamIpMegPingResult OBJECT-TYPE
		SYNTAX INTEGER
			{
			ok(0),
			timeout(1)
			}
		MAX-ACCESS read-only
		STATUS current
		DESCRIPTION
			"
			This object indicates the result of ip meg ping.
			"
		::= { hwMplsTpOamIpMegPingRespEntry 3 }

	hwMplsTpOamIpMegPingMepId OBJECT-TYPE
		SYNTAX Integer32
		MAX-ACCESS read-only
		STATUS current
		DESCRIPTION
			"
			This object indicates the mep id ip meg ping.
			"
		::= { hwMplsTpOamIpMegPingRespEntry 4 }

	hwMplsTpOamIpMegPingLsrId OBJECT-TYPE
		SYNTAX IpAddress
		MAX-ACCESS read-only
		STATUS current
		DESCRIPTION
			"
			This object indicates the lsr id of ip meg ping.
			"
		::= { hwMplsTpOamIpMegPingRespEntry 5 }

	hwMplsTpOamIpMegPingPktLen OBJECT-TYPE
		SYNTAX Integer32
		MAX-ACCESS read-only
		STATUS current
		DESCRIPTION
			"
			This object indicates the packet length of ip meg ping.
			"
		::= { hwMplsTpOamIpMegPingRespEntry 6 }

	hwMplsTpOamIpMegPingDelay OBJECT-TYPE
		SYNTAX Integer32
		MAX-ACCESS read-only
		STATUS current
		DESCRIPTION
			"
			This object indicates the delay of ip meg ping.
			"
		::= { hwMplsTpOamIpMegPingRespEntry 7 }

	hwMplsTpOamIpMegPingTtl OBJECT-TYPE
		SYNTAX Integer32
		MAX-ACCESS read-only
		STATUS current
		DESCRIPTION
			"
			This object indicates the Ttl of ip meg ping.
			"
		::= { hwMplsTpOamIpMegPingRespEntry 8 }

	hwMplsTpOamIpMegPingServiceType OBJECT-TYPE
            SYNTAX INTEGER
                {
                invalid(0),
                l2uni(1),
                l3uni(2)
                }

		MAX-ACCESS read-only
		STATUS current
		DESCRIPTION
			"
			This object indicates ip meg type of the ip meg ping
			"
		::= { hwMplsTpOamIpMegPingRespEntry 9 }

	hwMplsTpOamIpMegPingServiceIndex OBJECT-TYPE
		SYNTAX Integer32
		MAX-ACCESS read-only
		STATUS current
		DESCRIPTION
			"
			This object indicates 39's service index of the ip meg ping.
			"
		::= { hwMplsTpOamIpMegPingRespEntry 10 }

	hwMplsTpOamIpMegPingIfIndex OBJECT-TYPE
		SYNTAX Integer32
		MAX-ACCESS read-only
		STATUS current
		DESCRIPTION
			"
			This object indicates L2uni interface index of the ip meg ping.
			"
		::= { hwMplsTpOamIpMegPingRespEntry 11 }

	hwMplsTpOamIpMegPingVpnName OBJECT-TYPE
		SYNTAX OCTET STRING
		MAX-ACCESS read-only
		STATUS current
		DESCRIPTION
			"
			This object indicates L3uni vpn name of the ip meg ping.
			"
		::= { hwMplsTpOamIpMegPingRespEntry 12 }

	hwMplsTpOamIpMegPingReturnCode OBJECT-TYPE
            SYNTAX INTEGER
                {
                invalid(0),
                destination(3)
                }

		MAX-ACCESS read-only
		STATUS current
		DESCRIPTION
			"
			This object indicates ip meg return code of the ip meg ping
			"
		::= { hwMplsTpOamIpMegPingRespEntry 13 }


	hwMplsTpOamIpMegPingStatTable OBJECT-TYPE
		SYNTAX SEQUENCE OF HwMplsTpOamIpMegPingStatEntry
		MAX-ACCESS not-accessible
		STATUS current
		DESCRIPTION
			"
			The entries related to the MEG ping statistics information.
			"
		::= { hwMplsTpOamIpMegObject 2 }

	hwMplsTpOamIpMegPingStatEntry OBJECT-TYPE
		SYNTAX HwMplsTpOamIpMegPingStatEntry
		MAX-ACCESS not-accessible
		STATUS current
		DESCRIPTION
			" "
		INDEX { hwMplsTpOamMegId }
		::= { hwMplsTpOamIpMegPingStatTable 1 }

	HwMplsTpOamIpMegPingStatEntry ::=
		SEQUENCE {
			hwMplsTpOamIpMegPingState
				INTEGER,
			hwMplsTpOamIpMegPingTotalResult
				INTEGER,
			hwMplsTpOamIpMegPingFailReason
				INTEGER,
			hwMplsTpOamIpMegPingTxNum
				Integer32,
			hwMplsTpOamIpMegPingRxNum
				Integer32,
			hwMplsTpOamIpMegPingLossRate
				Integer32,
			hwMplsTpOamIpMegPingMinDelay
				Integer32,
			hwMplsTpOamIpMegPingMaxDelay
				Integer32,
			hwMplsTpOamIpMegPingAverDelay
				Integer32
		 }


	hwMplsTpOamIpMegPingState OBJECT-TYPE
		SYNTAX INTEGER
			{
			never(0),
			doing(1),
			done(2),
			stop(3)
			}
		MAX-ACCESS read-only
		STATUS current
		DESCRIPTION
			"
			This object indicates ping state of the ip meg.
			   The value can be:
			   0:never
			   1:doing
			   2:done
			   3:stop
			 "
		::= { hwMplsTpOamIpMegPingStatEntry 1 }

	hwMplsTpOamIpMegPingTotalResult OBJECT-TYPE
		SYNTAX INTEGER
			{
			ok(0),
			error(1)

			}
		MAX-ACCESS read-only
		STATUS current
		DESCRIPTION
			"
			This object indicates ping total result of the ip meg.
			   The value can be:
			   0:ok
			   1:error
			"
		::= { hwMplsTpOamIpMegPingStatEntry 2 }

	hwMplsTpOamIpMegPingFailReason OBJECT-TYPE
		SYNTAX INTEGER
			{
			ok(0)
			}
		MAX-ACCESS read-only
		STATUS current
		DESCRIPTION
			"
			ok(0)
			"
		::= { hwMplsTpOamIpMegPingStatEntry 3 }

	hwMplsTpOamIpMegPingTxNum OBJECT-TYPE
		SYNTAX Integer32
		MAX-ACCESS read-only
		STATUS current
		DESCRIPTION
			"
			This object indicates the num of packet send of the ip meg ping.
			"
		::= { hwMplsTpOamIpMegPingStatEntry 4 }

	hwMplsTpOamIpMegPingRxNum OBJECT-TYPE
		SYNTAX Integer32
		MAX-ACCESS read-only
		STATUS current
		DESCRIPTION
			"
			This object indicates the num of packet received of the ip meg ping.
			"
		::= { hwMplsTpOamIpMegPingStatEntry 5 }

	hwMplsTpOamIpMegPingLossRate OBJECT-TYPE
		SYNTAX Integer32
		MAX-ACCESS read-only
		STATUS current
		DESCRIPTION
			"
			This object indicates the packet loss rate of the ip meg ping.
			"
		::= { hwMplsTpOamIpMegPingStatEntry 6 }

	hwMplsTpOamIpMegPingMinDelay OBJECT-TYPE
		SYNTAX Integer32
		MAX-ACCESS read-only
		STATUS current
		DESCRIPTION
			"
			This object indicates the min delay of ping.
			"
		::= { hwMplsTpOamIpMegPingStatEntry 7 }

	hwMplsTpOamIpMegPingMaxDelay OBJECT-TYPE
		SYNTAX Integer32
		MAX-ACCESS read-only
		STATUS current
		DESCRIPTION
			"
			This object indicates the max delay of ping.
			"
		::= { hwMplsTpOamIpMegPingStatEntry 8 }

	hwMplsTpOamIpMegPingAverDelay OBJECT-TYPE
		SYNTAX Integer32
		MAX-ACCESS read-only
		STATUS current
		DESCRIPTION
			"
			This object indicates the average delay of ping.
			"
		::= { hwMplsTpOamIpMegPingStatEntry 9 }

	hwMplsTpOamIpMegTracertRespTable OBJECT-TYPE
		SYNTAX SEQUENCE OF HwMplsTpOamIpMegTracertRespEntry
		MAX-ACCESS not-accessible
		STATUS current
		DESCRIPTION
			"
			The response of the MEG ip tracert.
			"
		::= { hwMplsTpOamIpMegObject 3 }

	hwMplsTpOamIpMegTracertRespEntry OBJECT-TYPE
		SYNTAX HwMplsTpOamIpMegTracertRespEntry
		MAX-ACCESS not-accessible
		STATUS current
		DESCRIPTION
			" "
		INDEX { hwMplsTpOamMegId, hwMplsTpOamIpMegTracertSeqNum }
		::= { hwMplsTpOamIpMegTracertRespTable 1 }

	HwMplsTpOamIpMegTracertRespEntry ::=
		SEQUENCE {
			hwMplsTpOamIpMegTracertSeqNum
				Integer32,
			hwMplsTpOamIpMegTracertResult
				INTEGER,
			hwMplsTpOamIpMegTracertMepId
				Integer32,
			hwMplsTpOamIpMegTracertLsrId
				IpAddress,
			hwMplsTpOamIpMegTracertDelay
				Integer32,
			hwMplsTpOamIpMegTracertNodeType
				INTEGER,
			hwMplsTpOamIpMegTracertTtl
				Integer32,
			hwMplsTpOamIpMegTracertServiceType
				INTEGER,
			hwMplsTpOamIpMegTracertServiceIndex
				Integer32,
			hwMplsTpOamIpMegTracertIfIndex
				Integer32,
			hwMplsTpOamIpMegTracertVpnName
				OCTET STRING,
			hwMplsTpOamIpMegTracertReturnCode
				INTEGER
		 }

	hwMplsTpOamIpMegTracertSeqNum OBJECT-TYPE
		SYNTAX Integer32
		MAX-ACCESS accessible-for-notify
		STATUS current
		DESCRIPTION
			"
			This object indicates ip meg tracert sequence number.
			"
		::= { hwMplsTpOamIpMegTracertRespEntry 1 }

	hwMplsTpOamIpMegTracertResult OBJECT-TYPE
		SYNTAX INTEGER
			{
			ok(0),
			timeout(1)
			}
		MAX-ACCESS read-only
		STATUS current
		DESCRIPTION
			"
			This object indicates ip meg tracert result.
			"
		::= { hwMplsTpOamIpMegTracertRespEntry 2 }

	hwMplsTpOamIpMegTracertMepId OBJECT-TYPE
		SYNTAX Integer32 (0|1..8191)
		MAX-ACCESS read-only
		STATUS current
		DESCRIPTION
			"
			This object indicates ip meg tracert mep id.
			"
		::= { hwMplsTpOamIpMegTracertRespEntry 3 }

	hwMplsTpOamIpMegTracertLsrId OBJECT-TYPE
		SYNTAX IpAddress
		MAX-ACCESS read-only
		STATUS current
		DESCRIPTION
			"
			This object indicates ip meg tracert lsr id.
			"
		::= { hwMplsTpOamIpMegTracertRespEntry 4 }

	hwMplsTpOamIpMegTracertDelay OBJECT-TYPE
		SYNTAX Integer32
		MAX-ACCESS read-only
		STATUS current
		DESCRIPTION
			"
			This object indicates ip meg tracert delay.
			"
		::= { hwMplsTpOamIpMegTracertRespEntry 5 }

	hwMplsTpOamIpMegTracertNodeType OBJECT-TYPE
		SYNTAX  INTEGER
			{
			notsupport(0),
			ingress(1),
			transit(2),
			egress(3)
			}
		MAX-ACCESS read-only
		STATUS current
		DESCRIPTION
			"
			This object indicates ip meg tracert node type.
			"
		::= { hwMplsTpOamIpMegTracertRespEntry 6 }

	hwMplsTpOamIpMegTracertTtl OBJECT-TYPE
		SYNTAX Integer32
		MAX-ACCESS read-only
		STATUS current
		DESCRIPTION
			"
			This object indicates ip meg tracert ttl.
			"
		::= { hwMplsTpOamIpMegTracertRespEntry 7 }

	hwMplsTpOamIpMegTracertServiceType OBJECT-TYPE
		SYNTAX INTEGER
                {
                invalid(0),
                l2uni(1),
                l3uni(2)
                }
		MAX-ACCESS read-only
		STATUS current
		DESCRIPTION
			"
			This object indicates ip meg tracert service type.
			"
		::= { hwMplsTpOamIpMegTracertRespEntry 8 }

	hwMplsTpOamIpMegTracertServiceIndex OBJECT-TYPE
		SYNTAX Integer32
		MAX-ACCESS read-only
		STATUS current
		DESCRIPTION
			"
			This object indicates ip meg tracert service index of 39.
			"
		::= { hwMplsTpOamIpMegTracertRespEntry 9 }

	hwMplsTpOamIpMegTracertIfIndex OBJECT-TYPE
		SYNTAX Integer32
		MAX-ACCESS read-only
		STATUS current
		DESCRIPTION
			"
			This object indicates ip meg tracert ifIndex of L2uni.
			"
		::= { hwMplsTpOamIpMegTracertRespEntry 10 }

	hwMplsTpOamIpMegTracertVpnName OBJECT-TYPE
		SYNTAX OCTET STRING
		MAX-ACCESS read-only
		STATUS current
		DESCRIPTION
			"
			This object indicates ip meg tracert VpnName of L3uni.
			"
		::= { hwMplsTpOamIpMegTracertRespEntry 11 }

	hwMplsTpOamIpMegTracertReturnCode OBJECT-TYPE
            SYNTAX INTEGER
                {
                invalid(0),
                destination(3),
                transit(8)
                }

		MAX-ACCESS read-only
		STATUS current
		DESCRIPTION
			"
			This object indicates ip meg return code of the ip meg tracert.
			"
		::= { hwMplsTpOamIpMegTracertRespEntry 12 }

	hwMplsTpOamIpMegTracertStatTable OBJECT-TYPE
		SYNTAX SEQUENCE OF HwMplsTpOamIpMegTracertStatEntry
		MAX-ACCESS not-accessible
		STATUS current
		DESCRIPTION
			"
			The entries related to the IP MEG tracert states.
			"
		::= { hwMplsTpOamIpMegObject 4 }

	hwMplsTpOamIpMegTracertStatEntry OBJECT-TYPE
		SYNTAX HwMplsTpOamIpMegTracertStatEntry
		MAX-ACCESS not-accessible
		STATUS current
		DESCRIPTION
			" "
		INDEX { hwMplsTpOamMegId }
		::= { hwMplsTpOamIpMegTracertStatTable 1 }

	HwMplsTpOamIpMegTracertStatEntry ::=
		SEQUENCE {
			hwMplsTpOamIpMegTracertState
				INTEGER,
			hwMplsTpOamIpMegTracertTotalResult
				INTEGER,
			hwMplsTpOamIpMegTracertFailReason
				INTEGER
		 }

	hwMplsTpOamIpMegTracertState OBJECT-TYPE
		SYNTAX INTEGER
			{
			never(0),
			doing(1),
			done(2),
			stop(3)
			}
		MAX-ACCESS read-only
		STATUS current
		DESCRIPTION
			"
			This object indicates tracert state of the ip meg.
			   The value can be:
			   0:never
			   1:doing
			   2:done
			   3:stop
			 "
		::= { hwMplsTpOamIpMegTracertStatEntry 1 }

	hwMplsTpOamIpMegTracertTotalResult OBJECT-TYPE
		SYNTAX INTEGER
			{
			ok(0),
			error(1)

			}
		MAX-ACCESS read-only
		STATUS current
		DESCRIPTION
			"
			This object indicates tracert total result of the ip meg.
			   The value can be:
			   0:ok
			   1:error
			"
		::= { hwMplsTpOamIpMegTracertStatEntry 2 }

	hwMplsTpOamIpMegTracertFailReason OBJECT-TYPE
		SYNTAX INTEGER
			{
			ok(0)
			}
		MAX-ACCESS read-only
		STATUS current
		DESCRIPTION
			"
			ok(0)
			"
		::= { hwMplsTpOamIpMegTracertStatEntry 3 }


	hwMplsTpOamIpMegDataTable OBJECT-TYPE
		SYNTAX SEQUENCE OF HwMplsTpOamIpMegDataEntry
		MAX-ACCESS not-accessible
		STATUS current
		DESCRIPTION
			"
			The entries related to the IP MEG data.
			"
		::= { hwMplsTpOamIpMegObject 5 }

	hwMplsTpOamIpMegDataEntry OBJECT-TYPE
		SYNTAX HwMplsTpOamIpMegDataEntry
		MAX-ACCESS not-accessible
		STATUS current
		DESCRIPTION
			" "
		INDEX { hwMplsTpOamMegId, hwMplsTpOamMeIndex }
		::= { hwMplsTpOamIpMegDataTable 1 }

	HwMplsTpOamIpMegDataEntry ::=
		SEQUENCE {
			hwMplsTpOamIpMegMeMepId
				Integer32
		 }

         hwMplsTpOamIpMegMeMepId OBJECT-TYPE
            SYNTAX Integer32 (0|1..8191)
            MAX-ACCESS read-only
            STATUS current
            DESCRIPTION
                "
                This object indicates the MEP Id of IpMeg.
                "
            ::= { hwMplsTpOamIpMegDataEntry 1 }


        hwMplsTpOamConformance OBJECT IDENTIFIER ::= { hwMplsTpOamMib 20 }
        hwMplsTpOamCompliances OBJECT IDENTIFIER ::= { hwMplsTpOamConformance 1 }

        hwMplsTpOamFullCompliance MODULE-COMPLIANCE
            STATUS current
            DESCRIPTION
                "The compliance statement for the HUAWEI-TPOAM-MIB."
            MODULE -- this module
                MANDATORY-GROUPS { hwMplsTpOamMegGroup, hwMplsTpOamMeGroup, hwMplsTpOamLBGroup,hwMplsTpOamPerformanceStatisticGroup,
                hwMplsTpOamInterfaceAisGroup,hwMplsTpOamLookupGroup,hwMplsTpOamNotificationGroup, hwMplsTpOamTstGroup }
            ::= { hwMplsTpOamCompliances 1 }


        hwMplsTpOamGroups OBJECT IDENTIFIER ::= { hwMplsTpOamConformance 2 }


        hwMplsTpOamMegGroup OBJECT-GROUP
            OBJECTS { hwMplsTpOamMegId,hwMplsTpOamCCSendEnable,hwMplsTpOamCCReceiveEnable,hwMplsTpOamCCInterval,
                      hwMplsTpOamCCExp,hwMplsTpOamSingleLossReceiveEnable,hwMplsTpOamSingleLossEnable,hwMplsTpOamSingleLossCount,hwMplsTpOamSingleLossInterval,
                      hwMplsTpOamSingleLossExp,hwMplsTpOamDualLossEnable,hwMplsTpOamDualLossInterval,hwMplsTpOamDualLossSD1Threshold,hwMplsTpOamDualLossSD2Threshold,
                      hwMplsTpOamOneWayDelayMeasureEnable,hwMplsTpOamOneWayDelayMeasureInterval,hwMplsTpOamOneWayDelayMeasureCount,
                      hwMplsTpOamOneWayDelayMeasureExp,hwMplsTpOamOneWayDelayMeasureResetResult,hwMplsTpOamTwoWayDelayMeasureEnable,
                      hwMplsTpOamTwoWayDelayMeasureInterval,hwMplsTpOamTwoWayDelayMeasureCount,hwMplsTpOamTwoWayDelayMeasureExp,
                      hwMplsTpOamAisEnable,hwMplsTpOamAisInterval,hwMplsTpOamAisExp,
                      hwMplsTpOamSingleLossResetResult,hwMplsTpOamTwoWayDelayMeasureResetResult,
                      hwMplsTpOamTwoWayDelayMeasureTwoStamp,
                      hwMplsTpOamLockEnable,hwMplsTpOamLockInterval,hwMplsTpOamLockExp,hwMplsTpOamCsfEnable,hwMplsTpOamCsfInterval,
                      hwMplsTpOamCsfExp,hwMplsTpOamTstResetResult,hwMplsTpOamMegLevel,hwMplsTpOamRDIEnable,
                      hwMplsTpOamSingleLossProactiveSD1Threshold,hwMplsTpOamSingleLossProactiveSD2Threshold,hwMplsTpOamSingleLossProactiveEnable,
                      hwMplsTpOamOneWayDelayMeasureProactiveEnable,hwMplsTpOamTwoWayDelayMeasureProactiveEnable,
                      hwMplsTpOneWayDelayMeasurePaddingValue,hwMplsTpOneWayDelayMeasurePacketSize,hwMplsTpTwoWayDelayMeasurePaddingValue,hwMplsTpTwoWayDelayMeasurePacketSize,
                      hwMplsTpOamBitErrorDetectionSD1Threshold,hwMplsTpOamBitErrorDetectionSD2Threshold,hwMplsTpOamMegRowStatus,hwMplsTpOamSingleLossProactiveSD1ContinuousPeriod,
                      hwMplsTpOamSingleLossProactiveSD2ContinuousPeriod,hwMplsTpOamSingleLossProactiveSD1Period,hwMplsTpOamSingleLossProactiveSD1Count,
                      hwMplsTpOamSingleLossProactiveSD2Period,hwMplsTpOamSingleLossProactiveSD2Count,hwMplsTpOamSingleLossProactiveRevertivePeriod,
                      hwMplsTpOamOneWayDelayMeasureReceiveEnable
                   }
            STATUS current
            DESCRIPTION
                "The group for MEG."
            ::= { hwMplsTpOamGroups 1 }


        hwMplsTpOamMeGroup OBJECT-GROUP
            OBJECTS { hwMplsTpOamMegId,hwMplsTpOamMeIndex,hwMplsTpOamMeType,hwMplsTpOamMeDirection,hwMplsTpOamMeIfName,hwMplsTpOamMePeerip,
                      hwMplsTpOamMeVcId,hwMplsTpOamMeVcType,hwMplsTpOamMeVllRemotePeerIp,hwMplsTpOamMEVllTTL,hwMplsTpOamMeMepId,
                      hwMplsTpOamMeRemoteMepId,hwMplsTpOamMeState,hwMplsTpOamMeFarEndState,hwMplsTpOamMeNearEndState,hwMplsTpOamMeGal,hwMplsTpOamRingId,hwMplsTpOamRingDirection,
                      hwMplsTpOamMeRowStatus,hwMplsTpOamMeSwitchPeerIp,hwMplsTpOamMeSwitchVcId,hwMplsTpOamError,hwMplsTpOamMeMipId
                    }
            STATUS current
            DESCRIPTION
                "The group for ME."
            ::= { hwMplsTpOamGroups 2 }


        hwMplsTpOamLBGroup OBJECT-GROUP
            OBJECTS { hwMplsTpOamLBState,hwMplsTpOamLBTimeOut,hwMplsTpOamLBCount,hwMplsTpOamLBPacketSize,
                      hwMplsTpOamLBSendPacketNum,hwMplsTpOamLBRecvPacketNum,hwMplsTpOamLBPacketLossRatio,hwMplsTpOamLBRecvTimeDelayMin,
                      hwMplsTpOamLBRecvTimeDelayMax,hwMplsTpOamLBRecvTimeDelayAvg,hwMplsTpOamLBDestNodeType,hwMplsTpOamLBTTL,hwMplsTpOamLBNodeID,
                      hwMplsTpOamLBIFNum,hwMplsTpOamLBIsWithRequest,hwMplsTpOamLBDestMipId
                    }
            STATUS obsolete
            DESCRIPTION
                "The group for LB function."
            ::= { hwMplsTpOamGroups 3 }

        hwMplsTpOamPerformanceStatisticGroup OBJECT-GROUP
            OBJECTS { hwMplsTpOamSingleLossStatisticLocal,hwMplsTpOamSingleLossStatisticLocalRate,hwMplsTpOamSingleLossStatisticRemote,
                      hwMplsTpOamSingleLossStatisticRemoteRate,hwMplsTpOamSingleLossStatisticLocalMin,hwMplsTpOamSingleLossStatisticLocalMax,
                      hwMplsTpOamSingleLossStatisticLocalAverage,hwMplsTpOamSingleLossStatisticLocallRateMin,hwMplsTpOamSingleLossStatisticLocallRateMax,
                      hwMplsTpOamSingleLossStatisticLocallRateAverage,hwMplsTpOamSingleLossStatisticRemoteMin,hwMplsTpOamSingleLossStatisticRemoteMax,
                      hwMplsTpOamSingleLossStatisticRemoteAverage,hwMplsTpOamSingleLossStatisticRemoteRateMin,hwMplsTpOamSingleLossStatisticRemoteRateMax,
                      hwMplsTpOamSingleLossStatisticRemoteRateAverage,
                      hwMplsTpOamDelayMeasureStatisticOneWayAndVar,hwMplsTpOamDelayMeasureStatisticOneWayDelayMin,
                      hwMplsTpOamDelayMeasureStatisticOneWayDelayMax,hwMplsTpOamDelayMeasureStatisticOneWayDelayAverage,
                      hwMplsTpOamDelayMeasureStatisticOneWayVariationMin,hwMplsTpOamDelayMeasureStatisticOneWayVariationMax,
                      hwMplsTpOamDelayMeasureStatisticOneWayVariationAverage,
                      hwMplsTpOamDelayMeasureStatisticTwoWayAndVar,hwMplsTpOamDelayMeasureStatisticTwoWayDelayMin,
                      hwMplsTpOamDelayMeasureStatisticTwoWayDelayMax,hwMplsTpOamDelayMeasureStatisticTwoWayDelayAverage,
                      hwMplsTpOamDelayMeasureStatisticTwoWayVariationMin,hwMplsTpOamDelayMeasureStatisticTwoWayVariationMax,
                      hwMplsTpOamDelayMeasureStatisticTwoWayVariationAverage,hwMplsTpOamMeasureStatisticTestPacketNum
                    }
            STATUS obsolete
            DESCRIPTION
                "The group for statistics function."
            ::= { hwMplsTpOamGroups 4 }

        hwMplsTpOamInterfaceAisGroup OBJECT-GROUP
            OBJECTS { hwMplsTpOamInterfaceAisInterfaceName,hwMplsTpOamInterfaceAisEnable,hwMplsTpOamInterfaceAisInterval,
                      hwMplsTpOamInterfaceAisExp,hwMplsTpOamInterfaceAisRowStatus
                    }
            STATUS obsolete
            DESCRIPTION
                "The group for AIS function in the interface."
            ::= { hwMplsTpOamGroups 5 }

        hwMplsTpOamLookupGroup OBJECT-GROUP
            OBJECTS { hwMplsTpOamMegTeInterfaceName,hwMplsTpOamTeMeIndex,hwMplsTpOamTeMegId,
                      hwMplsTpOamMegVllPeerip,hwMplsTpOamMegVcType,hwMplsTpOamMegVcId,hwMplsTpOamVllMegId,
                      hwMplsTpOamVllMeIndex,hwMplsTpOamMegSectionInterfaceName,
                      hwMplsTpOamSectionMegId,hwMplsTpOamSectionMeIndex
                    }
            STATUS obsolete
            DESCRIPTION
                "The group for lookup."
            ::= { hwMplsTpOamGroups 6 }

        hwMplsTpOamNotificationGroup NOTIFICATION-GROUP
            NOTIFICATIONS { hwMplsTpOamLossOfConnection,hwMplsTpOamLossOfConnectionRecovery,hwMplsTpOamRemoteDefectIndication,
                            hwMplsTpOamRemoteDefectIndicationRecovery,hwMplsTpOamUnExpectMeg,hwMplsTpOamUnExpectMegRecovery,
                            hwMplsTpOamUnExpectMep,hwMplsTpOamUnExpectMepRecovery,hwMplsTpOamUnExpectPeriod,
                            hwMplsTpOamUnExpectPeriodRecovery,hwMplsTpOamUnExpectPhb,hwMplsTpOamUnExpectPhbRecovery,
                            hwMplsTpOamAlarmIndicationSignal,hwMplsTpOamAlarmIndicationSignalRecovery,hwMplsTpOamNearDualLossSD1,
                            hwMplsTpOamNearDualLossSD1Recovery,hwMplsTpOamFarDualLossSD1,hwMplsTpOamFarDualLossSD1Recovery,
                            hwMplsTpOamNearDualLossSD2,hwMplsTpOamNearDualLossSD2Recovery,hwMplsTpOamFarDualLossSD2,
                            hwMplsTpOamFarDualLossSD2Recovery,hwMplsTpOamLCK,hwMplsTpOamLCKRecovery,
                            hwMplsTpOamCSF,hwMplsTpOamCSFRecovery,hwMplsTpOamUnExpectMegLevel,
                            hwMplsTpOamUnExpectMegLevelRecovery,hwMplsTpOamSectionLossOfConnection,hwMplsTpOamSectionLossOfConnectionRecovery,
                            hwMplsTpOamSectionRemoteDefectIndication,hwMplsTpOamSectionRemoteDefectIndicationRecovery,
                            hwMplsTpOamSectionUnExpectMeg,hwMplsTpOamSectionUnExpectMegRecovery,
                            hwMplsTpOamSectionUnExpectMep,hwMplsTpOamSectionUnExpectMepRecovery,hwMplsTpOamSectionUnExpectPeriod,
                            hwMplsTpOamSectionUnExpectPeriodRecovery,hwMplsTpOamSectionUnExpectPhb,hwMplsTpOamSectionUnExpectPhbRecovery,
                            hwMplsTpOamSectionNearDualLossSD1,
                            hwMplsTpOamSectionNearDualLossSD1Recovery,hwMplsTpOamSectionFarDualLossSD1,hwMplsTpOamSectionFarDualLossSD1Recovery,
                            hwMplsTpOamSectionNearDualLossSD2,hwMplsTpOamSectionNearDualLossSD2Recovery,hwMplsTpOamSectionFarDualLossSD2,
                            hwMplsTpOamSectionFarDualLossSD2Recovery,hwMplsTpOamSectionLCK,hwMplsTpOamSectionLCKRecovery,
                            hwMplsTpOamSectionUnExpectMegLevel,
                            hwMplsTpOamSectionUnExpectMegLevelRecovery,hwMplsTpOamSectionLocalLock,hwMplsTpOamSectionLocalLockRecovery,
                            hwMplsTpOamLocalLock,hwMplsTpOamLocalLockRecovery,hwMplsTpOamIpMegPingTrap,hwMplsTpOamIpMegTracertTrap
                            }
            STATUS current
            DESCRIPTION
                "The group for notification."
            ::= { hwMplsTpOamGroups 7 }

       hwMplsTpOamScalarsGroup OBJECT-GROUP
            OBJECTS { hwMplsTpOamMode }
            STATUS obsolete
            DESCRIPTION
                "The group for mpls-tp oam."
            ::= { hwMplsTpOamGroups 8 }

       hwMplsTpOamTstGroup OBJECT-GROUP
            OBJECTS {hwMplsTpOamTstState,
                     hwMplsTpOamTstCount,
                     hwMplsTpOamTstExp,
                     hwMplsTpOamTstInterval,
                     hwMplsTpOamTstHardwareBasedEnable,
                     hwMplsTpOamTstRate,
                     hwMplsTpOamTstBlockFlowEnable
                    }
            STATUS obsolete
            DESCRIPTION
                "The group for Test Function."
            ::= { hwMplsTpOamGroups 9 }

        hwMplsTpOamDualLossLossRatioGroup OBJECT-GROUP
            OBJECTS { hwMplsTpOamDualLossLossRatio }
            STATUS obsolete
            DESCRIPTION
                "The group for DualLossLossRatio notify."
            ::= { hwMplsTpOamGroups 10 }
    END
