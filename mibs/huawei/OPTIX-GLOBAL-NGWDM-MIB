--
-- OPTIX-SONET-DataPm-MIB.mib
-- MIB generated by MG-SOFT Visual MIB Builder Version 3.0 Build 253
-- Monday, March 06, 2006 at 10:26:16
--
            -- =================================================================
--  Copyright (C) 2006 by HUAWEI TECHNOLOGIES. All rights reserved
--
--  Description:This MIB describes the DataPmformance interface of Huawei SONET transmit
--  Reference:
--  Version: V1.00
--  History:
-- 	<author>,<date>,<contents>
-- =================================================================
--

	OPTIX-GLOBAL-NGWDM-MIB DEFINITIONS ::= BEGIN

		IMPORTS
			optixCommonGlobal
				FROM OPTIX-OID-MIB
			MOD2Type, PerformanceEventType, ValidflagType, ObjType, DataPmEventType
				FROM OPTIX-GLOBAL-TC-MIB
			OBJECT-GROUP, MODULE-COMPLIANCE
				FROM SNMPv2-CONF
			Integer32, Unsigned32, OBJECT-TYPE, MODULE-IDENTITY
				FROM SNMPv2-SMI
			DateAndTime, DisplayString
				FROM SNMPv2-TC;


		optixGlobalNGWDM MODULE-IDENTITY
			LAST-UPDATED "201105010000Z"
			ORGANIZATION
				"Huawei Technologies co.,Ltd."
			CONTACT-INFO
				"R&D Building
				Huawei Technologies Co., Ltd.
				Bantian, Longgang District
				Shenzhen, P. R. China
				http://www.huawei.com
				Zip:518129
				E-mail:support@huawei.com"
			DESCRIPTION
				"Description."
			REVISION "201105010000Z"
			DESCRIPTION
				"The initial revision of this MIB module."
			::= { optixCommonGlobal 50 }



--
-- Node definitions
--

--  Alarm data
        -- 1.3.6.1.4.1.2011.2.25.3.40.50.20.20
        ne OBJECT IDENTIFIER ::= { optixGlobalNGWDM 20 }

-- -------------------------------------------------------------------------
-- Perfomance 15-MIN Current Data Table (RTRV-PER-<MOD2>)
-- -------------------------------------------------------------------------
        -- 1.3.6.1.4.1.2011.2.25.3.40.50.20.10
        nePer15mCurTable OBJECT-TYPE
            SYNTAX SEQUENCE OF NePer15mCurEntry
            MAX-ACCESS not-accessible
            STATUS current
            DESCRIPTION
                "nePer15mCur."
            ::= { ne 10 }

        -- 1.3.6.1.4.1.2011.2.25.3.40.50.20.10.1
        nePer15mCurEntry OBJECT-TYPE
            SYNTAX NePer15mCurEntry
            MAX-ACCESS not-accessible
            STATUS current
            DESCRIPTION
                "nePer15mCur."
            INDEX {nePer15mCurEid, nePer15mCurPara}
            ::= { nePer15mCurTable 1 }

        NePer15mCurEntry ::=
            SEQUENCE {
                nePer15mCurEid
                    PerformanceEventType,
                nePer15mCurMonValue
                    OCTET STRING,
                nePer15mCurVldty
                    INTEGER,
                nePer15mCurDateTime
                    DateAndTime,
                nePer15mCurParaLen
                    INTEGER,
                nePer15mCurPara
                    OCTET STRING
             }

        -- 1.3.6.1.4.1.2011.2.25.3.40.50.20.10.1.1
        nePer15mCurEid OBJECT-TYPE
            SYNTAX PerformanceEventType
            MAX-ACCESS read-only
            STATUS current
            DESCRIPTION
                "perEid."
            ::= { nePer15mCurEntry 1 }

        -- 1.3.6.1.4.1.2011.2.25.3.40.50.20.10.1.2
        nePer15mCurMonValue OBJECT-TYPE
            SYNTAX OCTET STRING (SIZE (0..100))
            MAX-ACCESS read-only
            STATUS current
            DESCRIPTION
                "perMonValue."
            ::= { nePer15mCurEntry 2 }

        -- 1.3.6.1.4.1.2011.2.25.3.40.50.20.10.3
        nePer15mCurVldty OBJECT-TYPE
            SYNTAX INTEGER
            MAX-ACCESS read-only
            STATUS current
            DESCRIPTION
                "perVldty. "
            ::= { nePer15mCurEntry 3 }

        -- 1.3.6.1.4.1.2011.2.25.3.40.50.20.10.1.4
        nePer15mCurDateTime OBJECT-TYPE
            SYNTAX DateAndTime
            MAX-ACCESS read-only
            STATUS current
            DESCRIPTION
                "perDateTime. "
            ::= { nePer15mCurEntry 4 }

        -- 1.3.6.1.4.1.2011.2.25.3.40.50.20.10.1.5
        nePer15mCurParaLen OBJECT-TYPE
            SYNTAX INTEGER
            MAX-ACCESS read-only
            STATUS current
            DESCRIPTION
                "perParaLen."
            ::= { nePer15mCurEntry 5 }

        -- 1.3.6.1.4.1.2011.2.25.3.40.50.20.10.1.6
        nePer15mCurPara OBJECT-TYPE
            SYNTAX OCTET STRING (SIZE (0..100))
            MAX-ACCESS read-only
            STATUS current
            DESCRIPTION
                "perPara."
            ::= { nePer15mCurEntry 6 }


-- Alarm data
      -- 1.3.6.1.4.1.2011.2.25.3.40.50.82
      apsgroup OBJECT IDENTIFIER ::={ optixGlobalNGWDM 82 }


-- -------------------------------------------------------------------------
-- Perfomance 15-MIN Current Data Table (RTRV-PER-<MOD2>)
-- -------------------------------------------------------------------------
        -- 1.3.6.1.4.1.2011.2.25.3.40.50.82.10
        apsgroupPer15MCurTable OBJECT-TYPE
            SYNTAX SEQUENCE OF ApsgroupPer15MCurEntry
            MAX-ACCESS not-accessible
            STATUS current
            DESCRIPTION
                "apsgroupPer15MCur."
            ::= { apsgroup 10 }

        -- 1.3.6.1.4.1.2011.2.25.3.40.50.82.10.1
        apsgroupPer15MCurEntry OBJECT-TYPE
            SYNTAX ApsgroupPer15MCurEntry
            MAX-ACCESS not-accessible
            STATUS current
            DESCRIPTION
              "apsgroupPer15MCur."
            INDEX { apsgroupPer15MCurEid, apsgroupPer15MCurPara }
            ::= { apsgroupPer15MCurTable 1 }

        ApsgroupPer15MCurEntry ::=
            SEQUENCE {
                apsgroupPer15MCurEid
                    PerformanceEventType,
                apsgroupPer15MCurMonValue
                    OCTET STRING,
                apsgroupPer15MCurVldty
                    INTEGER,
                apsgroupPer15MCurDateTime
                    DateAndTime,
                apsgroupPer15MCurParaLen
                    INTEGER,
                apsgroupPer15MCurPara
                    OCTET STRING
            }

        -- 1.3.6.1.4.1.2011.2.25.3.40.50.82.10.1.1
        apsgroupPer15MCurEid OBJECT-TYPE
            SYNTAX PerformanceEventType
            MAX-ACCESS read-only
            STATUS current
            DESCRIPTION
                "perEid."
            ::= { apsgroupPer15MCurEntry 1 }

        -- 1.3.6.1.4.1.2011.2.25.3.40.50.82.10.1.2
        apsgroupPer15MCurMonValue OBJECT-TYPE
            SYNTAX OCTET STRING (SIZE (0..100))
            MAX-ACCESS read-only
            STATUS current
            DESCRIPTION
                "perMonValue."
            ::= { apsgroupPer15MCurEntry 2 }

        -- 1.3.6.1.4.1.2011.2.25.3.40.50.82.10.1.3
        apsgroupPer15MCurVldty OBJECT-TYPE
            SYNTAX INTEGER
            MAX-ACCESS read-only
            STATUS current
            DESCRIPTION
                "perVldty. "
            ::= { apsgroupPer15MCurEntry 3 }

        -- 1.3.6.1.4.1.2011.2.25.3.40.50.82.10.1.4
        apsgroupPer15MCurDateTime OBJECT-TYPE
            SYNTAX DateAndTime
            MAX-ACCESS read-only
            STATUS current
            DESCRIPTION
                "perDateTime. "
            ::= { apsgroupPer15MCurEntry 4 }

        -- 1.3.6.1.4.1.2011.2.25.3.40.50.82.10.1.5
        apsgroupPer15MCurParaLen OBJECT-TYPE
            SYNTAX INTEGER
            MAX-ACCESS read-only
            STATUS current
            DESCRIPTION
                "perParaLen."
            ::= { apsgroupPer15MCurEntry 5 }

        -- 1.3.6.1.4.1.2011.2.25.3.40.50.82.10.1.6
        apsgroupPer15MCurPara OBJECT-TYPE
            SYNTAX OCTET STRING (SIZE (0..100))
            MAX-ACCESS read-only
            STATUS current
            DESCRIPTION
                "perPara."
            ::= { apsgroupPer15MCurEntry 6 }



-- -------------------------------------------------------------------------
-- Perfomance 15-MIN History Data Table (RTRV-PER-<MOD2>)
-- -------------------------------------------------------------------------
        -- 1.3.6.1.4.1.2011.2.25.3.40.50.82.20
        apsgroupPer15MHisTable OBJECT-TYPE
            SYNTAX SEQUENCE OF ApsgroupPer15MHisEntry
            MAX-ACCESS not-accessible
            STATUS current
            DESCRIPTION
                "apsgroupPer15MHis."
            ::= { apsgroup 20 }

        -- 1.3.6.1.4.1.2011.2.25.3.40.50.82.20.1
        apsgroupPer15MHisEntry OBJECT-TYPE
            SYNTAX ApsgroupPer15MHisEntry
            MAX-ACCESS not-accessible
            STATUS current
            DESCRIPTION
                "apsgroupPer15MHis."
            INDEX {apsgroupPer15MHisEid, apsgroupPer15MHisParaLen, apsgroupPer15MHisPara, apsgroupPer15MHisDateTimeStart, apsgroupPer15MHisDateTimeEnd}
            ::= { apsgroupPer15MHisTable 1 }

        ApsgroupPer15MHisEntry ::=
            SEQUENCE {
                apsgroupPer15MHisEid
                    PerformanceEventType,
                apsgroupPer15MHisParaLen
                    INTEGER,
                apsgroupPer15MHisPara
                    OCTET STRING,
                apsgroupPer15MHisMonValue
                    OCTET STRING,
                apsgroupPer15MHisDateTimeStart
                    DateAndTime,
                apsgroupPer15MHisDateTimeEnd
                    DateAndTime,
                apsgroupPer15MHisVldty
                    INTEGER,
             }

        -- 1.3.6.1.4.1.2011.2.25.3.40.50.82.20.1.1
        apsgroupPer15MHisEid OBJECT-TYPE
            SYNTAX PerformanceEventType
            MAX-ACCESS read-only
            STATUS current
            DESCRIPTION
                "perEid."
            ::= { apsgroupPer15MHisEntry 1 }

        -- 1.3.6.1.4.1.2011.2.25.3.40.50.82.20.1.2
        apsgroupPer15MHisParaLen OBJECT-TYPE
            SYNTAX INTEGER
            MAX-ACCESS read-only
            STATUS current
            DESCRIPTION
                "perParaLen."
            ::= { apsgroupPer15MHisEntry 2 }

        -- 1.3.6.1.4.1.2011.2.25.3.40.50.82.20.1.3
        apsgroupPer15MHisPara OBJECT-TYPE
            SYNTAX OCTET STRING (SIZE (0..100))
            MAX-ACCESS read-only
            STATUS current
            DESCRIPTION
                "perPara."
            ::= { apsgroupPer15MHisEntry 3 }

        -- 1.3.6.1.4.1.2011.2.25.3.40.50.82.20.1.4
        apsgroupPer15MHisMonValue OBJECT-TYPE
            SYNTAX OCTET STRING (SIZE (0..100))
            MAX-ACCESS read-only
            STATUS current
            DESCRIPTION
                "perMonValue."
            ::= { apsgroupPer15MHisEntry 4 }

        -- 1.3.6.1.4.1.2011.2.25.3.40.50.82.20.1.5
        apsgroupPer15MHisDateTimeStart OBJECT-TYPE
            SYNTAX DateAndTime
            MAX-ACCESS read-only
            STATUS current
            DESCRIPTION
                "perDateTimeStart. "
            ::= { apsgroupPer15MHisEntry 5 }

        -- 1.3.6.1.4.1.2011.2.25.3.40.50.82.20.1.6
        apsgroupPer15MHisDateTimeEnd OBJECT-TYPE
            SYNTAX DateAndTime
            MAX-ACCESS read-only
            STATUS current
            DESCRIPTION
                "perDateTimeEnd. "
            ::= { apsgroupPer15MHisEntry 6 }

        -- 1.3.6.1.4.1.2011.2.25.3.40.50.82.20.1.7
        apsgroupPer15MHisVldty OBJECT-TYPE
            SYNTAX INTEGER
            MAX-ACCESS read-only
            STATUS current
            DESCRIPTION
                "perVldty. "
            ::= { apsgroupPer15MHisEntry 7 }




-- -------------------------------------------------------------------------
-- Perfomance 24-HOUR Current Data Table (RTRV-PER-<MOD2>)
-- -------------------------------------------------------------------------
        -- 1.3.6.1.4.1.2011.2.25.3.40.50.82.30
        apsgroupPer24HCurTable OBJECT-TYPE
          SYNTAX SEQUENCE OF ApsgroupPer24HCurEntry
          MAX-ACCESS not-accessible
          STATUS current
          DESCRIPTION
              "apsgroupPer24HCur."
          ::= { apsgroup 30 }

        -- 1.3.6.1.4.1.2011.2.25.3.40.50.82.30.1
        apsgroupPer24HCurEntry OBJECT-TYPE
            SYNTAX ApsgroupPer24HCurEntry
            MAX-ACCESS not-accessible
            STATUS current
            DESCRIPTION
              "apsgroupPer24HCur."
            INDEX { apsgroupPer24HCurEid, apsgroupPer24HCurPara }
            ::= { apsgroupPer24HCurTable 1 }

        ApsgroupPer24HCurEntry ::=
            SEQUENCE {
                apsgroupPer24HCurEid
                    PerformanceEventType,
                apsgroupPer24HCurMonValue
                    OCTET STRING,
                apsgroupPer24HCurVldty
                    INTEGER,
                apsgroupPer24HCurDateTime
                    DateAndTime,
                apsgroupPer24HCurParaLen
                    INTEGER,
                apsgroupPer24HCurPara
                    OCTET STRING
            }

        -- 1.3.6.1.4.1.2011.2.25.3.40.50.82.30.1.1
        apsgroupPer24HCurEid OBJECT-TYPE
            SYNTAX PerformanceEventType
            MAX-ACCESS read-only
            STATUS current
            DESCRIPTION
                "perEid."
            ::= { apsgroupPer24HCurEntry 1 }

        -- 1.3.6.1.4.1.2011.2.25.3.40.50.82.30.1.2
        apsgroupPer24HCurMonValue OBJECT-TYPE
            SYNTAX OCTET STRING (SIZE (0..100))
            MAX-ACCESS read-only
            STATUS current
            DESCRIPTION
                "perMonValue."
            ::= { apsgroupPer24HCurEntry 2 }

        -- 1.3.6.1.4.1.2011.2.25.3.40.50.82.30.1.3
        apsgroupPer24HCurVldty OBJECT-TYPE
            SYNTAX INTEGER
            MAX-ACCESS read-only
            STATUS current
            DESCRIPTION
                "perVldty. "
            ::= { apsgroupPer24HCurEntry 3 }

        -- 1.3.6.1.4.1.2011.2.25.3.40.50.82.30.1.4
        apsgroupPer24HCurDateTime OBJECT-TYPE
            SYNTAX DateAndTime
            MAX-ACCESS read-only
            STATUS current
            DESCRIPTION
                "perDateTime. "
            ::= { apsgroupPer24HCurEntry 4 }

        -- 1.3.6.1.4.1.2011.2.25.3.40.50.82.30.1.5
        apsgroupPer24HCurParaLen OBJECT-TYPE
            SYNTAX INTEGER
            MAX-ACCESS read-only
            STATUS current
            DESCRIPTION
                "perParaLen."
            ::= { apsgroupPer24HCurEntry 5 }

        -- 1.3.6.1.4.1.2011.2.25.3.40.50.82.30.1.6
        apsgroupPer24HCurPara OBJECT-TYPE
            SYNTAX OCTET STRING (SIZE (0..100))
            MAX-ACCESS read-only
            STATUS current
            DESCRIPTION
                "perPara."
            ::= { apsgroupPer24HCurEntry 6 }




-- -------------------------------------------------------------------------
-- Perfomance 24-HOUR History Data Table (RTRV-PER-<MOD2>)
-- -------------------------------------------------------------------------
        -- 1.3.6.1.4.1.2011.2.25.3.40.50.82.40
        apsgroupPer24HHisTable OBJECT-TYPE
          SYNTAX SEQUENCE OF ApsgroupPer24HHisEntry
          MAX-ACCESS not-accessible
          STATUS current
          DESCRIPTION
              "apsgroupPer24HHis."
          ::= { apsgroup 40 }

        -- 1.3.6.1.4.1.2011.2.25.3.40.50.82.40.1
        apsgroupPer24HHisEntry OBJECT-TYPE
            SYNTAX ApsgroupPer24HHisEntry
            MAX-ACCESS not-accessible
            STATUS current
            DESCRIPTION
                "apsgroupPer24HHis."
            INDEX {apsgroupPer24HHisEid, apsgroupPer24HHisParaLen, apsgroupPer24HHisPara, apsgroupPer24HHisDateTimeStart, apsgroupPer24HHisDateTimeEnd}
            ::= { apsgroupPer24HHisTable 1 }

        ApsgroupPer24HHisEntry ::=
            SEQUENCE {
                apsgroupPer24HHisEid
                    PerformanceEventType,
                apsgroupPer24HHisParaLen
                    INTEGER,
                apsgroupPer24HHisPara
                    OCTET STRING,
                apsgroupPer24HHisMonValue
                    OCTET STRING,
                apsgroupPer24HHisDateTimeStart
                    DateAndTime,
                apsgroupPer24HHisDateTimeEnd
                    DateAndTime,
                apsgroupPer24HHisVldty
                    INTEGER,
             }

        -- 1.3.6.1.4.1.2011.2.25.3.40.50.82.40.1.1
        apsgroupPer24HHisEid OBJECT-TYPE
            SYNTAX PerformanceEventType
            MAX-ACCESS read-only
            STATUS current
            DESCRIPTION
                "perEid."
            ::= { apsgroupPer24HHisEntry 1 }

        -- 1.3.6.1.4.1.2011.2.25.3.40.50.82.40.1.2
        apsgroupPer24HHisParaLen OBJECT-TYPE
            SYNTAX INTEGER
            MAX-ACCESS read-only
            STATUS current
            DESCRIPTION
                "perParaLen."
            ::= { apsgroupPer24HHisEntry 2 }

        -- 1.3.6.1.4.1.2011.2.25.3.40.50.82.40.1.3
        apsgroupPer24HHisPara OBJECT-TYPE
            SYNTAX OCTET STRING (SIZE (0..100))
            MAX-ACCESS read-only
            STATUS current
            DESCRIPTION
                "perPara."
            ::= { apsgroupPer24HHisEntry 3 }

        -- 1.3.6.1.4.1.2011.2.25.3.40.50.82.40.1.4
        apsgroupPer24HHisMonValue OBJECT-TYPE
            SYNTAX OCTET STRING (SIZE (0..100))
            MAX-ACCESS read-only
            STATUS current
            DESCRIPTION
                "perMonValue."
            ::= { apsgroupPer24HHisEntry 4 }

        -- 1.3.6.1.4.1.2011.2.25.3.40.50.82.40.1.5
        apsgroupPer24HHisDateTimeStart OBJECT-TYPE
            SYNTAX DateAndTime
            MAX-ACCESS read-only
            STATUS current
            DESCRIPTION
                "perDateTimeStart. "
            ::= { apsgroupPer24HHisEntry 5 }

        -- 1.3.6.1.4.1.2011.2.25.3.40.50.82.40.1.6
        apsgroupPer24HHisDateTimeEnd OBJECT-TYPE
            SYNTAX DateAndTime
            MAX-ACCESS read-only
            STATUS current
            DESCRIPTION
                "perDateTimeEnd. "
            ::= { apsgroupPer24HHisEntry 6 }

        -- 1.3.6.1.4.1.2011.2.25.3.40.50.82.40.1.7
        apsgroupPer24HHisVldty OBJECT-TYPE
            SYNTAX INTEGER
            MAX-ACCESS read-only
            STATUS current
            DESCRIPTION
                "perVldty. "
            ::= { apsgroupPer24HHisEntry 7 }


-- Alarm data
      -- 1.3.6.1.4.1.2011.2.25.3.40.50.83
      tpsgroup OBJECT IDENTIFIER ::={ optixGlobalNGWDM 83 }


-- -------------------------------------------------------------------------
-- Perfomance 15-MIN Current Data Table (RTRV-PER-<MOD2>)
-- -------------------------------------------------------------------------
        -- 1.3.6.1.4.1.2011.2.25.3.40.50.83.10
        tpsgroupPer15MCurTable OBJECT-TYPE
            SYNTAX SEQUENCE OF TpsgroupPer15MCurEntry
            MAX-ACCESS not-accessible
            STATUS current
            DESCRIPTION
                "tpsgroupPer15MCur."
            ::= { tpsgroup 10 }

        -- 1.3.6.1.4.1.2011.2.25.3.40.50.83.10.1
        tpsgroupPer15MCurEntry OBJECT-TYPE
            SYNTAX TpsgroupPer15MCurEntry
            MAX-ACCESS not-accessible
            STATUS current
            DESCRIPTION
              "tpsgroupPer15MCur."
            INDEX { tpsgroupPer15MCurEid, tpsgroupPer15MCurPara }
            ::= { tpsgroupPer15MCurTable 1 }

        TpsgroupPer15MCurEntry ::=
            SEQUENCE {
                tpsgroupPer15MCurEid
                    PerformanceEventType,
                tpsgroupPer15MCurMonValue
                    OCTET STRING,
                tpsgroupPer15MCurVldty
                    INTEGER,
                tpsgroupPer15MCurDateTime
                    DateAndTime,
                tpsgroupPer15MCurParaLen
                    INTEGER,
                tpsgroupPer15MCurPara
                    OCTET STRING
            }

        -- 1.3.6.1.4.1.2011.2.25.3.40.50.83.10.1.1
        tpsgroupPer15MCurEid OBJECT-TYPE
            SYNTAX PerformanceEventType
            MAX-ACCESS read-only
            STATUS current
            DESCRIPTION
                "perEid."
            ::= { tpsgroupPer15MCurEntry 1 }

        -- 1.3.6.1.4.1.2011.2.25.3.40.50.83.10.1.2
        tpsgroupPer15MCurMonValue OBJECT-TYPE
            SYNTAX OCTET STRING (SIZE (0..100))
            MAX-ACCESS read-only
            STATUS current
            DESCRIPTION
                "perMonValue."
            ::= { tpsgroupPer15MCurEntry 2 }

        -- 1.3.6.1.4.1.2011.2.25.3.40.50.83.10.1.3
        tpsgroupPer15MCurVldty OBJECT-TYPE
            SYNTAX INTEGER
            MAX-ACCESS read-only
            STATUS current
            DESCRIPTION
                "perVldty. "
            ::= { tpsgroupPer15MCurEntry 3 }

        -- 1.3.6.1.4.1.2011.2.25.3.40.50.83.10.1.4
        tpsgroupPer15MCurDateTime OBJECT-TYPE
            SYNTAX DateAndTime
            MAX-ACCESS read-only
            STATUS current
            DESCRIPTION
                "perDateTime. "
            ::= { tpsgroupPer15MCurEntry 4 }

        -- 1.3.6.1.4.1.2011.2.25.3.40.50.83.10.1.5
        tpsgroupPer15MCurParaLen OBJECT-TYPE
            SYNTAX INTEGER
            MAX-ACCESS read-only
            STATUS current
            DESCRIPTION
                "perParaLen."
            ::= { tpsgroupPer15MCurEntry 5 }

        -- 1.3.6.1.4.1.2011.2.25.3.40.50.83.10.1.6
        tpsgroupPer15MCurPara OBJECT-TYPE
            SYNTAX OCTET STRING (SIZE (0..100))
            MAX-ACCESS read-only
            STATUS current
            DESCRIPTION
                "perPara."
            ::= { tpsgroupPer15MCurEntry 6 }



-- -------------------------------------------------------------------------
-- Perfomance 15-MIN History Data Table (RTRV-PER-<MOD2>)
-- -------------------------------------------------------------------------
        -- 1.3.6.1.4.1.2011.2.25.3.40.50.83.20
        tpsgroupPer15MHisTable OBJECT-TYPE
            SYNTAX SEQUENCE OF TpsgroupPer15MHisEntry
            MAX-ACCESS not-accessible
            STATUS current
            DESCRIPTION
                "tpsgroupPer15MHis."
            ::= { tpsgroup 20 }

        -- 1.3.6.1.4.1.2011.2.25.3.40.50.83.20.1
        tpsgroupPer15MHisEntry OBJECT-TYPE
            SYNTAX TpsgroupPer15MHisEntry
            MAX-ACCESS not-accessible
            STATUS current
            DESCRIPTION
                "tpsgroupPer15MHis."
            INDEX {tpsgroupPer15MHisEid, tpsgroupPer15MHisParaLen, tpsgroupPer15MHisPara, tpsgroupPer15MHisDateTimeStart, tpsgroupPer15MHisDateTimeEnd}
            ::= { tpsgroupPer15MHisTable 1 }

        TpsgroupPer15MHisEntry ::=
            SEQUENCE {
                tpsgroupPer15MHisEid
                    PerformanceEventType,
                tpsgroupPer15MHisParaLen
                    INTEGER,
                tpsgroupPer15MHisPara
                    OCTET STRING,
                tpsgroupPer15MHisMonValue
                    OCTET STRING,
                tpsgroupPer15MHisDateTimeStart
                    DateAndTime,
                tpsgroupPer15MHisDateTimeEnd
                    DateAndTime,
                tpsgroupPer15MHisVldty
                    INTEGER,
             }

        -- 1.3.6.1.4.1.2011.2.25.3.40.50.83.20.1.1
        tpsgroupPer15MHisEid OBJECT-TYPE
            SYNTAX PerformanceEventType
            MAX-ACCESS read-only
            STATUS current
            DESCRIPTION
                "perEid."
            ::= { tpsgroupPer15MHisEntry 1 }

        -- 1.3.6.1.4.1.2011.2.25.3.40.50.83.20.1.2
        tpsgroupPer15MHisParaLen OBJECT-TYPE
            SYNTAX INTEGER
            MAX-ACCESS read-only
            STATUS current
            DESCRIPTION
                "perParaLen."
            ::= { tpsgroupPer15MHisEntry 2 }

        -- 1.3.6.1.4.1.2011.2.25.3.40.50.83.20.1.3
        tpsgroupPer15MHisPara OBJECT-TYPE
            SYNTAX OCTET STRING (SIZE (0..100))
            MAX-ACCESS read-only
            STATUS current
            DESCRIPTION
                "perPara."
            ::= { tpsgroupPer15MHisEntry 3 }

        -- 1.3.6.1.4.1.2011.2.25.3.40.50.83.20.1.4
        tpsgroupPer15MHisMonValue OBJECT-TYPE
            SYNTAX OCTET STRING (SIZE (0..100))
            MAX-ACCESS read-only
            STATUS current
            DESCRIPTION
                "perMonValue."
            ::= { tpsgroupPer15MHisEntry 4 }

        -- 1.3.6.1.4.1.2011.2.25.3.40.50.83.20.1.5
        tpsgroupPer15MHisDateTimeStart OBJECT-TYPE
            SYNTAX DateAndTime
            MAX-ACCESS read-only
            STATUS current
            DESCRIPTION
                "perDateTimeStart. "
            ::= { tpsgroupPer15MHisEntry 5 }

        -- 1.3.6.1.4.1.2011.2.25.3.40.50.83.20.1.6
        tpsgroupPer15MHisDateTimeEnd OBJECT-TYPE
            SYNTAX DateAndTime
            MAX-ACCESS read-only
            STATUS current
            DESCRIPTION
                "perDateTimeEnd. "
            ::= { tpsgroupPer15MHisEntry 6 }

        -- 1.3.6.1.4.1.2011.2.25.3.40.50.83.20.1.7
        tpsgroupPer15MHisVldty OBJECT-TYPE
            SYNTAX INTEGER
            MAX-ACCESS read-only
            STATUS current
            DESCRIPTION
                "perVldty. "
            ::= { tpsgroupPer15MHisEntry 7 }




-- -------------------------------------------------------------------------
-- Perfomance 24-HOUR Current Data Table (RTRV-PER-<MOD2>)
-- -------------------------------------------------------------------------
        -- 1.3.6.1.4.1.2011.2.25.3.40.50.83.30
        tpsgroupPer24HCurTable OBJECT-TYPE
          SYNTAX SEQUENCE OF TpsgroupPer24HCurEntry
          MAX-ACCESS not-accessible
          STATUS current
          DESCRIPTION
              "tpsgroupPer24HCur."
          ::= { tpsgroup 30 }

        -- 1.3.6.1.4.1.2011.2.25.3.40.50.83.30.1
        tpsgroupPer24HCurEntry OBJECT-TYPE
            SYNTAX TpsgroupPer24HCurEntry
            MAX-ACCESS not-accessible
            STATUS current
            DESCRIPTION
              "tpsgroupPer24HCur."
            INDEX { tpsgroupPer24HCurEid, tpsgroupPer24HCurPara }
            ::= { tpsgroupPer24HCurTable 1 }

        TpsgroupPer24HCurEntry ::=
            SEQUENCE {
                tpsgroupPer24HCurEid
                    PerformanceEventType,
                tpsgroupPer24HCurMonValue
                    OCTET STRING,
                tpsgroupPer24HCurVldty
                    INTEGER,
                tpsgroupPer24HCurDateTime
                    DateAndTime,
                tpsgroupPer24HCurParaLen
                    INTEGER,
                tpsgroupPer24HCurPara
                    OCTET STRING
            }

        -- 1.3.6.1.4.1.2011.2.25.3.40.50.83.30.1.1
        tpsgroupPer24HCurEid OBJECT-TYPE
            SYNTAX PerformanceEventType
            MAX-ACCESS read-only
            STATUS current
            DESCRIPTION
                "perEid."
            ::= { tpsgroupPer24HCurEntry 1 }

        -- 1.3.6.1.4.1.2011.2.25.3.40.50.83.30.1.2
        tpsgroupPer24HCurMonValue OBJECT-TYPE
            SYNTAX OCTET STRING (SIZE (0..100))
            MAX-ACCESS read-only
            STATUS current
            DESCRIPTION
                "perMonValue."
            ::= { tpsgroupPer24HCurEntry 2 }

        -- 1.3.6.1.4.1.2011.2.25.3.40.50.83.30.1.3
        tpsgroupPer24HCurVldty OBJECT-TYPE
            SYNTAX INTEGER
            MAX-ACCESS read-only
            STATUS current
            DESCRIPTION
                "perVldty. "
            ::= { tpsgroupPer24HCurEntry 3 }

        -- 1.3.6.1.4.1.2011.2.25.3.40.50.83.30.1.4
        tpsgroupPer24HCurDateTime OBJECT-TYPE
            SYNTAX DateAndTime
            MAX-ACCESS read-only
            STATUS current
            DESCRIPTION
                "perDateTime. "
            ::= { tpsgroupPer24HCurEntry 4 }

        -- 1.3.6.1.4.1.2011.2.25.3.40.50.83.30.1.5
        tpsgroupPer24HCurParaLen OBJECT-TYPE
            SYNTAX INTEGER
            MAX-ACCESS read-only
            STATUS current
            DESCRIPTION
                "perParaLen."
            ::= { tpsgroupPer24HCurEntry 5 }

        -- 1.3.6.1.4.1.2011.2.25.3.40.50.83.30.1.6
        tpsgroupPer24HCurPara OBJECT-TYPE
            SYNTAX OCTET STRING (SIZE (0..100))
            MAX-ACCESS read-only
            STATUS current
            DESCRIPTION
                "perPara."
            ::= { tpsgroupPer24HCurEntry 6 }




-- -------------------------------------------------------------------------
-- Perfomance 24-HOUR History Data Table (RTRV-PER-<MOD2>)
-- -------------------------------------------------------------------------
        -- 1.3.6.1.4.1.2011.2.25.3.40.50.83.40
        tpsgroupPer24HHisTable OBJECT-TYPE
          SYNTAX SEQUENCE OF TpsgroupPer24HHisEntry
          MAX-ACCESS not-accessible
          STATUS current
          DESCRIPTION
              "tpsgroupPer24HHis."
          ::= { tpsgroup 40 }

        -- 1.3.6.1.4.1.2011.2.25.3.40.50.83.40.1
        tpsgroupPer24HHisEntry OBJECT-TYPE
            SYNTAX TpsgroupPer24HHisEntry
            MAX-ACCESS not-accessible
            STATUS current
            DESCRIPTION
                "tpsgroupPer24HHis."
            INDEX {tpsgroupPer24HHisEid, tpsgroupPer24HHisParaLen, tpsgroupPer24HHisPara, tpsgroupPer24HHisDateTimeStart, tpsgroupPer24HHisDateTimeEnd}
            ::= { tpsgroupPer24HHisTable 1 }

        TpsgroupPer24HHisEntry ::=
            SEQUENCE {
                tpsgroupPer24HHisEid
                    PerformanceEventType,
                tpsgroupPer24HHisParaLen
                    INTEGER,
                tpsgroupPer24HHisPara
                    OCTET STRING,
                tpsgroupPer24HHisMonValue
                    OCTET STRING,
                tpsgroupPer24HHisDateTimeStart
                    DateAndTime,
                tpsgroupPer24HHisDateTimeEnd
                    DateAndTime,
                tpsgroupPer24HHisVldty
                    INTEGER,
             }

        -- 1.3.6.1.4.1.2011.2.25.3.40.50.83.40.1.1
        tpsgroupPer24HHisEid OBJECT-TYPE
            SYNTAX PerformanceEventType
            MAX-ACCESS read-only
            STATUS current
            DESCRIPTION
                "perEid."
            ::= { tpsgroupPer24HHisEntry 1 }

        -- 1.3.6.1.4.1.2011.2.25.3.40.50.83.40.1.2
        tpsgroupPer24HHisParaLen OBJECT-TYPE
            SYNTAX INTEGER
            MAX-ACCESS read-only
            STATUS current
            DESCRIPTION
                "perParaLen."
            ::= { tpsgroupPer24HHisEntry 2 }

        -- 1.3.6.1.4.1.2011.2.25.3.40.50.83.40.1.3
        tpsgroupPer24HHisPara OBJECT-TYPE
            SYNTAX OCTET STRING (SIZE (0..100))
            MAX-ACCESS read-only
            STATUS current
            DESCRIPTION
                "perPara."
            ::= { tpsgroupPer24HHisEntry 3 }

        -- 1.3.6.1.4.1.2011.2.25.3.40.50.83.40.1.4
        tpsgroupPer24HHisMonValue OBJECT-TYPE
            SYNTAX OCTET STRING (SIZE (0..100))
            MAX-ACCESS read-only
            STATUS current
            DESCRIPTION
                "perMonValue."
            ::= { tpsgroupPer24HHisEntry 4 }

        -- 1.3.6.1.4.1.2011.2.25.3.40.50.83.40.1.5
        tpsgroupPer24HHisDateTimeStart OBJECT-TYPE
            SYNTAX DateAndTime
            MAX-ACCESS read-only
            STATUS current
            DESCRIPTION
                "perDateTimeStart. "
            ::= { tpsgroupPer24HHisEntry 5 }

        -- 1.3.6.1.4.1.2011.2.25.3.40.50.83.40.1.6
        tpsgroupPer24HHisDateTimeEnd OBJECT-TYPE
            SYNTAX DateAndTime
            MAX-ACCESS read-only
            STATUS current
            DESCRIPTION
                "perDateTimeEnd. "
            ::= { tpsgroupPer24HHisEntry 6 }

        -- 1.3.6.1.4.1.2011.2.25.3.40.50.83.40.1.7
        tpsgroupPer24HHisVldty OBJECT-TYPE
            SYNTAX INTEGER
            MAX-ACCESS read-only
            STATUS current
            DESCRIPTION
                "perVldty. "
            ::= { tpsgroupPer24HHisEntry 7 }


-- Alarm data
      -- 1.3.6.1.4.1.2011.2.25.3.40.50.86
      synsource OBJECT IDENTIFIER ::={ optixGlobalNGWDM 86 }


-- -------------------------------------------------------------------------
-- Perfomance 15-MIN Current Data Table (RTRV-PER-<MOD2>)
-- -------------------------------------------------------------------------
        -- 1.3.6.1.4.1.2011.2.25.3.40.50.86.10
        synsourcePer15MCurTable OBJECT-TYPE
            SYNTAX SEQUENCE OF SynsourcePer15MCurEntry
            MAX-ACCESS not-accessible
            STATUS current
            DESCRIPTION
                "synsourcePer15MCur."
            ::= { synsource 10 }

        -- 1.3.6.1.4.1.2011.2.25.3.40.50.86.10.1
        synsourcePer15MCurEntry OBJECT-TYPE
            SYNTAX SynsourcePer15MCurEntry
            MAX-ACCESS not-accessible
            STATUS current
            DESCRIPTION
              "synsourcePer15MCur."
            INDEX { synsourcePer15MCurEid, synsourcePer15MCurPara }
            ::= { synsourcePer15MCurTable 1 }

        SynsourcePer15MCurEntry ::=
            SEQUENCE {
                synsourcePer15MCurEid
                    PerformanceEventType,
                synsourcePer15MCurMonValue
                    OCTET STRING,
                synsourcePer15MCurVldty
                    INTEGER,
                synsourcePer15MCurDateTime
                    DateAndTime,
                synsourcePer15MCurParaLen
                    INTEGER,
                synsourcePer15MCurPara
                    OCTET STRING
            }

        -- 1.3.6.1.4.1.2011.2.25.3.40.50.86.10.1.1
        synsourcePer15MCurEid OBJECT-TYPE
            SYNTAX PerformanceEventType
            MAX-ACCESS read-only
            STATUS current
            DESCRIPTION
                "perEid."
            ::= { synsourcePer15MCurEntry 1 }

        -- 1.3.6.1.4.1.2011.2.25.3.40.50.86.10.1.2
        synsourcePer15MCurMonValue OBJECT-TYPE
            SYNTAX OCTET STRING (SIZE (0..100))
            MAX-ACCESS read-only
            STATUS current
            DESCRIPTION
                "perMonValue."
            ::= { synsourcePer15MCurEntry 2 }

        -- 1.3.6.1.4.1.2011.2.25.3.40.50.86.10.1.3
        synsourcePer15MCurVldty OBJECT-TYPE
            SYNTAX INTEGER
            MAX-ACCESS read-only
            STATUS current
            DESCRIPTION
                "perVldty. "
            ::= { synsourcePer15MCurEntry 3 }

        -- 1.3.6.1.4.1.2011.2.25.3.40.50.86.10.1.4
        synsourcePer15MCurDateTime OBJECT-TYPE
            SYNTAX DateAndTime
            MAX-ACCESS read-only
            STATUS current
            DESCRIPTION
                "perDateTime. "
            ::= { synsourcePer15MCurEntry 4 }

        -- 1.3.6.1.4.1.2011.2.25.3.40.50.86.10.1.5
        synsourcePer15MCurParaLen OBJECT-TYPE
            SYNTAX INTEGER
            MAX-ACCESS read-only
            STATUS current
            DESCRIPTION
                "perParaLen."
            ::= { synsourcePer15MCurEntry 5 }

        -- 1.3.6.1.4.1.2011.2.25.3.40.50.86.10.1.6
        synsourcePer15MCurPara OBJECT-TYPE
            SYNTAX OCTET STRING (SIZE (0..100))
            MAX-ACCESS read-only
            STATUS current
            DESCRIPTION
                "perPara."
            ::= { synsourcePer15MCurEntry 6 }



-- -------------------------------------------------------------------------
-- Perfomance 15-MIN History Data Table (RTRV-PER-<MOD2>)
-- -------------------------------------------------------------------------
        -- 1.3.6.1.4.1.2011.2.25.3.40.50.86.20
        synsourcePer15MHisTable OBJECT-TYPE
            SYNTAX SEQUENCE OF SynsourcePer15MHisEntry
            MAX-ACCESS not-accessible
            STATUS current
            DESCRIPTION
                "synsourcePer15MHis."
            ::= { synsource 20 }

        -- 1.3.6.1.4.1.2011.2.25.3.40.50.86.20.1
        synsourcePer15MHisEntry OBJECT-TYPE
            SYNTAX SynsourcePer15MHisEntry
            MAX-ACCESS not-accessible
            STATUS current
            DESCRIPTION
                "synsourcePer15MHis."
            INDEX {synsourcePer15MHisEid, synsourcePer15MHisParaLen, synsourcePer15MHisPara, synsourcePer15MHisDateTimeStart, synsourcePer15MHisDateTimeEnd}
            ::= { synsourcePer15MHisTable 1 }

        SynsourcePer15MHisEntry ::=
            SEQUENCE {
                synsourcePer15MHisEid
                    PerformanceEventType,
                synsourcePer15MHisParaLen
                    INTEGER,
                synsourcePer15MHisPara
                    OCTET STRING,
                synsourcePer15MHisMonValue
                    OCTET STRING,
                synsourcePer15MHisDateTimeStart
                    DateAndTime,
                synsourcePer15MHisDateTimeEnd
                    DateAndTime,
                synsourcePer15MHisVldty
                    INTEGER,
             }

        -- 1.3.6.1.4.1.2011.2.25.3.40.50.86.20.1.1
        synsourcePer15MHisEid OBJECT-TYPE
            SYNTAX PerformanceEventType
            MAX-ACCESS read-only
            STATUS current
            DESCRIPTION
                "perEid."
            ::= { synsourcePer15MHisEntry 1 }

        -- 1.3.6.1.4.1.2011.2.25.3.40.50.86.20.1.2
        synsourcePer15MHisParaLen OBJECT-TYPE
            SYNTAX INTEGER
            MAX-ACCESS read-only
            STATUS current
            DESCRIPTION
                "perParaLen."
            ::= { synsourcePer15MHisEntry 2 }

        -- 1.3.6.1.4.1.2011.2.25.3.40.50.86.20.1.3
        synsourcePer15MHisPara OBJECT-TYPE
            SYNTAX OCTET STRING (SIZE (0..100))
            MAX-ACCESS read-only
            STATUS current
            DESCRIPTION
                "perPara."
            ::= { synsourcePer15MHisEntry 3 }

        -- 1.3.6.1.4.1.2011.2.25.3.40.50.86.20.1.4
        synsourcePer15MHisMonValue OBJECT-TYPE
            SYNTAX OCTET STRING (SIZE (0..100))
            MAX-ACCESS read-only
            STATUS current
            DESCRIPTION
                "perMonValue."
            ::= { synsourcePer15MHisEntry 4 }

        -- 1.3.6.1.4.1.2011.2.25.3.40.50.86.20.1.5
        synsourcePer15MHisDateTimeStart OBJECT-TYPE
            SYNTAX DateAndTime
            MAX-ACCESS read-only
            STATUS current
            DESCRIPTION
                "perDateTimeStart. "
            ::= { synsourcePer15MHisEntry 5 }

        -- 1.3.6.1.4.1.2011.2.25.3.40.50.86.20.1.6
        synsourcePer15MHisDateTimeEnd OBJECT-TYPE
            SYNTAX DateAndTime
            MAX-ACCESS read-only
            STATUS current
            DESCRIPTION
                "perDateTimeEnd. "
            ::= { synsourcePer15MHisEntry 6 }

        -- 1.3.6.1.4.1.2011.2.25.3.40.50.86.20.1.7
        synsourcePer15MHisVldty OBJECT-TYPE
            SYNTAX INTEGER
            MAX-ACCESS read-only
            STATUS current
            DESCRIPTION
                "perVldty. "
            ::= { synsourcePer15MHisEntry 7 }




-- -------------------------------------------------------------------------
-- Perfomance 24-HOUR Current Data Table (RTRV-PER-<MOD2>)
-- -------------------------------------------------------------------------
        -- 1.3.6.1.4.1.2011.2.25.3.40.50.86.30
        synsourcePer24HCurTable OBJECT-TYPE
          SYNTAX SEQUENCE OF SynsourcePer24HCurEntry
          MAX-ACCESS not-accessible
          STATUS current
          DESCRIPTION
              "synsourcePer24HCur."
          ::= { synsource 30 }

        -- 1.3.6.1.4.1.2011.2.25.3.40.50.86.30.1
        synsourcePer24HCurEntry OBJECT-TYPE
            SYNTAX SynsourcePer24HCurEntry
            MAX-ACCESS not-accessible
            STATUS current
            DESCRIPTION
              "synsourcePer24HCur."
            INDEX { synsourcePer24HCurEid, synsourcePer24HCurPara }
            ::= { synsourcePer24HCurTable 1 }

        SynsourcePer24HCurEntry ::=
            SEQUENCE {
                synsourcePer24HCurEid
                    PerformanceEventType,
                synsourcePer24HCurMonValue
                    OCTET STRING,
                synsourcePer24HCurVldty
                    INTEGER,
                synsourcePer24HCurDateTime
                    DateAndTime,
                synsourcePer24HCurParaLen
                    INTEGER,
                synsourcePer24HCurPara
                    OCTET STRING
            }

        -- 1.3.6.1.4.1.2011.2.25.3.40.50.86.30.1.1
        synsourcePer24HCurEid OBJECT-TYPE
            SYNTAX PerformanceEventType
            MAX-ACCESS read-only
            STATUS current
            DESCRIPTION
                "perEid."
            ::= { synsourcePer24HCurEntry 1 }

        -- 1.3.6.1.4.1.2011.2.25.3.40.50.86.30.1.2
        synsourcePer24HCurMonValue OBJECT-TYPE
            SYNTAX OCTET STRING (SIZE (0..100))
            MAX-ACCESS read-only
            STATUS current
            DESCRIPTION
                "perMonValue."
            ::= { synsourcePer24HCurEntry 2 }

        -- 1.3.6.1.4.1.2011.2.25.3.40.50.86.30.1.3
        synsourcePer24HCurVldty OBJECT-TYPE
            SYNTAX INTEGER
            MAX-ACCESS read-only
            STATUS current
            DESCRIPTION
                "perVldty. "
            ::= { synsourcePer24HCurEntry 3 }

        -- 1.3.6.1.4.1.2011.2.25.3.40.50.86.30.1.4
        synsourcePer24HCurDateTime OBJECT-TYPE
            SYNTAX DateAndTime
            MAX-ACCESS read-only
            STATUS current
            DESCRIPTION
                "perDateTime. "
            ::= { synsourcePer24HCurEntry 4 }

        -- 1.3.6.1.4.1.2011.2.25.3.40.50.86.30.1.5
        synsourcePer24HCurParaLen OBJECT-TYPE
            SYNTAX INTEGER
            MAX-ACCESS read-only
            STATUS current
            DESCRIPTION
                "perParaLen."
            ::= { synsourcePer24HCurEntry 5 }

        -- 1.3.6.1.4.1.2011.2.25.3.40.50.86.30.1.6
        synsourcePer24HCurPara OBJECT-TYPE
            SYNTAX OCTET STRING (SIZE (0..100))
            MAX-ACCESS read-only
            STATUS current
            DESCRIPTION
                "perPara."
            ::= { synsourcePer24HCurEntry 6 }




-- -------------------------------------------------------------------------
-- Perfomance 24-HOUR History Data Table (RTRV-PER-<MOD2>)
-- -------------------------------------------------------------------------
        -- 1.3.6.1.4.1.2011.2.25.3.40.50.86.40
        synsourcePer24HHisTable OBJECT-TYPE
          SYNTAX SEQUENCE OF SynsourcePer24HHisEntry
          MAX-ACCESS not-accessible
          STATUS current
          DESCRIPTION
              "synsourcePer24HHis."
          ::= { synsource 40 }

        -- 1.3.6.1.4.1.2011.2.25.3.40.50.86.40.1
        synsourcePer24HHisEntry OBJECT-TYPE
            SYNTAX SynsourcePer24HHisEntry
            MAX-ACCESS not-accessible
            STATUS current
            DESCRIPTION
                "synsourcePer24HHis."
            INDEX {synsourcePer24HHisEid, synsourcePer24HHisParaLen, synsourcePer24HHisPara, synsourcePer24HHisDateTimeStart, synsourcePer24HHisDateTimeEnd}
            ::= { synsourcePer24HHisTable 1 }

        SynsourcePer24HHisEntry ::=
            SEQUENCE {
                synsourcePer24HHisEid
                    PerformanceEventType,
                synsourcePer24HHisParaLen
                    INTEGER,
                synsourcePer24HHisPara
                    OCTET STRING,
                synsourcePer24HHisMonValue
                    OCTET STRING,
                synsourcePer24HHisDateTimeStart
                    DateAndTime,
                synsourcePer24HHisDateTimeEnd
                    DateAndTime,
                synsourcePer24HHisVldty
                    INTEGER,
             }

        -- 1.3.6.1.4.1.2011.2.25.3.40.50.86.40.1.1
        synsourcePer24HHisEid OBJECT-TYPE
            SYNTAX PerformanceEventType
            MAX-ACCESS read-only
            STATUS current
            DESCRIPTION
                "perEid."
            ::= { synsourcePer24HHisEntry 1 }

        -- 1.3.6.1.4.1.2011.2.25.3.40.50.86.40.1.2
        synsourcePer24HHisParaLen OBJECT-TYPE
            SYNTAX INTEGER
            MAX-ACCESS read-only
            STATUS current
            DESCRIPTION
                "perParaLen."
            ::= { synsourcePer24HHisEntry 2 }

        -- 1.3.6.1.4.1.2011.2.25.3.40.50.86.40.1.3
        synsourcePer24HHisPara OBJECT-TYPE
            SYNTAX OCTET STRING (SIZE (0..100))
            MAX-ACCESS read-only
            STATUS current
            DESCRIPTION
                "perPara."
            ::= { synsourcePer24HHisEntry 3 }

        -- 1.3.6.1.4.1.2011.2.25.3.40.50.86.40.1.4
        synsourcePer24HHisMonValue OBJECT-TYPE
            SYNTAX OCTET STRING (SIZE (0..100))
            MAX-ACCESS read-only
            STATUS current
            DESCRIPTION
                "perMonValue."
            ::= { synsourcePer24HHisEntry 4 }

        -- 1.3.6.1.4.1.2011.2.25.3.40.50.86.40.1.5
        synsourcePer24HHisDateTimeStart OBJECT-TYPE
            SYNTAX DateAndTime
            MAX-ACCESS read-only
            STATUS current
            DESCRIPTION
                "perDateTimeStart. "
            ::= { synsourcePer24HHisEntry 5 }

        -- 1.3.6.1.4.1.2011.2.25.3.40.50.86.40.1.6
        synsourcePer24HHisDateTimeEnd OBJECT-TYPE
            SYNTAX DateAndTime
            MAX-ACCESS read-only
            STATUS current
            DESCRIPTION
                "perDateTimeEnd. "
            ::= { synsourcePer24HHisEntry 6 }

        -- 1.3.6.1.4.1.2011.2.25.3.40.50.86.40.1.7
        synsourcePer24HHisVldty OBJECT-TYPE
            SYNTAX INTEGER
            MAX-ACCESS read-only
            STATUS current
            DESCRIPTION
                "perVldty. "
            ::= { synsourcePer24HHisEntry 7 }


--  Alarm data
		-- 1.3.6.1.4.1.2011.2.25.3.40.50.87
		osc-path OBJECT IDENTIFIER ::= { optixGlobalNGWDM 87 }

-- -------------------------------------------------------------------------
-- Perfomance 15-MIN Current Data Table (RTRV-PER-<MOD2>)
-- -------------------------------------------------------------------------
		-- 1.3.6.1.4.1.2011.2.25.3.40.50.87.10
		osc-pathPer15mCurTable OBJECT-TYPE
			SYNTAX SEQUENCE OF Osc-pathPer15mCurEntry
			MAX-ACCESS not-accessible
			STATUS current
			DESCRIPTION
				"osc-pathPer15mCur."
			::= { osc-path 10 }

		-- 1.3.6.1.4.1.2011.2.25.3.40.50.87.10.1
		osc-pathPer15mCurEntry OBJECT-TYPE
			SYNTAX Osc-pathPer15mCurEntry
			MAX-ACCESS not-accessible
			STATUS current
			DESCRIPTION
				"osc-pathPer15mCur."
			INDEX {osc-pathPer15mCurEid, osc-pathPer15mCurPara}
			::= { osc-pathPer15mCurTable 1 }

		Osc-pathPer15mCurEntry ::=
			SEQUENCE {
				osc-pathPer15mCurEid
					PerformanceEventType,
				osc-pathPer15mCurMonValue
					Counter64,
				osc-pathPer15mCurVldty
					INTEGER,
				osc-pathPer15mCurDateTime
					DateAndTime,
				osc-pathPer15mCurParaLen
					INTEGER,
				osc-pathPer15mCurPara
					OCTET STRING
			 }

		-- 1.3.6.1.4.1.2011.2.25.3.40.50.87.10.1.1
		osc-pathPer15mCurEid OBJECT-TYPE
			SYNTAX PerformanceEventType
			MAX-ACCESS read-write
			STATUS current
			DESCRIPTION
				"perEid."
			::= { osc-pathPer15mCurEntry 1 }

		-- 1.3.6.1.4.1.2011.2.25.3.40.50.87.10.1.2
		osc-pathPer15mCurMonValue OBJECT-TYPE
			SYNTAX Counter64
			MAX-ACCESS read-write
			STATUS current
			DESCRIPTION
				"perMonValue."
			::= { osc-pathPer15mCurEntry 2 }

		-- 1.3.6.1.4.1.2011.2.25.3.40.50.87.10.3
		osc-pathPer15mCurVldty OBJECT-TYPE
			SYNTAX INTEGER
			MAX-ACCESS read-write
			STATUS current
			DESCRIPTION
				"perVldty. "
			::= { osc-pathPer15mCurEntry 3 }

		-- 1.3.6.1.4.1.2011.2.25.3.40.50.87.10.1.4
		osc-pathPer15mCurDateTime OBJECT-TYPE
			SYNTAX DateAndTime
			MAX-ACCESS read-write
			STATUS current
			DESCRIPTION
				"perDateTime. "
			::= { osc-pathPer15mCurEntry 4 }

		-- 1.3.6.1.4.1.2011.2.25.3.40.50.87.10.1.5
		osc-pathPer15mCurParaLen OBJECT-TYPE
			SYNTAX INTEGER
			MAX-ACCESS read-write
			STATUS current
			DESCRIPTION
				"perParaLen."
			::= { osc-pathPer15mCurEntry 5 }

		-- 1.3.6.1.4.1.2011.2.25.3.40.50.87.10.1.6
		osc-pathPer15mCurPara OBJECT-TYPE
			SYNTAX OCTET STRING (SIZE (0..100))
			MAX-ACCESS read-only
			STATUS current
			DESCRIPTION
				"perPara."
			::= { osc-pathPer15mCurEntry 6 }

-- -------------------------------------------------------------------------
-- Perfomance 15-MIN History Data Table (RTRV-PER-<MOD2>)
-- -------------------------------------------------------------------------
		osc-pathPer15MHisTable OBJECT-TYPE
			SYNTAX SEQUENCE OF Osc-pathPer15MHisEntry
			MAX-ACCESS not-accessible
			STATUS current
			DESCRIPTION
				"osc-pathPer15MHis."
			::= { osc-path 20 }

		osc-pathPer15MHisEntry OBJECT-TYPE
			SYNTAX Osc-pathPer15MHisEntry
			MAX-ACCESS not-accessible
			STATUS current
			DESCRIPTION
				"osc-pathPer15MHis."
			INDEX {osc-pathPer15MHisEid, osc-pathPer15MHisParaLen, osc-pathPer15MHisPara, osc-pathPer15MHisDateTimeStart, osc-pathPer15MHisDateTimeEnd}
			::= { osc-pathPer15MHisTable 1 }

		Osc-pathPer15MHisEntry ::=
			SEQUENCE {
				osc-pathPer15MHisEid
					PerformanceEventType,
				osc-pathPer15MHisParaLen
					INTEGER,
				osc-pathPer15MHisPara
					OCTET STRING,
				osc-pathPer15MHisMonValue
					Counter64,
				osc-pathPer15MHisDateTimeStart
					DateAndTime,
				osc-pathPer15MHisDateTimeEnd
					DateAndTime,
				osc-pathPer15MHisVldty
					INTEGER,
			 }

		osc-pathPer15MHisEid OBJECT-TYPE
			SYNTAX PerformanceEventType
			MAX-ACCESS read-only
			STATUS current
			DESCRIPTION
				"perEid."
			::= { osc-pathPer15MHisEntry 1 }

		osc-pathPer15MHisParaLen OBJECT-TYPE
			SYNTAX INTEGER
			MAX-ACCESS read-only
			STATUS current
			DESCRIPTION
				"perParaLen."
			::= { osc-pathPer15MHisEntry 2 }

		osc-pathPer15MHisPara OBJECT-TYPE
			SYNTAX OCTET STRING (SIZE (0..100))
			MAX-ACCESS read-only
			STATUS current
			DESCRIPTION
				"perPara."
			::= { osc-pathPer15MHisEntry 3 }

		osc-pathPer15MHisMonValue OBJECT-TYPE
			SYNTAX Counter64
			MAX-ACCESS read-only
			STATUS current
			DESCRIPTION
				"perMonValue."
			::= { osc-pathPer15MHisEntry 4 }

		osc-pathPer15MHisDateTimeStart OBJECT-TYPE
			SYNTAX DateAndTime
			MAX-ACCESS read-only
			STATUS current
			DESCRIPTION
				"perDateTimeStart. "
			::= { osc-pathPer15MHisEntry 5 }

		osc-pathPer15MHisDateTimeEnd OBJECT-TYPE
			SYNTAX DateAndTime
			MAX-ACCESS read-only
			STATUS current
			DESCRIPTION
				"perDateTimeEnd. "
			::= { osc-pathPer15MHisEntry 6 }

		osc-pathPer15MHisVldty OBJECT-TYPE
			SYNTAX INTEGER
			MAX-ACCESS read-only
			STATUS current
			DESCRIPTION
				"perVldty. "
			::= { osc-pathPer15MHisEntry 7 }

-- -------------------------------------------------------------------------
-- Perfomance 24-HOUR Current Data Table (RTRV-PER-<MOD2>)
-- -------------------------------------------------------------------------
		osc-pathPer24HCurTable OBJECT-TYPE
			SYNTAX SEQUENCE OF Osc-pathPer24HCurEntry
			MAX-ACCESS not-accessible
			STATUS current
			DESCRIPTION
				"osc-pathPer24HCur."
			::= { osc-path 30 }

		osc-pathPer24HCurEntry OBJECT-TYPE
			SYNTAX Osc-pathPer24HCurEntry
			MAX-ACCESS not-accessible
			STATUS current
			DESCRIPTION
				"osc-pathPer24HCur."
			INDEX {osc-pathPer24HCurEid, osc-pathPer24HCurPara}
			::= { osc-pathPer24HCurTable 1 }

		Osc-pathPer24HCurEntry ::=
			SEQUENCE {
				osc-pathPer24HCurEid
					PerformanceEventType,
				osc-pathPer24HCurMonValue
					Counter64,
				osc-pathPer24HCurVldty
					INTEGER,
				osc-pathPer24HCurDateTime
					DateAndTime,
				osc-pathPer24HCurParaLen
					INTEGER,
				osc-pathPer24HCurPara
					OCTET STRING
			 }

		osc-pathPer24HCurEid OBJECT-TYPE
			SYNTAX PerformanceEventType
			MAX-ACCESS read-write
			STATUS current
			DESCRIPTION
				"perEid."
			::= { osc-pathPer24HCurEntry 1 }

		osc-pathPer24HCurMonValue OBJECT-TYPE
			SYNTAX Counter64
			MAX-ACCESS read-write
			STATUS current
			DESCRIPTION
				"perMonValue."
			::= { osc-pathPer24HCurEntry 2 }

		osc-pathPer24HCurVldty OBJECT-TYPE
			SYNTAX INTEGER
			MAX-ACCESS read-write
			STATUS current
			DESCRIPTION
				"perVldty. "
			::= { osc-pathPer24HCurEntry 3 }

		osc-pathPer24HCurDateTime OBJECT-TYPE
			SYNTAX DateAndTime
			MAX-ACCESS read-write
			STATUS current
			DESCRIPTION
				"perDateTime. "
			::= { osc-pathPer24HCurEntry 4 }

		osc-pathPer24HCurParaLen OBJECT-TYPE
			SYNTAX INTEGER
			MAX-ACCESS read-write
			STATUS current
			DESCRIPTION
				"perParaLen."
			::= { osc-pathPer24HCurEntry 5 }

		osc-pathPer24HCurPara OBJECT-TYPE
			SYNTAX OCTET STRING (SIZE (0..100))
			MAX-ACCESS read-only
			STATUS current
			DESCRIPTION
				"perPara."
			::= { osc-pathPer24HCurEntry 6 }

-- -------------------------------------------------------------------------
-- Perfomance 24-HOUR History Data Table (RTRV-PER-<MOD2>)
-- -------------------------------------------------------------------------
		osc-pathPer24HHisTable OBJECT-TYPE
			SYNTAX SEQUENCE OF Osc-pathPer24HHisEntry
			MAX-ACCESS not-accessible
			STATUS current
			DESCRIPTION
				"osc-pathPer24HHis."
			::= { osc-path 40 }

		osc-pathPer24HHisEntry OBJECT-TYPE
			SYNTAX Osc-pathPer24HHisEntry
			MAX-ACCESS not-accessible
			STATUS current
			DESCRIPTION
				"osc-pathPer24HHis."
			INDEX {osc-pathPer24HHisEid, osc-pathPer24HHisParaLen, osc-pathPer24HHisPara, osc-pathPer24HHisDateTimeStart, osc-pathPer24HHisDateTimeEnd}
			::= { osc-pathPer24HHisTable 1 }

		Osc-pathPer24HHisEntry ::=
			SEQUENCE {
				osc-pathPer24HHisEid
					PerformanceEventType,
				osc-pathPer24HHisParaLen
					INTEGER,
				osc-pathPer24HHisPara
					OCTET STRING,
				osc-pathPer24HHisMonValue
					Counter64,
				osc-pathPer24HHisDateTimeStart
					DateAndTime,
				osc-pathPer24HHisDateTimeEnd
					DateAndTime,
				osc-pathPer24HHisVldty
					INTEGER,
			 }

		osc-pathPer24HHisEid OBJECT-TYPE
			SYNTAX PerformanceEventType
			MAX-ACCESS read-only
			STATUS current
			DESCRIPTION
				"perEid."
			::= { osc-pathPer24HHisEntry 1 }

		osc-pathPer24HHisParaLen OBJECT-TYPE
			SYNTAX INTEGER
			MAX-ACCESS read-only
			STATUS current
			DESCRIPTION
				"perParaLen."
			::= { osc-pathPer24HHisEntry 2 }

		osc-pathPer24HHisPara OBJECT-TYPE
			SYNTAX OCTET STRING (SIZE (0..100))
			MAX-ACCESS read-only
			STATUS current
			DESCRIPTION
				"perPara."
			::= { osc-pathPer24HHisEntry 3 }

		osc-pathPer24HHisMonValue OBJECT-TYPE
			SYNTAX Counter64
			MAX-ACCESS read-only
			STATUS current
			DESCRIPTION
				"perMonValue."
			::= { osc-pathPer24HHisEntry 4 }

		osc-pathPer24HHisDateTimeStart OBJECT-TYPE
			SYNTAX DateAndTime
			MAX-ACCESS read-only
			STATUS current
			DESCRIPTION
				"perDateTimeStart. "
			::= { osc-pathPer24HHisEntry 5 }

		osc-pathPer24HHisDateTimeEnd OBJECT-TYPE
			SYNTAX DateAndTime
			MAX-ACCESS read-only
			STATUS current
			DESCRIPTION
				"perDateTimeEnd. "
			::= { osc-pathPer24HHisEntry 6 }

		osc-pathPer24HHisVldty OBJECT-TYPE
			SYNTAX INTEGER
			MAX-ACCESS read-only
			STATUS current
			DESCRIPTION
				"perVldty. "
			::= { osc-pathPer24HHisEntry 7 }

-- -------------------------------------------------------------------------
-- Perfomance 15-MIN History Data Table (RTRV-PER-<MOD2>)
-- -------------------------------------------------------------------------
        nePer15MHisTable OBJECT-TYPE
            SYNTAX SEQUENCE OF NePer15MHisEntry
            MAX-ACCESS not-accessible
            STATUS current
            DESCRIPTION
                "nePer15MHis."
            ::= { ne 20 }


        nePer15MHisEntry OBJECT-TYPE
            SYNTAX NePer15MHisEntry
            MAX-ACCESS not-accessible
            STATUS current
            DESCRIPTION
                "nePer15MHis."
            INDEX {nePer15MHisEid, nePer15MHisParaLen, nePer15MHisPara, nePer15MHisDateTimeStart, nePer15MHisDateTimeEnd}
            ::= { nePer15MHisTable 1 }

        NePer15MHisEntry ::=
            SEQUENCE {
                nePer15MHisEid
                    PerformanceEventType,
                nePer15MHisParaLen
                    INTEGER,
                nePer15MHisPara
                    OCTET STRING,
                nePer15MHisMonValue
                    OCTET STRING,
                nePer15MHisDateTimeStart
                    DateAndTime,
                nePer15MHisDateTimeEnd
                    DateAndTime,
                nePer15MHisVldty
                    INTEGER,
             }

        nePer15MHisEid OBJECT-TYPE
            SYNTAX PerformanceEventType
            MAX-ACCESS read-only
            STATUS current
            DESCRIPTION
                "perEid."
            ::= { nePer15MHisEntry 1 }

        nePer15MHisParaLen OBJECT-TYPE
            SYNTAX INTEGER
            MAX-ACCESS read-only
            STATUS current
            DESCRIPTION
                "perParaLen."
            ::= { nePer15MHisEntry 2 }


        nePer15MHisPara OBJECT-TYPE
            SYNTAX OCTET STRING (SIZE (0..100))
            MAX-ACCESS read-only
            STATUS current
            DESCRIPTION
                "perPara."
            ::= { nePer15MHisEntry 3 }



        nePer15MHisMonValue OBJECT-TYPE
            SYNTAX OCTET STRING (SIZE (0..100))
            MAX-ACCESS read-only
            STATUS current
            DESCRIPTION
                "perMonValue."
            ::= { nePer15MHisEntry 4 }



        nePer15MHisDateTimeStart OBJECT-TYPE
            SYNTAX DateAndTime
            MAX-ACCESS read-only
            STATUS current
            DESCRIPTION
                "perDateTimeStart. "
            ::= { nePer15MHisEntry 5 }

        nePer15MHisDateTimeEnd OBJECT-TYPE
            SYNTAX DateAndTime
            MAX-ACCESS read-only
            STATUS current
            DESCRIPTION
                "perDateTimeEnd. "
            ::= { nePer15MHisEntry 6 }


        nePer15MHisVldty OBJECT-TYPE
            SYNTAX INTEGER
            MAX-ACCESS read-only
            STATUS current
            DESCRIPTION
                "perVldty. "
            ::= { nePer15MHisEntry 7 }


-- -------------------------------------------------------------------------
-- Perfomance 24-HOUR Current Data Table (RTRV-PER-<MOD2>)
-- -------------------------------------------------------------------------
        nePer24HCurTable OBJECT-TYPE
            SYNTAX SEQUENCE OF NePer24HCurEntry
            MAX-ACCESS not-accessible
            STATUS current
            DESCRIPTION
                "nePer24HCur."
            ::= { ne 30 }


        nePer24HCurEntry OBJECT-TYPE
            SYNTAX NePer24HCurEntry
            MAX-ACCESS not-accessible
            STATUS current
            DESCRIPTION
                "nePer24HCur."
            INDEX {nePer24HCurEid, nePer24HCurPara}
            ::= { nePer24HCurTable 1 }

        NePer24HCurEntry ::=
            SEQUENCE {
                nePer24HCurEid
                    PerformanceEventType,
                nePer24HCurMonValue
                    OCTET STRING,
                nePer24HCurVldty
                    INTEGER,
                nePer24HCurDateTime
                    DateAndTime,
                nePer24HCurParaLen
                    INTEGER,
                nePer24HCurPara
                    OCTET STRING
             }


        nePer24HCurEid OBJECT-TYPE
            SYNTAX PerformanceEventType
            MAX-ACCESS read-only
            STATUS current
            DESCRIPTION
                "perEid."
            ::= { nePer24HCurEntry 1 }


        nePer24HCurMonValue OBJECT-TYPE
            SYNTAX OCTET STRING (SIZE (0..100))
            MAX-ACCESS read-only
            STATUS current
            DESCRIPTION
                "perMonValue."
            ::= { nePer24HCurEntry 2 }


        nePer24HCurVldty OBJECT-TYPE
            SYNTAX INTEGER
            MAX-ACCESS read-only
            STATUS current
            DESCRIPTION
                "perVldty. "
            ::= { nePer24HCurEntry 3 }


        nePer24HCurDateTime OBJECT-TYPE
            SYNTAX DateAndTime
            MAX-ACCESS read-only
            STATUS current
            DESCRIPTION
                "perDateTime. "
            ::= { nePer24HCurEntry 4 }


        nePer24HCurParaLen OBJECT-TYPE
            SYNTAX INTEGER
            MAX-ACCESS read-only
            STATUS current
            DESCRIPTION
                "perParaLen."
            ::= { nePer24HCurEntry 5 }


        nePer24HCurPara OBJECT-TYPE
            SYNTAX OCTET STRING (SIZE (0..100))
            MAX-ACCESS read-only
            STATUS current
            DESCRIPTION
                "perPara."
            ::= { nePer24HCurEntry 6 }


-- -------------------------------------------------------------------------
-- Perfomance 24-HOUR History Data Table (RTRV-PER-<MOD2>)
-- -------------------------------------------------------------------------
        nePer24HHisTable OBJECT-TYPE
            SYNTAX SEQUENCE OF NePer24HHisEntry
            MAX-ACCESS not-accessible
            STATUS current
            DESCRIPTION
                "nePer24HHis."
            ::= { ne 40 }


        nePer24HHisEntry OBJECT-TYPE
            SYNTAX NePer24HHisEntry
            MAX-ACCESS not-accessible
            STATUS current
            DESCRIPTION
                "nePer24HHis."
            INDEX {nePer24HHisEid, nePer24HHisParaLen, nePer24HHisPara, nePer24HHisDateTimeStart, nePer24HHisDateTimeEnd}
            ::= { nePer24HHisTable 1 }

        NePer24HHisEntry ::=
            SEQUENCE {
                nePer24HHisEid
                    PerformanceEventType,
              nePer24HHisParaLen
                    INTEGER,
                nePer24HHisPara
                    OCTET STRING,
                nePer24HHisMonValue
                    OCTET STRING,
                nePer24HHisDateTimeStart
                    DateAndTime,
                nePer24HHisDateTimeEnd
                    DateAndTime,
                nePer24HHisVldty
                    INTEGER,
             }

        nePer24HHisEid OBJECT-TYPE
            SYNTAX PerformanceEventType
            MAX-ACCESS read-only
            STATUS current
            DESCRIPTION
                "perEid."
            ::= { nePer24HHisEntry 1 }

        nePer24HHisParaLen OBJECT-TYPE
            SYNTAX INTEGER
            MAX-ACCESS read-only
            STATUS current
            DESCRIPTION
                "perParaLen."
            ::= { nePer24HHisEntry 2 }


        nePer24HHisPara OBJECT-TYPE
            SYNTAX OCTET STRING (SIZE (0..100))
            MAX-ACCESS read-only
            STATUS current
            DESCRIPTION
                "perPara."
            ::= { nePer24HHisEntry 3 }



        nePer24HHisMonValue OBJECT-TYPE
            SYNTAX OCTET STRING (SIZE (0..100))
            MAX-ACCESS read-only
            STATUS current
            DESCRIPTION
                "perMonValue."
            ::= { nePer24HHisEntry 4 }



        nePer24HHisDateTimeStart OBJECT-TYPE
            SYNTAX DateAndTime
            MAX-ACCESS read-only
            STATUS current
            DESCRIPTION
                "perDateTimeStart. "
            ::= { nePer24HHisEntry 5 }

        nePer24HHisDateTimeEnd OBJECT-TYPE
            SYNTAX DateAndTime
            MAX-ACCESS read-only
            STATUS current
            DESCRIPTION
                "perDateTimeEnd. "
            ::= { nePer24HHisEntry 6 }


        nePer24HHisVldty OBJECT-TYPE
            SYNTAX INTEGER
            MAX-ACCESS read-only
            STATUS current
            DESCRIPTION
                "perVldty. "
            ::= { nePer24HHisEntry 7 }

-- Alarm data
      -- 1.3.6.1.4.1.2011.2.25.3.40.50.21
      board OBJECT IDENTIFIER ::={ optixGlobalNGWDM 21 }


-- -------------------------------------------------------------------------
-- Perfomance 15-MIN Current Data Table (RTRV-PER-<MOD2>)
-- -------------------------------------------------------------------------
        -- 1.3.6.1.4.1.2011.2.25.3.40.50.21.10
        boardPer15MCurTable OBJECT-TYPE
          SYNTAX SEQUENCE OF BoardPer15MCurEntry
          MAX-ACCESS not-accessible
          STATUS current
          DESCRIPTION
              "boardPer15MCur."
          ::= { board 10 }

        -- 1.3.6.1.4.1.2011.2.25.3.40.50.21.10.1
        boardPer15MCurEntry OBJECT-TYPE
            SYNTAX BoardPer15MCurEntry
            MAX-ACCESS not-accessible
            STATUS current
            DESCRIPTION
              "boardPer15MCur."
            INDEX { boardPer15MCurEid, boardPer15MCurPara }
            ::= { boardPer15MCurTable 1 }

        BoardPer15MCurEntry ::=
            SEQUENCE {
                boardPer15MCurEid
                    PerformanceEventType,
                boardPer15MCurMonValue
                    OCTET STRING,
                boardPer15MCurVldty
                    INTEGER,
                boardPer15MCurDateTime
                    DateAndTime,
                boardPer15MCurParaLen
                    INTEGER,
                boardPer15MCurPara
                    OCTET STRING
            }

        -- 1.3.6.1.4.1.2011.2.25.3.40.50.21.10.1.1
        boardPer15MCurEid OBJECT-TYPE
            SYNTAX PerformanceEventType
            MAX-ACCESS read-only
            STATUS current
            DESCRIPTION
                "perEid."
            ::= { boardPer15MCurEntry 1 }

        -- 1.3.6.1.4.1.2011.2.25.3.40.50.21.10.1.2
        boardPer15MCurMonValue OBJECT-TYPE
            SYNTAX OCTET STRING (SIZE (0..100))
            MAX-ACCESS read-only
            STATUS current
            DESCRIPTION
                "perMonValue."
            ::= { boardPer15MCurEntry 2 }

        -- 1.3.6.1.4.1.2011.2.25.3.40.50.21.10.1.3
        boardPer15MCurVldty OBJECT-TYPE
            SYNTAX INTEGER
            MAX-ACCESS read-only
            STATUS current
            DESCRIPTION
                "perVldty. "
            ::= { boardPer15MCurEntry 3 }

        -- 1.3.6.1.4.1.2011.2.25.3.40.50.21.10.1.4
        boardPer15MCurDateTime OBJECT-TYPE
            SYNTAX DateAndTime
            MAX-ACCESS read-only
            STATUS current
            DESCRIPTION
                "perDateTime. "
            ::= { boardPer15MCurEntry 4 }

        -- 1.3.6.1.4.1.2011.2.25.3.40.50.21.10.1.5
        boardPer15MCurParaLen OBJECT-TYPE
            SYNTAX INTEGER
            MAX-ACCESS read-only
            STATUS current
            DESCRIPTION
                "perParaLen."
            ::= { boardPer15MCurEntry 5 }

        -- 1.3.6.1.4.1.2011.2.25.3.40.50.21.10.1.6
        boardPer15MCurPara OBJECT-TYPE
            SYNTAX OCTET STRING (SIZE (0..100))
            MAX-ACCESS read-only
            STATUS current
            DESCRIPTION
                "perPara."
            ::= { boardPer15MCurEntry 6 }




-- -------------------------------------------------------------------------
-- Perfomance 15-MIN History Data Table (RTRV-PER-<MOD2>)
-- -------------------------------------------------------------------------
        -- 1.3.6.1.4.1.2011.2.25.3.40.50.21.20
        boardPer15MHisTable OBJECT-TYPE
          SYNTAX SEQUENCE OF BoardPer15MHisEntry
          MAX-ACCESS not-accessible
          STATUS current
          DESCRIPTION
              "boardPer15MHis."
          ::= { board 20 }

        -- 1.3.6.1.4.1.2011.2.25.3.40.50.21.20.1
        boardPer15MHisEntry OBJECT-TYPE
            SYNTAX BoardPer15MHisEntry
            MAX-ACCESS not-accessible
            STATUS current
            DESCRIPTION
                "boardPer15MHis."
            INDEX {boardPer15MHisEid, boardPer15MHisParaLen, boardPer15MHisPara, boardPer15MHisDateTimeStart, boardPer15MHisDateTimeEnd}
            ::= { boardPer15MHisTable 1 }

        BoardPer15MHisEntry ::=
            SEQUENCE {
                boardPer15MHisEid
                    PerformanceEventType,
                boardPer15MHisParaLen
                    INTEGER,
                boardPer15MHisPara
                    OCTET STRING,
                boardPer15MHisMonValue
                    OCTET STRING,
                boardPer15MHisDateTimeStart
                    DateAndTime,
                boardPer15MHisDateTimeEnd
                    DateAndTime,
                boardPer15MHisVldty
                    INTEGER,
             }

        -- 1.3.6.1.4.1.2011.2.25.3.40.50.21.20.1.1
        boardPer15MHisEid OBJECT-TYPE
            SYNTAX PerformanceEventType
            MAX-ACCESS read-only
            STATUS current
            DESCRIPTION
                "perEid."
            ::= { boardPer15MHisEntry 1 }

        -- 1.3.6.1.4.1.2011.2.25.3.40.50.21.20.1.2
        boardPer15MHisParaLen OBJECT-TYPE
            SYNTAX INTEGER
            MAX-ACCESS read-only
            STATUS current
            DESCRIPTION
                "perParaLen."
            ::= { boardPer15MHisEntry 2 }

        -- 1.3.6.1.4.1.2011.2.25.3.40.50.21.20.1.3
        boardPer15MHisPara OBJECT-TYPE
            SYNTAX OCTET STRING (SIZE (0..100))
            MAX-ACCESS read-only
            STATUS current
            DESCRIPTION
                "perPara."
            ::= { boardPer15MHisEntry 3 }

        -- 1.3.6.1.4.1.2011.2.25.3.40.50.21.20.1.4
        boardPer15MHisMonValue OBJECT-TYPE
            SYNTAX OCTET STRING (SIZE (0..100))
            MAX-ACCESS read-only
            STATUS current
            DESCRIPTION
                "perMonValue."
            ::= { boardPer15MHisEntry 4 }

        -- 1.3.6.1.4.1.2011.2.25.3.40.50.21.20.1.5
        boardPer15MHisDateTimeStart OBJECT-TYPE
            SYNTAX DateAndTime
            MAX-ACCESS read-only
            STATUS current
            DESCRIPTION
                "perDateTimeStart. "
            ::= { boardPer15MHisEntry 5 }

        -- 1.3.6.1.4.1.2011.2.25.3.40.50.21.20.1.6
        boardPer15MHisDateTimeEnd OBJECT-TYPE
            SYNTAX DateAndTime
            MAX-ACCESS read-only
            STATUS current
            DESCRIPTION
                "perDateTimeEnd. "
            ::= { boardPer15MHisEntry 6 }

        -- 1.3.6.1.4.1.2011.2.25.3.40.50.21.20.1.7
        boardPer15MHisVldty OBJECT-TYPE
            SYNTAX INTEGER
            MAX-ACCESS read-only
            STATUS current
            DESCRIPTION
                "perVldty. "
            ::= { boardPer15MHisEntry 7 }




-- -------------------------------------------------------------------------
-- Perfomance 24-HOUR Current Data Table (RTRV-PER-<MOD2>)
-- -------------------------------------------------------------------------
        -- 1.3.6.1.4.1.2011.2.25.3.40.50.21.30
        boardPer24HCurTable OBJECT-TYPE
          SYNTAX SEQUENCE OF BoardPer24HCurEntry
          MAX-ACCESS not-accessible
          STATUS current
          DESCRIPTION
              "boardPer24HCur."
          ::= { board 30 }

        -- 1.3.6.1.4.1.2011.2.25.3.40.50.21.30.1
        boardPer24HCurEntry OBJECT-TYPE
            SYNTAX BoardPer24HCurEntry
            MAX-ACCESS not-accessible
            STATUS current
            DESCRIPTION
              "boardPer24HCur."
            INDEX { boardPer24HCurEid, boardPer24HCurPara }
            ::= { boardPer24HCurTable 1 }

        BoardPer24HCurEntry ::=
            SEQUENCE {
                boardPer24HCurEid
                    PerformanceEventType,
                boardPer24HCurMonValue
                    OCTET STRING,
                boardPer24HCurVldty
                    INTEGER,
                boardPer24HCurDateTime
                    DateAndTime,
                boardPer24HCurParaLen
                    INTEGER,
                boardPer24HCurPara
                    OCTET STRING
            }

        -- 1.3.6.1.4.1.2011.2.25.3.40.50.21.30.1.1
        boardPer24HCurEid OBJECT-TYPE
            SYNTAX PerformanceEventType
            MAX-ACCESS read-only
            STATUS current
            DESCRIPTION
                "perEid."
            ::= { boardPer24HCurEntry 1 }

        -- 1.3.6.1.4.1.2011.2.25.3.40.50.21.30.1.2
        boardPer24HCurMonValue OBJECT-TYPE
            SYNTAX OCTET STRING (SIZE (0..100))
            MAX-ACCESS read-only
            STATUS current
            DESCRIPTION
                "perMonValue."
            ::= { boardPer24HCurEntry 2 }

        -- 1.3.6.1.4.1.2011.2.25.3.40.50.21.30.1.3
        boardPer24HCurVldty OBJECT-TYPE
            SYNTAX INTEGER
            MAX-ACCESS read-only
            STATUS current
            DESCRIPTION
                "perVldty. "
            ::= { boardPer24HCurEntry 3 }

        -- 1.3.6.1.4.1.2011.2.25.3.40.50.21.30.1.4
        boardPer24HCurDateTime OBJECT-TYPE
            SYNTAX DateAndTime
            MAX-ACCESS read-only
            STATUS current
            DESCRIPTION
                "perDateTime. "
            ::= { boardPer24HCurEntry 4 }

        -- 1.3.6.1.4.1.2011.2.25.3.40.50.21.30.1.5
        boardPer24HCurParaLen OBJECT-TYPE
            SYNTAX INTEGER
            MAX-ACCESS read-only
            STATUS current
            DESCRIPTION
                "perParaLen."
            ::= { boardPer24HCurEntry 5 }

        -- 1.3.6.1.4.1.2011.2.25.3.40.50.21.30.1.6
        boardPer24HCurPara OBJECT-TYPE
            SYNTAX OCTET STRING (SIZE (0..100))
            MAX-ACCESS read-only
            STATUS current
            DESCRIPTION
                "perPara."
            ::= { boardPer24HCurEntry 6 }




-- -------------------------------------------------------------------------
-- Perfomance 24-HOUR History Data Table (RTRV-PER-<MOD2>)
-- -------------------------------------------------------------------------
        -- 1.3.6.1.4.1.2011.2.25.3.40.50.21.40
        boardPer24HHisTable OBJECT-TYPE
          SYNTAX SEQUENCE OF BoardPer24HHisEntry
          MAX-ACCESS not-accessible
          STATUS current
          DESCRIPTION
              "boardPer24HHis."
          ::= { board 40 }

        -- 1.3.6.1.4.1.2011.2.25.3.40.50.21.40.1
        boardPer24HHisEntry OBJECT-TYPE
            SYNTAX BoardPer24HHisEntry
            MAX-ACCESS not-accessible
            STATUS current
            DESCRIPTION
                "boardPer24HHis."
            INDEX {boardPer24HHisEid, boardPer24HHisParaLen, boardPer24HHisPara, boardPer24HHisDateTimeStart, boardPer24HHisDateTimeEnd}
            ::= { boardPer24HHisTable 1 }

        BoardPer24HHisEntry ::=
            SEQUENCE {
                boardPer24HHisEid
                    PerformanceEventType,
                boardPer24HHisParaLen
                    INTEGER,
                boardPer24HHisPara
                    OCTET STRING,
                boardPer24HHisMonValue
                    OCTET STRING,
                boardPer24HHisDateTimeStart
                    DateAndTime,
                boardPer24HHisDateTimeEnd
                    DateAndTime,
                boardPer24HHisVldty
                    INTEGER,
             }

        -- 1.3.6.1.4.1.2011.2.25.3.40.50.21.40.1.1
        boardPer24HHisEid OBJECT-TYPE
            SYNTAX PerformanceEventType
            MAX-ACCESS read-only
            STATUS current
            DESCRIPTION
                "perEid."
            ::= { boardPer24HHisEntry 1 }

        -- 1.3.6.1.4.1.2011.2.25.3.40.50.21.40.1.2
        boardPer24HHisParaLen OBJECT-TYPE
            SYNTAX INTEGER
            MAX-ACCESS read-only
            STATUS current
            DESCRIPTION
                "perParaLen."
            ::= { boardPer24HHisEntry 2 }

        -- 1.3.6.1.4.1.2011.2.25.3.40.50.21.40.1.3
        boardPer24HHisPara OBJECT-TYPE
            SYNTAX OCTET STRING (SIZE (0..100))
            MAX-ACCESS read-only
            STATUS current
            DESCRIPTION
                "perPara."
            ::= { boardPer24HHisEntry 3 }

        -- 1.3.6.1.4.1.2011.2.25.3.40.50.21.40.1.4
        boardPer24HHisMonValue OBJECT-TYPE
            SYNTAX OCTET STRING (SIZE (0..100))
            MAX-ACCESS read-only
            STATUS current
            DESCRIPTION
                "perMonValue."
            ::= { boardPer24HHisEntry 4 }

        -- 1.3.6.1.4.1.2011.2.25.3.40.50.21.40.1.5
        boardPer24HHisDateTimeStart OBJECT-TYPE
            SYNTAX DateAndTime
            MAX-ACCESS read-only
            STATUS current
            DESCRIPTION
                "perDateTimeStart. "
            ::= { boardPer24HHisEntry 5 }

        -- 1.3.6.1.4.1.2011.2.25.3.40.50.21.40.1.6
        boardPer24HHisDateTimeEnd OBJECT-TYPE
            SYNTAX DateAndTime
            MAX-ACCESS read-only
            STATUS current
            DESCRIPTION
                "perDateTimeEnd. "
            ::= { boardPer24HHisEntry 6 }

        -- 1.3.6.1.4.1.2011.2.25.3.40.50.21.40.1.7
        boardPer24HHisVldty OBJECT-TYPE
            SYNTAX INTEGER
            MAX-ACCESS read-only
            STATUS current
            DESCRIPTION
                "perVldty. "
            ::= { boardPer24HHisEntry 7 }




-- Alarm data
      -- 1.3.6.1.4.1.2011.2.25.3.40.50.23
      sccbd OBJECT IDENTIFIER ::={ optixGlobalNGWDM 23 }


-- -------------------------------------------------------------------------
-- Perfomance 15-MIN Current Data Table (RTRV-PER-<MOD2>)
-- -------------------------------------------------------------------------
        -- 1.3.6.1.4.1.2011.2.25.3.40.50.23.10
        sccbdPer15MCurTable OBJECT-TYPE
          SYNTAX SEQUENCE OF SccbdPer15MCurEntry
          MAX-ACCESS not-accessible
          STATUS current
          DESCRIPTION
              "sccbdPer15MCur."
          ::= { sccbd 10 }

        -- 1.3.6.1.4.1.2011.2.25.3.40.50.23.10.1
        sccbdPer15MCurEntry OBJECT-TYPE
            SYNTAX SccbdPer15MCurEntry
            MAX-ACCESS not-accessible
            STATUS current
            DESCRIPTION
              "sccbdPer15MCur."
            INDEX { sccbdPer15MCurEid, sccbdPer15MCurPara }
            ::= { sccbdPer15MCurTable 1 }

        SccbdPer15MCurEntry ::=
            SEQUENCE {
                sccbdPer15MCurEid
                    PerformanceEventType,
                sccbdPer15MCurMonValue
                    OCTET STRING,
                sccbdPer15MCurVldty
                    INTEGER,
                sccbdPer15MCurDateTime
                    DateAndTime,
                sccbdPer15MCurParaLen
                    INTEGER,
                sccbdPer15MCurPara
                    OCTET STRING
            }

        -- 1.3.6.1.4.1.2011.2.25.3.40.50.23.10.1.1
        sccbdPer15MCurEid OBJECT-TYPE
            SYNTAX PerformanceEventType
            MAX-ACCESS read-only
            STATUS current
            DESCRIPTION
                "perEid."
            ::= { sccbdPer15MCurEntry 1 }

        -- 1.3.6.1.4.1.2011.2.25.3.40.50.23.10.1.2
        sccbdPer15MCurMonValue OBJECT-TYPE
            SYNTAX OCTET STRING (SIZE (0..100))
            MAX-ACCESS read-only
            STATUS current
            DESCRIPTION
                "perMonValue."
            ::= { sccbdPer15MCurEntry 2 }

        -- 1.3.6.1.4.1.2011.2.25.3.40.50.23.10.1.3
        sccbdPer15MCurVldty OBJECT-TYPE
            SYNTAX INTEGER
            MAX-ACCESS read-only
            STATUS current
            DESCRIPTION
                "perVldty. "
            ::= { sccbdPer15MCurEntry 3 }

        -- 1.3.6.1.4.1.2011.2.25.3.40.50.23.10.1.4
        sccbdPer15MCurDateTime OBJECT-TYPE
            SYNTAX DateAndTime
            MAX-ACCESS read-only
            STATUS current
            DESCRIPTION
                "perDateTime. "
            ::= { sccbdPer15MCurEntry 4 }

        -- 1.3.6.1.4.1.2011.2.25.3.40.50.23.10.1.5
        sccbdPer15MCurParaLen OBJECT-TYPE
            SYNTAX INTEGER
            MAX-ACCESS read-only
            STATUS current
            DESCRIPTION
                "perParaLen."
            ::= { sccbdPer15MCurEntry 5 }

        -- 1.3.6.1.4.1.2011.2.25.3.40.50.23.10.1.6
        sccbdPer15MCurPara OBJECT-TYPE
            SYNTAX OCTET STRING (SIZE (0..100))
            MAX-ACCESS read-only
            STATUS current
            DESCRIPTION
                "perPara."
            ::= { sccbdPer15MCurEntry 6 }




-- -------------------------------------------------------------------------
-- Perfomance 15-MIN History Data Table (RTRV-PER-<MOD2>)
-- -------------------------------------------------------------------------
        -- 1.3.6.1.4.1.2011.2.25.3.40.50.23.20
        sccbdPer15MHisTable OBJECT-TYPE
          SYNTAX SEQUENCE OF SccbdPer15MHisEntry
          MAX-ACCESS not-accessible
          STATUS current
          DESCRIPTION
              "sccbdPer15MHis."
          ::= { sccbd 20 }

        -- 1.3.6.1.4.1.2011.2.25.3.40.50.23.20.1
        sccbdPer15MHisEntry OBJECT-TYPE
            SYNTAX SccbdPer15MHisEntry
            MAX-ACCESS not-accessible
            STATUS current
            DESCRIPTION
                "sccbdPer15MHis."
            INDEX {sccbdPer15MHisEid, sccbdPer15MHisParaLen, sccbdPer15MHisPara, sccbdPer15MHisDateTimeStart, sccbdPer15MHisDateTimeEnd}
            ::= { sccbdPer15MHisTable 1 }

        SccbdPer15MHisEntry ::=
            SEQUENCE {
                sccbdPer15MHisEid
                    PerformanceEventType,
                sccbdPer15MHisParaLen
                    INTEGER,
                sccbdPer15MHisPara
                    OCTET STRING,
                sccbdPer15MHisMonValue
                    OCTET STRING,
                sccbdPer15MHisDateTimeStart
                    DateAndTime,
                sccbdPer15MHisDateTimeEnd
                    DateAndTime,
                sccbdPer15MHisVldty
                    INTEGER,
             }

        -- 1.3.6.1.4.1.2011.2.25.3.40.50.23.20.1.1
        sccbdPer15MHisEid OBJECT-TYPE
            SYNTAX PerformanceEventType
            MAX-ACCESS read-only
            STATUS current
            DESCRIPTION
                "perEid."
            ::= { sccbdPer15MHisEntry 1 }

        -- 1.3.6.1.4.1.2011.2.25.3.40.50.23.20.1.2
        sccbdPer15MHisParaLen OBJECT-TYPE
            SYNTAX INTEGER
            MAX-ACCESS read-only
            STATUS current
            DESCRIPTION
                "perParaLen."
            ::= { sccbdPer15MHisEntry 2 }

        -- 1.3.6.1.4.1.2011.2.25.3.40.50.23.20.1.3
        sccbdPer15MHisPara OBJECT-TYPE
            SYNTAX OCTET STRING (SIZE (0..100))
            MAX-ACCESS read-only
            STATUS current
            DESCRIPTION
                "perPara."
            ::= { sccbdPer15MHisEntry 3 }

        -- 1.3.6.1.4.1.2011.2.25.3.40.50.23.20.1.4
        sccbdPer15MHisMonValue OBJECT-TYPE
            SYNTAX OCTET STRING (SIZE (0..100))
            MAX-ACCESS read-only
            STATUS current
            DESCRIPTION
                "perMonValue."
            ::= { sccbdPer15MHisEntry 4 }

        -- 1.3.6.1.4.1.2011.2.25.3.40.50.23.20.1.5
        sccbdPer15MHisDateTimeStart OBJECT-TYPE
            SYNTAX DateAndTime
            MAX-ACCESS read-only
            STATUS current
            DESCRIPTION
                "perDateTimeStart. "
            ::= { sccbdPer15MHisEntry 5 }

        -- 1.3.6.1.4.1.2011.2.25.3.40.50.23.20.1.6
        sccbdPer15MHisDateTimeEnd OBJECT-TYPE
            SYNTAX DateAndTime
            MAX-ACCESS read-only
            STATUS current
            DESCRIPTION
                "perDateTimeEnd. "
            ::= { sccbdPer15MHisEntry 6 }

        -- 1.3.6.1.4.1.2011.2.25.3.40.50.23.20.1.7
        sccbdPer15MHisVldty OBJECT-TYPE
            SYNTAX INTEGER
            MAX-ACCESS read-only
            STATUS current
            DESCRIPTION
                "perVldty. "
            ::= { sccbdPer15MHisEntry 7 }




-- -------------------------------------------------------------------------
-- Perfomance 24-HOUR Current Data Table (RTRV-PER-<MOD2>)
-- -------------------------------------------------------------------------
        -- 1.3.6.1.4.1.2011.2.25.3.40.50.23.30
        sccbdPer24HCurTable OBJECT-TYPE
          SYNTAX SEQUENCE OF SccbdPer24HCurEntry
          MAX-ACCESS not-accessible
          STATUS current
          DESCRIPTION
              "sccbdPer24HCur."
          ::= { sccbd 30 }

        -- 1.3.6.1.4.1.2011.2.25.3.40.50.23.30.1
        sccbdPer24HCurEntry OBJECT-TYPE
            SYNTAX SccbdPer24HCurEntry
            MAX-ACCESS not-accessible
            STATUS current
            DESCRIPTION
              "sccbdPer24HCur."
            INDEX { sccbdPer24HCurEid, sccbdPer24HCurPara }
            ::= { sccbdPer24HCurTable 1 }

        SccbdPer24HCurEntry ::=
            SEQUENCE {
                sccbdPer24HCurEid
                    PerformanceEventType,
                sccbdPer24HCurMonValue
                    OCTET STRING,
                sccbdPer24HCurVldty
                    INTEGER,
                sccbdPer24HCurDateTime
                    DateAndTime,
                sccbdPer24HCurParaLen
                    INTEGER,
                sccbdPer24HCurPara
                    OCTET STRING
            }

        -- 1.3.6.1.4.1.2011.2.25.3.40.50.23.30.1.1
        sccbdPer24HCurEid OBJECT-TYPE
            SYNTAX PerformanceEventType
            MAX-ACCESS read-only
            STATUS current
            DESCRIPTION
                "perEid."
            ::= { sccbdPer24HCurEntry 1 }

        -- 1.3.6.1.4.1.2011.2.25.3.40.50.23.30.1.2
        sccbdPer24HCurMonValue OBJECT-TYPE
            SYNTAX OCTET STRING (SIZE (0..100))
            MAX-ACCESS read-only
            STATUS current
            DESCRIPTION
                "perMonValue."
            ::= { sccbdPer24HCurEntry 2 }

        -- 1.3.6.1.4.1.2011.2.25.3.40.50.23.30.1.3
        sccbdPer24HCurVldty OBJECT-TYPE
            SYNTAX INTEGER
            MAX-ACCESS read-only
            STATUS current
            DESCRIPTION
                "perVldty. "
            ::= { sccbdPer24HCurEntry 3 }

        -- 1.3.6.1.4.1.2011.2.25.3.40.50.23.30.1.4
        sccbdPer24HCurDateTime OBJECT-TYPE
            SYNTAX DateAndTime
            MAX-ACCESS read-only
            STATUS current
            DESCRIPTION
                "perDateTime. "
            ::= { sccbdPer24HCurEntry 4 }

        -- 1.3.6.1.4.1.2011.2.25.3.40.50.23.30.1.5
        sccbdPer24HCurParaLen OBJECT-TYPE
            SYNTAX INTEGER
            MAX-ACCESS read-only
            STATUS current
            DESCRIPTION
                "perParaLen."
            ::= { sccbdPer24HCurEntry 5 }

        -- 1.3.6.1.4.1.2011.2.25.3.40.50.23.30.1.6
        sccbdPer24HCurPara OBJECT-TYPE
            SYNTAX OCTET STRING (SIZE (0..100))
            MAX-ACCESS read-only
            STATUS current
            DESCRIPTION
                "perPara."
            ::= { sccbdPer24HCurEntry 6 }




-- -------------------------------------------------------------------------
-- Perfomance 24-HOUR History Data Table (RTRV-PER-<MOD2>)
-- -------------------------------------------------------------------------
        -- 1.3.6.1.4.1.2011.2.25.3.40.50.23.40
        sccbdPer24HHisTable OBJECT-TYPE
          SYNTAX SEQUENCE OF SccbdPer24HHisEntry
          MAX-ACCESS not-accessible
          STATUS current
          DESCRIPTION
              "sccbdPer24HHis."
          ::= { sccbd 40 }

        -- 1.3.6.1.4.1.2011.2.25.3.40.50.23.40.1
        sccbdPer24HHisEntry OBJECT-TYPE
            SYNTAX SccbdPer24HHisEntry
            MAX-ACCESS not-accessible
            STATUS current
            DESCRIPTION
                "sccbdPer24HHis."
            INDEX {sccbdPer24HHisEid, sccbdPer24HHisParaLen, sccbdPer24HHisPara, sccbdPer24HHisDateTimeStart, sccbdPer24HHisDateTimeEnd}
            ::= { sccbdPer24HHisTable 1 }

        SccbdPer24HHisEntry ::=
            SEQUENCE {
                sccbdPer24HHisEid
                    PerformanceEventType,
                sccbdPer24HHisParaLen
                    INTEGER,
                sccbdPer24HHisPara
                    OCTET STRING,
                sccbdPer24HHisMonValue
                    OCTET STRING,
                sccbdPer24HHisDateTimeStart
                    DateAndTime,
                sccbdPer24HHisDateTimeEnd
                    DateAndTime,
                sccbdPer24HHisVldty
                    INTEGER,
             }

        -- 1.3.6.1.4.1.2011.2.25.3.40.50.23.40.1.1
        sccbdPer24HHisEid OBJECT-TYPE
            SYNTAX PerformanceEventType
            MAX-ACCESS read-only
            STATUS current
            DESCRIPTION
                "perEid."
            ::= { sccbdPer24HHisEntry 1 }

        -- 1.3.6.1.4.1.2011.2.25.3.40.50.23.40.1.2
        sccbdPer24HHisParaLen OBJECT-TYPE
            SYNTAX INTEGER
            MAX-ACCESS read-only
            STATUS current
            DESCRIPTION
                "perParaLen."
            ::= { sccbdPer24HHisEntry 2 }

        -- 1.3.6.1.4.1.2011.2.25.3.40.50.23.40.1.3
        sccbdPer24HHisPara OBJECT-TYPE
            SYNTAX OCTET STRING (SIZE (0..100))
            MAX-ACCESS read-only
            STATUS current
            DESCRIPTION
                "perPara."
            ::= { sccbdPer24HHisEntry 3 }

        -- 1.3.6.1.4.1.2011.2.25.3.40.50.23.40.1.4
        sccbdPer24HHisMonValue OBJECT-TYPE
            SYNTAX OCTET STRING (SIZE (0..100))
            MAX-ACCESS read-only
            STATUS current
            DESCRIPTION
                "perMonValue."
            ::= { sccbdPer24HHisEntry 4 }

        -- 1.3.6.1.4.1.2011.2.25.3.40.50.23.40.1.5
        sccbdPer24HHisDateTimeStart OBJECT-TYPE
            SYNTAX DateAndTime
            MAX-ACCESS read-only
            STATUS current
            DESCRIPTION
                "perDateTimeStart. "
            ::= { sccbdPer24HHisEntry 5 }

        -- 1.3.6.1.4.1.2011.2.25.3.40.50.23.40.1.6
        sccbdPer24HHisDateTimeEnd OBJECT-TYPE
            SYNTAX DateAndTime
            MAX-ACCESS read-only
            STATUS current
            DESCRIPTION
                "perDateTimeEnd. "
            ::= { sccbdPer24HHisEntry 6 }

        -- 1.3.6.1.4.1.2011.2.25.3.40.50.23.40.1.7
        sccbdPer24HHisVldty OBJECT-TYPE
            SYNTAX INTEGER
            MAX-ACCESS read-only
            STATUS current
            DESCRIPTION
                "perVldty. "
            ::= { sccbdPer24HHisEntry 7 }




-- Alarm data
      -- 1.3.6.1.4.1.2011.2.25.3.40.50.30
      e1port OBJECT IDENTIFIER ::={ optixGlobalNGWDM 30 }


-- -------------------------------------------------------------------------
-- Perfomance 15-MIN Current Data Table (RTRV-PER-<MOD2>)
-- -------------------------------------------------------------------------
        -- 1.3.6.1.4.1.2011.2.25.3.40.50.30.10
        e1portPer15MCurTable OBJECT-TYPE
          SYNTAX SEQUENCE OF E1portPer15MCurEntry
          MAX-ACCESS not-accessible
          STATUS current
          DESCRIPTION
              "e1portPer15MCur."
          ::= { e1port 10 }

        -- 1.3.6.1.4.1.2011.2.25.3.40.50.30.10.1
        e1portPer15MCurEntry OBJECT-TYPE
            SYNTAX E1portPer15MCurEntry
            MAX-ACCESS not-accessible
            STATUS current
            DESCRIPTION
              "e1portPer15MCur."
            INDEX { e1portPer15MCurEid, e1portPer15MCurPara }
            ::= { e1portPer15MCurTable 1 }

        E1portPer15MCurEntry ::=
            SEQUENCE {
                e1portPer15MCurEid
                    PerformanceEventType,
                e1portPer15MCurMonValue
                    OCTET STRING,
                e1portPer15MCurVldty
                    INTEGER,
                e1portPer15MCurDateTime
                    DateAndTime,
                e1portPer15MCurParaLen
                    INTEGER,
                e1portPer15MCurPara
                    OCTET STRING
            }

        -- 1.3.6.1.4.1.2011.2.25.3.40.50.30.10.1.1
        e1portPer15MCurEid OBJECT-TYPE
            SYNTAX PerformanceEventType
            MAX-ACCESS read-only
            STATUS current
            DESCRIPTION
                "perEid."
            ::= { e1portPer15MCurEntry 1 }

        -- 1.3.6.1.4.1.2011.2.25.3.40.50.30.10.1.2
        e1portPer15MCurMonValue OBJECT-TYPE
            SYNTAX OCTET STRING (SIZE (0..100))
            MAX-ACCESS read-only
            STATUS current
            DESCRIPTION
                "perMonValue."
            ::= { e1portPer15MCurEntry 2 }

        -- 1.3.6.1.4.1.2011.2.25.3.40.50.30.10.1.3
        e1portPer15MCurVldty OBJECT-TYPE
            SYNTAX INTEGER
            MAX-ACCESS read-only
            STATUS current
            DESCRIPTION
                "perVldty. "
            ::= { e1portPer15MCurEntry 3 }

        -- 1.3.6.1.4.1.2011.2.25.3.40.50.30.10.1.4
        e1portPer15MCurDateTime OBJECT-TYPE
            SYNTAX DateAndTime
            MAX-ACCESS read-only
            STATUS current
            DESCRIPTION
                "perDateTime. "
            ::= { e1portPer15MCurEntry 4 }

        -- 1.3.6.1.4.1.2011.2.25.3.40.50.30.10.1.5
        e1portPer15MCurParaLen OBJECT-TYPE
            SYNTAX INTEGER
            MAX-ACCESS read-only
            STATUS current
            DESCRIPTION
                "perParaLen."
            ::= { e1portPer15MCurEntry 5 }

        -- 1.3.6.1.4.1.2011.2.25.3.40.50.30.10.1.6
        e1portPer15MCurPara OBJECT-TYPE
            SYNTAX OCTET STRING (SIZE (0..100))
            MAX-ACCESS read-only
            STATUS current
            DESCRIPTION
                "perPara."
            ::= { e1portPer15MCurEntry 6 }




-- -------------------------------------------------------------------------
-- Perfomance 15-MIN History Data Table (RTRV-PER-<MOD2>)
-- -------------------------------------------------------------------------
        -- 1.3.6.1.4.1.2011.2.25.3.40.50.30.20
        e1portPer15MHisTable OBJECT-TYPE
          SYNTAX SEQUENCE OF E1portPer15MHisEntry
          MAX-ACCESS not-accessible
          STATUS current
          DESCRIPTION
              "e1portPer15MHis."
          ::= { e1port 20 }

        -- 1.3.6.1.4.1.2011.2.25.3.40.50.30.20.1
        e1portPer15MHisEntry OBJECT-TYPE
            SYNTAX E1portPer15MHisEntry
            MAX-ACCESS not-accessible
            STATUS current
            DESCRIPTION
                "e1portPer15MHis."
            INDEX {e1portPer15MHisEid, e1portPer15MHisParaLen, e1portPer15MHisPara, e1portPer15MHisDateTimeStart, e1portPer15MHisDateTimeEnd}
            ::= { e1portPer15MHisTable 1 }

        E1portPer15MHisEntry ::=
            SEQUENCE {
                e1portPer15MHisEid
                    PerformanceEventType,
                e1portPer15MHisParaLen
                    INTEGER,
                e1portPer15MHisPara
                    OCTET STRING,
                e1portPer15MHisMonValue
                    OCTET STRING,
                e1portPer15MHisDateTimeStart
                    DateAndTime,
                e1portPer15MHisDateTimeEnd
                    DateAndTime,
                e1portPer15MHisVldty
                    INTEGER,
             }

        -- 1.3.6.1.4.1.2011.2.25.3.40.50.30.20.1.1
        e1portPer15MHisEid OBJECT-TYPE
            SYNTAX PerformanceEventType
            MAX-ACCESS read-only
            STATUS current
            DESCRIPTION
                "perEid."
            ::= { e1portPer15MHisEntry 1 }

        -- 1.3.6.1.4.1.2011.2.25.3.40.50.30.20.1.2
        e1portPer15MHisParaLen OBJECT-TYPE
            SYNTAX INTEGER
            MAX-ACCESS read-only
            STATUS current
            DESCRIPTION
                "perParaLen."
            ::= { e1portPer15MHisEntry 2 }

        -- 1.3.6.1.4.1.2011.2.25.3.40.50.30.20.1.3
        e1portPer15MHisPara OBJECT-TYPE
            SYNTAX OCTET STRING (SIZE (0..100))
            MAX-ACCESS read-only
            STATUS current
            DESCRIPTION
                "perPara."
            ::= { e1portPer15MHisEntry 3 }

        -- 1.3.6.1.4.1.2011.2.25.3.40.50.30.20.1.4
        e1portPer15MHisMonValue OBJECT-TYPE
            SYNTAX OCTET STRING (SIZE (0..100))
            MAX-ACCESS read-only
            STATUS current
            DESCRIPTION
                "perMonValue."
            ::= { e1portPer15MHisEntry 4 }

        -- 1.3.6.1.4.1.2011.2.25.3.40.50.30.20.1.5
        e1portPer15MHisDateTimeStart OBJECT-TYPE
            SYNTAX DateAndTime
            MAX-ACCESS read-only
            STATUS current
            DESCRIPTION
                "perDateTimeStart. "
            ::= { e1portPer15MHisEntry 5 }

        -- 1.3.6.1.4.1.2011.2.25.3.40.50.30.20.1.6
        e1portPer15MHisDateTimeEnd OBJECT-TYPE
            SYNTAX DateAndTime
            MAX-ACCESS read-only
            STATUS current
            DESCRIPTION
                "perDateTimeEnd. "
            ::= { e1portPer15MHisEntry 6 }

        -- 1.3.6.1.4.1.2011.2.25.3.40.50.30.20.1.7
        e1portPer15MHisVldty OBJECT-TYPE
            SYNTAX INTEGER
            MAX-ACCESS read-only
            STATUS current
            DESCRIPTION
                "perVldty. "
            ::= { e1portPer15MHisEntry 7 }




-- -------------------------------------------------------------------------
-- Perfomance 24-HOUR Current Data Table (RTRV-PER-<MOD2>)
-- -------------------------------------------------------------------------
        -- 1.3.6.1.4.1.2011.2.25.3.40.50.30.30
        e1portPer24HCurTable OBJECT-TYPE
          SYNTAX SEQUENCE OF E1portPer24HCurEntry
          MAX-ACCESS not-accessible
          STATUS current
          DESCRIPTION
              "e1portPer24HCur."
          ::= { e1port 30 }

        -- 1.3.6.1.4.1.2011.2.25.3.40.50.30.30.1
        e1portPer24HCurEntry OBJECT-TYPE
            SYNTAX E1portPer24HCurEntry
            MAX-ACCESS not-accessible
            STATUS current
            DESCRIPTION
              "e1portPer24HCur."
            INDEX { e1portPer24HCurEid, e1portPer24HCurPara }
            ::= { e1portPer24HCurTable 1 }

        E1portPer24HCurEntry ::=
            SEQUENCE {
                e1portPer24HCurEid
                    PerformanceEventType,
                e1portPer24HCurMonValue
                    OCTET STRING,
                e1portPer24HCurVldty
                    INTEGER,
                e1portPer24HCurDateTime
                    DateAndTime,
                e1portPer24HCurParaLen
                    INTEGER,
                e1portPer24HCurPara
                    OCTET STRING
            }

        -- 1.3.6.1.4.1.2011.2.25.3.40.50.30.30.1.1
        e1portPer24HCurEid OBJECT-TYPE
            SYNTAX PerformanceEventType
            MAX-ACCESS read-only
            STATUS current
            DESCRIPTION
                "perEid."
            ::= { e1portPer24HCurEntry 1 }

        -- 1.3.6.1.4.1.2011.2.25.3.40.50.30.30.1.2
        e1portPer24HCurMonValue OBJECT-TYPE
            SYNTAX OCTET STRING (SIZE (0..100))
            MAX-ACCESS read-only
            STATUS current
            DESCRIPTION
                "perMonValue."
            ::= { e1portPer24HCurEntry 2 }

        -- 1.3.6.1.4.1.2011.2.25.3.40.50.30.30.1.3
        e1portPer24HCurVldty OBJECT-TYPE
            SYNTAX INTEGER
            MAX-ACCESS read-only
            STATUS current
            DESCRIPTION
                "perVldty. "
            ::= { e1portPer24HCurEntry 3 }

        -- 1.3.6.1.4.1.2011.2.25.3.40.50.30.30.1.4
        e1portPer24HCurDateTime OBJECT-TYPE
            SYNTAX DateAndTime
            MAX-ACCESS read-only
            STATUS current
            DESCRIPTION
                "perDateTime. "
            ::= { e1portPer24HCurEntry 4 }

        -- 1.3.6.1.4.1.2011.2.25.3.40.50.30.30.1.5
        e1portPer24HCurParaLen OBJECT-TYPE
            SYNTAX INTEGER
            MAX-ACCESS read-only
            STATUS current
            DESCRIPTION
                "perParaLen."
            ::= { e1portPer24HCurEntry 5 }

        -- 1.3.6.1.4.1.2011.2.25.3.40.50.30.30.1.6
        e1portPer24HCurPara OBJECT-TYPE
            SYNTAX OCTET STRING (SIZE (0..100))
            MAX-ACCESS read-only
            STATUS current
            DESCRIPTION
                "perPara."
            ::= { e1portPer24HCurEntry 6 }




-- -------------------------------------------------------------------------
-- Perfomance 24-HOUR History Data Table (RTRV-PER-<MOD2>)
-- -------------------------------------------------------------------------
        -- 1.3.6.1.4.1.2011.2.25.3.40.50.30.40
        e1portPer24HHisTable OBJECT-TYPE
          SYNTAX SEQUENCE OF E1portPer24HHisEntry
          MAX-ACCESS not-accessible
          STATUS current
          DESCRIPTION
              "e1portPer24HHis."
          ::= { e1port 40 }

        -- 1.3.6.1.4.1.2011.2.25.3.40.50.30.40.1
        e1portPer24HHisEntry OBJECT-TYPE
            SYNTAX E1portPer24HHisEntry
            MAX-ACCESS not-accessible
            STATUS current
            DESCRIPTION
                "e1portPer24HHis."
            INDEX {e1portPer24HHisEid, e1portPer24HHisParaLen, e1portPer24HHisPara, e1portPer24HHisDateTimeStart, e1portPer24HHisDateTimeEnd}
            ::= { e1portPer24HHisTable 1 }

        E1portPer24HHisEntry ::=
            SEQUENCE {
                e1portPer24HHisEid
                    PerformanceEventType,
                e1portPer24HHisParaLen
                    INTEGER,
                e1portPer24HHisPara
                    OCTET STRING,
                e1portPer24HHisMonValue
                    OCTET STRING,
                e1portPer24HHisDateTimeStart
                    DateAndTime,
                e1portPer24HHisDateTimeEnd
                    DateAndTime,
                e1portPer24HHisVldty
                    INTEGER,
             }

        -- 1.3.6.1.4.1.2011.2.25.3.40.50.30.40.1.1
        e1portPer24HHisEid OBJECT-TYPE
            SYNTAX PerformanceEventType
            MAX-ACCESS read-only
            STATUS current
            DESCRIPTION
                "perEid."
            ::= { e1portPer24HHisEntry 1 }

        -- 1.3.6.1.4.1.2011.2.25.3.40.50.30.40.1.2
        e1portPer24HHisParaLen OBJECT-TYPE
            SYNTAX INTEGER
            MAX-ACCESS read-only
            STATUS current
            DESCRIPTION
                "perParaLen."
            ::= { e1portPer24HHisEntry 2 }

        -- 1.3.6.1.4.1.2011.2.25.3.40.50.30.40.1.3
        e1portPer24HHisPara OBJECT-TYPE
            SYNTAX OCTET STRING (SIZE (0..100))
            MAX-ACCESS read-only
            STATUS current
            DESCRIPTION
                "perPara."
            ::= { e1portPer24HHisEntry 3 }

        -- 1.3.6.1.4.1.2011.2.25.3.40.50.30.40.1.4
        e1portPer24HHisMonValue OBJECT-TYPE
            SYNTAX OCTET STRING (SIZE (0..100))
            MAX-ACCESS read-only
            STATUS current
            DESCRIPTION
                "perMonValue."
            ::= { e1portPer24HHisEntry 4 }

        -- 1.3.6.1.4.1.2011.2.25.3.40.50.30.40.1.5
        e1portPer24HHisDateTimeStart OBJECT-TYPE
            SYNTAX DateAndTime
            MAX-ACCESS read-only
            STATUS current
            DESCRIPTION
                "perDateTimeStart. "
            ::= { e1portPer24HHisEntry 5 }

        -- 1.3.6.1.4.1.2011.2.25.3.40.50.30.40.1.6
        e1portPer24HHisDateTimeEnd OBJECT-TYPE
            SYNTAX DateAndTime
            MAX-ACCESS read-only
            STATUS current
            DESCRIPTION
                "perDateTimeEnd. "
            ::= { e1portPer24HHisEntry 6 }

        -- 1.3.6.1.4.1.2011.2.25.3.40.50.30.40.1.7
        e1portPer24HHisVldty OBJECT-TYPE
            SYNTAX INTEGER
            MAX-ACCESS read-only
            STATUS current
            DESCRIPTION
                "perVldty. "
            ::= { e1portPer24HHisEntry 7 }




-- Alarm data
      -- 1.3.6.1.4.1.2011.2.25.3.40.50.34
      pl_path OBJECT IDENTIFIER ::={ optixGlobalNGWDM 34 }


-- -------------------------------------------------------------------------
-- Perfomance 15-MIN Current Data Table (RTRV-PER-<MOD2>)
-- -------------------------------------------------------------------------
        -- 1.3.6.1.4.1.2011.2.25.3.40.50.34.10
        pl_pathPer15MCurTable OBJECT-TYPE
          SYNTAX SEQUENCE OF Pl_pathPer15MCurEntry
          MAX-ACCESS not-accessible
          STATUS current
          DESCRIPTION
              "pl_pathPer15MCur."
          ::= { pl_path 10 }

        -- 1.3.6.1.4.1.2011.2.25.3.40.50.34.10.1
        pl_pathPer15MCurEntry OBJECT-TYPE
            SYNTAX Pl_pathPer15MCurEntry
            MAX-ACCESS not-accessible
            STATUS current
            DESCRIPTION
              "pl_pathPer15MCur."
            INDEX { pl_pathPer15MCurEid, pl_pathPer15MCurPara }
            ::= { pl_pathPer15MCurTable 1 }

        Pl_pathPer15MCurEntry ::=
            SEQUENCE {
                pl_pathPer15MCurEid
                    PerformanceEventType,
                pl_pathPer15MCurMonValue
                    OCTET STRING,
                pl_pathPer15MCurVldty
                    INTEGER,
                pl_pathPer15MCurDateTime
                    DateAndTime,
                pl_pathPer15MCurParaLen
                    INTEGER,
                pl_pathPer15MCurPara
                    OCTET STRING
            }

        -- 1.3.6.1.4.1.2011.2.25.3.40.50.34.10.1.1
        pl_pathPer15MCurEid OBJECT-TYPE
            SYNTAX PerformanceEventType
            MAX-ACCESS read-only
            STATUS current
            DESCRIPTION
                "perEid."
            ::= { pl_pathPer15MCurEntry 1 }

        -- 1.3.6.1.4.1.2011.2.25.3.40.50.34.10.1.2
        pl_pathPer15MCurMonValue OBJECT-TYPE
            SYNTAX OCTET STRING (SIZE (0..100))
            MAX-ACCESS read-only
            STATUS current
            DESCRIPTION
                "perMonValue."
            ::= { pl_pathPer15MCurEntry 2 }

        -- 1.3.6.1.4.1.2011.2.25.3.40.50.34.10.1.3
        pl_pathPer15MCurVldty OBJECT-TYPE
            SYNTAX INTEGER
            MAX-ACCESS read-only
            STATUS current
            DESCRIPTION
                "perVldty. "
            ::= { pl_pathPer15MCurEntry 3 }

        -- 1.3.6.1.4.1.2011.2.25.3.40.50.34.10.1.4
        pl_pathPer15MCurDateTime OBJECT-TYPE
            SYNTAX DateAndTime
            MAX-ACCESS read-only
            STATUS current
            DESCRIPTION
                "perDateTime. "
            ::= { pl_pathPer15MCurEntry 4 }

        -- 1.3.6.1.4.1.2011.2.25.3.40.50.34.10.1.5
        pl_pathPer15MCurParaLen OBJECT-TYPE
            SYNTAX INTEGER
            MAX-ACCESS read-only
            STATUS current
            DESCRIPTION
                "perParaLen."
            ::= { pl_pathPer15MCurEntry 5 }

        -- 1.3.6.1.4.1.2011.2.25.3.40.50.34.10.1.6
        pl_pathPer15MCurPara OBJECT-TYPE
            SYNTAX OCTET STRING (SIZE (0..100))
            MAX-ACCESS read-only
            STATUS current
            DESCRIPTION
                "perPara."
            ::= { pl_pathPer15MCurEntry 6 }




-- -------------------------------------------------------------------------
-- Perfomance 15-MIN History Data Table (RTRV-PER-<MOD2>)
-- -------------------------------------------------------------------------
        -- 1.3.6.1.4.1.2011.2.25.3.40.50.34.20
        pl_pathPer15MHisTable OBJECT-TYPE
          SYNTAX SEQUENCE OF Pl_pathPer15MHisEntry
          MAX-ACCESS not-accessible
          STATUS current
          DESCRIPTION
              "pl_pathPer15MHis."
          ::= { pl_path 20 }

        -- 1.3.6.1.4.1.2011.2.25.3.40.50.34.20.1
        pl_pathPer15MHisEntry OBJECT-TYPE
            SYNTAX Pl_pathPer15MHisEntry
            MAX-ACCESS not-accessible
            STATUS current
            DESCRIPTION
                "pl_pathPer15MHis."
            INDEX {pl_pathPer15MHisEid, pl_pathPer15MHisParaLen, pl_pathPer15MHisPara, pl_pathPer15MHisDateTimeStart, pl_pathPer15MHisDateTimeEnd}
            ::= { pl_pathPer15MHisTable 1 }

        Pl_pathPer15MHisEntry ::=
            SEQUENCE {
                pl_pathPer15MHisEid
                    PerformanceEventType,
                pl_pathPer15MHisParaLen
                    INTEGER,
                pl_pathPer15MHisPara
                    OCTET STRING,
                pl_pathPer15MHisMonValue
                    OCTET STRING,
                pl_pathPer15MHisDateTimeStart
                    DateAndTime,
                pl_pathPer15MHisDateTimeEnd
                    DateAndTime,
                pl_pathPer15MHisVldty
                    INTEGER,
             }

        -- 1.3.6.1.4.1.2011.2.25.3.40.50.34.20.1.1
        pl_pathPer15MHisEid OBJECT-TYPE
            SYNTAX PerformanceEventType
            MAX-ACCESS read-only
            STATUS current
            DESCRIPTION
                "perEid."
            ::= { pl_pathPer15MHisEntry 1 }

        -- 1.3.6.1.4.1.2011.2.25.3.40.50.34.20.1.2
        pl_pathPer15MHisParaLen OBJECT-TYPE
            SYNTAX INTEGER
            MAX-ACCESS read-only
            STATUS current
            DESCRIPTION
                "perParaLen."
            ::= { pl_pathPer15MHisEntry 2 }

        -- 1.3.6.1.4.1.2011.2.25.3.40.50.34.20.1.3
        pl_pathPer15MHisPara OBJECT-TYPE
            SYNTAX OCTET STRING (SIZE (0..100))
            MAX-ACCESS read-only
            STATUS current
            DESCRIPTION
                "perPara."
            ::= { pl_pathPer15MHisEntry 3 }

        -- 1.3.6.1.4.1.2011.2.25.3.40.50.34.20.1.4
        pl_pathPer15MHisMonValue OBJECT-TYPE
            SYNTAX OCTET STRING (SIZE (0..100))
            MAX-ACCESS read-only
            STATUS current
            DESCRIPTION
                "perMonValue."
            ::= { pl_pathPer15MHisEntry 4 }

        -- 1.3.6.1.4.1.2011.2.25.3.40.50.34.20.1.5
        pl_pathPer15MHisDateTimeStart OBJECT-TYPE
            SYNTAX DateAndTime
            MAX-ACCESS read-only
            STATUS current
            DESCRIPTION
                "perDateTimeStart. "
            ::= { pl_pathPer15MHisEntry 5 }

        -- 1.3.6.1.4.1.2011.2.25.3.40.50.34.20.1.6
        pl_pathPer15MHisDateTimeEnd OBJECT-TYPE
            SYNTAX DateAndTime
            MAX-ACCESS read-only
            STATUS current
            DESCRIPTION
                "perDateTimeEnd. "
            ::= { pl_pathPer15MHisEntry 6 }

        -- 1.3.6.1.4.1.2011.2.25.3.40.50.34.20.1.7
        pl_pathPer15MHisVldty OBJECT-TYPE
            SYNTAX INTEGER
            MAX-ACCESS read-only
            STATUS current
            DESCRIPTION
                "perVldty. "
            ::= { pl_pathPer15MHisEntry 7 }




-- -------------------------------------------------------------------------
-- Perfomance 24-HOUR Current Data Table (RTRV-PER-<MOD2>)
-- -------------------------------------------------------------------------
        -- 1.3.6.1.4.1.2011.2.25.3.40.50.34.30
        pl_pathPer24HCurTable OBJECT-TYPE
          SYNTAX SEQUENCE OF Pl_pathPer24HCurEntry
          MAX-ACCESS not-accessible
          STATUS current
          DESCRIPTION
              "pl_pathPer24HCur."
          ::= { pl_path 30 }

        -- 1.3.6.1.4.1.2011.2.25.3.40.50.34.30.1
        pl_pathPer24HCurEntry OBJECT-TYPE
            SYNTAX Pl_pathPer24HCurEntry
            MAX-ACCESS not-accessible
            STATUS current
            DESCRIPTION
              "pl_pathPer24HCur."
            INDEX { pl_pathPer24HCurEid, pl_pathPer24HCurPara }
            ::= { pl_pathPer24HCurTable 1 }

        Pl_pathPer24HCurEntry ::=
            SEQUENCE {
                pl_pathPer24HCurEid
                    PerformanceEventType,
                pl_pathPer24HCurMonValue
                    OCTET STRING,
                pl_pathPer24HCurVldty
                    INTEGER,
                pl_pathPer24HCurDateTime
                    DateAndTime,
                pl_pathPer24HCurParaLen
                    INTEGER,
                pl_pathPer24HCurPara
                    OCTET STRING
            }

        -- 1.3.6.1.4.1.2011.2.25.3.40.50.34.30.1.1
        pl_pathPer24HCurEid OBJECT-TYPE
            SYNTAX PerformanceEventType
            MAX-ACCESS read-only
            STATUS current
            DESCRIPTION
                "perEid."
            ::= { pl_pathPer24HCurEntry 1 }

        -- 1.3.6.1.4.1.2011.2.25.3.40.50.34.30.1.2
        pl_pathPer24HCurMonValue OBJECT-TYPE
            SYNTAX OCTET STRING (SIZE (0..100))
            MAX-ACCESS read-only
            STATUS current
            DESCRIPTION
                "perMonValue."
            ::= { pl_pathPer24HCurEntry 2 }

        -- 1.3.6.1.4.1.2011.2.25.3.40.50.34.30.1.3
        pl_pathPer24HCurVldty OBJECT-TYPE
            SYNTAX INTEGER
            MAX-ACCESS read-only
            STATUS current
            DESCRIPTION
                "perVldty. "
            ::= { pl_pathPer24HCurEntry 3 }

        -- 1.3.6.1.4.1.2011.2.25.3.40.50.34.30.1.4
        pl_pathPer24HCurDateTime OBJECT-TYPE
            SYNTAX DateAndTime
            MAX-ACCESS read-only
            STATUS current
            DESCRIPTION
                "perDateTime. "
            ::= { pl_pathPer24HCurEntry 4 }

        -- 1.3.6.1.4.1.2011.2.25.3.40.50.34.30.1.5
        pl_pathPer24HCurParaLen OBJECT-TYPE
            SYNTAX INTEGER
            MAX-ACCESS read-only
            STATUS current
            DESCRIPTION
                "perParaLen."
            ::= { pl_pathPer24HCurEntry 5 }

        -- 1.3.6.1.4.1.2011.2.25.3.40.50.34.30.1.6
        pl_pathPer24HCurPara OBJECT-TYPE
            SYNTAX OCTET STRING (SIZE (0..100))
            MAX-ACCESS read-only
            STATUS current
            DESCRIPTION
                "perPara."
            ::= { pl_pathPer24HCurEntry 6 }




-- -------------------------------------------------------------------------
-- Perfomance 24-HOUR History Data Table (RTRV-PER-<MOD2>)
-- -------------------------------------------------------------------------
        -- 1.3.6.1.4.1.2011.2.25.3.40.50.34.40
        pl_pathPer24HHisTable OBJECT-TYPE
          SYNTAX SEQUENCE OF Pl_pathPer24HHisEntry
          MAX-ACCESS not-accessible
          STATUS current
          DESCRIPTION
              "pl_pathPer24HHis."
          ::= { pl_path 40 }

        -- 1.3.6.1.4.1.2011.2.25.3.40.50.34.40.1
        pl_pathPer24HHisEntry OBJECT-TYPE
            SYNTAX Pl_pathPer24HHisEntry
            MAX-ACCESS not-accessible
            STATUS current
            DESCRIPTION
                "pl_pathPer24HHis."
            INDEX {pl_pathPer24HHisEid, pl_pathPer24HHisParaLen, pl_pathPer24HHisPara, pl_pathPer24HHisDateTimeStart, pl_pathPer24HHisDateTimeEnd}
            ::= { pl_pathPer24HHisTable 1 }

        Pl_pathPer24HHisEntry ::=
            SEQUENCE {
                pl_pathPer24HHisEid
                    PerformanceEventType,
                pl_pathPer24HHisParaLen
                    INTEGER,
                pl_pathPer24HHisPara
                    OCTET STRING,
                pl_pathPer24HHisMonValue
                    OCTET STRING,
                pl_pathPer24HHisDateTimeStart
                    DateAndTime,
                pl_pathPer24HHisDateTimeEnd
                    DateAndTime,
                pl_pathPer24HHisVldty
                    INTEGER,
             }

        -- 1.3.6.1.4.1.2011.2.25.3.40.50.34.40.1.1
        pl_pathPer24HHisEid OBJECT-TYPE
            SYNTAX PerformanceEventType
            MAX-ACCESS read-only
            STATUS current
            DESCRIPTION
                "perEid."
            ::= { pl_pathPer24HHisEntry 1 }

        -- 1.3.6.1.4.1.2011.2.25.3.40.50.34.40.1.2
        pl_pathPer24HHisParaLen OBJECT-TYPE
            SYNTAX INTEGER
            MAX-ACCESS read-only
            STATUS current
            DESCRIPTION
                "perParaLen."
            ::= { pl_pathPer24HHisEntry 2 }

        -- 1.3.6.1.4.1.2011.2.25.3.40.50.34.40.1.3
        pl_pathPer24HHisPara OBJECT-TYPE
            SYNTAX OCTET STRING (SIZE (0..100))
            MAX-ACCESS read-only
            STATUS current
            DESCRIPTION
                "perPara."
            ::= { pl_pathPer24HHisEntry 3 }

        -- 1.3.6.1.4.1.2011.2.25.3.40.50.34.40.1.4
        pl_pathPer24HHisMonValue OBJECT-TYPE
            SYNTAX OCTET STRING (SIZE (0..100))
            MAX-ACCESS read-only
            STATUS current
            DESCRIPTION
                "perMonValue."
            ::= { pl_pathPer24HHisEntry 4 }

        -- 1.3.6.1.4.1.2011.2.25.3.40.50.34.40.1.5
        pl_pathPer24HHisDateTimeStart OBJECT-TYPE
            SYNTAX DateAndTime
            MAX-ACCESS read-only
            STATUS current
            DESCRIPTION
                "perDateTimeStart. "
            ::= { pl_pathPer24HHisEntry 5 }

        -- 1.3.6.1.4.1.2011.2.25.3.40.50.34.40.1.6
        pl_pathPer24HHisDateTimeEnd OBJECT-TYPE
            SYNTAX DateAndTime
            MAX-ACCESS read-only
            STATUS current
            DESCRIPTION
                "perDateTimeEnd. "
            ::= { pl_pathPer24HHisEntry 6 }

        -- 1.3.6.1.4.1.2011.2.25.3.40.50.34.40.1.7
        pl_pathPer24HHisVldty OBJECT-TYPE
            SYNTAX INTEGER
            MAX-ACCESS read-only
            STATUS current
            DESCRIPTION
                "perVldty. "
            ::= { pl_pathPer24HHisEntry 7 }




-- Alarm data
      -- 1.3.6.1.4.1.2011.2.25.3.40.50.80
      client_port OBJECT IDENTIFIER ::={ optixGlobalNGWDM 80 }


-- -------------------------------------------------------------------------
-- Perfomance 15-MIN Current Data Table (RTRV-PER-<MOD2>)
-- -------------------------------------------------------------------------
        -- 1.3.6.1.4.1.2011.2.25.3.40.50.80.10
        client_portPer15MCurTable OBJECT-TYPE
          SYNTAX SEQUENCE OF Client_portPer15MCurEntry
          MAX-ACCESS not-accessible
          STATUS current
          DESCRIPTION
              "client_portPer15MCur."
          ::= { client_port 10 }

        -- 1.3.6.1.4.1.2011.2.25.3.40.50.80.10.1
        client_portPer15MCurEntry OBJECT-TYPE
            SYNTAX Client_portPer15MCurEntry
            MAX-ACCESS not-accessible
            STATUS current
            DESCRIPTION
              "client_portPer15MCur."
            INDEX { client_portPer15MCurEid, client_portPer15MCurPara }
            ::= { client_portPer15MCurTable 1 }

        Client_portPer15MCurEntry ::=
            SEQUENCE {
                client_portPer15MCurEid
                    PerformanceEventType,
                client_portPer15MCurMonValue
                    OCTET STRING,
                client_portPer15MCurVldty
                    INTEGER,
                client_portPer15MCurDateTime
                    DateAndTime,
                client_portPer15MCurParaLen
                    INTEGER,
                client_portPer15MCurPara
                    OCTET STRING
            }

        -- 1.3.6.1.4.1.2011.2.25.3.40.50.80.10.1.1
        client_portPer15MCurEid OBJECT-TYPE
            SYNTAX PerformanceEventType
            MAX-ACCESS read-only
            STATUS current
            DESCRIPTION
                "perEid."
            ::= { client_portPer15MCurEntry 1 }

        -- 1.3.6.1.4.1.2011.2.25.3.40.50.80.10.1.2
        client_portPer15MCurMonValue OBJECT-TYPE
            SYNTAX OCTET STRING (SIZE (0..100))
            MAX-ACCESS read-only
            STATUS current
            DESCRIPTION
                "perMonValue."
            ::= { client_portPer15MCurEntry 2 }

        -- 1.3.6.1.4.1.2011.2.25.3.40.50.80.10.1.3
        client_portPer15MCurVldty OBJECT-TYPE
            SYNTAX INTEGER
            MAX-ACCESS read-only
            STATUS current
            DESCRIPTION
                "perVldty. "
            ::= { client_portPer15MCurEntry 3 }

        -- 1.3.6.1.4.1.2011.2.25.3.40.50.80.10.1.4
        client_portPer15MCurDateTime OBJECT-TYPE
            SYNTAX DateAndTime
            MAX-ACCESS read-only
            STATUS current
            DESCRIPTION
                "perDateTime. "
            ::= { client_portPer15MCurEntry 4 }

        -- 1.3.6.1.4.1.2011.2.25.3.40.50.80.10.1.5
        client_portPer15MCurParaLen OBJECT-TYPE
            SYNTAX INTEGER
            MAX-ACCESS read-only
            STATUS current
            DESCRIPTION
                "perParaLen."
            ::= { client_portPer15MCurEntry 5 }

        -- 1.3.6.1.4.1.2011.2.25.3.40.50.80.10.1.6
        client_portPer15MCurPara OBJECT-TYPE
            SYNTAX OCTET STRING (SIZE (0..100))
            MAX-ACCESS read-only
            STATUS current
            DESCRIPTION
                "perPara."
            ::= { client_portPer15MCurEntry 6 }




-- -------------------------------------------------------------------------
-- Perfomance 15-MIN History Data Table (RTRV-PER-<MOD2>)
-- -------------------------------------------------------------------------
        -- 1.3.6.1.4.1.2011.2.25.3.40.50.80.20
        client_portPer15MHisTable OBJECT-TYPE
          SYNTAX SEQUENCE OF Client_portPer15MHisEntry
          MAX-ACCESS not-accessible
          STATUS current
          DESCRIPTION
              "client_portPer15MHis."
          ::= { client_port 20 }

        -- 1.3.6.1.4.1.2011.2.25.3.40.50.80.20.1
        client_portPer15MHisEntry OBJECT-TYPE
            SYNTAX Client_portPer15MHisEntry
            MAX-ACCESS not-accessible
            STATUS current
            DESCRIPTION
                "client_portPer15MHis."
            INDEX {client_portPer15MHisEid, client_portPer15MHisParaLen, client_portPer15MHisPara, client_portPer15MHisDateTimeStart, client_portPer15MHisDateTimeEnd}
            ::= { client_portPer15MHisTable 1 }

        Client_portPer15MHisEntry ::=
            SEQUENCE {
                client_portPer15MHisEid
                    PerformanceEventType,
                client_portPer15MHisParaLen
                    INTEGER,
                client_portPer15MHisPara
                    OCTET STRING,
                client_portPer15MHisMonValue
                    OCTET STRING,
                client_portPer15MHisDateTimeStart
                    DateAndTime,
                client_portPer15MHisDateTimeEnd
                    DateAndTime,
                client_portPer15MHisVldty
                    INTEGER,
             }

        -- 1.3.6.1.4.1.2011.2.25.3.40.50.80.20.1.1
        client_portPer15MHisEid OBJECT-TYPE
            SYNTAX PerformanceEventType
            MAX-ACCESS read-only
            STATUS current
            DESCRIPTION
                "perEid."
            ::= { client_portPer15MHisEntry 1 }

        -- 1.3.6.1.4.1.2011.2.25.3.40.50.80.20.1.2
        client_portPer15MHisParaLen OBJECT-TYPE
            SYNTAX INTEGER
            MAX-ACCESS read-only
            STATUS current
            DESCRIPTION
                "perParaLen."
            ::= { client_portPer15MHisEntry 2 }

        -- 1.3.6.1.4.1.2011.2.25.3.40.50.80.20.1.3
        client_portPer15MHisPara OBJECT-TYPE
            SYNTAX OCTET STRING (SIZE (0..100))
            MAX-ACCESS read-only
            STATUS current
            DESCRIPTION
                "perPara."
            ::= { client_portPer15MHisEntry 3 }

        -- 1.3.6.1.4.1.2011.2.25.3.40.50.80.20.1.4
        client_portPer15MHisMonValue OBJECT-TYPE
            SYNTAX OCTET STRING (SIZE (0..100))
            MAX-ACCESS read-only
            STATUS current
            DESCRIPTION
                "perMonValue."
            ::= { client_portPer15MHisEntry 4 }

        -- 1.3.6.1.4.1.2011.2.25.3.40.50.80.20.1.5
        client_portPer15MHisDateTimeStart OBJECT-TYPE
            SYNTAX DateAndTime
            MAX-ACCESS read-only
            STATUS current
            DESCRIPTION
                "perDateTimeStart. "
            ::= { client_portPer15MHisEntry 5 }

        -- 1.3.6.1.4.1.2011.2.25.3.40.50.80.20.1.6
        client_portPer15MHisDateTimeEnd OBJECT-TYPE
            SYNTAX DateAndTime
            MAX-ACCESS read-only
            STATUS current
            DESCRIPTION
                "perDateTimeEnd. "
            ::= { client_portPer15MHisEntry 6 }

        -- 1.3.6.1.4.1.2011.2.25.3.40.50.80.20.1.7
        client_portPer15MHisVldty OBJECT-TYPE
            SYNTAX INTEGER
            MAX-ACCESS read-only
            STATUS current
            DESCRIPTION
                "perVldty. "
            ::= { client_portPer15MHisEntry 7 }




-- -------------------------------------------------------------------------
-- Perfomance 24-HOUR Current Data Table (RTRV-PER-<MOD2>)
-- -------------------------------------------------------------------------
        -- 1.3.6.1.4.1.2011.2.25.3.40.50.80.30
        client_portPer24HCurTable OBJECT-TYPE
          SYNTAX SEQUENCE OF Client_portPer24HCurEntry
          MAX-ACCESS not-accessible
          STATUS current
          DESCRIPTION
              "client_portPer24HCur."
          ::= { client_port 30 }

        -- 1.3.6.1.4.1.2011.2.25.3.40.50.80.30.1
        client_portPer24HCurEntry OBJECT-TYPE
            SYNTAX Client_portPer24HCurEntry
            MAX-ACCESS not-accessible
            STATUS current
            DESCRIPTION
              "client_portPer24HCur."
            INDEX { client_portPer24HCurEid, client_portPer24HCurPara }
            ::= { client_portPer24HCurTable 1 }

        Client_portPer24HCurEntry ::=
            SEQUENCE {
                client_portPer24HCurEid
                    PerformanceEventType,
                client_portPer24HCurMonValue
                    OCTET STRING,
                client_portPer24HCurVldty
                    INTEGER,
                client_portPer24HCurDateTime
                    DateAndTime,
                client_portPer24HCurParaLen
                    INTEGER,
                client_portPer24HCurPara
                    OCTET STRING
            }

        -- 1.3.6.1.4.1.2011.2.25.3.40.50.80.30.1.1
        client_portPer24HCurEid OBJECT-TYPE
            SYNTAX PerformanceEventType
            MAX-ACCESS read-only
            STATUS current
            DESCRIPTION
                "perEid."
            ::= { client_portPer24HCurEntry 1 }

        -- 1.3.6.1.4.1.2011.2.25.3.40.50.80.30.1.2
        client_portPer24HCurMonValue OBJECT-TYPE
            SYNTAX OCTET STRING (SIZE (0..100))
            MAX-ACCESS read-only
            STATUS current
            DESCRIPTION
                "perMonValue."
            ::= { client_portPer24HCurEntry 2 }

        -- 1.3.6.1.4.1.2011.2.25.3.40.50.80.30.1.3
        client_portPer24HCurVldty OBJECT-TYPE
            SYNTAX INTEGER
            MAX-ACCESS read-only
            STATUS current
            DESCRIPTION
                "perVldty. "
            ::= { client_portPer24HCurEntry 3 }

        -- 1.3.6.1.4.1.2011.2.25.3.40.50.80.30.1.4
        client_portPer24HCurDateTime OBJECT-TYPE
            SYNTAX DateAndTime
            MAX-ACCESS read-only
            STATUS current
            DESCRIPTION
                "perDateTime. "
            ::= { client_portPer24HCurEntry 4 }

        -- 1.3.6.1.4.1.2011.2.25.3.40.50.80.30.1.5
        client_portPer24HCurParaLen OBJECT-TYPE
            SYNTAX INTEGER
            MAX-ACCESS read-only
            STATUS current
            DESCRIPTION
                "perParaLen."
            ::= { client_portPer24HCurEntry 5 }

        -- 1.3.6.1.4.1.2011.2.25.3.40.50.80.30.1.6
        client_portPer24HCurPara OBJECT-TYPE
            SYNTAX OCTET STRING (SIZE (0..100))
            MAX-ACCESS read-only
            STATUS current
            DESCRIPTION
                "perPara."
            ::= { client_portPer24HCurEntry 6 }




-- -------------------------------------------------------------------------
-- Perfomance 24-HOUR History Data Table (RTRV-PER-<MOD2>)
-- -------------------------------------------------------------------------
        -- 1.3.6.1.4.1.2011.2.25.3.40.50.80.40
        client_portPer24HHisTable OBJECT-TYPE
          SYNTAX SEQUENCE OF Client_portPer24HHisEntry
          MAX-ACCESS not-accessible
          STATUS current
          DESCRIPTION
              "client_portPer24HHis."
          ::= { client_port 40 }

        -- 1.3.6.1.4.1.2011.2.25.3.40.50.80.40.1
        client_portPer24HHisEntry OBJECT-TYPE
            SYNTAX Client_portPer24HHisEntry
            MAX-ACCESS not-accessible
            STATUS current
            DESCRIPTION
                "client_portPer24HHis."
            INDEX {client_portPer24HHisEid, client_portPer24HHisParaLen, client_portPer24HHisPara, client_portPer24HHisDateTimeStart, client_portPer24HHisDateTimeEnd}
            ::= { client_portPer24HHisTable 1 }

        Client_portPer24HHisEntry ::=
            SEQUENCE {
                client_portPer24HHisEid
                    PerformanceEventType,
                client_portPer24HHisParaLen
                    INTEGER,
                client_portPer24HHisPara
                    OCTET STRING,
                client_portPer24HHisMonValue
                    OCTET STRING,
                client_portPer24HHisDateTimeStart
                    DateAndTime,
                client_portPer24HHisDateTimeEnd
                    DateAndTime,
                client_portPer24HHisVldty
                    INTEGER,
             }

        -- 1.3.6.1.4.1.2011.2.25.3.40.50.80.40.1.1
        client_portPer24HHisEid OBJECT-TYPE
            SYNTAX PerformanceEventType
            MAX-ACCESS read-only
            STATUS current
            DESCRIPTION
                "perEid."
            ::= { client_portPer24HHisEntry 1 }

        -- 1.3.6.1.4.1.2011.2.25.3.40.50.80.40.1.2
        client_portPer24HHisParaLen OBJECT-TYPE
            SYNTAX INTEGER
            MAX-ACCESS read-only
            STATUS current
            DESCRIPTION
                "perParaLen."
            ::= { client_portPer24HHisEntry 2 }

        -- 1.3.6.1.4.1.2011.2.25.3.40.50.80.40.1.3
        client_portPer24HHisPara OBJECT-TYPE
            SYNTAX OCTET STRING (SIZE (0..100))
            MAX-ACCESS read-only
            STATUS current
            DESCRIPTION
                "perPara."
            ::= { client_portPer24HHisEntry 3 }

        -- 1.3.6.1.4.1.2011.2.25.3.40.50.80.40.1.4
        client_portPer24HHisMonValue OBJECT-TYPE
            SYNTAX OCTET STRING (SIZE (0..100))
            MAX-ACCESS read-only
            STATUS current
            DESCRIPTION
                "perMonValue."
            ::= { client_portPer24HHisEntry 4 }

        -- 1.3.6.1.4.1.2011.2.25.3.40.50.80.40.1.5
        client_portPer24HHisDateTimeStart OBJECT-TYPE
            SYNTAX DateAndTime
            MAX-ACCESS read-only
            STATUS current
            DESCRIPTION
                "perDateTimeStart. "
            ::= { client_portPer24HHisEntry 5 }

        -- 1.3.6.1.4.1.2011.2.25.3.40.50.80.40.1.6
        client_portPer24HHisDateTimeEnd OBJECT-TYPE
            SYNTAX DateAndTime
            MAX-ACCESS read-only
            STATUS current
            DESCRIPTION
                "perDateTimeEnd. "
            ::= { client_portPer24HHisEntry 6 }

        -- 1.3.6.1.4.1.2011.2.25.3.40.50.80.40.1.7
        client_portPer24HHisVldty OBJECT-TYPE
            SYNTAX INTEGER
            MAX-ACCESS read-only
            STATUS current
            DESCRIPTION
                "perVldty. "
            ::= { client_portPer24HHisEntry 7 }




-- Alarm data
      -- 1.3.6.1.4.1.2011.2.25.3.40.50.81
      och_port OBJECT IDENTIFIER ::={ optixGlobalNGWDM 81 }


-- -------------------------------------------------------------------------
-- Perfomance 15-MIN Current Data Table (RTRV-PER-<MOD2>)
-- -------------------------------------------------------------------------
        -- 1.3.6.1.4.1.2011.2.25.3.40.50.81.10
        och_portPer15MCurTable OBJECT-TYPE
          SYNTAX SEQUENCE OF Och_portPer15MCurEntry
          MAX-ACCESS not-accessible
          STATUS current
          DESCRIPTION
              "och_portPer15MCur."
          ::= { och_port 10 }

        -- 1.3.6.1.4.1.2011.2.25.3.40.50.81.10.1
        och_portPer15MCurEntry OBJECT-TYPE
            SYNTAX Och_portPer15MCurEntry
            MAX-ACCESS not-accessible
            STATUS current
            DESCRIPTION
              "och_portPer15MCur."
            INDEX { och_portPer15MCurEid, och_portPer15MCurPara }
            ::= { och_portPer15MCurTable 1 }

        Och_portPer15MCurEntry ::=
            SEQUENCE {
                och_portPer15MCurEid
                    PerformanceEventType,
                och_portPer15MCurMonValue
                    OCTET STRING,
                och_portPer15MCurVldty
                    INTEGER,
                och_portPer15MCurDateTime
                    DateAndTime,
                och_portPer15MCurParaLen
                    INTEGER,
                och_portPer15MCurPara
                    OCTET STRING
            }

        -- 1.3.6.1.4.1.2011.2.25.3.40.50.81.10.1.1
        och_portPer15MCurEid OBJECT-TYPE
            SYNTAX PerformanceEventType
            MAX-ACCESS read-only
            STATUS current
            DESCRIPTION
                "perEid."
            ::= { och_portPer15MCurEntry 1 }

        -- 1.3.6.1.4.1.2011.2.25.3.40.50.81.10.1.2
        och_portPer15MCurMonValue OBJECT-TYPE
            SYNTAX OCTET STRING (SIZE (0..100))
            MAX-ACCESS read-only
            STATUS current
            DESCRIPTION
                "perMonValue."
            ::= { och_portPer15MCurEntry 2 }

        -- 1.3.6.1.4.1.2011.2.25.3.40.50.81.10.1.3
        och_portPer15MCurVldty OBJECT-TYPE
            SYNTAX INTEGER
            MAX-ACCESS read-only
            STATUS current
            DESCRIPTION
                "perVldty. "
            ::= { och_portPer15MCurEntry 3 }

        -- 1.3.6.1.4.1.2011.2.25.3.40.50.81.10.1.4
        och_portPer15MCurDateTime OBJECT-TYPE
            SYNTAX DateAndTime
            MAX-ACCESS read-only
            STATUS current
            DESCRIPTION
                "perDateTime. "
            ::= { och_portPer15MCurEntry 4 }

        -- 1.3.6.1.4.1.2011.2.25.3.40.50.81.10.1.5
        och_portPer15MCurParaLen OBJECT-TYPE
            SYNTAX INTEGER
            MAX-ACCESS read-only
            STATUS current
            DESCRIPTION
                "perParaLen."
            ::= { och_portPer15MCurEntry 5 }

        -- 1.3.6.1.4.1.2011.2.25.3.40.50.81.10.1.6
        och_portPer15MCurPara OBJECT-TYPE
            SYNTAX OCTET STRING (SIZE (0..100))
            MAX-ACCESS read-only
            STATUS current
            DESCRIPTION
                "perPara."
            ::= { och_portPer15MCurEntry 6 }




-- -------------------------------------------------------------------------
-- Perfomance 15-MIN History Data Table (RTRV-PER-<MOD2>)
-- -------------------------------------------------------------------------
        -- 1.3.6.1.4.1.2011.2.25.3.40.50.81.20
        och_portPer15MHisTable OBJECT-TYPE
          SYNTAX SEQUENCE OF Och_portPer15MHisEntry
          MAX-ACCESS not-accessible
          STATUS current
          DESCRIPTION
              "och_portPer15MHis."
          ::= { och_port 20 }

        -- 1.3.6.1.4.1.2011.2.25.3.40.50.81.20.1
        och_portPer15MHisEntry OBJECT-TYPE
            SYNTAX Och_portPer15MHisEntry
            MAX-ACCESS not-accessible
            STATUS current
            DESCRIPTION
                "och_portPer15MHis."
            INDEX {och_portPer15MHisEid, och_portPer15MHisParaLen, och_portPer15MHisPara, och_portPer15MHisDateTimeStart, och_portPer15MHisDateTimeEnd}
            ::= { och_portPer15MHisTable 1 }

        Och_portPer15MHisEntry ::=
            SEQUENCE {
                och_portPer15MHisEid
                    PerformanceEventType,
                och_portPer15MHisParaLen
                    INTEGER,
                och_portPer15MHisPara
                    OCTET STRING,
                och_portPer15MHisMonValue
                    OCTET STRING,
                och_portPer15MHisDateTimeStart
                    DateAndTime,
                och_portPer15MHisDateTimeEnd
                    DateAndTime,
                och_portPer15MHisVldty
                    INTEGER,
             }

        -- 1.3.6.1.4.1.2011.2.25.3.40.50.81.20.1.1
        och_portPer15MHisEid OBJECT-TYPE
            SYNTAX PerformanceEventType
            MAX-ACCESS read-only
            STATUS current
            DESCRIPTION
                "perEid."
            ::= { och_portPer15MHisEntry 1 }

        -- 1.3.6.1.4.1.2011.2.25.3.40.50.81.20.1.2
        och_portPer15MHisParaLen OBJECT-TYPE
            SYNTAX INTEGER
            MAX-ACCESS read-only
            STATUS current
            DESCRIPTION
                "perParaLen."
            ::= { och_portPer15MHisEntry 2 }

        -- 1.3.6.1.4.1.2011.2.25.3.40.50.81.20.1.3
        och_portPer15MHisPara OBJECT-TYPE
            SYNTAX OCTET STRING (SIZE (0..100))
            MAX-ACCESS read-only
            STATUS current
            DESCRIPTION
                "perPara."
            ::= { och_portPer15MHisEntry 3 }

        -- 1.3.6.1.4.1.2011.2.25.3.40.50.81.20.1.4
        och_portPer15MHisMonValue OBJECT-TYPE
            SYNTAX OCTET STRING (SIZE (0..100))
            MAX-ACCESS read-only
            STATUS current
            DESCRIPTION
                "perMonValue."
            ::= { och_portPer15MHisEntry 4 }

        -- 1.3.6.1.4.1.2011.2.25.3.40.50.81.20.1.5
        och_portPer15MHisDateTimeStart OBJECT-TYPE
            SYNTAX DateAndTime
            MAX-ACCESS read-only
            STATUS current
            DESCRIPTION
                "perDateTimeStart. "
            ::= { och_portPer15MHisEntry 5 }

        -- 1.3.6.1.4.1.2011.2.25.3.40.50.81.20.1.6
        och_portPer15MHisDateTimeEnd OBJECT-TYPE
            SYNTAX DateAndTime
            MAX-ACCESS read-only
            STATUS current
            DESCRIPTION
                "perDateTimeEnd. "
            ::= { och_portPer15MHisEntry 6 }

        -- 1.3.6.1.4.1.2011.2.25.3.40.50.81.20.1.7
        och_portPer15MHisVldty OBJECT-TYPE
            SYNTAX INTEGER
            MAX-ACCESS read-only
            STATUS current
            DESCRIPTION
                "perVldty. "
            ::= { och_portPer15MHisEntry 7 }




-- -------------------------------------------------------------------------
-- Perfomance 24-HOUR Current Data Table (RTRV-PER-<MOD2>)
-- -------------------------------------------------------------------------
        -- 1.3.6.1.4.1.2011.2.25.3.40.50.81.30
        och_portPer24HCurTable OBJECT-TYPE
          SYNTAX SEQUENCE OF Och_portPer24HCurEntry
          MAX-ACCESS not-accessible
          STATUS current
          DESCRIPTION
              "och_portPer24HCur."
          ::= { och_port 30 }

        -- 1.3.6.1.4.1.2011.2.25.3.40.50.81.30.1
        och_portPer24HCurEntry OBJECT-TYPE
            SYNTAX Och_portPer24HCurEntry
            MAX-ACCESS not-accessible
            STATUS current
            DESCRIPTION
              "och_portPer24HCur."
            INDEX { och_portPer24HCurEid, och_portPer24HCurPara }
            ::= { och_portPer24HCurTable 1 }

        Och_portPer24HCurEntry ::=
            SEQUENCE {
                och_portPer24HCurEid
                    PerformanceEventType,
                och_portPer24HCurMonValue
                    OCTET STRING,
                och_portPer24HCurVldty
                    INTEGER,
                och_portPer24HCurDateTime
                    DateAndTime,
                och_portPer24HCurParaLen
                    INTEGER,
                och_portPer24HCurPara
                    OCTET STRING
            }

        -- 1.3.6.1.4.1.2011.2.25.3.40.50.81.30.1.1
        och_portPer24HCurEid OBJECT-TYPE
            SYNTAX PerformanceEventType
            MAX-ACCESS read-only
            STATUS current
            DESCRIPTION
                "perEid."
            ::= { och_portPer24HCurEntry 1 }

        -- 1.3.6.1.4.1.2011.2.25.3.40.50.81.30.1.2
        och_portPer24HCurMonValue OBJECT-TYPE
            SYNTAX OCTET STRING (SIZE (0..100))
            MAX-ACCESS read-only
            STATUS current
            DESCRIPTION
                "perMonValue."
            ::= { och_portPer24HCurEntry 2 }

        -- 1.3.6.1.4.1.2011.2.25.3.40.50.81.30.1.3
        och_portPer24HCurVldty OBJECT-TYPE
            SYNTAX INTEGER
            MAX-ACCESS read-only
            STATUS current
            DESCRIPTION
                "perVldty. "
            ::= { och_portPer24HCurEntry 3 }

        -- 1.3.6.1.4.1.2011.2.25.3.40.50.81.30.1.4
        och_portPer24HCurDateTime OBJECT-TYPE
            SYNTAX DateAndTime
            MAX-ACCESS read-only
            STATUS current
            DESCRIPTION
                "perDateTime. "
            ::= { och_portPer24HCurEntry 4 }

        -- 1.3.6.1.4.1.2011.2.25.3.40.50.81.30.1.5
        och_portPer24HCurParaLen OBJECT-TYPE
            SYNTAX INTEGER
            MAX-ACCESS read-only
            STATUS current
            DESCRIPTION
                "perParaLen."
            ::= { och_portPer24HCurEntry 5 }

        -- 1.3.6.1.4.1.2011.2.25.3.40.50.81.30.1.6
        och_portPer24HCurPara OBJECT-TYPE
            SYNTAX OCTET STRING (SIZE (0..100))
            MAX-ACCESS read-only
            STATUS current
            DESCRIPTION
                "perPara."
            ::= { och_portPer24HCurEntry 6 }




-- -------------------------------------------------------------------------
-- Perfomance 24-HOUR History Data Table (RTRV-PER-<MOD2>)
-- -------------------------------------------------------------------------
        -- 1.3.6.1.4.1.2011.2.25.3.40.50.81.40
        och_portPer24HHisTable OBJECT-TYPE
          SYNTAX SEQUENCE OF Och_portPer24HHisEntry
          MAX-ACCESS not-accessible
          STATUS current
          DESCRIPTION
              "och_portPer24HHis."
          ::= { och_port 40 }

        -- 1.3.6.1.4.1.2011.2.25.3.40.50.81.40.1
        och_portPer24HHisEntry OBJECT-TYPE
            SYNTAX Och_portPer24HHisEntry
            MAX-ACCESS not-accessible
            STATUS current
            DESCRIPTION
                "och_portPer24HHis."
            INDEX {och_portPer24HHisEid, och_portPer24HHisParaLen, och_portPer24HHisPara, och_portPer24HHisDateTimeStart, och_portPer24HHisDateTimeEnd}
            ::= { och_portPer24HHisTable 1 }

        Och_portPer24HHisEntry ::=
            SEQUENCE {
                och_portPer24HHisEid
                    PerformanceEventType,
                och_portPer24HHisParaLen
                    INTEGER,
                och_portPer24HHisPara
                    OCTET STRING,
                och_portPer24HHisMonValue
                    OCTET STRING,
                och_portPer24HHisDateTimeStart
                    DateAndTime,
                och_portPer24HHisDateTimeEnd
                    DateAndTime,
                och_portPer24HHisVldty
                    INTEGER,
             }

        -- 1.3.6.1.4.1.2011.2.25.3.40.50.81.40.1.1
        och_portPer24HHisEid OBJECT-TYPE
            SYNTAX PerformanceEventType
            MAX-ACCESS read-only
            STATUS current
            DESCRIPTION
                "perEid."
            ::= { och_portPer24HHisEntry 1 }

        -- 1.3.6.1.4.1.2011.2.25.3.40.50.81.40.1.2
        och_portPer24HHisParaLen OBJECT-TYPE
            SYNTAX INTEGER
            MAX-ACCESS read-only
            STATUS current
            DESCRIPTION
                "perParaLen."
            ::= { och_portPer24HHisEntry 2 }

        -- 1.3.6.1.4.1.2011.2.25.3.40.50.81.40.1.3
        och_portPer24HHisPara OBJECT-TYPE
            SYNTAX OCTET STRING (SIZE (0..100))
            MAX-ACCESS read-only
            STATUS current
            DESCRIPTION
                "perPara."
            ::= { och_portPer24HHisEntry 3 }

        -- 1.3.6.1.4.1.2011.2.25.3.40.50.81.40.1.4
        och_portPer24HHisMonValue OBJECT-TYPE
            SYNTAX OCTET STRING (SIZE (0..100))
            MAX-ACCESS read-only
            STATUS current
            DESCRIPTION
                "perMonValue."
            ::= { och_portPer24HHisEntry 4 }

        -- 1.3.6.1.4.1.2011.2.25.3.40.50.81.40.1.5
        och_portPer24HHisDateTimeStart OBJECT-TYPE
            SYNTAX DateAndTime
            MAX-ACCESS read-only
            STATUS current
            DESCRIPTION
                "perDateTimeStart. "
            ::= { och_portPer24HHisEntry 5 }

        -- 1.3.6.1.4.1.2011.2.25.3.40.50.81.40.1.6
        och_portPer24HHisDateTimeEnd OBJECT-TYPE
            SYNTAX DateAndTime
            MAX-ACCESS read-only
            STATUS current
            DESCRIPTION
                "perDateTimeEnd. "
            ::= { och_portPer24HHisEntry 6 }

        -- 1.3.6.1.4.1.2011.2.25.3.40.50.81.40.1.7
        och_portPer24HHisVldty OBJECT-TYPE
            SYNTAX INTEGER
            MAX-ACCESS read-only
            STATUS current
            DESCRIPTION
                "perVldty. "
            ::= { och_portPer24HHisEntry 7 }




-- Alarm data
      -- 1.3.6.1.4.1.2011.2.25.3.40.50.88
      otu1_path OBJECT IDENTIFIER ::={ optixGlobalNGWDM 88 }


-- -------------------------------------------------------------------------
-- Perfomance 15-MIN Current Data Table (RTRV-PER-<MOD2>)
-- -------------------------------------------------------------------------
        -- 1.3.6.1.4.1.2011.2.25.3.40.50.88.10
        otu1_pathPer15MCurTable OBJECT-TYPE
          SYNTAX SEQUENCE OF Otu1_pathPer15MCurEntry
          MAX-ACCESS not-accessible
          STATUS current
          DESCRIPTION
              "otu1_pathPer15MCur."
          ::= { otu1_path 10 }

        -- 1.3.6.1.4.1.2011.2.25.3.40.50.88.10.1
        otu1_pathPer15MCurEntry OBJECT-TYPE
            SYNTAX Otu1_pathPer15MCurEntry
            MAX-ACCESS not-accessible
            STATUS current
            DESCRIPTION
              "otu1_pathPer15MCur."
            INDEX { otu1_pathPer15MCurEid, otu1_pathPer15MCurPara }
            ::= { otu1_pathPer15MCurTable 1 }

        Otu1_pathPer15MCurEntry ::=
            SEQUENCE {
                otu1_pathPer15MCurEid
                    PerformanceEventType,
                otu1_pathPer15MCurMonValue
                    OCTET STRING,
                otu1_pathPer15MCurVldty
                    INTEGER,
                otu1_pathPer15MCurDateTime
                    DateAndTime,
                otu1_pathPer15MCurParaLen
                    INTEGER,
                otu1_pathPer15MCurPara
                    OCTET STRING
            }

        -- 1.3.6.1.4.1.2011.2.25.3.40.50.88.10.1.1
        otu1_pathPer15MCurEid OBJECT-TYPE
            SYNTAX PerformanceEventType
            MAX-ACCESS read-only
            STATUS current
            DESCRIPTION
                "perEid."
            ::= { otu1_pathPer15MCurEntry 1 }

        -- 1.3.6.1.4.1.2011.2.25.3.40.50.88.10.1.2
        otu1_pathPer15MCurMonValue OBJECT-TYPE
            SYNTAX OCTET STRING (SIZE (0..100))
            MAX-ACCESS read-only
            STATUS current
            DESCRIPTION
                "perMonValue."
            ::= { otu1_pathPer15MCurEntry 2 }

        -- 1.3.6.1.4.1.2011.2.25.3.40.50.88.10.1.3
        otu1_pathPer15MCurVldty OBJECT-TYPE
            SYNTAX INTEGER
            MAX-ACCESS read-only
            STATUS current
            DESCRIPTION
                "perVldty. "
            ::= { otu1_pathPer15MCurEntry 3 }

        -- 1.3.6.1.4.1.2011.2.25.3.40.50.88.10.1.4
        otu1_pathPer15MCurDateTime OBJECT-TYPE
            SYNTAX DateAndTime
            MAX-ACCESS read-only
            STATUS current
            DESCRIPTION
                "perDateTime. "
            ::= { otu1_pathPer15MCurEntry 4 }

        -- 1.3.6.1.4.1.2011.2.25.3.40.50.88.10.1.5
        otu1_pathPer15MCurParaLen OBJECT-TYPE
            SYNTAX INTEGER
            MAX-ACCESS read-only
            STATUS current
            DESCRIPTION
                "perParaLen."
            ::= { otu1_pathPer15MCurEntry 5 }

        -- 1.3.6.1.4.1.2011.2.25.3.40.50.88.10.1.6
        otu1_pathPer15MCurPara OBJECT-TYPE
            SYNTAX OCTET STRING (SIZE (0..100))
            MAX-ACCESS read-only
            STATUS current
            DESCRIPTION
                "perPara."
            ::= { otu1_pathPer15MCurEntry 6 }




-- -------------------------------------------------------------------------
-- Perfomance 15-MIN History Data Table (RTRV-PER-<MOD2>)
-- -------------------------------------------------------------------------
        -- 1.3.6.1.4.1.2011.2.25.3.40.50.88.20
        otu1_pathPer15MHisTable OBJECT-TYPE
          SYNTAX SEQUENCE OF Otu1_pathPer15MHisEntry
          MAX-ACCESS not-accessible
          STATUS current
          DESCRIPTION
              "otu1_pathPer15MHis."
          ::= { otu1_path 20 }

        -- 1.3.6.1.4.1.2011.2.25.3.40.50.88.20.1
        otu1_pathPer15MHisEntry OBJECT-TYPE
            SYNTAX Otu1_pathPer15MHisEntry
            MAX-ACCESS not-accessible
            STATUS current
            DESCRIPTION
                "otu1_pathPer15MHis."
            INDEX {otu1_pathPer15MHisEid, otu1_pathPer15MHisParaLen, otu1_pathPer15MHisPara, otu1_pathPer15MHisDateTimeStart, otu1_pathPer15MHisDateTimeEnd}
            ::= { otu1_pathPer15MHisTable 1 }

        Otu1_pathPer15MHisEntry ::=
            SEQUENCE {
                otu1_pathPer15MHisEid
                    PerformanceEventType,
                otu1_pathPer15MHisParaLen
                    INTEGER,
                otu1_pathPer15MHisPara
                    OCTET STRING,
                otu1_pathPer15MHisMonValue
                    OCTET STRING,
                otu1_pathPer15MHisDateTimeStart
                    DateAndTime,
                otu1_pathPer15MHisDateTimeEnd
                    DateAndTime,
                otu1_pathPer15MHisVldty
                    INTEGER,
             }

        -- 1.3.6.1.4.1.2011.2.25.3.40.50.88.20.1.1
        otu1_pathPer15MHisEid OBJECT-TYPE
            SYNTAX PerformanceEventType
            MAX-ACCESS read-only
            STATUS current
            DESCRIPTION
                "perEid."
            ::= { otu1_pathPer15MHisEntry 1 }

        -- 1.3.6.1.4.1.2011.2.25.3.40.50.88.20.1.2
        otu1_pathPer15MHisParaLen OBJECT-TYPE
            SYNTAX INTEGER
            MAX-ACCESS read-only
            STATUS current
            DESCRIPTION
                "perParaLen."
            ::= { otu1_pathPer15MHisEntry 2 }

        -- 1.3.6.1.4.1.2011.2.25.3.40.50.88.20.1.3
        otu1_pathPer15MHisPara OBJECT-TYPE
            SYNTAX OCTET STRING (SIZE (0..100))
            MAX-ACCESS read-only
            STATUS current
            DESCRIPTION
                "perPara."
            ::= { otu1_pathPer15MHisEntry 3 }

        -- 1.3.6.1.4.1.2011.2.25.3.40.50.88.20.1.4
        otu1_pathPer15MHisMonValue OBJECT-TYPE
            SYNTAX OCTET STRING (SIZE (0..100))
            MAX-ACCESS read-only
            STATUS current
            DESCRIPTION
                "perMonValue."
            ::= { otu1_pathPer15MHisEntry 4 }

        -- 1.3.6.1.4.1.2011.2.25.3.40.50.88.20.1.5
        otu1_pathPer15MHisDateTimeStart OBJECT-TYPE
            SYNTAX DateAndTime
            MAX-ACCESS read-only
            STATUS current
            DESCRIPTION
                "perDateTimeStart. "
            ::= { otu1_pathPer15MHisEntry 5 }

        -- 1.3.6.1.4.1.2011.2.25.3.40.50.88.20.1.6
        otu1_pathPer15MHisDateTimeEnd OBJECT-TYPE
            SYNTAX DateAndTime
            MAX-ACCESS read-only
            STATUS current
            DESCRIPTION
                "perDateTimeEnd. "
            ::= { otu1_pathPer15MHisEntry 6 }

        -- 1.3.6.1.4.1.2011.2.25.3.40.50.88.20.1.7
        otu1_pathPer15MHisVldty OBJECT-TYPE
            SYNTAX INTEGER
            MAX-ACCESS read-only
            STATUS current
            DESCRIPTION
                "perVldty. "
            ::= { otu1_pathPer15MHisEntry 7 }




-- -------------------------------------------------------------------------
-- Perfomance 24-HOUR Current Data Table (RTRV-PER-<MOD2>)
-- -------------------------------------------------------------------------
        -- 1.3.6.1.4.1.2011.2.25.3.40.50.88.30
        otu1_pathPer24HCurTable OBJECT-TYPE
          SYNTAX SEQUENCE OF Otu1_pathPer24HCurEntry
          MAX-ACCESS not-accessible
          STATUS current
          DESCRIPTION
              "otu1_pathPer24HCur."
          ::= { otu1_path 30 }

        -- 1.3.6.1.4.1.2011.2.25.3.40.50.88.30.1
        otu1_pathPer24HCurEntry OBJECT-TYPE
            SYNTAX Otu1_pathPer24HCurEntry
            MAX-ACCESS not-accessible
            STATUS current
            DESCRIPTION
              "otu1_pathPer24HCur."
            INDEX { otu1_pathPer24HCurEid, otu1_pathPer24HCurPara }
            ::= { otu1_pathPer24HCurTable 1 }

        Otu1_pathPer24HCurEntry ::=
            SEQUENCE {
                otu1_pathPer24HCurEid
                    PerformanceEventType,
                otu1_pathPer24HCurMonValue
                    OCTET STRING,
                otu1_pathPer24HCurVldty
                    INTEGER,
                otu1_pathPer24HCurDateTime
                    DateAndTime,
                otu1_pathPer24HCurParaLen
                    INTEGER,
                otu1_pathPer24HCurPara
                    OCTET STRING
            }

        -- 1.3.6.1.4.1.2011.2.25.3.40.50.88.30.1.1
        otu1_pathPer24HCurEid OBJECT-TYPE
            SYNTAX PerformanceEventType
            MAX-ACCESS read-only
            STATUS current
            DESCRIPTION
                "perEid."
            ::= { otu1_pathPer24HCurEntry 1 }

        -- 1.3.6.1.4.1.2011.2.25.3.40.50.88.30.1.2
        otu1_pathPer24HCurMonValue OBJECT-TYPE
            SYNTAX OCTET STRING (SIZE (0..100))
            MAX-ACCESS read-only
            STATUS current
            DESCRIPTION
                "perMonValue."
            ::= { otu1_pathPer24HCurEntry 2 }

        -- 1.3.6.1.4.1.2011.2.25.3.40.50.88.30.1.3
        otu1_pathPer24HCurVldty OBJECT-TYPE
            SYNTAX INTEGER
            MAX-ACCESS read-only
            STATUS current
            DESCRIPTION
                "perVldty. "
            ::= { otu1_pathPer24HCurEntry 3 }

        -- 1.3.6.1.4.1.2011.2.25.3.40.50.88.30.1.4
        otu1_pathPer24HCurDateTime OBJECT-TYPE
            SYNTAX DateAndTime
            MAX-ACCESS read-only
            STATUS current
            DESCRIPTION
                "perDateTime. "
            ::= { otu1_pathPer24HCurEntry 4 }

        -- 1.3.6.1.4.1.2011.2.25.3.40.50.88.30.1.5
        otu1_pathPer24HCurParaLen OBJECT-TYPE
            SYNTAX INTEGER
            MAX-ACCESS read-only
            STATUS current
            DESCRIPTION
                "perParaLen."
            ::= { otu1_pathPer24HCurEntry 5 }

        -- 1.3.6.1.4.1.2011.2.25.3.40.50.88.30.1.6
        otu1_pathPer24HCurPara OBJECT-TYPE
            SYNTAX OCTET STRING (SIZE (0..100))
            MAX-ACCESS read-only
            STATUS current
            DESCRIPTION
                "perPara."
            ::= { otu1_pathPer24HCurEntry 6 }




-- -------------------------------------------------------------------------
-- Perfomance 24-HOUR History Data Table (RTRV-PER-<MOD2>)
-- -------------------------------------------------------------------------
        -- 1.3.6.1.4.1.2011.2.25.3.40.50.88.40
        otu1_pathPer24HHisTable OBJECT-TYPE
          SYNTAX SEQUENCE OF Otu1_pathPer24HHisEntry
          MAX-ACCESS not-accessible
          STATUS current
          DESCRIPTION
              "otu1_pathPer24HHis."
          ::= { otu1_path 40 }

        -- 1.3.6.1.4.1.2011.2.25.3.40.50.88.40.1
        otu1_pathPer24HHisEntry OBJECT-TYPE
            SYNTAX Otu1_pathPer24HHisEntry
            MAX-ACCESS not-accessible
            STATUS current
            DESCRIPTION
                "otu1_pathPer24HHis."
            INDEX {otu1_pathPer24HHisEid, otu1_pathPer24HHisParaLen, otu1_pathPer24HHisPara, otu1_pathPer24HHisDateTimeStart, otu1_pathPer24HHisDateTimeEnd}
            ::= { otu1_pathPer24HHisTable 1 }

        Otu1_pathPer24HHisEntry ::=
            SEQUENCE {
                otu1_pathPer24HHisEid
                    PerformanceEventType,
                otu1_pathPer24HHisParaLen
                    INTEGER,
                otu1_pathPer24HHisPara
                    OCTET STRING,
                otu1_pathPer24HHisMonValue
                    OCTET STRING,
                otu1_pathPer24HHisDateTimeStart
                    DateAndTime,
                otu1_pathPer24HHisDateTimeEnd
                    DateAndTime,
                otu1_pathPer24HHisVldty
                    INTEGER,
             }

        -- 1.3.6.1.4.1.2011.2.25.3.40.50.88.40.1.1
        otu1_pathPer24HHisEid OBJECT-TYPE
            SYNTAX PerformanceEventType
            MAX-ACCESS read-only
            STATUS current
            DESCRIPTION
                "perEid."
            ::= { otu1_pathPer24HHisEntry 1 }

        -- 1.3.6.1.4.1.2011.2.25.3.40.50.88.40.1.2
        otu1_pathPer24HHisParaLen OBJECT-TYPE
            SYNTAX INTEGER
            MAX-ACCESS read-only
            STATUS current
            DESCRIPTION
                "perParaLen."
            ::= { otu1_pathPer24HHisEntry 2 }

        -- 1.3.6.1.4.1.2011.2.25.3.40.50.88.40.1.3
        otu1_pathPer24HHisPara OBJECT-TYPE
            SYNTAX OCTET STRING (SIZE (0..100))
            MAX-ACCESS read-only
            STATUS current
            DESCRIPTION
                "perPara."
            ::= { otu1_pathPer24HHisEntry 3 }

        -- 1.3.6.1.4.1.2011.2.25.3.40.50.88.40.1.4
        otu1_pathPer24HHisMonValue OBJECT-TYPE
            SYNTAX OCTET STRING (SIZE (0..100))
            MAX-ACCESS read-only
            STATUS current
            DESCRIPTION
                "perMonValue."
            ::= { otu1_pathPer24HHisEntry 4 }

        -- 1.3.6.1.4.1.2011.2.25.3.40.50.88.40.1.5
        otu1_pathPer24HHisDateTimeStart OBJECT-TYPE
            SYNTAX DateAndTime
            MAX-ACCESS read-only
            STATUS current
            DESCRIPTION
                "perDateTimeStart. "
            ::= { otu1_pathPer24HHisEntry 5 }

        -- 1.3.6.1.4.1.2011.2.25.3.40.50.88.40.1.6
        otu1_pathPer24HHisDateTimeEnd OBJECT-TYPE
            SYNTAX DateAndTime
            MAX-ACCESS read-only
            STATUS current
            DESCRIPTION
                "perDateTimeEnd. "
            ::= { otu1_pathPer24HHisEntry 6 }

        -- 1.3.6.1.4.1.2011.2.25.3.40.50.88.40.1.7
        otu1_pathPer24HHisVldty OBJECT-TYPE
            SYNTAX INTEGER
            MAX-ACCESS read-only
            STATUS current
            DESCRIPTION
                "perVldty. "
            ::= { otu1_pathPer24HHisEntry 7 }




-- Alarm data
      -- 1.3.6.1.4.1.2011.2.25.3.40.50.89
      otu2_path OBJECT IDENTIFIER ::={ optixGlobalNGWDM 89 }


-- -------------------------------------------------------------------------
-- Perfomance 15-MIN Current Data Table (RTRV-PER-<MOD2>)
-- -------------------------------------------------------------------------
        -- 1.3.6.1.4.1.2011.2.25.3.40.50.89.10
        otu2_pathPer15MCurTable OBJECT-TYPE
          SYNTAX SEQUENCE OF Otu2_pathPer15MCurEntry
          MAX-ACCESS not-accessible
          STATUS current
          DESCRIPTION
              "otu2_pathPer15MCur."
          ::= { otu2_path 10 }

        -- 1.3.6.1.4.1.2011.2.25.3.40.50.89.10.1
        otu2_pathPer15MCurEntry OBJECT-TYPE
            SYNTAX Otu2_pathPer15MCurEntry
            MAX-ACCESS not-accessible
            STATUS current
            DESCRIPTION
              "otu2_pathPer15MCur."
            INDEX { otu2_pathPer15MCurEid, otu2_pathPer15MCurPara }
            ::= { otu2_pathPer15MCurTable 1 }

        Otu2_pathPer15MCurEntry ::=
            SEQUENCE {
                otu2_pathPer15MCurEid
                    PerformanceEventType,
                otu2_pathPer15MCurMonValue
                    OCTET STRING,
                otu2_pathPer15MCurVldty
                    INTEGER,
                otu2_pathPer15MCurDateTime
                    DateAndTime,
                otu2_pathPer15MCurParaLen
                    INTEGER,
                otu2_pathPer15MCurPara
                    OCTET STRING
            }

        -- 1.3.6.1.4.1.2011.2.25.3.40.50.89.10.1.1
        otu2_pathPer15MCurEid OBJECT-TYPE
            SYNTAX PerformanceEventType
            MAX-ACCESS read-only
            STATUS current
            DESCRIPTION
                "perEid."
            ::= { otu2_pathPer15MCurEntry 1 }

        -- 1.3.6.1.4.1.2011.2.25.3.40.50.89.10.1.2
        otu2_pathPer15MCurMonValue OBJECT-TYPE
            SYNTAX OCTET STRING (SIZE (0..100))
            MAX-ACCESS read-only
            STATUS current
            DESCRIPTION
                "perMonValue."
            ::= { otu2_pathPer15MCurEntry 2 }

        -- 1.3.6.1.4.1.2011.2.25.3.40.50.89.10.1.3
        otu2_pathPer15MCurVldty OBJECT-TYPE
            SYNTAX INTEGER
            MAX-ACCESS read-only
            STATUS current
            DESCRIPTION
                "perVldty. "
            ::= { otu2_pathPer15MCurEntry 3 }

        -- 1.3.6.1.4.1.2011.2.25.3.40.50.89.10.1.4
        otu2_pathPer15MCurDateTime OBJECT-TYPE
            SYNTAX DateAndTime
            MAX-ACCESS read-only
            STATUS current
            DESCRIPTION
                "perDateTime. "
            ::= { otu2_pathPer15MCurEntry 4 }

        -- 1.3.6.1.4.1.2011.2.25.3.40.50.89.10.1.5
        otu2_pathPer15MCurParaLen OBJECT-TYPE
            SYNTAX INTEGER
            MAX-ACCESS read-only
            STATUS current
            DESCRIPTION
                "perParaLen."
            ::= { otu2_pathPer15MCurEntry 5 }

        -- 1.3.6.1.4.1.2011.2.25.3.40.50.89.10.1.6
        otu2_pathPer15MCurPara OBJECT-TYPE
            SYNTAX OCTET STRING (SIZE (0..100))
            MAX-ACCESS read-only
            STATUS current
            DESCRIPTION
                "perPara."
            ::= { otu2_pathPer15MCurEntry 6 }




-- -------------------------------------------------------------------------
-- Perfomance 15-MIN History Data Table (RTRV-PER-<MOD2>)
-- -------------------------------------------------------------------------
        -- 1.3.6.1.4.1.2011.2.25.3.40.50.89.20
        otu2_pathPer15MHisTable OBJECT-TYPE
          SYNTAX SEQUENCE OF Otu2_pathPer15MHisEntry
          MAX-ACCESS not-accessible
          STATUS current
          DESCRIPTION
              "otu2_pathPer15MHis."
          ::= { otu2_path 20 }

        -- 1.3.6.1.4.1.2011.2.25.3.40.50.89.20.1
        otu2_pathPer15MHisEntry OBJECT-TYPE
            SYNTAX Otu2_pathPer15MHisEntry
            MAX-ACCESS not-accessible
            STATUS current
            DESCRIPTION
                "otu2_pathPer15MHis."
            INDEX {otu2_pathPer15MHisEid, otu2_pathPer15MHisParaLen, otu2_pathPer15MHisPara, otu2_pathPer15MHisDateTimeStart, otu2_pathPer15MHisDateTimeEnd}
            ::= { otu2_pathPer15MHisTable 1 }

        Otu2_pathPer15MHisEntry ::=
            SEQUENCE {
                otu2_pathPer15MHisEid
                    PerformanceEventType,
                otu2_pathPer15MHisParaLen
                    INTEGER,
                otu2_pathPer15MHisPara
                    OCTET STRING,
                otu2_pathPer15MHisMonValue
                    OCTET STRING,
                otu2_pathPer15MHisDateTimeStart
                    DateAndTime,
                otu2_pathPer15MHisDateTimeEnd
                    DateAndTime,
                otu2_pathPer15MHisVldty
                    INTEGER,
             }

        -- 1.3.6.1.4.1.2011.2.25.3.40.50.89.20.1.1
        otu2_pathPer15MHisEid OBJECT-TYPE
            SYNTAX PerformanceEventType
            MAX-ACCESS read-only
            STATUS current
            DESCRIPTION
                "perEid."
            ::= { otu2_pathPer15MHisEntry 1 }

        -- 1.3.6.1.4.1.2011.2.25.3.40.50.89.20.1.2
        otu2_pathPer15MHisParaLen OBJECT-TYPE
            SYNTAX INTEGER
            MAX-ACCESS read-only
            STATUS current
            DESCRIPTION
                "perParaLen."
            ::= { otu2_pathPer15MHisEntry 2 }

        -- 1.3.6.1.4.1.2011.2.25.3.40.50.89.20.1.3
        otu2_pathPer15MHisPara OBJECT-TYPE
            SYNTAX OCTET STRING (SIZE (0..100))
            MAX-ACCESS read-only
            STATUS current
            DESCRIPTION
                "perPara."
            ::= { otu2_pathPer15MHisEntry 3 }

        -- 1.3.6.1.4.1.2011.2.25.3.40.50.89.20.1.4
        otu2_pathPer15MHisMonValue OBJECT-TYPE
            SYNTAX OCTET STRING (SIZE (0..100))
            MAX-ACCESS read-only
            STATUS current
            DESCRIPTION
                "perMonValue."
            ::= { otu2_pathPer15MHisEntry 4 }

        -- 1.3.6.1.4.1.2011.2.25.3.40.50.89.20.1.5
        otu2_pathPer15MHisDateTimeStart OBJECT-TYPE
            SYNTAX DateAndTime
            MAX-ACCESS read-only
            STATUS current
            DESCRIPTION
                "perDateTimeStart. "
            ::= { otu2_pathPer15MHisEntry 5 }

        -- 1.3.6.1.4.1.2011.2.25.3.40.50.89.20.1.6
        otu2_pathPer15MHisDateTimeEnd OBJECT-TYPE
            SYNTAX DateAndTime
            MAX-ACCESS read-only
            STATUS current
            DESCRIPTION
                "perDateTimeEnd. "
            ::= { otu2_pathPer15MHisEntry 6 }

        -- 1.3.6.1.4.1.2011.2.25.3.40.50.89.20.1.7
        otu2_pathPer15MHisVldty OBJECT-TYPE
            SYNTAX INTEGER
            MAX-ACCESS read-only
            STATUS current
            DESCRIPTION
                "perVldty. "
            ::= { otu2_pathPer15MHisEntry 7 }




-- -------------------------------------------------------------------------
-- Perfomance 24-HOUR Current Data Table (RTRV-PER-<MOD2>)
-- -------------------------------------------------------------------------
        -- 1.3.6.1.4.1.2011.2.25.3.40.50.89.30
        otu2_pathPer24HCurTable OBJECT-TYPE
          SYNTAX SEQUENCE OF Otu2_pathPer24HCurEntry
          MAX-ACCESS not-accessible
          STATUS current
          DESCRIPTION
              "otu2_pathPer24HCur."
          ::= { otu2_path 30 }

        -- 1.3.6.1.4.1.2011.2.25.3.40.50.89.30.1
        otu2_pathPer24HCurEntry OBJECT-TYPE
            SYNTAX Otu2_pathPer24HCurEntry
            MAX-ACCESS not-accessible
            STATUS current
            DESCRIPTION
              "otu2_pathPer24HCur."
            INDEX { otu2_pathPer24HCurEid, otu2_pathPer24HCurPara }
            ::= { otu2_pathPer24HCurTable 1 }

        Otu2_pathPer24HCurEntry ::=
            SEQUENCE {
                otu2_pathPer24HCurEid
                    PerformanceEventType,
                otu2_pathPer24HCurMonValue
                    OCTET STRING,
                otu2_pathPer24HCurVldty
                    INTEGER,
                otu2_pathPer24HCurDateTime
                    DateAndTime,
                otu2_pathPer24HCurParaLen
                    INTEGER,
                otu2_pathPer24HCurPara
                    OCTET STRING
            }

        -- 1.3.6.1.4.1.2011.2.25.3.40.50.89.30.1.1
        otu2_pathPer24HCurEid OBJECT-TYPE
            SYNTAX PerformanceEventType
            MAX-ACCESS read-only
            STATUS current
            DESCRIPTION
                "perEid."
            ::= { otu2_pathPer24HCurEntry 1 }

        -- 1.3.6.1.4.1.2011.2.25.3.40.50.89.30.1.2
        otu2_pathPer24HCurMonValue OBJECT-TYPE
            SYNTAX OCTET STRING (SIZE (0..100))
            MAX-ACCESS read-only
            STATUS current
            DESCRIPTION
                "perMonValue."
            ::= { otu2_pathPer24HCurEntry 2 }

        -- 1.3.6.1.4.1.2011.2.25.3.40.50.89.30.1.3
        otu2_pathPer24HCurVldty OBJECT-TYPE
            SYNTAX INTEGER
            MAX-ACCESS read-only
            STATUS current
            DESCRIPTION
                "perVldty. "
            ::= { otu2_pathPer24HCurEntry 3 }

        -- 1.3.6.1.4.1.2011.2.25.3.40.50.89.30.1.4
        otu2_pathPer24HCurDateTime OBJECT-TYPE
            SYNTAX DateAndTime
            MAX-ACCESS read-only
            STATUS current
            DESCRIPTION
                "perDateTime. "
            ::= { otu2_pathPer24HCurEntry 4 }

        -- 1.3.6.1.4.1.2011.2.25.3.40.50.89.30.1.5
        otu2_pathPer24HCurParaLen OBJECT-TYPE
            SYNTAX INTEGER
            MAX-ACCESS read-only
            STATUS current
            DESCRIPTION
                "perParaLen."
            ::= { otu2_pathPer24HCurEntry 5 }

        -- 1.3.6.1.4.1.2011.2.25.3.40.50.89.30.1.6
        otu2_pathPer24HCurPara OBJECT-TYPE
            SYNTAX OCTET STRING (SIZE (0..100))
            MAX-ACCESS read-only
            STATUS current
            DESCRIPTION
                "perPara."
            ::= { otu2_pathPer24HCurEntry 6 }




-- -------------------------------------------------------------------------
-- Perfomance 24-HOUR History Data Table (RTRV-PER-<MOD2>)
-- -------------------------------------------------------------------------
        -- 1.3.6.1.4.1.2011.2.25.3.40.50.89.40
        otu2_pathPer24HHisTable OBJECT-TYPE
          SYNTAX SEQUENCE OF Otu2_pathPer24HHisEntry
          MAX-ACCESS not-accessible
          STATUS current
          DESCRIPTION
              "otu2_pathPer24HHis."
          ::= { otu2_path 40 }

        -- 1.3.6.1.4.1.2011.2.25.3.40.50.89.40.1
        otu2_pathPer24HHisEntry OBJECT-TYPE
            SYNTAX Otu2_pathPer24HHisEntry
            MAX-ACCESS not-accessible
            STATUS current
            DESCRIPTION
                "otu2_pathPer24HHis."
            INDEX {otu2_pathPer24HHisEid, otu2_pathPer24HHisParaLen, otu2_pathPer24HHisPara, otu2_pathPer24HHisDateTimeStart, otu2_pathPer24HHisDateTimeEnd}
            ::= { otu2_pathPer24HHisTable 1 }

        Otu2_pathPer24HHisEntry ::=
            SEQUENCE {
                otu2_pathPer24HHisEid
                    PerformanceEventType,
                otu2_pathPer24HHisParaLen
                    INTEGER,
                otu2_pathPer24HHisPara
                    OCTET STRING,
                otu2_pathPer24HHisMonValue
                    OCTET STRING,
                otu2_pathPer24HHisDateTimeStart
                    DateAndTime,
                otu2_pathPer24HHisDateTimeEnd
                    DateAndTime,
                otu2_pathPer24HHisVldty
                    INTEGER,
             }

        -- 1.3.6.1.4.1.2011.2.25.3.40.50.89.40.1.1
        otu2_pathPer24HHisEid OBJECT-TYPE
            SYNTAX PerformanceEventType
            MAX-ACCESS read-only
            STATUS current
            DESCRIPTION
                "perEid."
            ::= { otu2_pathPer24HHisEntry 1 }

        -- 1.3.6.1.4.1.2011.2.25.3.40.50.89.40.1.2
        otu2_pathPer24HHisParaLen OBJECT-TYPE
            SYNTAX INTEGER
            MAX-ACCESS read-only
            STATUS current
            DESCRIPTION
                "perParaLen."
            ::= { otu2_pathPer24HHisEntry 2 }

        -- 1.3.6.1.4.1.2011.2.25.3.40.50.89.40.1.3
        otu2_pathPer24HHisPara OBJECT-TYPE
            SYNTAX OCTET STRING (SIZE (0..100))
            MAX-ACCESS read-only
            STATUS current
            DESCRIPTION
                "perPara."
            ::= { otu2_pathPer24HHisEntry 3 }

        -- 1.3.6.1.4.1.2011.2.25.3.40.50.89.40.1.4
        otu2_pathPer24HHisMonValue OBJECT-TYPE
            SYNTAX OCTET STRING (SIZE (0..100))
            MAX-ACCESS read-only
            STATUS current
            DESCRIPTION
                "perMonValue."
            ::= { otu2_pathPer24HHisEntry 4 }

        -- 1.3.6.1.4.1.2011.2.25.3.40.50.89.40.1.5
        otu2_pathPer24HHisDateTimeStart OBJECT-TYPE
            SYNTAX DateAndTime
            MAX-ACCESS read-only
            STATUS current
            DESCRIPTION
                "perDateTimeStart. "
            ::= { otu2_pathPer24HHisEntry 5 }

        -- 1.3.6.1.4.1.2011.2.25.3.40.50.89.40.1.6
        otu2_pathPer24HHisDateTimeEnd OBJECT-TYPE
            SYNTAX DateAndTime
            MAX-ACCESS read-only
            STATUS current
            DESCRIPTION
                "perDateTimeEnd. "
            ::= { otu2_pathPer24HHisEntry 6 }

        -- 1.3.6.1.4.1.2011.2.25.3.40.50.89.40.1.7
        otu2_pathPer24HHisVldty OBJECT-TYPE
            SYNTAX INTEGER
            MAX-ACCESS read-only
            STATUS current
            DESCRIPTION
                "perVldty. "
            ::= { otu2_pathPer24HHisEntry 7 }




-- Alarm data
      -- 1.3.6.1.4.1.2011.2.25.3.40.50.90
      otu3_path OBJECT IDENTIFIER ::={ optixGlobalNGWDM 90 }


-- -------------------------------------------------------------------------
-- Perfomance 15-MIN Current Data Table (RTRV-PER-<MOD2>)
-- -------------------------------------------------------------------------
        -- 1.3.6.1.4.1.2011.2.25.3.40.50.90.10
        otu3_pathPer15MCurTable OBJECT-TYPE
          SYNTAX SEQUENCE OF Otu3_pathPer15MCurEntry
          MAX-ACCESS not-accessible
          STATUS current
          DESCRIPTION
              "otu3_pathPer15MCur."
          ::= { otu3_path 10 }

        -- 1.3.6.1.4.1.2011.2.25.3.40.50.90.10.1
        otu3_pathPer15MCurEntry OBJECT-TYPE
            SYNTAX Otu3_pathPer15MCurEntry
            MAX-ACCESS not-accessible
            STATUS current
            DESCRIPTION
              "otu3_pathPer15MCur."
            INDEX { otu3_pathPer15MCurEid, otu3_pathPer15MCurPara }
            ::= { otu3_pathPer15MCurTable 1 }

        Otu3_pathPer15MCurEntry ::=
            SEQUENCE {
                otu3_pathPer15MCurEid
                    PerformanceEventType,
                otu3_pathPer15MCurMonValue
                    OCTET STRING,
                otu3_pathPer15MCurVldty
                    INTEGER,
                otu3_pathPer15MCurDateTime
                    DateAndTime,
                otu3_pathPer15MCurParaLen
                    INTEGER,
                otu3_pathPer15MCurPara
                    OCTET STRING
            }

        -- 1.3.6.1.4.1.2011.2.25.3.40.50.90.10.1.1
        otu3_pathPer15MCurEid OBJECT-TYPE
            SYNTAX PerformanceEventType
            MAX-ACCESS read-only
            STATUS current
            DESCRIPTION
                "perEid."
            ::= { otu3_pathPer15MCurEntry 1 }

        -- 1.3.6.1.4.1.2011.2.25.3.40.50.90.10.1.2
        otu3_pathPer15MCurMonValue OBJECT-TYPE
            SYNTAX OCTET STRING (SIZE (0..100))
            MAX-ACCESS read-only
            STATUS current
            DESCRIPTION
                "perMonValue."
            ::= { otu3_pathPer15MCurEntry 2 }

        -- 1.3.6.1.4.1.2011.2.25.3.40.50.90.10.1.3
        otu3_pathPer15MCurVldty OBJECT-TYPE
            SYNTAX INTEGER
            MAX-ACCESS read-only
            STATUS current
            DESCRIPTION
                "perVldty. "
            ::= { otu3_pathPer15MCurEntry 3 }

        -- 1.3.6.1.4.1.2011.2.25.3.40.50.90.10.1.4
        otu3_pathPer15MCurDateTime OBJECT-TYPE
            SYNTAX DateAndTime
            MAX-ACCESS read-only
            STATUS current
            DESCRIPTION
                "perDateTime. "
            ::= { otu3_pathPer15MCurEntry 4 }

        -- 1.3.6.1.4.1.2011.2.25.3.40.50.90.10.1.5
        otu3_pathPer15MCurParaLen OBJECT-TYPE
            SYNTAX INTEGER
            MAX-ACCESS read-only
            STATUS current
            DESCRIPTION
                "perParaLen."
            ::= { otu3_pathPer15MCurEntry 5 }

        -- 1.3.6.1.4.1.2011.2.25.3.40.50.90.10.1.6
        otu3_pathPer15MCurPara OBJECT-TYPE
            SYNTAX OCTET STRING (SIZE (0..100))
            MAX-ACCESS read-only
            STATUS current
            DESCRIPTION
                "perPara."
            ::= { otu3_pathPer15MCurEntry 6 }




-- -------------------------------------------------------------------------
-- Perfomance 15-MIN History Data Table (RTRV-PER-<MOD2>)
-- -------------------------------------------------------------------------
        -- 1.3.6.1.4.1.2011.2.25.3.40.50.90.20
        otu3_pathPer15MHisTable OBJECT-TYPE
          SYNTAX SEQUENCE OF Otu3_pathPer15MHisEntry
          MAX-ACCESS not-accessible
          STATUS current
          DESCRIPTION
              "otu3_pathPer15MHis."
          ::= { otu3_path 20 }

        -- 1.3.6.1.4.1.2011.2.25.3.40.50.90.20.1
        otu3_pathPer15MHisEntry OBJECT-TYPE
            SYNTAX Otu3_pathPer15MHisEntry
            MAX-ACCESS not-accessible
            STATUS current
            DESCRIPTION
                "otu3_pathPer15MHis."
            INDEX {otu3_pathPer15MHisEid, otu3_pathPer15MHisParaLen, otu3_pathPer15MHisPara, otu3_pathPer15MHisDateTimeStart, otu3_pathPer15MHisDateTimeEnd}
            ::= { otu3_pathPer15MHisTable 1 }

        Otu3_pathPer15MHisEntry ::=
            SEQUENCE {
                otu3_pathPer15MHisEid
                    PerformanceEventType,
                otu3_pathPer15MHisParaLen
                    INTEGER,
                otu3_pathPer15MHisPara
                    OCTET STRING,
                otu3_pathPer15MHisMonValue
                    OCTET STRING,
                otu3_pathPer15MHisDateTimeStart
                    DateAndTime,
                otu3_pathPer15MHisDateTimeEnd
                    DateAndTime,
                otu3_pathPer15MHisVldty
                    INTEGER,
             }

        -- 1.3.6.1.4.1.2011.2.25.3.40.50.90.20.1.1
        otu3_pathPer15MHisEid OBJECT-TYPE
            SYNTAX PerformanceEventType
            MAX-ACCESS read-only
            STATUS current
            DESCRIPTION
                "perEid."
            ::= { otu3_pathPer15MHisEntry 1 }

        -- 1.3.6.1.4.1.2011.2.25.3.40.50.90.20.1.2
        otu3_pathPer15MHisParaLen OBJECT-TYPE
            SYNTAX INTEGER
            MAX-ACCESS read-only
            STATUS current
            DESCRIPTION
                "perParaLen."
            ::= { otu3_pathPer15MHisEntry 2 }

        -- 1.3.6.1.4.1.2011.2.25.3.40.50.90.20.1.3
        otu3_pathPer15MHisPara OBJECT-TYPE
            SYNTAX OCTET STRING (SIZE (0..100))
            MAX-ACCESS read-only
            STATUS current
            DESCRIPTION
                "perPara."
            ::= { otu3_pathPer15MHisEntry 3 }

        -- 1.3.6.1.4.1.2011.2.25.3.40.50.90.20.1.4
        otu3_pathPer15MHisMonValue OBJECT-TYPE
            SYNTAX OCTET STRING (SIZE (0..100))
            MAX-ACCESS read-only
            STATUS current
            DESCRIPTION
                "perMonValue."
            ::= { otu3_pathPer15MHisEntry 4 }

        -- 1.3.6.1.4.1.2011.2.25.3.40.50.90.20.1.5
        otu3_pathPer15MHisDateTimeStart OBJECT-TYPE
            SYNTAX DateAndTime
            MAX-ACCESS read-only
            STATUS current
            DESCRIPTION
                "perDateTimeStart. "
            ::= { otu3_pathPer15MHisEntry 5 }

        -- 1.3.6.1.4.1.2011.2.25.3.40.50.90.20.1.6
        otu3_pathPer15MHisDateTimeEnd OBJECT-TYPE
            SYNTAX DateAndTime
            MAX-ACCESS read-only
            STATUS current
            DESCRIPTION
                "perDateTimeEnd. "
            ::= { otu3_pathPer15MHisEntry 6 }

        -- 1.3.6.1.4.1.2011.2.25.3.40.50.90.20.1.7
        otu3_pathPer15MHisVldty OBJECT-TYPE
            SYNTAX INTEGER
            MAX-ACCESS read-only
            STATUS current
            DESCRIPTION
                "perVldty. "
            ::= { otu3_pathPer15MHisEntry 7 }




-- -------------------------------------------------------------------------
-- Perfomance 24-HOUR Current Data Table (RTRV-PER-<MOD2>)
-- -------------------------------------------------------------------------
        -- 1.3.6.1.4.1.2011.2.25.3.40.50.90.30
        otu3_pathPer24HCurTable OBJECT-TYPE
          SYNTAX SEQUENCE OF Otu3_pathPer24HCurEntry
          MAX-ACCESS not-accessible
          STATUS current
          DESCRIPTION
              "otu3_pathPer24HCur."
          ::= { otu3_path 30 }

        -- 1.3.6.1.4.1.2011.2.25.3.40.50.90.30.1
        otu3_pathPer24HCurEntry OBJECT-TYPE
            SYNTAX Otu3_pathPer24HCurEntry
            MAX-ACCESS not-accessible
            STATUS current
            DESCRIPTION
              "otu3_pathPer24HCur."
            INDEX { otu3_pathPer24HCurEid, otu3_pathPer24HCurPara }
            ::= { otu3_pathPer24HCurTable 1 }

        Otu3_pathPer24HCurEntry ::=
            SEQUENCE {
                otu3_pathPer24HCurEid
                    PerformanceEventType,
                otu3_pathPer24HCurMonValue
                    OCTET STRING,
                otu3_pathPer24HCurVldty
                    INTEGER,
                otu3_pathPer24HCurDateTime
                    DateAndTime,
                otu3_pathPer24HCurParaLen
                    INTEGER,
                otu3_pathPer24HCurPara
                    OCTET STRING
            }

        -- 1.3.6.1.4.1.2011.2.25.3.40.50.90.30.1.1
        otu3_pathPer24HCurEid OBJECT-TYPE
            SYNTAX PerformanceEventType
            MAX-ACCESS read-only
            STATUS current
            DESCRIPTION
                "perEid."
            ::= { otu3_pathPer24HCurEntry 1 }

        -- 1.3.6.1.4.1.2011.2.25.3.40.50.90.30.1.2
        otu3_pathPer24HCurMonValue OBJECT-TYPE
            SYNTAX OCTET STRING (SIZE (0..100))
            MAX-ACCESS read-only
            STATUS current
            DESCRIPTION
                "perMonValue."
            ::= { otu3_pathPer24HCurEntry 2 }

        -- 1.3.6.1.4.1.2011.2.25.3.40.50.90.30.1.3
        otu3_pathPer24HCurVldty OBJECT-TYPE
            SYNTAX INTEGER
            MAX-ACCESS read-only
            STATUS current
            DESCRIPTION
                "perVldty. "
            ::= { otu3_pathPer24HCurEntry 3 }

        -- 1.3.6.1.4.1.2011.2.25.3.40.50.90.30.1.4
        otu3_pathPer24HCurDateTime OBJECT-TYPE
            SYNTAX DateAndTime
            MAX-ACCESS read-only
            STATUS current
            DESCRIPTION
                "perDateTime. "
            ::= { otu3_pathPer24HCurEntry 4 }

        -- 1.3.6.1.4.1.2011.2.25.3.40.50.90.30.1.5
        otu3_pathPer24HCurParaLen OBJECT-TYPE
            SYNTAX INTEGER
            MAX-ACCESS read-only
            STATUS current
            DESCRIPTION
                "perParaLen."
            ::= { otu3_pathPer24HCurEntry 5 }

        -- 1.3.6.1.4.1.2011.2.25.3.40.50.90.30.1.6
        otu3_pathPer24HCurPara OBJECT-TYPE
            SYNTAX OCTET STRING (SIZE (0..100))
            MAX-ACCESS read-only
            STATUS current
            DESCRIPTION
                "perPara."
            ::= { otu3_pathPer24HCurEntry 6 }




-- -------------------------------------------------------------------------
-- Perfomance 24-HOUR History Data Table (RTRV-PER-<MOD2>)
-- -------------------------------------------------------------------------
        -- 1.3.6.1.4.1.2011.2.25.3.40.50.90.40
        otu3_pathPer24HHisTable OBJECT-TYPE
          SYNTAX SEQUENCE OF Otu3_pathPer24HHisEntry
          MAX-ACCESS not-accessible
          STATUS current
          DESCRIPTION
              "otu3_pathPer24HHis."
          ::= { otu3_path 40 }

        -- 1.3.6.1.4.1.2011.2.25.3.40.50.90.40.1
        otu3_pathPer24HHisEntry OBJECT-TYPE
            SYNTAX Otu3_pathPer24HHisEntry
            MAX-ACCESS not-accessible
            STATUS current
            DESCRIPTION
                "otu3_pathPer24HHis."
            INDEX {otu3_pathPer24HHisEid, otu3_pathPer24HHisParaLen, otu3_pathPer24HHisPara, otu3_pathPer24HHisDateTimeStart, otu3_pathPer24HHisDateTimeEnd}
            ::= { otu3_pathPer24HHisTable 1 }

        Otu3_pathPer24HHisEntry ::=
            SEQUENCE {
                otu3_pathPer24HHisEid
                    PerformanceEventType,
                otu3_pathPer24HHisParaLen
                    INTEGER,
                otu3_pathPer24HHisPara
                    OCTET STRING,
                otu3_pathPer24HHisMonValue
                    OCTET STRING,
                otu3_pathPer24HHisDateTimeStart
                    DateAndTime,
                otu3_pathPer24HHisDateTimeEnd
                    DateAndTime,
                otu3_pathPer24HHisVldty
                    INTEGER,
             }

        -- 1.3.6.1.4.1.2011.2.25.3.40.50.90.40.1.1
        otu3_pathPer24HHisEid OBJECT-TYPE
            SYNTAX PerformanceEventType
            MAX-ACCESS read-only
            STATUS current
            DESCRIPTION
                "perEid."
            ::= { otu3_pathPer24HHisEntry 1 }

        -- 1.3.6.1.4.1.2011.2.25.3.40.50.90.40.1.2
        otu3_pathPer24HHisParaLen OBJECT-TYPE
            SYNTAX INTEGER
            MAX-ACCESS read-only
            STATUS current
            DESCRIPTION
                "perParaLen."
            ::= { otu3_pathPer24HHisEntry 2 }

        -- 1.3.6.1.4.1.2011.2.25.3.40.50.90.40.1.3
        otu3_pathPer24HHisPara OBJECT-TYPE
            SYNTAX OCTET STRING (SIZE (0..100))
            MAX-ACCESS read-only
            STATUS current
            DESCRIPTION
                "perPara."
            ::= { otu3_pathPer24HHisEntry 3 }

        -- 1.3.6.1.4.1.2011.2.25.3.40.50.90.40.1.4
        otu3_pathPer24HHisMonValue OBJECT-TYPE
            SYNTAX OCTET STRING (SIZE (0..100))
            MAX-ACCESS read-only
            STATUS current
            DESCRIPTION
                "perMonValue."
            ::= { otu3_pathPer24HHisEntry 4 }

        -- 1.3.6.1.4.1.2011.2.25.3.40.50.90.40.1.5
        otu3_pathPer24HHisDateTimeStart OBJECT-TYPE
            SYNTAX DateAndTime
            MAX-ACCESS read-only
            STATUS current
            DESCRIPTION
                "perDateTimeStart. "
            ::= { otu3_pathPer24HHisEntry 5 }

        -- 1.3.6.1.4.1.2011.2.25.3.40.50.90.40.1.6
        otu3_pathPer24HHisDateTimeEnd OBJECT-TYPE
            SYNTAX DateAndTime
            MAX-ACCESS read-only
            STATUS current
            DESCRIPTION
                "perDateTimeEnd. "
            ::= { otu3_pathPer24HHisEntry 6 }

        -- 1.3.6.1.4.1.2011.2.25.3.40.50.90.40.1.7
        otu3_pathPer24HHisVldty OBJECT-TYPE
            SYNTAX INTEGER
            MAX-ACCESS read-only
            STATUS current
            DESCRIPTION
                "perVldty. "
            ::= { otu3_pathPer24HHisEntry 7 }




-- Alarm data
      -- 1.3.6.1.4.1.2011.2.25.3.40.50.92
      odu1_path OBJECT IDENTIFIER ::={ optixGlobalNGWDM 92 }


-- -------------------------------------------------------------------------
-- Perfomance 15-MIN Current Data Table (RTRV-PER-<MOD2>)
-- -------------------------------------------------------------------------
        -- 1.3.6.1.4.1.2011.2.25.3.40.50.92.10
        odu1_pathPer15MCurTable OBJECT-TYPE
          SYNTAX SEQUENCE OF Odu1_pathPer15MCurEntry
          MAX-ACCESS not-accessible
          STATUS current
          DESCRIPTION
              "odu1_pathPer15MCur."
          ::= { odu1_path 10 }

        -- 1.3.6.1.4.1.2011.2.25.3.40.50.92.10.1
        odu1_pathPer15MCurEntry OBJECT-TYPE
            SYNTAX Odu1_pathPer15MCurEntry
            MAX-ACCESS not-accessible
            STATUS current
            DESCRIPTION
              "odu1_pathPer15MCur."
            INDEX { odu1_pathPer15MCurEid, odu1_pathPer15MCurPara }
            ::= { odu1_pathPer15MCurTable 1 }

        Odu1_pathPer15MCurEntry ::=
            SEQUENCE {
                odu1_pathPer15MCurEid
                    PerformanceEventType,
                odu1_pathPer15MCurMonValue
                    OCTET STRING,
                odu1_pathPer15MCurVldty
                    INTEGER,
                odu1_pathPer15MCurDateTime
                    DateAndTime,
                odu1_pathPer15MCurParaLen
                    INTEGER,
                odu1_pathPer15MCurPara
                    OCTET STRING
            }

        -- 1.3.6.1.4.1.2011.2.25.3.40.50.92.10.1.1
        odu1_pathPer15MCurEid OBJECT-TYPE
            SYNTAX PerformanceEventType
            MAX-ACCESS read-only
            STATUS current
            DESCRIPTION
                "perEid."
            ::= { odu1_pathPer15MCurEntry 1 }

        -- 1.3.6.1.4.1.2011.2.25.3.40.50.92.10.1.2
        odu1_pathPer15MCurMonValue OBJECT-TYPE
            SYNTAX OCTET STRING (SIZE (0..100))
            MAX-ACCESS read-only
            STATUS current
            DESCRIPTION
                "perMonValue."
            ::= { odu1_pathPer15MCurEntry 2 }

        -- 1.3.6.1.4.1.2011.2.25.3.40.50.92.10.1.3
        odu1_pathPer15MCurVldty OBJECT-TYPE
            SYNTAX INTEGER
            MAX-ACCESS read-only
            STATUS current
            DESCRIPTION
                "perVldty. "
            ::= { odu1_pathPer15MCurEntry 3 }

        -- 1.3.6.1.4.1.2011.2.25.3.40.50.92.10.1.4
        odu1_pathPer15MCurDateTime OBJECT-TYPE
            SYNTAX DateAndTime
            MAX-ACCESS read-only
            STATUS current
            DESCRIPTION
                "perDateTime. "
            ::= { odu1_pathPer15MCurEntry 4 }

        -- 1.3.6.1.4.1.2011.2.25.3.40.50.92.10.1.5
        odu1_pathPer15MCurParaLen OBJECT-TYPE
            SYNTAX INTEGER
            MAX-ACCESS read-only
            STATUS current
            DESCRIPTION
                "perParaLen."
            ::= { odu1_pathPer15MCurEntry 5 }

        -- 1.3.6.1.4.1.2011.2.25.3.40.50.92.10.1.6
        odu1_pathPer15MCurPara OBJECT-TYPE
            SYNTAX OCTET STRING (SIZE (0..100))
            MAX-ACCESS read-only
            STATUS current
            DESCRIPTION
                "perPara."
            ::= { odu1_pathPer15MCurEntry 6 }




-- -------------------------------------------------------------------------
-- Perfomance 15-MIN History Data Table (RTRV-PER-<MOD2>)
-- -------------------------------------------------------------------------
        -- 1.3.6.1.4.1.2011.2.25.3.40.50.92.20
        odu1_pathPer15MHisTable OBJECT-TYPE
          SYNTAX SEQUENCE OF Odu1_pathPer15MHisEntry
          MAX-ACCESS not-accessible
          STATUS current
          DESCRIPTION
              "odu1_pathPer15MHis."
          ::= { odu1_path 20 }

        -- 1.3.6.1.4.1.2011.2.25.3.40.50.92.20.1
        odu1_pathPer15MHisEntry OBJECT-TYPE
            SYNTAX Odu1_pathPer15MHisEntry
            MAX-ACCESS not-accessible
            STATUS current
            DESCRIPTION
                "odu1_pathPer15MHis."
            INDEX {odu1_pathPer15MHisEid, odu1_pathPer15MHisParaLen, odu1_pathPer15MHisPara, odu1_pathPer15MHisDateTimeStart, odu1_pathPer15MHisDateTimeEnd}
            ::= { odu1_pathPer15MHisTable 1 }

        Odu1_pathPer15MHisEntry ::=
            SEQUENCE {
                odu1_pathPer15MHisEid
                    PerformanceEventType,
                odu1_pathPer15MHisParaLen
                    INTEGER,
                odu1_pathPer15MHisPara
                    OCTET STRING,
                odu1_pathPer15MHisMonValue
                    OCTET STRING,
                odu1_pathPer15MHisDateTimeStart
                    DateAndTime,
                odu1_pathPer15MHisDateTimeEnd
                    DateAndTime,
                odu1_pathPer15MHisVldty
                    INTEGER,
             }

        -- 1.3.6.1.4.1.2011.2.25.3.40.50.92.20.1.1
        odu1_pathPer15MHisEid OBJECT-TYPE
            SYNTAX PerformanceEventType
            MAX-ACCESS read-only
            STATUS current
            DESCRIPTION
                "perEid."
            ::= { odu1_pathPer15MHisEntry 1 }

        -- 1.3.6.1.4.1.2011.2.25.3.40.50.92.20.1.2
        odu1_pathPer15MHisParaLen OBJECT-TYPE
            SYNTAX INTEGER
            MAX-ACCESS read-only
            STATUS current
            DESCRIPTION
                "perParaLen."
            ::= { odu1_pathPer15MHisEntry 2 }

        -- 1.3.6.1.4.1.2011.2.25.3.40.50.92.20.1.3
        odu1_pathPer15MHisPara OBJECT-TYPE
            SYNTAX OCTET STRING (SIZE (0..100))
            MAX-ACCESS read-only
            STATUS current
            DESCRIPTION
                "perPara."
            ::= { odu1_pathPer15MHisEntry 3 }

        -- 1.3.6.1.4.1.2011.2.25.3.40.50.92.20.1.4
        odu1_pathPer15MHisMonValue OBJECT-TYPE
            SYNTAX OCTET STRING (SIZE (0..100))
            MAX-ACCESS read-only
            STATUS current
            DESCRIPTION
                "perMonValue."
            ::= { odu1_pathPer15MHisEntry 4 }

        -- 1.3.6.1.4.1.2011.2.25.3.40.50.92.20.1.5
        odu1_pathPer15MHisDateTimeStart OBJECT-TYPE
            SYNTAX DateAndTime
            MAX-ACCESS read-only
            STATUS current
            DESCRIPTION
                "perDateTimeStart. "
            ::= { odu1_pathPer15MHisEntry 5 }

        -- 1.3.6.1.4.1.2011.2.25.3.40.50.92.20.1.6
        odu1_pathPer15MHisDateTimeEnd OBJECT-TYPE
            SYNTAX DateAndTime
            MAX-ACCESS read-only
            STATUS current
            DESCRIPTION
                "perDateTimeEnd. "
            ::= { odu1_pathPer15MHisEntry 6 }

        -- 1.3.6.1.4.1.2011.2.25.3.40.50.92.20.1.7
        odu1_pathPer15MHisVldty OBJECT-TYPE
            SYNTAX INTEGER
            MAX-ACCESS read-only
            STATUS current
            DESCRIPTION
                "perVldty. "
            ::= { odu1_pathPer15MHisEntry 7 }




-- -------------------------------------------------------------------------
-- Perfomance 24-HOUR Current Data Table (RTRV-PER-<MOD2>)
-- -------------------------------------------------------------------------
        -- 1.3.6.1.4.1.2011.2.25.3.40.50.92.30
        odu1_pathPer24HCurTable OBJECT-TYPE
          SYNTAX SEQUENCE OF Odu1_pathPer24HCurEntry
          MAX-ACCESS not-accessible
          STATUS current
          DESCRIPTION
              "odu1_pathPer24HCur."
          ::= { odu1_path 30 }

        -- 1.3.6.1.4.1.2011.2.25.3.40.50.92.30.1
        odu1_pathPer24HCurEntry OBJECT-TYPE
            SYNTAX Odu1_pathPer24HCurEntry
            MAX-ACCESS not-accessible
            STATUS current
            DESCRIPTION
              "odu1_pathPer24HCur."
            INDEX { odu1_pathPer24HCurEid, odu1_pathPer24HCurPara }
            ::= { odu1_pathPer24HCurTable 1 }

        Odu1_pathPer24HCurEntry ::=
            SEQUENCE {
                odu1_pathPer24HCurEid
                    PerformanceEventType,
                odu1_pathPer24HCurMonValue
                    OCTET STRING,
                odu1_pathPer24HCurVldty
                    INTEGER,
                odu1_pathPer24HCurDateTime
                    DateAndTime,
                odu1_pathPer24HCurParaLen
                    INTEGER,
                odu1_pathPer24HCurPara
                    OCTET STRING
            }

        -- 1.3.6.1.4.1.2011.2.25.3.40.50.92.30.1.1
        odu1_pathPer24HCurEid OBJECT-TYPE
            SYNTAX PerformanceEventType
            MAX-ACCESS read-only
            STATUS current
            DESCRIPTION
                "perEid."
            ::= { odu1_pathPer24HCurEntry 1 }

        -- 1.3.6.1.4.1.2011.2.25.3.40.50.92.30.1.2
        odu1_pathPer24HCurMonValue OBJECT-TYPE
            SYNTAX OCTET STRING (SIZE (0..100))
            MAX-ACCESS read-only
            STATUS current
            DESCRIPTION
                "perMonValue."
            ::= { odu1_pathPer24HCurEntry 2 }

        -- 1.3.6.1.4.1.2011.2.25.3.40.50.92.30.1.3
        odu1_pathPer24HCurVldty OBJECT-TYPE
            SYNTAX INTEGER
            MAX-ACCESS read-only
            STATUS current
            DESCRIPTION
                "perVldty. "
            ::= { odu1_pathPer24HCurEntry 3 }

        -- 1.3.6.1.4.1.2011.2.25.3.40.50.92.30.1.4
        odu1_pathPer24HCurDateTime OBJECT-TYPE
            SYNTAX DateAndTime
            MAX-ACCESS read-only
            STATUS current
            DESCRIPTION
                "perDateTime. "
            ::= { odu1_pathPer24HCurEntry 4 }

        -- 1.3.6.1.4.1.2011.2.25.3.40.50.92.30.1.5
        odu1_pathPer24HCurParaLen OBJECT-TYPE
            SYNTAX INTEGER
            MAX-ACCESS read-only
            STATUS current
            DESCRIPTION
                "perParaLen."
            ::= { odu1_pathPer24HCurEntry 5 }

        -- 1.3.6.1.4.1.2011.2.25.3.40.50.92.30.1.6
        odu1_pathPer24HCurPara OBJECT-TYPE
            SYNTAX OCTET STRING (SIZE (0..100))
            MAX-ACCESS read-only
            STATUS current
            DESCRIPTION
                "perPara."
            ::= { odu1_pathPer24HCurEntry 6 }




-- -------------------------------------------------------------------------
-- Perfomance 24-HOUR History Data Table (RTRV-PER-<MOD2>)
-- -------------------------------------------------------------------------
        -- 1.3.6.1.4.1.2011.2.25.3.40.50.92.40
        odu1_pathPer24HHisTable OBJECT-TYPE
          SYNTAX SEQUENCE OF Odu1_pathPer24HHisEntry
          MAX-ACCESS not-accessible
          STATUS current
          DESCRIPTION
              "odu1_pathPer24HHis."
          ::= { odu1_path 40 }

        -- 1.3.6.1.4.1.2011.2.25.3.40.50.92.40.1
        odu1_pathPer24HHisEntry OBJECT-TYPE
            SYNTAX Odu1_pathPer24HHisEntry
            MAX-ACCESS not-accessible
            STATUS current
            DESCRIPTION
                "odu1_pathPer24HHis."
            INDEX {odu1_pathPer24HHisEid, odu1_pathPer24HHisParaLen, odu1_pathPer24HHisPara, odu1_pathPer24HHisDateTimeStart, odu1_pathPer24HHisDateTimeEnd}
            ::= { odu1_pathPer24HHisTable 1 }

        Odu1_pathPer24HHisEntry ::=
            SEQUENCE {
                odu1_pathPer24HHisEid
                    PerformanceEventType,
                odu1_pathPer24HHisParaLen
                    INTEGER,
                odu1_pathPer24HHisPara
                    OCTET STRING,
                odu1_pathPer24HHisMonValue
                    OCTET STRING,
                odu1_pathPer24HHisDateTimeStart
                    DateAndTime,
                odu1_pathPer24HHisDateTimeEnd
                    DateAndTime,
                odu1_pathPer24HHisVldty
                    INTEGER,
             }

        -- 1.3.6.1.4.1.2011.2.25.3.40.50.92.40.1.1
        odu1_pathPer24HHisEid OBJECT-TYPE
            SYNTAX PerformanceEventType
            MAX-ACCESS read-only
            STATUS current
            DESCRIPTION
                "perEid."
            ::= { odu1_pathPer24HHisEntry 1 }

        -- 1.3.6.1.4.1.2011.2.25.3.40.50.92.40.1.2
        odu1_pathPer24HHisParaLen OBJECT-TYPE
            SYNTAX INTEGER
            MAX-ACCESS read-only
            STATUS current
            DESCRIPTION
                "perParaLen."
            ::= { odu1_pathPer24HHisEntry 2 }

        -- 1.3.6.1.4.1.2011.2.25.3.40.50.92.40.1.3
        odu1_pathPer24HHisPara OBJECT-TYPE
            SYNTAX OCTET STRING (SIZE (0..100))
            MAX-ACCESS read-only
            STATUS current
            DESCRIPTION
                "perPara."
            ::= { odu1_pathPer24HHisEntry 3 }

        -- 1.3.6.1.4.1.2011.2.25.3.40.50.92.40.1.4
        odu1_pathPer24HHisMonValue OBJECT-TYPE
            SYNTAX OCTET STRING (SIZE (0..100))
            MAX-ACCESS read-only
            STATUS current
            DESCRIPTION
                "perMonValue."
            ::= { odu1_pathPer24HHisEntry 4 }

        -- 1.3.6.1.4.1.2011.2.25.3.40.50.92.40.1.5
        odu1_pathPer24HHisDateTimeStart OBJECT-TYPE
            SYNTAX DateAndTime
            MAX-ACCESS read-only
            STATUS current
            DESCRIPTION
                "perDateTimeStart. "
            ::= { odu1_pathPer24HHisEntry 5 }

        -- 1.3.6.1.4.1.2011.2.25.3.40.50.92.40.1.6
        odu1_pathPer24HHisDateTimeEnd OBJECT-TYPE
            SYNTAX DateAndTime
            MAX-ACCESS read-only
            STATUS current
            DESCRIPTION
                "perDateTimeEnd. "
            ::= { odu1_pathPer24HHisEntry 6 }

        -- 1.3.6.1.4.1.2011.2.25.3.40.50.92.40.1.7
        odu1_pathPer24HHisVldty OBJECT-TYPE
            SYNTAX INTEGER
            MAX-ACCESS read-only
            STATUS current
            DESCRIPTION
                "perVldty. "
            ::= { odu1_pathPer24HHisEntry 7 }




-- Alarm data
      -- 1.3.6.1.4.1.2011.2.25.3.40.50.97
      new_Eth_port OBJECT IDENTIFIER ::={ optixGlobalNGWDM 97 }


-- -------------------------------------------------------------------------
-- Perfomance 15-MIN Current Data Table (RTRV-PER-<MOD2>)
-- -------------------------------------------------------------------------
        -- 1.3.6.1.4.1.2011.2.25.3.40.50.97.10
        new_Eth_portPer15MCurTable OBJECT-TYPE
          SYNTAX SEQUENCE OF New_Eth_portPer15MCurEntry
          MAX-ACCESS not-accessible
          STATUS current
          DESCRIPTION
              "new_Eth_portPer15MCur."
          ::= { new_Eth_port 10 }

        -- 1.3.6.1.4.1.2011.2.25.3.40.50.97.10.1
        new_Eth_portPer15MCurEntry OBJECT-TYPE
            SYNTAX New_Eth_portPer15MCurEntry
            MAX-ACCESS not-accessible
            STATUS current
            DESCRIPTION
              "new_Eth_portPer15MCur."
            INDEX { new_Eth_portPer15MCurEid, new_Eth_portPer15MCurPara }
            ::= { new_Eth_portPer15MCurTable 1 }

        New_Eth_portPer15MCurEntry ::=
            SEQUENCE {
                new_Eth_portPer15MCurEid
                    PerformanceEventType,
                new_Eth_portPer15MCurMonValue
                    OCTET STRING,
                new_Eth_portPer15MCurVldty
                    INTEGER,
                new_Eth_portPer15MCurDateTime
                    DateAndTime,
                new_Eth_portPer15MCurParaLen
                    INTEGER,
                new_Eth_portPer15MCurPara
                    OCTET STRING
            }

        -- 1.3.6.1.4.1.2011.2.25.3.40.50.97.10.1.1
        new_Eth_portPer15MCurEid OBJECT-TYPE
            SYNTAX PerformanceEventType
            MAX-ACCESS read-only
            STATUS current
            DESCRIPTION
                "perEid."
            ::= { new_Eth_portPer15MCurEntry 1 }

        -- 1.3.6.1.4.1.2011.2.25.3.40.50.97.10.1.2
        new_Eth_portPer15MCurMonValue OBJECT-TYPE
            SYNTAX OCTET STRING (SIZE (0..100))
            MAX-ACCESS read-only
            STATUS current
            DESCRIPTION
                "perMonValue."
            ::= { new_Eth_portPer15MCurEntry 2 }

        -- 1.3.6.1.4.1.2011.2.25.3.40.50.97.10.1.3
        new_Eth_portPer15MCurVldty OBJECT-TYPE
            SYNTAX INTEGER
            MAX-ACCESS read-only
            STATUS current
            DESCRIPTION
                "perVldty. "
            ::= { new_Eth_portPer15MCurEntry 3 }

        -- 1.3.6.1.4.1.2011.2.25.3.40.50.97.10.1.4
        new_Eth_portPer15MCurDateTime OBJECT-TYPE
            SYNTAX DateAndTime
            MAX-ACCESS read-only
            STATUS current
            DESCRIPTION
                "perDateTime. "
            ::= { new_Eth_portPer15MCurEntry 4 }

        -- 1.3.6.1.4.1.2011.2.25.3.40.50.97.10.1.5
        new_Eth_portPer15MCurParaLen OBJECT-TYPE
            SYNTAX INTEGER
            MAX-ACCESS read-only
            STATUS current
            DESCRIPTION
                "perParaLen."
            ::= { new_Eth_portPer15MCurEntry 5 }

        -- 1.3.6.1.4.1.2011.2.25.3.40.50.97.10.1.6
        new_Eth_portPer15MCurPara OBJECT-TYPE
            SYNTAX OCTET STRING (SIZE (0..100))
            MAX-ACCESS read-only
            STATUS current
            DESCRIPTION
                "perPara."
            ::= { new_Eth_portPer15MCurEntry 6 }




-- -------------------------------------------------------------------------
-- Perfomance 15-MIN History Data Table (RTRV-PER-<MOD2>)
-- -------------------------------------------------------------------------
        -- 1.3.6.1.4.1.2011.2.25.3.40.50.97.20
        new_Eth_portPer15MHisTable OBJECT-TYPE
          SYNTAX SEQUENCE OF New_Eth_portPer15MHisEntry
          MAX-ACCESS not-accessible
          STATUS current
          DESCRIPTION
              "new_Eth_portPer15MHis."
          ::= { new_Eth_port 20 }

        -- 1.3.6.1.4.1.2011.2.25.3.40.50.97.20.1
        new_Eth_portPer15MHisEntry OBJECT-TYPE
            SYNTAX New_Eth_portPer15MHisEntry
            MAX-ACCESS not-accessible
            STATUS current
            DESCRIPTION
                "new_Eth_portPer15MHis."
            INDEX {new_Eth_portPer15MHisEid, new_Eth_portPer15MHisParaLen, new_Eth_portPer15MHisPara, new_Eth_portPer15MHisDateTimeStart, new_Eth_portPer15MHisDateTimeEnd}
            ::= { new_Eth_portPer15MHisTable 1 }

        New_Eth_portPer15MHisEntry ::=
            SEQUENCE {
                new_Eth_portPer15MHisEid
                    PerformanceEventType,
                new_Eth_portPer15MHisParaLen
                    INTEGER,
                new_Eth_portPer15MHisPara
                    OCTET STRING,
                new_Eth_portPer15MHisMonValue
                    OCTET STRING,
                new_Eth_portPer15MHisDateTimeStart
                    DateAndTime,
                new_Eth_portPer15MHisDateTimeEnd
                    DateAndTime,
                new_Eth_portPer15MHisVldty
                    INTEGER,
             }

        -- 1.3.6.1.4.1.2011.2.25.3.40.50.97.20.1.1
        new_Eth_portPer15MHisEid OBJECT-TYPE
            SYNTAX PerformanceEventType
            MAX-ACCESS read-only
            STATUS current
            DESCRIPTION
                "perEid."
            ::= { new_Eth_portPer15MHisEntry 1 }

        -- 1.3.6.1.4.1.2011.2.25.3.40.50.97.20.1.2
        new_Eth_portPer15MHisParaLen OBJECT-TYPE
            SYNTAX INTEGER
            MAX-ACCESS read-only
            STATUS current
            DESCRIPTION
                "perParaLen."
            ::= { new_Eth_portPer15MHisEntry 2 }

        -- 1.3.6.1.4.1.2011.2.25.3.40.50.97.20.1.3
        new_Eth_portPer15MHisPara OBJECT-TYPE
            SYNTAX OCTET STRING (SIZE (0..100))
            MAX-ACCESS read-only
            STATUS current
            DESCRIPTION
                "perPara."
            ::= { new_Eth_portPer15MHisEntry 3 }

        -- 1.3.6.1.4.1.2011.2.25.3.40.50.97.20.1.4
        new_Eth_portPer15MHisMonValue OBJECT-TYPE
            SYNTAX OCTET STRING (SIZE (0..100))
            MAX-ACCESS read-only
            STATUS current
            DESCRIPTION
                "perMonValue."
            ::= { new_Eth_portPer15MHisEntry 4 }

        -- 1.3.6.1.4.1.2011.2.25.3.40.50.97.20.1.5
        new_Eth_portPer15MHisDateTimeStart OBJECT-TYPE
            SYNTAX DateAndTime
            MAX-ACCESS read-only
            STATUS current
            DESCRIPTION
                "perDateTimeStart. "
            ::= { new_Eth_portPer15MHisEntry 5 }

        -- 1.3.6.1.4.1.2011.2.25.3.40.50.97.20.1.6
        new_Eth_portPer15MHisDateTimeEnd OBJECT-TYPE
            SYNTAX DateAndTime
            MAX-ACCESS read-only
            STATUS current
            DESCRIPTION
                "perDateTimeEnd. "
            ::= { new_Eth_portPer15MHisEntry 6 }

        -- 1.3.6.1.4.1.2011.2.25.3.40.50.97.20.1.7
        new_Eth_portPer15MHisVldty OBJECT-TYPE
            SYNTAX INTEGER
            MAX-ACCESS read-only
            STATUS current
            DESCRIPTION
                "perVldty. "
            ::= { new_Eth_portPer15MHisEntry 7 }




-- -------------------------------------------------------------------------
-- Perfomance 24-HOUR Current Data Table (RTRV-PER-<MOD2>)
-- -------------------------------------------------------------------------
        -- 1.3.6.1.4.1.2011.2.25.3.40.50.97.30
        new_Eth_portPer24HCurTable OBJECT-TYPE
          SYNTAX SEQUENCE OF New_Eth_portPer24HCurEntry
          MAX-ACCESS not-accessible
          STATUS current
          DESCRIPTION
              "new_Eth_portPer24HCur."
          ::= { new_Eth_port 30 }

        -- 1.3.6.1.4.1.2011.2.25.3.40.50.97.30.1
        new_Eth_portPer24HCurEntry OBJECT-TYPE
            SYNTAX New_Eth_portPer24HCurEntry
            MAX-ACCESS not-accessible
            STATUS current
            DESCRIPTION
              "new_Eth_portPer24HCur."
            INDEX { new_Eth_portPer24HCurEid, new_Eth_portPer24HCurPara }
            ::= { new_Eth_portPer24HCurTable 1 }

        New_Eth_portPer24HCurEntry ::=
            SEQUENCE {
                new_Eth_portPer24HCurEid
                    PerformanceEventType,
                new_Eth_portPer24HCurMonValue
                    OCTET STRING,
                new_Eth_portPer24HCurVldty
                    INTEGER,
                new_Eth_portPer24HCurDateTime
                    DateAndTime,
                new_Eth_portPer24HCurParaLen
                    INTEGER,
                new_Eth_portPer24HCurPara
                    OCTET STRING
            }

        -- 1.3.6.1.4.1.2011.2.25.3.40.50.97.30.1.1
        new_Eth_portPer24HCurEid OBJECT-TYPE
            SYNTAX PerformanceEventType
            MAX-ACCESS read-only
            STATUS current
            DESCRIPTION
                "perEid."
            ::= { new_Eth_portPer24HCurEntry 1 }

        -- 1.3.6.1.4.1.2011.2.25.3.40.50.97.30.1.2
        new_Eth_portPer24HCurMonValue OBJECT-TYPE
            SYNTAX OCTET STRING (SIZE (0..100))
            MAX-ACCESS read-only
            STATUS current
            DESCRIPTION
                "perMonValue."
            ::= { new_Eth_portPer24HCurEntry 2 }

        -- 1.3.6.1.4.1.2011.2.25.3.40.50.97.30.1.3
        new_Eth_portPer24HCurVldty OBJECT-TYPE
            SYNTAX INTEGER
            MAX-ACCESS read-only
            STATUS current
            DESCRIPTION
                "perVldty. "
            ::= { new_Eth_portPer24HCurEntry 3 }

        -- 1.3.6.1.4.1.2011.2.25.3.40.50.97.30.1.4
        new_Eth_portPer24HCurDateTime OBJECT-TYPE
            SYNTAX DateAndTime
            MAX-ACCESS read-only
            STATUS current
            DESCRIPTION
                "perDateTime. "
            ::= { new_Eth_portPer24HCurEntry 4 }

        -- 1.3.6.1.4.1.2011.2.25.3.40.50.97.30.1.5
        new_Eth_portPer24HCurParaLen OBJECT-TYPE
            SYNTAX INTEGER
            MAX-ACCESS read-only
            STATUS current
            DESCRIPTION
                "perParaLen."
            ::= { new_Eth_portPer24HCurEntry 5 }

        -- 1.3.6.1.4.1.2011.2.25.3.40.50.97.30.1.6
        new_Eth_portPer24HCurPara OBJECT-TYPE
            SYNTAX OCTET STRING (SIZE (0..100))
            MAX-ACCESS read-only
            STATUS current
            DESCRIPTION
                "perPara."
            ::= { new_Eth_portPer24HCurEntry 6 }




-- -------------------------------------------------------------------------
-- Perfomance 24-HOUR History Data Table (RTRV-PER-<MOD2>)
-- -------------------------------------------------------------------------
        -- 1.3.6.1.4.1.2011.2.25.3.40.50.97.40
        new_Eth_portPer24HHisTable OBJECT-TYPE
          SYNTAX SEQUENCE OF New_Eth_portPer24HHisEntry
          MAX-ACCESS not-accessible
          STATUS current
          DESCRIPTION
              "new_Eth_portPer24HHis."
          ::= { new_Eth_port 40 }

        -- 1.3.6.1.4.1.2011.2.25.3.40.50.97.40.1
        new_Eth_portPer24HHisEntry OBJECT-TYPE
            SYNTAX New_Eth_portPer24HHisEntry
            MAX-ACCESS not-accessible
            STATUS current
            DESCRIPTION
                "new_Eth_portPer24HHis."
            INDEX {new_Eth_portPer24HHisEid, new_Eth_portPer24HHisParaLen, new_Eth_portPer24HHisPara, new_Eth_portPer24HHisDateTimeStart, new_Eth_portPer24HHisDateTimeEnd}
            ::= { new_Eth_portPer24HHisTable 1 }

        New_Eth_portPer24HHisEntry ::=
            SEQUENCE {
                new_Eth_portPer24HHisEid
                    PerformanceEventType,
                new_Eth_portPer24HHisParaLen
                    INTEGER,
                new_Eth_portPer24HHisPara
                    OCTET STRING,
                new_Eth_portPer24HHisMonValue
                    OCTET STRING,
                new_Eth_portPer24HHisDateTimeStart
                    DateAndTime,
                new_Eth_portPer24HHisDateTimeEnd
                    DateAndTime,
                new_Eth_portPer24HHisVldty
                    INTEGER,
             }

        -- 1.3.6.1.4.1.2011.2.25.3.40.50.97.40.1.1
        new_Eth_portPer24HHisEid OBJECT-TYPE
            SYNTAX PerformanceEventType
            MAX-ACCESS read-only
            STATUS current
            DESCRIPTION
                "perEid."
            ::= { new_Eth_portPer24HHisEntry 1 }

        -- 1.3.6.1.4.1.2011.2.25.3.40.50.97.40.1.2
        new_Eth_portPer24HHisParaLen OBJECT-TYPE
            SYNTAX INTEGER
            MAX-ACCESS read-only
            STATUS current
            DESCRIPTION
                "perParaLen."
            ::= { new_Eth_portPer24HHisEntry 2 }

        -- 1.3.6.1.4.1.2011.2.25.3.40.50.97.40.1.3
        new_Eth_portPer24HHisPara OBJECT-TYPE
            SYNTAX OCTET STRING (SIZE (0..100))
            MAX-ACCESS read-only
            STATUS current
            DESCRIPTION
                "perPara."
            ::= { new_Eth_portPer24HHisEntry 3 }

        -- 1.3.6.1.4.1.2011.2.25.3.40.50.97.40.1.4
        new_Eth_portPer24HHisMonValue OBJECT-TYPE
            SYNTAX OCTET STRING (SIZE (0..100))
            MAX-ACCESS read-only
            STATUS current
            DESCRIPTION
                "perMonValue."
            ::= { new_Eth_portPer24HHisEntry 4 }

        -- 1.3.6.1.4.1.2011.2.25.3.40.50.97.40.1.5
        new_Eth_portPer24HHisDateTimeStart OBJECT-TYPE
            SYNTAX DateAndTime
            MAX-ACCESS read-only
            STATUS current
            DESCRIPTION
                "perDateTimeStart. "
            ::= { new_Eth_portPer24HHisEntry 5 }

        -- 1.3.6.1.4.1.2011.2.25.3.40.50.97.40.1.6
        new_Eth_portPer24HHisDateTimeEnd OBJECT-TYPE
            SYNTAX DateAndTime
            MAX-ACCESS read-only
            STATUS current
            DESCRIPTION
                "perDateTimeEnd. "
            ::= { new_Eth_portPer24HHisEntry 6 }

        -- 1.3.6.1.4.1.2011.2.25.3.40.50.97.40.1.7
        new_Eth_portPer24HHisVldty OBJECT-TYPE
            SYNTAX INTEGER
            MAX-ACCESS read-only
            STATUS current
            DESCRIPTION
                "perVldty. "
            ::= { new_Eth_portPer24HHisEntry 7 }




-- Alarm data
      -- 1.3.6.1.4.1.2011.2.25.3.40.50.98
      eth_path OBJECT IDENTIFIER ::={ optixGlobalNGWDM 98 }


-- -------------------------------------------------------------------------
-- Perfomance 15-MIN Current Data Table (RTRV-PER-<MOD2>)
-- -------------------------------------------------------------------------
        -- 1.3.6.1.4.1.2011.2.25.3.40.50.98.10
        eth_pathPer15MCurTable OBJECT-TYPE
          SYNTAX SEQUENCE OF Eth_pathPer15MCurEntry
          MAX-ACCESS not-accessible
          STATUS current
          DESCRIPTION
              "eth_pathPer15MCur."
          ::= { eth_path 10 }

        -- 1.3.6.1.4.1.2011.2.25.3.40.50.98.10.1
        eth_pathPer15MCurEntry OBJECT-TYPE
            SYNTAX Eth_pathPer15MCurEntry
            MAX-ACCESS not-accessible
            STATUS current
            DESCRIPTION
              "eth_pathPer15MCur."
            INDEX { eth_pathPer15MCurEid, eth_pathPer15MCurPara }
            ::= { eth_pathPer15MCurTable 1 }

        Eth_pathPer15MCurEntry ::=
            SEQUENCE {
                eth_pathPer15MCurEid
                    PerformanceEventType,
                eth_pathPer15MCurMonValue
                    OCTET STRING,
                eth_pathPer15MCurVldty
                    INTEGER,
                eth_pathPer15MCurDateTime
                    DateAndTime,
                eth_pathPer15MCurParaLen
                    INTEGER,
                eth_pathPer15MCurPara
                    OCTET STRING
            }

        -- 1.3.6.1.4.1.2011.2.25.3.40.50.98.10.1.1
        eth_pathPer15MCurEid OBJECT-TYPE
            SYNTAX PerformanceEventType
            MAX-ACCESS read-only
            STATUS current
            DESCRIPTION
                "perEid."
            ::= { eth_pathPer15MCurEntry 1 }

        -- 1.3.6.1.4.1.2011.2.25.3.40.50.98.10.1.2
        eth_pathPer15MCurMonValue OBJECT-TYPE
            SYNTAX OCTET STRING (SIZE (0..100))
            MAX-ACCESS read-only
            STATUS current
            DESCRIPTION
                "perMonValue."
            ::= { eth_pathPer15MCurEntry 2 }

        -- 1.3.6.1.4.1.2011.2.25.3.40.50.98.10.1.3
        eth_pathPer15MCurVldty OBJECT-TYPE
            SYNTAX INTEGER
            MAX-ACCESS read-only
            STATUS current
            DESCRIPTION
                "perVldty. "
            ::= { eth_pathPer15MCurEntry 3 }

        -- 1.3.6.1.4.1.2011.2.25.3.40.50.98.10.1.4
        eth_pathPer15MCurDateTime OBJECT-TYPE
            SYNTAX DateAndTime
            MAX-ACCESS read-only
            STATUS current
            DESCRIPTION
                "perDateTime. "
            ::= { eth_pathPer15MCurEntry 4 }

        -- 1.3.6.1.4.1.2011.2.25.3.40.50.98.10.1.5
        eth_pathPer15MCurParaLen OBJECT-TYPE
            SYNTAX INTEGER
            MAX-ACCESS read-only
            STATUS current
            DESCRIPTION
                "perParaLen."
            ::= { eth_pathPer15MCurEntry 5 }

        -- 1.3.6.1.4.1.2011.2.25.3.40.50.98.10.1.6
        eth_pathPer15MCurPara OBJECT-TYPE
            SYNTAX OCTET STRING (SIZE (0..100))
            MAX-ACCESS read-only
            STATUS current
            DESCRIPTION
                "perPara."
            ::= { eth_pathPer15MCurEntry 6 }



-- -------------------------------------------------------------------------
-- Perfomance 15-MIN History Data Table (RTRV-PER-<MOD2>)
-- -------------------------------------------------------------------------
        -- 1.3.6.1.4.1.2011.2.25.3.40.50.98.20
        eth_pathPer15MHisTable OBJECT-TYPE
          SYNTAX SEQUENCE OF Eth_pathPer15MHisEntry
          MAX-ACCESS not-accessible
          STATUS current
          DESCRIPTION
              "eth_pathPer15MHis."
          ::= { eth_path 20 }

        -- 1.3.6.1.4.1.2011.2.25.3.40.50.98.20.1
        eth_pathPer15MHisEntry OBJECT-TYPE
            SYNTAX Eth_pathPer15MHisEntry
            MAX-ACCESS not-accessible
            STATUS current
            DESCRIPTION
                "eth_pathPer15MHis."
            INDEX {eth_pathPer15MHisEid, eth_pathPer15MHisParaLen, eth_pathPer15MHisPara, eth_pathPer15MHisDateTimeStart, eth_pathPer15MHisDateTimeEnd}
            ::= { eth_pathPer15MHisTable 1 }

        Eth_pathPer15MHisEntry ::=
            SEQUENCE {
                eth_pathPer15MHisEid
                    PerformanceEventType,
                eth_pathPer15MHisParaLen
                    INTEGER,
                eth_pathPer15MHisPara
                    OCTET STRING,
                eth_pathPer15MHisMonValue
                    OCTET STRING,
                eth_pathPer15MHisDateTimeStart
                    DateAndTime,
                eth_pathPer15MHisDateTimeEnd
                    DateAndTime,
                eth_pathPer15MHisVldty
                    INTEGER,
             }

        -- 1.3.6.1.4.1.2011.2.25.3.40.50.98.20.1.1
        eth_pathPer15MHisEid OBJECT-TYPE
            SYNTAX PerformanceEventType
            MAX-ACCESS read-only
            STATUS current
            DESCRIPTION
                "perEid."
            ::= { eth_pathPer15MHisEntry 1 }

        -- 1.3.6.1.4.1.2011.2.25.3.40.50.98.20.1.2
        eth_pathPer15MHisParaLen OBJECT-TYPE
            SYNTAX INTEGER
            MAX-ACCESS read-only
            STATUS current
            DESCRIPTION
                "perParaLen."
            ::= { eth_pathPer15MHisEntry 2 }

        -- 1.3.6.1.4.1.2011.2.25.3.40.50.98.20.1.3
        eth_pathPer15MHisPara OBJECT-TYPE
            SYNTAX OCTET STRING (SIZE (0..100))
            MAX-ACCESS read-only
            STATUS current
            DESCRIPTION
                "perPara."
            ::= { eth_pathPer15MHisEntry 3 }

        -- 1.3.6.1.4.1.2011.2.25.3.40.50.98.20.1.4
        eth_pathPer15MHisMonValue OBJECT-TYPE
            SYNTAX OCTET STRING (SIZE (0..100))
            MAX-ACCESS read-only
            STATUS current
            DESCRIPTION
                "perMonValue."
            ::= { eth_pathPer15MHisEntry 4 }

        -- 1.3.6.1.4.1.2011.2.25.3.40.50.98.20.1.5
        eth_pathPer15MHisDateTimeStart OBJECT-TYPE
            SYNTAX DateAndTime
            MAX-ACCESS read-only
            STATUS current
            DESCRIPTION
                "perDateTimeStart. "
            ::= { eth_pathPer15MHisEntry 5 }

        -- 1.3.6.1.4.1.2011.2.25.3.40.50.98.20.1.6
        eth_pathPer15MHisDateTimeEnd OBJECT-TYPE
            SYNTAX DateAndTime
            MAX-ACCESS read-only
            STATUS current
            DESCRIPTION
                "perDateTimeEnd. "
            ::= { eth_pathPer15MHisEntry 6 }

        -- 1.3.6.1.4.1.2011.2.25.3.40.50.98.20.1.7
        eth_pathPer15MHisVldty OBJECT-TYPE
            SYNTAX INTEGER
            MAX-ACCESS read-only
            STATUS current
            DESCRIPTION
                "perVldty. "
            ::= { eth_pathPer15MHisEntry 7 }




-- -------------------------------------------------------------------------
-- Perfomance 24-HOUR Current Data Table (RTRV-PER-<MOD2>)
-- -------------------------------------------------------------------------
        -- 1.3.6.1.4.1.2011.2.25.3.40.50.98.30
        eth_pathPer24HCurTable OBJECT-TYPE
          SYNTAX SEQUENCE OF Eth_pathPer24HCurEntry
          MAX-ACCESS not-accessible
          STATUS current
          DESCRIPTION
              "eth_pathPer24HCur."
          ::= { eth_path 30 }

        -- 1.3.6.1.4.1.2011.2.25.3.40.50.98.30.1
        eth_pathPer24HCurEntry OBJECT-TYPE
            SYNTAX Eth_pathPer24HCurEntry
            MAX-ACCESS not-accessible
            STATUS current
            DESCRIPTION
              "eth_pathPer24HCur."
            INDEX { eth_pathPer24HCurEid, eth_pathPer24HCurPara }
            ::= { eth_pathPer24HCurTable 1 }

        Eth_pathPer24HCurEntry ::=
            SEQUENCE {
                eth_pathPer24HCurEid
                    PerformanceEventType,
                eth_pathPer24HCurMonValue
                    OCTET STRING,
                eth_pathPer24HCurVldty
                    INTEGER,
                eth_pathPer24HCurDateTime
                    DateAndTime,
                eth_pathPer24HCurParaLen
                    INTEGER,
                eth_pathPer24HCurPara
                    OCTET STRING
            }

        -- 1.3.6.1.4.1.2011.2.25.3.40.50.98.30.1.1
        eth_pathPer24HCurEid OBJECT-TYPE
            SYNTAX PerformanceEventType
            MAX-ACCESS read-only
            STATUS current
            DESCRIPTION
                "perEid."
            ::= { eth_pathPer24HCurEntry 1 }

        -- 1.3.6.1.4.1.2011.2.25.3.40.50.98.30.1.2
        eth_pathPer24HCurMonValue OBJECT-TYPE
            SYNTAX OCTET STRING (SIZE (0..100))
            MAX-ACCESS read-only
            STATUS current
            DESCRIPTION
                "perMonValue."
            ::= { eth_pathPer24HCurEntry 2 }

        -- 1.3.6.1.4.1.2011.2.25.3.40.50.98.30.1.3
        eth_pathPer24HCurVldty OBJECT-TYPE
            SYNTAX INTEGER
            MAX-ACCESS read-only
            STATUS current
            DESCRIPTION
                "perVldty. "
            ::= { eth_pathPer24HCurEntry 3 }

        -- 1.3.6.1.4.1.2011.2.25.3.40.50.98.30.1.4
        eth_pathPer24HCurDateTime OBJECT-TYPE
            SYNTAX DateAndTime
            MAX-ACCESS read-only
            STATUS current
            DESCRIPTION
                "perDateTime. "
            ::= { eth_pathPer24HCurEntry 4 }

        -- 1.3.6.1.4.1.2011.2.25.3.40.50.98.30.1.5
        eth_pathPer24HCurParaLen OBJECT-TYPE
            SYNTAX INTEGER
            MAX-ACCESS read-only
            STATUS current
            DESCRIPTION
                "perParaLen."
            ::= { eth_pathPer24HCurEntry 5 }

        -- 1.3.6.1.4.1.2011.2.25.3.40.50.98.30.1.6
        eth_pathPer24HCurPara OBJECT-TYPE
            SYNTAX OCTET STRING (SIZE (0..100))
            MAX-ACCESS read-only
            STATUS current
            DESCRIPTION
                "perPara."
            ::= { eth_pathPer24HCurEntry 6 }




-- -------------------------------------------------------------------------
-- Perfomance 24-HOUR History Data Table (RTRV-PER-<MOD2>)
-- -------------------------------------------------------------------------
        -- 1.3.6.1.4.1.2011.2.25.3.40.50.98.40
        eth_pathPer24HHisTable OBJECT-TYPE
          SYNTAX SEQUENCE OF Eth_pathPer24HHisEntry
          MAX-ACCESS not-accessible
          STATUS current
          DESCRIPTION
              "eth_pathPer24HHis."
          ::= { eth_path 40 }

        -- 1.3.6.1.4.1.2011.2.25.3.40.50.98.40.1
        eth_pathPer24HHisEntry OBJECT-TYPE
            SYNTAX Eth_pathPer24HHisEntry
            MAX-ACCESS not-accessible
            STATUS current
            DESCRIPTION
                "eth_pathPer24HHis."
            INDEX {eth_pathPer24HHisEid, eth_pathPer24HHisParaLen, eth_pathPer24HHisPara, eth_pathPer24HHisDateTimeStart, eth_pathPer24HHisDateTimeEnd}
            ::= { eth_pathPer24HHisTable 1 }

        Eth_pathPer24HHisEntry ::=
            SEQUENCE {
                eth_pathPer24HHisEid
                    PerformanceEventType,
                eth_pathPer24HHisParaLen
                    INTEGER,
                eth_pathPer24HHisPara
                    OCTET STRING,
                eth_pathPer24HHisMonValue
                    OCTET STRING,
                eth_pathPer24HHisDateTimeStart
                    DateAndTime,
                eth_pathPer24HHisDateTimeEnd
                    DateAndTime,
                eth_pathPer24HHisVldty
                    INTEGER,
             }

        -- 1.3.6.1.4.1.2011.2.25.3.40.50.98.40.1.1
        eth_pathPer24HHisEid OBJECT-TYPE
            SYNTAX PerformanceEventType
            MAX-ACCESS read-only
            STATUS current
            DESCRIPTION
                "perEid."
            ::= { eth_pathPer24HHisEntry 1 }

        -- 1.3.6.1.4.1.2011.2.25.3.40.50.98.40.1.2
        eth_pathPer24HHisParaLen OBJECT-TYPE
            SYNTAX INTEGER
            MAX-ACCESS read-only
            STATUS current
            DESCRIPTION
                "perParaLen."
            ::= { eth_pathPer24HHisEntry 2 }

        -- 1.3.6.1.4.1.2011.2.25.3.40.50.98.40.1.3
        eth_pathPer24HHisPara OBJECT-TYPE
            SYNTAX OCTET STRING (SIZE (0..100))
            MAX-ACCESS read-only
            STATUS current
            DESCRIPTION
                "perPara."
            ::= { eth_pathPer24HHisEntry 3 }

        -- 1.3.6.1.4.1.2011.2.25.3.40.50.98.40.1.4
        eth_pathPer24HHisMonValue OBJECT-TYPE
            SYNTAX OCTET STRING (SIZE (0..100))
            MAX-ACCESS read-only
            STATUS current
            DESCRIPTION
                "perMonValue."
            ::= { eth_pathPer24HHisEntry 4 }

        -- 1.3.6.1.4.1.2011.2.25.3.40.50.98.40.1.5
        eth_pathPer24HHisDateTimeStart OBJECT-TYPE
            SYNTAX DateAndTime
            MAX-ACCESS read-only
            STATUS current
            DESCRIPTION
                "perDateTimeStart. "
            ::= { eth_pathPer24HHisEntry 5 }

        -- 1.3.6.1.4.1.2011.2.25.3.40.50.98.40.1.6
        eth_pathPer24HHisDateTimeEnd OBJECT-TYPE
            SYNTAX DateAndTime
            MAX-ACCESS read-only
            STATUS current
            DESCRIPTION
                "perDateTimeEnd. "
            ::= { eth_pathPer24HHisEntry 6 }

        -- 1.3.6.1.4.1.2011.2.25.3.40.50.98.40.1.7
        eth_pathPer24HHisVldty OBJECT-TYPE
            SYNTAX INTEGER
            MAX-ACCESS read-only
            STATUS current
            DESCRIPTION
                "perVldty. "
            ::= { eth_pathPer24HHisEntry 7 }


-- Alarm data
      -- 1.3.6.1.4.1.2011.2.25.3.40.50.99
      fc_path OBJECT IDENTIFIER ::={ optixGlobalNGWDM 99 }


-- -------------------------------------------------------------------------
-- Perfomance 15-MIN Current Data Table (RTRV-PER-<MOD2>)
-- -------------------------------------------------------------------------
        -- 1.3.6.1.4.1.2011.2.25.3.40.50.99.10
        fc_pathPer15MCurTable OBJECT-TYPE
          SYNTAX SEQUENCE OF Fc_pathPer15MCurEntry
          MAX-ACCESS not-accessible
          STATUS current
          DESCRIPTION
              "fc_pathPer15MCur."
          ::= { fc_path 10 }

        -- 1.3.6.1.4.1.2011.2.25.3.40.50.99.10.1
        fc_pathPer15MCurEntry OBJECT-TYPE
            SYNTAX Fc_pathPer15MCurEntry
            MAX-ACCESS not-accessible
            STATUS current
            DESCRIPTION
              "fc_pathPer15MCur."
            INDEX { fc_pathPer15MCurEid, fc_pathPer15MCurPara }
            ::= { fc_pathPer15MCurTable 1 }

        Fc_pathPer15MCurEntry ::=
            SEQUENCE {
                fc_pathPer15MCurEid
                    PerformanceEventType,
                fc_pathPer15MCurMonValue
                    OCTET STRING,
                fc_pathPer15MCurVldty
                    INTEGER,
                fc_pathPer15MCurDateTime
                    DateAndTime,
                fc_pathPer15MCurParaLen
                    INTEGER,
                fc_pathPer15MCurPara
                    OCTET STRING
            }

        -- 1.3.6.1.4.1.2011.2.25.3.40.50.99.10.1.1
        fc_pathPer15MCurEid OBJECT-TYPE
            SYNTAX PerformanceEventType
            MAX-ACCESS read-only
            STATUS current
            DESCRIPTION
                "perEid."
            ::= { fc_pathPer15MCurEntry 1 }

        -- 1.3.6.1.4.1.2011.2.25.3.40.50.99.10.1.2
        fc_pathPer15MCurMonValue OBJECT-TYPE
            SYNTAX OCTET STRING (SIZE (0..100))
            MAX-ACCESS read-only
            STATUS current
            DESCRIPTION
                "perMonValue."
            ::= { fc_pathPer15MCurEntry 2 }

        -- 1.3.6.1.4.1.2011.2.25.3.40.50.99.10.1.3
        fc_pathPer15MCurVldty OBJECT-TYPE
            SYNTAX INTEGER
            MAX-ACCESS read-only
            STATUS current
            DESCRIPTION
                "perVldty. "
            ::= { fc_pathPer15MCurEntry 3 }

        -- 1.3.6.1.4.1.2011.2.25.3.40.50.99.10.1.4
        fc_pathPer15MCurDateTime OBJECT-TYPE
            SYNTAX DateAndTime
            MAX-ACCESS read-only
            STATUS current
            DESCRIPTION
                "perDateTime. "
            ::= { fc_pathPer15MCurEntry 4 }

        -- 1.3.6.1.4.1.2011.2.25.3.40.50.99.10.1.5
        fc_pathPer15MCurParaLen OBJECT-TYPE
            SYNTAX INTEGER
            MAX-ACCESS read-only
            STATUS current
            DESCRIPTION
                "perParaLen."
            ::= { fc_pathPer15MCurEntry 5 }

        -- 1.3.6.1.4.1.2011.2.25.3.40.50.99.10.1.6
        fc_pathPer15MCurPara OBJECT-TYPE
            SYNTAX OCTET STRING (SIZE (0..100))
            MAX-ACCESS read-only
            STATUS current
            DESCRIPTION
                "perPara."
            ::= { fc_pathPer15MCurEntry 6 }




-- -------------------------------------------------------------------------
-- Perfomance 15-MIN History Data Table (RTRV-PER-<MOD2>)
-- -------------------------------------------------------------------------
        -- 1.3.6.1.4.1.2011.2.25.3.40.50.99.20
        fc_pathPer15MHisTable OBJECT-TYPE
          SYNTAX SEQUENCE OF Fc_pathPer15MHisEntry
          MAX-ACCESS not-accessible
          STATUS current
          DESCRIPTION
              "fc_pathPer15MHis."
          ::= { fc_path 20 }

        -- 1.3.6.1.4.1.2011.2.25.3.40.50.99.20.1
        fc_pathPer15MHisEntry OBJECT-TYPE
            SYNTAX Fc_pathPer15MHisEntry
            MAX-ACCESS not-accessible
            STATUS current
            DESCRIPTION
                "fc_pathPer15MHis."
            INDEX {fc_pathPer15MHisEid, fc_pathPer15MHisParaLen, fc_pathPer15MHisPara, fc_pathPer15MHisDateTimeStart, fc_pathPer15MHisDateTimeEnd}
            ::= { fc_pathPer15MHisTable 1 }

        Fc_pathPer15MHisEntry ::=
            SEQUENCE {
                fc_pathPer15MHisEid
                    PerformanceEventType,
                fc_pathPer15MHisParaLen
                    INTEGER,
                fc_pathPer15MHisPara
                    OCTET STRING,
                fc_pathPer15MHisMonValue
                    OCTET STRING,
                fc_pathPer15MHisDateTimeStart
                    DateAndTime,
                fc_pathPer15MHisDateTimeEnd
                    DateAndTime,
                fc_pathPer15MHisVldty
                    INTEGER,
             }

        -- 1.3.6.1.4.1.2011.2.25.3.40.50.99.20.1.1
        fc_pathPer15MHisEid OBJECT-TYPE
            SYNTAX PerformanceEventType
            MAX-ACCESS read-only
            STATUS current
            DESCRIPTION
                "perEid."
            ::= { fc_pathPer15MHisEntry 1 }

        -- 1.3.6.1.4.1.2011.2.25.3.40.50.99.20.1.2
        fc_pathPer15MHisParaLen OBJECT-TYPE
            SYNTAX INTEGER
            MAX-ACCESS read-only
            STATUS current
            DESCRIPTION
                "perParaLen."
            ::= { fc_pathPer15MHisEntry 2 }

        -- 1.3.6.1.4.1.2011.2.25.3.40.50.99.20.1.3
        fc_pathPer15MHisPara OBJECT-TYPE
            SYNTAX OCTET STRING (SIZE (0..100))
            MAX-ACCESS read-only
            STATUS current
            DESCRIPTION
                "perPara."
            ::= { fc_pathPer15MHisEntry 3 }

        -- 1.3.6.1.4.1.2011.2.25.3.40.50.99.20.1.4
        fc_pathPer15MHisMonValue OBJECT-TYPE
            SYNTAX OCTET STRING (SIZE (0..100))
            MAX-ACCESS read-only
            STATUS current
            DESCRIPTION
                "perMonValue."
            ::= { fc_pathPer15MHisEntry 4 }

        -- 1.3.6.1.4.1.2011.2.25.3.40.50.99.20.1.5
        fc_pathPer15MHisDateTimeStart OBJECT-TYPE
            SYNTAX DateAndTime
            MAX-ACCESS read-only
            STATUS current
            DESCRIPTION
                "perDateTimeStart. "
            ::= { fc_pathPer15MHisEntry 5 }

        -- 1.3.6.1.4.1.2011.2.25.3.40.50.99.20.1.6
        fc_pathPer15MHisDateTimeEnd OBJECT-TYPE
            SYNTAX DateAndTime
            MAX-ACCESS read-only
            STATUS current
            DESCRIPTION
                "perDateTimeEnd. "
            ::= { fc_pathPer15MHisEntry 6 }

        -- 1.3.6.1.4.1.2011.2.25.3.40.50.99.20.1.7
        fc_pathPer15MHisVldty OBJECT-TYPE
            SYNTAX INTEGER
            MAX-ACCESS read-only
            STATUS current
            DESCRIPTION
                "perVldty. "
            ::= { fc_pathPer15MHisEntry 7 }




-- -------------------------------------------------------------------------
-- Perfomance 24-HOUR Current Data Table (RTRV-PER-<MOD2>)
-- -------------------------------------------------------------------------
        -- 1.3.6.1.4.1.2011.2.25.3.40.50.99.30
        fc_pathPer24HCurTable OBJECT-TYPE
          SYNTAX SEQUENCE OF Fc_pathPer24HCurEntry
          MAX-ACCESS not-accessible
          STATUS current
          DESCRIPTION
              "fc_pathPer24HCur."
          ::= { fc_path 30 }

        -- 1.3.6.1.4.1.2011.2.25.3.40.50.99.30.1
        fc_pathPer24HCurEntry OBJECT-TYPE
            SYNTAX Fc_pathPer24HCurEntry
            MAX-ACCESS not-accessible
            STATUS current
            DESCRIPTION
              "fc_pathPer24HCur."
            INDEX { fc_pathPer24HCurEid, fc_pathPer24HCurPara }
            ::= { fc_pathPer24HCurTable 1 }

        Fc_pathPer24HCurEntry ::=
            SEQUENCE {
                fc_pathPer24HCurEid
                    PerformanceEventType,
                fc_pathPer24HCurMonValue
                    OCTET STRING,
                fc_pathPer24HCurVldty
                    INTEGER,
                fc_pathPer24HCurDateTime
                    DateAndTime,
                fc_pathPer24HCurParaLen
                    INTEGER,
                fc_pathPer24HCurPara
                    OCTET STRING
            }

        -- 1.3.6.1.4.1.2011.2.25.3.40.50.99.30.1.1
        fc_pathPer24HCurEid OBJECT-TYPE
            SYNTAX PerformanceEventType
            MAX-ACCESS read-only
            STATUS current
            DESCRIPTION
                "perEid."
            ::= { fc_pathPer24HCurEntry 1 }

        -- 1.3.6.1.4.1.2011.2.25.3.40.50.99.30.1.2
        fc_pathPer24HCurMonValue OBJECT-TYPE
            SYNTAX OCTET STRING (SIZE (0..100))
            MAX-ACCESS read-only
            STATUS current
            DESCRIPTION
                "perMonValue."
            ::= { fc_pathPer24HCurEntry 2 }

        -- 1.3.6.1.4.1.2011.2.25.3.40.50.99.30.1.3
        fc_pathPer24HCurVldty OBJECT-TYPE
            SYNTAX INTEGER
            MAX-ACCESS read-only
            STATUS current
            DESCRIPTION
                "perVldty. "
            ::= { fc_pathPer24HCurEntry 3 }

        -- 1.3.6.1.4.1.2011.2.25.3.40.50.99.30.1.4
        fc_pathPer24HCurDateTime OBJECT-TYPE
            SYNTAX DateAndTime
            MAX-ACCESS read-only
            STATUS current
            DESCRIPTION
                "perDateTime. "
            ::= { fc_pathPer24HCurEntry 4 }

        -- 1.3.6.1.4.1.2011.2.25.3.40.50.99.30.1.5
        fc_pathPer24HCurParaLen OBJECT-TYPE
            SYNTAX INTEGER
            MAX-ACCESS read-only
            STATUS current
            DESCRIPTION
                "perParaLen."
            ::= { fc_pathPer24HCurEntry 5 }

        -- 1.3.6.1.4.1.2011.2.25.3.40.50.99.30.1.6
        fc_pathPer24HCurPara OBJECT-TYPE
            SYNTAX OCTET STRING (SIZE (0..100))
            MAX-ACCESS read-only
            STATUS current
            DESCRIPTION
                "perPara."
            ::= { fc_pathPer24HCurEntry 6 }




-- -------------------------------------------------------------------------
-- Perfomance 24-HOUR History Data Table (RTRV-PER-<MOD2>)
-- -------------------------------------------------------------------------
        -- 1.3.6.1.4.1.2011.2.25.3.40.50.99.40
        fc_pathPer24HHisTable OBJECT-TYPE
          SYNTAX SEQUENCE OF Fc_pathPer24HHisEntry
          MAX-ACCESS not-accessible
          STATUS current
          DESCRIPTION
              "fc_pathPer24HHis."
          ::= { fc_path 40 }

        -- 1.3.6.1.4.1.2011.2.25.3.40.50.99.40.1
        fc_pathPer24HHisEntry OBJECT-TYPE
            SYNTAX Fc_pathPer24HHisEntry
            MAX-ACCESS not-accessible
            STATUS current
            DESCRIPTION
                "fc_pathPer24HHis."
            INDEX {fc_pathPer24HHisEid, fc_pathPer24HHisParaLen, fc_pathPer24HHisPara, fc_pathPer24HHisDateTimeStart, fc_pathPer24HHisDateTimeEnd}
            ::= { fc_pathPer24HHisTable 1 }

        Fc_pathPer24HHisEntry ::=
            SEQUENCE {
                fc_pathPer24HHisEid
                    PerformanceEventType,
                fc_pathPer24HHisParaLen
                    INTEGER,
                fc_pathPer24HHisPara
                    OCTET STRING,
                fc_pathPer24HHisMonValue
                    OCTET STRING,
                fc_pathPer24HHisDateTimeStart
                    DateAndTime,
                fc_pathPer24HHisDateTimeEnd
                    DateAndTime,
                fc_pathPer24HHisVldty
                    INTEGER,
             }

        -- 1.3.6.1.4.1.2011.2.25.3.40.50.99.40.1.1
        fc_pathPer24HHisEid OBJECT-TYPE
            SYNTAX PerformanceEventType
            MAX-ACCESS read-only
            STATUS current
            DESCRIPTION
                "perEid."
            ::= { fc_pathPer24HHisEntry 1 }

        -- 1.3.6.1.4.1.2011.2.25.3.40.50.99.40.1.2
        fc_pathPer24HHisParaLen OBJECT-TYPE
            SYNTAX INTEGER
            MAX-ACCESS read-only
            STATUS current
            DESCRIPTION
                "perParaLen."
            ::= { fc_pathPer24HHisEntry 2 }

        -- 1.3.6.1.4.1.2011.2.25.3.40.50.99.40.1.3
        fc_pathPer24HHisPara OBJECT-TYPE
            SYNTAX OCTET STRING (SIZE (0..100))
            MAX-ACCESS read-only
            STATUS current
            DESCRIPTION
                "perPara."
            ::= { fc_pathPer24HHisEntry 3 }

        -- 1.3.6.1.4.1.2011.2.25.3.40.50.99.40.1.4
        fc_pathPer24HHisMonValue OBJECT-TYPE
            SYNTAX OCTET STRING (SIZE (0..100))
            MAX-ACCESS read-only
            STATUS current
            DESCRIPTION
                "perMonValue."
            ::= { fc_pathPer24HHisEntry 4 }

        -- 1.3.6.1.4.1.2011.2.25.3.40.50.99.40.1.5
        fc_pathPer24HHisDateTimeStart OBJECT-TYPE
            SYNTAX DateAndTime
            MAX-ACCESS read-only
            STATUS current
            DESCRIPTION
                "perDateTimeStart. "
            ::= { fc_pathPer24HHisEntry 5 }

        -- 1.3.6.1.4.1.2011.2.25.3.40.50.99.40.1.6
        fc_pathPer24HHisDateTimeEnd OBJECT-TYPE
            SYNTAX DateAndTime
            MAX-ACCESS read-only
            STATUS current
            DESCRIPTION
                "perDateTimeEnd. "
            ::= { fc_pathPer24HHisEntry 6 }

        -- 1.3.6.1.4.1.2011.2.25.3.40.50.99.40.1.7
        fc_pathPer24HHisVldty OBJECT-TYPE
            SYNTAX INTEGER
            MAX-ACCESS read-only
            STATUS current
            DESCRIPTION
                "perVldty. "
            ::= { fc_pathPer24HHisEntry 7 }




-- Alarm data
      -- 1.3.6.1.4.1.2011.2.25.3.40.50.100
      fec OBJECT IDENTIFIER ::={ optixGlobalNGWDM 100 }


-- -------------------------------------------------------------------------
-- Perfomance 15-MIN Current Data Table (RTRV-PER-<MOD2>)
-- -------------------------------------------------------------------------
        -- 1.3.6.1.4.1.2011.2.25.3.40.50.100.10
        fecPer15MCurTable OBJECT-TYPE
          SYNTAX SEQUENCE OF FecPer15MCurEntry
          MAX-ACCESS not-accessible
          STATUS current
          DESCRIPTION
              "fecPer15MCur."
          ::= { fec 10 }

        -- 1.3.6.1.4.1.2011.2.25.3.40.50.100.10.1
        fecPer15MCurEntry OBJECT-TYPE
            SYNTAX FecPer15MCurEntry
            MAX-ACCESS not-accessible
            STATUS current
            DESCRIPTION
              "fecPer15MCur."
            INDEX { fecPer15MCurEid, fecPer15MCurPara }
            ::= { fecPer15MCurTable 1 }

        FecPer15MCurEntry ::=
            SEQUENCE {
                fecPer15MCurEid
                    PerformanceEventType,
                fecPer15MCurMonValue
                    OCTET STRING,
                fecPer15MCurVldty
                    INTEGER,
                fecPer15MCurDateTime
                    DateAndTime,
                fecPer15MCurParaLen
                    INTEGER,
                fecPer15MCurPara
                    OCTET STRING
            }

        -- 1.3.6.1.4.1.2011.2.25.3.40.50.100.10.1.1
        fecPer15MCurEid OBJECT-TYPE
            SYNTAX PerformanceEventType
            MAX-ACCESS read-only
            STATUS current
            DESCRIPTION
                "perEid."
            ::= { fecPer15MCurEntry 1 }

        -- 1.3.6.1.4.1.2011.2.25.3.40.50.100.10.1.2
        fecPer15MCurMonValue OBJECT-TYPE
            SYNTAX OCTET STRING (SIZE (0..100))
            MAX-ACCESS read-only
            STATUS current
            DESCRIPTION
                "perMonValue."
            ::= { fecPer15MCurEntry 2 }

        -- 1.3.6.1.4.1.2011.2.25.3.40.50.100.10.1.3
        fecPer15MCurVldty OBJECT-TYPE
            SYNTAX INTEGER
            MAX-ACCESS read-only
            STATUS current
            DESCRIPTION
                "perVldty. "
            ::= { fecPer15MCurEntry 3 }

        -- 1.3.6.1.4.1.2011.2.25.3.40.50.100.10.1.4
        fecPer15MCurDateTime OBJECT-TYPE
            SYNTAX DateAndTime
            MAX-ACCESS read-only
            STATUS current
            DESCRIPTION
                "perDateTime. "
            ::= { fecPer15MCurEntry 4 }

        -- 1.3.6.1.4.1.2011.2.25.3.40.50.100.10.1.5
        fecPer15MCurParaLen OBJECT-TYPE
            SYNTAX INTEGER
            MAX-ACCESS read-only
            STATUS current
            DESCRIPTION
                "perParaLen."
            ::= { fecPer15MCurEntry 5 }

        -- 1.3.6.1.4.1.2011.2.25.3.40.50.100.10.1.6
        fecPer15MCurPara OBJECT-TYPE
            SYNTAX OCTET STRING (SIZE (0..100))
            MAX-ACCESS read-only
            STATUS current
            DESCRIPTION
                "perPara."
            ::= { fecPer15MCurEntry 6 }




-- -------------------------------------------------------------------------
-- Perfomance 15-MIN History Data Table (RTRV-PER-<MOD2>)
-- -------------------------------------------------------------------------
        -- 1.3.6.1.4.1.2011.2.25.3.40.50.100.20
        fecPer15MHisTable OBJECT-TYPE
          SYNTAX SEQUENCE OF FecPer15MHisEntry
          MAX-ACCESS not-accessible
          STATUS current
          DESCRIPTION
              "fecPer15MHis."
          ::= { fec 20 }

        -- 1.3.6.1.4.1.2011.2.25.3.40.50.100.20.1
        fecPer15MHisEntry OBJECT-TYPE
            SYNTAX FecPer15MHisEntry
            MAX-ACCESS not-accessible
            STATUS current
            DESCRIPTION
                "fecPer15MHis."
            INDEX {fecPer15MHisEid, fecPer15MHisParaLen, fecPer15MHisPara, fecPer15MHisDateTimeStart, fecPer15MHisDateTimeEnd}
            ::= { fecPer15MHisTable 1 }

        FecPer15MHisEntry ::=
            SEQUENCE {
                fecPer15MHisEid
                    PerformanceEventType,
                fecPer15MHisParaLen
                    INTEGER,
                fecPer15MHisPara
                    OCTET STRING,
                fecPer15MHisMonValue
                    OCTET STRING,
                fecPer15MHisDateTimeStart
                    DateAndTime,
                fecPer15MHisDateTimeEnd
                    DateAndTime,
                fecPer15MHisVldty
                    INTEGER,
             }

        -- 1.3.6.1.4.1.2011.2.25.3.40.50.100.20.1.1
        fecPer15MHisEid OBJECT-TYPE
            SYNTAX PerformanceEventType
            MAX-ACCESS read-only
            STATUS current
            DESCRIPTION
                "perEid."
            ::= { fecPer15MHisEntry 1 }

        -- 1.3.6.1.4.1.2011.2.25.3.40.50.100.20.1.2
        fecPer15MHisParaLen OBJECT-TYPE
            SYNTAX INTEGER
            MAX-ACCESS read-only
            STATUS current
            DESCRIPTION
                "perParaLen."
            ::= { fecPer15MHisEntry 2 }

        -- 1.3.6.1.4.1.2011.2.25.3.40.50.100.20.1.3
        fecPer15MHisPara OBJECT-TYPE
            SYNTAX OCTET STRING (SIZE (0..100))
            MAX-ACCESS read-only
            STATUS current
            DESCRIPTION
                "perPara."
            ::= { fecPer15MHisEntry 3 }

        -- 1.3.6.1.4.1.2011.2.25.3.40.50.100.20.1.4
        fecPer15MHisMonValue OBJECT-TYPE
            SYNTAX OCTET STRING (SIZE (0..100))
            MAX-ACCESS read-only
            STATUS current
            DESCRIPTION
                "perMonValue."
            ::= { fecPer15MHisEntry 4 }

        -- 1.3.6.1.4.1.2011.2.25.3.40.50.100.20.1.5
        fecPer15MHisDateTimeStart OBJECT-TYPE
            SYNTAX DateAndTime
            MAX-ACCESS read-only
            STATUS current
            DESCRIPTION
                "perDateTimeStart. "
            ::= { fecPer15MHisEntry 5 }

        -- 1.3.6.1.4.1.2011.2.25.3.40.50.100.20.1.6
        fecPer15MHisDateTimeEnd OBJECT-TYPE
            SYNTAX DateAndTime
            MAX-ACCESS read-only
            STATUS current
            DESCRIPTION
                "perDateTimeEnd. "
            ::= { fecPer15MHisEntry 6 }

        -- 1.3.6.1.4.1.2011.2.25.3.40.50.100.20.1.7
        fecPer15MHisVldty OBJECT-TYPE
            SYNTAX INTEGER
            MAX-ACCESS read-only
            STATUS current
            DESCRIPTION
                "perVldty. "
            ::= { fecPer15MHisEntry 7 }




-- -------------------------------------------------------------------------
-- Perfomance 24-HOUR Current Data Table (RTRV-PER-<MOD2>)
-- -------------------------------------------------------------------------
        -- 1.3.6.1.4.1.2011.2.25.3.40.50.100.30
        fecPer24HCurTable OBJECT-TYPE
          SYNTAX SEQUENCE OF FecPer24HCurEntry
          MAX-ACCESS not-accessible
          STATUS current
          DESCRIPTION
              "fecPer24HCur."
          ::= { fec 30 }

        -- 1.3.6.1.4.1.2011.2.25.3.40.50.100.30.1
        fecPer24HCurEntry OBJECT-TYPE
            SYNTAX FecPer24HCurEntry
            MAX-ACCESS not-accessible
            STATUS current
            DESCRIPTION
              "fecPer24HCur."
            INDEX { fecPer24HCurEid, fecPer24HCurPara }
            ::= { fecPer24HCurTable 1 }

        FecPer24HCurEntry ::=
            SEQUENCE {
                fecPer24HCurEid
                    PerformanceEventType,
                fecPer24HCurMonValue
                    OCTET STRING,
                fecPer24HCurVldty
                    INTEGER,
                fecPer24HCurDateTime
                    DateAndTime,
                fecPer24HCurParaLen
                    INTEGER,
                fecPer24HCurPara
                    OCTET STRING
            }

        -- 1.3.6.1.4.1.2011.2.25.3.40.50.100.30.1.1
        fecPer24HCurEid OBJECT-TYPE
            SYNTAX PerformanceEventType
            MAX-ACCESS read-only
            STATUS current
            DESCRIPTION
                "perEid."
            ::= { fecPer24HCurEntry 1 }

        -- 1.3.6.1.4.1.2011.2.25.3.40.50.100.30.1.2
        fecPer24HCurMonValue OBJECT-TYPE
            SYNTAX OCTET STRING (SIZE (0..100))
            MAX-ACCESS read-only
            STATUS current
            DESCRIPTION
                "perMonValue."
            ::= { fecPer24HCurEntry 2 }

        -- 1.3.6.1.4.1.2011.2.25.3.40.50.100.30.1.3
        fecPer24HCurVldty OBJECT-TYPE
            SYNTAX INTEGER
            MAX-ACCESS read-only
            STATUS current
            DESCRIPTION
                "perVldty. "
            ::= { fecPer24HCurEntry 3 }

        -- 1.3.6.1.4.1.2011.2.25.3.40.50.100.30.1.4
        fecPer24HCurDateTime OBJECT-TYPE
            SYNTAX DateAndTime
            MAX-ACCESS read-only
            STATUS current
            DESCRIPTION
                "perDateTime. "
            ::= { fecPer24HCurEntry 4 }

        -- 1.3.6.1.4.1.2011.2.25.3.40.50.100.30.1.5
        fecPer24HCurParaLen OBJECT-TYPE
            SYNTAX INTEGER
            MAX-ACCESS read-only
            STATUS current
            DESCRIPTION
                "perParaLen."
            ::= { fecPer24HCurEntry 5 }

        -- 1.3.6.1.4.1.2011.2.25.3.40.50.100.30.1.6
        fecPer24HCurPara OBJECT-TYPE
            SYNTAX OCTET STRING (SIZE (0..100))
            MAX-ACCESS read-only
            STATUS current
            DESCRIPTION
                "perPara."
            ::= { fecPer24HCurEntry 6 }




-- -------------------------------------------------------------------------
-- Perfomance 24-HOUR History Data Table (RTRV-PER-<MOD2>)
-- -------------------------------------------------------------------------
        -- 1.3.6.1.4.1.2011.2.25.3.40.50.100.40
        fecPer24HHisTable OBJECT-TYPE
          SYNTAX SEQUENCE OF FecPer24HHisEntry
          MAX-ACCESS not-accessible
          STATUS current
          DESCRIPTION
              "fecPer24HHis."
          ::= { fec 40 }

        -- 1.3.6.1.4.1.2011.2.25.3.40.50.100.40.1
        fecPer24HHisEntry OBJECT-TYPE
            SYNTAX FecPer24HHisEntry
            MAX-ACCESS not-accessible
            STATUS current
            DESCRIPTION
                "fecPer24HHis."
            INDEX {fecPer24HHisEid, fecPer24HHisParaLen, fecPer24HHisPara, fecPer24HHisDateTimeStart, fecPer24HHisDateTimeEnd}
            ::= { fecPer24HHisTable 1 }

        FecPer24HHisEntry ::=
            SEQUENCE {
                fecPer24HHisEid
                    PerformanceEventType,
                fecPer24HHisParaLen
                    INTEGER,
                fecPer24HHisPara
                    OCTET STRING,
                fecPer24HHisMonValue
                    OCTET STRING,
                fecPer24HHisDateTimeStart
                    DateAndTime,
                fecPer24HHisDateTimeEnd
                    DateAndTime,
                fecPer24HHisVldty
                    INTEGER,
             }

        -- 1.3.6.1.4.1.2011.2.25.3.40.50.100.40.1.1
        fecPer24HHisEid OBJECT-TYPE
            SYNTAX PerformanceEventType
            MAX-ACCESS read-only
            STATUS current
            DESCRIPTION
                "perEid."
            ::= { fecPer24HHisEntry 1 }

        -- 1.3.6.1.4.1.2011.2.25.3.40.50.100.40.1.2
        fecPer24HHisParaLen OBJECT-TYPE
            SYNTAX INTEGER
            MAX-ACCESS read-only
            STATUS current
            DESCRIPTION
                "perParaLen."
            ::= { fecPer24HHisEntry 2 }

        -- 1.3.6.1.4.1.2011.2.25.3.40.50.100.40.1.3
        fecPer24HHisPara OBJECT-TYPE
            SYNTAX OCTET STRING (SIZE (0..100))
            MAX-ACCESS read-only
            STATUS current
            DESCRIPTION
                "perPara."
            ::= { fecPer24HHisEntry 3 }

        -- 1.3.6.1.4.1.2011.2.25.3.40.50.100.40.1.4
        fecPer24HHisMonValue OBJECT-TYPE
            SYNTAX OCTET STRING (SIZE (0..100))
            MAX-ACCESS read-only
            STATUS current
            DESCRIPTION
                "perMonValue."
            ::= { fecPer24HHisEntry 4 }

        -- 1.3.6.1.4.1.2011.2.25.3.40.50.100.40.1.5
        fecPer24HHisDateTimeStart OBJECT-TYPE
            SYNTAX DateAndTime
            MAX-ACCESS read-only
            STATUS current
            DESCRIPTION
                "perDateTimeStart. "
            ::= { fecPer24HHisEntry 5 }

        -- 1.3.6.1.4.1.2011.2.25.3.40.50.100.40.1.6
        fecPer24HHisDateTimeEnd OBJECT-TYPE
            SYNTAX DateAndTime
            MAX-ACCESS read-only
            STATUS current
            DESCRIPTION
                "perDateTimeEnd. "
            ::= { fecPer24HHisEntry 6 }

        -- 1.3.6.1.4.1.2011.2.25.3.40.50.100.40.1.7
        fecPer24HHisVldty OBJECT-TYPE
            SYNTAX INTEGER
            MAX-ACCESS read-only
            STATUS current
            DESCRIPTION
                "perVldty. "
            ::= { fecPer24HHisEntry 7 }




-- Alarm data
      -- 1.3.6.1.4.1.2011.2.25.3.40.50.101
      new_port OBJECT IDENTIFIER ::={ optixGlobalNGWDM 101 }


-- -------------------------------------------------------------------------
-- Perfomance 15-MIN Current Data Table (RTRV-PER-<MOD2>)
-- -------------------------------------------------------------------------
        -- 1.3.6.1.4.1.2011.2.25.3.40.50.101.10
        new_portPer15MCurTable OBJECT-TYPE
          SYNTAX SEQUENCE OF New_portPer15MCurEntry
          MAX-ACCESS not-accessible
          STATUS current
          DESCRIPTION
              "new_portPer15MCur."
          ::= { new_port 10 }

        -- 1.3.6.1.4.1.2011.2.25.3.40.50.101.10.1
        new_portPer15MCurEntry OBJECT-TYPE
            SYNTAX New_portPer15MCurEntry
            MAX-ACCESS not-accessible
            STATUS current
            DESCRIPTION
              "new_portPer15MCur."
            INDEX { new_portPer15MCurEid, new_portPer15MCurPara }
            ::= { new_portPer15MCurTable 1 }

        New_portPer15MCurEntry ::=
            SEQUENCE {
                new_portPer15MCurEid
                    PerformanceEventType,
                new_portPer15MCurMonValue
                    OCTET STRING,
                new_portPer15MCurVldty
                    INTEGER,
                new_portPer15MCurDateTime
                    DateAndTime,
                new_portPer15MCurParaLen
                    INTEGER,
                new_portPer15MCurPara
                    OCTET STRING
            }

        -- 1.3.6.1.4.1.2011.2.25.3.40.50.101.10.1.1
        new_portPer15MCurEid OBJECT-TYPE
            SYNTAX PerformanceEventType
            MAX-ACCESS read-only
            STATUS current
            DESCRIPTION
                "perEid."
            ::= { new_portPer15MCurEntry 1 }

        -- 1.3.6.1.4.1.2011.2.25.3.40.50.101.10.1.2
        new_portPer15MCurMonValue OBJECT-TYPE
            SYNTAX OCTET STRING (SIZE (0..100))
            MAX-ACCESS read-only
            STATUS current
            DESCRIPTION
                "perMonValue."
            ::= { new_portPer15MCurEntry 2 }

        -- 1.3.6.1.4.1.2011.2.25.3.40.50.101.10.1.3
        new_portPer15MCurVldty OBJECT-TYPE
            SYNTAX INTEGER
            MAX-ACCESS read-only
            STATUS current
            DESCRIPTION
                "perVldty. "
            ::= { new_portPer15MCurEntry 3 }

        -- 1.3.6.1.4.1.2011.2.25.3.40.50.101.10.1.4
        new_portPer15MCurDateTime OBJECT-TYPE
            SYNTAX DateAndTime
            MAX-ACCESS read-only
            STATUS current
            DESCRIPTION
                "perDateTime. "
            ::= { new_portPer15MCurEntry 4 }

        -- 1.3.6.1.4.1.2011.2.25.3.40.50.101.10.1.5
        new_portPer15MCurParaLen OBJECT-TYPE
            SYNTAX INTEGER
            MAX-ACCESS read-only
            STATUS current
            DESCRIPTION
                "perParaLen."
            ::= { new_portPer15MCurEntry 5 }

        -- 1.3.6.1.4.1.2011.2.25.3.40.50.101.10.1.6
        new_portPer15MCurPara OBJECT-TYPE
            SYNTAX OCTET STRING (SIZE (0..100))
            MAX-ACCESS read-only
            STATUS current
            DESCRIPTION
                "perPara."
            ::= { new_portPer15MCurEntry 6 }




-- -------------------------------------------------------------------------
-- Perfomance 15-MIN History Data Table (RTRV-PER-<MOD2>)
-- -------------------------------------------------------------------------
        -- 1.3.6.1.4.1.2011.2.25.3.40.50.101.20
        new_portPer15MHisTable OBJECT-TYPE
          SYNTAX SEQUENCE OF New_portPer15MHisEntry
          MAX-ACCESS not-accessible
          STATUS current
          DESCRIPTION
              "new_portPer15MHis."
          ::= { new_port 20 }

        -- 1.3.6.1.4.1.2011.2.25.3.40.50.101.20.1
        new_portPer15MHisEntry OBJECT-TYPE
            SYNTAX New_portPer15MHisEntry
            MAX-ACCESS not-accessible
            STATUS current
            DESCRIPTION
                "new_portPer15MHis."
            INDEX {new_portPer15MHisEid, new_portPer15MHisParaLen, new_portPer15MHisPara, new_portPer15MHisDateTimeStart, new_portPer15MHisDateTimeEnd}
            ::= { new_portPer15MHisTable 1 }

        New_portPer15MHisEntry ::=
            SEQUENCE {
                new_portPer15MHisEid
                    PerformanceEventType,
                new_portPer15MHisParaLen
                    INTEGER,
                new_portPer15MHisPara
                    OCTET STRING,
                new_portPer15MHisMonValue
                    OCTET STRING,
                new_portPer15MHisDateTimeStart
                    DateAndTime,
                new_portPer15MHisDateTimeEnd
                    DateAndTime,
                new_portPer15MHisVldty
                    INTEGER,
             }

        -- 1.3.6.1.4.1.2011.2.25.3.40.50.101.20.1.1
        new_portPer15MHisEid OBJECT-TYPE
            SYNTAX PerformanceEventType
            MAX-ACCESS read-only
            STATUS current
            DESCRIPTION
                "perEid."
            ::= { new_portPer15MHisEntry 1 }

        -- 1.3.6.1.4.1.2011.2.25.3.40.50.101.20.1.2
        new_portPer15MHisParaLen OBJECT-TYPE
            SYNTAX INTEGER
            MAX-ACCESS read-only
            STATUS current
            DESCRIPTION
                "perParaLen."
            ::= { new_portPer15MHisEntry 2 }

        -- 1.3.6.1.4.1.2011.2.25.3.40.50.101.20.1.3
        new_portPer15MHisPara OBJECT-TYPE
            SYNTAX OCTET STRING (SIZE (0..100))
            MAX-ACCESS read-only
            STATUS current
            DESCRIPTION
                "perPara."
            ::= { new_portPer15MHisEntry 3 }

        -- 1.3.6.1.4.1.2011.2.25.3.40.50.101.20.1.4
        new_portPer15MHisMonValue OBJECT-TYPE
            SYNTAX OCTET STRING (SIZE (0..100))
            MAX-ACCESS read-only
            STATUS current
            DESCRIPTION
                "perMonValue."
            ::= { new_portPer15MHisEntry 4 }

        -- 1.3.6.1.4.1.2011.2.25.3.40.50.101.20.1.5
        new_portPer15MHisDateTimeStart OBJECT-TYPE
            SYNTAX DateAndTime
            MAX-ACCESS read-only
            STATUS current
            DESCRIPTION
                "perDateTimeStart. "
            ::= { new_portPer15MHisEntry 5 }

        -- 1.3.6.1.4.1.2011.2.25.3.40.50.101.20.1.6
        new_portPer15MHisDateTimeEnd OBJECT-TYPE
            SYNTAX DateAndTime
            MAX-ACCESS read-only
            STATUS current
            DESCRIPTION
                "perDateTimeEnd. "
            ::= { new_portPer15MHisEntry 6 }

        -- 1.3.6.1.4.1.2011.2.25.3.40.50.101.20.1.7
        new_portPer15MHisVldty OBJECT-TYPE
            SYNTAX INTEGER
            MAX-ACCESS read-only
            STATUS current
            DESCRIPTION
                "perVldty. "
            ::= { new_portPer15MHisEntry 7 }




-- -------------------------------------------------------------------------
-- Perfomance 24-HOUR Current Data Table (RTRV-PER-<MOD2>)
-- -------------------------------------------------------------------------
        -- 1.3.6.1.4.1.2011.2.25.3.40.50.101.30
        new_portPer24HCurTable OBJECT-TYPE
          SYNTAX SEQUENCE OF New_portPer24HCurEntry
          MAX-ACCESS not-accessible
          STATUS current
          DESCRIPTION
              "new_portPer24HCur."
          ::= { new_port 30 }

        -- 1.3.6.1.4.1.2011.2.25.3.40.50.101.30.1
        new_portPer24HCurEntry OBJECT-TYPE
            SYNTAX New_portPer24HCurEntry
            MAX-ACCESS not-accessible
            STATUS current
            DESCRIPTION
              "new_portPer24HCur."
            INDEX { new_portPer24HCurEid, new_portPer24HCurPara }
            ::= { new_portPer24HCurTable 1 }

        New_portPer24HCurEntry ::=
            SEQUENCE {
                new_portPer24HCurEid
                    PerformanceEventType,
                new_portPer24HCurMonValue
                    OCTET STRING,
                new_portPer24HCurVldty
                    INTEGER,
                new_portPer24HCurDateTime
                    DateAndTime,
                new_portPer24HCurParaLen
                    INTEGER,
                new_portPer24HCurPara
                    OCTET STRING
            }

        -- 1.3.6.1.4.1.2011.2.25.3.40.50.101.30.1.1
        new_portPer24HCurEid OBJECT-TYPE
            SYNTAX PerformanceEventType
            MAX-ACCESS read-only
            STATUS current
            DESCRIPTION
                "perEid."
            ::= { new_portPer24HCurEntry 1 }

        -- 1.3.6.1.4.1.2011.2.25.3.40.50.101.30.1.2
        new_portPer24HCurMonValue OBJECT-TYPE
            SYNTAX OCTET STRING (SIZE (0..100))
            MAX-ACCESS read-only
            STATUS current
            DESCRIPTION
                "perMonValue."
            ::= { new_portPer24HCurEntry 2 }

        -- 1.3.6.1.4.1.2011.2.25.3.40.50.101.30.1.3
        new_portPer24HCurVldty OBJECT-TYPE
            SYNTAX INTEGER
            MAX-ACCESS read-only
            STATUS current
            DESCRIPTION
                "perVldty. "
            ::= { new_portPer24HCurEntry 3 }

        -- 1.3.6.1.4.1.2011.2.25.3.40.50.101.30.1.4
        new_portPer24HCurDateTime OBJECT-TYPE
            SYNTAX DateAndTime
            MAX-ACCESS read-only
            STATUS current
            DESCRIPTION
                "perDateTime. "
            ::= { new_portPer24HCurEntry 4 }

        -- 1.3.6.1.4.1.2011.2.25.3.40.50.101.30.1.5
        new_portPer24HCurParaLen OBJECT-TYPE
            SYNTAX INTEGER
            MAX-ACCESS read-only
            STATUS current
            DESCRIPTION
                "perParaLen."
            ::= { new_portPer24HCurEntry 5 }

        -- 1.3.6.1.4.1.2011.2.25.3.40.50.101.30.1.6
        new_portPer24HCurPara OBJECT-TYPE
            SYNTAX OCTET STRING (SIZE (0..100))
            MAX-ACCESS read-only
            STATUS current
            DESCRIPTION
                "perPara."
            ::= { new_portPer24HCurEntry 6 }




-- -------------------------------------------------------------------------
-- Perfomance 24-HOUR History Data Table (RTRV-PER-<MOD2>)
-- -------------------------------------------------------------------------
        -- 1.3.6.1.4.1.2011.2.25.3.40.50.101.40
        new_portPer24HHisTable OBJECT-TYPE
          SYNTAX SEQUENCE OF New_portPer24HHisEntry
          MAX-ACCESS not-accessible
          STATUS current
          DESCRIPTION
              "new_portPer24HHis."
          ::= { new_port 40 }

        -- 1.3.6.1.4.1.2011.2.25.3.40.50.101.40.1
        new_portPer24HHisEntry OBJECT-TYPE
            SYNTAX New_portPer24HHisEntry
            MAX-ACCESS not-accessible
            STATUS current
            DESCRIPTION
                "new_portPer24HHis."
            INDEX {new_portPer24HHisEid, new_portPer24HHisParaLen, new_portPer24HHisPara, new_portPer24HHisDateTimeStart, new_portPer24HHisDateTimeEnd}
            ::= { new_portPer24HHisTable 1 }

        New_portPer24HHisEntry ::=
            SEQUENCE {
                new_portPer24HHisEid
                    PerformanceEventType,
                new_portPer24HHisParaLen
                    INTEGER,
                new_portPer24HHisPara
                    OCTET STRING,
                new_portPer24HHisMonValue
                    OCTET STRING,
                new_portPer24HHisDateTimeStart
                    DateAndTime,
                new_portPer24HHisDateTimeEnd
                    DateAndTime,
                new_portPer24HHisVldty
                    INTEGER,
             }

        -- 1.3.6.1.4.1.2011.2.25.3.40.50.101.40.1.1
        new_portPer24HHisEid OBJECT-TYPE
            SYNTAX PerformanceEventType
            MAX-ACCESS read-only
            STATUS current
            DESCRIPTION
                "perEid."
            ::= { new_portPer24HHisEntry 1 }

        -- 1.3.6.1.4.1.2011.2.25.3.40.50.101.40.1.2
        new_portPer24HHisParaLen OBJECT-TYPE
            SYNTAX INTEGER
            MAX-ACCESS read-only
            STATUS current
            DESCRIPTION
                "perParaLen."
            ::= { new_portPer24HHisEntry 2 }

        -- 1.3.6.1.4.1.2011.2.25.3.40.50.101.40.1.3
        new_portPer24HHisPara OBJECT-TYPE
            SYNTAX OCTET STRING (SIZE (0..100))
            MAX-ACCESS read-only
            STATUS current
            DESCRIPTION
                "perPara."
            ::= { new_portPer24HHisEntry 3 }

        -- 1.3.6.1.4.1.2011.2.25.3.40.50.101.40.1.4
        new_portPer24HHisMonValue OBJECT-TYPE
            SYNTAX OCTET STRING (SIZE (0..100))
            MAX-ACCESS read-only
            STATUS current
            DESCRIPTION
                "perMonValue."
            ::= { new_portPer24HHisEntry 4 }

        -- 1.3.6.1.4.1.2011.2.25.3.40.50.101.40.1.5
        new_portPer24HHisDateTimeStart OBJECT-TYPE
            SYNTAX DateAndTime
            MAX-ACCESS read-only
            STATUS current
            DESCRIPTION
                "perDateTimeStart. "
            ::= { new_portPer24HHisEntry 5 }

        -- 1.3.6.1.4.1.2011.2.25.3.40.50.101.40.1.6
        new_portPer24HHisDateTimeEnd OBJECT-TYPE
            SYNTAX DateAndTime
            MAX-ACCESS read-only
            STATUS current
            DESCRIPTION
                "perDateTimeEnd. "
            ::= { new_portPer24HHisEntry 6 }

        -- 1.3.6.1.4.1.2011.2.25.3.40.50.101.40.1.7
        new_portPer24HHisVldty OBJECT-TYPE
            SYNTAX INTEGER
            MAX-ACCESS read-only
            STATUS current
            DESCRIPTION
                "perVldty. "
            ::= { new_portPer24HHisEntry 7 }




-- Alarm data
      -- 1.3.6.1.4.1.2011.2.25.3.40.50.120
      odu1_tcm1 OBJECT IDENTIFIER ::={ optixGlobalNGWDM 120 }


-- -------------------------------------------------------------------------
-- Perfomance 15-MIN Current Data Table (RTRV-PER-<MOD2>)
-- -------------------------------------------------------------------------
        -- 1.3.6.1.4.1.2011.2.25.3.40.50.120.10
        odu1_tcm1Per15MCurTable OBJECT-TYPE
          SYNTAX SEQUENCE OF Odu1_tcm1Per15MCurEntry
          MAX-ACCESS not-accessible
          STATUS current
          DESCRIPTION
              "odu1_tcm1Per15MCur."
          ::= { odu1_tcm1 10 }

        -- 1.3.6.1.4.1.2011.2.25.3.40.50.120.10.1
        odu1_tcm1Per15MCurEntry OBJECT-TYPE
            SYNTAX Odu1_tcm1Per15MCurEntry
            MAX-ACCESS not-accessible
            STATUS current
            DESCRIPTION
              "odu1_tcm1Per15MCur."
            INDEX { odu1_tcm1Per15MCurEid, odu1_tcm1Per15MCurPara }
            ::= { odu1_tcm1Per15MCurTable 1 }

        Odu1_tcm1Per15MCurEntry ::=
            SEQUENCE {
                odu1_tcm1Per15MCurEid
                    PerformanceEventType,
                odu1_tcm1Per15MCurMonValue
                    OCTET STRING,
                odu1_tcm1Per15MCurVldty
                    INTEGER,
                odu1_tcm1Per15MCurDateTime
                    DateAndTime,
                odu1_tcm1Per15MCurParaLen
                    INTEGER,
                odu1_tcm1Per15MCurPara
                    OCTET STRING
            }

        -- 1.3.6.1.4.1.2011.2.25.3.40.50.120.10.1.1
        odu1_tcm1Per15MCurEid OBJECT-TYPE
            SYNTAX PerformanceEventType
            MAX-ACCESS read-only
            STATUS current
            DESCRIPTION
                "perEid."
            ::= { odu1_tcm1Per15MCurEntry 1 }

        -- 1.3.6.1.4.1.2011.2.25.3.40.50.120.10.1.2
        odu1_tcm1Per15MCurMonValue OBJECT-TYPE
            SYNTAX OCTET STRING (SIZE (0..100))
            MAX-ACCESS read-only
            STATUS current
            DESCRIPTION
                "perMonValue."
            ::= { odu1_tcm1Per15MCurEntry 2 }

        -- 1.3.6.1.4.1.2011.2.25.3.40.50.120.10.1.3
        odu1_tcm1Per15MCurVldty OBJECT-TYPE
            SYNTAX INTEGER
            MAX-ACCESS read-only
            STATUS current
            DESCRIPTION
                "perVldty. "
            ::= { odu1_tcm1Per15MCurEntry 3 }

        -- 1.3.6.1.4.1.2011.2.25.3.40.50.120.10.1.4
        odu1_tcm1Per15MCurDateTime OBJECT-TYPE
            SYNTAX DateAndTime
            MAX-ACCESS read-only
            STATUS current
            DESCRIPTION
                "perDateTime. "
            ::= { odu1_tcm1Per15MCurEntry 4 }

        -- 1.3.6.1.4.1.2011.2.25.3.40.50.120.10.1.5
        odu1_tcm1Per15MCurParaLen OBJECT-TYPE
            SYNTAX INTEGER
            MAX-ACCESS read-only
            STATUS current
            DESCRIPTION
                "perParaLen."
            ::= { odu1_tcm1Per15MCurEntry 5 }

        -- 1.3.6.1.4.1.2011.2.25.3.40.50.120.10.1.6
        odu1_tcm1Per15MCurPara OBJECT-TYPE
            SYNTAX OCTET STRING (SIZE (0..100))
            MAX-ACCESS read-only
            STATUS current
            DESCRIPTION
                "perPara."
            ::= { odu1_tcm1Per15MCurEntry 6 }




-- -------------------------------------------------------------------------
-- Perfomance 15-MIN History Data Table (RTRV-PER-<MOD2>)
-- -------------------------------------------------------------------------
        -- 1.3.6.1.4.1.2011.2.25.3.40.50.120.20
        odu1_tcm1Per15MHisTable OBJECT-TYPE
          SYNTAX SEQUENCE OF Odu1_tcm1Per15MHisEntry
          MAX-ACCESS not-accessible
          STATUS current
          DESCRIPTION
              "odu1_tcm1Per15MHis."
          ::= { odu1_tcm1 20 }

        -- 1.3.6.1.4.1.2011.2.25.3.40.50.120.20.1
        odu1_tcm1Per15MHisEntry OBJECT-TYPE
            SYNTAX Odu1_tcm1Per15MHisEntry
            MAX-ACCESS not-accessible
            STATUS current
            DESCRIPTION
                "odu1_tcm1Per15MHis."
            INDEX {odu1_tcm1Per15MHisEid, odu1_tcm1Per15MHisParaLen, odu1_tcm1Per15MHisPara, odu1_tcm1Per15MHisDateTimeStart, odu1_tcm1Per15MHisDateTimeEnd}
            ::= { odu1_tcm1Per15MHisTable 1 }

        Odu1_tcm1Per15MHisEntry ::=
            SEQUENCE {
                odu1_tcm1Per15MHisEid
                    PerformanceEventType,
                odu1_tcm1Per15MHisParaLen
                    INTEGER,
                odu1_tcm1Per15MHisPara
                    OCTET STRING,
                odu1_tcm1Per15MHisMonValue
                    OCTET STRING,
                odu1_tcm1Per15MHisDateTimeStart
                    DateAndTime,
                odu1_tcm1Per15MHisDateTimeEnd
                    DateAndTime,
                odu1_tcm1Per15MHisVldty
                    INTEGER,
             }

        -- 1.3.6.1.4.1.2011.2.25.3.40.50.120.20.1.1
        odu1_tcm1Per15MHisEid OBJECT-TYPE
            SYNTAX PerformanceEventType
            MAX-ACCESS read-only
            STATUS current
            DESCRIPTION
                "perEid."
            ::= { odu1_tcm1Per15MHisEntry 1 }

        -- 1.3.6.1.4.1.2011.2.25.3.40.50.120.20.1.2
        odu1_tcm1Per15MHisParaLen OBJECT-TYPE
            SYNTAX INTEGER
            MAX-ACCESS read-only
            STATUS current
            DESCRIPTION
                "perParaLen."
            ::= { odu1_tcm1Per15MHisEntry 2 }

        -- 1.3.6.1.4.1.2011.2.25.3.40.50.120.20.1.3
        odu1_tcm1Per15MHisPara OBJECT-TYPE
            SYNTAX OCTET STRING (SIZE (0..100))
            MAX-ACCESS read-only
            STATUS current
            DESCRIPTION
                "perPara."
            ::= { odu1_tcm1Per15MHisEntry 3 }

        -- 1.3.6.1.4.1.2011.2.25.3.40.50.120.20.1.4
        odu1_tcm1Per15MHisMonValue OBJECT-TYPE
            SYNTAX OCTET STRING (SIZE (0..100))
            MAX-ACCESS read-only
            STATUS current
            DESCRIPTION
                "perMonValue."
            ::= { odu1_tcm1Per15MHisEntry 4 }

        -- 1.3.6.1.4.1.2011.2.25.3.40.50.120.20.1.5
        odu1_tcm1Per15MHisDateTimeStart OBJECT-TYPE
            SYNTAX DateAndTime
            MAX-ACCESS read-only
            STATUS current
            DESCRIPTION
                "perDateTimeStart. "
            ::= { odu1_tcm1Per15MHisEntry 5 }

        -- 1.3.6.1.4.1.2011.2.25.3.40.50.120.20.1.6
        odu1_tcm1Per15MHisDateTimeEnd OBJECT-TYPE
            SYNTAX DateAndTime
            MAX-ACCESS read-only
            STATUS current
            DESCRIPTION
                "perDateTimeEnd. "
            ::= { odu1_tcm1Per15MHisEntry 6 }

        -- 1.3.6.1.4.1.2011.2.25.3.40.50.120.20.1.7
        odu1_tcm1Per15MHisVldty OBJECT-TYPE
            SYNTAX INTEGER
            MAX-ACCESS read-only
            STATUS current
            DESCRIPTION
                "perVldty. "
            ::= { odu1_tcm1Per15MHisEntry 7 }




-- -------------------------------------------------------------------------
-- Perfomance 24-HOUR Current Data Table (RTRV-PER-<MOD2>)
-- -------------------------------------------------------------------------
        -- 1.3.6.1.4.1.2011.2.25.3.40.50.120.30
        odu1_tcm1Per24HCurTable OBJECT-TYPE
          SYNTAX SEQUENCE OF Odu1_tcm1Per24HCurEntry
          MAX-ACCESS not-accessible
          STATUS current
          DESCRIPTION
              "odu1_tcm1Per24HCur."
          ::= { odu1_tcm1 30 }

        -- 1.3.6.1.4.1.2011.2.25.3.40.50.120.30.1
        odu1_tcm1Per24HCurEntry OBJECT-TYPE
            SYNTAX Odu1_tcm1Per24HCurEntry
            MAX-ACCESS not-accessible
            STATUS current
            DESCRIPTION
              "odu1_tcm1Per24HCur."
            INDEX { odu1_tcm1Per24HCurEid, odu1_tcm1Per24HCurPara }
            ::= { odu1_tcm1Per24HCurTable 1 }

        Odu1_tcm1Per24HCurEntry ::=
            SEQUENCE {
                odu1_tcm1Per24HCurEid
                    PerformanceEventType,
                odu1_tcm1Per24HCurMonValue
                    OCTET STRING,
                odu1_tcm1Per24HCurVldty
                    INTEGER,
                odu1_tcm1Per24HCurDateTime
                    DateAndTime,
                odu1_tcm1Per24HCurParaLen
                    INTEGER,
                odu1_tcm1Per24HCurPara
                    OCTET STRING
            }

        -- 1.3.6.1.4.1.2011.2.25.3.40.50.120.30.1.1
        odu1_tcm1Per24HCurEid OBJECT-TYPE
            SYNTAX PerformanceEventType
            MAX-ACCESS read-only
            STATUS current
            DESCRIPTION
                "perEid."
            ::= { odu1_tcm1Per24HCurEntry 1 }

        -- 1.3.6.1.4.1.2011.2.25.3.40.50.120.30.1.2
        odu1_tcm1Per24HCurMonValue OBJECT-TYPE
            SYNTAX OCTET STRING (SIZE (0..100))
            MAX-ACCESS read-only
            STATUS current
            DESCRIPTION
                "perMonValue."
            ::= { odu1_tcm1Per24HCurEntry 2 }

        -- 1.3.6.1.4.1.2011.2.25.3.40.50.120.30.1.3
        odu1_tcm1Per24HCurVldty OBJECT-TYPE
            SYNTAX INTEGER
            MAX-ACCESS read-only
            STATUS current
            DESCRIPTION
                "perVldty. "
            ::= { odu1_tcm1Per24HCurEntry 3 }

        -- 1.3.6.1.4.1.2011.2.25.3.40.50.120.30.1.4
        odu1_tcm1Per24HCurDateTime OBJECT-TYPE
            SYNTAX DateAndTime
            MAX-ACCESS read-only
            STATUS current
            DESCRIPTION
                "perDateTime. "
            ::= { odu1_tcm1Per24HCurEntry 4 }

        -- 1.3.6.1.4.1.2011.2.25.3.40.50.120.30.1.5
        odu1_tcm1Per24HCurParaLen OBJECT-TYPE
            SYNTAX INTEGER
            MAX-ACCESS read-only
            STATUS current
            DESCRIPTION
                "perParaLen."
            ::= { odu1_tcm1Per24HCurEntry 5 }

        -- 1.3.6.1.4.1.2011.2.25.3.40.50.120.30.1.6
        odu1_tcm1Per24HCurPara OBJECT-TYPE
            SYNTAX OCTET STRING (SIZE (0..100))
            MAX-ACCESS read-only
            STATUS current
            DESCRIPTION
                "perPara."
            ::= { odu1_tcm1Per24HCurEntry 6 }




-- -------------------------------------------------------------------------
-- Perfomance 24-HOUR History Data Table (RTRV-PER-<MOD2>)
-- -------------------------------------------------------------------------
        -- 1.3.6.1.4.1.2011.2.25.3.40.50.120.40
        odu1_tcm1Per24HHisTable OBJECT-TYPE
          SYNTAX SEQUENCE OF Odu1_tcm1Per24HHisEntry
          MAX-ACCESS not-accessible
          STATUS current
          DESCRIPTION
              "odu1_tcm1Per24HHis."
          ::= { odu1_tcm1 40 }

        -- 1.3.6.1.4.1.2011.2.25.3.40.50.120.40.1
        odu1_tcm1Per24HHisEntry OBJECT-TYPE
            SYNTAX Odu1_tcm1Per24HHisEntry
            MAX-ACCESS not-accessible
            STATUS current
            DESCRIPTION
                "odu1_tcm1Per24HHis."
            INDEX {odu1_tcm1Per24HHisEid, odu1_tcm1Per24HHisParaLen, odu1_tcm1Per24HHisPara, odu1_tcm1Per24HHisDateTimeStart, odu1_tcm1Per24HHisDateTimeEnd}
            ::= { odu1_tcm1Per24HHisTable 1 }

        Odu1_tcm1Per24HHisEntry ::=
            SEQUENCE {
                odu1_tcm1Per24HHisEid
                    PerformanceEventType,
                odu1_tcm1Per24HHisParaLen
                    INTEGER,
                odu1_tcm1Per24HHisPara
                    OCTET STRING,
                odu1_tcm1Per24HHisMonValue
                    OCTET STRING,
                odu1_tcm1Per24HHisDateTimeStart
                    DateAndTime,
                odu1_tcm1Per24HHisDateTimeEnd
                    DateAndTime,
                odu1_tcm1Per24HHisVldty
                    INTEGER,
             }

        -- 1.3.6.1.4.1.2011.2.25.3.40.50.120.40.1.1
        odu1_tcm1Per24HHisEid OBJECT-TYPE
            SYNTAX PerformanceEventType
            MAX-ACCESS read-only
            STATUS current
            DESCRIPTION
                "perEid."
            ::= { odu1_tcm1Per24HHisEntry 1 }

        -- 1.3.6.1.4.1.2011.2.25.3.40.50.120.40.1.2
        odu1_tcm1Per24HHisParaLen OBJECT-TYPE
            SYNTAX INTEGER
            MAX-ACCESS read-only
            STATUS current
            DESCRIPTION
                "perParaLen."
            ::= { odu1_tcm1Per24HHisEntry 2 }

        -- 1.3.6.1.4.1.2011.2.25.3.40.50.120.40.1.3
        odu1_tcm1Per24HHisPara OBJECT-TYPE
            SYNTAX OCTET STRING (SIZE (0..100))
            MAX-ACCESS read-only
            STATUS current
            DESCRIPTION
                "perPara."
            ::= { odu1_tcm1Per24HHisEntry 3 }

        -- 1.3.6.1.4.1.2011.2.25.3.40.50.120.40.1.4
        odu1_tcm1Per24HHisMonValue OBJECT-TYPE
            SYNTAX OCTET STRING (SIZE (0..100))
            MAX-ACCESS read-only
            STATUS current
            DESCRIPTION
                "perMonValue."
            ::= { odu1_tcm1Per24HHisEntry 4 }

        -- 1.3.6.1.4.1.2011.2.25.3.40.50.120.40.1.5
        odu1_tcm1Per24HHisDateTimeStart OBJECT-TYPE
            SYNTAX DateAndTime
            MAX-ACCESS read-only
            STATUS current
            DESCRIPTION
                "perDateTimeStart. "
            ::= { odu1_tcm1Per24HHisEntry 5 }

        -- 1.3.6.1.4.1.2011.2.25.3.40.50.120.40.1.6
        odu1_tcm1Per24HHisDateTimeEnd OBJECT-TYPE
            SYNTAX DateAndTime
            MAX-ACCESS read-only
            STATUS current
            DESCRIPTION
                "perDateTimeEnd. "
            ::= { odu1_tcm1Per24HHisEntry 6 }

        -- 1.3.6.1.4.1.2011.2.25.3.40.50.120.40.1.7
        odu1_tcm1Per24HHisVldty OBJECT-TYPE
            SYNTAX INTEGER
            MAX-ACCESS read-only
            STATUS current
            DESCRIPTION
                "perVldty. "
            ::= { odu1_tcm1Per24HHisEntry 7 }




-- Alarm data
      -- 1.3.6.1.4.1.2011.2.25.3.40.50.121
      odu1_tcm2 OBJECT IDENTIFIER ::={ optixGlobalNGWDM 121 }


-- -------------------------------------------------------------------------
-- Perfomance 15-MIN Current Data Table (RTRV-PER-<MOD2>)
-- -------------------------------------------------------------------------
        -- 1.3.6.1.4.1.2011.2.25.3.40.50.121.10
        odu1_tcm2Per15MCurTable OBJECT-TYPE
          SYNTAX SEQUENCE OF Odu1_tcm2Per15MCurEntry
          MAX-ACCESS not-accessible
          STATUS current
          DESCRIPTION
              "odu1_tcm2Per15MCur."
          ::= { odu1_tcm2 10 }

        -- 1.3.6.1.4.1.2011.2.25.3.40.50.121.10.1
        odu1_tcm2Per15MCurEntry OBJECT-TYPE
            SYNTAX Odu1_tcm2Per15MCurEntry
            MAX-ACCESS not-accessible
            STATUS current
            DESCRIPTION
              "odu1_tcm2Per15MCur."
            INDEX { odu1_tcm2Per15MCurEid, odu1_tcm2Per15MCurPara }
            ::= { odu1_tcm2Per15MCurTable 1 }

        Odu1_tcm2Per15MCurEntry ::=
            SEQUENCE {
                odu1_tcm2Per15MCurEid
                    PerformanceEventType,
                odu1_tcm2Per15MCurMonValue
                    OCTET STRING,
                odu1_tcm2Per15MCurVldty
                    INTEGER,
                odu1_tcm2Per15MCurDateTime
                    DateAndTime,
                odu1_tcm2Per15MCurParaLen
                    INTEGER,
                odu1_tcm2Per15MCurPara
                    OCTET STRING
            }

        -- 1.3.6.1.4.1.2011.2.25.3.40.50.121.10.1.1
        odu1_tcm2Per15MCurEid OBJECT-TYPE
            SYNTAX PerformanceEventType
            MAX-ACCESS read-only
            STATUS current
            DESCRIPTION
                "perEid."
            ::= { odu1_tcm2Per15MCurEntry 1 }

        -- 1.3.6.1.4.1.2011.2.25.3.40.50.121.10.1.2
        odu1_tcm2Per15MCurMonValue OBJECT-TYPE
            SYNTAX OCTET STRING (SIZE (0..100))
            MAX-ACCESS read-only
            STATUS current
            DESCRIPTION
                "perMonValue."
            ::= { odu1_tcm2Per15MCurEntry 2 }

        -- 1.3.6.1.4.1.2011.2.25.3.40.50.121.10.1.3
        odu1_tcm2Per15MCurVldty OBJECT-TYPE
            SYNTAX INTEGER
            MAX-ACCESS read-only
            STATUS current
            DESCRIPTION
                "perVldty. "
            ::= { odu1_tcm2Per15MCurEntry 3 }

        -- 1.3.6.1.4.1.2011.2.25.3.40.50.121.10.1.4
        odu1_tcm2Per15MCurDateTime OBJECT-TYPE
            SYNTAX DateAndTime
            MAX-ACCESS read-only
            STATUS current
            DESCRIPTION
                "perDateTime. "
            ::= { odu1_tcm2Per15MCurEntry 4 }

        -- 1.3.6.1.4.1.2011.2.25.3.40.50.121.10.1.5
        odu1_tcm2Per15MCurParaLen OBJECT-TYPE
            SYNTAX INTEGER
            MAX-ACCESS read-only
            STATUS current
            DESCRIPTION
                "perParaLen."
            ::= { odu1_tcm2Per15MCurEntry 5 }

        -- 1.3.6.1.4.1.2011.2.25.3.40.50.121.10.1.6
        odu1_tcm2Per15MCurPara OBJECT-TYPE
            SYNTAX OCTET STRING (SIZE (0..100))
            MAX-ACCESS read-only
            STATUS current
            DESCRIPTION
                "perPara."
            ::= { odu1_tcm2Per15MCurEntry 6 }




-- -------------------------------------------------------------------------
-- Perfomance 15-MIN History Data Table (RTRV-PER-<MOD2>)
-- -------------------------------------------------------------------------
        -- 1.3.6.1.4.1.2011.2.25.3.40.50.121.20
        odu1_tcm2Per15MHisTable OBJECT-TYPE
          SYNTAX SEQUENCE OF Odu1_tcm2Per15MHisEntry
          MAX-ACCESS not-accessible
          STATUS current
          DESCRIPTION
              "odu1_tcm2Per15MHis."
          ::= { odu1_tcm2 20 }

        -- 1.3.6.1.4.1.2011.2.25.3.40.50.121.20.1
        odu1_tcm2Per15MHisEntry OBJECT-TYPE
            SYNTAX Odu1_tcm2Per15MHisEntry
            MAX-ACCESS not-accessible
            STATUS current
            DESCRIPTION
                "odu1_tcm2Per15MHis."
            INDEX {odu1_tcm2Per15MHisEid, odu1_tcm2Per15MHisParaLen, odu1_tcm2Per15MHisPara, odu1_tcm2Per15MHisDateTimeStart, odu1_tcm2Per15MHisDateTimeEnd}
            ::= { odu1_tcm2Per15MHisTable 1 }

        Odu1_tcm2Per15MHisEntry ::=
            SEQUENCE {
                odu1_tcm2Per15MHisEid
                    PerformanceEventType,
                odu1_tcm2Per15MHisParaLen
                    INTEGER,
                odu1_tcm2Per15MHisPara
                    OCTET STRING,
                odu1_tcm2Per15MHisMonValue
                    OCTET STRING,
                odu1_tcm2Per15MHisDateTimeStart
                    DateAndTime,
                odu1_tcm2Per15MHisDateTimeEnd
                    DateAndTime,
                odu1_tcm2Per15MHisVldty
                    INTEGER,
             }

        -- 1.3.6.1.4.1.2011.2.25.3.40.50.121.20.1.1
        odu1_tcm2Per15MHisEid OBJECT-TYPE
            SYNTAX PerformanceEventType
            MAX-ACCESS read-only
            STATUS current
            DESCRIPTION
                "perEid."
            ::= { odu1_tcm2Per15MHisEntry 1 }

        -- 1.3.6.1.4.1.2011.2.25.3.40.50.121.20.1.2
        odu1_tcm2Per15MHisParaLen OBJECT-TYPE
            SYNTAX INTEGER
            MAX-ACCESS read-only
            STATUS current
            DESCRIPTION
                "perParaLen."
            ::= { odu1_tcm2Per15MHisEntry 2 }

        -- 1.3.6.1.4.1.2011.2.25.3.40.50.121.20.1.3
        odu1_tcm2Per15MHisPara OBJECT-TYPE
            SYNTAX OCTET STRING (SIZE (0..100))
            MAX-ACCESS read-only
            STATUS current
            DESCRIPTION
                "perPara."
            ::= { odu1_tcm2Per15MHisEntry 3 }

        -- 1.3.6.1.4.1.2011.2.25.3.40.50.121.20.1.4
        odu1_tcm2Per15MHisMonValue OBJECT-TYPE
            SYNTAX OCTET STRING (SIZE (0..100))
            MAX-ACCESS read-only
            STATUS current
            DESCRIPTION
                "perMonValue."
            ::= { odu1_tcm2Per15MHisEntry 4 }

        -- 1.3.6.1.4.1.2011.2.25.3.40.50.121.20.1.5
        odu1_tcm2Per15MHisDateTimeStart OBJECT-TYPE
            SYNTAX DateAndTime
            MAX-ACCESS read-only
            STATUS current
            DESCRIPTION
                "perDateTimeStart. "
            ::= { odu1_tcm2Per15MHisEntry 5 }

        -- 1.3.6.1.4.1.2011.2.25.3.40.50.121.20.1.6
        odu1_tcm2Per15MHisDateTimeEnd OBJECT-TYPE
            SYNTAX DateAndTime
            MAX-ACCESS read-only
            STATUS current
            DESCRIPTION
                "perDateTimeEnd. "
            ::= { odu1_tcm2Per15MHisEntry 6 }

        -- 1.3.6.1.4.1.2011.2.25.3.40.50.121.20.1.7
        odu1_tcm2Per15MHisVldty OBJECT-TYPE
            SYNTAX INTEGER
            MAX-ACCESS read-only
            STATUS current
            DESCRIPTION
                "perVldty. "
            ::= { odu1_tcm2Per15MHisEntry 7 }




-- -------------------------------------------------------------------------
-- Perfomance 24-HOUR Current Data Table (RTRV-PER-<MOD2>)
-- -------------------------------------------------------------------------
        -- 1.3.6.1.4.1.2011.2.25.3.40.50.121.30
        odu1_tcm2Per24HCurTable OBJECT-TYPE
          SYNTAX SEQUENCE OF Odu1_tcm2Per24HCurEntry
          MAX-ACCESS not-accessible
          STATUS current
          DESCRIPTION
              "odu1_tcm2Per24HCur."
          ::= { odu1_tcm2 30 }

        -- 1.3.6.1.4.1.2011.2.25.3.40.50.121.30.1
        odu1_tcm2Per24HCurEntry OBJECT-TYPE
            SYNTAX Odu1_tcm2Per24HCurEntry
            MAX-ACCESS not-accessible
            STATUS current
            DESCRIPTION
              "odu1_tcm2Per24HCur."
            INDEX { odu1_tcm2Per24HCurEid, odu1_tcm2Per24HCurPara }
            ::= { odu1_tcm2Per24HCurTable 1 }

        Odu1_tcm2Per24HCurEntry ::=
            SEQUENCE {
                odu1_tcm2Per24HCurEid
                    PerformanceEventType,
                odu1_tcm2Per24HCurMonValue
                    OCTET STRING,
                odu1_tcm2Per24HCurVldty
                    INTEGER,
                odu1_tcm2Per24HCurDateTime
                    DateAndTime,
                odu1_tcm2Per24HCurParaLen
                    INTEGER,
                odu1_tcm2Per24HCurPara
                    OCTET STRING
            }

        -- 1.3.6.1.4.1.2011.2.25.3.40.50.121.30.1.1
        odu1_tcm2Per24HCurEid OBJECT-TYPE
            SYNTAX PerformanceEventType
            MAX-ACCESS read-only
            STATUS current
            DESCRIPTION
                "perEid."
            ::= { odu1_tcm2Per24HCurEntry 1 }

        -- 1.3.6.1.4.1.2011.2.25.3.40.50.121.30.1.2
        odu1_tcm2Per24HCurMonValue OBJECT-TYPE
            SYNTAX OCTET STRING (SIZE (0..100))
            MAX-ACCESS read-only
            STATUS current
            DESCRIPTION
                "perMonValue."
            ::= { odu1_tcm2Per24HCurEntry 2 }

        -- 1.3.6.1.4.1.2011.2.25.3.40.50.121.30.1.3
        odu1_tcm2Per24HCurVldty OBJECT-TYPE
            SYNTAX INTEGER
            MAX-ACCESS read-only
            STATUS current
            DESCRIPTION
                "perVldty. "
            ::= { odu1_tcm2Per24HCurEntry 3 }

        -- 1.3.6.1.4.1.2011.2.25.3.40.50.121.30.1.4
        odu1_tcm2Per24HCurDateTime OBJECT-TYPE
            SYNTAX DateAndTime
            MAX-ACCESS read-only
            STATUS current
            DESCRIPTION
                "perDateTime. "
            ::= { odu1_tcm2Per24HCurEntry 4 }

        -- 1.3.6.1.4.1.2011.2.25.3.40.50.121.30.1.5
        odu1_tcm2Per24HCurParaLen OBJECT-TYPE
            SYNTAX INTEGER
            MAX-ACCESS read-only
            STATUS current
            DESCRIPTION
                "perParaLen."
            ::= { odu1_tcm2Per24HCurEntry 5 }

        -- 1.3.6.1.4.1.2011.2.25.3.40.50.121.30.1.6
        odu1_tcm2Per24HCurPara OBJECT-TYPE
            SYNTAX OCTET STRING (SIZE (0..100))
            MAX-ACCESS read-only
            STATUS current
            DESCRIPTION
                "perPara."
            ::= { odu1_tcm2Per24HCurEntry 6 }




-- -------------------------------------------------------------------------
-- Perfomance 24-HOUR History Data Table (RTRV-PER-<MOD2>)
-- -------------------------------------------------------------------------
        -- 1.3.6.1.4.1.2011.2.25.3.40.50.121.40
        odu1_tcm2Per24HHisTable OBJECT-TYPE
          SYNTAX SEQUENCE OF Odu1_tcm2Per24HHisEntry
          MAX-ACCESS not-accessible
          STATUS current
          DESCRIPTION
              "odu1_tcm2Per24HHis."
          ::= { odu1_tcm2 40 }

        -- 1.3.6.1.4.1.2011.2.25.3.40.50.121.40.1
        odu1_tcm2Per24HHisEntry OBJECT-TYPE
            SYNTAX Odu1_tcm2Per24HHisEntry
            MAX-ACCESS not-accessible
            STATUS current
            DESCRIPTION
                "odu1_tcm2Per24HHis."
            INDEX {odu1_tcm2Per24HHisEid, odu1_tcm2Per24HHisParaLen, odu1_tcm2Per24HHisPara, odu1_tcm2Per24HHisDateTimeStart, odu1_tcm2Per24HHisDateTimeEnd}
            ::= { odu1_tcm2Per24HHisTable 1 }

        Odu1_tcm2Per24HHisEntry ::=
            SEQUENCE {
                odu1_tcm2Per24HHisEid
                    PerformanceEventType,
                odu1_tcm2Per24HHisParaLen
                    INTEGER,
                odu1_tcm2Per24HHisPara
                    OCTET STRING,
                odu1_tcm2Per24HHisMonValue
                    OCTET STRING,
                odu1_tcm2Per24HHisDateTimeStart
                    DateAndTime,
                odu1_tcm2Per24HHisDateTimeEnd
                    DateAndTime,
                odu1_tcm2Per24HHisVldty
                    INTEGER,
             }

        -- 1.3.6.1.4.1.2011.2.25.3.40.50.121.40.1.1
        odu1_tcm2Per24HHisEid OBJECT-TYPE
            SYNTAX PerformanceEventType
            MAX-ACCESS read-only
            STATUS current
            DESCRIPTION
                "perEid."
            ::= { odu1_tcm2Per24HHisEntry 1 }

        -- 1.3.6.1.4.1.2011.2.25.3.40.50.121.40.1.2
        odu1_tcm2Per24HHisParaLen OBJECT-TYPE
            SYNTAX INTEGER
            MAX-ACCESS read-only
            STATUS current
            DESCRIPTION
                "perParaLen."
            ::= { odu1_tcm2Per24HHisEntry 2 }

        -- 1.3.6.1.4.1.2011.2.25.3.40.50.121.40.1.3
        odu1_tcm2Per24HHisPara OBJECT-TYPE
            SYNTAX OCTET STRING (SIZE (0..100))
            MAX-ACCESS read-only
            STATUS current
            DESCRIPTION
                "perPara."
            ::= { odu1_tcm2Per24HHisEntry 3 }

        -- 1.3.6.1.4.1.2011.2.25.3.40.50.121.40.1.4
        odu1_tcm2Per24HHisMonValue OBJECT-TYPE
            SYNTAX OCTET STRING (SIZE (0..100))
            MAX-ACCESS read-only
            STATUS current
            DESCRIPTION
                "perMonValue."
            ::= { odu1_tcm2Per24HHisEntry 4 }

        -- 1.3.6.1.4.1.2011.2.25.3.40.50.121.40.1.5
        odu1_tcm2Per24HHisDateTimeStart OBJECT-TYPE
            SYNTAX DateAndTime
            MAX-ACCESS read-only
            STATUS current
            DESCRIPTION
                "perDateTimeStart. "
            ::= { odu1_tcm2Per24HHisEntry 5 }

        -- 1.3.6.1.4.1.2011.2.25.3.40.50.121.40.1.6
        odu1_tcm2Per24HHisDateTimeEnd OBJECT-TYPE
            SYNTAX DateAndTime
            MAX-ACCESS read-only
            STATUS current
            DESCRIPTION
                "perDateTimeEnd. "
            ::= { odu1_tcm2Per24HHisEntry 6 }

        -- 1.3.6.1.4.1.2011.2.25.3.40.50.121.40.1.7
        odu1_tcm2Per24HHisVldty OBJECT-TYPE
            SYNTAX INTEGER
            MAX-ACCESS read-only
            STATUS current
            DESCRIPTION
                "perVldty. "
            ::= { odu1_tcm2Per24HHisEntry 7 }




-- Alarm data
      -- 1.3.6.1.4.1.2011.2.25.3.40.50.122
      odu1_tcm3 OBJECT IDENTIFIER ::={ optixGlobalNGWDM 122 }


-- -------------------------------------------------------------------------
-- Perfomance 15-MIN Current Data Table (RTRV-PER-<MOD2>)
-- -------------------------------------------------------------------------
        -- 1.3.6.1.4.1.2011.2.25.3.40.50.122.10
        odu1_tcm3Per15MCurTable OBJECT-TYPE
          SYNTAX SEQUENCE OF Odu1_tcm3Per15MCurEntry
          MAX-ACCESS not-accessible
          STATUS current
          DESCRIPTION
              "odu1_tcm3Per15MCur."
          ::= { odu1_tcm3 10 }

        -- 1.3.6.1.4.1.2011.2.25.3.40.50.122.10.1
        odu1_tcm3Per15MCurEntry OBJECT-TYPE
            SYNTAX Odu1_tcm3Per15MCurEntry
            MAX-ACCESS not-accessible
            STATUS current
            DESCRIPTION
              "odu1_tcm3Per15MCur."
            INDEX { odu1_tcm3Per15MCurEid, odu1_tcm3Per15MCurPara }
            ::= { odu1_tcm3Per15MCurTable 1 }

        Odu1_tcm3Per15MCurEntry ::=
            SEQUENCE {
                odu1_tcm3Per15MCurEid
                    PerformanceEventType,
                odu1_tcm3Per15MCurMonValue
                    OCTET STRING,
                odu1_tcm3Per15MCurVldty
                    INTEGER,
                odu1_tcm3Per15MCurDateTime
                    DateAndTime,
                odu1_tcm3Per15MCurParaLen
                    INTEGER,
                odu1_tcm3Per15MCurPara
                    OCTET STRING
            }

        -- 1.3.6.1.4.1.2011.2.25.3.40.50.122.10.1.1
        odu1_tcm3Per15MCurEid OBJECT-TYPE
            SYNTAX PerformanceEventType
            MAX-ACCESS read-only
            STATUS current
            DESCRIPTION
                "perEid."
            ::= { odu1_tcm3Per15MCurEntry 1 }

        -- 1.3.6.1.4.1.2011.2.25.3.40.50.122.10.1.2
        odu1_tcm3Per15MCurMonValue OBJECT-TYPE
            SYNTAX OCTET STRING (SIZE (0..100))
            MAX-ACCESS read-only
            STATUS current
            DESCRIPTION
                "perMonValue."
            ::= { odu1_tcm3Per15MCurEntry 2 }

        -- 1.3.6.1.4.1.2011.2.25.3.40.50.122.10.1.3
        odu1_tcm3Per15MCurVldty OBJECT-TYPE
            SYNTAX INTEGER
            MAX-ACCESS read-only
            STATUS current
            DESCRIPTION
                "perVldty. "
            ::= { odu1_tcm3Per15MCurEntry 3 }

        -- 1.3.6.1.4.1.2011.2.25.3.40.50.122.10.1.4
        odu1_tcm3Per15MCurDateTime OBJECT-TYPE
            SYNTAX DateAndTime
            MAX-ACCESS read-only
            STATUS current
            DESCRIPTION
                "perDateTime. "
            ::= { odu1_tcm3Per15MCurEntry 4 }

        -- 1.3.6.1.4.1.2011.2.25.3.40.50.122.10.1.5
        odu1_tcm3Per15MCurParaLen OBJECT-TYPE
            SYNTAX INTEGER
            MAX-ACCESS read-only
            STATUS current
            DESCRIPTION
                "perParaLen."
            ::= { odu1_tcm3Per15MCurEntry 5 }

        -- 1.3.6.1.4.1.2011.2.25.3.40.50.122.10.1.6
        odu1_tcm3Per15MCurPara OBJECT-TYPE
            SYNTAX OCTET STRING (SIZE (0..100))
            MAX-ACCESS read-only
            STATUS current
            DESCRIPTION
                "perPara."
            ::= { odu1_tcm3Per15MCurEntry 6 }




-- -------------------------------------------------------------------------
-- Perfomance 15-MIN History Data Table (RTRV-PER-<MOD2>)
-- -------------------------------------------------------------------------
        -- 1.3.6.1.4.1.2011.2.25.3.40.50.122.20
        odu1_tcm3Per15MHisTable OBJECT-TYPE
          SYNTAX SEQUENCE OF Odu1_tcm3Per15MHisEntry
          MAX-ACCESS not-accessible
          STATUS current
          DESCRIPTION
              "odu1_tcm3Per15MHis."
          ::= { odu1_tcm3 20 }

        -- 1.3.6.1.4.1.2011.2.25.3.40.50.122.20.1
        odu1_tcm3Per15MHisEntry OBJECT-TYPE
            SYNTAX Odu1_tcm3Per15MHisEntry
            MAX-ACCESS not-accessible
            STATUS current
            DESCRIPTION
                "odu1_tcm3Per15MHis."
            INDEX {odu1_tcm3Per15MHisEid, odu1_tcm3Per15MHisParaLen, odu1_tcm3Per15MHisPara, odu1_tcm3Per15MHisDateTimeStart, odu1_tcm3Per15MHisDateTimeEnd}
            ::= { odu1_tcm3Per15MHisTable 1 }

        Odu1_tcm3Per15MHisEntry ::=
            SEQUENCE {
                odu1_tcm3Per15MHisEid
                    PerformanceEventType,
                odu1_tcm3Per15MHisParaLen
                    INTEGER,
                odu1_tcm3Per15MHisPara
                    OCTET STRING,
                odu1_tcm3Per15MHisMonValue
                    OCTET STRING,
                odu1_tcm3Per15MHisDateTimeStart
                    DateAndTime,
                odu1_tcm3Per15MHisDateTimeEnd
                    DateAndTime,
                odu1_tcm3Per15MHisVldty
                    INTEGER,
             }

        -- 1.3.6.1.4.1.2011.2.25.3.40.50.122.20.1.1
        odu1_tcm3Per15MHisEid OBJECT-TYPE
            SYNTAX PerformanceEventType
            MAX-ACCESS read-only
            STATUS current
            DESCRIPTION
                "perEid."
            ::= { odu1_tcm3Per15MHisEntry 1 }

        -- 1.3.6.1.4.1.2011.2.25.3.40.50.122.20.1.2
        odu1_tcm3Per15MHisParaLen OBJECT-TYPE
            SYNTAX INTEGER
            MAX-ACCESS read-only
            STATUS current
            DESCRIPTION
                "perParaLen."
            ::= { odu1_tcm3Per15MHisEntry 2 }

        -- 1.3.6.1.4.1.2011.2.25.3.40.50.122.20.1.3
        odu1_tcm3Per15MHisPara OBJECT-TYPE
            SYNTAX OCTET STRING (SIZE (0..100))
            MAX-ACCESS read-only
            STATUS current
            DESCRIPTION
                "perPara."
            ::= { odu1_tcm3Per15MHisEntry 3 }

        -- 1.3.6.1.4.1.2011.2.25.3.40.50.122.20.1.4
        odu1_tcm3Per15MHisMonValue OBJECT-TYPE
            SYNTAX OCTET STRING (SIZE (0..100))
            MAX-ACCESS read-only
            STATUS current
            DESCRIPTION
                "perMonValue."
            ::= { odu1_tcm3Per15MHisEntry 4 }

        -- 1.3.6.1.4.1.2011.2.25.3.40.50.122.20.1.5
        odu1_tcm3Per15MHisDateTimeStart OBJECT-TYPE
            SYNTAX DateAndTime
            MAX-ACCESS read-only
            STATUS current
            DESCRIPTION
                "perDateTimeStart. "
            ::= { odu1_tcm3Per15MHisEntry 5 }

        -- 1.3.6.1.4.1.2011.2.25.3.40.50.122.20.1.6
        odu1_tcm3Per15MHisDateTimeEnd OBJECT-TYPE
            SYNTAX DateAndTime
            MAX-ACCESS read-only
            STATUS current
            DESCRIPTION
                "perDateTimeEnd. "
            ::= { odu1_tcm3Per15MHisEntry 6 }

        -- 1.3.6.1.4.1.2011.2.25.3.40.50.122.20.1.7
        odu1_tcm3Per15MHisVldty OBJECT-TYPE
            SYNTAX INTEGER
            MAX-ACCESS read-only
            STATUS current
            DESCRIPTION
                "perVldty. "
            ::= { odu1_tcm3Per15MHisEntry 7 }




-- -------------------------------------------------------------------------
-- Perfomance 24-HOUR Current Data Table (RTRV-PER-<MOD2>)
-- -------------------------------------------------------------------------
        -- 1.3.6.1.4.1.2011.2.25.3.40.50.122.30
        odu1_tcm3Per24HCurTable OBJECT-TYPE
          SYNTAX SEQUENCE OF Odu1_tcm3Per24HCurEntry
          MAX-ACCESS not-accessible
          STATUS current
          DESCRIPTION
              "odu1_tcm3Per24HCur."
          ::= { odu1_tcm3 30 }

        -- 1.3.6.1.4.1.2011.2.25.3.40.50.122.30.1
        odu1_tcm3Per24HCurEntry OBJECT-TYPE
            SYNTAX Odu1_tcm3Per24HCurEntry
            MAX-ACCESS not-accessible
            STATUS current
            DESCRIPTION
              "odu1_tcm3Per24HCur."
            INDEX { odu1_tcm3Per24HCurEid, odu1_tcm3Per24HCurPara }
            ::= { odu1_tcm3Per24HCurTable 1 }

        Odu1_tcm3Per24HCurEntry ::=
            SEQUENCE {
                odu1_tcm3Per24HCurEid
                    PerformanceEventType,
                odu1_tcm3Per24HCurMonValue
                    OCTET STRING,
                odu1_tcm3Per24HCurVldty
                    INTEGER,
                odu1_tcm3Per24HCurDateTime
                    DateAndTime,
                odu1_tcm3Per24HCurParaLen
                    INTEGER,
                odu1_tcm3Per24HCurPara
                    OCTET STRING
            }

        -- 1.3.6.1.4.1.2011.2.25.3.40.50.122.30.1.1
        odu1_tcm3Per24HCurEid OBJECT-TYPE
            SYNTAX PerformanceEventType
            MAX-ACCESS read-only
            STATUS current
            DESCRIPTION
                "perEid."
            ::= { odu1_tcm3Per24HCurEntry 1 }

        -- 1.3.6.1.4.1.2011.2.25.3.40.50.122.30.1.2
        odu1_tcm3Per24HCurMonValue OBJECT-TYPE
            SYNTAX OCTET STRING (SIZE (0..100))
            MAX-ACCESS read-only
            STATUS current
            DESCRIPTION
                "perMonValue."
            ::= { odu1_tcm3Per24HCurEntry 2 }

        -- 1.3.6.1.4.1.2011.2.25.3.40.50.122.30.1.3
        odu1_tcm3Per24HCurVldty OBJECT-TYPE
            SYNTAX INTEGER
            MAX-ACCESS read-only
            STATUS current
            DESCRIPTION
                "perVldty. "
            ::= { odu1_tcm3Per24HCurEntry 3 }

        -- 1.3.6.1.4.1.2011.2.25.3.40.50.122.30.1.4
        odu1_tcm3Per24HCurDateTime OBJECT-TYPE
            SYNTAX DateAndTime
            MAX-ACCESS read-only
            STATUS current
            DESCRIPTION
                "perDateTime. "
            ::= { odu1_tcm3Per24HCurEntry 4 }

        -- 1.3.6.1.4.1.2011.2.25.3.40.50.122.30.1.5
        odu1_tcm3Per24HCurParaLen OBJECT-TYPE
            SYNTAX INTEGER
            MAX-ACCESS read-only
            STATUS current
            DESCRIPTION
                "perParaLen."
            ::= { odu1_tcm3Per24HCurEntry 5 }

        -- 1.3.6.1.4.1.2011.2.25.3.40.50.122.30.1.6
        odu1_tcm3Per24HCurPara OBJECT-TYPE
            SYNTAX OCTET STRING (SIZE (0..100))
            MAX-ACCESS read-only
            STATUS current
            DESCRIPTION
                "perPara."
            ::= { odu1_tcm3Per24HCurEntry 6 }




-- -------------------------------------------------------------------------
-- Perfomance 24-HOUR History Data Table (RTRV-PER-<MOD2>)
-- -------------------------------------------------------------------------
        -- 1.3.6.1.4.1.2011.2.25.3.40.50.122.40
        odu1_tcm3Per24HHisTable OBJECT-TYPE
          SYNTAX SEQUENCE OF Odu1_tcm3Per24HHisEntry
          MAX-ACCESS not-accessible
          STATUS current
          DESCRIPTION
              "odu1_tcm3Per24HHis."
          ::= { odu1_tcm3 40 }

        -- 1.3.6.1.4.1.2011.2.25.3.40.50.122.40.1
        odu1_tcm3Per24HHisEntry OBJECT-TYPE
            SYNTAX Odu1_tcm3Per24HHisEntry
            MAX-ACCESS not-accessible
            STATUS current
            DESCRIPTION
                "odu1_tcm3Per24HHis."
            INDEX {odu1_tcm3Per24HHisEid, odu1_tcm3Per24HHisParaLen, odu1_tcm3Per24HHisPara, odu1_tcm3Per24HHisDateTimeStart, odu1_tcm3Per24HHisDateTimeEnd}
            ::= { odu1_tcm3Per24HHisTable 1 }

        Odu1_tcm3Per24HHisEntry ::=
            SEQUENCE {
                odu1_tcm3Per24HHisEid
                    PerformanceEventType,
                odu1_tcm3Per24HHisParaLen
                    INTEGER,
                odu1_tcm3Per24HHisPara
                    OCTET STRING,
                odu1_tcm3Per24HHisMonValue
                    OCTET STRING,
                odu1_tcm3Per24HHisDateTimeStart
                    DateAndTime,
                odu1_tcm3Per24HHisDateTimeEnd
                    DateAndTime,
                odu1_tcm3Per24HHisVldty
                    INTEGER,
             }

        -- 1.3.6.1.4.1.2011.2.25.3.40.50.122.40.1.1
        odu1_tcm3Per24HHisEid OBJECT-TYPE
            SYNTAX PerformanceEventType
            MAX-ACCESS read-only
            STATUS current
            DESCRIPTION
                "perEid."
            ::= { odu1_tcm3Per24HHisEntry 1 }

        -- 1.3.6.1.4.1.2011.2.25.3.40.50.122.40.1.2
        odu1_tcm3Per24HHisParaLen OBJECT-TYPE
            SYNTAX INTEGER
            MAX-ACCESS read-only
            STATUS current
            DESCRIPTION
                "perParaLen."
            ::= { odu1_tcm3Per24HHisEntry 2 }

        -- 1.3.6.1.4.1.2011.2.25.3.40.50.122.40.1.3
        odu1_tcm3Per24HHisPara OBJECT-TYPE
            SYNTAX OCTET STRING (SIZE (0..100))
            MAX-ACCESS read-only
            STATUS current
            DESCRIPTION
                "perPara."
            ::= { odu1_tcm3Per24HHisEntry 3 }

        -- 1.3.6.1.4.1.2011.2.25.3.40.50.122.40.1.4
        odu1_tcm3Per24HHisMonValue OBJECT-TYPE
            SYNTAX OCTET STRING (SIZE (0..100))
            MAX-ACCESS read-only
            STATUS current
            DESCRIPTION
                "perMonValue."
            ::= { odu1_tcm3Per24HHisEntry 4 }

        -- 1.3.6.1.4.1.2011.2.25.3.40.50.122.40.1.5
        odu1_tcm3Per24HHisDateTimeStart OBJECT-TYPE
            SYNTAX DateAndTime
            MAX-ACCESS read-only
            STATUS current
            DESCRIPTION
                "perDateTimeStart. "
            ::= { odu1_tcm3Per24HHisEntry 5 }

        -- 1.3.6.1.4.1.2011.2.25.3.40.50.122.40.1.6
        odu1_tcm3Per24HHisDateTimeEnd OBJECT-TYPE
            SYNTAX DateAndTime
            MAX-ACCESS read-only
            STATUS current
            DESCRIPTION
                "perDateTimeEnd. "
            ::= { odu1_tcm3Per24HHisEntry 6 }

        -- 1.3.6.1.4.1.2011.2.25.3.40.50.122.40.1.7
        odu1_tcm3Per24HHisVldty OBJECT-TYPE
            SYNTAX INTEGER
            MAX-ACCESS read-only
            STATUS current
            DESCRIPTION
                "perVldty. "
            ::= { odu1_tcm3Per24HHisEntry 7 }




-- Alarm data
      -- 1.3.6.1.4.1.2011.2.25.3.40.50.123
      odu1_tcm4 OBJECT IDENTIFIER ::={ optixGlobalNGWDM 123 }


-- -------------------------------------------------------------------------
-- Perfomance 15-MIN Current Data Table (RTRV-PER-<MOD2>)
-- -------------------------------------------------------------------------
        -- 1.3.6.1.4.1.2011.2.25.3.40.50.123.10
        odu1_tcm4Per15MCurTable OBJECT-TYPE
          SYNTAX SEQUENCE OF Odu1_tcm4Per15MCurEntry
          MAX-ACCESS not-accessible
          STATUS current
          DESCRIPTION
              "odu1_tcm4Per15MCur."
          ::= { odu1_tcm4 10 }

        -- 1.3.6.1.4.1.2011.2.25.3.40.50.123.10.1
        odu1_tcm4Per15MCurEntry OBJECT-TYPE
            SYNTAX Odu1_tcm4Per15MCurEntry
            MAX-ACCESS not-accessible
            STATUS current
            DESCRIPTION
              "odu1_tcm4Per15MCur."
            INDEX { odu1_tcm4Per15MCurEid, odu1_tcm4Per15MCurPara }
            ::= { odu1_tcm4Per15MCurTable 1 }

        Odu1_tcm4Per15MCurEntry ::=
            SEQUENCE {
                odu1_tcm4Per15MCurEid
                    PerformanceEventType,
                odu1_tcm4Per15MCurMonValue
                    OCTET STRING,
                odu1_tcm4Per15MCurVldty
                    INTEGER,
                odu1_tcm4Per15MCurDateTime
                    DateAndTime,
                odu1_tcm4Per15MCurParaLen
                    INTEGER,
                odu1_tcm4Per15MCurPara
                    OCTET STRING
            }

        -- 1.3.6.1.4.1.2011.2.25.3.40.50.123.10.1.1
        odu1_tcm4Per15MCurEid OBJECT-TYPE
            SYNTAX PerformanceEventType
            MAX-ACCESS read-only
            STATUS current
            DESCRIPTION
                "perEid."
            ::= { odu1_tcm4Per15MCurEntry 1 }

        -- 1.3.6.1.4.1.2011.2.25.3.40.50.123.10.1.2
        odu1_tcm4Per15MCurMonValue OBJECT-TYPE
            SYNTAX OCTET STRING (SIZE (0..100))
            MAX-ACCESS read-only
            STATUS current
            DESCRIPTION
                "perMonValue."
            ::= { odu1_tcm4Per15MCurEntry 2 }

        -- 1.3.6.1.4.1.2011.2.25.3.40.50.123.10.1.3
        odu1_tcm4Per15MCurVldty OBJECT-TYPE
            SYNTAX INTEGER
            MAX-ACCESS read-only
            STATUS current
            DESCRIPTION
                "perVldty. "
            ::= { odu1_tcm4Per15MCurEntry 3 }

        -- 1.3.6.1.4.1.2011.2.25.3.40.50.123.10.1.4
        odu1_tcm4Per15MCurDateTime OBJECT-TYPE
            SYNTAX DateAndTime
            MAX-ACCESS read-only
            STATUS current
            DESCRIPTION
                "perDateTime. "
            ::= { odu1_tcm4Per15MCurEntry 4 }

        -- 1.3.6.1.4.1.2011.2.25.3.40.50.123.10.1.5
        odu1_tcm4Per15MCurParaLen OBJECT-TYPE
            SYNTAX INTEGER
            MAX-ACCESS read-only
            STATUS current
            DESCRIPTION
                "perParaLen."
            ::= { odu1_tcm4Per15MCurEntry 5 }

        -- 1.3.6.1.4.1.2011.2.25.3.40.50.123.10.1.6
        odu1_tcm4Per15MCurPara OBJECT-TYPE
            SYNTAX OCTET STRING (SIZE (0..100))
            MAX-ACCESS read-only
            STATUS current
            DESCRIPTION
                "perPara."
            ::= { odu1_tcm4Per15MCurEntry 6 }




-- -------------------------------------------------------------------------
-- Perfomance 15-MIN History Data Table (RTRV-PER-<MOD2>)
-- -------------------------------------------------------------------------
        -- 1.3.6.1.4.1.2011.2.25.3.40.50.123.20
        odu1_tcm4Per15MHisTable OBJECT-TYPE
          SYNTAX SEQUENCE OF Odu1_tcm4Per15MHisEntry
          MAX-ACCESS not-accessible
          STATUS current
          DESCRIPTION
              "odu1_tcm4Per15MHis."
          ::= { odu1_tcm4 20 }

        -- 1.3.6.1.4.1.2011.2.25.3.40.50.123.20.1
        odu1_tcm4Per15MHisEntry OBJECT-TYPE
            SYNTAX Odu1_tcm4Per15MHisEntry
            MAX-ACCESS not-accessible
            STATUS current
            DESCRIPTION
                "odu1_tcm4Per15MHis."
            INDEX {odu1_tcm4Per15MHisEid, odu1_tcm4Per15MHisParaLen, odu1_tcm4Per15MHisPara, odu1_tcm4Per15MHisDateTimeStart, odu1_tcm4Per15MHisDateTimeEnd}
            ::= { odu1_tcm4Per15MHisTable 1 }

        Odu1_tcm4Per15MHisEntry ::=
            SEQUENCE {
                odu1_tcm4Per15MHisEid
                    PerformanceEventType,
                odu1_tcm4Per15MHisParaLen
                    INTEGER,
                odu1_tcm4Per15MHisPara
                    OCTET STRING,
                odu1_tcm4Per15MHisMonValue
                    OCTET STRING,
                odu1_tcm4Per15MHisDateTimeStart
                    DateAndTime,
                odu1_tcm4Per15MHisDateTimeEnd
                    DateAndTime,
                odu1_tcm4Per15MHisVldty
                    INTEGER,
             }

        -- 1.3.6.1.4.1.2011.2.25.3.40.50.123.20.1.1
        odu1_tcm4Per15MHisEid OBJECT-TYPE
            SYNTAX PerformanceEventType
            MAX-ACCESS read-only
            STATUS current
            DESCRIPTION
                "perEid."
            ::= { odu1_tcm4Per15MHisEntry 1 }

        -- 1.3.6.1.4.1.2011.2.25.3.40.50.123.20.1.2
        odu1_tcm4Per15MHisParaLen OBJECT-TYPE
            SYNTAX INTEGER
            MAX-ACCESS read-only
            STATUS current
            DESCRIPTION
                "perParaLen."
            ::= { odu1_tcm4Per15MHisEntry 2 }

        -- 1.3.6.1.4.1.2011.2.25.3.40.50.123.20.1.3
        odu1_tcm4Per15MHisPara OBJECT-TYPE
            SYNTAX OCTET STRING (SIZE (0..100))
            MAX-ACCESS read-only
            STATUS current
            DESCRIPTION
                "perPara."
            ::= { odu1_tcm4Per15MHisEntry 3 }

        -- 1.3.6.1.4.1.2011.2.25.3.40.50.123.20.1.4
        odu1_tcm4Per15MHisMonValue OBJECT-TYPE
            SYNTAX OCTET STRING (SIZE (0..100))
            MAX-ACCESS read-only
            STATUS current
            DESCRIPTION
                "perMonValue."
            ::= { odu1_tcm4Per15MHisEntry 4 }

        -- 1.3.6.1.4.1.2011.2.25.3.40.50.123.20.1.5
        odu1_tcm4Per15MHisDateTimeStart OBJECT-TYPE
            SYNTAX DateAndTime
            MAX-ACCESS read-only
            STATUS current
            DESCRIPTION
                "perDateTimeStart. "
            ::= { odu1_tcm4Per15MHisEntry 5 }

        -- 1.3.6.1.4.1.2011.2.25.3.40.50.123.20.1.6
        odu1_tcm4Per15MHisDateTimeEnd OBJECT-TYPE
            SYNTAX DateAndTime
            MAX-ACCESS read-only
            STATUS current
            DESCRIPTION
                "perDateTimeEnd. "
            ::= { odu1_tcm4Per15MHisEntry 6 }

        -- 1.3.6.1.4.1.2011.2.25.3.40.50.123.20.1.7
        odu1_tcm4Per15MHisVldty OBJECT-TYPE
            SYNTAX INTEGER
            MAX-ACCESS read-only
            STATUS current
            DESCRIPTION
                "perVldty. "
            ::= { odu1_tcm4Per15MHisEntry 7 }




-- -------------------------------------------------------------------------
-- Perfomance 24-HOUR Current Data Table (RTRV-PER-<MOD2>)
-- -------------------------------------------------------------------------
        -- 1.3.6.1.4.1.2011.2.25.3.40.50.123.30
        odu1_tcm4Per24HCurTable OBJECT-TYPE
          SYNTAX SEQUENCE OF Odu1_tcm4Per24HCurEntry
          MAX-ACCESS not-accessible
          STATUS current
          DESCRIPTION
              "odu1_tcm4Per24HCur."
          ::= { odu1_tcm4 30 }

        -- 1.3.6.1.4.1.2011.2.25.3.40.50.123.30.1
        odu1_tcm4Per24HCurEntry OBJECT-TYPE
            SYNTAX Odu1_tcm4Per24HCurEntry
            MAX-ACCESS not-accessible
            STATUS current
            DESCRIPTION
              "odu1_tcm4Per24HCur."
            INDEX { odu1_tcm4Per24HCurEid, odu1_tcm4Per24HCurPara }
            ::= { odu1_tcm4Per24HCurTable 1 }

        Odu1_tcm4Per24HCurEntry ::=
            SEQUENCE {
                odu1_tcm4Per24HCurEid
                    PerformanceEventType,
                odu1_tcm4Per24HCurMonValue
                    OCTET STRING,
                odu1_tcm4Per24HCurVldty
                    INTEGER,
                odu1_tcm4Per24HCurDateTime
                    DateAndTime,
                odu1_tcm4Per24HCurParaLen
                    INTEGER,
                odu1_tcm4Per24HCurPara
                    OCTET STRING
            }

        -- 1.3.6.1.4.1.2011.2.25.3.40.50.123.30.1.1
        odu1_tcm4Per24HCurEid OBJECT-TYPE
            SYNTAX PerformanceEventType
            MAX-ACCESS read-only
            STATUS current
            DESCRIPTION
                "perEid."
            ::= { odu1_tcm4Per24HCurEntry 1 }

        -- 1.3.6.1.4.1.2011.2.25.3.40.50.123.30.1.2
        odu1_tcm4Per24HCurMonValue OBJECT-TYPE
            SYNTAX OCTET STRING (SIZE (0..100))
            MAX-ACCESS read-only
            STATUS current
            DESCRIPTION
                "perMonValue."
            ::= { odu1_tcm4Per24HCurEntry 2 }

        -- 1.3.6.1.4.1.2011.2.25.3.40.50.123.30.1.3
        odu1_tcm4Per24HCurVldty OBJECT-TYPE
            SYNTAX INTEGER
            MAX-ACCESS read-only
            STATUS current
            DESCRIPTION
                "perVldty. "
            ::= { odu1_tcm4Per24HCurEntry 3 }

        -- 1.3.6.1.4.1.2011.2.25.3.40.50.123.30.1.4
        odu1_tcm4Per24HCurDateTime OBJECT-TYPE
            SYNTAX DateAndTime
            MAX-ACCESS read-only
            STATUS current
            DESCRIPTION
                "perDateTime. "
            ::= { odu1_tcm4Per24HCurEntry 4 }

        -- 1.3.6.1.4.1.2011.2.25.3.40.50.123.30.1.5
        odu1_tcm4Per24HCurParaLen OBJECT-TYPE
            SYNTAX INTEGER
            MAX-ACCESS read-only
            STATUS current
            DESCRIPTION
                "perParaLen."
            ::= { odu1_tcm4Per24HCurEntry 5 }

        -- 1.3.6.1.4.1.2011.2.25.3.40.50.123.30.1.6
        odu1_tcm4Per24HCurPara OBJECT-TYPE
            SYNTAX OCTET STRING (SIZE (0..100))
            MAX-ACCESS read-only
            STATUS current
            DESCRIPTION
                "perPara."
            ::= { odu1_tcm4Per24HCurEntry 6 }




-- -------------------------------------------------------------------------
-- Perfomance 24-HOUR History Data Table (RTRV-PER-<MOD2>)
-- -------------------------------------------------------------------------
        -- 1.3.6.1.4.1.2011.2.25.3.40.50.123.40
        odu1_tcm4Per24HHisTable OBJECT-TYPE
          SYNTAX SEQUENCE OF Odu1_tcm4Per24HHisEntry
          MAX-ACCESS not-accessible
          STATUS current
          DESCRIPTION
              "odu1_tcm4Per24HHis."
          ::= { odu1_tcm4 40 }

        -- 1.3.6.1.4.1.2011.2.25.3.40.50.123.40.1
        odu1_tcm4Per24HHisEntry OBJECT-TYPE
            SYNTAX Odu1_tcm4Per24HHisEntry
            MAX-ACCESS not-accessible
            STATUS current
            DESCRIPTION
                "odu1_tcm4Per24HHis."
            INDEX {odu1_tcm4Per24HHisEid, odu1_tcm4Per24HHisParaLen, odu1_tcm4Per24HHisPara, odu1_tcm4Per24HHisDateTimeStart, odu1_tcm4Per24HHisDateTimeEnd}
            ::= { odu1_tcm4Per24HHisTable 1 }

        Odu1_tcm4Per24HHisEntry ::=
            SEQUENCE {
                odu1_tcm4Per24HHisEid
                    PerformanceEventType,
                odu1_tcm4Per24HHisParaLen
                    INTEGER,
                odu1_tcm4Per24HHisPara
                    OCTET STRING,
                odu1_tcm4Per24HHisMonValue
                    OCTET STRING,
                odu1_tcm4Per24HHisDateTimeStart
                    DateAndTime,
                odu1_tcm4Per24HHisDateTimeEnd
                    DateAndTime,
                odu1_tcm4Per24HHisVldty
                    INTEGER,
             }

        -- 1.3.6.1.4.1.2011.2.25.3.40.50.123.40.1.1
        odu1_tcm4Per24HHisEid OBJECT-TYPE
            SYNTAX PerformanceEventType
            MAX-ACCESS read-only
            STATUS current
            DESCRIPTION
                "perEid."
            ::= { odu1_tcm4Per24HHisEntry 1 }

        -- 1.3.6.1.4.1.2011.2.25.3.40.50.123.40.1.2
        odu1_tcm4Per24HHisParaLen OBJECT-TYPE
            SYNTAX INTEGER
            MAX-ACCESS read-only
            STATUS current
            DESCRIPTION
                "perParaLen."
            ::= { odu1_tcm4Per24HHisEntry 2 }

        -- 1.3.6.1.4.1.2011.2.25.3.40.50.123.40.1.3
        odu1_tcm4Per24HHisPara OBJECT-TYPE
            SYNTAX OCTET STRING (SIZE (0..100))
            MAX-ACCESS read-only
            STATUS current
            DESCRIPTION
                "perPara."
            ::= { odu1_tcm4Per24HHisEntry 3 }

        -- 1.3.6.1.4.1.2011.2.25.3.40.50.123.40.1.4
        odu1_tcm4Per24HHisMonValue OBJECT-TYPE
            SYNTAX OCTET STRING (SIZE (0..100))
            MAX-ACCESS read-only
            STATUS current
            DESCRIPTION
                "perMonValue."
            ::= { odu1_tcm4Per24HHisEntry 4 }

        -- 1.3.6.1.4.1.2011.2.25.3.40.50.123.40.1.5
        odu1_tcm4Per24HHisDateTimeStart OBJECT-TYPE
            SYNTAX DateAndTime
            MAX-ACCESS read-only
            STATUS current
            DESCRIPTION
                "perDateTimeStart. "
            ::= { odu1_tcm4Per24HHisEntry 5 }

        -- 1.3.6.1.4.1.2011.2.25.3.40.50.123.40.1.6
        odu1_tcm4Per24HHisDateTimeEnd OBJECT-TYPE
            SYNTAX DateAndTime
            MAX-ACCESS read-only
            STATUS current
            DESCRIPTION
                "perDateTimeEnd. "
            ::= { odu1_tcm4Per24HHisEntry 6 }

        -- 1.3.6.1.4.1.2011.2.25.3.40.50.123.40.1.7
        odu1_tcm4Per24HHisVldty OBJECT-TYPE
            SYNTAX INTEGER
            MAX-ACCESS read-only
            STATUS current
            DESCRIPTION
                "perVldty. "
            ::= { odu1_tcm4Per24HHisEntry 7 }




-- Alarm data
      -- 1.3.6.1.4.1.2011.2.25.3.40.50.124
      odu1_tcm5 OBJECT IDENTIFIER ::={ optixGlobalNGWDM 124 }


-- -------------------------------------------------------------------------
-- Perfomance 15-MIN Current Data Table (RTRV-PER-<MOD2>)
-- -------------------------------------------------------------------------
        -- 1.3.6.1.4.1.2011.2.25.3.40.50.124.10
        odu1_tcm5Per15MCurTable OBJECT-TYPE
          SYNTAX SEQUENCE OF Odu1_tcm5Per15MCurEntry
          MAX-ACCESS not-accessible
          STATUS current
          DESCRIPTION
              "odu1_tcm5Per15MCur."
          ::= { odu1_tcm5 10 }

        -- 1.3.6.1.4.1.2011.2.25.3.40.50.124.10.1
        odu1_tcm5Per15MCurEntry OBJECT-TYPE
            SYNTAX Odu1_tcm5Per15MCurEntry
            MAX-ACCESS not-accessible
            STATUS current
            DESCRIPTION
              "odu1_tcm5Per15MCur."
            INDEX { odu1_tcm5Per15MCurEid, odu1_tcm5Per15MCurPara }
            ::= { odu1_tcm5Per15MCurTable 1 }

        Odu1_tcm5Per15MCurEntry ::=
            SEQUENCE {
                odu1_tcm5Per15MCurEid
                    PerformanceEventType,
                odu1_tcm5Per15MCurMonValue
                    OCTET STRING,
                odu1_tcm5Per15MCurVldty
                    INTEGER,
                odu1_tcm5Per15MCurDateTime
                    DateAndTime,
                odu1_tcm5Per15MCurParaLen
                    INTEGER,
                odu1_tcm5Per15MCurPara
                    OCTET STRING
            }

        -- 1.3.6.1.4.1.2011.2.25.3.40.50.124.10.1.1
        odu1_tcm5Per15MCurEid OBJECT-TYPE
            SYNTAX PerformanceEventType
            MAX-ACCESS read-only
            STATUS current
            DESCRIPTION
                "perEid."
            ::= { odu1_tcm5Per15MCurEntry 1 }

        -- 1.3.6.1.4.1.2011.2.25.3.40.50.124.10.1.2
        odu1_tcm5Per15MCurMonValue OBJECT-TYPE
            SYNTAX OCTET STRING (SIZE (0..100))
            MAX-ACCESS read-only
            STATUS current
            DESCRIPTION
                "perMonValue."
            ::= { odu1_tcm5Per15MCurEntry 2 }

        -- 1.3.6.1.4.1.2011.2.25.3.40.50.124.10.1.3
        odu1_tcm5Per15MCurVldty OBJECT-TYPE
            SYNTAX INTEGER
            MAX-ACCESS read-only
            STATUS current
            DESCRIPTION
                "perVldty. "
            ::= { odu1_tcm5Per15MCurEntry 3 }

        -- 1.3.6.1.4.1.2011.2.25.3.40.50.124.10.1.4
        odu1_tcm5Per15MCurDateTime OBJECT-TYPE
            SYNTAX DateAndTime
            MAX-ACCESS read-only
            STATUS current
            DESCRIPTION
                "perDateTime. "
            ::= { odu1_tcm5Per15MCurEntry 4 }

        -- 1.3.6.1.4.1.2011.2.25.3.40.50.124.10.1.5
        odu1_tcm5Per15MCurParaLen OBJECT-TYPE
            SYNTAX INTEGER
            MAX-ACCESS read-only
            STATUS current
            DESCRIPTION
                "perParaLen."
            ::= { odu1_tcm5Per15MCurEntry 5 }

        -- 1.3.6.1.4.1.2011.2.25.3.40.50.124.10.1.6
        odu1_tcm5Per15MCurPara OBJECT-TYPE
            SYNTAX OCTET STRING (SIZE (0..100))
            MAX-ACCESS read-only
            STATUS current
            DESCRIPTION
                "perPara."
            ::= { odu1_tcm5Per15MCurEntry 6 }




-- -------------------------------------------------------------------------
-- Perfomance 15-MIN History Data Table (RTRV-PER-<MOD2>)
-- -------------------------------------------------------------------------
        -- 1.3.6.1.4.1.2011.2.25.3.40.50.124.20
        odu1_tcm5Per15MHisTable OBJECT-TYPE
          SYNTAX SEQUENCE OF Odu1_tcm5Per15MHisEntry
          MAX-ACCESS not-accessible
          STATUS current
          DESCRIPTION
              "odu1_tcm5Per15MHis."
          ::= { odu1_tcm5 20 }

        -- 1.3.6.1.4.1.2011.2.25.3.40.50.124.20.1
        odu1_tcm5Per15MHisEntry OBJECT-TYPE
            SYNTAX Odu1_tcm5Per15MHisEntry
            MAX-ACCESS not-accessible
            STATUS current
            DESCRIPTION
                "odu1_tcm5Per15MHis."
            INDEX {odu1_tcm5Per15MHisEid, odu1_tcm5Per15MHisParaLen, odu1_tcm5Per15MHisPara, odu1_tcm5Per15MHisDateTimeStart, odu1_tcm5Per15MHisDateTimeEnd}
            ::= { odu1_tcm5Per15MHisTable 1 }

        Odu1_tcm5Per15MHisEntry ::=
            SEQUENCE {
                odu1_tcm5Per15MHisEid
                    PerformanceEventType,
                odu1_tcm5Per15MHisParaLen
                    INTEGER,
                odu1_tcm5Per15MHisPara
                    OCTET STRING,
                odu1_tcm5Per15MHisMonValue
                    OCTET STRING,
                odu1_tcm5Per15MHisDateTimeStart
                    DateAndTime,
                odu1_tcm5Per15MHisDateTimeEnd
                    DateAndTime,
                odu1_tcm5Per15MHisVldty
                    INTEGER,
             }

        -- 1.3.6.1.4.1.2011.2.25.3.40.50.124.20.1.1
        odu1_tcm5Per15MHisEid OBJECT-TYPE
            SYNTAX PerformanceEventType
            MAX-ACCESS read-only
            STATUS current
            DESCRIPTION
                "perEid."
            ::= { odu1_tcm5Per15MHisEntry 1 }

        -- 1.3.6.1.4.1.2011.2.25.3.40.50.124.20.1.2
        odu1_tcm5Per15MHisParaLen OBJECT-TYPE
            SYNTAX INTEGER
            MAX-ACCESS read-only
            STATUS current
            DESCRIPTION
                "perParaLen."
            ::= { odu1_tcm5Per15MHisEntry 2 }

        -- 1.3.6.1.4.1.2011.2.25.3.40.50.124.20.1.3
        odu1_tcm5Per15MHisPara OBJECT-TYPE
            SYNTAX OCTET STRING (SIZE (0..100))
            MAX-ACCESS read-only
            STATUS current
            DESCRIPTION
                "perPara."
            ::= { odu1_tcm5Per15MHisEntry 3 }

        -- 1.3.6.1.4.1.2011.2.25.3.40.50.124.20.1.4
        odu1_tcm5Per15MHisMonValue OBJECT-TYPE
            SYNTAX OCTET STRING (SIZE (0..100))
            MAX-ACCESS read-only
            STATUS current
            DESCRIPTION
                "perMonValue."
            ::= { odu1_tcm5Per15MHisEntry 4 }

        -- 1.3.6.1.4.1.2011.2.25.3.40.50.124.20.1.5
        odu1_tcm5Per15MHisDateTimeStart OBJECT-TYPE
            SYNTAX DateAndTime
            MAX-ACCESS read-only
            STATUS current
            DESCRIPTION
                "perDateTimeStart. "
            ::= { odu1_tcm5Per15MHisEntry 5 }

        -- 1.3.6.1.4.1.2011.2.25.3.40.50.124.20.1.6
        odu1_tcm5Per15MHisDateTimeEnd OBJECT-TYPE
            SYNTAX DateAndTime
            MAX-ACCESS read-only
            STATUS current
            DESCRIPTION
                "perDateTimeEnd. "
            ::= { odu1_tcm5Per15MHisEntry 6 }

        -- 1.3.6.1.4.1.2011.2.25.3.40.50.124.20.1.7
        odu1_tcm5Per15MHisVldty OBJECT-TYPE
            SYNTAX INTEGER
            MAX-ACCESS read-only
            STATUS current
            DESCRIPTION
                "perVldty. "
            ::= { odu1_tcm5Per15MHisEntry 7 }




-- -------------------------------------------------------------------------
-- Perfomance 24-HOUR Current Data Table (RTRV-PER-<MOD2>)
-- -------------------------------------------------------------------------
        -- 1.3.6.1.4.1.2011.2.25.3.40.50.124.30
        odu1_tcm5Per24HCurTable OBJECT-TYPE
          SYNTAX SEQUENCE OF Odu1_tcm5Per24HCurEntry
          MAX-ACCESS not-accessible
          STATUS current
          DESCRIPTION
              "odu1_tcm5Per24HCur."
          ::= { odu1_tcm5 30 }

        -- 1.3.6.1.4.1.2011.2.25.3.40.50.124.30.1
        odu1_tcm5Per24HCurEntry OBJECT-TYPE
            SYNTAX Odu1_tcm5Per24HCurEntry
            MAX-ACCESS not-accessible
            STATUS current
            DESCRIPTION
              "odu1_tcm5Per24HCur."
            INDEX { odu1_tcm5Per24HCurEid, odu1_tcm5Per24HCurPara }
            ::= { odu1_tcm5Per24HCurTable 1 }

        Odu1_tcm5Per24HCurEntry ::=
            SEQUENCE {
                odu1_tcm5Per24HCurEid
                    PerformanceEventType,
                odu1_tcm5Per24HCurMonValue
                    OCTET STRING,
                odu1_tcm5Per24HCurVldty
                    INTEGER,
                odu1_tcm5Per24HCurDateTime
                    DateAndTime,
                odu1_tcm5Per24HCurParaLen
                    INTEGER,
                odu1_tcm5Per24HCurPara
                    OCTET STRING
            }

        -- 1.3.6.1.4.1.2011.2.25.3.40.50.124.30.1.1
        odu1_tcm5Per24HCurEid OBJECT-TYPE
            SYNTAX PerformanceEventType
            MAX-ACCESS read-only
            STATUS current
            DESCRIPTION
                "perEid."
            ::= { odu1_tcm5Per24HCurEntry 1 }

        -- 1.3.6.1.4.1.2011.2.25.3.40.50.124.30.1.2
        odu1_tcm5Per24HCurMonValue OBJECT-TYPE
            SYNTAX OCTET STRING (SIZE (0..100))
            MAX-ACCESS read-only
            STATUS current
            DESCRIPTION
                "perMonValue."
            ::= { odu1_tcm5Per24HCurEntry 2 }

        -- 1.3.6.1.4.1.2011.2.25.3.40.50.124.30.1.3
        odu1_tcm5Per24HCurVldty OBJECT-TYPE
            SYNTAX INTEGER
            MAX-ACCESS read-only
            STATUS current
            DESCRIPTION
                "perVldty. "
            ::= { odu1_tcm5Per24HCurEntry 3 }

        -- 1.3.6.1.4.1.2011.2.25.3.40.50.124.30.1.4
        odu1_tcm5Per24HCurDateTime OBJECT-TYPE
            SYNTAX DateAndTime
            MAX-ACCESS read-only
            STATUS current
            DESCRIPTION
                "perDateTime. "
            ::= { odu1_tcm5Per24HCurEntry 4 }

        -- 1.3.6.1.4.1.2011.2.25.3.40.50.124.30.1.5
        odu1_tcm5Per24HCurParaLen OBJECT-TYPE
            SYNTAX INTEGER
            MAX-ACCESS read-only
            STATUS current
            DESCRIPTION
                "perParaLen."
            ::= { odu1_tcm5Per24HCurEntry 5 }

        -- 1.3.6.1.4.1.2011.2.25.3.40.50.124.30.1.6
        odu1_tcm5Per24HCurPara OBJECT-TYPE
            SYNTAX OCTET STRING (SIZE (0..100))
            MAX-ACCESS read-only
            STATUS current
            DESCRIPTION
                "perPara."
            ::= { odu1_tcm5Per24HCurEntry 6 }




-- -------------------------------------------------------------------------
-- Perfomance 24-HOUR History Data Table (RTRV-PER-<MOD2>)
-- -------------------------------------------------------------------------
        -- 1.3.6.1.4.1.2011.2.25.3.40.50.124.40
        odu1_tcm5Per24HHisTable OBJECT-TYPE
          SYNTAX SEQUENCE OF Odu1_tcm5Per24HHisEntry
          MAX-ACCESS not-accessible
          STATUS current
          DESCRIPTION
              "odu1_tcm5Per24HHis."
          ::= { odu1_tcm5 40 }

        -- 1.3.6.1.4.1.2011.2.25.3.40.50.124.40.1
        odu1_tcm5Per24HHisEntry OBJECT-TYPE
            SYNTAX Odu1_tcm5Per24HHisEntry
            MAX-ACCESS not-accessible
            STATUS current
            DESCRIPTION
                "odu1_tcm5Per24HHis."
            INDEX {odu1_tcm5Per24HHisEid, odu1_tcm5Per24HHisParaLen, odu1_tcm5Per24HHisPara, odu1_tcm5Per24HHisDateTimeStart, odu1_tcm5Per24HHisDateTimeEnd}
            ::= { odu1_tcm5Per24HHisTable 1 }

        Odu1_tcm5Per24HHisEntry ::=
            SEQUENCE {
                odu1_tcm5Per24HHisEid
                    PerformanceEventType,
                odu1_tcm5Per24HHisParaLen
                    INTEGER,
                odu1_tcm5Per24HHisPara
                    OCTET STRING,
                odu1_tcm5Per24HHisMonValue
                    OCTET STRING,
                odu1_tcm5Per24HHisDateTimeStart
                    DateAndTime,
                odu1_tcm5Per24HHisDateTimeEnd
                    DateAndTime,
                odu1_tcm5Per24HHisVldty
                    INTEGER,
             }

        -- 1.3.6.1.4.1.2011.2.25.3.40.50.124.40.1.1
        odu1_tcm5Per24HHisEid OBJECT-TYPE
            SYNTAX PerformanceEventType
            MAX-ACCESS read-only
            STATUS current
            DESCRIPTION
                "perEid."
            ::= { odu1_tcm5Per24HHisEntry 1 }

        -- 1.3.6.1.4.1.2011.2.25.3.40.50.124.40.1.2
        odu1_tcm5Per24HHisParaLen OBJECT-TYPE
            SYNTAX INTEGER
            MAX-ACCESS read-only
            STATUS current
            DESCRIPTION
                "perParaLen."
            ::= { odu1_tcm5Per24HHisEntry 2 }

        -- 1.3.6.1.4.1.2011.2.25.3.40.50.124.40.1.3
        odu1_tcm5Per24HHisPara OBJECT-TYPE
            SYNTAX OCTET STRING (SIZE (0..100))
            MAX-ACCESS read-only
            STATUS current
            DESCRIPTION
                "perPara."
            ::= { odu1_tcm5Per24HHisEntry 3 }

        -- 1.3.6.1.4.1.2011.2.25.3.40.50.124.40.1.4
        odu1_tcm5Per24HHisMonValue OBJECT-TYPE
            SYNTAX OCTET STRING (SIZE (0..100))
            MAX-ACCESS read-only
            STATUS current
            DESCRIPTION
                "perMonValue."
            ::= { odu1_tcm5Per24HHisEntry 4 }

        -- 1.3.6.1.4.1.2011.2.25.3.40.50.124.40.1.5
        odu1_tcm5Per24HHisDateTimeStart OBJECT-TYPE
            SYNTAX DateAndTime
            MAX-ACCESS read-only
            STATUS current
            DESCRIPTION
                "perDateTimeStart. "
            ::= { odu1_tcm5Per24HHisEntry 5 }

        -- 1.3.6.1.4.1.2011.2.25.3.40.50.124.40.1.6
        odu1_tcm5Per24HHisDateTimeEnd OBJECT-TYPE
            SYNTAX DateAndTime
            MAX-ACCESS read-only
            STATUS current
            DESCRIPTION
                "perDateTimeEnd. "
            ::= { odu1_tcm5Per24HHisEntry 6 }

        -- 1.3.6.1.4.1.2011.2.25.3.40.50.124.40.1.7
        odu1_tcm5Per24HHisVldty OBJECT-TYPE
            SYNTAX INTEGER
            MAX-ACCESS read-only
            STATUS current
            DESCRIPTION
                "perVldty. "
            ::= { odu1_tcm5Per24HHisEntry 7 }




-- Alarm data
      -- 1.3.6.1.4.1.2011.2.25.3.40.50.125
      odu1_tcm6 OBJECT IDENTIFIER ::={ optixGlobalNGWDM 125 }


-- -------------------------------------------------------------------------
-- Perfomance 15-MIN Current Data Table (RTRV-PER-<MOD2>)
-- -------------------------------------------------------------------------
        -- 1.3.6.1.4.1.2011.2.25.3.40.50.125.10
        odu1_tcm6Per15MCurTable OBJECT-TYPE
          SYNTAX SEQUENCE OF Odu1_tcm6Per15MCurEntry
          MAX-ACCESS not-accessible
          STATUS current
          DESCRIPTION
              "odu1_tcm6Per15MCur."
          ::= { odu1_tcm6 10 }

        -- 1.3.6.1.4.1.2011.2.25.3.40.50.125.10.1
        odu1_tcm6Per15MCurEntry OBJECT-TYPE
            SYNTAX Odu1_tcm6Per15MCurEntry
            MAX-ACCESS not-accessible
            STATUS current
            DESCRIPTION
              "odu1_tcm6Per15MCur."
            INDEX { odu1_tcm6Per15MCurEid, odu1_tcm6Per15MCurPara }
            ::= { odu1_tcm6Per15MCurTable 1 }

        Odu1_tcm6Per15MCurEntry ::=
            SEQUENCE {
                odu1_tcm6Per15MCurEid
                    PerformanceEventType,
                odu1_tcm6Per15MCurMonValue
                    OCTET STRING,
                odu1_tcm6Per15MCurVldty
                    INTEGER,
                odu1_tcm6Per15MCurDateTime
                    DateAndTime,
                odu1_tcm6Per15MCurParaLen
                    INTEGER,
                odu1_tcm6Per15MCurPara
                    OCTET STRING
            }

        -- 1.3.6.1.4.1.2011.2.25.3.40.50.125.10.1.1
        odu1_tcm6Per15MCurEid OBJECT-TYPE
            SYNTAX PerformanceEventType
            MAX-ACCESS read-only
            STATUS current
            DESCRIPTION
                "perEid."
            ::= { odu1_tcm6Per15MCurEntry 1 }

        -- 1.3.6.1.4.1.2011.2.25.3.40.50.125.10.1.2
        odu1_tcm6Per15MCurMonValue OBJECT-TYPE
            SYNTAX OCTET STRING (SIZE (0..100))
            MAX-ACCESS read-only
            STATUS current
            DESCRIPTION
                "perMonValue."
            ::= { odu1_tcm6Per15MCurEntry 2 }

        -- 1.3.6.1.4.1.2011.2.25.3.40.50.125.10.1.3
        odu1_tcm6Per15MCurVldty OBJECT-TYPE
            SYNTAX INTEGER
            MAX-ACCESS read-only
            STATUS current
            DESCRIPTION
                "perVldty. "
            ::= { odu1_tcm6Per15MCurEntry 3 }

        -- 1.3.6.1.4.1.2011.2.25.3.40.50.125.10.1.4
        odu1_tcm6Per15MCurDateTime OBJECT-TYPE
            SYNTAX DateAndTime
            MAX-ACCESS read-only
            STATUS current
            DESCRIPTION
                "perDateTime. "
            ::= { odu1_tcm6Per15MCurEntry 4 }

        -- 1.3.6.1.4.1.2011.2.25.3.40.50.125.10.1.5
        odu1_tcm6Per15MCurParaLen OBJECT-TYPE
            SYNTAX INTEGER
            MAX-ACCESS read-only
            STATUS current
            DESCRIPTION
                "perParaLen."
            ::= { odu1_tcm6Per15MCurEntry 5 }

        -- 1.3.6.1.4.1.2011.2.25.3.40.50.125.10.1.6
        odu1_tcm6Per15MCurPara OBJECT-TYPE
            SYNTAX OCTET STRING (SIZE (0..100))
            MAX-ACCESS read-only
            STATUS current
            DESCRIPTION
                "perPara."
            ::= { odu1_tcm6Per15MCurEntry 6 }




-- -------------------------------------------------------------------------
-- Perfomance 15-MIN History Data Table (RTRV-PER-<MOD2>)
-- -------------------------------------------------------------------------
        -- 1.3.6.1.4.1.2011.2.25.3.40.50.125.20
        odu1_tcm6Per15MHisTable OBJECT-TYPE
          SYNTAX SEQUENCE OF Odu1_tcm6Per15MHisEntry
          MAX-ACCESS not-accessible
          STATUS current
          DESCRIPTION
              "odu1_tcm6Per15MHis."
          ::= { odu1_tcm6 20 }

        -- 1.3.6.1.4.1.2011.2.25.3.40.50.125.20.1
        odu1_tcm6Per15MHisEntry OBJECT-TYPE
            SYNTAX Odu1_tcm6Per15MHisEntry
            MAX-ACCESS not-accessible
            STATUS current
            DESCRIPTION
                "odu1_tcm6Per15MHis."
            INDEX {odu1_tcm6Per15MHisEid, odu1_tcm6Per15MHisParaLen, odu1_tcm6Per15MHisPara, odu1_tcm6Per15MHisDateTimeStart, odu1_tcm6Per15MHisDateTimeEnd}
            ::= { odu1_tcm6Per15MHisTable 1 }

        Odu1_tcm6Per15MHisEntry ::=
            SEQUENCE {
                odu1_tcm6Per15MHisEid
                    PerformanceEventType,
                odu1_tcm6Per15MHisParaLen
                    INTEGER,
                odu1_tcm6Per15MHisPara
                    OCTET STRING,
                odu1_tcm6Per15MHisMonValue
                    OCTET STRING,
                odu1_tcm6Per15MHisDateTimeStart
                    DateAndTime,
                odu1_tcm6Per15MHisDateTimeEnd
                    DateAndTime,
                odu1_tcm6Per15MHisVldty
                    INTEGER,
             }

        -- 1.3.6.1.4.1.2011.2.25.3.40.50.125.20.1.1
        odu1_tcm6Per15MHisEid OBJECT-TYPE
            SYNTAX PerformanceEventType
            MAX-ACCESS read-only
            STATUS current
            DESCRIPTION
                "perEid."
            ::= { odu1_tcm6Per15MHisEntry 1 }

        -- 1.3.6.1.4.1.2011.2.25.3.40.50.125.20.1.2
        odu1_tcm6Per15MHisParaLen OBJECT-TYPE
            SYNTAX INTEGER
            MAX-ACCESS read-only
            STATUS current
            DESCRIPTION
                "perParaLen."
            ::= { odu1_tcm6Per15MHisEntry 2 }

        -- 1.3.6.1.4.1.2011.2.25.3.40.50.125.20.1.3
        odu1_tcm6Per15MHisPara OBJECT-TYPE
            SYNTAX OCTET STRING (SIZE (0..100))
            MAX-ACCESS read-only
            STATUS current
            DESCRIPTION
                "perPara."
            ::= { odu1_tcm6Per15MHisEntry 3 }

        -- 1.3.6.1.4.1.2011.2.25.3.40.50.125.20.1.4
        odu1_tcm6Per15MHisMonValue OBJECT-TYPE
            SYNTAX OCTET STRING (SIZE (0..100))
            MAX-ACCESS read-only
            STATUS current
            DESCRIPTION
                "perMonValue."
            ::= { odu1_tcm6Per15MHisEntry 4 }

        -- 1.3.6.1.4.1.2011.2.25.3.40.50.125.20.1.5
        odu1_tcm6Per15MHisDateTimeStart OBJECT-TYPE
            SYNTAX DateAndTime
            MAX-ACCESS read-only
            STATUS current
            DESCRIPTION
                "perDateTimeStart. "
            ::= { odu1_tcm6Per15MHisEntry 5 }

        -- 1.3.6.1.4.1.2011.2.25.3.40.50.125.20.1.6
        odu1_tcm6Per15MHisDateTimeEnd OBJECT-TYPE
            SYNTAX DateAndTime
            MAX-ACCESS read-only
            STATUS current
            DESCRIPTION
                "perDateTimeEnd. "
            ::= { odu1_tcm6Per15MHisEntry 6 }

        -- 1.3.6.1.4.1.2011.2.25.3.40.50.125.20.1.7
        odu1_tcm6Per15MHisVldty OBJECT-TYPE
            SYNTAX INTEGER
            MAX-ACCESS read-only
            STATUS current
            DESCRIPTION
                "perVldty. "
            ::= { odu1_tcm6Per15MHisEntry 7 }




-- -------------------------------------------------------------------------
-- Perfomance 24-HOUR Current Data Table (RTRV-PER-<MOD2>)
-- -------------------------------------------------------------------------
        -- 1.3.6.1.4.1.2011.2.25.3.40.50.125.30
        odu1_tcm6Per24HCurTable OBJECT-TYPE
          SYNTAX SEQUENCE OF Odu1_tcm6Per24HCurEntry
          MAX-ACCESS not-accessible
          STATUS current
          DESCRIPTION
              "odu1_tcm6Per24HCur."
          ::= { odu1_tcm6 30 }

        -- 1.3.6.1.4.1.2011.2.25.3.40.50.125.30.1
        odu1_tcm6Per24HCurEntry OBJECT-TYPE
            SYNTAX Odu1_tcm6Per24HCurEntry
            MAX-ACCESS not-accessible
            STATUS current
            DESCRIPTION
              "odu1_tcm6Per24HCur."
            INDEX { odu1_tcm6Per24HCurEid, odu1_tcm6Per24HCurPara }
            ::= { odu1_tcm6Per24HCurTable 1 }

        Odu1_tcm6Per24HCurEntry ::=
            SEQUENCE {
                odu1_tcm6Per24HCurEid
                    PerformanceEventType,
                odu1_tcm6Per24HCurMonValue
                    OCTET STRING,
                odu1_tcm6Per24HCurVldty
                    INTEGER,
                odu1_tcm6Per24HCurDateTime
                    DateAndTime,
                odu1_tcm6Per24HCurParaLen
                    INTEGER,
                odu1_tcm6Per24HCurPara
                    OCTET STRING
            }

        -- 1.3.6.1.4.1.2011.2.25.3.40.50.125.30.1.1
        odu1_tcm6Per24HCurEid OBJECT-TYPE
            SYNTAX PerformanceEventType
            MAX-ACCESS read-only
            STATUS current
            DESCRIPTION
                "perEid."
            ::= { odu1_tcm6Per24HCurEntry 1 }

        -- 1.3.6.1.4.1.2011.2.25.3.40.50.125.30.1.2
        odu1_tcm6Per24HCurMonValue OBJECT-TYPE
            SYNTAX OCTET STRING (SIZE (0..100))
            MAX-ACCESS read-only
            STATUS current
            DESCRIPTION
                "perMonValue."
            ::= { odu1_tcm6Per24HCurEntry 2 }

        -- 1.3.6.1.4.1.2011.2.25.3.40.50.125.30.1.3
        odu1_tcm6Per24HCurVldty OBJECT-TYPE
            SYNTAX INTEGER
            MAX-ACCESS read-only
            STATUS current
            DESCRIPTION
                "perVldty. "
            ::= { odu1_tcm6Per24HCurEntry 3 }

        -- 1.3.6.1.4.1.2011.2.25.3.40.50.125.30.1.4
        odu1_tcm6Per24HCurDateTime OBJECT-TYPE
            SYNTAX DateAndTime
            MAX-ACCESS read-only
            STATUS current
            DESCRIPTION
                "perDateTime. "
            ::= { odu1_tcm6Per24HCurEntry 4 }

        -- 1.3.6.1.4.1.2011.2.25.3.40.50.125.30.1.5
        odu1_tcm6Per24HCurParaLen OBJECT-TYPE
            SYNTAX INTEGER
            MAX-ACCESS read-only
            STATUS current
            DESCRIPTION
                "perParaLen."
            ::= { odu1_tcm6Per24HCurEntry 5 }

        -- 1.3.6.1.4.1.2011.2.25.3.40.50.125.30.1.6
        odu1_tcm6Per24HCurPara OBJECT-TYPE
            SYNTAX OCTET STRING (SIZE (0..100))
            MAX-ACCESS read-only
            STATUS current
            DESCRIPTION
                "perPara."
            ::= { odu1_tcm6Per24HCurEntry 6 }




-- -------------------------------------------------------------------------
-- Perfomance 24-HOUR History Data Table (RTRV-PER-<MOD2>)
-- -------------------------------------------------------------------------
        -- 1.3.6.1.4.1.2011.2.25.3.40.50.125.40
        odu1_tcm6Per24HHisTable OBJECT-TYPE
          SYNTAX SEQUENCE OF Odu1_tcm6Per24HHisEntry
          MAX-ACCESS not-accessible
          STATUS current
          DESCRIPTION
              "odu1_tcm6Per24HHis."
          ::= { odu1_tcm6 40 }

        -- 1.3.6.1.4.1.2011.2.25.3.40.50.125.40.1
        odu1_tcm6Per24HHisEntry OBJECT-TYPE
            SYNTAX Odu1_tcm6Per24HHisEntry
            MAX-ACCESS not-accessible
            STATUS current
            DESCRIPTION
                "odu1_tcm6Per24HHis."
            INDEX {odu1_tcm6Per24HHisEid, odu1_tcm6Per24HHisParaLen, odu1_tcm6Per24HHisPara, odu1_tcm6Per24HHisDateTimeStart, odu1_tcm6Per24HHisDateTimeEnd}
            ::= { odu1_tcm6Per24HHisTable 1 }

        Odu1_tcm6Per24HHisEntry ::=
            SEQUENCE {
                odu1_tcm6Per24HHisEid
                    PerformanceEventType,
                odu1_tcm6Per24HHisParaLen
                    INTEGER,
                odu1_tcm6Per24HHisPara
                    OCTET STRING,
                odu1_tcm6Per24HHisMonValue
                    OCTET STRING,
                odu1_tcm6Per24HHisDateTimeStart
                    DateAndTime,
                odu1_tcm6Per24HHisDateTimeEnd
                    DateAndTime,
                odu1_tcm6Per24HHisVldty
                    INTEGER,
             }

        -- 1.3.6.1.4.1.2011.2.25.3.40.50.125.40.1.1
        odu1_tcm6Per24HHisEid OBJECT-TYPE
            SYNTAX PerformanceEventType
            MAX-ACCESS read-only
            STATUS current
            DESCRIPTION
                "perEid."
            ::= { odu1_tcm6Per24HHisEntry 1 }

        -- 1.3.6.1.4.1.2011.2.25.3.40.50.125.40.1.2
        odu1_tcm6Per24HHisParaLen OBJECT-TYPE
            SYNTAX INTEGER
            MAX-ACCESS read-only
            STATUS current
            DESCRIPTION
                "perParaLen."
            ::= { odu1_tcm6Per24HHisEntry 2 }

        -- 1.3.6.1.4.1.2011.2.25.3.40.50.125.40.1.3
        odu1_tcm6Per24HHisPara OBJECT-TYPE
            SYNTAX OCTET STRING (SIZE (0..100))
            MAX-ACCESS read-only
            STATUS current
            DESCRIPTION
                "perPara."
            ::= { odu1_tcm6Per24HHisEntry 3 }

        -- 1.3.6.1.4.1.2011.2.25.3.40.50.125.40.1.4
        odu1_tcm6Per24HHisMonValue OBJECT-TYPE
            SYNTAX OCTET STRING (SIZE (0..100))
            MAX-ACCESS read-only
            STATUS current
            DESCRIPTION
                "perMonValue."
            ::= { odu1_tcm6Per24HHisEntry 4 }

        -- 1.3.6.1.4.1.2011.2.25.3.40.50.125.40.1.5
        odu1_tcm6Per24HHisDateTimeStart OBJECT-TYPE
            SYNTAX DateAndTime
            MAX-ACCESS read-only
            STATUS current
            DESCRIPTION
                "perDateTimeStart. "
            ::= { odu1_tcm6Per24HHisEntry 5 }

        -- 1.3.6.1.4.1.2011.2.25.3.40.50.125.40.1.6
        odu1_tcm6Per24HHisDateTimeEnd OBJECT-TYPE
            SYNTAX DateAndTime
            MAX-ACCESS read-only
            STATUS current
            DESCRIPTION
                "perDateTimeEnd. "
            ::= { odu1_tcm6Per24HHisEntry 6 }

        -- 1.3.6.1.4.1.2011.2.25.3.40.50.125.40.1.7
        odu1_tcm6Per24HHisVldty OBJECT-TYPE
            SYNTAX INTEGER
            MAX-ACCESS read-only
            STATUS current
            DESCRIPTION
                "perVldty. "
            ::= { odu1_tcm6Per24HHisEntry 7 }




-- Alarm data
      -- 1.3.6.1.4.1.2011.2.25.3.40.50.126
      odu2_tcm1 OBJECT IDENTIFIER ::={ optixGlobalNGWDM 126 }


-- -------------------------------------------------------------------------
-- Perfomance 15-MIN Current Data Table (RTRV-PER-<MOD2>)
-- -------------------------------------------------------------------------
        -- 1.3.6.1.4.1.2011.2.25.3.40.50.126.10
        odu2_tcm1Per15MCurTable OBJECT-TYPE
          SYNTAX SEQUENCE OF Odu2_tcm1Per15MCurEntry
          MAX-ACCESS not-accessible
          STATUS current
          DESCRIPTION
              "odu2_tcm1Per15MCur."
          ::= { odu2_tcm1 10 }

        -- 1.3.6.1.4.1.2011.2.25.3.40.50.126.10.1
        odu2_tcm1Per15MCurEntry OBJECT-TYPE
            SYNTAX Odu2_tcm1Per15MCurEntry
            MAX-ACCESS not-accessible
            STATUS current
            DESCRIPTION
              "odu2_tcm1Per15MCur."
            INDEX { odu2_tcm1Per15MCurEid, odu2_tcm1Per15MCurPara }
            ::= { odu2_tcm1Per15MCurTable 1 }

        Odu2_tcm1Per15MCurEntry ::=
            SEQUENCE {
                odu2_tcm1Per15MCurEid
                    PerformanceEventType,
                odu2_tcm1Per15MCurMonValue
                    OCTET STRING,
                odu2_tcm1Per15MCurVldty
                    INTEGER,
                odu2_tcm1Per15MCurDateTime
                    DateAndTime,
                odu2_tcm1Per15MCurParaLen
                    INTEGER,
                odu2_tcm1Per15MCurPara
                    OCTET STRING
            }

        -- 1.3.6.1.4.1.2011.2.25.3.40.50.126.10.1.1
        odu2_tcm1Per15MCurEid OBJECT-TYPE
            SYNTAX PerformanceEventType
            MAX-ACCESS read-only
            STATUS current
            DESCRIPTION
                "perEid."
            ::= { odu2_tcm1Per15MCurEntry 1 }

        -- 1.3.6.1.4.1.2011.2.25.3.40.50.126.10.1.2
        odu2_tcm1Per15MCurMonValue OBJECT-TYPE
            SYNTAX OCTET STRING (SIZE (0..100))
            MAX-ACCESS read-only
            STATUS current
            DESCRIPTION
                "perMonValue."
            ::= { odu2_tcm1Per15MCurEntry 2 }

        -- 1.3.6.1.4.1.2011.2.25.3.40.50.126.10.1.3
        odu2_tcm1Per15MCurVldty OBJECT-TYPE
            SYNTAX INTEGER
            MAX-ACCESS read-only
            STATUS current
            DESCRIPTION
                "perVldty. "
            ::= { odu2_tcm1Per15MCurEntry 3 }

        -- 1.3.6.1.4.1.2011.2.25.3.40.50.126.10.1.4
        odu2_tcm1Per15MCurDateTime OBJECT-TYPE
            SYNTAX DateAndTime
            MAX-ACCESS read-only
            STATUS current
            DESCRIPTION
                "perDateTime. "
            ::= { odu2_tcm1Per15MCurEntry 4 }

        -- 1.3.6.1.4.1.2011.2.25.3.40.50.126.10.1.5
        odu2_tcm1Per15MCurParaLen OBJECT-TYPE
            SYNTAX INTEGER
            MAX-ACCESS read-only
            STATUS current
            DESCRIPTION
                "perParaLen."
            ::= { odu2_tcm1Per15MCurEntry 5 }

        -- 1.3.6.1.4.1.2011.2.25.3.40.50.126.10.1.6
        odu2_tcm1Per15MCurPara OBJECT-TYPE
            SYNTAX OCTET STRING (SIZE (0..100))
            MAX-ACCESS read-only
            STATUS current
            DESCRIPTION
                "perPara."
            ::= { odu2_tcm1Per15MCurEntry 6 }




-- -------------------------------------------------------------------------
-- Perfomance 15-MIN History Data Table (RTRV-PER-<MOD2>)
-- -------------------------------------------------------------------------
        -- 1.3.6.1.4.1.2011.2.25.3.40.50.126.20
        odu2_tcm1Per15MHisTable OBJECT-TYPE
          SYNTAX SEQUENCE OF Odu2_tcm1Per15MHisEntry
          MAX-ACCESS not-accessible
          STATUS current
          DESCRIPTION
              "odu2_tcm1Per15MHis."
          ::= { odu2_tcm1 20 }

        -- 1.3.6.1.4.1.2011.2.25.3.40.50.126.20.1
        odu2_tcm1Per15MHisEntry OBJECT-TYPE
            SYNTAX Odu2_tcm1Per15MHisEntry
            MAX-ACCESS not-accessible
            STATUS current
            DESCRIPTION
                "odu2_tcm1Per15MHis."
            INDEX {odu2_tcm1Per15MHisEid, odu2_tcm1Per15MHisParaLen, odu2_tcm1Per15MHisPara, odu2_tcm1Per15MHisDateTimeStart, odu2_tcm1Per15MHisDateTimeEnd}
            ::= { odu2_tcm1Per15MHisTable 1 }

        Odu2_tcm1Per15MHisEntry ::=
            SEQUENCE {
                odu2_tcm1Per15MHisEid
                    PerformanceEventType,
                odu2_tcm1Per15MHisParaLen
                    INTEGER,
                odu2_tcm1Per15MHisPara
                    OCTET STRING,
                odu2_tcm1Per15MHisMonValue
                    OCTET STRING,
                odu2_tcm1Per15MHisDateTimeStart
                    DateAndTime,
                odu2_tcm1Per15MHisDateTimeEnd
                    DateAndTime,
                odu2_tcm1Per15MHisVldty
                    INTEGER,
             }

        -- 1.3.6.1.4.1.2011.2.25.3.40.50.126.20.1.1
        odu2_tcm1Per15MHisEid OBJECT-TYPE
            SYNTAX PerformanceEventType
            MAX-ACCESS read-only
            STATUS current
            DESCRIPTION
                "perEid."
            ::= { odu2_tcm1Per15MHisEntry 1 }

        -- 1.3.6.1.4.1.2011.2.25.3.40.50.126.20.1.2
        odu2_tcm1Per15MHisParaLen OBJECT-TYPE
            SYNTAX INTEGER
            MAX-ACCESS read-only
            STATUS current
            DESCRIPTION
                "perParaLen."
            ::= { odu2_tcm1Per15MHisEntry 2 }

        -- 1.3.6.1.4.1.2011.2.25.3.40.50.126.20.1.3
        odu2_tcm1Per15MHisPara OBJECT-TYPE
            SYNTAX OCTET STRING (SIZE (0..100))
            MAX-ACCESS read-only
            STATUS current
            DESCRIPTION
                "perPara."
            ::= { odu2_tcm1Per15MHisEntry 3 }

        -- 1.3.6.1.4.1.2011.2.25.3.40.50.126.20.1.4
        odu2_tcm1Per15MHisMonValue OBJECT-TYPE
            SYNTAX OCTET STRING (SIZE (0..100))
            MAX-ACCESS read-only
            STATUS current
            DESCRIPTION
                "perMonValue."
            ::= { odu2_tcm1Per15MHisEntry 4 }

        -- 1.3.6.1.4.1.2011.2.25.3.40.50.126.20.1.5
        odu2_tcm1Per15MHisDateTimeStart OBJECT-TYPE
            SYNTAX DateAndTime
            MAX-ACCESS read-only
            STATUS current
            DESCRIPTION
                "perDateTimeStart. "
            ::= { odu2_tcm1Per15MHisEntry 5 }

        -- 1.3.6.1.4.1.2011.2.25.3.40.50.126.20.1.6
        odu2_tcm1Per15MHisDateTimeEnd OBJECT-TYPE
            SYNTAX DateAndTime
            MAX-ACCESS read-only
            STATUS current
            DESCRIPTION
                "perDateTimeEnd. "
            ::= { odu2_tcm1Per15MHisEntry 6 }

        -- 1.3.6.1.4.1.2011.2.25.3.40.50.126.20.1.7
        odu2_tcm1Per15MHisVldty OBJECT-TYPE
            SYNTAX INTEGER
            MAX-ACCESS read-only
            STATUS current
            DESCRIPTION
                "perVldty. "
            ::= { odu2_tcm1Per15MHisEntry 7 }




-- -------------------------------------------------------------------------
-- Perfomance 24-HOUR Current Data Table (RTRV-PER-<MOD2>)
-- -------------------------------------------------------------------------
        -- 1.3.6.1.4.1.2011.2.25.3.40.50.126.30
        odu2_tcm1Per24HCurTable OBJECT-TYPE
          SYNTAX SEQUENCE OF Odu2_tcm1Per24HCurEntry
          MAX-ACCESS not-accessible
          STATUS current
          DESCRIPTION
              "odu2_tcm1Per24HCur."
          ::= { odu2_tcm1 30 }

        -- 1.3.6.1.4.1.2011.2.25.3.40.50.126.30.1
        odu2_tcm1Per24HCurEntry OBJECT-TYPE
            SYNTAX Odu2_tcm1Per24HCurEntry
            MAX-ACCESS not-accessible
            STATUS current
            DESCRIPTION
              "odu2_tcm1Per24HCur."
            INDEX { odu2_tcm1Per24HCurEid, odu2_tcm1Per24HCurPara }
            ::= { odu2_tcm1Per24HCurTable 1 }

        Odu2_tcm1Per24HCurEntry ::=
            SEQUENCE {
                odu2_tcm1Per24HCurEid
                    PerformanceEventType,
                odu2_tcm1Per24HCurMonValue
                    OCTET STRING,
                odu2_tcm1Per24HCurVldty
                    INTEGER,
                odu2_tcm1Per24HCurDateTime
                    DateAndTime,
                odu2_tcm1Per24HCurParaLen
                    INTEGER,
                odu2_tcm1Per24HCurPara
                    OCTET STRING
            }

        -- 1.3.6.1.4.1.2011.2.25.3.40.50.126.30.1.1
        odu2_tcm1Per24HCurEid OBJECT-TYPE
            SYNTAX PerformanceEventType
            MAX-ACCESS read-only
            STATUS current
            DESCRIPTION
                "perEid."
            ::= { odu2_tcm1Per24HCurEntry 1 }

        -- 1.3.6.1.4.1.2011.2.25.3.40.50.126.30.1.2
        odu2_tcm1Per24HCurMonValue OBJECT-TYPE
            SYNTAX OCTET STRING (SIZE (0..100))
            MAX-ACCESS read-only
            STATUS current
            DESCRIPTION
                "perMonValue."
            ::= { odu2_tcm1Per24HCurEntry 2 }

        -- 1.3.6.1.4.1.2011.2.25.3.40.50.126.30.1.3
        odu2_tcm1Per24HCurVldty OBJECT-TYPE
            SYNTAX INTEGER
            MAX-ACCESS read-only
            STATUS current
            DESCRIPTION
                "perVldty. "
            ::= { odu2_tcm1Per24HCurEntry 3 }

        -- 1.3.6.1.4.1.2011.2.25.3.40.50.126.30.1.4
        odu2_tcm1Per24HCurDateTime OBJECT-TYPE
            SYNTAX DateAndTime
            MAX-ACCESS read-only
            STATUS current
            DESCRIPTION
                "perDateTime. "
            ::= { odu2_tcm1Per24HCurEntry 4 }

        -- 1.3.6.1.4.1.2011.2.25.3.40.50.126.30.1.5
        odu2_tcm1Per24HCurParaLen OBJECT-TYPE
            SYNTAX INTEGER
            MAX-ACCESS read-only
            STATUS current
            DESCRIPTION
                "perParaLen."
            ::= { odu2_tcm1Per24HCurEntry 5 }

        -- 1.3.6.1.4.1.2011.2.25.3.40.50.126.30.1.6
        odu2_tcm1Per24HCurPara OBJECT-TYPE
            SYNTAX OCTET STRING (SIZE (0..100))
            MAX-ACCESS read-only
            STATUS current
            DESCRIPTION
                "perPara."
            ::= { odu2_tcm1Per24HCurEntry 6 }




-- -------------------------------------------------------------------------
-- Perfomance 24-HOUR History Data Table (RTRV-PER-<MOD2>)
-- -------------------------------------------------------------------------
        -- 1.3.6.1.4.1.2011.2.25.3.40.50.126.40
        odu2_tcm1Per24HHisTable OBJECT-TYPE
          SYNTAX SEQUENCE OF Odu2_tcm1Per24HHisEntry
          MAX-ACCESS not-accessible
          STATUS current
          DESCRIPTION
              "odu2_tcm1Per24HHis."
          ::= { odu2_tcm1 40 }

        -- 1.3.6.1.4.1.2011.2.25.3.40.50.126.40.1
        odu2_tcm1Per24HHisEntry OBJECT-TYPE
            SYNTAX Odu2_tcm1Per24HHisEntry
            MAX-ACCESS not-accessible
            STATUS current
            DESCRIPTION
                "odu2_tcm1Per24HHis."
            INDEX {odu2_tcm1Per24HHisEid, odu2_tcm1Per24HHisParaLen, odu2_tcm1Per24HHisPara, odu2_tcm1Per24HHisDateTimeStart, odu2_tcm1Per24HHisDateTimeEnd}
            ::= { odu2_tcm1Per24HHisTable 1 }

        Odu2_tcm1Per24HHisEntry ::=
            SEQUENCE {
                odu2_tcm1Per24HHisEid
                    PerformanceEventType,
                odu2_tcm1Per24HHisParaLen
                    INTEGER,
                odu2_tcm1Per24HHisPara
                    OCTET STRING,
                odu2_tcm1Per24HHisMonValue
                    OCTET STRING,
                odu2_tcm1Per24HHisDateTimeStart
                    DateAndTime,
                odu2_tcm1Per24HHisDateTimeEnd
                    DateAndTime,
                odu2_tcm1Per24HHisVldty
                    INTEGER,
             }

        -- 1.3.6.1.4.1.2011.2.25.3.40.50.126.40.1.1
        odu2_tcm1Per24HHisEid OBJECT-TYPE
            SYNTAX PerformanceEventType
            MAX-ACCESS read-only
            STATUS current
            DESCRIPTION
                "perEid."
            ::= { odu2_tcm1Per24HHisEntry 1 }

        -- 1.3.6.1.4.1.2011.2.25.3.40.50.126.40.1.2
        odu2_tcm1Per24HHisParaLen OBJECT-TYPE
            SYNTAX INTEGER
            MAX-ACCESS read-only
            STATUS current
            DESCRIPTION
                "perParaLen."
            ::= { odu2_tcm1Per24HHisEntry 2 }

        -- 1.3.6.1.4.1.2011.2.25.3.40.50.126.40.1.3
        odu2_tcm1Per24HHisPara OBJECT-TYPE
            SYNTAX OCTET STRING (SIZE (0..100))
            MAX-ACCESS read-only
            STATUS current
            DESCRIPTION
                "perPara."
            ::= { odu2_tcm1Per24HHisEntry 3 }

        -- 1.3.6.1.4.1.2011.2.25.3.40.50.126.40.1.4
        odu2_tcm1Per24HHisMonValue OBJECT-TYPE
            SYNTAX OCTET STRING (SIZE (0..100))
            MAX-ACCESS read-only
            STATUS current
            DESCRIPTION
                "perMonValue."
            ::= { odu2_tcm1Per24HHisEntry 4 }

        -- 1.3.6.1.4.1.2011.2.25.3.40.50.126.40.1.5
        odu2_tcm1Per24HHisDateTimeStart OBJECT-TYPE
            SYNTAX DateAndTime
            MAX-ACCESS read-only
            STATUS current
            DESCRIPTION
                "perDateTimeStart. "
            ::= { odu2_tcm1Per24HHisEntry 5 }

        -- 1.3.6.1.4.1.2011.2.25.3.40.50.126.40.1.6
        odu2_tcm1Per24HHisDateTimeEnd OBJECT-TYPE
            SYNTAX DateAndTime
            MAX-ACCESS read-only
            STATUS current
            DESCRIPTION
                "perDateTimeEnd. "
            ::= { odu2_tcm1Per24HHisEntry 6 }

        -- 1.3.6.1.4.1.2011.2.25.3.40.50.126.40.1.7
        odu2_tcm1Per24HHisVldty OBJECT-TYPE
            SYNTAX INTEGER
            MAX-ACCESS read-only
            STATUS current
            DESCRIPTION
                "perVldty. "
            ::= { odu2_tcm1Per24HHisEntry 7 }




-- Alarm data
      -- 1.3.6.1.4.1.2011.2.25.3.40.50.127
      odu2_tcm2 OBJECT IDENTIFIER ::={ optixGlobalNGWDM 127 }


-- -------------------------------------------------------------------------
-- Perfomance 15-MIN Current Data Table (RTRV-PER-<MOD2>)
-- -------------------------------------------------------------------------
        -- 1.3.6.1.4.1.2011.2.25.3.40.50.127.10
        odu2_tcm2Per15MCurTable OBJECT-TYPE
          SYNTAX SEQUENCE OF Odu2_tcm2Per15MCurEntry
          MAX-ACCESS not-accessible
          STATUS current
          DESCRIPTION
              "odu2_tcm2Per15MCur."
          ::= { odu2_tcm2 10 }

        -- 1.3.6.1.4.1.2011.2.25.3.40.50.127.10.1
        odu2_tcm2Per15MCurEntry OBJECT-TYPE
            SYNTAX Odu2_tcm2Per15MCurEntry
            MAX-ACCESS not-accessible
            STATUS current
            DESCRIPTION
              "odu2_tcm2Per15MCur."
            INDEX { odu2_tcm2Per15MCurEid, odu2_tcm2Per15MCurPara }
            ::= { odu2_tcm2Per15MCurTable 1 }

        Odu2_tcm2Per15MCurEntry ::=
            SEQUENCE {
                odu2_tcm2Per15MCurEid
                    PerformanceEventType,
                odu2_tcm2Per15MCurMonValue
                    OCTET STRING,
                odu2_tcm2Per15MCurVldty
                    INTEGER,
                odu2_tcm2Per15MCurDateTime
                    DateAndTime,
                odu2_tcm2Per15MCurParaLen
                    INTEGER,
                odu2_tcm2Per15MCurPara
                    OCTET STRING
            }

        -- 1.3.6.1.4.1.2011.2.25.3.40.50.127.10.1.1
        odu2_tcm2Per15MCurEid OBJECT-TYPE
            SYNTAX PerformanceEventType
            MAX-ACCESS read-only
            STATUS current
            DESCRIPTION
                "perEid."
            ::= { odu2_tcm2Per15MCurEntry 1 }

        -- 1.3.6.1.4.1.2011.2.25.3.40.50.127.10.1.2
        odu2_tcm2Per15MCurMonValue OBJECT-TYPE
            SYNTAX OCTET STRING (SIZE (0..100))
            MAX-ACCESS read-only
            STATUS current
            DESCRIPTION
                "perMonValue."
            ::= { odu2_tcm2Per15MCurEntry 2 }

        -- 1.3.6.1.4.1.2011.2.25.3.40.50.127.10.1.3
        odu2_tcm2Per15MCurVldty OBJECT-TYPE
            SYNTAX INTEGER
            MAX-ACCESS read-only
            STATUS current
            DESCRIPTION
                "perVldty. "
            ::= { odu2_tcm2Per15MCurEntry 3 }

        -- 1.3.6.1.4.1.2011.2.25.3.40.50.127.10.1.4
        odu2_tcm2Per15MCurDateTime OBJECT-TYPE
            SYNTAX DateAndTime
            MAX-ACCESS read-only
            STATUS current
            DESCRIPTION
                "perDateTime. "
            ::= { odu2_tcm2Per15MCurEntry 4 }

        -- 1.3.6.1.4.1.2011.2.25.3.40.50.127.10.1.5
        odu2_tcm2Per15MCurParaLen OBJECT-TYPE
            SYNTAX INTEGER
            MAX-ACCESS read-only
            STATUS current
            DESCRIPTION
                "perParaLen."
            ::= { odu2_tcm2Per15MCurEntry 5 }

        -- 1.3.6.1.4.1.2011.2.25.3.40.50.127.10.1.6
        odu2_tcm2Per15MCurPara OBJECT-TYPE
            SYNTAX OCTET STRING (SIZE (0..100))
            MAX-ACCESS read-only
            STATUS current
            DESCRIPTION
                "perPara."
            ::= { odu2_tcm2Per15MCurEntry 6 }




-- -------------------------------------------------------------------------
-- Perfomance 15-MIN History Data Table (RTRV-PER-<MOD2>)
-- -------------------------------------------------------------------------
        -- 1.3.6.1.4.1.2011.2.25.3.40.50.127.20
        odu2_tcm2Per15MHisTable OBJECT-TYPE
          SYNTAX SEQUENCE OF Odu2_tcm2Per15MHisEntry
          MAX-ACCESS not-accessible
          STATUS current
          DESCRIPTION
              "odu2_tcm2Per15MHis."
          ::= { odu2_tcm2 20 }

        -- 1.3.6.1.4.1.2011.2.25.3.40.50.127.20.1
        odu2_tcm2Per15MHisEntry OBJECT-TYPE
            SYNTAX Odu2_tcm2Per15MHisEntry
            MAX-ACCESS not-accessible
            STATUS current
            DESCRIPTION
                "odu2_tcm2Per15MHis."
            INDEX {odu2_tcm2Per15MHisEid, odu2_tcm2Per15MHisParaLen, odu2_tcm2Per15MHisPara, odu2_tcm2Per15MHisDateTimeStart, odu2_tcm2Per15MHisDateTimeEnd}
            ::= { odu2_tcm2Per15MHisTable 1 }

        Odu2_tcm2Per15MHisEntry ::=
            SEQUENCE {
                odu2_tcm2Per15MHisEid
                    PerformanceEventType,
                odu2_tcm2Per15MHisParaLen
                    INTEGER,
                odu2_tcm2Per15MHisPara
                    OCTET STRING,
                odu2_tcm2Per15MHisMonValue
                    OCTET STRING,
                odu2_tcm2Per15MHisDateTimeStart
                    DateAndTime,
                odu2_tcm2Per15MHisDateTimeEnd
                    DateAndTime,
                odu2_tcm2Per15MHisVldty
                    INTEGER,
             }

        -- 1.3.6.1.4.1.2011.2.25.3.40.50.127.20.1.1
        odu2_tcm2Per15MHisEid OBJECT-TYPE
            SYNTAX PerformanceEventType
            MAX-ACCESS read-only
            STATUS current
            DESCRIPTION
                "perEid."
            ::= { odu2_tcm2Per15MHisEntry 1 }

        -- 1.3.6.1.4.1.2011.2.25.3.40.50.127.20.1.2
        odu2_tcm2Per15MHisParaLen OBJECT-TYPE
            SYNTAX INTEGER
            MAX-ACCESS read-only
            STATUS current
            DESCRIPTION
                "perParaLen."
            ::= { odu2_tcm2Per15MHisEntry 2 }

        -- 1.3.6.1.4.1.2011.2.25.3.40.50.127.20.1.3
        odu2_tcm2Per15MHisPara OBJECT-TYPE
            SYNTAX OCTET STRING (SIZE (0..100))
            MAX-ACCESS read-only
            STATUS current
            DESCRIPTION
                "perPara."
            ::= { odu2_tcm2Per15MHisEntry 3 }

        -- 1.3.6.1.4.1.2011.2.25.3.40.50.127.20.1.4
        odu2_tcm2Per15MHisMonValue OBJECT-TYPE
            SYNTAX OCTET STRING (SIZE (0..100))
            MAX-ACCESS read-only
            STATUS current
            DESCRIPTION
                "perMonValue."
            ::= { odu2_tcm2Per15MHisEntry 4 }

        -- 1.3.6.1.4.1.2011.2.25.3.40.50.127.20.1.5
        odu2_tcm2Per15MHisDateTimeStart OBJECT-TYPE
            SYNTAX DateAndTime
            MAX-ACCESS read-only
            STATUS current
            DESCRIPTION
                "perDateTimeStart. "
            ::= { odu2_tcm2Per15MHisEntry 5 }

        -- 1.3.6.1.4.1.2011.2.25.3.40.50.127.20.1.6
        odu2_tcm2Per15MHisDateTimeEnd OBJECT-TYPE
            SYNTAX DateAndTime
            MAX-ACCESS read-only
            STATUS current
            DESCRIPTION
                "perDateTimeEnd. "
            ::= { odu2_tcm2Per15MHisEntry 6 }

        -- 1.3.6.1.4.1.2011.2.25.3.40.50.127.20.1.7
        odu2_tcm2Per15MHisVldty OBJECT-TYPE
            SYNTAX INTEGER
            MAX-ACCESS read-only
            STATUS current
            DESCRIPTION
                "perVldty. "
            ::= { odu2_tcm2Per15MHisEntry 7 }




-- -------------------------------------------------------------------------
-- Perfomance 24-HOUR Current Data Table (RTRV-PER-<MOD2>)
-- -------------------------------------------------------------------------
        -- 1.3.6.1.4.1.2011.2.25.3.40.50.127.30
        odu2_tcm2Per24HCurTable OBJECT-TYPE
          SYNTAX SEQUENCE OF Odu2_tcm2Per24HCurEntry
          MAX-ACCESS not-accessible
          STATUS current
          DESCRIPTION
              "odu2_tcm2Per24HCur."
          ::= { odu2_tcm2 30 }

        -- 1.3.6.1.4.1.2011.2.25.3.40.50.127.30.1
        odu2_tcm2Per24HCurEntry OBJECT-TYPE
            SYNTAX Odu2_tcm2Per24HCurEntry
            MAX-ACCESS not-accessible
            STATUS current
            DESCRIPTION
              "odu2_tcm2Per24HCur."
            INDEX { odu2_tcm2Per24HCurEid, odu2_tcm2Per24HCurPara }
            ::= { odu2_tcm2Per24HCurTable 1 }

        Odu2_tcm2Per24HCurEntry ::=
            SEQUENCE {
                odu2_tcm2Per24HCurEid
                    PerformanceEventType,
                odu2_tcm2Per24HCurMonValue
                    OCTET STRING,
                odu2_tcm2Per24HCurVldty
                    INTEGER,
                odu2_tcm2Per24HCurDateTime
                    DateAndTime,
                odu2_tcm2Per24HCurParaLen
                    INTEGER,
                odu2_tcm2Per24HCurPara
                    OCTET STRING
            }

        -- 1.3.6.1.4.1.2011.2.25.3.40.50.127.30.1.1
        odu2_tcm2Per24HCurEid OBJECT-TYPE
            SYNTAX PerformanceEventType
            MAX-ACCESS read-only
            STATUS current
            DESCRIPTION
                "perEid."
            ::= { odu2_tcm2Per24HCurEntry 1 }

        -- 1.3.6.1.4.1.2011.2.25.3.40.50.127.30.1.2
        odu2_tcm2Per24HCurMonValue OBJECT-TYPE
            SYNTAX OCTET STRING (SIZE (0..100))
            MAX-ACCESS read-only
            STATUS current
            DESCRIPTION
                "perMonValue."
            ::= { odu2_tcm2Per24HCurEntry 2 }

        -- 1.3.6.1.4.1.2011.2.25.3.40.50.127.30.1.3
        odu2_tcm2Per24HCurVldty OBJECT-TYPE
            SYNTAX INTEGER
            MAX-ACCESS read-only
            STATUS current
            DESCRIPTION
                "perVldty. "
            ::= { odu2_tcm2Per24HCurEntry 3 }

        -- 1.3.6.1.4.1.2011.2.25.3.40.50.127.30.1.4
        odu2_tcm2Per24HCurDateTime OBJECT-TYPE
            SYNTAX DateAndTime
            MAX-ACCESS read-only
            STATUS current
            DESCRIPTION
                "perDateTime. "
            ::= { odu2_tcm2Per24HCurEntry 4 }

        -- 1.3.6.1.4.1.2011.2.25.3.40.50.127.30.1.5
        odu2_tcm2Per24HCurParaLen OBJECT-TYPE
            SYNTAX INTEGER
            MAX-ACCESS read-only
            STATUS current
            DESCRIPTION
                "perParaLen."
            ::= { odu2_tcm2Per24HCurEntry 5 }

        -- 1.3.6.1.4.1.2011.2.25.3.40.50.127.30.1.6
        odu2_tcm2Per24HCurPara OBJECT-TYPE
            SYNTAX OCTET STRING (SIZE (0..100))
            MAX-ACCESS read-only
            STATUS current
            DESCRIPTION
                "perPara."
            ::= { odu2_tcm2Per24HCurEntry 6 }




-- -------------------------------------------------------------------------
-- Perfomance 24-HOUR History Data Table (RTRV-PER-<MOD2>)
-- -------------------------------------------------------------------------
        -- 1.3.6.1.4.1.2011.2.25.3.40.50.127.40
        odu2_tcm2Per24HHisTable OBJECT-TYPE
          SYNTAX SEQUENCE OF Odu2_tcm2Per24HHisEntry
          MAX-ACCESS not-accessible
          STATUS current
          DESCRIPTION
              "odu2_tcm2Per24HHis."
          ::= { odu2_tcm2 40 }

        -- 1.3.6.1.4.1.2011.2.25.3.40.50.127.40.1
        odu2_tcm2Per24HHisEntry OBJECT-TYPE
            SYNTAX Odu2_tcm2Per24HHisEntry
            MAX-ACCESS not-accessible
            STATUS current
            DESCRIPTION
                "odu2_tcm2Per24HHis."
            INDEX {odu2_tcm2Per24HHisEid, odu2_tcm2Per24HHisParaLen, odu2_tcm2Per24HHisPara, odu2_tcm2Per24HHisDateTimeStart, odu2_tcm2Per24HHisDateTimeEnd}
            ::= { odu2_tcm2Per24HHisTable 1 }

        Odu2_tcm2Per24HHisEntry ::=
            SEQUENCE {
                odu2_tcm2Per24HHisEid
                    PerformanceEventType,
                odu2_tcm2Per24HHisParaLen
                    INTEGER,
                odu2_tcm2Per24HHisPara
                    OCTET STRING,
                odu2_tcm2Per24HHisMonValue
                    OCTET STRING,
                odu2_tcm2Per24HHisDateTimeStart
                    DateAndTime,
                odu2_tcm2Per24HHisDateTimeEnd
                    DateAndTime,
                odu2_tcm2Per24HHisVldty
                    INTEGER,
             }

        -- 1.3.6.1.4.1.2011.2.25.3.40.50.127.40.1.1
        odu2_tcm2Per24HHisEid OBJECT-TYPE
            SYNTAX PerformanceEventType
            MAX-ACCESS read-only
            STATUS current
            DESCRIPTION
                "perEid."
            ::= { odu2_tcm2Per24HHisEntry 1 }

        -- 1.3.6.1.4.1.2011.2.25.3.40.50.127.40.1.2
        odu2_tcm2Per24HHisParaLen OBJECT-TYPE
            SYNTAX INTEGER
            MAX-ACCESS read-only
            STATUS current
            DESCRIPTION
                "perParaLen."
            ::= { odu2_tcm2Per24HHisEntry 2 }

        -- 1.3.6.1.4.1.2011.2.25.3.40.50.127.40.1.3
        odu2_tcm2Per24HHisPara OBJECT-TYPE
            SYNTAX OCTET STRING (SIZE (0..100))
            MAX-ACCESS read-only
            STATUS current
            DESCRIPTION
                "perPara."
            ::= { odu2_tcm2Per24HHisEntry 3 }

        -- 1.3.6.1.4.1.2011.2.25.3.40.50.127.40.1.4
        odu2_tcm2Per24HHisMonValue OBJECT-TYPE
            SYNTAX OCTET STRING (SIZE (0..100))
            MAX-ACCESS read-only
            STATUS current
            DESCRIPTION
                "perMonValue."
            ::= { odu2_tcm2Per24HHisEntry 4 }

        -- 1.3.6.1.4.1.2011.2.25.3.40.50.127.40.1.5
        odu2_tcm2Per24HHisDateTimeStart OBJECT-TYPE
            SYNTAX DateAndTime
            MAX-ACCESS read-only
            STATUS current
            DESCRIPTION
                "perDateTimeStart. "
            ::= { odu2_tcm2Per24HHisEntry 5 }

        -- 1.3.6.1.4.1.2011.2.25.3.40.50.127.40.1.6
        odu2_tcm2Per24HHisDateTimeEnd OBJECT-TYPE
            SYNTAX DateAndTime
            MAX-ACCESS read-only
            STATUS current
            DESCRIPTION
                "perDateTimeEnd. "
            ::= { odu2_tcm2Per24HHisEntry 6 }

        -- 1.3.6.1.4.1.2011.2.25.3.40.50.127.40.1.7
        odu2_tcm2Per24HHisVldty OBJECT-TYPE
            SYNTAX INTEGER
            MAX-ACCESS read-only
            STATUS current
            DESCRIPTION
                "perVldty. "
            ::= { odu2_tcm2Per24HHisEntry 7 }




-- Alarm data
      -- 1.3.6.1.4.1.2011.2.25.3.40.50.128
      odu2_tcm3 OBJECT IDENTIFIER ::={ optixGlobalNGWDM 128 }


-- -------------------------------------------------------------------------
-- Perfomance 15-MIN Current Data Table (RTRV-PER-<MOD2>)
-- -------------------------------------------------------------------------
        -- 1.3.6.1.4.1.2011.2.25.3.40.50.128.10
        odu2_tcm3Per15MCurTable OBJECT-TYPE
          SYNTAX SEQUENCE OF Odu2_tcm3Per15MCurEntry
          MAX-ACCESS not-accessible
          STATUS current
          DESCRIPTION
              "odu2_tcm3Per15MCur."
          ::= { odu2_tcm3 10 }

        -- 1.3.6.1.4.1.2011.2.25.3.40.50.128.10.1
        odu2_tcm3Per15MCurEntry OBJECT-TYPE
            SYNTAX Odu2_tcm3Per15MCurEntry
            MAX-ACCESS not-accessible
            STATUS current
            DESCRIPTION
              "odu2_tcm3Per15MCur."
            INDEX { odu2_tcm3Per15MCurEid, odu2_tcm3Per15MCurPara }
            ::= { odu2_tcm3Per15MCurTable 1 }

        Odu2_tcm3Per15MCurEntry ::=
            SEQUENCE {
                odu2_tcm3Per15MCurEid
                    PerformanceEventType,
                odu2_tcm3Per15MCurMonValue
                    OCTET STRING,
                odu2_tcm3Per15MCurVldty
                    INTEGER,
                odu2_tcm3Per15MCurDateTime
                    DateAndTime,
                odu2_tcm3Per15MCurParaLen
                    INTEGER,
                odu2_tcm3Per15MCurPara
                    OCTET STRING
            }

        -- 1.3.6.1.4.1.2011.2.25.3.40.50.128.10.1.1
        odu2_tcm3Per15MCurEid OBJECT-TYPE
            SYNTAX PerformanceEventType
            MAX-ACCESS read-only
            STATUS current
            DESCRIPTION
                "perEid."
            ::= { odu2_tcm3Per15MCurEntry 1 }

        -- 1.3.6.1.4.1.2011.2.25.3.40.50.128.10.1.2
        odu2_tcm3Per15MCurMonValue OBJECT-TYPE
            SYNTAX OCTET STRING (SIZE (0..100))
            MAX-ACCESS read-only
            STATUS current
            DESCRIPTION
                "perMonValue."
            ::= { odu2_tcm3Per15MCurEntry 2 }

        -- 1.3.6.1.4.1.2011.2.25.3.40.50.128.10.1.3
        odu2_tcm3Per15MCurVldty OBJECT-TYPE
            SYNTAX INTEGER
            MAX-ACCESS read-only
            STATUS current
            DESCRIPTION
                "perVldty. "
            ::= { odu2_tcm3Per15MCurEntry 3 }

        -- 1.3.6.1.4.1.2011.2.25.3.40.50.128.10.1.4
        odu2_tcm3Per15MCurDateTime OBJECT-TYPE
            SYNTAX DateAndTime
            MAX-ACCESS read-only
            STATUS current
            DESCRIPTION
                "perDateTime. "
            ::= { odu2_tcm3Per15MCurEntry 4 }

        -- 1.3.6.1.4.1.2011.2.25.3.40.50.128.10.1.5
        odu2_tcm3Per15MCurParaLen OBJECT-TYPE
            SYNTAX INTEGER
            MAX-ACCESS read-only
            STATUS current
            DESCRIPTION
                "perParaLen."
            ::= { odu2_tcm3Per15MCurEntry 5 }

        -- 1.3.6.1.4.1.2011.2.25.3.40.50.128.10.1.6
        odu2_tcm3Per15MCurPara OBJECT-TYPE
            SYNTAX OCTET STRING (SIZE (0..100))
            MAX-ACCESS read-only
            STATUS current
            DESCRIPTION
                "perPara."
            ::= { odu2_tcm3Per15MCurEntry 6 }




-- -------------------------------------------------------------------------
-- Perfomance 15-MIN History Data Table (RTRV-PER-<MOD2>)
-- -------------------------------------------------------------------------
        -- 1.3.6.1.4.1.2011.2.25.3.40.50.128.20
        odu2_tcm3Per15MHisTable OBJECT-TYPE
          SYNTAX SEQUENCE OF Odu2_tcm3Per15MHisEntry
          MAX-ACCESS not-accessible
          STATUS current
          DESCRIPTION
              "odu2_tcm3Per15MHis."
          ::= { odu2_tcm3 20 }

        -- 1.3.6.1.4.1.2011.2.25.3.40.50.128.20.1
        odu2_tcm3Per15MHisEntry OBJECT-TYPE
            SYNTAX Odu2_tcm3Per15MHisEntry
            MAX-ACCESS not-accessible
            STATUS current
            DESCRIPTION
                "odu2_tcm3Per15MHis."
            INDEX {odu2_tcm3Per15MHisEid, odu2_tcm3Per15MHisParaLen, odu2_tcm3Per15MHisPara, odu2_tcm3Per15MHisDateTimeStart, odu2_tcm3Per15MHisDateTimeEnd}
            ::= { odu2_tcm3Per15MHisTable 1 }

        Odu2_tcm3Per15MHisEntry ::=
            SEQUENCE {
                odu2_tcm3Per15MHisEid
                    PerformanceEventType,
                odu2_tcm3Per15MHisParaLen
                    INTEGER,
                odu2_tcm3Per15MHisPara
                    OCTET STRING,
                odu2_tcm3Per15MHisMonValue
                    OCTET STRING,
                odu2_tcm3Per15MHisDateTimeStart
                    DateAndTime,
                odu2_tcm3Per15MHisDateTimeEnd
                    DateAndTime,
                odu2_tcm3Per15MHisVldty
                    INTEGER,
             }

        -- 1.3.6.1.4.1.2011.2.25.3.40.50.128.20.1.1
        odu2_tcm3Per15MHisEid OBJECT-TYPE
            SYNTAX PerformanceEventType
            MAX-ACCESS read-only
            STATUS current
            DESCRIPTION
                "perEid."
            ::= { odu2_tcm3Per15MHisEntry 1 }

        -- 1.3.6.1.4.1.2011.2.25.3.40.50.128.20.1.2
        odu2_tcm3Per15MHisParaLen OBJECT-TYPE
            SYNTAX INTEGER
            MAX-ACCESS read-only
            STATUS current
            DESCRIPTION
                "perParaLen."
            ::= { odu2_tcm3Per15MHisEntry 2 }

        -- 1.3.6.1.4.1.2011.2.25.3.40.50.128.20.1.3
        odu2_tcm3Per15MHisPara OBJECT-TYPE
            SYNTAX OCTET STRING (SIZE (0..100))
            MAX-ACCESS read-only
            STATUS current
            DESCRIPTION
                "perPara."
            ::= { odu2_tcm3Per15MHisEntry 3 }

        -- 1.3.6.1.4.1.2011.2.25.3.40.50.128.20.1.4
        odu2_tcm3Per15MHisMonValue OBJECT-TYPE
            SYNTAX OCTET STRING (SIZE (0..100))
            MAX-ACCESS read-only
            STATUS current
            DESCRIPTION
                "perMonValue."
            ::= { odu2_tcm3Per15MHisEntry 4 }

        -- 1.3.6.1.4.1.2011.2.25.3.40.50.128.20.1.5
        odu2_tcm3Per15MHisDateTimeStart OBJECT-TYPE
            SYNTAX DateAndTime
            MAX-ACCESS read-only
            STATUS current
            DESCRIPTION
                "perDateTimeStart. "
            ::= { odu2_tcm3Per15MHisEntry 5 }

        -- 1.3.6.1.4.1.2011.2.25.3.40.50.128.20.1.6
        odu2_tcm3Per15MHisDateTimeEnd OBJECT-TYPE
            SYNTAX DateAndTime
            MAX-ACCESS read-only
            STATUS current
            DESCRIPTION
                "perDateTimeEnd. "
            ::= { odu2_tcm3Per15MHisEntry 6 }

        -- 1.3.6.1.4.1.2011.2.25.3.40.50.128.20.1.7
        odu2_tcm3Per15MHisVldty OBJECT-TYPE
            SYNTAX INTEGER
            MAX-ACCESS read-only
            STATUS current
            DESCRIPTION
                "perVldty. "
            ::= { odu2_tcm3Per15MHisEntry 7 }




-- -------------------------------------------------------------------------
-- Perfomance 24-HOUR Current Data Table (RTRV-PER-<MOD2>)
-- -------------------------------------------------------------------------
        -- 1.3.6.1.4.1.2011.2.25.3.40.50.128.30
        odu2_tcm3Per24HCurTable OBJECT-TYPE
          SYNTAX SEQUENCE OF Odu2_tcm3Per24HCurEntry
          MAX-ACCESS not-accessible
          STATUS current
          DESCRIPTION
              "odu2_tcm3Per24HCur."
          ::= { odu2_tcm3 30 }

        -- 1.3.6.1.4.1.2011.2.25.3.40.50.128.30.1
        odu2_tcm3Per24HCurEntry OBJECT-TYPE
            SYNTAX Odu2_tcm3Per24HCurEntry
            MAX-ACCESS not-accessible
            STATUS current
            DESCRIPTION
              "odu2_tcm3Per24HCur."
            INDEX { odu2_tcm3Per24HCurEid, odu2_tcm3Per24HCurPara }
            ::= { odu2_tcm3Per24HCurTable 1 }

        Odu2_tcm3Per24HCurEntry ::=
            SEQUENCE {
                odu2_tcm3Per24HCurEid
                    PerformanceEventType,
                odu2_tcm3Per24HCurMonValue
                    OCTET STRING,
                odu2_tcm3Per24HCurVldty
                    INTEGER,
                odu2_tcm3Per24HCurDateTime
                    DateAndTime,
                odu2_tcm3Per24HCurParaLen
                    INTEGER,
                odu2_tcm3Per24HCurPara
                    OCTET STRING
            }

        -- 1.3.6.1.4.1.2011.2.25.3.40.50.128.30.1.1
        odu2_tcm3Per24HCurEid OBJECT-TYPE
            SYNTAX PerformanceEventType
            MAX-ACCESS read-only
            STATUS current
            DESCRIPTION
                "perEid."
            ::= { odu2_tcm3Per24HCurEntry 1 }

        -- 1.3.6.1.4.1.2011.2.25.3.40.50.128.30.1.2
        odu2_tcm3Per24HCurMonValue OBJECT-TYPE
            SYNTAX OCTET STRING (SIZE (0..100))
            MAX-ACCESS read-only
            STATUS current
            DESCRIPTION
                "perMonValue."
            ::= { odu2_tcm3Per24HCurEntry 2 }

        -- 1.3.6.1.4.1.2011.2.25.3.40.50.128.30.1.3
        odu2_tcm3Per24HCurVldty OBJECT-TYPE
            SYNTAX INTEGER
            MAX-ACCESS read-only
            STATUS current
            DESCRIPTION
                "perVldty. "
            ::= { odu2_tcm3Per24HCurEntry 3 }

        -- 1.3.6.1.4.1.2011.2.25.3.40.50.128.30.1.4
        odu2_tcm3Per24HCurDateTime OBJECT-TYPE
            SYNTAX DateAndTime
            MAX-ACCESS read-only
            STATUS current
            DESCRIPTION
                "perDateTime. "
            ::= { odu2_tcm3Per24HCurEntry 4 }

        -- 1.3.6.1.4.1.2011.2.25.3.40.50.128.30.1.5
        odu2_tcm3Per24HCurParaLen OBJECT-TYPE
            SYNTAX INTEGER
            MAX-ACCESS read-only
            STATUS current
            DESCRIPTION
                "perParaLen."
            ::= { odu2_tcm3Per24HCurEntry 5 }

        -- 1.3.6.1.4.1.2011.2.25.3.40.50.128.30.1.6
        odu2_tcm3Per24HCurPara OBJECT-TYPE
            SYNTAX OCTET STRING (SIZE (0..100))
            MAX-ACCESS read-only
            STATUS current
            DESCRIPTION
                "perPara."
            ::= { odu2_tcm3Per24HCurEntry 6 }




-- -------------------------------------------------------------------------
-- Perfomance 24-HOUR History Data Table (RTRV-PER-<MOD2>)
-- -------------------------------------------------------------------------
        -- 1.3.6.1.4.1.2011.2.25.3.40.50.128.40
        odu2_tcm3Per24HHisTable OBJECT-TYPE
          SYNTAX SEQUENCE OF Odu2_tcm3Per24HHisEntry
          MAX-ACCESS not-accessible
          STATUS current
          DESCRIPTION
              "odu2_tcm3Per24HHis."
          ::= { odu2_tcm3 40 }

        -- 1.3.6.1.4.1.2011.2.25.3.40.50.128.40.1
        odu2_tcm3Per24HHisEntry OBJECT-TYPE
            SYNTAX Odu2_tcm3Per24HHisEntry
            MAX-ACCESS not-accessible
            STATUS current
            DESCRIPTION
                "odu2_tcm3Per24HHis."
            INDEX {odu2_tcm3Per24HHisEid, odu2_tcm3Per24HHisParaLen, odu2_tcm3Per24HHisPara, odu2_tcm3Per24HHisDateTimeStart, odu2_tcm3Per24HHisDateTimeEnd}
            ::= { odu2_tcm3Per24HHisTable 1 }

        Odu2_tcm3Per24HHisEntry ::=
            SEQUENCE {
                odu2_tcm3Per24HHisEid
                    PerformanceEventType,
                odu2_tcm3Per24HHisParaLen
                    INTEGER,
                odu2_tcm3Per24HHisPara
                    OCTET STRING,
                odu2_tcm3Per24HHisMonValue
                    OCTET STRING,
                odu2_tcm3Per24HHisDateTimeStart
                    DateAndTime,
                odu2_tcm3Per24HHisDateTimeEnd
                    DateAndTime,
                odu2_tcm3Per24HHisVldty
                    INTEGER,
             }

        -- 1.3.6.1.4.1.2011.2.25.3.40.50.128.40.1.1
        odu2_tcm3Per24HHisEid OBJECT-TYPE
            SYNTAX PerformanceEventType
            MAX-ACCESS read-only
            STATUS current
            DESCRIPTION
                "perEid."
            ::= { odu2_tcm3Per24HHisEntry 1 }

        -- 1.3.6.1.4.1.2011.2.25.3.40.50.128.40.1.2
        odu2_tcm3Per24HHisParaLen OBJECT-TYPE
            SYNTAX INTEGER
            MAX-ACCESS read-only
            STATUS current
            DESCRIPTION
                "perParaLen."
            ::= { odu2_tcm3Per24HHisEntry 2 }

        -- 1.3.6.1.4.1.2011.2.25.3.40.50.128.40.1.3
        odu2_tcm3Per24HHisPara OBJECT-TYPE
            SYNTAX OCTET STRING (SIZE (0..100))
            MAX-ACCESS read-only
            STATUS current
            DESCRIPTION
                "perPara."
            ::= { odu2_tcm3Per24HHisEntry 3 }

        -- 1.3.6.1.4.1.2011.2.25.3.40.50.128.40.1.4
        odu2_tcm3Per24HHisMonValue OBJECT-TYPE
            SYNTAX OCTET STRING (SIZE (0..100))
            MAX-ACCESS read-only
            STATUS current
            DESCRIPTION
                "perMonValue."
            ::= { odu2_tcm3Per24HHisEntry 4 }

        -- 1.3.6.1.4.1.2011.2.25.3.40.50.128.40.1.5
        odu2_tcm3Per24HHisDateTimeStart OBJECT-TYPE
            SYNTAX DateAndTime
            MAX-ACCESS read-only
            STATUS current
            DESCRIPTION
                "perDateTimeStart. "
            ::= { odu2_tcm3Per24HHisEntry 5 }

        -- 1.3.6.1.4.1.2011.2.25.3.40.50.128.40.1.6
        odu2_tcm3Per24HHisDateTimeEnd OBJECT-TYPE
            SYNTAX DateAndTime
            MAX-ACCESS read-only
            STATUS current
            DESCRIPTION
                "perDateTimeEnd. "
            ::= { odu2_tcm3Per24HHisEntry 6 }

        -- 1.3.6.1.4.1.2011.2.25.3.40.50.128.40.1.7
        odu2_tcm3Per24HHisVldty OBJECT-TYPE
            SYNTAX INTEGER
            MAX-ACCESS read-only
            STATUS current
            DESCRIPTION
                "perVldty. "
            ::= { odu2_tcm3Per24HHisEntry 7 }




-- Alarm data
      -- 1.3.6.1.4.1.2011.2.25.3.40.50.129
      odu2_tcm4 OBJECT IDENTIFIER ::={ optixGlobalNGWDM 129 }


-- -------------------------------------------------------------------------
-- Perfomance 15-MIN Current Data Table (RTRV-PER-<MOD2>)
-- -------------------------------------------------------------------------
        -- 1.3.6.1.4.1.2011.2.25.3.40.50.129.10
        odu2_tcm4Per15MCurTable OBJECT-TYPE
          SYNTAX SEQUENCE OF Odu2_tcm4Per15MCurEntry
          MAX-ACCESS not-accessible
          STATUS current
          DESCRIPTION
              "odu2_tcm4Per15MCur."
          ::= { odu2_tcm4 10 }

        -- 1.3.6.1.4.1.2011.2.25.3.40.50.129.10.1
        odu2_tcm4Per15MCurEntry OBJECT-TYPE
            SYNTAX Odu2_tcm4Per15MCurEntry
            MAX-ACCESS not-accessible
            STATUS current
            DESCRIPTION
              "odu2_tcm4Per15MCur."
            INDEX { odu2_tcm4Per15MCurEid, odu2_tcm4Per15MCurPara }
            ::= { odu2_tcm4Per15MCurTable 1 }

        Odu2_tcm4Per15MCurEntry ::=
            SEQUENCE {
                odu2_tcm4Per15MCurEid
                    PerformanceEventType,
                odu2_tcm4Per15MCurMonValue
                    OCTET STRING,
                odu2_tcm4Per15MCurVldty
                    INTEGER,
                odu2_tcm4Per15MCurDateTime
                    DateAndTime,
                odu2_tcm4Per15MCurParaLen
                    INTEGER,
                odu2_tcm4Per15MCurPara
                    OCTET STRING
            }

        -- 1.3.6.1.4.1.2011.2.25.3.40.50.129.10.1.1
        odu2_tcm4Per15MCurEid OBJECT-TYPE
            SYNTAX PerformanceEventType
            MAX-ACCESS read-only
            STATUS current
            DESCRIPTION
                "perEid."
            ::= { odu2_tcm4Per15MCurEntry 1 }

        -- 1.3.6.1.4.1.2011.2.25.3.40.50.129.10.1.2
        odu2_tcm4Per15MCurMonValue OBJECT-TYPE
            SYNTAX OCTET STRING (SIZE (0..100))
            MAX-ACCESS read-only
            STATUS current
            DESCRIPTION
                "perMonValue."
            ::= { odu2_tcm4Per15MCurEntry 2 }

        -- 1.3.6.1.4.1.2011.2.25.3.40.50.129.10.1.3
        odu2_tcm4Per15MCurVldty OBJECT-TYPE
            SYNTAX INTEGER
            MAX-ACCESS read-only
            STATUS current
            DESCRIPTION
                "perVldty. "
            ::= { odu2_tcm4Per15MCurEntry 3 }

        -- 1.3.6.1.4.1.2011.2.25.3.40.50.129.10.1.4
        odu2_tcm4Per15MCurDateTime OBJECT-TYPE
            SYNTAX DateAndTime
            MAX-ACCESS read-only
            STATUS current
            DESCRIPTION
                "perDateTime. "
            ::= { odu2_tcm4Per15MCurEntry 4 }

        -- 1.3.6.1.4.1.2011.2.25.3.40.50.129.10.1.5
        odu2_tcm4Per15MCurParaLen OBJECT-TYPE
            SYNTAX INTEGER
            MAX-ACCESS read-only
            STATUS current
            DESCRIPTION
                "perParaLen."
            ::= { odu2_tcm4Per15MCurEntry 5 }

        -- 1.3.6.1.4.1.2011.2.25.3.40.50.129.10.1.6
        odu2_tcm4Per15MCurPara OBJECT-TYPE
            SYNTAX OCTET STRING (SIZE (0..100))
            MAX-ACCESS read-only
            STATUS current
            DESCRIPTION
                "perPara."
            ::= { odu2_tcm4Per15MCurEntry 6 }




-- -------------------------------------------------------------------------
-- Perfomance 15-MIN History Data Table (RTRV-PER-<MOD2>)
-- -------------------------------------------------------------------------
        -- 1.3.6.1.4.1.2011.2.25.3.40.50.129.20
        odu2_tcm4Per15MHisTable OBJECT-TYPE
          SYNTAX SEQUENCE OF Odu2_tcm4Per15MHisEntry
          MAX-ACCESS not-accessible
          STATUS current
          DESCRIPTION
              "odu2_tcm4Per15MHis."
          ::= { odu2_tcm4 20 }

        -- 1.3.6.1.4.1.2011.2.25.3.40.50.129.20.1
        odu2_tcm4Per15MHisEntry OBJECT-TYPE
            SYNTAX Odu2_tcm4Per15MHisEntry
            MAX-ACCESS not-accessible
            STATUS current
            DESCRIPTION
                "odu2_tcm4Per15MHis."
            INDEX {odu2_tcm4Per15MHisEid, odu2_tcm4Per15MHisParaLen, odu2_tcm4Per15MHisPara, odu2_tcm4Per15MHisDateTimeStart, odu2_tcm4Per15MHisDateTimeEnd}
            ::= { odu2_tcm4Per15MHisTable 1 }

        Odu2_tcm4Per15MHisEntry ::=
            SEQUENCE {
                odu2_tcm4Per15MHisEid
                    PerformanceEventType,
                odu2_tcm4Per15MHisParaLen
                    INTEGER,
                odu2_tcm4Per15MHisPara
                    OCTET STRING,
                odu2_tcm4Per15MHisMonValue
                    OCTET STRING,
                odu2_tcm4Per15MHisDateTimeStart
                    DateAndTime,
                odu2_tcm4Per15MHisDateTimeEnd
                    DateAndTime,
                odu2_tcm4Per15MHisVldty
                    INTEGER,
             }

        -- 1.3.6.1.4.1.2011.2.25.3.40.50.129.20.1.1
        odu2_tcm4Per15MHisEid OBJECT-TYPE
            SYNTAX PerformanceEventType
            MAX-ACCESS read-only
            STATUS current
            DESCRIPTION
                "perEid."
            ::= { odu2_tcm4Per15MHisEntry 1 }

        -- 1.3.6.1.4.1.2011.2.25.3.40.50.129.20.1.2
        odu2_tcm4Per15MHisParaLen OBJECT-TYPE
            SYNTAX INTEGER
            MAX-ACCESS read-only
            STATUS current
            DESCRIPTION
                "perParaLen."
            ::= { odu2_tcm4Per15MHisEntry 2 }

        -- 1.3.6.1.4.1.2011.2.25.3.40.50.129.20.1.3
        odu2_tcm4Per15MHisPara OBJECT-TYPE
            SYNTAX OCTET STRING (SIZE (0..100))
            MAX-ACCESS read-only
            STATUS current
            DESCRIPTION
                "perPara."
            ::= { odu2_tcm4Per15MHisEntry 3 }

        -- 1.3.6.1.4.1.2011.2.25.3.40.50.129.20.1.4
        odu2_tcm4Per15MHisMonValue OBJECT-TYPE
            SYNTAX OCTET STRING (SIZE (0..100))
            MAX-ACCESS read-only
            STATUS current
            DESCRIPTION
                "perMonValue."
            ::= { odu2_tcm4Per15MHisEntry 4 }

        -- 1.3.6.1.4.1.2011.2.25.3.40.50.129.20.1.5
        odu2_tcm4Per15MHisDateTimeStart OBJECT-TYPE
            SYNTAX DateAndTime
            MAX-ACCESS read-only
            STATUS current
            DESCRIPTION
                "perDateTimeStart. "
            ::= { odu2_tcm4Per15MHisEntry 5 }

        -- 1.3.6.1.4.1.2011.2.25.3.40.50.129.20.1.6
        odu2_tcm4Per15MHisDateTimeEnd OBJECT-TYPE
            SYNTAX DateAndTime
            MAX-ACCESS read-only
            STATUS current
            DESCRIPTION
                "perDateTimeEnd. "
            ::= { odu2_tcm4Per15MHisEntry 6 }

        -- 1.3.6.1.4.1.2011.2.25.3.40.50.129.20.1.7
        odu2_tcm4Per15MHisVldty OBJECT-TYPE
            SYNTAX INTEGER
            MAX-ACCESS read-only
            STATUS current
            DESCRIPTION
                "perVldty. "
            ::= { odu2_tcm4Per15MHisEntry 7 }




-- -------------------------------------------------------------------------
-- Perfomance 24-HOUR Current Data Table (RTRV-PER-<MOD2>)
-- -------------------------------------------------------------------------
        -- 1.3.6.1.4.1.2011.2.25.3.40.50.129.30
        odu2_tcm4Per24HCurTable OBJECT-TYPE
          SYNTAX SEQUENCE OF Odu2_tcm4Per24HCurEntry
          MAX-ACCESS not-accessible
          STATUS current
          DESCRIPTION
              "odu2_tcm4Per24HCur."
          ::= { odu2_tcm4 30 }

        -- 1.3.6.1.4.1.2011.2.25.3.40.50.129.30.1
        odu2_tcm4Per24HCurEntry OBJECT-TYPE
            SYNTAX Odu2_tcm4Per24HCurEntry
            MAX-ACCESS not-accessible
            STATUS current
            DESCRIPTION
              "odu2_tcm4Per24HCur."
            INDEX { odu2_tcm4Per24HCurEid, odu2_tcm4Per24HCurPara }
            ::= { odu2_tcm4Per24HCurTable 1 }

        Odu2_tcm4Per24HCurEntry ::=
            SEQUENCE {
                odu2_tcm4Per24HCurEid
                    PerformanceEventType,
                odu2_tcm4Per24HCurMonValue
                    OCTET STRING,
                odu2_tcm4Per24HCurVldty
                    INTEGER,
                odu2_tcm4Per24HCurDateTime
                    DateAndTime,
                odu2_tcm4Per24HCurParaLen
                    INTEGER,
                odu2_tcm4Per24HCurPara
                    OCTET STRING
            }

        -- 1.3.6.1.4.1.2011.2.25.3.40.50.129.30.1.1
        odu2_tcm4Per24HCurEid OBJECT-TYPE
            SYNTAX PerformanceEventType
            MAX-ACCESS read-only
            STATUS current
            DESCRIPTION
                "perEid."
            ::= { odu2_tcm4Per24HCurEntry 1 }

        -- 1.3.6.1.4.1.2011.2.25.3.40.50.129.30.1.2
        odu2_tcm4Per24HCurMonValue OBJECT-TYPE
            SYNTAX OCTET STRING (SIZE (0..100))
            MAX-ACCESS read-only
            STATUS current
            DESCRIPTION
                "perMonValue."
            ::= { odu2_tcm4Per24HCurEntry 2 }

        -- 1.3.6.1.4.1.2011.2.25.3.40.50.129.30.1.3
        odu2_tcm4Per24HCurVldty OBJECT-TYPE
            SYNTAX INTEGER
            MAX-ACCESS read-only
            STATUS current
            DESCRIPTION
                "perVldty. "
            ::= { odu2_tcm4Per24HCurEntry 3 }

        -- 1.3.6.1.4.1.2011.2.25.3.40.50.129.30.1.4
        odu2_tcm4Per24HCurDateTime OBJECT-TYPE
            SYNTAX DateAndTime
            MAX-ACCESS read-only
            STATUS current
            DESCRIPTION
                "perDateTime. "
            ::= { odu2_tcm4Per24HCurEntry 4 }

        -- 1.3.6.1.4.1.2011.2.25.3.40.50.129.30.1.5
        odu2_tcm4Per24HCurParaLen OBJECT-TYPE
            SYNTAX INTEGER
            MAX-ACCESS read-only
            STATUS current
            DESCRIPTION
                "perParaLen."
            ::= { odu2_tcm4Per24HCurEntry 5 }

        -- 1.3.6.1.4.1.2011.2.25.3.40.50.129.30.1.6
        odu2_tcm4Per24HCurPara OBJECT-TYPE
            SYNTAX OCTET STRING (SIZE (0..100))
            MAX-ACCESS read-only
            STATUS current
            DESCRIPTION
                "perPara."
            ::= { odu2_tcm4Per24HCurEntry 6 }




-- -------------------------------------------------------------------------
-- Perfomance 24-HOUR History Data Table (RTRV-PER-<MOD2>)
-- -------------------------------------------------------------------------
        -- 1.3.6.1.4.1.2011.2.25.3.40.50.129.40
        odu2_tcm4Per24HHisTable OBJECT-TYPE
          SYNTAX SEQUENCE OF Odu2_tcm4Per24HHisEntry
          MAX-ACCESS not-accessible
          STATUS current
          DESCRIPTION
              "odu2_tcm4Per24HHis."
          ::= { odu2_tcm4 40 }

        -- 1.3.6.1.4.1.2011.2.25.3.40.50.129.40.1
        odu2_tcm4Per24HHisEntry OBJECT-TYPE
            SYNTAX Odu2_tcm4Per24HHisEntry
            MAX-ACCESS not-accessible
            STATUS current
            DESCRIPTION
                "odu2_tcm4Per24HHis."
            INDEX {odu2_tcm4Per24HHisEid, odu2_tcm4Per24HHisParaLen, odu2_tcm4Per24HHisPara, odu2_tcm4Per24HHisDateTimeStart, odu2_tcm4Per24HHisDateTimeEnd}
            ::= { odu2_tcm4Per24HHisTable 1 }

        Odu2_tcm4Per24HHisEntry ::=
            SEQUENCE {
                odu2_tcm4Per24HHisEid
                    PerformanceEventType,
                odu2_tcm4Per24HHisParaLen
                    INTEGER,
                odu2_tcm4Per24HHisPara
                    OCTET STRING,
                odu2_tcm4Per24HHisMonValue
                    OCTET STRING,
                odu2_tcm4Per24HHisDateTimeStart
                    DateAndTime,
                odu2_tcm4Per24HHisDateTimeEnd
                    DateAndTime,
                odu2_tcm4Per24HHisVldty
                    INTEGER,
             }

        -- 1.3.6.1.4.1.2011.2.25.3.40.50.129.40.1.1
        odu2_tcm4Per24HHisEid OBJECT-TYPE
            SYNTAX PerformanceEventType
            MAX-ACCESS read-only
            STATUS current
            DESCRIPTION
                "perEid."
            ::= { odu2_tcm4Per24HHisEntry 1 }

        -- 1.3.6.1.4.1.2011.2.25.3.40.50.129.40.1.2
        odu2_tcm4Per24HHisParaLen OBJECT-TYPE
            SYNTAX INTEGER
            MAX-ACCESS read-only
            STATUS current
            DESCRIPTION
                "perParaLen."
            ::= { odu2_tcm4Per24HHisEntry 2 }

        -- 1.3.6.1.4.1.2011.2.25.3.40.50.129.40.1.3
        odu2_tcm4Per24HHisPara OBJECT-TYPE
            SYNTAX OCTET STRING (SIZE (0..100))
            MAX-ACCESS read-only
            STATUS current
            DESCRIPTION
                "perPara."
            ::= { odu2_tcm4Per24HHisEntry 3 }

        -- 1.3.6.1.4.1.2011.2.25.3.40.50.129.40.1.4
        odu2_tcm4Per24HHisMonValue OBJECT-TYPE
            SYNTAX OCTET STRING (SIZE (0..100))
            MAX-ACCESS read-only
            STATUS current
            DESCRIPTION
                "perMonValue."
            ::= { odu2_tcm4Per24HHisEntry 4 }

        -- 1.3.6.1.4.1.2011.2.25.3.40.50.129.40.1.5
        odu2_tcm4Per24HHisDateTimeStart OBJECT-TYPE
            SYNTAX DateAndTime
            MAX-ACCESS read-only
            STATUS current
            DESCRIPTION
                "perDateTimeStart. "
            ::= { odu2_tcm4Per24HHisEntry 5 }

        -- 1.3.6.1.4.1.2011.2.25.3.40.50.129.40.1.6
        odu2_tcm4Per24HHisDateTimeEnd OBJECT-TYPE
            SYNTAX DateAndTime
            MAX-ACCESS read-only
            STATUS current
            DESCRIPTION
                "perDateTimeEnd. "
            ::= { odu2_tcm4Per24HHisEntry 6 }

        -- 1.3.6.1.4.1.2011.2.25.3.40.50.129.40.1.7
        odu2_tcm4Per24HHisVldty OBJECT-TYPE
            SYNTAX INTEGER
            MAX-ACCESS read-only
            STATUS current
            DESCRIPTION
                "perVldty. "
            ::= { odu2_tcm4Per24HHisEntry 7 }




-- Alarm data
      -- 1.3.6.1.4.1.2011.2.25.3.40.50.130
      odu2_tcm5 OBJECT IDENTIFIER ::={ optixGlobalNGWDM 130 }


-- -------------------------------------------------------------------------
-- Perfomance 15-MIN Current Data Table (RTRV-PER-<MOD2>)
-- -------------------------------------------------------------------------
        -- 1.3.6.1.4.1.2011.2.25.3.40.50.130.10
        odu2_tcm5Per15MCurTable OBJECT-TYPE
          SYNTAX SEQUENCE OF Odu2_tcm5Per15MCurEntry
          MAX-ACCESS not-accessible
          STATUS current
          DESCRIPTION
              "odu2_tcm5Per15MCur."
          ::= { odu2_tcm5 10 }

        -- 1.3.6.1.4.1.2011.2.25.3.40.50.130.10.1
        odu2_tcm5Per15MCurEntry OBJECT-TYPE
            SYNTAX Odu2_tcm5Per15MCurEntry
            MAX-ACCESS not-accessible
            STATUS current
            DESCRIPTION
              "odu2_tcm5Per15MCur."
            INDEX { odu2_tcm5Per15MCurEid, odu2_tcm5Per15MCurPara }
            ::= { odu2_tcm5Per15MCurTable 1 }

        Odu2_tcm5Per15MCurEntry ::=
            SEQUENCE {
                odu2_tcm5Per15MCurEid
                    PerformanceEventType,
                odu2_tcm5Per15MCurMonValue
                    OCTET STRING,
                odu2_tcm5Per15MCurVldty
                    INTEGER,
                odu2_tcm5Per15MCurDateTime
                    DateAndTime,
                odu2_tcm5Per15MCurParaLen
                    INTEGER,
                odu2_tcm5Per15MCurPara
                    OCTET STRING
            }

        -- 1.3.6.1.4.1.2011.2.25.3.40.50.130.10.1.1
        odu2_tcm5Per15MCurEid OBJECT-TYPE
            SYNTAX PerformanceEventType
            MAX-ACCESS read-only
            STATUS current
            DESCRIPTION
                "perEid."
            ::= { odu2_tcm5Per15MCurEntry 1 }

        -- 1.3.6.1.4.1.2011.2.25.3.40.50.130.10.1.2
        odu2_tcm5Per15MCurMonValue OBJECT-TYPE
            SYNTAX OCTET STRING (SIZE (0..100))
            MAX-ACCESS read-only
            STATUS current
            DESCRIPTION
                "perMonValue."
            ::= { odu2_tcm5Per15MCurEntry 2 }

        -- 1.3.6.1.4.1.2011.2.25.3.40.50.130.10.1.3
        odu2_tcm5Per15MCurVldty OBJECT-TYPE
            SYNTAX INTEGER
            MAX-ACCESS read-only
            STATUS current
            DESCRIPTION
                "perVldty. "
            ::= { odu2_tcm5Per15MCurEntry 3 }

        -- 1.3.6.1.4.1.2011.2.25.3.40.50.130.10.1.4
        odu2_tcm5Per15MCurDateTime OBJECT-TYPE
            SYNTAX DateAndTime
            MAX-ACCESS read-only
            STATUS current
            DESCRIPTION
                "perDateTime. "
            ::= { odu2_tcm5Per15MCurEntry 4 }

        -- 1.3.6.1.4.1.2011.2.25.3.40.50.130.10.1.5
        odu2_tcm5Per15MCurParaLen OBJECT-TYPE
            SYNTAX INTEGER
            MAX-ACCESS read-only
            STATUS current
            DESCRIPTION
                "perParaLen."
            ::= { odu2_tcm5Per15MCurEntry 5 }

        -- 1.3.6.1.4.1.2011.2.25.3.40.50.130.10.1.6
        odu2_tcm5Per15MCurPara OBJECT-TYPE
            SYNTAX OCTET STRING (SIZE (0..100))
            MAX-ACCESS read-only
            STATUS current
            DESCRIPTION
                "perPara."
            ::= { odu2_tcm5Per15MCurEntry 6 }




-- -------------------------------------------------------------------------
-- Perfomance 15-MIN History Data Table (RTRV-PER-<MOD2>)
-- -------------------------------------------------------------------------
        -- 1.3.6.1.4.1.2011.2.25.3.40.50.130.20
        odu2_tcm5Per15MHisTable OBJECT-TYPE
          SYNTAX SEQUENCE OF Odu2_tcm5Per15MHisEntry
          MAX-ACCESS not-accessible
          STATUS current
          DESCRIPTION
              "odu2_tcm5Per15MHis."
          ::= { odu2_tcm5 20 }

        -- 1.3.6.1.4.1.2011.2.25.3.40.50.130.20.1
        odu2_tcm5Per15MHisEntry OBJECT-TYPE
            SYNTAX Odu2_tcm5Per15MHisEntry
            MAX-ACCESS not-accessible
            STATUS current
            DESCRIPTION
                "odu2_tcm5Per15MHis."
            INDEX {odu2_tcm5Per15MHisEid, odu2_tcm5Per15MHisParaLen, odu2_tcm5Per15MHisPara, odu2_tcm5Per15MHisDateTimeStart, odu2_tcm5Per15MHisDateTimeEnd}
            ::= { odu2_tcm5Per15MHisTable 1 }

        Odu2_tcm5Per15MHisEntry ::=
            SEQUENCE {
                odu2_tcm5Per15MHisEid
                    PerformanceEventType,
                odu2_tcm5Per15MHisParaLen
                    INTEGER,
                odu2_tcm5Per15MHisPara
                    OCTET STRING,
                odu2_tcm5Per15MHisMonValue
                    OCTET STRING,
                odu2_tcm5Per15MHisDateTimeStart
                    DateAndTime,
                odu2_tcm5Per15MHisDateTimeEnd
                    DateAndTime,
                odu2_tcm5Per15MHisVldty
                    INTEGER,
             }

        -- 1.3.6.1.4.1.2011.2.25.3.40.50.130.20.1.1
        odu2_tcm5Per15MHisEid OBJECT-TYPE
            SYNTAX PerformanceEventType
            MAX-ACCESS read-only
            STATUS current
            DESCRIPTION
                "perEid."
            ::= { odu2_tcm5Per15MHisEntry 1 }

        -- 1.3.6.1.4.1.2011.2.25.3.40.50.130.20.1.2
        odu2_tcm5Per15MHisParaLen OBJECT-TYPE
            SYNTAX INTEGER
            MAX-ACCESS read-only
            STATUS current
            DESCRIPTION
                "perParaLen."
            ::= { odu2_tcm5Per15MHisEntry 2 }

        -- 1.3.6.1.4.1.2011.2.25.3.40.50.130.20.1.3
        odu2_tcm5Per15MHisPara OBJECT-TYPE
            SYNTAX OCTET STRING (SIZE (0..100))
            MAX-ACCESS read-only
            STATUS current
            DESCRIPTION
                "perPara."
            ::= { odu2_tcm5Per15MHisEntry 3 }

        -- 1.3.6.1.4.1.2011.2.25.3.40.50.130.20.1.4
        odu2_tcm5Per15MHisMonValue OBJECT-TYPE
            SYNTAX OCTET STRING (SIZE (0..100))
            MAX-ACCESS read-only
            STATUS current
            DESCRIPTION
                "perMonValue."
            ::= { odu2_tcm5Per15MHisEntry 4 }

        -- 1.3.6.1.4.1.2011.2.25.3.40.50.130.20.1.5
        odu2_tcm5Per15MHisDateTimeStart OBJECT-TYPE
            SYNTAX DateAndTime
            MAX-ACCESS read-only
            STATUS current
            DESCRIPTION
                "perDateTimeStart. "
            ::= { odu2_tcm5Per15MHisEntry 5 }

        -- 1.3.6.1.4.1.2011.2.25.3.40.50.130.20.1.6
        odu2_tcm5Per15MHisDateTimeEnd OBJECT-TYPE
            SYNTAX DateAndTime
            MAX-ACCESS read-only
            STATUS current
            DESCRIPTION
                "perDateTimeEnd. "
            ::= { odu2_tcm5Per15MHisEntry 6 }

        -- 1.3.6.1.4.1.2011.2.25.3.40.50.130.20.1.7
        odu2_tcm5Per15MHisVldty OBJECT-TYPE
            SYNTAX INTEGER
            MAX-ACCESS read-only
            STATUS current
            DESCRIPTION
                "perVldty. "
            ::= { odu2_tcm5Per15MHisEntry 7 }




-- -------------------------------------------------------------------------
-- Perfomance 24-HOUR Current Data Table (RTRV-PER-<MOD2>)
-- -------------------------------------------------------------------------
        -- 1.3.6.1.4.1.2011.2.25.3.40.50.130.30
        odu2_tcm5Per24HCurTable OBJECT-TYPE
          SYNTAX SEQUENCE OF Odu2_tcm5Per24HCurEntry
          MAX-ACCESS not-accessible
          STATUS current
          DESCRIPTION
              "odu2_tcm5Per24HCur."
          ::= { odu2_tcm5 30 }

        -- 1.3.6.1.4.1.2011.2.25.3.40.50.130.30.1
        odu2_tcm5Per24HCurEntry OBJECT-TYPE
            SYNTAX Odu2_tcm5Per24HCurEntry
            MAX-ACCESS not-accessible
            STATUS current
            DESCRIPTION
              "odu2_tcm5Per24HCur."
            INDEX { odu2_tcm5Per24HCurEid, odu2_tcm5Per24HCurPara }
            ::= { odu2_tcm5Per24HCurTable 1 }

        Odu2_tcm5Per24HCurEntry ::=
            SEQUENCE {
                odu2_tcm5Per24HCurEid
                    PerformanceEventType,
                odu2_tcm5Per24HCurMonValue
                    OCTET STRING,
                odu2_tcm5Per24HCurVldty
                    INTEGER,
                odu2_tcm5Per24HCurDateTime
                    DateAndTime,
                odu2_tcm5Per24HCurParaLen
                    INTEGER,
                odu2_tcm5Per24HCurPara
                    OCTET STRING
            }

        -- 1.3.6.1.4.1.2011.2.25.3.40.50.130.30.1.1
        odu2_tcm5Per24HCurEid OBJECT-TYPE
            SYNTAX PerformanceEventType
            MAX-ACCESS read-only
            STATUS current
            DESCRIPTION
                "perEid."
            ::= { odu2_tcm5Per24HCurEntry 1 }

        -- 1.3.6.1.4.1.2011.2.25.3.40.50.130.30.1.2
        odu2_tcm5Per24HCurMonValue OBJECT-TYPE
            SYNTAX OCTET STRING (SIZE (0..100))
            MAX-ACCESS read-only
            STATUS current
            DESCRIPTION
                "perMonValue."
            ::= { odu2_tcm5Per24HCurEntry 2 }

        -- 1.3.6.1.4.1.2011.2.25.3.40.50.130.30.1.3
        odu2_tcm5Per24HCurVldty OBJECT-TYPE
            SYNTAX INTEGER
            MAX-ACCESS read-only
            STATUS current
            DESCRIPTION
                "perVldty. "
            ::= { odu2_tcm5Per24HCurEntry 3 }

        -- 1.3.6.1.4.1.2011.2.25.3.40.50.130.30.1.4
        odu2_tcm5Per24HCurDateTime OBJECT-TYPE
            SYNTAX DateAndTime
            MAX-ACCESS read-only
            STATUS current
            DESCRIPTION
                "perDateTime. "
            ::= { odu2_tcm5Per24HCurEntry 4 }

        -- 1.3.6.1.4.1.2011.2.25.3.40.50.130.30.1.5
        odu2_tcm5Per24HCurParaLen OBJECT-TYPE
            SYNTAX INTEGER
            MAX-ACCESS read-only
            STATUS current
            DESCRIPTION
                "perParaLen."
            ::= { odu2_tcm5Per24HCurEntry 5 }

        -- 1.3.6.1.4.1.2011.2.25.3.40.50.130.30.1.6
        odu2_tcm5Per24HCurPara OBJECT-TYPE
            SYNTAX OCTET STRING (SIZE (0..100))
            MAX-ACCESS read-only
            STATUS current
            DESCRIPTION
                "perPara."
            ::= { odu2_tcm5Per24HCurEntry 6 }




-- -------------------------------------------------------------------------
-- Perfomance 24-HOUR History Data Table (RTRV-PER-<MOD2>)
-- -------------------------------------------------------------------------
        -- 1.3.6.1.4.1.2011.2.25.3.40.50.130.40
        odu2_tcm5Per24HHisTable OBJECT-TYPE
          SYNTAX SEQUENCE OF Odu2_tcm5Per24HHisEntry
          MAX-ACCESS not-accessible
          STATUS current
          DESCRIPTION
              "odu2_tcm5Per24HHis."
          ::= { odu2_tcm5 40 }

        -- 1.3.6.1.4.1.2011.2.25.3.40.50.130.40.1
        odu2_tcm5Per24HHisEntry OBJECT-TYPE
            SYNTAX Odu2_tcm5Per24HHisEntry
            MAX-ACCESS not-accessible
            STATUS current
            DESCRIPTION
                "odu2_tcm5Per24HHis."
            INDEX {odu2_tcm5Per24HHisEid, odu2_tcm5Per24HHisParaLen, odu2_tcm5Per24HHisPara, odu2_tcm5Per24HHisDateTimeStart, odu2_tcm5Per24HHisDateTimeEnd}
            ::= { odu2_tcm5Per24HHisTable 1 }

        Odu2_tcm5Per24HHisEntry ::=
            SEQUENCE {
                odu2_tcm5Per24HHisEid
                    PerformanceEventType,
                odu2_tcm5Per24HHisParaLen
                    INTEGER,
                odu2_tcm5Per24HHisPara
                    OCTET STRING,
                odu2_tcm5Per24HHisMonValue
                    OCTET STRING,
                odu2_tcm5Per24HHisDateTimeStart
                    DateAndTime,
                odu2_tcm5Per24HHisDateTimeEnd
                    DateAndTime,
                odu2_tcm5Per24HHisVldty
                    INTEGER,
             }

        -- 1.3.6.1.4.1.2011.2.25.3.40.50.130.40.1.1
        odu2_tcm5Per24HHisEid OBJECT-TYPE
            SYNTAX PerformanceEventType
            MAX-ACCESS read-only
            STATUS current
            DESCRIPTION
                "perEid."
            ::= { odu2_tcm5Per24HHisEntry 1 }

        -- 1.3.6.1.4.1.2011.2.25.3.40.50.130.40.1.2
        odu2_tcm5Per24HHisParaLen OBJECT-TYPE
            SYNTAX INTEGER
            MAX-ACCESS read-only
            STATUS current
            DESCRIPTION
                "perParaLen."
            ::= { odu2_tcm5Per24HHisEntry 2 }

        -- 1.3.6.1.4.1.2011.2.25.3.40.50.130.40.1.3
        odu2_tcm5Per24HHisPara OBJECT-TYPE
            SYNTAX OCTET STRING (SIZE (0..100))
            MAX-ACCESS read-only
            STATUS current
            DESCRIPTION
                "perPara."
            ::= { odu2_tcm5Per24HHisEntry 3 }

        -- 1.3.6.1.4.1.2011.2.25.3.40.50.130.40.1.4
        odu2_tcm5Per24HHisMonValue OBJECT-TYPE
            SYNTAX OCTET STRING (SIZE (0..100))
            MAX-ACCESS read-only
            STATUS current
            DESCRIPTION
                "perMonValue."
            ::= { odu2_tcm5Per24HHisEntry 4 }

        -- 1.3.6.1.4.1.2011.2.25.3.40.50.130.40.1.5
        odu2_tcm5Per24HHisDateTimeStart OBJECT-TYPE
            SYNTAX DateAndTime
            MAX-ACCESS read-only
            STATUS current
            DESCRIPTION
                "perDateTimeStart. "
            ::= { odu2_tcm5Per24HHisEntry 5 }

        -- 1.3.6.1.4.1.2011.2.25.3.40.50.130.40.1.6
        odu2_tcm5Per24HHisDateTimeEnd OBJECT-TYPE
            SYNTAX DateAndTime
            MAX-ACCESS read-only
            STATUS current
            DESCRIPTION
                "perDateTimeEnd. "
            ::= { odu2_tcm5Per24HHisEntry 6 }

        -- 1.3.6.1.4.1.2011.2.25.3.40.50.130.40.1.7
        odu2_tcm5Per24HHisVldty OBJECT-TYPE
            SYNTAX INTEGER
            MAX-ACCESS read-only
            STATUS current
            DESCRIPTION
                "perVldty. "
            ::= { odu2_tcm5Per24HHisEntry 7 }




-- Alarm data
      -- 1.3.6.1.4.1.2011.2.25.3.40.50.131
      odu2_tcm6 OBJECT IDENTIFIER ::={ optixGlobalNGWDM 131 }


-- -------------------------------------------------------------------------
-- Perfomance 15-MIN Current Data Table (RTRV-PER-<MOD2>)
-- -------------------------------------------------------------------------
        -- 1.3.6.1.4.1.2011.2.25.3.40.50.131.10
        odu2_tcm6Per15MCurTable OBJECT-TYPE
          SYNTAX SEQUENCE OF Odu2_tcm6Per15MCurEntry
          MAX-ACCESS not-accessible
          STATUS current
          DESCRIPTION
              "odu2_tcm6Per15MCur."
          ::= { odu2_tcm6 10 }

        -- 1.3.6.1.4.1.2011.2.25.3.40.50.131.10.1
        odu2_tcm6Per15MCurEntry OBJECT-TYPE
            SYNTAX Odu2_tcm6Per15MCurEntry
            MAX-ACCESS not-accessible
            STATUS current
            DESCRIPTION
              "odu2_tcm6Per15MCur."
            INDEX { odu2_tcm6Per15MCurEid, odu2_tcm6Per15MCurPara }
            ::= { odu2_tcm6Per15MCurTable 1 }

        Odu2_tcm6Per15MCurEntry ::=
            SEQUENCE {
                odu2_tcm6Per15MCurEid
                    PerformanceEventType,
                odu2_tcm6Per15MCurMonValue
                    OCTET STRING,
                odu2_tcm6Per15MCurVldty
                    INTEGER,
                odu2_tcm6Per15MCurDateTime
                    DateAndTime,
                odu2_tcm6Per15MCurParaLen
                    INTEGER,
                odu2_tcm6Per15MCurPara
                    OCTET STRING
            }

        -- 1.3.6.1.4.1.2011.2.25.3.40.50.131.10.1.1
        odu2_tcm6Per15MCurEid OBJECT-TYPE
            SYNTAX PerformanceEventType
            MAX-ACCESS read-only
            STATUS current
            DESCRIPTION
                "perEid."
            ::= { odu2_tcm6Per15MCurEntry 1 }

        -- 1.3.6.1.4.1.2011.2.25.3.40.50.131.10.1.2
        odu2_tcm6Per15MCurMonValue OBJECT-TYPE
            SYNTAX OCTET STRING (SIZE (0..100))
            MAX-ACCESS read-only
            STATUS current
            DESCRIPTION
                "perMonValue."
            ::= { odu2_tcm6Per15MCurEntry 2 }

        -- 1.3.6.1.4.1.2011.2.25.3.40.50.131.10.1.3
        odu2_tcm6Per15MCurVldty OBJECT-TYPE
            SYNTAX INTEGER
            MAX-ACCESS read-only
            STATUS current
            DESCRIPTION
                "perVldty. "
            ::= { odu2_tcm6Per15MCurEntry 3 }

        -- 1.3.6.1.4.1.2011.2.25.3.40.50.131.10.1.4
        odu2_tcm6Per15MCurDateTime OBJECT-TYPE
            SYNTAX DateAndTime
            MAX-ACCESS read-only
            STATUS current
            DESCRIPTION
                "perDateTime. "
            ::= { odu2_tcm6Per15MCurEntry 4 }

        -- 1.3.6.1.4.1.2011.2.25.3.40.50.131.10.1.5
        odu2_tcm6Per15MCurParaLen OBJECT-TYPE
            SYNTAX INTEGER
            MAX-ACCESS read-only
            STATUS current
            DESCRIPTION
                "perParaLen."
            ::= { odu2_tcm6Per15MCurEntry 5 }

        -- 1.3.6.1.4.1.2011.2.25.3.40.50.131.10.1.6
        odu2_tcm6Per15MCurPara OBJECT-TYPE
            SYNTAX OCTET STRING (SIZE (0..100))
            MAX-ACCESS read-only
            STATUS current
            DESCRIPTION
                "perPara."
            ::= { odu2_tcm6Per15MCurEntry 6 }




-- -------------------------------------------------------------------------
-- Perfomance 15-MIN History Data Table (RTRV-PER-<MOD2>)
-- -------------------------------------------------------------------------
        -- 1.3.6.1.4.1.2011.2.25.3.40.50.131.20
        odu2_tcm6Per15MHisTable OBJECT-TYPE
          SYNTAX SEQUENCE OF Odu2_tcm6Per15MHisEntry
          MAX-ACCESS not-accessible
          STATUS current
          DESCRIPTION
              "odu2_tcm6Per15MHis."
          ::= { odu2_tcm6 20 }

        -- 1.3.6.1.4.1.2011.2.25.3.40.50.131.20.1
        odu2_tcm6Per15MHisEntry OBJECT-TYPE
            SYNTAX Odu2_tcm6Per15MHisEntry
            MAX-ACCESS not-accessible
            STATUS current
            DESCRIPTION
                "odu2_tcm6Per15MHis."
            INDEX {odu2_tcm6Per15MHisEid, odu2_tcm6Per15MHisParaLen, odu2_tcm6Per15MHisPara, odu2_tcm6Per15MHisDateTimeStart, odu2_tcm6Per15MHisDateTimeEnd}
            ::= { odu2_tcm6Per15MHisTable 1 }

        Odu2_tcm6Per15MHisEntry ::=
            SEQUENCE {
                odu2_tcm6Per15MHisEid
                    PerformanceEventType,
                odu2_tcm6Per15MHisParaLen
                    INTEGER,
                odu2_tcm6Per15MHisPara
                    OCTET STRING,
                odu2_tcm6Per15MHisMonValue
                    OCTET STRING,
                odu2_tcm6Per15MHisDateTimeStart
                    DateAndTime,
                odu2_tcm6Per15MHisDateTimeEnd
                    DateAndTime,
                odu2_tcm6Per15MHisVldty
                    INTEGER,
             }

        -- 1.3.6.1.4.1.2011.2.25.3.40.50.131.20.1.1
        odu2_tcm6Per15MHisEid OBJECT-TYPE
            SYNTAX PerformanceEventType
            MAX-ACCESS read-only
            STATUS current
            DESCRIPTION
                "perEid."
            ::= { odu2_tcm6Per15MHisEntry 1 }

        -- 1.3.6.1.4.1.2011.2.25.3.40.50.131.20.1.2
        odu2_tcm6Per15MHisParaLen OBJECT-TYPE
            SYNTAX INTEGER
            MAX-ACCESS read-only
            STATUS current
            DESCRIPTION
                "perParaLen."
            ::= { odu2_tcm6Per15MHisEntry 2 }

        -- 1.3.6.1.4.1.2011.2.25.3.40.50.131.20.1.3
        odu2_tcm6Per15MHisPara OBJECT-TYPE
            SYNTAX OCTET STRING (SIZE (0..100))
            MAX-ACCESS read-only
            STATUS current
            DESCRIPTION
                "perPara."
            ::= { odu2_tcm6Per15MHisEntry 3 }

        -- 1.3.6.1.4.1.2011.2.25.3.40.50.131.20.1.4
        odu2_tcm6Per15MHisMonValue OBJECT-TYPE
            SYNTAX OCTET STRING (SIZE (0..100))
            MAX-ACCESS read-only
            STATUS current
            DESCRIPTION
                "perMonValue."
            ::= { odu2_tcm6Per15MHisEntry 4 }

        -- 1.3.6.1.4.1.2011.2.25.3.40.50.131.20.1.5
        odu2_tcm6Per15MHisDateTimeStart OBJECT-TYPE
            SYNTAX DateAndTime
            MAX-ACCESS read-only
            STATUS current
            DESCRIPTION
                "perDateTimeStart. "
            ::= { odu2_tcm6Per15MHisEntry 5 }

        -- 1.3.6.1.4.1.2011.2.25.3.40.50.131.20.1.6
        odu2_tcm6Per15MHisDateTimeEnd OBJECT-TYPE
            SYNTAX DateAndTime
            MAX-ACCESS read-only
            STATUS current
            DESCRIPTION
                "perDateTimeEnd. "
            ::= { odu2_tcm6Per15MHisEntry 6 }

        -- 1.3.6.1.4.1.2011.2.25.3.40.50.131.20.1.7
        odu2_tcm6Per15MHisVldty OBJECT-TYPE
            SYNTAX INTEGER
            MAX-ACCESS read-only
            STATUS current
            DESCRIPTION
                "perVldty. "
            ::= { odu2_tcm6Per15MHisEntry 7 }




-- -------------------------------------------------------------------------
-- Perfomance 24-HOUR Current Data Table (RTRV-PER-<MOD2>)
-- -------------------------------------------------------------------------
        -- 1.3.6.1.4.1.2011.2.25.3.40.50.131.30
        odu2_tcm6Per24HCurTable OBJECT-TYPE
          SYNTAX SEQUENCE OF Odu2_tcm6Per24HCurEntry
          MAX-ACCESS not-accessible
          STATUS current
          DESCRIPTION
              "odu2_tcm6Per24HCur."
          ::= { odu2_tcm6 30 }

        -- 1.3.6.1.4.1.2011.2.25.3.40.50.131.30.1
        odu2_tcm6Per24HCurEntry OBJECT-TYPE
            SYNTAX Odu2_tcm6Per24HCurEntry
            MAX-ACCESS not-accessible
            STATUS current
            DESCRIPTION
              "odu2_tcm6Per24HCur."
            INDEX { odu2_tcm6Per24HCurEid, odu2_tcm6Per24HCurPara }
            ::= { odu2_tcm6Per24HCurTable 1 }

        Odu2_tcm6Per24HCurEntry ::=
            SEQUENCE {
                odu2_tcm6Per24HCurEid
                    PerformanceEventType,
                odu2_tcm6Per24HCurMonValue
                    OCTET STRING,
                odu2_tcm6Per24HCurVldty
                    INTEGER,
                odu2_tcm6Per24HCurDateTime
                    DateAndTime,
                odu2_tcm6Per24HCurParaLen
                    INTEGER,
                odu2_tcm6Per24HCurPara
                    OCTET STRING
            }

        -- 1.3.6.1.4.1.2011.2.25.3.40.50.131.30.1.1
        odu2_tcm6Per24HCurEid OBJECT-TYPE
            SYNTAX PerformanceEventType
            MAX-ACCESS read-only
            STATUS current
            DESCRIPTION
                "perEid."
            ::= { odu2_tcm6Per24HCurEntry 1 }

        -- 1.3.6.1.4.1.2011.2.25.3.40.50.131.30.1.2
        odu2_tcm6Per24HCurMonValue OBJECT-TYPE
            SYNTAX OCTET STRING (SIZE (0..100))
            MAX-ACCESS read-only
            STATUS current
            DESCRIPTION
                "perMonValue."
            ::= { odu2_tcm6Per24HCurEntry 2 }

        -- 1.3.6.1.4.1.2011.2.25.3.40.50.131.30.1.3
        odu2_tcm6Per24HCurVldty OBJECT-TYPE
            SYNTAX INTEGER
            MAX-ACCESS read-only
            STATUS current
            DESCRIPTION
                "perVldty. "
            ::= { odu2_tcm6Per24HCurEntry 3 }

        -- 1.3.6.1.4.1.2011.2.25.3.40.50.131.30.1.4
        odu2_tcm6Per24HCurDateTime OBJECT-TYPE
            SYNTAX DateAndTime
            MAX-ACCESS read-only
            STATUS current
            DESCRIPTION
                "perDateTime. "
            ::= { odu2_tcm6Per24HCurEntry 4 }

        -- 1.3.6.1.4.1.2011.2.25.3.40.50.131.30.1.5
        odu2_tcm6Per24HCurParaLen OBJECT-TYPE
            SYNTAX INTEGER
            MAX-ACCESS read-only
            STATUS current
            DESCRIPTION
                "perParaLen."
            ::= { odu2_tcm6Per24HCurEntry 5 }

        -- 1.3.6.1.4.1.2011.2.25.3.40.50.131.30.1.6
        odu2_tcm6Per24HCurPara OBJECT-TYPE
            SYNTAX OCTET STRING (SIZE (0..100))
            MAX-ACCESS read-only
            STATUS current
            DESCRIPTION
                "perPara."
            ::= { odu2_tcm6Per24HCurEntry 6 }




-- -------------------------------------------------------------------------
-- Perfomance 24-HOUR History Data Table (RTRV-PER-<MOD2>)
-- -------------------------------------------------------------------------
        -- 1.3.6.1.4.1.2011.2.25.3.40.50.131.40
        odu2_tcm6Per24HHisTable OBJECT-TYPE
          SYNTAX SEQUENCE OF Odu2_tcm6Per24HHisEntry
          MAX-ACCESS not-accessible
          STATUS current
          DESCRIPTION
              "odu2_tcm6Per24HHis."
          ::= { odu2_tcm6 40 }

        -- 1.3.6.1.4.1.2011.2.25.3.40.50.131.40.1
        odu2_tcm6Per24HHisEntry OBJECT-TYPE
            SYNTAX Odu2_tcm6Per24HHisEntry
            MAX-ACCESS not-accessible
            STATUS current
            DESCRIPTION
                "odu2_tcm6Per24HHis."
            INDEX {odu2_tcm6Per24HHisEid, odu2_tcm6Per24HHisParaLen, odu2_tcm6Per24HHisPara, odu2_tcm6Per24HHisDateTimeStart, odu2_tcm6Per24HHisDateTimeEnd}
            ::= { odu2_tcm6Per24HHisTable 1 }

        Odu2_tcm6Per24HHisEntry ::=
            SEQUENCE {
                odu2_tcm6Per24HHisEid
                    PerformanceEventType,
                odu2_tcm6Per24HHisParaLen
                    INTEGER,
                odu2_tcm6Per24HHisPara
                    OCTET STRING,
                odu2_tcm6Per24HHisMonValue
                    OCTET STRING,
                odu2_tcm6Per24HHisDateTimeStart
                    DateAndTime,
                odu2_tcm6Per24HHisDateTimeEnd
                    DateAndTime,
                odu2_tcm6Per24HHisVldty
                    INTEGER,
             }

        -- 1.3.6.1.4.1.2011.2.25.3.40.50.131.40.1.1
        odu2_tcm6Per24HHisEid OBJECT-TYPE
            SYNTAX PerformanceEventType
            MAX-ACCESS read-only
            STATUS current
            DESCRIPTION
                "perEid."
            ::= { odu2_tcm6Per24HHisEntry 1 }

        -- 1.3.6.1.4.1.2011.2.25.3.40.50.131.40.1.2
        odu2_tcm6Per24HHisParaLen OBJECT-TYPE
            SYNTAX INTEGER
            MAX-ACCESS read-only
            STATUS current
            DESCRIPTION
                "perParaLen."
            ::= { odu2_tcm6Per24HHisEntry 2 }

        -- 1.3.6.1.4.1.2011.2.25.3.40.50.131.40.1.3
        odu2_tcm6Per24HHisPara OBJECT-TYPE
            SYNTAX OCTET STRING (SIZE (0..100))
            MAX-ACCESS read-only
            STATUS current
            DESCRIPTION
                "perPara."
            ::= { odu2_tcm6Per24HHisEntry 3 }

        -- 1.3.6.1.4.1.2011.2.25.3.40.50.131.40.1.4
        odu2_tcm6Per24HHisMonValue OBJECT-TYPE
            SYNTAX OCTET STRING (SIZE (0..100))
            MAX-ACCESS read-only
            STATUS current
            DESCRIPTION
                "perMonValue."
            ::= { odu2_tcm6Per24HHisEntry 4 }

        -- 1.3.6.1.4.1.2011.2.25.3.40.50.131.40.1.5
        odu2_tcm6Per24HHisDateTimeStart OBJECT-TYPE
            SYNTAX DateAndTime
            MAX-ACCESS read-only
            STATUS current
            DESCRIPTION
                "perDateTimeStart. "
            ::= { odu2_tcm6Per24HHisEntry 5 }

        -- 1.3.6.1.4.1.2011.2.25.3.40.50.131.40.1.6
        odu2_tcm6Per24HHisDateTimeEnd OBJECT-TYPE
            SYNTAX DateAndTime
            MAX-ACCESS read-only
            STATUS current
            DESCRIPTION
                "perDateTimeEnd. "
            ::= { odu2_tcm6Per24HHisEntry 6 }

        -- 1.3.6.1.4.1.2011.2.25.3.40.50.131.40.1.7
        odu2_tcm6Per24HHisVldty OBJECT-TYPE
            SYNTAX INTEGER
            MAX-ACCESS read-only
            STATUS current
            DESCRIPTION
                "perVldty. "
            ::= { odu2_tcm6Per24HHisEntry 7 }




-- Alarm data
      -- 1.3.6.1.4.1.2011.2.25.3.40.50.132
      odu3_tcm1 OBJECT IDENTIFIER ::={ optixGlobalNGWDM 132 }


-- -------------------------------------------------------------------------
-- Perfomance 15-MIN Current Data Table (RTRV-PER-<MOD2>)
-- -------------------------------------------------------------------------
        -- 1.3.6.1.4.1.2011.2.25.3.40.50.132.10
        odu3_tcm1Per15MCurTable OBJECT-TYPE
          SYNTAX SEQUENCE OF Odu3_tcm1Per15MCurEntry
          MAX-ACCESS not-accessible
          STATUS current
          DESCRIPTION
              "odu3_tcm1Per15MCur."
          ::= { odu3_tcm1 10 }

        -- 1.3.6.1.4.1.2011.2.25.3.40.50.132.10.1
        odu3_tcm1Per15MCurEntry OBJECT-TYPE
            SYNTAX Odu3_tcm1Per15MCurEntry
            MAX-ACCESS not-accessible
            STATUS current
            DESCRIPTION
              "odu3_tcm1Per15MCur."
            INDEX { odu3_tcm1Per15MCurEid, odu3_tcm1Per15MCurPara }
            ::= { odu3_tcm1Per15MCurTable 1 }

        Odu3_tcm1Per15MCurEntry ::=
            SEQUENCE {
                odu3_tcm1Per15MCurEid
                    PerformanceEventType,
                odu3_tcm1Per15MCurMonValue
                    OCTET STRING,
                odu3_tcm1Per15MCurVldty
                    INTEGER,
                odu3_tcm1Per15MCurDateTime
                    DateAndTime,
                odu3_tcm1Per15MCurParaLen
                    INTEGER,
                odu3_tcm1Per15MCurPara
                    OCTET STRING
            }

        -- 1.3.6.1.4.1.2011.2.25.3.40.50.132.10.1.1
        odu3_tcm1Per15MCurEid OBJECT-TYPE
            SYNTAX PerformanceEventType
            MAX-ACCESS read-only
            STATUS current
            DESCRIPTION
                "perEid."
            ::= { odu3_tcm1Per15MCurEntry 1 }

        -- 1.3.6.1.4.1.2011.2.25.3.40.50.132.10.1.2
        odu3_tcm1Per15MCurMonValue OBJECT-TYPE
            SYNTAX OCTET STRING (SIZE (0..100))
            MAX-ACCESS read-only
            STATUS current
            DESCRIPTION
                "perMonValue."
            ::= { odu3_tcm1Per15MCurEntry 2 }

        -- 1.3.6.1.4.1.2011.2.25.3.40.50.132.10.1.3
        odu3_tcm1Per15MCurVldty OBJECT-TYPE
            SYNTAX INTEGER
            MAX-ACCESS read-only
            STATUS current
            DESCRIPTION
                "perVldty. "
            ::= { odu3_tcm1Per15MCurEntry 3 }

        -- 1.3.6.1.4.1.2011.2.25.3.40.50.132.10.1.4
        odu3_tcm1Per15MCurDateTime OBJECT-TYPE
            SYNTAX DateAndTime
            MAX-ACCESS read-only
            STATUS current
            DESCRIPTION
                "perDateTime. "
            ::= { odu3_tcm1Per15MCurEntry 4 }

        -- 1.3.6.1.4.1.2011.2.25.3.40.50.132.10.1.5
        odu3_tcm1Per15MCurParaLen OBJECT-TYPE
            SYNTAX INTEGER
            MAX-ACCESS read-only
            STATUS current
            DESCRIPTION
                "perParaLen."
            ::= { odu3_tcm1Per15MCurEntry 5 }

        -- 1.3.6.1.4.1.2011.2.25.3.40.50.132.10.1.6
        odu3_tcm1Per15MCurPara OBJECT-TYPE
            SYNTAX OCTET STRING (SIZE (0..100))
            MAX-ACCESS read-only
            STATUS current
            DESCRIPTION
                "perPara."
            ::= { odu3_tcm1Per15MCurEntry 6 }




-- -------------------------------------------------------------------------
-- Perfomance 15-MIN History Data Table (RTRV-PER-<MOD2>)
-- -------------------------------------------------------------------------
        -- 1.3.6.1.4.1.2011.2.25.3.40.50.132.20
        odu3_tcm1Per15MHisTable OBJECT-TYPE
          SYNTAX SEQUENCE OF Odu3_tcm1Per15MHisEntry
          MAX-ACCESS not-accessible
          STATUS current
          DESCRIPTION
              "odu3_tcm1Per15MHis."
          ::= { odu3_tcm1 20 }

        -- 1.3.6.1.4.1.2011.2.25.3.40.50.132.20.1
        odu3_tcm1Per15MHisEntry OBJECT-TYPE
            SYNTAX Odu3_tcm1Per15MHisEntry
            MAX-ACCESS not-accessible
            STATUS current
            DESCRIPTION
                "odu3_tcm1Per15MHis."
            INDEX {odu3_tcm1Per15MHisEid, odu3_tcm1Per15MHisParaLen, odu3_tcm1Per15MHisPara, odu3_tcm1Per15MHisDateTimeStart, odu3_tcm1Per15MHisDateTimeEnd}
            ::= { odu3_tcm1Per15MHisTable 1 }

        Odu3_tcm1Per15MHisEntry ::=
            SEQUENCE {
                odu3_tcm1Per15MHisEid
                    PerformanceEventType,
                odu3_tcm1Per15MHisParaLen
                    INTEGER,
                odu3_tcm1Per15MHisPara
                    OCTET STRING,
                odu3_tcm1Per15MHisMonValue
                    OCTET STRING,
                odu3_tcm1Per15MHisDateTimeStart
                    DateAndTime,
                odu3_tcm1Per15MHisDateTimeEnd
                    DateAndTime,
                odu3_tcm1Per15MHisVldty
                    INTEGER,
             }

        -- 1.3.6.1.4.1.2011.2.25.3.40.50.132.20.1.1
        odu3_tcm1Per15MHisEid OBJECT-TYPE
            SYNTAX PerformanceEventType
            MAX-ACCESS read-only
            STATUS current
            DESCRIPTION
                "perEid."
            ::= { odu3_tcm1Per15MHisEntry 1 }

        -- 1.3.6.1.4.1.2011.2.25.3.40.50.132.20.1.2
        odu3_tcm1Per15MHisParaLen OBJECT-TYPE
            SYNTAX INTEGER
            MAX-ACCESS read-only
            STATUS current
            DESCRIPTION
                "perParaLen."
            ::= { odu3_tcm1Per15MHisEntry 2 }

        -- 1.3.6.1.4.1.2011.2.25.3.40.50.132.20.1.3
        odu3_tcm1Per15MHisPara OBJECT-TYPE
            SYNTAX OCTET STRING (SIZE (0..100))
            MAX-ACCESS read-only
            STATUS current
            DESCRIPTION
                "perPara."
            ::= { odu3_tcm1Per15MHisEntry 3 }

        -- 1.3.6.1.4.1.2011.2.25.3.40.50.132.20.1.4
        odu3_tcm1Per15MHisMonValue OBJECT-TYPE
            SYNTAX OCTET STRING (SIZE (0..100))
            MAX-ACCESS read-only
            STATUS current
            DESCRIPTION
                "perMonValue."
            ::= { odu3_tcm1Per15MHisEntry 4 }

        -- 1.3.6.1.4.1.2011.2.25.3.40.50.132.20.1.5
        odu3_tcm1Per15MHisDateTimeStart OBJECT-TYPE
            SYNTAX DateAndTime
            MAX-ACCESS read-only
            STATUS current
            DESCRIPTION
                "perDateTimeStart. "
            ::= { odu3_tcm1Per15MHisEntry 5 }

        -- 1.3.6.1.4.1.2011.2.25.3.40.50.132.20.1.6
        odu3_tcm1Per15MHisDateTimeEnd OBJECT-TYPE
            SYNTAX DateAndTime
            MAX-ACCESS read-only
            STATUS current
            DESCRIPTION
                "perDateTimeEnd. "
            ::= { odu3_tcm1Per15MHisEntry 6 }

        -- 1.3.6.1.4.1.2011.2.25.3.40.50.132.20.1.7
        odu3_tcm1Per15MHisVldty OBJECT-TYPE
            SYNTAX INTEGER
            MAX-ACCESS read-only
            STATUS current
            DESCRIPTION
                "perVldty. "
            ::= { odu3_tcm1Per15MHisEntry 7 }




-- -------------------------------------------------------------------------
-- Perfomance 24-HOUR Current Data Table (RTRV-PER-<MOD2>)
-- -------------------------------------------------------------------------
        -- 1.3.6.1.4.1.2011.2.25.3.40.50.132.30
        odu3_tcm1Per24HCurTable OBJECT-TYPE
          SYNTAX SEQUENCE OF Odu3_tcm1Per24HCurEntry
          MAX-ACCESS not-accessible
          STATUS current
          DESCRIPTION
              "odu3_tcm1Per24HCur."
          ::= { odu3_tcm1 30 }

        -- 1.3.6.1.4.1.2011.2.25.3.40.50.132.30.1
        odu3_tcm1Per24HCurEntry OBJECT-TYPE
            SYNTAX Odu3_tcm1Per24HCurEntry
            MAX-ACCESS not-accessible
            STATUS current
            DESCRIPTION
              "odu3_tcm1Per24HCur."
            INDEX { odu3_tcm1Per24HCurEid, odu3_tcm1Per24HCurPara }
            ::= { odu3_tcm1Per24HCurTable 1 }

        Odu3_tcm1Per24HCurEntry ::=
            SEQUENCE {
                odu3_tcm1Per24HCurEid
                    PerformanceEventType,
                odu3_tcm1Per24HCurMonValue
                    OCTET STRING,
                odu3_tcm1Per24HCurVldty
                    INTEGER,
                odu3_tcm1Per24HCurDateTime
                    DateAndTime,
                odu3_tcm1Per24HCurParaLen
                    INTEGER,
                odu3_tcm1Per24HCurPara
                    OCTET STRING
            }

        -- 1.3.6.1.4.1.2011.2.25.3.40.50.132.30.1.1
        odu3_tcm1Per24HCurEid OBJECT-TYPE
            SYNTAX PerformanceEventType
            MAX-ACCESS read-only
            STATUS current
            DESCRIPTION
                "perEid."
            ::= { odu3_tcm1Per24HCurEntry 1 }

        -- 1.3.6.1.4.1.2011.2.25.3.40.50.132.30.1.2
        odu3_tcm1Per24HCurMonValue OBJECT-TYPE
            SYNTAX OCTET STRING (SIZE (0..100))
            MAX-ACCESS read-only
            STATUS current
            DESCRIPTION
                "perMonValue."
            ::= { odu3_tcm1Per24HCurEntry 2 }

        -- 1.3.6.1.4.1.2011.2.25.3.40.50.132.30.1.3
        odu3_tcm1Per24HCurVldty OBJECT-TYPE
            SYNTAX INTEGER
            MAX-ACCESS read-only
            STATUS current
            DESCRIPTION
                "perVldty. "
            ::= { odu3_tcm1Per24HCurEntry 3 }

        -- 1.3.6.1.4.1.2011.2.25.3.40.50.132.30.1.4
        odu3_tcm1Per24HCurDateTime OBJECT-TYPE
            SYNTAX DateAndTime
            MAX-ACCESS read-only
            STATUS current
            DESCRIPTION
                "perDateTime. "
            ::= { odu3_tcm1Per24HCurEntry 4 }

        -- 1.3.6.1.4.1.2011.2.25.3.40.50.132.30.1.5
        odu3_tcm1Per24HCurParaLen OBJECT-TYPE
            SYNTAX INTEGER
            MAX-ACCESS read-only
            STATUS current
            DESCRIPTION
                "perParaLen."
            ::= { odu3_tcm1Per24HCurEntry 5 }

        -- 1.3.6.1.4.1.2011.2.25.3.40.50.132.30.1.6
        odu3_tcm1Per24HCurPara OBJECT-TYPE
            SYNTAX OCTET STRING (SIZE (0..100))
            MAX-ACCESS read-only
            STATUS current
            DESCRIPTION
                "perPara."
            ::= { odu3_tcm1Per24HCurEntry 6 }




-- -------------------------------------------------------------------------
-- Perfomance 24-HOUR History Data Table (RTRV-PER-<MOD2>)
-- -------------------------------------------------------------------------
        -- 1.3.6.1.4.1.2011.2.25.3.40.50.132.40
        odu3_tcm1Per24HHisTable OBJECT-TYPE
          SYNTAX SEQUENCE OF Odu3_tcm1Per24HHisEntry
          MAX-ACCESS not-accessible
          STATUS current
          DESCRIPTION
              "odu3_tcm1Per24HHis."
          ::= { odu3_tcm1 40 }

        -- 1.3.6.1.4.1.2011.2.25.3.40.50.132.40.1
        odu3_tcm1Per24HHisEntry OBJECT-TYPE
            SYNTAX Odu3_tcm1Per24HHisEntry
            MAX-ACCESS not-accessible
            STATUS current
            DESCRIPTION
                "odu3_tcm1Per24HHis."
            INDEX {odu3_tcm1Per24HHisEid, odu3_tcm1Per24HHisParaLen, odu3_tcm1Per24HHisPara, odu3_tcm1Per24HHisDateTimeStart, odu3_tcm1Per24HHisDateTimeEnd}
            ::= { odu3_tcm1Per24HHisTable 1 }

        Odu3_tcm1Per24HHisEntry ::=
            SEQUENCE {
                odu3_tcm1Per24HHisEid
                    PerformanceEventType,
                odu3_tcm1Per24HHisParaLen
                    INTEGER,
                odu3_tcm1Per24HHisPara
                    OCTET STRING,
                odu3_tcm1Per24HHisMonValue
                    OCTET STRING,
                odu3_tcm1Per24HHisDateTimeStart
                    DateAndTime,
                odu3_tcm1Per24HHisDateTimeEnd
                    DateAndTime,
                odu3_tcm1Per24HHisVldty
                    INTEGER,
             }

        -- 1.3.6.1.4.1.2011.2.25.3.40.50.132.40.1.1
        odu3_tcm1Per24HHisEid OBJECT-TYPE
            SYNTAX PerformanceEventType
            MAX-ACCESS read-only
            STATUS current
            DESCRIPTION
                "perEid."
            ::= { odu3_tcm1Per24HHisEntry 1 }

        -- 1.3.6.1.4.1.2011.2.25.3.40.50.132.40.1.2
        odu3_tcm1Per24HHisParaLen OBJECT-TYPE
            SYNTAX INTEGER
            MAX-ACCESS read-only
            STATUS current
            DESCRIPTION
                "perParaLen."
            ::= { odu3_tcm1Per24HHisEntry 2 }

        -- 1.3.6.1.4.1.2011.2.25.3.40.50.132.40.1.3
        odu3_tcm1Per24HHisPara OBJECT-TYPE
            SYNTAX OCTET STRING (SIZE (0..100))
            MAX-ACCESS read-only
            STATUS current
            DESCRIPTION
                "perPara."
            ::= { odu3_tcm1Per24HHisEntry 3 }

        -- 1.3.6.1.4.1.2011.2.25.3.40.50.132.40.1.4
        odu3_tcm1Per24HHisMonValue OBJECT-TYPE
            SYNTAX OCTET STRING (SIZE (0..100))
            MAX-ACCESS read-only
            STATUS current
            DESCRIPTION
                "perMonValue."
            ::= { odu3_tcm1Per24HHisEntry 4 }

        -- 1.3.6.1.4.1.2011.2.25.3.40.50.132.40.1.5
        odu3_tcm1Per24HHisDateTimeStart OBJECT-TYPE
            SYNTAX DateAndTime
            MAX-ACCESS read-only
            STATUS current
            DESCRIPTION
                "perDateTimeStart. "
            ::= { odu3_tcm1Per24HHisEntry 5 }

        -- 1.3.6.1.4.1.2011.2.25.3.40.50.132.40.1.6
        odu3_tcm1Per24HHisDateTimeEnd OBJECT-TYPE
            SYNTAX DateAndTime
            MAX-ACCESS read-only
            STATUS current
            DESCRIPTION
                "perDateTimeEnd. "
            ::= { odu3_tcm1Per24HHisEntry 6 }

        -- 1.3.6.1.4.1.2011.2.25.3.40.50.132.40.1.7
        odu3_tcm1Per24HHisVldty OBJECT-TYPE
            SYNTAX INTEGER
            MAX-ACCESS read-only
            STATUS current
            DESCRIPTION
                "perVldty. "
            ::= { odu3_tcm1Per24HHisEntry 7 }




-- Alarm data
      -- 1.3.6.1.4.1.2011.2.25.3.40.50.133
      odu3_tcm2 OBJECT IDENTIFIER ::={ optixGlobalNGWDM 133 }


-- -------------------------------------------------------------------------
-- Perfomance 15-MIN Current Data Table (RTRV-PER-<MOD2>)
-- -------------------------------------------------------------------------
        -- 1.3.6.1.4.1.2011.2.25.3.40.50.133.10
        odu3_tcm2Per15MCurTable OBJECT-TYPE
          SYNTAX SEQUENCE OF Odu3_tcm2Per15MCurEntry
          MAX-ACCESS not-accessible
          STATUS current
          DESCRIPTION
              "odu3_tcm2Per15MCur."
          ::= { odu3_tcm2 10 }

        -- 1.3.6.1.4.1.2011.2.25.3.40.50.133.10.1
        odu3_tcm2Per15MCurEntry OBJECT-TYPE
            SYNTAX Odu3_tcm2Per15MCurEntry
            MAX-ACCESS not-accessible
            STATUS current
            DESCRIPTION
              "odu3_tcm2Per15MCur."
            INDEX { odu3_tcm2Per15MCurEid, odu3_tcm2Per15MCurPara }
            ::= { odu3_tcm2Per15MCurTable 1 }

        Odu3_tcm2Per15MCurEntry ::=
            SEQUENCE {
                odu3_tcm2Per15MCurEid
                    PerformanceEventType,
                odu3_tcm2Per15MCurMonValue
                    OCTET STRING,
                odu3_tcm2Per15MCurVldty
                    INTEGER,
                odu3_tcm2Per15MCurDateTime
                    DateAndTime,
                odu3_tcm2Per15MCurParaLen
                    INTEGER,
                odu3_tcm2Per15MCurPara
                    OCTET STRING
            }

        -- 1.3.6.1.4.1.2011.2.25.3.40.50.133.10.1.1
        odu3_tcm2Per15MCurEid OBJECT-TYPE
            SYNTAX PerformanceEventType
            MAX-ACCESS read-only
            STATUS current
            DESCRIPTION
                "perEid."
            ::= { odu3_tcm2Per15MCurEntry 1 }

        -- 1.3.6.1.4.1.2011.2.25.3.40.50.133.10.1.2
        odu3_tcm2Per15MCurMonValue OBJECT-TYPE
            SYNTAX OCTET STRING (SIZE (0..100))
            MAX-ACCESS read-only
            STATUS current
            DESCRIPTION
                "perMonValue."
            ::= { odu3_tcm2Per15MCurEntry 2 }

        -- 1.3.6.1.4.1.2011.2.25.3.40.50.133.10.1.3
        odu3_tcm2Per15MCurVldty OBJECT-TYPE
            SYNTAX INTEGER
            MAX-ACCESS read-only
            STATUS current
            DESCRIPTION
                "perVldty. "
            ::= { odu3_tcm2Per15MCurEntry 3 }

        -- 1.3.6.1.4.1.2011.2.25.3.40.50.133.10.1.4
        odu3_tcm2Per15MCurDateTime OBJECT-TYPE
            SYNTAX DateAndTime
            MAX-ACCESS read-only
            STATUS current
            DESCRIPTION
                "perDateTime. "
            ::= { odu3_tcm2Per15MCurEntry 4 }

        -- 1.3.6.1.4.1.2011.2.25.3.40.50.133.10.1.5
        odu3_tcm2Per15MCurParaLen OBJECT-TYPE
            SYNTAX INTEGER
            MAX-ACCESS read-only
            STATUS current
            DESCRIPTION
                "perParaLen."
            ::= { odu3_tcm2Per15MCurEntry 5 }

        -- 1.3.6.1.4.1.2011.2.25.3.40.50.133.10.1.6
        odu3_tcm2Per15MCurPara OBJECT-TYPE
            SYNTAX OCTET STRING (SIZE (0..100))
            MAX-ACCESS read-only
            STATUS current
            DESCRIPTION
                "perPara."
            ::= { odu3_tcm2Per15MCurEntry 6 }




-- -------------------------------------------------------------------------
-- Perfomance 15-MIN History Data Table (RTRV-PER-<MOD2>)
-- -------------------------------------------------------------------------
        -- 1.3.6.1.4.1.2011.2.25.3.40.50.133.20
        odu3_tcm2Per15MHisTable OBJECT-TYPE
          SYNTAX SEQUENCE OF Odu3_tcm2Per15MHisEntry
          MAX-ACCESS not-accessible
          STATUS current
          DESCRIPTION
              "odu3_tcm2Per15MHis."
          ::= { odu3_tcm2 20 }

        -- 1.3.6.1.4.1.2011.2.25.3.40.50.133.20.1
        odu3_tcm2Per15MHisEntry OBJECT-TYPE
            SYNTAX Odu3_tcm2Per15MHisEntry
            MAX-ACCESS not-accessible
            STATUS current
            DESCRIPTION
                "odu3_tcm2Per15MHis."
            INDEX {odu3_tcm2Per15MHisEid, odu3_tcm2Per15MHisParaLen, odu3_tcm2Per15MHisPara, odu3_tcm2Per15MHisDateTimeStart, odu3_tcm2Per15MHisDateTimeEnd}
            ::= { odu3_tcm2Per15MHisTable 1 }

        Odu3_tcm2Per15MHisEntry ::=
            SEQUENCE {
                odu3_tcm2Per15MHisEid
                    PerformanceEventType,
                odu3_tcm2Per15MHisParaLen
                    INTEGER,
                odu3_tcm2Per15MHisPara
                    OCTET STRING,
                odu3_tcm2Per15MHisMonValue
                    OCTET STRING,
                odu3_tcm2Per15MHisDateTimeStart
                    DateAndTime,
                odu3_tcm2Per15MHisDateTimeEnd
                    DateAndTime,
                odu3_tcm2Per15MHisVldty
                    INTEGER,
             }

        -- 1.3.6.1.4.1.2011.2.25.3.40.50.133.20.1.1
        odu3_tcm2Per15MHisEid OBJECT-TYPE
            SYNTAX PerformanceEventType
            MAX-ACCESS read-only
            STATUS current
            DESCRIPTION
                "perEid."
            ::= { odu3_tcm2Per15MHisEntry 1 }

        -- 1.3.6.1.4.1.2011.2.25.3.40.50.133.20.1.2
        odu3_tcm2Per15MHisParaLen OBJECT-TYPE
            SYNTAX INTEGER
            MAX-ACCESS read-only
            STATUS current
            DESCRIPTION
                "perParaLen."
            ::= { odu3_tcm2Per15MHisEntry 2 }

        -- 1.3.6.1.4.1.2011.2.25.3.40.50.133.20.1.3
        odu3_tcm2Per15MHisPara OBJECT-TYPE
            SYNTAX OCTET STRING (SIZE (0..100))
            MAX-ACCESS read-only
            STATUS current
            DESCRIPTION
                "perPara."
            ::= { odu3_tcm2Per15MHisEntry 3 }

        -- 1.3.6.1.4.1.2011.2.25.3.40.50.133.20.1.4
        odu3_tcm2Per15MHisMonValue OBJECT-TYPE
            SYNTAX OCTET STRING (SIZE (0..100))
            MAX-ACCESS read-only
            STATUS current
            DESCRIPTION
                "perMonValue."
            ::= { odu3_tcm2Per15MHisEntry 4 }

        -- 1.3.6.1.4.1.2011.2.25.3.40.50.133.20.1.5
        odu3_tcm2Per15MHisDateTimeStart OBJECT-TYPE
            SYNTAX DateAndTime
            MAX-ACCESS read-only
            STATUS current
            DESCRIPTION
                "perDateTimeStart. "
            ::= { odu3_tcm2Per15MHisEntry 5 }

        -- 1.3.6.1.4.1.2011.2.25.3.40.50.133.20.1.6
        odu3_tcm2Per15MHisDateTimeEnd OBJECT-TYPE
            SYNTAX DateAndTime
            MAX-ACCESS read-only
            STATUS current
            DESCRIPTION
                "perDateTimeEnd. "
            ::= { odu3_tcm2Per15MHisEntry 6 }

        -- 1.3.6.1.4.1.2011.2.25.3.40.50.133.20.1.7
        odu3_tcm2Per15MHisVldty OBJECT-TYPE
            SYNTAX INTEGER
            MAX-ACCESS read-only
            STATUS current
            DESCRIPTION
                "perVldty. "
            ::= { odu3_tcm2Per15MHisEntry 7 }




-- -------------------------------------------------------------------------
-- Perfomance 24-HOUR Current Data Table (RTRV-PER-<MOD2>)
-- -------------------------------------------------------------------------
        -- 1.3.6.1.4.1.2011.2.25.3.40.50.133.30
        odu3_tcm2Per24HCurTable OBJECT-TYPE
          SYNTAX SEQUENCE OF Odu3_tcm2Per24HCurEntry
          MAX-ACCESS not-accessible
          STATUS current
          DESCRIPTION
              "odu3_tcm2Per24HCur."
          ::= { odu3_tcm2 30 }

        -- 1.3.6.1.4.1.2011.2.25.3.40.50.133.30.1
        odu3_tcm2Per24HCurEntry OBJECT-TYPE
            SYNTAX Odu3_tcm2Per24HCurEntry
            MAX-ACCESS not-accessible
            STATUS current
            DESCRIPTION
              "odu3_tcm2Per24HCur."
            INDEX { odu3_tcm2Per24HCurEid, odu3_tcm2Per24HCurPara }
            ::= { odu3_tcm2Per24HCurTable 1 }

        Odu3_tcm2Per24HCurEntry ::=
            SEQUENCE {
                odu3_tcm2Per24HCurEid
                    PerformanceEventType,
                odu3_tcm2Per24HCurMonValue
                    OCTET STRING,
                odu3_tcm2Per24HCurVldty
                    INTEGER,
                odu3_tcm2Per24HCurDateTime
                    DateAndTime,
                odu3_tcm2Per24HCurParaLen
                    INTEGER,
                odu3_tcm2Per24HCurPara
                    OCTET STRING
            }

        -- 1.3.6.1.4.1.2011.2.25.3.40.50.133.30.1.1
        odu3_tcm2Per24HCurEid OBJECT-TYPE
            SYNTAX PerformanceEventType
            MAX-ACCESS read-only
            STATUS current
            DESCRIPTION
                "perEid."
            ::= { odu3_tcm2Per24HCurEntry 1 }

        -- 1.3.6.1.4.1.2011.2.25.3.40.50.133.30.1.2
        odu3_tcm2Per24HCurMonValue OBJECT-TYPE
            SYNTAX OCTET STRING (SIZE (0..100))
            MAX-ACCESS read-only
            STATUS current
            DESCRIPTION
                "perMonValue."
            ::= { odu3_tcm2Per24HCurEntry 2 }

        -- 1.3.6.1.4.1.2011.2.25.3.40.50.133.30.1.3
        odu3_tcm2Per24HCurVldty OBJECT-TYPE
            SYNTAX INTEGER
            MAX-ACCESS read-only
            STATUS current
            DESCRIPTION
                "perVldty. "
            ::= { odu3_tcm2Per24HCurEntry 3 }

        -- 1.3.6.1.4.1.2011.2.25.3.40.50.133.30.1.4
        odu3_tcm2Per24HCurDateTime OBJECT-TYPE
            SYNTAX DateAndTime
            MAX-ACCESS read-only
            STATUS current
            DESCRIPTION
                "perDateTime. "
            ::= { odu3_tcm2Per24HCurEntry 4 }

        -- 1.3.6.1.4.1.2011.2.25.3.40.50.133.30.1.5
        odu3_tcm2Per24HCurParaLen OBJECT-TYPE
            SYNTAX INTEGER
            MAX-ACCESS read-only
            STATUS current
            DESCRIPTION
                "perParaLen."
            ::= { odu3_tcm2Per24HCurEntry 5 }

        -- 1.3.6.1.4.1.2011.2.25.3.40.50.133.30.1.6
        odu3_tcm2Per24HCurPara OBJECT-TYPE
            SYNTAX OCTET STRING (SIZE (0..100))
            MAX-ACCESS read-only
            STATUS current
            DESCRIPTION
                "perPara."
            ::= { odu3_tcm2Per24HCurEntry 6 }




-- -------------------------------------------------------------------------
-- Perfomance 24-HOUR History Data Table (RTRV-PER-<MOD2>)
-- -------------------------------------------------------------------------
        -- 1.3.6.1.4.1.2011.2.25.3.40.50.133.40
        odu3_tcm2Per24HHisTable OBJECT-TYPE
          SYNTAX SEQUENCE OF Odu3_tcm2Per24HHisEntry
          MAX-ACCESS not-accessible
          STATUS current
          DESCRIPTION
              "odu3_tcm2Per24HHis."
          ::= { odu3_tcm2 40 }

        -- 1.3.6.1.4.1.2011.2.25.3.40.50.133.40.1
        odu3_tcm2Per24HHisEntry OBJECT-TYPE
            SYNTAX Odu3_tcm2Per24HHisEntry
            MAX-ACCESS not-accessible
            STATUS current
            DESCRIPTION
                "odu3_tcm2Per24HHis."
            INDEX {odu3_tcm2Per24HHisEid, odu3_tcm2Per24HHisParaLen, odu3_tcm2Per24HHisPara, odu3_tcm2Per24HHisDateTimeStart, odu3_tcm2Per24HHisDateTimeEnd}
            ::= { odu3_tcm2Per24HHisTable 1 }

        Odu3_tcm2Per24HHisEntry ::=
            SEQUENCE {
                odu3_tcm2Per24HHisEid
                    PerformanceEventType,
                odu3_tcm2Per24HHisParaLen
                    INTEGER,
                odu3_tcm2Per24HHisPara
                    OCTET STRING,
                odu3_tcm2Per24HHisMonValue
                    OCTET STRING,
                odu3_tcm2Per24HHisDateTimeStart
                    DateAndTime,
                odu3_tcm2Per24HHisDateTimeEnd
                    DateAndTime,
                odu3_tcm2Per24HHisVldty
                    INTEGER,
             }

        -- 1.3.6.1.4.1.2011.2.25.3.40.50.133.40.1.1
        odu3_tcm2Per24HHisEid OBJECT-TYPE
            SYNTAX PerformanceEventType
            MAX-ACCESS read-only
            STATUS current
            DESCRIPTION
                "perEid."
            ::= { odu3_tcm2Per24HHisEntry 1 }

        -- 1.3.6.1.4.1.2011.2.25.3.40.50.133.40.1.2
        odu3_tcm2Per24HHisParaLen OBJECT-TYPE
            SYNTAX INTEGER
            MAX-ACCESS read-only
            STATUS current
            DESCRIPTION
                "perParaLen."
            ::= { odu3_tcm2Per24HHisEntry 2 }

        -- 1.3.6.1.4.1.2011.2.25.3.40.50.133.40.1.3
        odu3_tcm2Per24HHisPara OBJECT-TYPE
            SYNTAX OCTET STRING (SIZE (0..100))
            MAX-ACCESS read-only
            STATUS current
            DESCRIPTION
                "perPara."
            ::= { odu3_tcm2Per24HHisEntry 3 }

        -- 1.3.6.1.4.1.2011.2.25.3.40.50.133.40.1.4
        odu3_tcm2Per24HHisMonValue OBJECT-TYPE
            SYNTAX OCTET STRING (SIZE (0..100))
            MAX-ACCESS read-only
            STATUS current
            DESCRIPTION
                "perMonValue."
            ::= { odu3_tcm2Per24HHisEntry 4 }

        -- 1.3.6.1.4.1.2011.2.25.3.40.50.133.40.1.5
        odu3_tcm2Per24HHisDateTimeStart OBJECT-TYPE
            SYNTAX DateAndTime
            MAX-ACCESS read-only
            STATUS current
            DESCRIPTION
                "perDateTimeStart. "
            ::= { odu3_tcm2Per24HHisEntry 5 }

        -- 1.3.6.1.4.1.2011.2.25.3.40.50.133.40.1.6
        odu3_tcm2Per24HHisDateTimeEnd OBJECT-TYPE
            SYNTAX DateAndTime
            MAX-ACCESS read-only
            STATUS current
            DESCRIPTION
                "perDateTimeEnd. "
            ::= { odu3_tcm2Per24HHisEntry 6 }

        -- 1.3.6.1.4.1.2011.2.25.3.40.50.133.40.1.7
        odu3_tcm2Per24HHisVldty OBJECT-TYPE
            SYNTAX INTEGER
            MAX-ACCESS read-only
            STATUS current
            DESCRIPTION
                "perVldty. "
            ::= { odu3_tcm2Per24HHisEntry 7 }




-- Alarm data
      -- 1.3.6.1.4.1.2011.2.25.3.40.50.134
      odu3_tcm3 OBJECT IDENTIFIER ::={ optixGlobalNGWDM 134 }


-- -------------------------------------------------------------------------
-- Perfomance 15-MIN Current Data Table (RTRV-PER-<MOD2>)
-- -------------------------------------------------------------------------
        -- 1.3.6.1.4.1.2011.2.25.3.40.50.134.10
        odu3_tcm3Per15MCurTable OBJECT-TYPE
          SYNTAX SEQUENCE OF Odu3_tcm3Per15MCurEntry
          MAX-ACCESS not-accessible
          STATUS current
          DESCRIPTION
              "odu3_tcm3Per15MCur."
          ::= { odu3_tcm3 10 }

        -- 1.3.6.1.4.1.2011.2.25.3.40.50.134.10.1
        odu3_tcm3Per15MCurEntry OBJECT-TYPE
            SYNTAX Odu3_tcm3Per15MCurEntry
            MAX-ACCESS not-accessible
            STATUS current
            DESCRIPTION
              "odu3_tcm3Per15MCur."
            INDEX { odu3_tcm3Per15MCurEid, odu3_tcm3Per15MCurPara }
            ::= { odu3_tcm3Per15MCurTable 1 }

        Odu3_tcm3Per15MCurEntry ::=
            SEQUENCE {
                odu3_tcm3Per15MCurEid
                    PerformanceEventType,
                odu3_tcm3Per15MCurMonValue
                    OCTET STRING,
                odu3_tcm3Per15MCurVldty
                    INTEGER,
                odu3_tcm3Per15MCurDateTime
                    DateAndTime,
                odu3_tcm3Per15MCurParaLen
                    INTEGER,
                odu3_tcm3Per15MCurPara
                    OCTET STRING
            }

        -- 1.3.6.1.4.1.2011.2.25.3.40.50.134.10.1.1
        odu3_tcm3Per15MCurEid OBJECT-TYPE
            SYNTAX PerformanceEventType
            MAX-ACCESS read-only
            STATUS current
            DESCRIPTION
                "perEid."
            ::= { odu3_tcm3Per15MCurEntry 1 }

        -- 1.3.6.1.4.1.2011.2.25.3.40.50.134.10.1.2
        odu3_tcm3Per15MCurMonValue OBJECT-TYPE
            SYNTAX OCTET STRING (SIZE (0..100))
            MAX-ACCESS read-only
            STATUS current
            DESCRIPTION
                "perMonValue."
            ::= { odu3_tcm3Per15MCurEntry 2 }

        -- 1.3.6.1.4.1.2011.2.25.3.40.50.134.10.1.3
        odu3_tcm3Per15MCurVldty OBJECT-TYPE
            SYNTAX INTEGER
            MAX-ACCESS read-only
            STATUS current
            DESCRIPTION
                "perVldty. "
            ::= { odu3_tcm3Per15MCurEntry 3 }

        -- 1.3.6.1.4.1.2011.2.25.3.40.50.134.10.1.4
        odu3_tcm3Per15MCurDateTime OBJECT-TYPE
            SYNTAX DateAndTime
            MAX-ACCESS read-only
            STATUS current
            DESCRIPTION
                "perDateTime. "
            ::= { odu3_tcm3Per15MCurEntry 4 }

        -- 1.3.6.1.4.1.2011.2.25.3.40.50.134.10.1.5
        odu3_tcm3Per15MCurParaLen OBJECT-TYPE
            SYNTAX INTEGER
            MAX-ACCESS read-only
            STATUS current
            DESCRIPTION
                "perParaLen."
            ::= { odu3_tcm3Per15MCurEntry 5 }

        -- 1.3.6.1.4.1.2011.2.25.3.40.50.134.10.1.6
        odu3_tcm3Per15MCurPara OBJECT-TYPE
            SYNTAX OCTET STRING (SIZE (0..100))
            MAX-ACCESS read-only
            STATUS current
            DESCRIPTION
                "perPara."
            ::= { odu3_tcm3Per15MCurEntry 6 }




-- -------------------------------------------------------------------------
-- Perfomance 15-MIN History Data Table (RTRV-PER-<MOD2>)
-- -------------------------------------------------------------------------
        -- 1.3.6.1.4.1.2011.2.25.3.40.50.134.20
        odu3_tcm3Per15MHisTable OBJECT-TYPE
          SYNTAX SEQUENCE OF Odu3_tcm3Per15MHisEntry
          MAX-ACCESS not-accessible
          STATUS current
          DESCRIPTION
              "odu3_tcm3Per15MHis."
          ::= { odu3_tcm3 20 }

        -- 1.3.6.1.4.1.2011.2.25.3.40.50.134.20.1
        odu3_tcm3Per15MHisEntry OBJECT-TYPE
            SYNTAX Odu3_tcm3Per15MHisEntry
            MAX-ACCESS not-accessible
            STATUS current
            DESCRIPTION
                "odu3_tcm3Per15MHis."
            INDEX {odu3_tcm3Per15MHisEid, odu3_tcm3Per15MHisParaLen, odu3_tcm3Per15MHisPara, odu3_tcm3Per15MHisDateTimeStart, odu3_tcm3Per15MHisDateTimeEnd}
            ::= { odu3_tcm3Per15MHisTable 1 }

        Odu3_tcm3Per15MHisEntry ::=
            SEQUENCE {
                odu3_tcm3Per15MHisEid
                    PerformanceEventType,
                odu3_tcm3Per15MHisParaLen
                    INTEGER,
                odu3_tcm3Per15MHisPara
                    OCTET STRING,
                odu3_tcm3Per15MHisMonValue
                    OCTET STRING,
                odu3_tcm3Per15MHisDateTimeStart
                    DateAndTime,
                odu3_tcm3Per15MHisDateTimeEnd
                    DateAndTime,
                odu3_tcm3Per15MHisVldty
                    INTEGER,
             }

        -- 1.3.6.1.4.1.2011.2.25.3.40.50.134.20.1.1
        odu3_tcm3Per15MHisEid OBJECT-TYPE
            SYNTAX PerformanceEventType
            MAX-ACCESS read-only
            STATUS current
            DESCRIPTION
                "perEid."
            ::= { odu3_tcm3Per15MHisEntry 1 }

        -- 1.3.6.1.4.1.2011.2.25.3.40.50.134.20.1.2
        odu3_tcm3Per15MHisParaLen OBJECT-TYPE
            SYNTAX INTEGER
            MAX-ACCESS read-only
            STATUS current
            DESCRIPTION
                "perParaLen."
            ::= { odu3_tcm3Per15MHisEntry 2 }

        -- 1.3.6.1.4.1.2011.2.25.3.40.50.134.20.1.3
        odu3_tcm3Per15MHisPara OBJECT-TYPE
            SYNTAX OCTET STRING (SIZE (0..100))
            MAX-ACCESS read-only
            STATUS current
            DESCRIPTION
                "perPara."
            ::= { odu3_tcm3Per15MHisEntry 3 }

        -- 1.3.6.1.4.1.2011.2.25.3.40.50.134.20.1.4
        odu3_tcm3Per15MHisMonValue OBJECT-TYPE
            SYNTAX OCTET STRING (SIZE (0..100))
            MAX-ACCESS read-only
            STATUS current
            DESCRIPTION
                "perMonValue."
            ::= { odu3_tcm3Per15MHisEntry 4 }

        -- 1.3.6.1.4.1.2011.2.25.3.40.50.134.20.1.5
        odu3_tcm3Per15MHisDateTimeStart OBJECT-TYPE
            SYNTAX DateAndTime
            MAX-ACCESS read-only
            STATUS current
            DESCRIPTION
                "perDateTimeStart. "
            ::= { odu3_tcm3Per15MHisEntry 5 }

        -- 1.3.6.1.4.1.2011.2.25.3.40.50.134.20.1.6
        odu3_tcm3Per15MHisDateTimeEnd OBJECT-TYPE
            SYNTAX DateAndTime
            MAX-ACCESS read-only
            STATUS current
            DESCRIPTION
                "perDateTimeEnd. "
            ::= { odu3_tcm3Per15MHisEntry 6 }

        -- 1.3.6.1.4.1.2011.2.25.3.40.50.134.20.1.7
        odu3_tcm3Per15MHisVldty OBJECT-TYPE
            SYNTAX INTEGER
            MAX-ACCESS read-only
            STATUS current
            DESCRIPTION
                "perVldty. "
            ::= { odu3_tcm3Per15MHisEntry 7 }




-- -------------------------------------------------------------------------
-- Perfomance 24-HOUR Current Data Table (RTRV-PER-<MOD2>)
-- -------------------------------------------------------------------------
        -- 1.3.6.1.4.1.2011.2.25.3.40.50.134.30
        odu3_tcm3Per24HCurTable OBJECT-TYPE
          SYNTAX SEQUENCE OF Odu3_tcm3Per24HCurEntry
          MAX-ACCESS not-accessible
          STATUS current
          DESCRIPTION
              "odu3_tcm3Per24HCur."
          ::= { odu3_tcm3 30 }

        -- 1.3.6.1.4.1.2011.2.25.3.40.50.134.30.1
        odu3_tcm3Per24HCurEntry OBJECT-TYPE
            SYNTAX Odu3_tcm3Per24HCurEntry
            MAX-ACCESS not-accessible
            STATUS current
            DESCRIPTION
              "odu3_tcm3Per24HCur."
            INDEX { odu3_tcm3Per24HCurEid, odu3_tcm3Per24HCurPara }
            ::= { odu3_tcm3Per24HCurTable 1 }

        Odu3_tcm3Per24HCurEntry ::=
            SEQUENCE {
                odu3_tcm3Per24HCurEid
                    PerformanceEventType,
                odu3_tcm3Per24HCurMonValue
                    OCTET STRING,
                odu3_tcm3Per24HCurVldty
                    INTEGER,
                odu3_tcm3Per24HCurDateTime
                    DateAndTime,
                odu3_tcm3Per24HCurParaLen
                    INTEGER,
                odu3_tcm3Per24HCurPara
                    OCTET STRING
            }

        -- 1.3.6.1.4.1.2011.2.25.3.40.50.134.30.1.1
        odu3_tcm3Per24HCurEid OBJECT-TYPE
            SYNTAX PerformanceEventType
            MAX-ACCESS read-only
            STATUS current
            DESCRIPTION
                "perEid."
            ::= { odu3_tcm3Per24HCurEntry 1 }

        -- 1.3.6.1.4.1.2011.2.25.3.40.50.134.30.1.2
        odu3_tcm3Per24HCurMonValue OBJECT-TYPE
            SYNTAX OCTET STRING (SIZE (0..100))
            MAX-ACCESS read-only
            STATUS current
            DESCRIPTION
                "perMonValue."
            ::= { odu3_tcm3Per24HCurEntry 2 }

        -- 1.3.6.1.4.1.2011.2.25.3.40.50.134.30.1.3
        odu3_tcm3Per24HCurVldty OBJECT-TYPE
            SYNTAX INTEGER
            MAX-ACCESS read-only
            STATUS current
            DESCRIPTION
                "perVldty. "
            ::= { odu3_tcm3Per24HCurEntry 3 }

        -- 1.3.6.1.4.1.2011.2.25.3.40.50.134.30.1.4
        odu3_tcm3Per24HCurDateTime OBJECT-TYPE
            SYNTAX DateAndTime
            MAX-ACCESS read-only
            STATUS current
            DESCRIPTION
                "perDateTime. "
            ::= { odu3_tcm3Per24HCurEntry 4 }

        -- 1.3.6.1.4.1.2011.2.25.3.40.50.134.30.1.5
        odu3_tcm3Per24HCurParaLen OBJECT-TYPE
            SYNTAX INTEGER
            MAX-ACCESS read-only
            STATUS current
            DESCRIPTION
                "perParaLen."
            ::= { odu3_tcm3Per24HCurEntry 5 }

        -- 1.3.6.1.4.1.2011.2.25.3.40.50.134.30.1.6
        odu3_tcm3Per24HCurPara OBJECT-TYPE
            SYNTAX OCTET STRING (SIZE (0..100))
            MAX-ACCESS read-only
            STATUS current
            DESCRIPTION
                "perPara."
            ::= { odu3_tcm3Per24HCurEntry 6 }




-- -------------------------------------------------------------------------
-- Perfomance 24-HOUR History Data Table (RTRV-PER-<MOD2>)
-- -------------------------------------------------------------------------
        -- 1.3.6.1.4.1.2011.2.25.3.40.50.134.40
        odu3_tcm3Per24HHisTable OBJECT-TYPE
          SYNTAX SEQUENCE OF Odu3_tcm3Per24HHisEntry
          MAX-ACCESS not-accessible
          STATUS current
          DESCRIPTION
              "odu3_tcm3Per24HHis."
          ::= { odu3_tcm3 40 }

        -- 1.3.6.1.4.1.2011.2.25.3.40.50.134.40.1
        odu3_tcm3Per24HHisEntry OBJECT-TYPE
            SYNTAX Odu3_tcm3Per24HHisEntry
            MAX-ACCESS not-accessible
            STATUS current
            DESCRIPTION
                "odu3_tcm3Per24HHis."
            INDEX {odu3_tcm3Per24HHisEid, odu3_tcm3Per24HHisParaLen, odu3_tcm3Per24HHisPara, odu3_tcm3Per24HHisDateTimeStart, odu3_tcm3Per24HHisDateTimeEnd}
            ::= { odu3_tcm3Per24HHisTable 1 }

        Odu3_tcm3Per24HHisEntry ::=
            SEQUENCE {
                odu3_tcm3Per24HHisEid
                    PerformanceEventType,
                odu3_tcm3Per24HHisParaLen
                    INTEGER,
                odu3_tcm3Per24HHisPara
                    OCTET STRING,
                odu3_tcm3Per24HHisMonValue
                    OCTET STRING,
                odu3_tcm3Per24HHisDateTimeStart
                    DateAndTime,
                odu3_tcm3Per24HHisDateTimeEnd
                    DateAndTime,
                odu3_tcm3Per24HHisVldty
                    INTEGER,
             }

        -- 1.3.6.1.4.1.2011.2.25.3.40.50.134.40.1.1
        odu3_tcm3Per24HHisEid OBJECT-TYPE
            SYNTAX PerformanceEventType
            MAX-ACCESS read-only
            STATUS current
            DESCRIPTION
                "perEid."
            ::= { odu3_tcm3Per24HHisEntry 1 }

        -- 1.3.6.1.4.1.2011.2.25.3.40.50.134.40.1.2
        odu3_tcm3Per24HHisParaLen OBJECT-TYPE
            SYNTAX INTEGER
            MAX-ACCESS read-only
            STATUS current
            DESCRIPTION
                "perParaLen."
            ::= { odu3_tcm3Per24HHisEntry 2 }

        -- 1.3.6.1.4.1.2011.2.25.3.40.50.134.40.1.3
        odu3_tcm3Per24HHisPara OBJECT-TYPE
            SYNTAX OCTET STRING (SIZE (0..100))
            MAX-ACCESS read-only
            STATUS current
            DESCRIPTION
                "perPara."
            ::= { odu3_tcm3Per24HHisEntry 3 }

        -- 1.3.6.1.4.1.2011.2.25.3.40.50.134.40.1.4
        odu3_tcm3Per24HHisMonValue OBJECT-TYPE
            SYNTAX OCTET STRING (SIZE (0..100))
            MAX-ACCESS read-only
            STATUS current
            DESCRIPTION
                "perMonValue."
            ::= { odu3_tcm3Per24HHisEntry 4 }

        -- 1.3.6.1.4.1.2011.2.25.3.40.50.134.40.1.5
        odu3_tcm3Per24HHisDateTimeStart OBJECT-TYPE
            SYNTAX DateAndTime
            MAX-ACCESS read-only
            STATUS current
            DESCRIPTION
                "perDateTimeStart. "
            ::= { odu3_tcm3Per24HHisEntry 5 }

        -- 1.3.6.1.4.1.2011.2.25.3.40.50.134.40.1.6
        odu3_tcm3Per24HHisDateTimeEnd OBJECT-TYPE
            SYNTAX DateAndTime
            MAX-ACCESS read-only
            STATUS current
            DESCRIPTION
                "perDateTimeEnd. "
            ::= { odu3_tcm3Per24HHisEntry 6 }

        -- 1.3.6.1.4.1.2011.2.25.3.40.50.134.40.1.7
        odu3_tcm3Per24HHisVldty OBJECT-TYPE
            SYNTAX INTEGER
            MAX-ACCESS read-only
            STATUS current
            DESCRIPTION
                "perVldty. "
            ::= { odu3_tcm3Per24HHisEntry 7 }




-- Alarm data
      -- 1.3.6.1.4.1.2011.2.25.3.40.50.135
      odu3_tcm4 OBJECT IDENTIFIER ::={ optixGlobalNGWDM 135 }


-- -------------------------------------------------------------------------
-- Perfomance 15-MIN Current Data Table (RTRV-PER-<MOD2>)
-- -------------------------------------------------------------------------
        -- 1.3.6.1.4.1.2011.2.25.3.40.50.135.10
        odu3_tcm4Per15MCurTable OBJECT-TYPE
          SYNTAX SEQUENCE OF Odu3_tcm4Per15MCurEntry
          MAX-ACCESS not-accessible
          STATUS current
          DESCRIPTION
              "odu3_tcm4Per15MCur."
          ::= { odu3_tcm4 10 }

        -- 1.3.6.1.4.1.2011.2.25.3.40.50.135.10.1
        odu3_tcm4Per15MCurEntry OBJECT-TYPE
            SYNTAX Odu3_tcm4Per15MCurEntry
            MAX-ACCESS not-accessible
            STATUS current
            DESCRIPTION
              "odu3_tcm4Per15MCur."
            INDEX { odu3_tcm4Per15MCurEid, odu3_tcm4Per15MCurPara }
            ::= { odu3_tcm4Per15MCurTable 1 }

        Odu3_tcm4Per15MCurEntry ::=
            SEQUENCE {
                odu3_tcm4Per15MCurEid
                    PerformanceEventType,
                odu3_tcm4Per15MCurMonValue
                    OCTET STRING,
                odu3_tcm4Per15MCurVldty
                    INTEGER,
                odu3_tcm4Per15MCurDateTime
                    DateAndTime,
                odu3_tcm4Per15MCurParaLen
                    INTEGER,
                odu3_tcm4Per15MCurPara
                    OCTET STRING
            }

        -- 1.3.6.1.4.1.2011.2.25.3.40.50.135.10.1.1
        odu3_tcm4Per15MCurEid OBJECT-TYPE
            SYNTAX PerformanceEventType
            MAX-ACCESS read-only
            STATUS current
            DESCRIPTION
                "perEid."
            ::= { odu3_tcm4Per15MCurEntry 1 }

        -- 1.3.6.1.4.1.2011.2.25.3.40.50.135.10.1.2
        odu3_tcm4Per15MCurMonValue OBJECT-TYPE
            SYNTAX OCTET STRING (SIZE (0..100))
            MAX-ACCESS read-only
            STATUS current
            DESCRIPTION
                "perMonValue."
            ::= { odu3_tcm4Per15MCurEntry 2 }

        -- 1.3.6.1.4.1.2011.2.25.3.40.50.135.10.1.3
        odu3_tcm4Per15MCurVldty OBJECT-TYPE
            SYNTAX INTEGER
            MAX-ACCESS read-only
            STATUS current
            DESCRIPTION
                "perVldty. "
            ::= { odu3_tcm4Per15MCurEntry 3 }

        -- 1.3.6.1.4.1.2011.2.25.3.40.50.135.10.1.4
        odu3_tcm4Per15MCurDateTime OBJECT-TYPE
            SYNTAX DateAndTime
            MAX-ACCESS read-only
            STATUS current
            DESCRIPTION
                "perDateTime. "
            ::= { odu3_tcm4Per15MCurEntry 4 }

        -- 1.3.6.1.4.1.2011.2.25.3.40.50.135.10.1.5
        odu3_tcm4Per15MCurParaLen OBJECT-TYPE
            SYNTAX INTEGER
            MAX-ACCESS read-only
            STATUS current
            DESCRIPTION
                "perParaLen."
            ::= { odu3_tcm4Per15MCurEntry 5 }

        -- 1.3.6.1.4.1.2011.2.25.3.40.50.135.10.1.6
        odu3_tcm4Per15MCurPara OBJECT-TYPE
            SYNTAX OCTET STRING (SIZE (0..100))
            MAX-ACCESS read-only
            STATUS current
            DESCRIPTION
                "perPara."
            ::= { odu3_tcm4Per15MCurEntry 6 }




-- -------------------------------------------------------------------------
-- Perfomance 15-MIN History Data Table (RTRV-PER-<MOD2>)
-- -------------------------------------------------------------------------
        -- 1.3.6.1.4.1.2011.2.25.3.40.50.135.20
        odu3_tcm4Per15MHisTable OBJECT-TYPE
          SYNTAX SEQUENCE OF Odu3_tcm4Per15MHisEntry
          MAX-ACCESS not-accessible
          STATUS current
          DESCRIPTION
              "odu3_tcm4Per15MHis."
          ::= { odu3_tcm4 20 }

        -- 1.3.6.1.4.1.2011.2.25.3.40.50.135.20.1
        odu3_tcm4Per15MHisEntry OBJECT-TYPE
            SYNTAX Odu3_tcm4Per15MHisEntry
            MAX-ACCESS not-accessible
            STATUS current
            DESCRIPTION
                "odu3_tcm4Per15MHis."
            INDEX {odu3_tcm4Per15MHisEid, odu3_tcm4Per15MHisParaLen, odu3_tcm4Per15MHisPara, odu3_tcm4Per15MHisDateTimeStart, odu3_tcm4Per15MHisDateTimeEnd}
            ::= { odu3_tcm4Per15MHisTable 1 }

        Odu3_tcm4Per15MHisEntry ::=
            SEQUENCE {
                odu3_tcm4Per15MHisEid
                    PerformanceEventType,
                odu3_tcm4Per15MHisParaLen
                    INTEGER,
                odu3_tcm4Per15MHisPara
                    OCTET STRING,
                odu3_tcm4Per15MHisMonValue
                    OCTET STRING,
                odu3_tcm4Per15MHisDateTimeStart
                    DateAndTime,
                odu3_tcm4Per15MHisDateTimeEnd
                    DateAndTime,
                odu3_tcm4Per15MHisVldty
                    INTEGER,
             }

        -- 1.3.6.1.4.1.2011.2.25.3.40.50.135.20.1.1
        odu3_tcm4Per15MHisEid OBJECT-TYPE
            SYNTAX PerformanceEventType
            MAX-ACCESS read-only
            STATUS current
            DESCRIPTION
                "perEid."
            ::= { odu3_tcm4Per15MHisEntry 1 }

        -- 1.3.6.1.4.1.2011.2.25.3.40.50.135.20.1.2
        odu3_tcm4Per15MHisParaLen OBJECT-TYPE
            SYNTAX INTEGER
            MAX-ACCESS read-only
            STATUS current
            DESCRIPTION
                "perParaLen."
            ::= { odu3_tcm4Per15MHisEntry 2 }

        -- 1.3.6.1.4.1.2011.2.25.3.40.50.135.20.1.3
        odu3_tcm4Per15MHisPara OBJECT-TYPE
            SYNTAX OCTET STRING (SIZE (0..100))
            MAX-ACCESS read-only
            STATUS current
            DESCRIPTION
                "perPara."
            ::= { odu3_tcm4Per15MHisEntry 3 }

        -- 1.3.6.1.4.1.2011.2.25.3.40.50.135.20.1.4
        odu3_tcm4Per15MHisMonValue OBJECT-TYPE
            SYNTAX OCTET STRING (SIZE (0..100))
            MAX-ACCESS read-only
            STATUS current
            DESCRIPTION
                "perMonValue."
            ::= { odu3_tcm4Per15MHisEntry 4 }

        -- 1.3.6.1.4.1.2011.2.25.3.40.50.135.20.1.5
        odu3_tcm4Per15MHisDateTimeStart OBJECT-TYPE
            SYNTAX DateAndTime
            MAX-ACCESS read-only
            STATUS current
            DESCRIPTION
                "perDateTimeStart. "
            ::= { odu3_tcm4Per15MHisEntry 5 }

        -- 1.3.6.1.4.1.2011.2.25.3.40.50.135.20.1.6
        odu3_tcm4Per15MHisDateTimeEnd OBJECT-TYPE
            SYNTAX DateAndTime
            MAX-ACCESS read-only
            STATUS current
            DESCRIPTION
                "perDateTimeEnd. "
            ::= { odu3_tcm4Per15MHisEntry 6 }

        -- 1.3.6.1.4.1.2011.2.25.3.40.50.135.20.1.7
        odu3_tcm4Per15MHisVldty OBJECT-TYPE
            SYNTAX INTEGER
            MAX-ACCESS read-only
            STATUS current
            DESCRIPTION
                "perVldty. "
            ::= { odu3_tcm4Per15MHisEntry 7 }




-- -------------------------------------------------------------------------
-- Perfomance 24-HOUR Current Data Table (RTRV-PER-<MOD2>)
-- -------------------------------------------------------------------------
        -- 1.3.6.1.4.1.2011.2.25.3.40.50.135.30
        odu3_tcm4Per24HCurTable OBJECT-TYPE
          SYNTAX SEQUENCE OF Odu3_tcm4Per24HCurEntry
          MAX-ACCESS not-accessible
          STATUS current
          DESCRIPTION
              "odu3_tcm4Per24HCur."
          ::= { odu3_tcm4 30 }

        -- 1.3.6.1.4.1.2011.2.25.3.40.50.135.30.1
        odu3_tcm4Per24HCurEntry OBJECT-TYPE
            SYNTAX Odu3_tcm4Per24HCurEntry
            MAX-ACCESS not-accessible
            STATUS current
            DESCRIPTION
              "odu3_tcm4Per24HCur."
            INDEX { odu3_tcm4Per24HCurEid, odu3_tcm4Per24HCurPara }
            ::= { odu3_tcm4Per24HCurTable 1 }

        Odu3_tcm4Per24HCurEntry ::=
            SEQUENCE {
                odu3_tcm4Per24HCurEid
                    PerformanceEventType,
                odu3_tcm4Per24HCurMonValue
                    OCTET STRING,
                odu3_tcm4Per24HCurVldty
                    INTEGER,
                odu3_tcm4Per24HCurDateTime
                    DateAndTime,
                odu3_tcm4Per24HCurParaLen
                    INTEGER,
                odu3_tcm4Per24HCurPara
                    OCTET STRING
            }

        -- 1.3.6.1.4.1.2011.2.25.3.40.50.135.30.1.1
        odu3_tcm4Per24HCurEid OBJECT-TYPE
            SYNTAX PerformanceEventType
            MAX-ACCESS read-only
            STATUS current
            DESCRIPTION
                "perEid."
            ::= { odu3_tcm4Per24HCurEntry 1 }

        -- 1.3.6.1.4.1.2011.2.25.3.40.50.135.30.1.2
        odu3_tcm4Per24HCurMonValue OBJECT-TYPE
            SYNTAX OCTET STRING (SIZE (0..100))
            MAX-ACCESS read-only
            STATUS current
            DESCRIPTION
                "perMonValue."
            ::= { odu3_tcm4Per24HCurEntry 2 }

        -- 1.3.6.1.4.1.2011.2.25.3.40.50.135.30.1.3
        odu3_tcm4Per24HCurVldty OBJECT-TYPE
            SYNTAX INTEGER
            MAX-ACCESS read-only
            STATUS current
            DESCRIPTION
                "perVldty. "
            ::= { odu3_tcm4Per24HCurEntry 3 }

        -- 1.3.6.1.4.1.2011.2.25.3.40.50.135.30.1.4
        odu3_tcm4Per24HCurDateTime OBJECT-TYPE
            SYNTAX DateAndTime
            MAX-ACCESS read-only
            STATUS current
            DESCRIPTION
                "perDateTime. "
            ::= { odu3_tcm4Per24HCurEntry 4 }

        -- 1.3.6.1.4.1.2011.2.25.3.40.50.135.30.1.5
        odu3_tcm4Per24HCurParaLen OBJECT-TYPE
            SYNTAX INTEGER
            MAX-ACCESS read-only
            STATUS current
            DESCRIPTION
                "perParaLen."
            ::= { odu3_tcm4Per24HCurEntry 5 }

        -- 1.3.6.1.4.1.2011.2.25.3.40.50.135.30.1.6
        odu3_tcm4Per24HCurPara OBJECT-TYPE
            SYNTAX OCTET STRING (SIZE (0..100))
            MAX-ACCESS read-only
            STATUS current
            DESCRIPTION
                "perPara."
            ::= { odu3_tcm4Per24HCurEntry 6 }




-- -------------------------------------------------------------------------
-- Perfomance 24-HOUR History Data Table (RTRV-PER-<MOD2>)
-- -------------------------------------------------------------------------
        -- 1.3.6.1.4.1.2011.2.25.3.40.50.135.40
        odu3_tcm4Per24HHisTable OBJECT-TYPE
          SYNTAX SEQUENCE OF Odu3_tcm4Per24HHisEntry
          MAX-ACCESS not-accessible
          STATUS current
          DESCRIPTION
              "odu3_tcm4Per24HHis."
          ::= { odu3_tcm4 40 }

        -- 1.3.6.1.4.1.2011.2.25.3.40.50.135.40.1
        odu3_tcm4Per24HHisEntry OBJECT-TYPE
            SYNTAX Odu3_tcm4Per24HHisEntry
            MAX-ACCESS not-accessible
            STATUS current
            DESCRIPTION
                "odu3_tcm4Per24HHis."
            INDEX {odu3_tcm4Per24HHisEid, odu3_tcm4Per24HHisParaLen, odu3_tcm4Per24HHisPara, odu3_tcm4Per24HHisDateTimeStart, odu3_tcm4Per24HHisDateTimeEnd}
            ::= { odu3_tcm4Per24HHisTable 1 }

        Odu3_tcm4Per24HHisEntry ::=
            SEQUENCE {
                odu3_tcm4Per24HHisEid
                    PerformanceEventType,
                odu3_tcm4Per24HHisParaLen
                    INTEGER,
                odu3_tcm4Per24HHisPara
                    OCTET STRING,
                odu3_tcm4Per24HHisMonValue
                    OCTET STRING,
                odu3_tcm4Per24HHisDateTimeStart
                    DateAndTime,
                odu3_tcm4Per24HHisDateTimeEnd
                    DateAndTime,
                odu3_tcm4Per24HHisVldty
                    INTEGER,
             }

        -- 1.3.6.1.4.1.2011.2.25.3.40.50.135.40.1.1
        odu3_tcm4Per24HHisEid OBJECT-TYPE
            SYNTAX PerformanceEventType
            MAX-ACCESS read-only
            STATUS current
            DESCRIPTION
                "perEid."
            ::= { odu3_tcm4Per24HHisEntry 1 }

        -- 1.3.6.1.4.1.2011.2.25.3.40.50.135.40.1.2
        odu3_tcm4Per24HHisParaLen OBJECT-TYPE
            SYNTAX INTEGER
            MAX-ACCESS read-only
            STATUS current
            DESCRIPTION
                "perParaLen."
            ::= { odu3_tcm4Per24HHisEntry 2 }

        -- 1.3.6.1.4.1.2011.2.25.3.40.50.135.40.1.3
        odu3_tcm4Per24HHisPara OBJECT-TYPE
            SYNTAX OCTET STRING (SIZE (0..100))
            MAX-ACCESS read-only
            STATUS current
            DESCRIPTION
                "perPara."
            ::= { odu3_tcm4Per24HHisEntry 3 }

        -- 1.3.6.1.4.1.2011.2.25.3.40.50.135.40.1.4
        odu3_tcm4Per24HHisMonValue OBJECT-TYPE
            SYNTAX OCTET STRING (SIZE (0..100))
            MAX-ACCESS read-only
            STATUS current
            DESCRIPTION
                "perMonValue."
            ::= { odu3_tcm4Per24HHisEntry 4 }

        -- 1.3.6.1.4.1.2011.2.25.3.40.50.135.40.1.5
        odu3_tcm4Per24HHisDateTimeStart OBJECT-TYPE
            SYNTAX DateAndTime
            MAX-ACCESS read-only
            STATUS current
            DESCRIPTION
                "perDateTimeStart. "
            ::= { odu3_tcm4Per24HHisEntry 5 }

        -- 1.3.6.1.4.1.2011.2.25.3.40.50.135.40.1.6
        odu3_tcm4Per24HHisDateTimeEnd OBJECT-TYPE
            SYNTAX DateAndTime
            MAX-ACCESS read-only
            STATUS current
            DESCRIPTION
                "perDateTimeEnd. "
            ::= { odu3_tcm4Per24HHisEntry 6 }

        -- 1.3.6.1.4.1.2011.2.25.3.40.50.135.40.1.7
        odu3_tcm4Per24HHisVldty OBJECT-TYPE
            SYNTAX INTEGER
            MAX-ACCESS read-only
            STATUS current
            DESCRIPTION
                "perVldty. "
            ::= { odu3_tcm4Per24HHisEntry 7 }




-- Alarm data
      -- 1.3.6.1.4.1.2011.2.25.3.40.50.136
      odu3_tcm5 OBJECT IDENTIFIER ::={ optixGlobalNGWDM 136 }


-- -------------------------------------------------------------------------
-- Perfomance 15-MIN Current Data Table (RTRV-PER-<MOD2>)
-- -------------------------------------------------------------------------
        -- 1.3.6.1.4.1.2011.2.25.3.40.50.136.10
        odu3_tcm5Per15MCurTable OBJECT-TYPE
          SYNTAX SEQUENCE OF Odu3_tcm5Per15MCurEntry
          MAX-ACCESS not-accessible
          STATUS current
          DESCRIPTION
              "odu3_tcm5Per15MCur."
          ::= { odu3_tcm5 10 }

        -- 1.3.6.1.4.1.2011.2.25.3.40.50.136.10.1
        odu3_tcm5Per15MCurEntry OBJECT-TYPE
            SYNTAX Odu3_tcm5Per15MCurEntry
            MAX-ACCESS not-accessible
            STATUS current
            DESCRIPTION
              "odu3_tcm5Per15MCur."
            INDEX { odu3_tcm5Per15MCurEid, odu3_tcm5Per15MCurPara }
            ::= { odu3_tcm5Per15MCurTable 1 }

        Odu3_tcm5Per15MCurEntry ::=
            SEQUENCE {
                odu3_tcm5Per15MCurEid
                    PerformanceEventType,
                odu3_tcm5Per15MCurMonValue
                    OCTET STRING,
                odu3_tcm5Per15MCurVldty
                    INTEGER,
                odu3_tcm5Per15MCurDateTime
                    DateAndTime,
                odu3_tcm5Per15MCurParaLen
                    INTEGER,
                odu3_tcm5Per15MCurPara
                    OCTET STRING
            }

        -- 1.3.6.1.4.1.2011.2.25.3.40.50.136.10.1.1
        odu3_tcm5Per15MCurEid OBJECT-TYPE
            SYNTAX PerformanceEventType
            MAX-ACCESS read-only
            STATUS current
            DESCRIPTION
                "perEid."
            ::= { odu3_tcm5Per15MCurEntry 1 }

        -- 1.3.6.1.4.1.2011.2.25.3.40.50.136.10.1.2
        odu3_tcm5Per15MCurMonValue OBJECT-TYPE
            SYNTAX OCTET STRING (SIZE (0..100))
            MAX-ACCESS read-only
            STATUS current
            DESCRIPTION
                "perMonValue."
            ::= { odu3_tcm5Per15MCurEntry 2 }

        -- 1.3.6.1.4.1.2011.2.25.3.40.50.136.10.1.3
        odu3_tcm5Per15MCurVldty OBJECT-TYPE
            SYNTAX INTEGER
            MAX-ACCESS read-only
            STATUS current
            DESCRIPTION
                "perVldty. "
            ::= { odu3_tcm5Per15MCurEntry 3 }

        -- 1.3.6.1.4.1.2011.2.25.3.40.50.136.10.1.4
        odu3_tcm5Per15MCurDateTime OBJECT-TYPE
            SYNTAX DateAndTime
            MAX-ACCESS read-only
            STATUS current
            DESCRIPTION
                "perDateTime. "
            ::= { odu3_tcm5Per15MCurEntry 4 }

        -- 1.3.6.1.4.1.2011.2.25.3.40.50.136.10.1.5
        odu3_tcm5Per15MCurParaLen OBJECT-TYPE
            SYNTAX INTEGER
            MAX-ACCESS read-only
            STATUS current
            DESCRIPTION
                "perParaLen."
            ::= { odu3_tcm5Per15MCurEntry 5 }

        -- 1.3.6.1.4.1.2011.2.25.3.40.50.136.10.1.6
        odu3_tcm5Per15MCurPara OBJECT-TYPE
            SYNTAX OCTET STRING (SIZE (0..100))
            MAX-ACCESS read-only
            STATUS current
            DESCRIPTION
                "perPara."
            ::= { odu3_tcm5Per15MCurEntry 6 }




-- -------------------------------------------------------------------------
-- Perfomance 15-MIN History Data Table (RTRV-PER-<MOD2>)
-- -------------------------------------------------------------------------
        -- 1.3.6.1.4.1.2011.2.25.3.40.50.136.20
        odu3_tcm5Per15MHisTable OBJECT-TYPE
          SYNTAX SEQUENCE OF Odu3_tcm5Per15MHisEntry
          MAX-ACCESS not-accessible
          STATUS current
          DESCRIPTION
              "odu3_tcm5Per15MHis."
          ::= { odu3_tcm5 20 }

        -- 1.3.6.1.4.1.2011.2.25.3.40.50.136.20.1
        odu3_tcm5Per15MHisEntry OBJECT-TYPE
            SYNTAX Odu3_tcm5Per15MHisEntry
            MAX-ACCESS not-accessible
            STATUS current
            DESCRIPTION
                "odu3_tcm5Per15MHis."
            INDEX {odu3_tcm5Per15MHisEid, odu3_tcm5Per15MHisParaLen, odu3_tcm5Per15MHisPara, odu3_tcm5Per15MHisDateTimeStart, odu3_tcm5Per15MHisDateTimeEnd}
            ::= { odu3_tcm5Per15MHisTable 1 }

        Odu3_tcm5Per15MHisEntry ::=
            SEQUENCE {
                odu3_tcm5Per15MHisEid
                    PerformanceEventType,
                odu3_tcm5Per15MHisParaLen
                    INTEGER,
                odu3_tcm5Per15MHisPara
                    OCTET STRING,
                odu3_tcm5Per15MHisMonValue
                    OCTET STRING,
                odu3_tcm5Per15MHisDateTimeStart
                    DateAndTime,
                odu3_tcm5Per15MHisDateTimeEnd
                    DateAndTime,
                odu3_tcm5Per15MHisVldty
                    INTEGER,
             }

        -- 1.3.6.1.4.1.2011.2.25.3.40.50.136.20.1.1
        odu3_tcm5Per15MHisEid OBJECT-TYPE
            SYNTAX PerformanceEventType
            MAX-ACCESS read-only
            STATUS current
            DESCRIPTION
                "perEid."
            ::= { odu3_tcm5Per15MHisEntry 1 }

        -- 1.3.6.1.4.1.2011.2.25.3.40.50.136.20.1.2
        odu3_tcm5Per15MHisParaLen OBJECT-TYPE
            SYNTAX INTEGER
            MAX-ACCESS read-only
            STATUS current
            DESCRIPTION
                "perParaLen."
            ::= { odu3_tcm5Per15MHisEntry 2 }

        -- 1.3.6.1.4.1.2011.2.25.3.40.50.136.20.1.3
        odu3_tcm5Per15MHisPara OBJECT-TYPE
            SYNTAX OCTET STRING (SIZE (0..100))
            MAX-ACCESS read-only
            STATUS current
            DESCRIPTION
                "perPara."
            ::= { odu3_tcm5Per15MHisEntry 3 }

        -- 1.3.6.1.4.1.2011.2.25.3.40.50.136.20.1.4
        odu3_tcm5Per15MHisMonValue OBJECT-TYPE
            SYNTAX OCTET STRING (SIZE (0..100))
            MAX-ACCESS read-only
            STATUS current
            DESCRIPTION
                "perMonValue."
            ::= { odu3_tcm5Per15MHisEntry 4 }

        -- 1.3.6.1.4.1.2011.2.25.3.40.50.136.20.1.5
        odu3_tcm5Per15MHisDateTimeStart OBJECT-TYPE
            SYNTAX DateAndTime
            MAX-ACCESS read-only
            STATUS current
            DESCRIPTION
                "perDateTimeStart. "
            ::= { odu3_tcm5Per15MHisEntry 5 }

        -- 1.3.6.1.4.1.2011.2.25.3.40.50.136.20.1.6
        odu3_tcm5Per15MHisDateTimeEnd OBJECT-TYPE
            SYNTAX DateAndTime
            MAX-ACCESS read-only
            STATUS current
            DESCRIPTION
                "perDateTimeEnd. "
            ::= { odu3_tcm5Per15MHisEntry 6 }

        -- 1.3.6.1.4.1.2011.2.25.3.40.50.136.20.1.7
        odu3_tcm5Per15MHisVldty OBJECT-TYPE
            SYNTAX INTEGER
            MAX-ACCESS read-only
            STATUS current
            DESCRIPTION
                "perVldty. "
            ::= { odu3_tcm5Per15MHisEntry 7 }




-- -------------------------------------------------------------------------
-- Perfomance 24-HOUR Current Data Table (RTRV-PER-<MOD2>)
-- -------------------------------------------------------------------------
        -- 1.3.6.1.4.1.2011.2.25.3.40.50.136.30
        odu3_tcm5Per24HCurTable OBJECT-TYPE
          SYNTAX SEQUENCE OF Odu3_tcm5Per24HCurEntry
          MAX-ACCESS not-accessible
          STATUS current
          DESCRIPTION
              "odu3_tcm5Per24HCur."
          ::= { odu3_tcm5 30 }

        -- 1.3.6.1.4.1.2011.2.25.3.40.50.136.30.1
        odu3_tcm5Per24HCurEntry OBJECT-TYPE
            SYNTAX Odu3_tcm5Per24HCurEntry
            MAX-ACCESS not-accessible
            STATUS current
            DESCRIPTION
              "odu3_tcm5Per24HCur."
            INDEX { odu3_tcm5Per24HCurEid, odu3_tcm5Per24HCurPara }
            ::= { odu3_tcm5Per24HCurTable 1 }

        Odu3_tcm5Per24HCurEntry ::=
            SEQUENCE {
                odu3_tcm5Per24HCurEid
                    PerformanceEventType,
                odu3_tcm5Per24HCurMonValue
                    OCTET STRING,
                odu3_tcm5Per24HCurVldty
                    INTEGER,
                odu3_tcm5Per24HCurDateTime
                    DateAndTime,
                odu3_tcm5Per24HCurParaLen
                    INTEGER,
                odu3_tcm5Per24HCurPara
                    OCTET STRING
            }

        -- 1.3.6.1.4.1.2011.2.25.3.40.50.136.30.1.1
        odu3_tcm5Per24HCurEid OBJECT-TYPE
            SYNTAX PerformanceEventType
            MAX-ACCESS read-only
            STATUS current
            DESCRIPTION
                "perEid."
            ::= { odu3_tcm5Per24HCurEntry 1 }

        -- 1.3.6.1.4.1.2011.2.25.3.40.50.136.30.1.2
        odu3_tcm5Per24HCurMonValue OBJECT-TYPE
            SYNTAX OCTET STRING (SIZE (0..100))
            MAX-ACCESS read-only
            STATUS current
            DESCRIPTION
                "perMonValue."
            ::= { odu3_tcm5Per24HCurEntry 2 }

        -- 1.3.6.1.4.1.2011.2.25.3.40.50.136.30.1.3
        odu3_tcm5Per24HCurVldty OBJECT-TYPE
            SYNTAX INTEGER
            MAX-ACCESS read-only
            STATUS current
            DESCRIPTION
                "perVldty. "
            ::= { odu3_tcm5Per24HCurEntry 3 }

        -- 1.3.6.1.4.1.2011.2.25.3.40.50.136.30.1.4
        odu3_tcm5Per24HCurDateTime OBJECT-TYPE
            SYNTAX DateAndTime
            MAX-ACCESS read-only
            STATUS current
            DESCRIPTION
                "perDateTime. "
            ::= { odu3_tcm5Per24HCurEntry 4 }

        -- 1.3.6.1.4.1.2011.2.25.3.40.50.136.30.1.5
        odu3_tcm5Per24HCurParaLen OBJECT-TYPE
            SYNTAX INTEGER
            MAX-ACCESS read-only
            STATUS current
            DESCRIPTION
                "perParaLen."
            ::= { odu3_tcm5Per24HCurEntry 5 }

        -- 1.3.6.1.4.1.2011.2.25.3.40.50.136.30.1.6
        odu3_tcm5Per24HCurPara OBJECT-TYPE
            SYNTAX OCTET STRING (SIZE (0..100))
            MAX-ACCESS read-only
            STATUS current
            DESCRIPTION
                "perPara."
            ::= { odu3_tcm5Per24HCurEntry 6 }




-- -------------------------------------------------------------------------
-- Perfomance 24-HOUR History Data Table (RTRV-PER-<MOD2>)
-- -------------------------------------------------------------------------
        -- 1.3.6.1.4.1.2011.2.25.3.40.50.136.40
        odu3_tcm5Per24HHisTable OBJECT-TYPE
          SYNTAX SEQUENCE OF Odu3_tcm5Per24HHisEntry
          MAX-ACCESS not-accessible
          STATUS current
          DESCRIPTION
              "odu3_tcm5Per24HHis."
          ::= { odu3_tcm5 40 }

        -- 1.3.6.1.4.1.2011.2.25.3.40.50.136.40.1
        odu3_tcm5Per24HHisEntry OBJECT-TYPE
            SYNTAX Odu3_tcm5Per24HHisEntry
            MAX-ACCESS not-accessible
            STATUS current
            DESCRIPTION
                "odu3_tcm5Per24HHis."
            INDEX {odu3_tcm5Per24HHisEid, odu3_tcm5Per24HHisParaLen, odu3_tcm5Per24HHisPara, odu3_tcm5Per24HHisDateTimeStart, odu3_tcm5Per24HHisDateTimeEnd}
            ::= { odu3_tcm5Per24HHisTable 1 }

        Odu3_tcm5Per24HHisEntry ::=
            SEQUENCE {
                odu3_tcm5Per24HHisEid
                    PerformanceEventType,
                odu3_tcm5Per24HHisParaLen
                    INTEGER,
                odu3_tcm5Per24HHisPara
                    OCTET STRING,
                odu3_tcm5Per24HHisMonValue
                    OCTET STRING,
                odu3_tcm5Per24HHisDateTimeStart
                    DateAndTime,
                odu3_tcm5Per24HHisDateTimeEnd
                    DateAndTime,
                odu3_tcm5Per24HHisVldty
                    INTEGER,
             }

        -- 1.3.6.1.4.1.2011.2.25.3.40.50.136.40.1.1
        odu3_tcm5Per24HHisEid OBJECT-TYPE
            SYNTAX PerformanceEventType
            MAX-ACCESS read-only
            STATUS current
            DESCRIPTION
                "perEid."
            ::= { odu3_tcm5Per24HHisEntry 1 }

        -- 1.3.6.1.4.1.2011.2.25.3.40.50.136.40.1.2
        odu3_tcm5Per24HHisParaLen OBJECT-TYPE
            SYNTAX INTEGER
            MAX-ACCESS read-only
            STATUS current
            DESCRIPTION
                "perParaLen."
            ::= { odu3_tcm5Per24HHisEntry 2 }

        -- 1.3.6.1.4.1.2011.2.25.3.40.50.136.40.1.3
        odu3_tcm5Per24HHisPara OBJECT-TYPE
            SYNTAX OCTET STRING (SIZE (0..100))
            MAX-ACCESS read-only
            STATUS current
            DESCRIPTION
                "perPara."
            ::= { odu3_tcm5Per24HHisEntry 3 }

        -- 1.3.6.1.4.1.2011.2.25.3.40.50.136.40.1.4
        odu3_tcm5Per24HHisMonValue OBJECT-TYPE
            SYNTAX OCTET STRING (SIZE (0..100))
            MAX-ACCESS read-only
            STATUS current
            DESCRIPTION
                "perMonValue."
            ::= { odu3_tcm5Per24HHisEntry 4 }

        -- 1.3.6.1.4.1.2011.2.25.3.40.50.136.40.1.5
        odu3_tcm5Per24HHisDateTimeStart OBJECT-TYPE
            SYNTAX DateAndTime
            MAX-ACCESS read-only
            STATUS current
            DESCRIPTION
                "perDateTimeStart. "
            ::= { odu3_tcm5Per24HHisEntry 5 }

        -- 1.3.6.1.4.1.2011.2.25.3.40.50.136.40.1.6
        odu3_tcm5Per24HHisDateTimeEnd OBJECT-TYPE
            SYNTAX DateAndTime
            MAX-ACCESS read-only
            STATUS current
            DESCRIPTION
                "perDateTimeEnd. "
            ::= { odu3_tcm5Per24HHisEntry 6 }

        -- 1.3.6.1.4.1.2011.2.25.3.40.50.136.40.1.7
        odu3_tcm5Per24HHisVldty OBJECT-TYPE
            SYNTAX INTEGER
            MAX-ACCESS read-only
            STATUS current
            DESCRIPTION
                "perVldty. "
            ::= { odu3_tcm5Per24HHisEntry 7 }




-- Alarm data
      -- 1.3.6.1.4.1.2011.2.25.3.40.50.137
      odu3_tcm6 OBJECT IDENTIFIER ::={ optixGlobalNGWDM 137 }


-- -------------------------------------------------------------------------
-- Perfomance 15-MIN Current Data Table (RTRV-PER-<MOD2>)
-- -------------------------------------------------------------------------
        -- 1.3.6.1.4.1.2011.2.25.3.40.50.137.10
        odu3_tcm6Per15MCurTable OBJECT-TYPE
          SYNTAX SEQUENCE OF Odu3_tcm6Per15MCurEntry
          MAX-ACCESS not-accessible
          STATUS current
          DESCRIPTION
              "odu3_tcm6Per15MCur."
          ::= { odu3_tcm6 10 }

        -- 1.3.6.1.4.1.2011.2.25.3.40.50.137.10.1
        odu3_tcm6Per15MCurEntry OBJECT-TYPE
            SYNTAX Odu3_tcm6Per15MCurEntry
            MAX-ACCESS not-accessible
            STATUS current
            DESCRIPTION
              "odu3_tcm6Per15MCur."
            INDEX { odu3_tcm6Per15MCurEid, odu3_tcm6Per15MCurPara }
            ::= { odu3_tcm6Per15MCurTable 1 }

        Odu3_tcm6Per15MCurEntry ::=
            SEQUENCE {
                odu3_tcm6Per15MCurEid
                    PerformanceEventType,
                odu3_tcm6Per15MCurMonValue
                    OCTET STRING,
                odu3_tcm6Per15MCurVldty
                    INTEGER,
                odu3_tcm6Per15MCurDateTime
                    DateAndTime,
                odu3_tcm6Per15MCurParaLen
                    INTEGER,
                odu3_tcm6Per15MCurPara
                    OCTET STRING
            }

        -- 1.3.6.1.4.1.2011.2.25.3.40.50.137.10.1.1
        odu3_tcm6Per15MCurEid OBJECT-TYPE
            SYNTAX PerformanceEventType
            MAX-ACCESS read-only
            STATUS current
            DESCRIPTION
                "perEid."
            ::= { odu3_tcm6Per15MCurEntry 1 }

        -- 1.3.6.1.4.1.2011.2.25.3.40.50.137.10.1.2
        odu3_tcm6Per15MCurMonValue OBJECT-TYPE
            SYNTAX OCTET STRING (SIZE (0..100))
            MAX-ACCESS read-only
            STATUS current
            DESCRIPTION
                "perMonValue."
            ::= { odu3_tcm6Per15MCurEntry 2 }

        -- 1.3.6.1.4.1.2011.2.25.3.40.50.137.10.1.3
        odu3_tcm6Per15MCurVldty OBJECT-TYPE
            SYNTAX INTEGER
            MAX-ACCESS read-only
            STATUS current
            DESCRIPTION
                "perVldty. "
            ::= { odu3_tcm6Per15MCurEntry 3 }

        -- 1.3.6.1.4.1.2011.2.25.3.40.50.137.10.1.4
        odu3_tcm6Per15MCurDateTime OBJECT-TYPE
            SYNTAX DateAndTime
            MAX-ACCESS read-only
            STATUS current
            DESCRIPTION
                "perDateTime. "
            ::= { odu3_tcm6Per15MCurEntry 4 }

        -- 1.3.6.1.4.1.2011.2.25.3.40.50.137.10.1.5
        odu3_tcm6Per15MCurParaLen OBJECT-TYPE
            SYNTAX INTEGER
            MAX-ACCESS read-only
            STATUS current
            DESCRIPTION
                "perParaLen."
            ::= { odu3_tcm6Per15MCurEntry 5 }

        -- 1.3.6.1.4.1.2011.2.25.3.40.50.137.10.1.6
        odu3_tcm6Per15MCurPara OBJECT-TYPE
            SYNTAX OCTET STRING (SIZE (0..100))
            MAX-ACCESS read-only
            STATUS current
            DESCRIPTION
                "perPara."
            ::= { odu3_tcm6Per15MCurEntry 6 }




-- -------------------------------------------------------------------------
-- Perfomance 15-MIN History Data Table (RTRV-PER-<MOD2>)
-- -------------------------------------------------------------------------
        -- 1.3.6.1.4.1.2011.2.25.3.40.50.137.20
        odu3_tcm6Per15MHisTable OBJECT-TYPE
          SYNTAX SEQUENCE OF Odu3_tcm6Per15MHisEntry
          MAX-ACCESS not-accessible
          STATUS current
          DESCRIPTION
              "odu3_tcm6Per15MHis."
          ::= { odu3_tcm6 20 }

        -- 1.3.6.1.4.1.2011.2.25.3.40.50.137.20.1
        odu3_tcm6Per15MHisEntry OBJECT-TYPE
            SYNTAX Odu3_tcm6Per15MHisEntry
            MAX-ACCESS not-accessible
            STATUS current
            DESCRIPTION
                "odu3_tcm6Per15MHis."
            INDEX {odu3_tcm6Per15MHisEid, odu3_tcm6Per15MHisParaLen, odu3_tcm6Per15MHisPara, odu3_tcm6Per15MHisDateTimeStart, odu3_tcm6Per15MHisDateTimeEnd}
            ::= { odu3_tcm6Per15MHisTable 1 }

        Odu3_tcm6Per15MHisEntry ::=
            SEQUENCE {
                odu3_tcm6Per15MHisEid
                    PerformanceEventType,
                odu3_tcm6Per15MHisParaLen
                    INTEGER,
                odu3_tcm6Per15MHisPara
                    OCTET STRING,
                odu3_tcm6Per15MHisMonValue
                    OCTET STRING,
                odu3_tcm6Per15MHisDateTimeStart
                    DateAndTime,
                odu3_tcm6Per15MHisDateTimeEnd
                    DateAndTime,
                odu3_tcm6Per15MHisVldty
                    INTEGER,
             }

        -- 1.3.6.1.4.1.2011.2.25.3.40.50.137.20.1.1
        odu3_tcm6Per15MHisEid OBJECT-TYPE
            SYNTAX PerformanceEventType
            MAX-ACCESS read-only
            STATUS current
            DESCRIPTION
                "perEid."
            ::= { odu3_tcm6Per15MHisEntry 1 }

        -- 1.3.6.1.4.1.2011.2.25.3.40.50.137.20.1.2
        odu3_tcm6Per15MHisParaLen OBJECT-TYPE
            SYNTAX INTEGER
            MAX-ACCESS read-only
            STATUS current
            DESCRIPTION
                "perParaLen."
            ::= { odu3_tcm6Per15MHisEntry 2 }

        -- 1.3.6.1.4.1.2011.2.25.3.40.50.137.20.1.3
        odu3_tcm6Per15MHisPara OBJECT-TYPE
            SYNTAX OCTET STRING (SIZE (0..100))
            MAX-ACCESS read-only
            STATUS current
            DESCRIPTION
                "perPara."
            ::= { odu3_tcm6Per15MHisEntry 3 }

        -- 1.3.6.1.4.1.2011.2.25.3.40.50.137.20.1.4
        odu3_tcm6Per15MHisMonValue OBJECT-TYPE
            SYNTAX OCTET STRING (SIZE (0..100))
            MAX-ACCESS read-only
            STATUS current
            DESCRIPTION
                "perMonValue."
            ::= { odu3_tcm6Per15MHisEntry 4 }

        -- 1.3.6.1.4.1.2011.2.25.3.40.50.137.20.1.5
        odu3_tcm6Per15MHisDateTimeStart OBJECT-TYPE
            SYNTAX DateAndTime
            MAX-ACCESS read-only
            STATUS current
            DESCRIPTION
                "perDateTimeStart. "
            ::= { odu3_tcm6Per15MHisEntry 5 }

        -- 1.3.6.1.4.1.2011.2.25.3.40.50.137.20.1.6
        odu3_tcm6Per15MHisDateTimeEnd OBJECT-TYPE
            SYNTAX DateAndTime
            MAX-ACCESS read-only
            STATUS current
            DESCRIPTION
                "perDateTimeEnd. "
            ::= { odu3_tcm6Per15MHisEntry 6 }

        -- 1.3.6.1.4.1.2011.2.25.3.40.50.137.20.1.7
        odu3_tcm6Per15MHisVldty OBJECT-TYPE
            SYNTAX INTEGER
            MAX-ACCESS read-only
            STATUS current
            DESCRIPTION
                "perVldty. "
            ::= { odu3_tcm6Per15MHisEntry 7 }




-- -------------------------------------------------------------------------
-- Perfomance 24-HOUR Current Data Table (RTRV-PER-<MOD2>)
-- -------------------------------------------------------------------------
        -- 1.3.6.1.4.1.2011.2.25.3.40.50.137.30
        odu3_tcm6Per24HCurTable OBJECT-TYPE
          SYNTAX SEQUENCE OF Odu3_tcm6Per24HCurEntry
          MAX-ACCESS not-accessible
          STATUS current
          DESCRIPTION
              "odu3_tcm6Per24HCur."
          ::= { odu3_tcm6 30 }

        -- 1.3.6.1.4.1.2011.2.25.3.40.50.137.30.1
        odu3_tcm6Per24HCurEntry OBJECT-TYPE
            SYNTAX Odu3_tcm6Per24HCurEntry
            MAX-ACCESS not-accessible
            STATUS current
            DESCRIPTION
              "odu3_tcm6Per24HCur."
            INDEX { odu3_tcm6Per24HCurEid, odu3_tcm6Per24HCurPara }
            ::= { odu3_tcm6Per24HCurTable 1 }

        Odu3_tcm6Per24HCurEntry ::=
            SEQUENCE {
                odu3_tcm6Per24HCurEid
                    PerformanceEventType,
                odu3_tcm6Per24HCurMonValue
                    OCTET STRING,
                odu3_tcm6Per24HCurVldty
                    INTEGER,
                odu3_tcm6Per24HCurDateTime
                    DateAndTime,
                odu3_tcm6Per24HCurParaLen
                    INTEGER,
                odu3_tcm6Per24HCurPara
                    OCTET STRING
            }

        -- 1.3.6.1.4.1.2011.2.25.3.40.50.137.30.1.1
        odu3_tcm6Per24HCurEid OBJECT-TYPE
            SYNTAX PerformanceEventType
            MAX-ACCESS read-only
            STATUS current
            DESCRIPTION
                "perEid."
            ::= { odu3_tcm6Per24HCurEntry 1 }

        -- 1.3.6.1.4.1.2011.2.25.3.40.50.137.30.1.2
        odu3_tcm6Per24HCurMonValue OBJECT-TYPE
            SYNTAX OCTET STRING (SIZE (0..100))
            MAX-ACCESS read-only
            STATUS current
            DESCRIPTION
                "perMonValue."
            ::= { odu3_tcm6Per24HCurEntry 2 }

        -- 1.3.6.1.4.1.2011.2.25.3.40.50.137.30.1.3
        odu3_tcm6Per24HCurVldty OBJECT-TYPE
            SYNTAX INTEGER
            MAX-ACCESS read-only
            STATUS current
            DESCRIPTION
                "perVldty. "
            ::= { odu3_tcm6Per24HCurEntry 3 }

        -- 1.3.6.1.4.1.2011.2.25.3.40.50.137.30.1.4
        odu3_tcm6Per24HCurDateTime OBJECT-TYPE
            SYNTAX DateAndTime
            MAX-ACCESS read-only
            STATUS current
            DESCRIPTION
                "perDateTime. "
            ::= { odu3_tcm6Per24HCurEntry 4 }

        -- 1.3.6.1.4.1.2011.2.25.3.40.50.137.30.1.5
        odu3_tcm6Per24HCurParaLen OBJECT-TYPE
            SYNTAX INTEGER
            MAX-ACCESS read-only
            STATUS current
            DESCRIPTION
                "perParaLen."
            ::= { odu3_tcm6Per24HCurEntry 5 }

        -- 1.3.6.1.4.1.2011.2.25.3.40.50.137.30.1.6
        odu3_tcm6Per24HCurPara OBJECT-TYPE
            SYNTAX OCTET STRING (SIZE (0..100))
            MAX-ACCESS read-only
            STATUS current
            DESCRIPTION
                "perPara."
            ::= { odu3_tcm6Per24HCurEntry 6 }




-- -------------------------------------------------------------------------
-- Perfomance 24-HOUR History Data Table (RTRV-PER-<MOD2>)
-- -------------------------------------------------------------------------
        -- 1.3.6.1.4.1.2011.2.25.3.40.50.137.40
        odu3_tcm6Per24HHisTable OBJECT-TYPE
          SYNTAX SEQUENCE OF Odu3_tcm6Per24HHisEntry
          MAX-ACCESS not-accessible
          STATUS current
          DESCRIPTION
              "odu3_tcm6Per24HHis."
          ::= { odu3_tcm6 40 }

        -- 1.3.6.1.4.1.2011.2.25.3.40.50.137.40.1
        odu3_tcm6Per24HHisEntry OBJECT-TYPE
            SYNTAX Odu3_tcm6Per24HHisEntry
            MAX-ACCESS not-accessible
            STATUS current
            DESCRIPTION
                "odu3_tcm6Per24HHis."
            INDEX {odu3_tcm6Per24HHisEid, odu3_tcm6Per24HHisParaLen, odu3_tcm6Per24HHisPara, odu3_tcm6Per24HHisDateTimeStart, odu3_tcm6Per24HHisDateTimeEnd}
            ::= { odu3_tcm6Per24HHisTable 1 }

        Odu3_tcm6Per24HHisEntry ::=
            SEQUENCE {
                odu3_tcm6Per24HHisEid
                    PerformanceEventType,
                odu3_tcm6Per24HHisParaLen
                    INTEGER,
                odu3_tcm6Per24HHisPara
                    OCTET STRING,
                odu3_tcm6Per24HHisMonValue
                    OCTET STRING,
                odu3_tcm6Per24HHisDateTimeStart
                    DateAndTime,
                odu3_tcm6Per24HHisDateTimeEnd
                    DateAndTime,
                odu3_tcm6Per24HHisVldty
                    INTEGER,
             }

        -- 1.3.6.1.4.1.2011.2.25.3.40.50.137.40.1.1
        odu3_tcm6Per24HHisEid OBJECT-TYPE
            SYNTAX PerformanceEventType
            MAX-ACCESS read-only
            STATUS current
            DESCRIPTION
                "perEid."
            ::= { odu3_tcm6Per24HHisEntry 1 }

        -- 1.3.6.1.4.1.2011.2.25.3.40.50.137.40.1.2
        odu3_tcm6Per24HHisParaLen OBJECT-TYPE
            SYNTAX INTEGER
            MAX-ACCESS read-only
            STATUS current
            DESCRIPTION
                "perParaLen."
            ::= { odu3_tcm6Per24HHisEntry 2 }

        -- 1.3.6.1.4.1.2011.2.25.3.40.50.137.40.1.3
        odu3_tcm6Per24HHisPara OBJECT-TYPE
            SYNTAX OCTET STRING (SIZE (0..100))
            MAX-ACCESS read-only
            STATUS current
            DESCRIPTION
                "perPara."
            ::= { odu3_tcm6Per24HHisEntry 3 }

        -- 1.3.6.1.4.1.2011.2.25.3.40.50.137.40.1.4
        odu3_tcm6Per24HHisMonValue OBJECT-TYPE
            SYNTAX OCTET STRING (SIZE (0..100))
            MAX-ACCESS read-only
            STATUS current
            DESCRIPTION
                "perMonValue."
            ::= { odu3_tcm6Per24HHisEntry 4 }

        -- 1.3.6.1.4.1.2011.2.25.3.40.50.137.40.1.5
        odu3_tcm6Per24HHisDateTimeStart OBJECT-TYPE
            SYNTAX DateAndTime
            MAX-ACCESS read-only
            STATUS current
            DESCRIPTION
                "perDateTimeStart. "
            ::= { odu3_tcm6Per24HHisEntry 5 }

        -- 1.3.6.1.4.1.2011.2.25.3.40.50.137.40.1.6
        odu3_tcm6Per24HHisDateTimeEnd OBJECT-TYPE
            SYNTAX DateAndTime
            MAX-ACCESS read-only
            STATUS current
            DESCRIPTION
                "perDateTimeEnd. "
            ::= { odu3_tcm6Per24HHisEntry 6 }

        -- 1.3.6.1.4.1.2011.2.25.3.40.50.137.40.1.7
        odu3_tcm6Per24HHisVldty OBJECT-TYPE
            SYNTAX INTEGER
            MAX-ACCESS read-only
            STATUS current
            DESCRIPTION
                "perVldty. "
            ::= { odu3_tcm6Per24HHisEntry 7 }




-- Alarm data
      -- 1.3.6.1.4.1.2011.2.25.3.40.50.144
      sdh_optport OBJECT IDENTIFIER ::={ optixGlobalNGWDM 144 }


-- -------------------------------------------------------------------------
-- Perfomance 15-MIN Current Data Table (RTRV-PER-<MOD2>)
-- -------------------------------------------------------------------------
        -- 1.3.6.1.4.1.2011.2.25.3.40.50.144.10
        sdh_optportPer15MCurTable OBJECT-TYPE
          SYNTAX SEQUENCE OF Sdh_optportPer15MCurEntry
          MAX-ACCESS not-accessible
          STATUS current
          DESCRIPTION
              "sdh_optportPer15MCur."
          ::= { sdh_optport 10 }

        -- 1.3.6.1.4.1.2011.2.25.3.40.50.144.10.1
        sdh_optportPer15MCurEntry OBJECT-TYPE
            SYNTAX Sdh_optportPer15MCurEntry
            MAX-ACCESS not-accessible
            STATUS current
            DESCRIPTION
              "sdh_optportPer15MCur."
            INDEX { sdh_optportPer15MCurEid, sdh_optportPer15MCurPara }
            ::= { sdh_optportPer15MCurTable 1 }

        Sdh_optportPer15MCurEntry ::=
            SEQUENCE {
                sdh_optportPer15MCurEid
                    PerformanceEventType,
                sdh_optportPer15MCurMonValue
                    OCTET STRING,
                sdh_optportPer15MCurVldty
                    INTEGER,
                sdh_optportPer15MCurDateTime
                    DateAndTime,
                sdh_optportPer15MCurParaLen
                    INTEGER,
                sdh_optportPer15MCurPara
                    OCTET STRING
            }

        -- 1.3.6.1.4.1.2011.2.25.3.40.50.144.10.1.1
        sdh_optportPer15MCurEid OBJECT-TYPE
            SYNTAX PerformanceEventType
            MAX-ACCESS read-only
            STATUS current
            DESCRIPTION
                "perEid."
            ::= { sdh_optportPer15MCurEntry 1 }

        -- 1.3.6.1.4.1.2011.2.25.3.40.50.144.10.1.2
        sdh_optportPer15MCurMonValue OBJECT-TYPE
            SYNTAX OCTET STRING (SIZE (0..100))
            MAX-ACCESS read-only
            STATUS current
            DESCRIPTION
                "perMonValue."
            ::= { sdh_optportPer15MCurEntry 2 }

        -- 1.3.6.1.4.1.2011.2.25.3.40.50.144.10.1.3
        sdh_optportPer15MCurVldty OBJECT-TYPE
            SYNTAX INTEGER
            MAX-ACCESS read-only
            STATUS current
            DESCRIPTION
                "perVldty. "
            ::= { sdh_optportPer15MCurEntry 3 }

        -- 1.3.6.1.4.1.2011.2.25.3.40.50.144.10.1.4
        sdh_optportPer15MCurDateTime OBJECT-TYPE
            SYNTAX DateAndTime
            MAX-ACCESS read-only
            STATUS current
            DESCRIPTION
                "perDateTime. "
            ::= { sdh_optportPer15MCurEntry 4 }

        -- 1.3.6.1.4.1.2011.2.25.3.40.50.144.10.1.5
        sdh_optportPer15MCurParaLen OBJECT-TYPE
            SYNTAX INTEGER
            MAX-ACCESS read-only
            STATUS current
            DESCRIPTION
                "perParaLen."
            ::= { sdh_optportPer15MCurEntry 5 }

        -- 1.3.6.1.4.1.2011.2.25.3.40.50.144.10.1.6
        sdh_optportPer15MCurPara OBJECT-TYPE
            SYNTAX OCTET STRING (SIZE (0..100))
            MAX-ACCESS read-only
            STATUS current
            DESCRIPTION
                "perPara."
            ::= { sdh_optportPer15MCurEntry 6 }




-- -------------------------------------------------------------------------
-- Perfomance 15-MIN History Data Table (RTRV-PER-<MOD2>)
-- -------------------------------------------------------------------------
        -- 1.3.6.1.4.1.2011.2.25.3.40.50.144.20
        sdh_optportPer15MHisTable OBJECT-TYPE
          SYNTAX SEQUENCE OF Sdh_optportPer15MHisEntry
          MAX-ACCESS not-accessible
          STATUS current
          DESCRIPTION
              "sdh_optportPer15MHis."
          ::= { sdh_optport 20 }

        -- 1.3.6.1.4.1.2011.2.25.3.40.50.144.20.1
        sdh_optportPer15MHisEntry OBJECT-TYPE
            SYNTAX Sdh_optportPer15MHisEntry
            MAX-ACCESS not-accessible
            STATUS current
            DESCRIPTION
                "sdh_optportPer15MHis."
            INDEX {sdh_optportPer15MHisEid, sdh_optportPer15MHisParaLen, sdh_optportPer15MHisPara, sdh_optportPer15MHisDateTimeStart, sdh_optportPer15MHisDateTimeEnd}
            ::= { sdh_optportPer15MHisTable 1 }

        Sdh_optportPer15MHisEntry ::=
            SEQUENCE {
                sdh_optportPer15MHisEid
                    PerformanceEventType,
                sdh_optportPer15MHisParaLen
                    INTEGER,
                sdh_optportPer15MHisPara
                    OCTET STRING,
                sdh_optportPer15MHisMonValue
                    OCTET STRING,
                sdh_optportPer15MHisDateTimeStart
                    DateAndTime,
                sdh_optportPer15MHisDateTimeEnd
                    DateAndTime,
                sdh_optportPer15MHisVldty
                    INTEGER,
             }

        -- 1.3.6.1.4.1.2011.2.25.3.40.50.144.20.1.1
        sdh_optportPer15MHisEid OBJECT-TYPE
            SYNTAX PerformanceEventType
            MAX-ACCESS read-only
            STATUS current
            DESCRIPTION
                "perEid."
            ::= { sdh_optportPer15MHisEntry 1 }

        -- 1.3.6.1.4.1.2011.2.25.3.40.50.144.20.1.2
        sdh_optportPer15MHisParaLen OBJECT-TYPE
            SYNTAX INTEGER
            MAX-ACCESS read-only
            STATUS current
            DESCRIPTION
                "perParaLen."
            ::= { sdh_optportPer15MHisEntry 2 }

        -- 1.3.6.1.4.1.2011.2.25.3.40.50.144.20.1.3
        sdh_optportPer15MHisPara OBJECT-TYPE
            SYNTAX OCTET STRING (SIZE (0..100))
            MAX-ACCESS read-only
            STATUS current
            DESCRIPTION
                "perPara."
            ::= { sdh_optportPer15MHisEntry 3 }

        -- 1.3.6.1.4.1.2011.2.25.3.40.50.144.20.1.4
        sdh_optportPer15MHisMonValue OBJECT-TYPE
            SYNTAX OCTET STRING (SIZE (0..100))
            MAX-ACCESS read-only
            STATUS current
            DESCRIPTION
                "perMonValue."
            ::= { sdh_optportPer15MHisEntry 4 }

        -- 1.3.6.1.4.1.2011.2.25.3.40.50.144.20.1.5
        sdh_optportPer15MHisDateTimeStart OBJECT-TYPE
            SYNTAX DateAndTime
            MAX-ACCESS read-only
            STATUS current
            DESCRIPTION
                "perDateTimeStart. "
            ::= { sdh_optportPer15MHisEntry 5 }

        -- 1.3.6.1.4.1.2011.2.25.3.40.50.144.20.1.6
        sdh_optportPer15MHisDateTimeEnd OBJECT-TYPE
            SYNTAX DateAndTime
            MAX-ACCESS read-only
            STATUS current
            DESCRIPTION
                "perDateTimeEnd. "
            ::= { sdh_optportPer15MHisEntry 6 }

        -- 1.3.6.1.4.1.2011.2.25.3.40.50.144.20.1.7
        sdh_optportPer15MHisVldty OBJECT-TYPE
            SYNTAX INTEGER
            MAX-ACCESS read-only
            STATUS current
            DESCRIPTION
                "perVldty. "
            ::= { sdh_optportPer15MHisEntry 7 }




-- -------------------------------------------------------------------------
-- Perfomance 24-HOUR Current Data Table (RTRV-PER-<MOD2>)
-- -------------------------------------------------------------------------
        -- 1.3.6.1.4.1.2011.2.25.3.40.50.144.30
        sdh_optportPer24HCurTable OBJECT-TYPE
          SYNTAX SEQUENCE OF Sdh_optportPer24HCurEntry
          MAX-ACCESS not-accessible
          STATUS current
          DESCRIPTION
              "sdh_optportPer24HCur."
          ::= { sdh_optport 30 }

        -- 1.3.6.1.4.1.2011.2.25.3.40.50.144.30.1
        sdh_optportPer24HCurEntry OBJECT-TYPE
            SYNTAX Sdh_optportPer24HCurEntry
            MAX-ACCESS not-accessible
            STATUS current
            DESCRIPTION
              "sdh_optportPer24HCur."
            INDEX { sdh_optportPer24HCurEid, sdh_optportPer24HCurPara }
            ::= { sdh_optportPer24HCurTable 1 }

        Sdh_optportPer24HCurEntry ::=
            SEQUENCE {
                sdh_optportPer24HCurEid
                    PerformanceEventType,
                sdh_optportPer24HCurMonValue
                    OCTET STRING,
                sdh_optportPer24HCurVldty
                    INTEGER,
                sdh_optportPer24HCurDateTime
                    DateAndTime,
                sdh_optportPer24HCurParaLen
                    INTEGER,
                sdh_optportPer24HCurPara
                    OCTET STRING
            }

        -- 1.3.6.1.4.1.2011.2.25.3.40.50.144.30.1.1
        sdh_optportPer24HCurEid OBJECT-TYPE
            SYNTAX PerformanceEventType
            MAX-ACCESS read-only
            STATUS current
            DESCRIPTION
                "perEid."
            ::= { sdh_optportPer24HCurEntry 1 }

        -- 1.3.6.1.4.1.2011.2.25.3.40.50.144.30.1.2
        sdh_optportPer24HCurMonValue OBJECT-TYPE
            SYNTAX OCTET STRING (SIZE (0..100))
            MAX-ACCESS read-only
            STATUS current
            DESCRIPTION
                "perMonValue."
            ::= { sdh_optportPer24HCurEntry 2 }

        -- 1.3.6.1.4.1.2011.2.25.3.40.50.144.30.1.3
        sdh_optportPer24HCurVldty OBJECT-TYPE
            SYNTAX INTEGER
            MAX-ACCESS read-only
            STATUS current
            DESCRIPTION
                "perVldty. "
            ::= { sdh_optportPer24HCurEntry 3 }

        -- 1.3.6.1.4.1.2011.2.25.3.40.50.144.30.1.4
        sdh_optportPer24HCurDateTime OBJECT-TYPE
            SYNTAX DateAndTime
            MAX-ACCESS read-only
            STATUS current
            DESCRIPTION
                "perDateTime. "
            ::= { sdh_optportPer24HCurEntry 4 }

        -- 1.3.6.1.4.1.2011.2.25.3.40.50.144.30.1.5
        sdh_optportPer24HCurParaLen OBJECT-TYPE
            SYNTAX INTEGER
            MAX-ACCESS read-only
            STATUS current
            DESCRIPTION
                "perParaLen."
            ::= { sdh_optportPer24HCurEntry 5 }

        -- 1.3.6.1.4.1.2011.2.25.3.40.50.144.30.1.6
        sdh_optportPer24HCurPara OBJECT-TYPE
            SYNTAX OCTET STRING (SIZE (0..100))
            MAX-ACCESS read-only
            STATUS current
            DESCRIPTION
                "perPara."
            ::= { sdh_optportPer24HCurEntry 6 }




-- -------------------------------------------------------------------------
-- Perfomance 24-HOUR History Data Table (RTRV-PER-<MOD2>)
-- -------------------------------------------------------------------------
        -- 1.3.6.1.4.1.2011.2.25.3.40.50.144.40
        sdh_optportPer24HHisTable OBJECT-TYPE
          SYNTAX SEQUENCE OF Sdh_optportPer24HHisEntry
          MAX-ACCESS not-accessible
          STATUS current
          DESCRIPTION
              "sdh_optportPer24HHis."
          ::= { sdh_optport 40 }

        -- 1.3.6.1.4.1.2011.2.25.3.40.50.144.40.1
        sdh_optportPer24HHisEntry OBJECT-TYPE
            SYNTAX Sdh_optportPer24HHisEntry
            MAX-ACCESS not-accessible
            STATUS current
            DESCRIPTION
                "sdh_optportPer24HHis."
            INDEX {sdh_optportPer24HHisEid, sdh_optportPer24HHisParaLen, sdh_optportPer24HHisPara, sdh_optportPer24HHisDateTimeStart, sdh_optportPer24HHisDateTimeEnd}
            ::= { sdh_optportPer24HHisTable 1 }

        Sdh_optportPer24HHisEntry ::=
            SEQUENCE {
                sdh_optportPer24HHisEid
                    PerformanceEventType,
                sdh_optportPer24HHisParaLen
                    INTEGER,
                sdh_optportPer24HHisPara
                    OCTET STRING,
                sdh_optportPer24HHisMonValue
                    OCTET STRING,
                sdh_optportPer24HHisDateTimeStart
                    DateAndTime,
                sdh_optportPer24HHisDateTimeEnd
                    DateAndTime,
                sdh_optportPer24HHisVldty
                    INTEGER,
             }

        -- 1.3.6.1.4.1.2011.2.25.3.40.50.144.40.1.1
        sdh_optportPer24HHisEid OBJECT-TYPE
            SYNTAX PerformanceEventType
            MAX-ACCESS read-only
            STATUS current
            DESCRIPTION
                "perEid."
            ::= { sdh_optportPer24HHisEntry 1 }

        -- 1.3.6.1.4.1.2011.2.25.3.40.50.144.40.1.2
        sdh_optportPer24HHisParaLen OBJECT-TYPE
            SYNTAX INTEGER
            MAX-ACCESS read-only
            STATUS current
            DESCRIPTION
                "perParaLen."
            ::= { sdh_optportPer24HHisEntry 2 }

        -- 1.3.6.1.4.1.2011.2.25.3.40.50.144.40.1.3
        sdh_optportPer24HHisPara OBJECT-TYPE
            SYNTAX OCTET STRING (SIZE (0..100))
            MAX-ACCESS read-only
            STATUS current
            DESCRIPTION
                "perPara."
            ::= { sdh_optportPer24HHisEntry 3 }

        -- 1.3.6.1.4.1.2011.2.25.3.40.50.144.40.1.4
        sdh_optportPer24HHisMonValue OBJECT-TYPE
            SYNTAX OCTET STRING (SIZE (0..100))
            MAX-ACCESS read-only
            STATUS current
            DESCRIPTION
                "perMonValue."
            ::= { sdh_optportPer24HHisEntry 4 }

        -- 1.3.6.1.4.1.2011.2.25.3.40.50.144.40.1.5
        sdh_optportPer24HHisDateTimeStart OBJECT-TYPE
            SYNTAX DateAndTime
            MAX-ACCESS read-only
            STATUS current
            DESCRIPTION
                "perDateTimeStart. "
            ::= { sdh_optportPer24HHisEntry 5 }

        -- 1.3.6.1.4.1.2011.2.25.3.40.50.144.40.1.6
        sdh_optportPer24HHisDateTimeEnd OBJECT-TYPE
            SYNTAX DateAndTime
            MAX-ACCESS read-only
            STATUS current
            DESCRIPTION
                "perDateTimeEnd. "
            ::= { sdh_optportPer24HHisEntry 6 }

        -- 1.3.6.1.4.1.2011.2.25.3.40.50.144.40.1.7
        sdh_optportPer24HHisVldty OBJECT-TYPE
            SYNTAX INTEGER
            MAX-ACCESS read-only
            STATUS current
            DESCRIPTION
                "perVldty. "
            ::= { sdh_optportPer24HHisEntry 7 }




-- Alarm data
      -- 1.3.6.1.4.1.2011.2.25.3.40.50.146
      sdh_vc12path OBJECT IDENTIFIER ::={ optixGlobalNGWDM 146 }


-- -------------------------------------------------------------------------
-- Perfomance 15-MIN Current Data Table (RTRV-PER-<MOD2>)
-- -------------------------------------------------------------------------
        -- 1.3.6.1.4.1.2011.2.25.3.40.50.146.10
        sdh_vc12pathPer15MCurTable OBJECT-TYPE
          SYNTAX SEQUENCE OF Sdh_vc12pathPer15MCurEntry
          MAX-ACCESS not-accessible
          STATUS current
          DESCRIPTION
              "sdh_vc12pathPer15MCur."
          ::= { sdh_vc12path 10 }

        -- 1.3.6.1.4.1.2011.2.25.3.40.50.146.10.1
        sdh_vc12pathPer15MCurEntry OBJECT-TYPE
            SYNTAX Sdh_vc12pathPer15MCurEntry
            MAX-ACCESS not-accessible
            STATUS current
            DESCRIPTION
              "sdh_vc12pathPer15MCur."
            INDEX { sdh_vc12pathPer15MCurEid, sdh_vc12pathPer15MCurPara }
            ::= { sdh_vc12pathPer15MCurTable 1 }

        Sdh_vc12pathPer15MCurEntry ::=
            SEQUENCE {
                sdh_vc12pathPer15MCurEid
                    PerformanceEventType,
                sdh_vc12pathPer15MCurMonValue
                    OCTET STRING,
                sdh_vc12pathPer15MCurVldty
                    INTEGER,
                sdh_vc12pathPer15MCurDateTime
                    DateAndTime,
                sdh_vc12pathPer15MCurParaLen
                    INTEGER,
                sdh_vc12pathPer15MCurPara
                    OCTET STRING
            }

        -- 1.3.6.1.4.1.2011.2.25.3.40.50.146.10.1.1
        sdh_vc12pathPer15MCurEid OBJECT-TYPE
            SYNTAX PerformanceEventType
            MAX-ACCESS read-only
            STATUS current
            DESCRIPTION
                "perEid."
            ::= { sdh_vc12pathPer15MCurEntry 1 }

        -- 1.3.6.1.4.1.2011.2.25.3.40.50.146.10.1.2
        sdh_vc12pathPer15MCurMonValue OBJECT-TYPE
            SYNTAX OCTET STRING (SIZE (0..100))
            MAX-ACCESS read-only
            STATUS current
            DESCRIPTION
                "perMonValue."
            ::= { sdh_vc12pathPer15MCurEntry 2 }

        -- 1.3.6.1.4.1.2011.2.25.3.40.50.146.10.1.3
        sdh_vc12pathPer15MCurVldty OBJECT-TYPE
            SYNTAX INTEGER
            MAX-ACCESS read-only
            STATUS current
            DESCRIPTION
                "perVldty. "
            ::= { sdh_vc12pathPer15MCurEntry 3 }

        -- 1.3.6.1.4.1.2011.2.25.3.40.50.146.10.1.4
        sdh_vc12pathPer15MCurDateTime OBJECT-TYPE
            SYNTAX DateAndTime
            MAX-ACCESS read-only
            STATUS current
            DESCRIPTION
                "perDateTime. "
            ::= { sdh_vc12pathPer15MCurEntry 4 }

        -- 1.3.6.1.4.1.2011.2.25.3.40.50.146.10.1.5
        sdh_vc12pathPer15MCurParaLen OBJECT-TYPE
            SYNTAX INTEGER
            MAX-ACCESS read-only
            STATUS current
            DESCRIPTION
                "perParaLen."
            ::= { sdh_vc12pathPer15MCurEntry 5 }

        -- 1.3.6.1.4.1.2011.2.25.3.40.50.146.10.1.6
        sdh_vc12pathPer15MCurPara OBJECT-TYPE
            SYNTAX OCTET STRING (SIZE (0..100))
            MAX-ACCESS read-only
            STATUS current
            DESCRIPTION
                "perPara."
            ::= { sdh_vc12pathPer15MCurEntry 6 }




-- -------------------------------------------------------------------------
-- Perfomance 15-MIN History Data Table (RTRV-PER-<MOD2>)
-- -------------------------------------------------------------------------
        -- 1.3.6.1.4.1.2011.2.25.3.40.50.146.20
        sdh_vc12pathPer15MHisTable OBJECT-TYPE
          SYNTAX SEQUENCE OF Sdh_vc12pathPer15MHisEntry
          MAX-ACCESS not-accessible
          STATUS current
          DESCRIPTION
              "sdh_vc12pathPer15MHis."
          ::= { sdh_vc12path 20 }

        -- 1.3.6.1.4.1.2011.2.25.3.40.50.146.20.1
        sdh_vc12pathPer15MHisEntry OBJECT-TYPE
            SYNTAX Sdh_vc12pathPer15MHisEntry
            MAX-ACCESS not-accessible
            STATUS current
            DESCRIPTION
                "sdh_vc12pathPer15MHis."
            INDEX {sdh_vc12pathPer15MHisEid, sdh_vc12pathPer15MHisParaLen, sdh_vc12pathPer15MHisPara, sdh_vc12pathPer15MHisDateTimeStart, sdh_vc12pathPer15MHisDateTimeEnd}
            ::= { sdh_vc12pathPer15MHisTable 1 }

        Sdh_vc12pathPer15MHisEntry ::=
            SEQUENCE {
                sdh_vc12pathPer15MHisEid
                    PerformanceEventType,
                sdh_vc12pathPer15MHisParaLen
                    INTEGER,
                sdh_vc12pathPer15MHisPara
                    OCTET STRING,
                sdh_vc12pathPer15MHisMonValue
                    OCTET STRING,
                sdh_vc12pathPer15MHisDateTimeStart
                    DateAndTime,
                sdh_vc12pathPer15MHisDateTimeEnd
                    DateAndTime,
                sdh_vc12pathPer15MHisVldty
                    INTEGER,
             }

        -- 1.3.6.1.4.1.2011.2.25.3.40.50.146.20.1.1
        sdh_vc12pathPer15MHisEid OBJECT-TYPE
            SYNTAX PerformanceEventType
            MAX-ACCESS read-only
            STATUS current
            DESCRIPTION
                "perEid."
            ::= { sdh_vc12pathPer15MHisEntry 1 }

        -- 1.3.6.1.4.1.2011.2.25.3.40.50.146.20.1.2
        sdh_vc12pathPer15MHisParaLen OBJECT-TYPE
            SYNTAX INTEGER
            MAX-ACCESS read-only
            STATUS current
            DESCRIPTION
                "perParaLen."
            ::= { sdh_vc12pathPer15MHisEntry 2 }

        -- 1.3.6.1.4.1.2011.2.25.3.40.50.146.20.1.3
        sdh_vc12pathPer15MHisPara OBJECT-TYPE
            SYNTAX OCTET STRING (SIZE (0..100))
            MAX-ACCESS read-only
            STATUS current
            DESCRIPTION
                "perPara."
            ::= { sdh_vc12pathPer15MHisEntry 3 }

        -- 1.3.6.1.4.1.2011.2.25.3.40.50.146.20.1.4
        sdh_vc12pathPer15MHisMonValue OBJECT-TYPE
            SYNTAX OCTET STRING (SIZE (0..100))
            MAX-ACCESS read-only
            STATUS current
            DESCRIPTION
                "perMonValue."
            ::= { sdh_vc12pathPer15MHisEntry 4 }

        -- 1.3.6.1.4.1.2011.2.25.3.40.50.146.20.1.5
        sdh_vc12pathPer15MHisDateTimeStart OBJECT-TYPE
            SYNTAX DateAndTime
            MAX-ACCESS read-only
            STATUS current
            DESCRIPTION
                "perDateTimeStart. "
            ::= { sdh_vc12pathPer15MHisEntry 5 }

        -- 1.3.6.1.4.1.2011.2.25.3.40.50.146.20.1.6
        sdh_vc12pathPer15MHisDateTimeEnd OBJECT-TYPE
            SYNTAX DateAndTime
            MAX-ACCESS read-only
            STATUS current
            DESCRIPTION
                "perDateTimeEnd. "
            ::= { sdh_vc12pathPer15MHisEntry 6 }

        -- 1.3.6.1.4.1.2011.2.25.3.40.50.146.20.1.7
        sdh_vc12pathPer15MHisVldty OBJECT-TYPE
            SYNTAX INTEGER
            MAX-ACCESS read-only
            STATUS current
            DESCRIPTION
                "perVldty. "
            ::= { sdh_vc12pathPer15MHisEntry 7 }




-- -------------------------------------------------------------------------
-- Perfomance 24-HOUR Current Data Table (RTRV-PER-<MOD2>)
-- -------------------------------------------------------------------------
        -- 1.3.6.1.4.1.2011.2.25.3.40.50.146.30
        sdh_vc12pathPer24HCurTable OBJECT-TYPE
          SYNTAX SEQUENCE OF Sdh_vc12pathPer24HCurEntry
          MAX-ACCESS not-accessible
          STATUS current
          DESCRIPTION
              "sdh_vc12pathPer24HCur."
          ::= { sdh_vc12path 30 }

        -- 1.3.6.1.4.1.2011.2.25.3.40.50.146.30.1
        sdh_vc12pathPer24HCurEntry OBJECT-TYPE
            SYNTAX Sdh_vc12pathPer24HCurEntry
            MAX-ACCESS not-accessible
            STATUS current
            DESCRIPTION
              "sdh_vc12pathPer24HCur."
            INDEX { sdh_vc12pathPer24HCurEid, sdh_vc12pathPer24HCurPara }
            ::= { sdh_vc12pathPer24HCurTable 1 }

        Sdh_vc12pathPer24HCurEntry ::=
            SEQUENCE {
                sdh_vc12pathPer24HCurEid
                    PerformanceEventType,
                sdh_vc12pathPer24HCurMonValue
                    OCTET STRING,
                sdh_vc12pathPer24HCurVldty
                    INTEGER,
                sdh_vc12pathPer24HCurDateTime
                    DateAndTime,
                sdh_vc12pathPer24HCurParaLen
                    INTEGER,
                sdh_vc12pathPer24HCurPara
                    OCTET STRING
            }

        -- 1.3.6.1.4.1.2011.2.25.3.40.50.146.30.1.1
        sdh_vc12pathPer24HCurEid OBJECT-TYPE
            SYNTAX PerformanceEventType
            MAX-ACCESS read-only
            STATUS current
            DESCRIPTION
                "perEid."
            ::= { sdh_vc12pathPer24HCurEntry 1 }

        -- 1.3.6.1.4.1.2011.2.25.3.40.50.146.30.1.2
        sdh_vc12pathPer24HCurMonValue OBJECT-TYPE
            SYNTAX OCTET STRING (SIZE (0..100))
            MAX-ACCESS read-only
            STATUS current
            DESCRIPTION
                "perMonValue."
            ::= { sdh_vc12pathPer24HCurEntry 2 }

        -- 1.3.6.1.4.1.2011.2.25.3.40.50.146.30.1.3
        sdh_vc12pathPer24HCurVldty OBJECT-TYPE
            SYNTAX INTEGER
            MAX-ACCESS read-only
            STATUS current
            DESCRIPTION
                "perVldty. "
            ::= { sdh_vc12pathPer24HCurEntry 3 }

        -- 1.3.6.1.4.1.2011.2.25.3.40.50.146.30.1.4
        sdh_vc12pathPer24HCurDateTime OBJECT-TYPE
            SYNTAX DateAndTime
            MAX-ACCESS read-only
            STATUS current
            DESCRIPTION
                "perDateTime. "
            ::= { sdh_vc12pathPer24HCurEntry 4 }

        -- 1.3.6.1.4.1.2011.2.25.3.40.50.146.30.1.5
        sdh_vc12pathPer24HCurParaLen OBJECT-TYPE
            SYNTAX INTEGER
            MAX-ACCESS read-only
            STATUS current
            DESCRIPTION
                "perParaLen."
            ::= { sdh_vc12pathPer24HCurEntry 5 }

        -- 1.3.6.1.4.1.2011.2.25.3.40.50.146.30.1.6
        sdh_vc12pathPer24HCurPara OBJECT-TYPE
            SYNTAX OCTET STRING (SIZE (0..100))
            MAX-ACCESS read-only
            STATUS current
            DESCRIPTION
                "perPara."
            ::= { sdh_vc12pathPer24HCurEntry 6 }




-- -------------------------------------------------------------------------
-- Perfomance 24-HOUR History Data Table (RTRV-PER-<MOD2>)
-- -------------------------------------------------------------------------
        -- 1.3.6.1.4.1.2011.2.25.3.40.50.146.40
        sdh_vc12pathPer24HHisTable OBJECT-TYPE
          SYNTAX SEQUENCE OF Sdh_vc12pathPer24HHisEntry
          MAX-ACCESS not-accessible
          STATUS current
          DESCRIPTION
              "sdh_vc12pathPer24HHis."
          ::= { sdh_vc12path 40 }

        -- 1.3.6.1.4.1.2011.2.25.3.40.50.146.40.1
        sdh_vc12pathPer24HHisEntry OBJECT-TYPE
            SYNTAX Sdh_vc12pathPer24HHisEntry
            MAX-ACCESS not-accessible
            STATUS current
            DESCRIPTION
                "sdh_vc12pathPer24HHis."
            INDEX {sdh_vc12pathPer24HHisEid, sdh_vc12pathPer24HHisParaLen, sdh_vc12pathPer24HHisPara, sdh_vc12pathPer24HHisDateTimeStart, sdh_vc12pathPer24HHisDateTimeEnd}
            ::= { sdh_vc12pathPer24HHisTable 1 }

        Sdh_vc12pathPer24HHisEntry ::=
            SEQUENCE {
                sdh_vc12pathPer24HHisEid
                    PerformanceEventType,
                sdh_vc12pathPer24HHisParaLen
                    INTEGER,
                sdh_vc12pathPer24HHisPara
                    OCTET STRING,
                sdh_vc12pathPer24HHisMonValue
                    OCTET STRING,
                sdh_vc12pathPer24HHisDateTimeStart
                    DateAndTime,
                sdh_vc12pathPer24HHisDateTimeEnd
                    DateAndTime,
                sdh_vc12pathPer24HHisVldty
                    INTEGER,
             }

        -- 1.3.6.1.4.1.2011.2.25.3.40.50.146.40.1.1
        sdh_vc12pathPer24HHisEid OBJECT-TYPE
            SYNTAX PerformanceEventType
            MAX-ACCESS read-only
            STATUS current
            DESCRIPTION
                "perEid."
            ::= { sdh_vc12pathPer24HHisEntry 1 }

        -- 1.3.6.1.4.1.2011.2.25.3.40.50.146.40.1.2
        sdh_vc12pathPer24HHisParaLen OBJECT-TYPE
            SYNTAX INTEGER
            MAX-ACCESS read-only
            STATUS current
            DESCRIPTION
                "perParaLen."
            ::= { sdh_vc12pathPer24HHisEntry 2 }

        -- 1.3.6.1.4.1.2011.2.25.3.40.50.146.40.1.3
        sdh_vc12pathPer24HHisPara OBJECT-TYPE
            SYNTAX OCTET STRING (SIZE (0..100))
            MAX-ACCESS read-only
            STATUS current
            DESCRIPTION
                "perPara."
            ::= { sdh_vc12pathPer24HHisEntry 3 }

        -- 1.3.6.1.4.1.2011.2.25.3.40.50.146.40.1.4
        sdh_vc12pathPer24HHisMonValue OBJECT-TYPE
            SYNTAX OCTET STRING (SIZE (0..100))
            MAX-ACCESS read-only
            STATUS current
            DESCRIPTION
                "perMonValue."
            ::= { sdh_vc12pathPer24HHisEntry 4 }

        -- 1.3.6.1.4.1.2011.2.25.3.40.50.146.40.1.5
        sdh_vc12pathPer24HHisDateTimeStart OBJECT-TYPE
            SYNTAX DateAndTime
            MAX-ACCESS read-only
            STATUS current
            DESCRIPTION
                "perDateTimeStart. "
            ::= { sdh_vc12pathPer24HHisEntry 5 }

        -- 1.3.6.1.4.1.2011.2.25.3.40.50.146.40.1.6
        sdh_vc12pathPer24HHisDateTimeEnd OBJECT-TYPE
            SYNTAX DateAndTime
            MAX-ACCESS read-only
            STATUS current
            DESCRIPTION
                "perDateTimeEnd. "
            ::= { sdh_vc12pathPer24HHisEntry 6 }

        -- 1.3.6.1.4.1.2011.2.25.3.40.50.146.40.1.7
        sdh_vc12pathPer24HHisVldty OBJECT-TYPE
            SYNTAX INTEGER
            MAX-ACCESS read-only
            STATUS current
            DESCRIPTION
                "perVldty. "
            ::= { sdh_vc12pathPer24HHisEntry 7 }




-- Alarm data
      -- 1.3.6.1.4.1.2011.2.25.3.40.50.147
      sdh_vc3path OBJECT IDENTIFIER ::={ optixGlobalNGWDM 147 }


-- -------------------------------------------------------------------------
-- Perfomance 15-MIN Current Data Table (RTRV-PER-<MOD2>)
-- -------------------------------------------------------------------------
        -- 1.3.6.1.4.1.2011.2.25.3.40.50.147.10
        sdh_vc3pathPer15MCurTable OBJECT-TYPE
          SYNTAX SEQUENCE OF Sdh_vc3pathPer15MCurEntry
          MAX-ACCESS not-accessible
          STATUS current
          DESCRIPTION
              "sdh_vc3pathPer15MCur."
          ::= { sdh_vc3path 10 }

        -- 1.3.6.1.4.1.2011.2.25.3.40.50.147.10.1
        sdh_vc3pathPer15MCurEntry OBJECT-TYPE
            SYNTAX Sdh_vc3pathPer15MCurEntry
            MAX-ACCESS not-accessible
            STATUS current
            DESCRIPTION
              "sdh_vc3pathPer15MCur."
            INDEX { sdh_vc3pathPer15MCurEid, sdh_vc3pathPer15MCurPara }
            ::= { sdh_vc3pathPer15MCurTable 1 }

        Sdh_vc3pathPer15MCurEntry ::=
            SEQUENCE {
                sdh_vc3pathPer15MCurEid
                    PerformanceEventType,
                sdh_vc3pathPer15MCurMonValue
                    OCTET STRING,
                sdh_vc3pathPer15MCurVldty
                    INTEGER,
                sdh_vc3pathPer15MCurDateTime
                    DateAndTime,
                sdh_vc3pathPer15MCurParaLen
                    INTEGER,
                sdh_vc3pathPer15MCurPara
                    OCTET STRING
            }

        -- 1.3.6.1.4.1.2011.2.25.3.40.50.147.10.1.1
        sdh_vc3pathPer15MCurEid OBJECT-TYPE
            SYNTAX PerformanceEventType
            MAX-ACCESS read-only
            STATUS current
            DESCRIPTION
                "perEid."
            ::= { sdh_vc3pathPer15MCurEntry 1 }

        -- 1.3.6.1.4.1.2011.2.25.3.40.50.147.10.1.2
        sdh_vc3pathPer15MCurMonValue OBJECT-TYPE
            SYNTAX OCTET STRING (SIZE (0..100))
            MAX-ACCESS read-only
            STATUS current
            DESCRIPTION
                "perMonValue."
            ::= { sdh_vc3pathPer15MCurEntry 2 }

        -- 1.3.6.1.4.1.2011.2.25.3.40.50.147.10.1.3
        sdh_vc3pathPer15MCurVldty OBJECT-TYPE
            SYNTAX INTEGER
            MAX-ACCESS read-only
            STATUS current
            DESCRIPTION
                "perVldty. "
            ::= { sdh_vc3pathPer15MCurEntry 3 }

        -- 1.3.6.1.4.1.2011.2.25.3.40.50.147.10.1.4
        sdh_vc3pathPer15MCurDateTime OBJECT-TYPE
            SYNTAX DateAndTime
            MAX-ACCESS read-only
            STATUS current
            DESCRIPTION
                "perDateTime. "
            ::= { sdh_vc3pathPer15MCurEntry 4 }

        -- 1.3.6.1.4.1.2011.2.25.3.40.50.147.10.1.5
        sdh_vc3pathPer15MCurParaLen OBJECT-TYPE
            SYNTAX INTEGER
            MAX-ACCESS read-only
            STATUS current
            DESCRIPTION
                "perParaLen."
            ::= { sdh_vc3pathPer15MCurEntry 5 }

        -- 1.3.6.1.4.1.2011.2.25.3.40.50.147.10.1.6
        sdh_vc3pathPer15MCurPara OBJECT-TYPE
            SYNTAX OCTET STRING (SIZE (0..100))
            MAX-ACCESS read-only
            STATUS current
            DESCRIPTION
                "perPara."
            ::= { sdh_vc3pathPer15MCurEntry 6 }




-- -------------------------------------------------------------------------
-- Perfomance 15-MIN History Data Table (RTRV-PER-<MOD2>)
-- -------------------------------------------------------------------------
        -- 1.3.6.1.4.1.2011.2.25.3.40.50.147.20
        sdh_vc3pathPer15MHisTable OBJECT-TYPE
          SYNTAX SEQUENCE OF Sdh_vc3pathPer15MHisEntry
          MAX-ACCESS not-accessible
          STATUS current
          DESCRIPTION
              "sdh_vc3pathPer15MHis."
          ::= { sdh_vc3path 20 }

        -- 1.3.6.1.4.1.2011.2.25.3.40.50.147.20.1
        sdh_vc3pathPer15MHisEntry OBJECT-TYPE
            SYNTAX Sdh_vc3pathPer15MHisEntry
            MAX-ACCESS not-accessible
            STATUS current
            DESCRIPTION
                "sdh_vc3pathPer15MHis."
            INDEX {sdh_vc3pathPer15MHisEid, sdh_vc3pathPer15MHisParaLen, sdh_vc3pathPer15MHisPara, sdh_vc3pathPer15MHisDateTimeStart, sdh_vc3pathPer15MHisDateTimeEnd}
            ::= { sdh_vc3pathPer15MHisTable 1 }

        Sdh_vc3pathPer15MHisEntry ::=
            SEQUENCE {
                sdh_vc3pathPer15MHisEid
                    PerformanceEventType,
                sdh_vc3pathPer15MHisParaLen
                    INTEGER,
                sdh_vc3pathPer15MHisPara
                    OCTET STRING,
                sdh_vc3pathPer15MHisMonValue
                    OCTET STRING,
                sdh_vc3pathPer15MHisDateTimeStart
                    DateAndTime,
                sdh_vc3pathPer15MHisDateTimeEnd
                    DateAndTime,
                sdh_vc3pathPer15MHisVldty
                    INTEGER,
             }

        -- 1.3.6.1.4.1.2011.2.25.3.40.50.147.20.1.1
        sdh_vc3pathPer15MHisEid OBJECT-TYPE
            SYNTAX PerformanceEventType
            MAX-ACCESS read-only
            STATUS current
            DESCRIPTION
                "perEid."
            ::= { sdh_vc3pathPer15MHisEntry 1 }

        -- 1.3.6.1.4.1.2011.2.25.3.40.50.147.20.1.2
        sdh_vc3pathPer15MHisParaLen OBJECT-TYPE
            SYNTAX INTEGER
            MAX-ACCESS read-only
            STATUS current
            DESCRIPTION
                "perParaLen."
            ::= { sdh_vc3pathPer15MHisEntry 2 }

        -- 1.3.6.1.4.1.2011.2.25.3.40.50.147.20.1.3
        sdh_vc3pathPer15MHisPara OBJECT-TYPE
            SYNTAX OCTET STRING (SIZE (0..100))
            MAX-ACCESS read-only
            STATUS current
            DESCRIPTION
                "perPara."
            ::= { sdh_vc3pathPer15MHisEntry 3 }

        -- 1.3.6.1.4.1.2011.2.25.3.40.50.147.20.1.4
        sdh_vc3pathPer15MHisMonValue OBJECT-TYPE
            SYNTAX OCTET STRING (SIZE (0..100))
            MAX-ACCESS read-only
            STATUS current
            DESCRIPTION
                "perMonValue."
            ::= { sdh_vc3pathPer15MHisEntry 4 }

        -- 1.3.6.1.4.1.2011.2.25.3.40.50.147.20.1.5
        sdh_vc3pathPer15MHisDateTimeStart OBJECT-TYPE
            SYNTAX DateAndTime
            MAX-ACCESS read-only
            STATUS current
            DESCRIPTION
                "perDateTimeStart. "
            ::= { sdh_vc3pathPer15MHisEntry 5 }

        -- 1.3.6.1.4.1.2011.2.25.3.40.50.147.20.1.6
        sdh_vc3pathPer15MHisDateTimeEnd OBJECT-TYPE
            SYNTAX DateAndTime
            MAX-ACCESS read-only
            STATUS current
            DESCRIPTION
                "perDateTimeEnd. "
            ::= { sdh_vc3pathPer15MHisEntry 6 }

        -- 1.3.6.1.4.1.2011.2.25.3.40.50.147.20.1.7
        sdh_vc3pathPer15MHisVldty OBJECT-TYPE
            SYNTAX INTEGER
            MAX-ACCESS read-only
            STATUS current
            DESCRIPTION
                "perVldty. "
            ::= { sdh_vc3pathPer15MHisEntry 7 }




-- -------------------------------------------------------------------------
-- Perfomance 24-HOUR Current Data Table (RTRV-PER-<MOD2>)
-- -------------------------------------------------------------------------
        -- 1.3.6.1.4.1.2011.2.25.3.40.50.147.30
        sdh_vc3pathPer24HCurTable OBJECT-TYPE
          SYNTAX SEQUENCE OF Sdh_vc3pathPer24HCurEntry
          MAX-ACCESS not-accessible
          STATUS current
          DESCRIPTION
              "sdh_vc3pathPer24HCur."
          ::= { sdh_vc3path 30 }

        -- 1.3.6.1.4.1.2011.2.25.3.40.50.147.30.1
        sdh_vc3pathPer24HCurEntry OBJECT-TYPE
            SYNTAX Sdh_vc3pathPer24HCurEntry
            MAX-ACCESS not-accessible
            STATUS current
            DESCRIPTION
              "sdh_vc3pathPer24HCur."
            INDEX { sdh_vc3pathPer24HCurEid, sdh_vc3pathPer24HCurPara }
            ::= { sdh_vc3pathPer24HCurTable 1 }

        Sdh_vc3pathPer24HCurEntry ::=
            SEQUENCE {
                sdh_vc3pathPer24HCurEid
                    PerformanceEventType,
                sdh_vc3pathPer24HCurMonValue
                    OCTET STRING,
                sdh_vc3pathPer24HCurVldty
                    INTEGER,
                sdh_vc3pathPer24HCurDateTime
                    DateAndTime,
                sdh_vc3pathPer24HCurParaLen
                    INTEGER,
                sdh_vc3pathPer24HCurPara
                    OCTET STRING
            }

        -- 1.3.6.1.4.1.2011.2.25.3.40.50.147.30.1.1
        sdh_vc3pathPer24HCurEid OBJECT-TYPE
            SYNTAX PerformanceEventType
            MAX-ACCESS read-only
            STATUS current
            DESCRIPTION
                "perEid."
            ::= { sdh_vc3pathPer24HCurEntry 1 }

        -- 1.3.6.1.4.1.2011.2.25.3.40.50.147.30.1.2
        sdh_vc3pathPer24HCurMonValue OBJECT-TYPE
            SYNTAX OCTET STRING (SIZE (0..100))
            MAX-ACCESS read-only
            STATUS current
            DESCRIPTION
                "perMonValue."
            ::= { sdh_vc3pathPer24HCurEntry 2 }

        -- 1.3.6.1.4.1.2011.2.25.3.40.50.147.30.1.3
        sdh_vc3pathPer24HCurVldty OBJECT-TYPE
            SYNTAX INTEGER
            MAX-ACCESS read-only
            STATUS current
            DESCRIPTION
                "perVldty. "
            ::= { sdh_vc3pathPer24HCurEntry 3 }

        -- 1.3.6.1.4.1.2011.2.25.3.40.50.147.30.1.4
        sdh_vc3pathPer24HCurDateTime OBJECT-TYPE
            SYNTAX DateAndTime
            MAX-ACCESS read-only
            STATUS current
            DESCRIPTION
                "perDateTime. "
            ::= { sdh_vc3pathPer24HCurEntry 4 }

        -- 1.3.6.1.4.1.2011.2.25.3.40.50.147.30.1.5
        sdh_vc3pathPer24HCurParaLen OBJECT-TYPE
            SYNTAX INTEGER
            MAX-ACCESS read-only
            STATUS current
            DESCRIPTION
                "perParaLen."
            ::= { sdh_vc3pathPer24HCurEntry 5 }

        -- 1.3.6.1.4.1.2011.2.25.3.40.50.147.30.1.6
        sdh_vc3pathPer24HCurPara OBJECT-TYPE
            SYNTAX OCTET STRING (SIZE (0..100))
            MAX-ACCESS read-only
            STATUS current
            DESCRIPTION
                "perPara."
            ::= { sdh_vc3pathPer24HCurEntry 6 }




-- -------------------------------------------------------------------------
-- Perfomance 24-HOUR History Data Table (RTRV-PER-<MOD2>)
-- -------------------------------------------------------------------------
        -- 1.3.6.1.4.1.2011.2.25.3.40.50.147.40
        sdh_vc3pathPer24HHisTable OBJECT-TYPE
          SYNTAX SEQUENCE OF Sdh_vc3pathPer24HHisEntry
          MAX-ACCESS not-accessible
          STATUS current
          DESCRIPTION
              "sdh_vc3pathPer24HHis."
          ::= { sdh_vc3path 40 }

        -- 1.3.6.1.4.1.2011.2.25.3.40.50.147.40.1
        sdh_vc3pathPer24HHisEntry OBJECT-TYPE
            SYNTAX Sdh_vc3pathPer24HHisEntry
            MAX-ACCESS not-accessible
            STATUS current
            DESCRIPTION
                "sdh_vc3pathPer24HHis."
            INDEX {sdh_vc3pathPer24HHisEid, sdh_vc3pathPer24HHisParaLen, sdh_vc3pathPer24HHisPara, sdh_vc3pathPer24HHisDateTimeStart, sdh_vc3pathPer24HHisDateTimeEnd}
            ::= { sdh_vc3pathPer24HHisTable 1 }

        Sdh_vc3pathPer24HHisEntry ::=
            SEQUENCE {
                sdh_vc3pathPer24HHisEid
                    PerformanceEventType,
                sdh_vc3pathPer24HHisParaLen
                    INTEGER,
                sdh_vc3pathPer24HHisPara
                    OCTET STRING,
                sdh_vc3pathPer24HHisMonValue
                    OCTET STRING,
                sdh_vc3pathPer24HHisDateTimeStart
                    DateAndTime,
                sdh_vc3pathPer24HHisDateTimeEnd
                    DateAndTime,
                sdh_vc3pathPer24HHisVldty
                    INTEGER,
             }

        -- 1.3.6.1.4.1.2011.2.25.3.40.50.147.40.1.1
        sdh_vc3pathPer24HHisEid OBJECT-TYPE
            SYNTAX PerformanceEventType
            MAX-ACCESS read-only
            STATUS current
            DESCRIPTION
                "perEid."
            ::= { sdh_vc3pathPer24HHisEntry 1 }

        -- 1.3.6.1.4.1.2011.2.25.3.40.50.147.40.1.2
        sdh_vc3pathPer24HHisParaLen OBJECT-TYPE
            SYNTAX INTEGER
            MAX-ACCESS read-only
            STATUS current
            DESCRIPTION
                "perParaLen."
            ::= { sdh_vc3pathPer24HHisEntry 2 }

        -- 1.3.6.1.4.1.2011.2.25.3.40.50.147.40.1.3
        sdh_vc3pathPer24HHisPara OBJECT-TYPE
            SYNTAX OCTET STRING (SIZE (0..100))
            MAX-ACCESS read-only
            STATUS current
            DESCRIPTION
                "perPara."
            ::= { sdh_vc3pathPer24HHisEntry 3 }

        -- 1.3.6.1.4.1.2011.2.25.3.40.50.147.40.1.4
        sdh_vc3pathPer24HHisMonValue OBJECT-TYPE
            SYNTAX OCTET STRING (SIZE (0..100))
            MAX-ACCESS read-only
            STATUS current
            DESCRIPTION
                "perMonValue."
            ::= { sdh_vc3pathPer24HHisEntry 4 }

        -- 1.3.6.1.4.1.2011.2.25.3.40.50.147.40.1.5
        sdh_vc3pathPer24HHisDateTimeStart OBJECT-TYPE
            SYNTAX DateAndTime
            MAX-ACCESS read-only
            STATUS current
            DESCRIPTION
                "perDateTimeStart. "
            ::= { sdh_vc3pathPer24HHisEntry 5 }

        -- 1.3.6.1.4.1.2011.2.25.3.40.50.147.40.1.6
        sdh_vc3pathPer24HHisDateTimeEnd OBJECT-TYPE
            SYNTAX DateAndTime
            MAX-ACCESS read-only
            STATUS current
            DESCRIPTION
                "perDateTimeEnd. "
            ::= { sdh_vc3pathPer24HHisEntry 6 }

        -- 1.3.6.1.4.1.2011.2.25.3.40.50.147.40.1.7
        sdh_vc3pathPer24HHisVldty OBJECT-TYPE
            SYNTAX INTEGER
            MAX-ACCESS read-only
            STATUS current
            DESCRIPTION
                "perVldty. "
            ::= { sdh_vc3pathPer24HHisEntry 7 }




-- Alarm data
      -- 1.3.6.1.4.1.2011.2.25.3.40.50.153
      new_subcard OBJECT IDENTIFIER ::={ optixGlobalNGWDM 153 }


-- -------------------------------------------------------------------------
-- Perfomance 15-MIN Current Data Table (RTRV-PER-<MOD2>)
-- -------------------------------------------------------------------------
        -- 1.3.6.1.4.1.2011.2.25.3.40.50.153.10
        new_subcardPer15MCurTable OBJECT-TYPE
          SYNTAX SEQUENCE OF New_subcardPer15MCurEntry
          MAX-ACCESS not-accessible
          STATUS current
          DESCRIPTION
              "new_subcardPer15MCur."
          ::= { new_subcard 10 }

        -- 1.3.6.1.4.1.2011.2.25.3.40.50.153.10.1
        new_subcardPer15MCurEntry OBJECT-TYPE
            SYNTAX New_subcardPer15MCurEntry
            MAX-ACCESS not-accessible
            STATUS current
            DESCRIPTION
              "new_subcardPer15MCur."
            INDEX { new_subcardPer15MCurEid, new_subcardPer15MCurPara }
            ::= { new_subcardPer15MCurTable 1 }

        New_subcardPer15MCurEntry ::=
            SEQUENCE {
                new_subcardPer15MCurEid
                    PerformanceEventType,
                new_subcardPer15MCurMonValue
                    OCTET STRING,
                new_subcardPer15MCurVldty
                    INTEGER,
                new_subcardPer15MCurDateTime
                    DateAndTime,
                new_subcardPer15MCurParaLen
                    INTEGER,
                new_subcardPer15MCurPara
                    OCTET STRING
            }

        -- 1.3.6.1.4.1.2011.2.25.3.40.50.153.10.1.1
        new_subcardPer15MCurEid OBJECT-TYPE
            SYNTAX PerformanceEventType
            MAX-ACCESS read-only
            STATUS current
            DESCRIPTION
                "perEid."
            ::= { new_subcardPer15MCurEntry 1 }

        -- 1.3.6.1.4.1.2011.2.25.3.40.50.153.10.1.2
        new_subcardPer15MCurMonValue OBJECT-TYPE
            SYNTAX OCTET STRING (SIZE (0..100))
            MAX-ACCESS read-only
            STATUS current
            DESCRIPTION
                "perMonValue."
            ::= { new_subcardPer15MCurEntry 2 }

        -- 1.3.6.1.4.1.2011.2.25.3.40.50.153.10.1.3
        new_subcardPer15MCurVldty OBJECT-TYPE
            SYNTAX INTEGER
            MAX-ACCESS read-only
            STATUS current
            DESCRIPTION
                "perVldty. "
            ::= { new_subcardPer15MCurEntry 3 }

        -- 1.3.6.1.4.1.2011.2.25.3.40.50.153.10.1.4
        new_subcardPer15MCurDateTime OBJECT-TYPE
            SYNTAX DateAndTime
            MAX-ACCESS read-only
            STATUS current
            DESCRIPTION
                "perDateTime. "
            ::= { new_subcardPer15MCurEntry 4 }

        -- 1.3.6.1.4.1.2011.2.25.3.40.50.153.10.1.5
        new_subcardPer15MCurParaLen OBJECT-TYPE
            SYNTAX INTEGER
            MAX-ACCESS read-only
            STATUS current
            DESCRIPTION
                "perParaLen."
            ::= { new_subcardPer15MCurEntry 5 }

        -- 1.3.6.1.4.1.2011.2.25.3.40.50.153.10.1.6
        new_subcardPer15MCurPara OBJECT-TYPE
            SYNTAX OCTET STRING (SIZE (0..100))
            MAX-ACCESS read-only
            STATUS current
            DESCRIPTION
                "perPara."
            ::= { new_subcardPer15MCurEntry 6 }




-- -------------------------------------------------------------------------
-- Perfomance 15-MIN History Data Table (RTRV-PER-<MOD2>)
-- -------------------------------------------------------------------------
        -- 1.3.6.1.4.1.2011.2.25.3.40.50.153.20
        new_subcardPer15MHisTable OBJECT-TYPE
          SYNTAX SEQUENCE OF New_subcardPer15MHisEntry
          MAX-ACCESS not-accessible
          STATUS current
          DESCRIPTION
              "new_subcardPer15MHis."
          ::= { new_subcard 20 }

        -- 1.3.6.1.4.1.2011.2.25.3.40.50.153.20.1
        new_subcardPer15MHisEntry OBJECT-TYPE
            SYNTAX New_subcardPer15MHisEntry
            MAX-ACCESS not-accessible
            STATUS current
            DESCRIPTION
                "new_subcardPer15MHis."
            INDEX {new_subcardPer15MHisEid, new_subcardPer15MHisParaLen, new_subcardPer15MHisPara, new_subcardPer15MHisDateTimeStart, new_subcardPer15MHisDateTimeEnd}
            ::= { new_subcardPer15MHisTable 1 }

        New_subcardPer15MHisEntry ::=
            SEQUENCE {
                new_subcardPer15MHisEid
                    PerformanceEventType,
                new_subcardPer15MHisParaLen
                    INTEGER,
                new_subcardPer15MHisPara
                    OCTET STRING,
                new_subcardPer15MHisMonValue
                    OCTET STRING,
                new_subcardPer15MHisDateTimeStart
                    DateAndTime,
                new_subcardPer15MHisDateTimeEnd
                    DateAndTime,
                new_subcardPer15MHisVldty
                    INTEGER,
             }

        -- 1.3.6.1.4.1.2011.2.25.3.40.50.153.20.1.1
        new_subcardPer15MHisEid OBJECT-TYPE
            SYNTAX PerformanceEventType
            MAX-ACCESS read-only
            STATUS current
            DESCRIPTION
                "perEid."
            ::= { new_subcardPer15MHisEntry 1 }

        -- 1.3.6.1.4.1.2011.2.25.3.40.50.153.20.1.2
        new_subcardPer15MHisParaLen OBJECT-TYPE
            SYNTAX INTEGER
            MAX-ACCESS read-only
            STATUS current
            DESCRIPTION
                "perParaLen."
            ::= { new_subcardPer15MHisEntry 2 }

        -- 1.3.6.1.4.1.2011.2.25.3.40.50.153.20.1.3
        new_subcardPer15MHisPara OBJECT-TYPE
            SYNTAX OCTET STRING (SIZE (0..100))
            MAX-ACCESS read-only
            STATUS current
            DESCRIPTION
                "perPara."
            ::= { new_subcardPer15MHisEntry 3 }

        -- 1.3.6.1.4.1.2011.2.25.3.40.50.153.20.1.4
        new_subcardPer15MHisMonValue OBJECT-TYPE
            SYNTAX OCTET STRING (SIZE (0..100))
            MAX-ACCESS read-only
            STATUS current
            DESCRIPTION
                "perMonValue."
            ::= { new_subcardPer15MHisEntry 4 }

        -- 1.3.6.1.4.1.2011.2.25.3.40.50.153.20.1.5
        new_subcardPer15MHisDateTimeStart OBJECT-TYPE
            SYNTAX DateAndTime
            MAX-ACCESS read-only
            STATUS current
            DESCRIPTION
                "perDateTimeStart. "
            ::= { new_subcardPer15MHisEntry 5 }

        -- 1.3.6.1.4.1.2011.2.25.3.40.50.153.20.1.6
        new_subcardPer15MHisDateTimeEnd OBJECT-TYPE
            SYNTAX DateAndTime
            MAX-ACCESS read-only
            STATUS current
            DESCRIPTION
                "perDateTimeEnd. "
            ::= { new_subcardPer15MHisEntry 6 }

        -- 1.3.6.1.4.1.2011.2.25.3.40.50.153.20.1.7
        new_subcardPer15MHisVldty OBJECT-TYPE
            SYNTAX INTEGER
            MAX-ACCESS read-only
            STATUS current
            DESCRIPTION
                "perVldty. "
            ::= { new_subcardPer15MHisEntry 7 }




-- -------------------------------------------------------------------------
-- Perfomance 24-HOUR Current Data Table (RTRV-PER-<MOD2>)
-- -------------------------------------------------------------------------
        -- 1.3.6.1.4.1.2011.2.25.3.40.50.153.30
        new_subcardPer24HCurTable OBJECT-TYPE
          SYNTAX SEQUENCE OF New_subcardPer24HCurEntry
          MAX-ACCESS not-accessible
          STATUS current
          DESCRIPTION
              "new_subcardPer24HCur."
          ::= { new_subcard 30 }

        -- 1.3.6.1.4.1.2011.2.25.3.40.50.153.30.1
        new_subcardPer24HCurEntry OBJECT-TYPE
            SYNTAX New_subcardPer24HCurEntry
            MAX-ACCESS not-accessible
            STATUS current
            DESCRIPTION
              "new_subcardPer24HCur."
            INDEX { new_subcardPer24HCurEid, new_subcardPer24HCurPara }
            ::= { new_subcardPer24HCurTable 1 }

        New_subcardPer24HCurEntry ::=
            SEQUENCE {
                new_subcardPer24HCurEid
                    PerformanceEventType,
                new_subcardPer24HCurMonValue
                    OCTET STRING,
                new_subcardPer24HCurVldty
                    INTEGER,
                new_subcardPer24HCurDateTime
                    DateAndTime,
                new_subcardPer24HCurParaLen
                    INTEGER,
                new_subcardPer24HCurPara
                    OCTET STRING
            }

        -- 1.3.6.1.4.1.2011.2.25.3.40.50.153.30.1.1
        new_subcardPer24HCurEid OBJECT-TYPE
            SYNTAX PerformanceEventType
            MAX-ACCESS read-only
            STATUS current
            DESCRIPTION
                "perEid."
            ::= { new_subcardPer24HCurEntry 1 }

        -- 1.3.6.1.4.1.2011.2.25.3.40.50.153.30.1.2
        new_subcardPer24HCurMonValue OBJECT-TYPE
            SYNTAX OCTET STRING (SIZE (0..100))
            MAX-ACCESS read-only
            STATUS current
            DESCRIPTION
                "perMonValue."
            ::= { new_subcardPer24HCurEntry 2 }

        -- 1.3.6.1.4.1.2011.2.25.3.40.50.153.30.1.3
        new_subcardPer24HCurVldty OBJECT-TYPE
            SYNTAX INTEGER
            MAX-ACCESS read-only
            STATUS current
            DESCRIPTION
                "perVldty. "
            ::= { new_subcardPer24HCurEntry 3 }

        -- 1.3.6.1.4.1.2011.2.25.3.40.50.153.30.1.4
        new_subcardPer24HCurDateTime OBJECT-TYPE
            SYNTAX DateAndTime
            MAX-ACCESS read-only
            STATUS current
            DESCRIPTION
                "perDateTime. "
            ::= { new_subcardPer24HCurEntry 4 }

        -- 1.3.6.1.4.1.2011.2.25.3.40.50.153.30.1.5
        new_subcardPer24HCurParaLen OBJECT-TYPE
            SYNTAX INTEGER
            MAX-ACCESS read-only
            STATUS current
            DESCRIPTION
                "perParaLen."
            ::= { new_subcardPer24HCurEntry 5 }

        -- 1.3.6.1.4.1.2011.2.25.3.40.50.153.30.1.6
        new_subcardPer24HCurPara OBJECT-TYPE
            SYNTAX OCTET STRING (SIZE (0..100))
            MAX-ACCESS read-only
            STATUS current
            DESCRIPTION
                "perPara."
            ::= { new_subcardPer24HCurEntry 6 }




-- -------------------------------------------------------------------------
-- Perfomance 24-HOUR History Data Table (RTRV-PER-<MOD2>)
-- -------------------------------------------------------------------------
        -- 1.3.6.1.4.1.2011.2.25.3.40.50.153.40
        new_subcardPer24HHisTable OBJECT-TYPE
          SYNTAX SEQUENCE OF New_subcardPer24HHisEntry
          MAX-ACCESS not-accessible
          STATUS current
          DESCRIPTION
              "new_subcardPer24HHis."
          ::= { new_subcard 40 }

        -- 1.3.6.1.4.1.2011.2.25.3.40.50.153.40.1
        new_subcardPer24HHisEntry OBJECT-TYPE
            SYNTAX New_subcardPer24HHisEntry
            MAX-ACCESS not-accessible
            STATUS current
            DESCRIPTION
                "new_subcardPer24HHis."
            INDEX {new_subcardPer24HHisEid, new_subcardPer24HHisParaLen, new_subcardPer24HHisPara, new_subcardPer24HHisDateTimeStart, new_subcardPer24HHisDateTimeEnd}
            ::= { new_subcardPer24HHisTable 1 }

        New_subcardPer24HHisEntry ::=
            SEQUENCE {
                new_subcardPer24HHisEid
                    PerformanceEventType,
                new_subcardPer24HHisParaLen
                    INTEGER,
                new_subcardPer24HHisPara
                    OCTET STRING,
                new_subcardPer24HHisMonValue
                    OCTET STRING,
                new_subcardPer24HHisDateTimeStart
                    DateAndTime,
                new_subcardPer24HHisDateTimeEnd
                    DateAndTime,
                new_subcardPer24HHisVldty
                    INTEGER,
             }

        -- 1.3.6.1.4.1.2011.2.25.3.40.50.153.40.1.1
        new_subcardPer24HHisEid OBJECT-TYPE
            SYNTAX PerformanceEventType
            MAX-ACCESS read-only
            STATUS current
            DESCRIPTION
                "perEid."
            ::= { new_subcardPer24HHisEntry 1 }

        -- 1.3.6.1.4.1.2011.2.25.3.40.50.153.40.1.2
        new_subcardPer24HHisParaLen OBJECT-TYPE
            SYNTAX INTEGER
            MAX-ACCESS read-only
            STATUS current
            DESCRIPTION
                "perParaLen."
            ::= { new_subcardPer24HHisEntry 2 }

        -- 1.3.6.1.4.1.2011.2.25.3.40.50.153.40.1.3
        new_subcardPer24HHisPara OBJECT-TYPE
            SYNTAX OCTET STRING (SIZE (0..100))
            MAX-ACCESS read-only
            STATUS current
            DESCRIPTION
                "perPara."
            ::= { new_subcardPer24HHisEntry 3 }

        -- 1.3.6.1.4.1.2011.2.25.3.40.50.153.40.1.4
        new_subcardPer24HHisMonValue OBJECT-TYPE
            SYNTAX OCTET STRING (SIZE (0..100))
            MAX-ACCESS read-only
            STATUS current
            DESCRIPTION
                "perMonValue."
            ::= { new_subcardPer24HHisEntry 4 }

        -- 1.3.6.1.4.1.2011.2.25.3.40.50.153.40.1.5
        new_subcardPer24HHisDateTimeStart OBJECT-TYPE
            SYNTAX DateAndTime
            MAX-ACCESS read-only
            STATUS current
            DESCRIPTION
                "perDateTimeStart. "
            ::= { new_subcardPer24HHisEntry 5 }

        -- 1.3.6.1.4.1.2011.2.25.3.40.50.153.40.1.6
        new_subcardPer24HHisDateTimeEnd OBJECT-TYPE
            SYNTAX DateAndTime
            MAX-ACCESS read-only
            STATUS current
            DESCRIPTION
                "perDateTimeEnd. "
            ::= { new_subcardPer24HHisEntry 6 }

        -- 1.3.6.1.4.1.2011.2.25.3.40.50.153.40.1.7
        new_subcardPer24HHisVldty OBJECT-TYPE
            SYNTAX INTEGER
            MAX-ACCESS read-only
            STATUS current
            DESCRIPTION
                "perVldty. "
            ::= { new_subcardPer24HHisEntry 7 }



-- Alarm data
      -- 1.3.6.1.4.1.2011.2.25.3.40.50.166
      voa OBJECT IDENTIFIER ::={ optixGlobalNGWDM 166 }


-- -------------------------------------------------------------------------
-- Perfomance 15-MIN Current Data Table (RTRV-PER-<MOD2>)
-- -------------------------------------------------------------------------
        -- 1.3.6.1.4.1.2011.2.25.3.40.50.166.10
        voaPer15MCurTable OBJECT-TYPE
            SYNTAX SEQUENCE OF VoaPer15MCurEntry
            MAX-ACCESS not-accessible
            STATUS current
            DESCRIPTION
                "voaPer15MCur."
            ::= { voa 10 }

        -- 1.3.6.1.4.1.2011.2.25.3.40.50.166.10.1
        voaPer15MCurEntry OBJECT-TYPE
            SYNTAX VoaPer15MCurEntry
            MAX-ACCESS not-accessible
            STATUS current
            DESCRIPTION
              "voaPer15MCur."
            INDEX { voaPer15MCurEid, voaPer15MCurPara }
            ::= { voaPer15MCurTable 1 }

        VoaPer15MCurEntry ::=
            SEQUENCE {
                voaPer15MCurEid
                    PerformanceEventType,
                voaPer15MCurMonValue
                    OCTET STRING,
                voaPer15MCurVldty
                    INTEGER,
                voaPer15MCurDateTime
                    DateAndTime,
                voaPer15MCurParaLen
                    INTEGER,
                voaPer15MCurPara
                    OCTET STRING
            }

        -- 1.3.6.1.4.1.2011.2.25.3.40.50.166.10.1.1
        voaPer15MCurEid OBJECT-TYPE
            SYNTAX PerformanceEventType
            MAX-ACCESS read-only
            STATUS current
            DESCRIPTION
                "perEid."
            ::= { voaPer15MCurEntry 1 }

        -- 1.3.6.1.4.1.2011.2.25.3.40.50.166.10.1.2
        voaPer15MCurMonValue OBJECT-TYPE
            SYNTAX OCTET STRING (SIZE (0..100))
            MAX-ACCESS read-only
            STATUS current
            DESCRIPTION
                "perMonValue."
            ::= { voaPer15MCurEntry 2 }

        -- 1.3.6.1.4.1.2011.2.25.3.40.50.166.10.1.3
        voaPer15MCurVldty OBJECT-TYPE
            SYNTAX INTEGER
            MAX-ACCESS read-only
            STATUS current
            DESCRIPTION
                "perVldty. "
            ::= { voaPer15MCurEntry 3 }

        -- 1.3.6.1.4.1.2011.2.25.3.40.50.166.10.1.4
        voaPer15MCurDateTime OBJECT-TYPE
            SYNTAX DateAndTime
            MAX-ACCESS read-only
            STATUS current
            DESCRIPTION
                "perDateTime. "
            ::= { voaPer15MCurEntry 4 }

        -- 1.3.6.1.4.1.2011.2.25.3.40.50.166.10.1.5
        voaPer15MCurParaLen OBJECT-TYPE
            SYNTAX INTEGER
            MAX-ACCESS read-only
            STATUS current
            DESCRIPTION
                "perParaLen."
            ::= { voaPer15MCurEntry 5 }

        -- 1.3.6.1.4.1.2011.2.25.3.40.50.166.10.1.6
        voaPer15MCurPara OBJECT-TYPE
            SYNTAX OCTET STRING (SIZE (0..100))
            MAX-ACCESS read-only
            STATUS current
            DESCRIPTION
                "perPara."
            ::= { voaPer15MCurEntry 6 }



-- -------------------------------------------------------------------------
-- Perfomance 15-MIN History Data Table (RTRV-PER-<MOD2>)
-- -------------------------------------------------------------------------
        -- 1.3.6.1.4.1.2011.2.25.3.40.50.166.20
        voaPer15MHisTable OBJECT-TYPE
            SYNTAX SEQUENCE OF VoaPer15MHisEntry
            MAX-ACCESS not-accessible
            STATUS current
            DESCRIPTION
                "voaPer15MHis."
            ::= { voa 20 }

        -- 1.3.6.1.4.1.2011.2.25.3.40.50.166.20.1
        voaPer15MHisEntry OBJECT-TYPE
            SYNTAX VoaPer15MHisEntry
            MAX-ACCESS not-accessible
            STATUS current
            DESCRIPTION
                "voaPer15MHis."
            INDEX {voaPer15MHisEid, voaPer15MHisParaLen, voaPer15MHisPara, voaPer15MHisDateTimeStart, voaPer15MHisDateTimeEnd}
            ::= { voaPer15MHisTable 1 }

        VoaPer15MHisEntry ::=
            SEQUENCE {
                voaPer15MHisEid
                    PerformanceEventType,
                voaPer15MHisParaLen
                    INTEGER,
                voaPer15MHisPara
                    OCTET STRING,
                voaPer15MHisMonValue
                    OCTET STRING,
                voaPer15MHisDateTimeStart
                    DateAndTime,
                voaPer15MHisDateTimeEnd
                    DateAndTime,
                voaPer15MHisVldty
                    INTEGER,
             }

        -- 1.3.6.1.4.1.2011.2.25.3.40.50.166.20.1.1
        voaPer15MHisEid OBJECT-TYPE
            SYNTAX PerformanceEventType
            MAX-ACCESS read-only
            STATUS current
            DESCRIPTION
                "perEid."
            ::= { voaPer15MHisEntry 1 }

        -- 1.3.6.1.4.1.2011.2.25.3.40.50.166.20.1.2
        voaPer15MHisParaLen OBJECT-TYPE
            SYNTAX INTEGER
            MAX-ACCESS read-only
            STATUS current
            DESCRIPTION
                "perParaLen."
            ::= { voaPer15MHisEntry 2 }

        -- 1.3.6.1.4.1.2011.2.25.3.40.50.166.20.1.3
        voaPer15MHisPara OBJECT-TYPE
            SYNTAX OCTET STRING (SIZE (0..100))
            MAX-ACCESS read-only
            STATUS current
            DESCRIPTION
                "perPara."
            ::= { voaPer15MHisEntry 3 }

        -- 1.3.6.1.4.1.2011.2.25.3.40.50.166.20.1.4
        voaPer15MHisMonValue OBJECT-TYPE
            SYNTAX OCTET STRING (SIZE (0..100))
            MAX-ACCESS read-only
            STATUS current
            DESCRIPTION
                "perMonValue."
            ::= { voaPer15MHisEntry 4 }

        -- 1.3.6.1.4.1.2011.2.25.3.40.50.166.20.1.5
        voaPer15MHisDateTimeStart OBJECT-TYPE
            SYNTAX DateAndTime
            MAX-ACCESS read-only
            STATUS current
            DESCRIPTION
                "perDateTimeStart. "
            ::= { voaPer15MHisEntry 5 }

        -- 1.3.6.1.4.1.2011.2.25.3.40.50.166.20.1.6
        voaPer15MHisDateTimeEnd OBJECT-TYPE
            SYNTAX DateAndTime
            MAX-ACCESS read-only
            STATUS current
            DESCRIPTION
                "perDateTimeEnd. "
            ::= { voaPer15MHisEntry 6 }

        -- 1.3.6.1.4.1.2011.2.25.3.40.50.166.20.1.7
        voaPer15MHisVldty OBJECT-TYPE
            SYNTAX INTEGER
            MAX-ACCESS read-only
            STATUS current
            DESCRIPTION
                "perVldty. "
            ::= { voaPer15MHisEntry 7 }




-- -------------------------------------------------------------------------
-- Perfomance 24-HOUR Current Data Table (RTRV-PER-<MOD2>)
-- -------------------------------------------------------------------------
        -- 1.3.6.1.4.1.2011.2.25.3.40.50.166.30
        voaPer24HCurTable OBJECT-TYPE
          SYNTAX SEQUENCE OF VoaPer24HCurEntry
          MAX-ACCESS not-accessible
          STATUS current
          DESCRIPTION
              "voaPer24HCur."
          ::= { voa 30 }

        -- 1.3.6.1.4.1.2011.2.25.3.40.50.166.30.1
        voaPer24HCurEntry OBJECT-TYPE
            SYNTAX VoaPer24HCurEntry
            MAX-ACCESS not-accessible
            STATUS current
            DESCRIPTION
              "voaPer24HCur."
            INDEX { voaPer24HCurEid, voaPer24HCurPara }
            ::= { voaPer24HCurTable 1 }

        VoaPer24HCurEntry ::=
            SEQUENCE {
                voaPer24HCurEid
                    PerformanceEventType,
                voaPer24HCurMonValue
                    OCTET STRING,
                voaPer24HCurVldty
                    INTEGER,
                voaPer24HCurDateTime
                    DateAndTime,
                voaPer24HCurParaLen
                    INTEGER,
                voaPer24HCurPara
                    OCTET STRING
            }

        -- 1.3.6.1.4.1.2011.2.25.3.40.50.166.30.1.1
        voaPer24HCurEid OBJECT-TYPE
            SYNTAX PerformanceEventType
            MAX-ACCESS read-only
            STATUS current
            DESCRIPTION
                "perEid."
            ::= { voaPer24HCurEntry 1 }

        -- 1.3.6.1.4.1.2011.2.25.3.40.50.166.30.1.2
        voaPer24HCurMonValue OBJECT-TYPE
            SYNTAX OCTET STRING (SIZE (0..100))
            MAX-ACCESS read-only
            STATUS current
            DESCRIPTION
                "perMonValue."
            ::= { voaPer24HCurEntry 2 }

        -- 1.3.6.1.4.1.2011.2.25.3.40.50.166.30.1.3
        voaPer24HCurVldty OBJECT-TYPE
            SYNTAX INTEGER
            MAX-ACCESS read-only
            STATUS current
            DESCRIPTION
                "perVldty. "
            ::= { voaPer24HCurEntry 3 }

        -- 1.3.6.1.4.1.2011.2.25.3.40.50.166.30.1.4
        voaPer24HCurDateTime OBJECT-TYPE
            SYNTAX DateAndTime
            MAX-ACCESS read-only
            STATUS current
            DESCRIPTION
                "perDateTime. "
            ::= { voaPer24HCurEntry 4 }

        -- 1.3.6.1.4.1.2011.2.25.3.40.50.166.30.1.5
        voaPer24HCurParaLen OBJECT-TYPE
            SYNTAX INTEGER
            MAX-ACCESS read-only
            STATUS current
            DESCRIPTION
                "perParaLen."
            ::= { voaPer24HCurEntry 5 }

        -- 1.3.6.1.4.1.2011.2.25.3.40.50.166.30.1.6
        voaPer24HCurPara OBJECT-TYPE
            SYNTAX OCTET STRING (SIZE (0..100))
            MAX-ACCESS read-only
            STATUS current
            DESCRIPTION
                "perPara."
            ::= { voaPer24HCurEntry 6 }




-- -------------------------------------------------------------------------
-- Perfomance 24-HOUR History Data Table (RTRV-PER-<MOD2>)
-- -------------------------------------------------------------------------
        -- 1.3.6.1.4.1.2011.2.25.3.40.50.166.40
        voaPer24HHisTable OBJECT-TYPE
          SYNTAX SEQUENCE OF VoaPer24HHisEntry
          MAX-ACCESS not-accessible
          STATUS current
          DESCRIPTION
              "voaPer24HHis."
          ::= { voa 40 }

        -- 1.3.6.1.4.1.2011.2.25.3.40.50.166.40.1
        voaPer24HHisEntry OBJECT-TYPE
            SYNTAX VoaPer24HHisEntry
            MAX-ACCESS not-accessible
            STATUS current
            DESCRIPTION
                "voaPer24HHis."
            INDEX {voaPer24HHisEid, voaPer24HHisParaLen, voaPer24HHisPara, voaPer24HHisDateTimeStart, voaPer24HHisDateTimeEnd}
            ::= { voaPer24HHisTable 1 }

        VoaPer24HHisEntry ::=
            SEQUENCE {
                voaPer24HHisEid
                    PerformanceEventType,
                voaPer24HHisParaLen
                    INTEGER,
                voaPer24HHisPara
                    OCTET STRING,
                voaPer24HHisMonValue
                    OCTET STRING,
                voaPer24HHisDateTimeStart
                    DateAndTime,
                voaPer24HHisDateTimeEnd
                    DateAndTime,
                voaPer24HHisVldty
                    INTEGER,
             }

        -- 1.3.6.1.4.1.2011.2.25.3.40.50.166.40.1.1
        voaPer24HHisEid OBJECT-TYPE
            SYNTAX PerformanceEventType
            MAX-ACCESS read-only
            STATUS current
            DESCRIPTION
                "perEid."
            ::= { voaPer24HHisEntry 1 }

        -- 1.3.6.1.4.1.2011.2.25.3.40.50.166.40.1.2
        voaPer24HHisParaLen OBJECT-TYPE
            SYNTAX INTEGER
            MAX-ACCESS read-only
            STATUS current
            DESCRIPTION
                "perParaLen."
            ::= { voaPer24HHisEntry 2 }

        -- 1.3.6.1.4.1.2011.2.25.3.40.50.166.40.1.3
        voaPer24HHisPara OBJECT-TYPE
            SYNTAX OCTET STRING (SIZE (0..100))
            MAX-ACCESS read-only
            STATUS current
            DESCRIPTION
                "perPara."
            ::= { voaPer24HHisEntry 3 }

        -- 1.3.6.1.4.1.2011.2.25.3.40.50.166.40.1.4
        voaPer24HHisMonValue OBJECT-TYPE
            SYNTAX OCTET STRING (SIZE (0..100))
            MAX-ACCESS read-only
            STATUS current
            DESCRIPTION
                "perMonValue."
            ::= { voaPer24HHisEntry 4 }

        -- 1.3.6.1.4.1.2011.2.25.3.40.50.166.40.1.5
        voaPer24HHisDateTimeStart OBJECT-TYPE
            SYNTAX DateAndTime
            MAX-ACCESS read-only
            STATUS current
            DESCRIPTION
                "perDateTimeStart. "
            ::= { voaPer24HHisEntry 5 }

        -- 1.3.6.1.4.1.2011.2.25.3.40.50.166.40.1.6
        voaPer24HHisDateTimeEnd OBJECT-TYPE
            SYNTAX DateAndTime
            MAX-ACCESS read-only
            STATUS current
            DESCRIPTION
                "perDateTimeEnd. "
            ::= { voaPer24HHisEntry 6 }

        -- 1.3.6.1.4.1.2011.2.25.3.40.50.166.40.1.7
        voaPer24HHisVldty OBJECT-TYPE
            SYNTAX INTEGER
            MAX-ACCESS read-only
            STATUS current
            DESCRIPTION
                "perVldty. "
            ::= { voaPer24HHisEntry 7 }


-- Alarm data
      -- 1.3.6.1.4.1.2011.2.25.3.40.50.282
      flex_och OBJECT IDENTIFIER ::={ optixGlobalNGWDM 282 }


-- -------------------------------------------------------------------------
-- Perfomance 15-MIN Current Data Table (RTRV-PER-<MOD2>)
-- -------------------------------------------------------------------------
        -- 1.3.6.1.4.1.2011.2.25.3.40.50.282.10
        flex_ochPer15MCurTable OBJECT-TYPE
            SYNTAX SEQUENCE OF Flex_ochPer15MCurEntry
            MAX-ACCESS not-accessible
            STATUS current
            DESCRIPTION
                "flex_ochPer15MCur."
            ::= { flex_och 10 }

        -- 1.3.6.1.4.1.2011.2.25.3.40.50.282.10.1
        flex_ochPer15MCurEntry OBJECT-TYPE
            SYNTAX Flex_ochPer15MCurEntry
            MAX-ACCESS not-accessible
            STATUS current
            DESCRIPTION
              "flex_ochPer15MCur."
            INDEX { flex_ochPer15MCurEid, flex_ochPer15MCurPara }
            ::= { flex_ochPer15MCurTable 1 }

        Flex_ochPer15MCurEntry ::=
            SEQUENCE {
                flex_ochPer15MCurEid
                    PerformanceEventType,
                flex_ochPer15MCurMonValue
                    OCTET STRING,
                flex_ochPer15MCurVldty
                    INTEGER,
                flex_ochPer15MCurDateTime
                    DateAndTime,
                flex_ochPer15MCurParaLen
                    INTEGER,
                flex_ochPer15MCurPara
                    OCTET STRING
            }

        -- 1.3.6.1.4.1.2011.2.25.3.40.50.282.10.1.1
        flex_ochPer15MCurEid OBJECT-TYPE
            SYNTAX PerformanceEventType
            MAX-ACCESS read-only
            STATUS current
            DESCRIPTION
                "perEid."
            ::= { flex_ochPer15MCurEntry 1 }

        -- 1.3.6.1.4.1.2011.2.25.3.40.50.282.10.1.2
        flex_ochPer15MCurMonValue OBJECT-TYPE
            SYNTAX OCTET STRING (SIZE (0..100))
            MAX-ACCESS read-only
            STATUS current
            DESCRIPTION
                "perMonValue."
            ::= { flex_ochPer15MCurEntry 2 }

        -- 1.3.6.1.4.1.2011.2.25.3.40.50.282.10.1.3
        flex_ochPer15MCurVldty OBJECT-TYPE
            SYNTAX INTEGER
            MAX-ACCESS read-only
            STATUS current
            DESCRIPTION
                "perVldty. "
            ::= { flex_ochPer15MCurEntry 3 }

        -- 1.3.6.1.4.1.2011.2.25.3.40.50.282.10.1.4
        flex_ochPer15MCurDateTime OBJECT-TYPE
            SYNTAX DateAndTime
            MAX-ACCESS read-only
            STATUS current
            DESCRIPTION
                "perDateTime. "
            ::= { flex_ochPer15MCurEntry 4 }

        -- 1.3.6.1.4.1.2011.2.25.3.40.50.282.10.1.5
        flex_ochPer15MCurParaLen OBJECT-TYPE
            SYNTAX INTEGER
            MAX-ACCESS read-only
            STATUS current
            DESCRIPTION
                "perParaLen."
            ::= { flex_ochPer15MCurEntry 5 }

        -- 1.3.6.1.4.1.2011.2.25.3.40.50.282.10.1.6
        flex_ochPer15MCurPara OBJECT-TYPE
            SYNTAX OCTET STRING (SIZE (0..100))
            MAX-ACCESS read-only
            STATUS current
            DESCRIPTION
                "perPara."
            ::= { flex_ochPer15MCurEntry 6 }



-- -------------------------------------------------------------------------
-- Perfomance 15-MIN History Data Table (RTRV-PER-<MOD2>)
-- -------------------------------------------------------------------------
        -- 1.3.6.1.4.1.2011.2.25.3.40.50.282.20
        flex_ochPer15MHisTable OBJECT-TYPE
            SYNTAX SEQUENCE OF Flex_ochPer15MHisEntry
            MAX-ACCESS not-accessible
            STATUS current
            DESCRIPTION
                "flex_ochPer15MHis."
            ::= { flex_och 20 }

        -- 1.3.6.1.4.1.2011.2.25.3.40.50.282.20.1
        flex_ochPer15MHisEntry OBJECT-TYPE
            SYNTAX Flex_ochPer15MHisEntry
            MAX-ACCESS not-accessible
            STATUS current
            DESCRIPTION
                "flex_ochPer15MHis."
            INDEX {flex_ochPer15MHisEid, flex_ochPer15MHisParaLen, flex_ochPer15MHisPara, flex_ochPer15MHisDateTimeStart, flex_ochPer15MHisDateTimeEnd}
            ::= { flex_ochPer15MHisTable 1 }

        Flex_ochPer15MHisEntry ::=
            SEQUENCE {
                flex_ochPer15MHisEid
                    PerformanceEventType,
                flex_ochPer15MHisParaLen
                    INTEGER,
                flex_ochPer15MHisPara
                    OCTET STRING,
                flex_ochPer15MHisMonValue
                    OCTET STRING,
                flex_ochPer15MHisDateTimeStart
                    DateAndTime,
                flex_ochPer15MHisDateTimeEnd
                    DateAndTime,
                flex_ochPer15MHisVldty
                    INTEGER,
             }

        -- 1.3.6.1.4.1.2011.2.25.3.40.50.282.20.1.1
        flex_ochPer15MHisEid OBJECT-TYPE
            SYNTAX PerformanceEventType
            MAX-ACCESS read-only
            STATUS current
            DESCRIPTION
                "perEid."
            ::= { flex_ochPer15MHisEntry 1 }

        -- 1.3.6.1.4.1.2011.2.25.3.40.50.282.20.1.2
        flex_ochPer15MHisParaLen OBJECT-TYPE
            SYNTAX INTEGER
            MAX-ACCESS read-only
            STATUS current
            DESCRIPTION
                "perParaLen."
            ::= { flex_ochPer15MHisEntry 2 }

        -- 1.3.6.1.4.1.2011.2.25.3.40.50.282.20.1.3
        flex_ochPer15MHisPara OBJECT-TYPE
            SYNTAX OCTET STRING (SIZE (0..100))
            MAX-ACCESS read-only
            STATUS current
            DESCRIPTION
                "perPara."
            ::= { flex_ochPer15MHisEntry 3 }

        -- 1.3.6.1.4.1.2011.2.25.3.40.50.282.20.1.4
        flex_ochPer15MHisMonValue OBJECT-TYPE
            SYNTAX OCTET STRING (SIZE (0..100))
            MAX-ACCESS read-only
            STATUS current
            DESCRIPTION
                "perMonValue."
            ::= { flex_ochPer15MHisEntry 4 }

        -- 1.3.6.1.4.1.2011.2.25.3.40.50.282.20.1.5
        flex_ochPer15MHisDateTimeStart OBJECT-TYPE
            SYNTAX DateAndTime
            MAX-ACCESS read-only
            STATUS current
            DESCRIPTION
                "perDateTimeStart. "
            ::= { flex_ochPer15MHisEntry 5 }

        -- 1.3.6.1.4.1.2011.2.25.3.40.50.282.20.1.6
        flex_ochPer15MHisDateTimeEnd OBJECT-TYPE
            SYNTAX DateAndTime
            MAX-ACCESS read-only
            STATUS current
            DESCRIPTION
                "perDateTimeEnd. "
            ::= { flex_ochPer15MHisEntry 6 }

        -- 1.3.6.1.4.1.2011.2.25.3.40.50.282.20.1.7
        flex_ochPer15MHisVldty OBJECT-TYPE
            SYNTAX INTEGER
            MAX-ACCESS read-only
            STATUS current
            DESCRIPTION
                "perVldty. "
            ::= { flex_ochPer15MHisEntry 7 }




-- -------------------------------------------------------------------------
-- Perfomance 24-HOUR Current Data Table (RTRV-PER-<MOD2>)
-- -------------------------------------------------------------------------
        -- 1.3.6.1.4.1.2011.2.25.3.40.50.282.30
        flex_ochPer24HCurTable OBJECT-TYPE
          SYNTAX SEQUENCE OF Flex_ochPer24HCurEntry
          MAX-ACCESS not-accessible
          STATUS current
          DESCRIPTION
              "flex_ochPer24HCur."
          ::= { flex_och 30 }

        -- 1.3.6.1.4.1.2011.2.25.3.40.50.282.30.1
        flex_ochPer24HCurEntry OBJECT-TYPE
            SYNTAX Flex_ochPer24HCurEntry
            MAX-ACCESS not-accessible
            STATUS current
            DESCRIPTION
              "flex_ochPer24HCur."
            INDEX { flex_ochPer24HCurEid, flex_ochPer24HCurPara }
            ::= { flex_ochPer24HCurTable 1 }

        Flex_ochPer24HCurEntry ::=
            SEQUENCE {
                flex_ochPer24HCurEid
                    PerformanceEventType,
                flex_ochPer24HCurMonValue
                    OCTET STRING,
                flex_ochPer24HCurVldty
                    INTEGER,
                flex_ochPer24HCurDateTime
                    DateAndTime,
                flex_ochPer24HCurParaLen
                    INTEGER,
                flex_ochPer24HCurPara
                    OCTET STRING
            }

        -- 1.3.6.1.4.1.2011.2.25.3.40.50.282.30.1.1
        flex_ochPer24HCurEid OBJECT-TYPE
            SYNTAX PerformanceEventType
            MAX-ACCESS read-only
            STATUS current
            DESCRIPTION
                "perEid."
            ::= { flex_ochPer24HCurEntry 1 }

        -- 1.3.6.1.4.1.2011.2.25.3.40.50.282.30.1.2
        flex_ochPer24HCurMonValue OBJECT-TYPE
            SYNTAX OCTET STRING (SIZE (0..100))
            MAX-ACCESS read-only
            STATUS current
            DESCRIPTION
                "perMonValue."
            ::= { flex_ochPer24HCurEntry 2 }

        -- 1.3.6.1.4.1.2011.2.25.3.40.50.282.30.1.3
        flex_ochPer24HCurVldty OBJECT-TYPE
            SYNTAX INTEGER
            MAX-ACCESS read-only
            STATUS current
            DESCRIPTION
                "perVldty. "
            ::= { flex_ochPer24HCurEntry 3 }

        -- 1.3.6.1.4.1.2011.2.25.3.40.50.282.30.1.4
        flex_ochPer24HCurDateTime OBJECT-TYPE
            SYNTAX DateAndTime
            MAX-ACCESS read-only
            STATUS current
            DESCRIPTION
                "perDateTime. "
            ::= { flex_ochPer24HCurEntry 4 }

        -- 1.3.6.1.4.1.2011.2.25.3.40.50.282.30.1.5
        flex_ochPer24HCurParaLen OBJECT-TYPE
            SYNTAX INTEGER
            MAX-ACCESS read-only
            STATUS current
            DESCRIPTION
                "perParaLen."
            ::= { flex_ochPer24HCurEntry 5 }

        -- 1.3.6.1.4.1.2011.2.25.3.40.50.282.30.1.6
        flex_ochPer24HCurPara OBJECT-TYPE
            SYNTAX OCTET STRING (SIZE (0..100))
            MAX-ACCESS read-only
            STATUS current
            DESCRIPTION
                "perPara."
            ::= { flex_ochPer24HCurEntry 6 }




-- -------------------------------------------------------------------------
-- Perfomance 24-HOUR History Data Table (RTRV-PER-<MOD2>)
-- -------------------------------------------------------------------------
        -- 1.3.6.1.4.1.2011.2.25.3.40.50.282.40
        flex_ochPer24HHisTable OBJECT-TYPE
          SYNTAX SEQUENCE OF Flex_ochPer24HHisEntry
          MAX-ACCESS not-accessible
          STATUS current
          DESCRIPTION
              "flex_ochPer24HHis."
          ::= { flex_och 40 }

        -- 1.3.6.1.4.1.2011.2.25.3.40.50.282.40.1
        flex_ochPer24HHisEntry OBJECT-TYPE
            SYNTAX Flex_ochPer24HHisEntry
            MAX-ACCESS not-accessible
            STATUS current
            DESCRIPTION
                "flex_ochPer24HHis."
            INDEX {flex_ochPer24HHisEid, flex_ochPer24HHisParaLen, flex_ochPer24HHisPara, flex_ochPer24HHisDateTimeStart, flex_ochPer24HHisDateTimeEnd}
            ::= { flex_ochPer24HHisTable 1 }

        Flex_ochPer24HHisEntry ::=
            SEQUENCE {
                flex_ochPer24HHisEid
                    PerformanceEventType,
                flex_ochPer24HHisParaLen
                    INTEGER,
                flex_ochPer24HHisPara
                    OCTET STRING,
                flex_ochPer24HHisMonValue
                    OCTET STRING,
                flex_ochPer24HHisDateTimeStart
                    DateAndTime,
                flex_ochPer24HHisDateTimeEnd
                    DateAndTime,
                flex_ochPer24HHisVldty
                    INTEGER,
             }

        -- 1.3.6.1.4.1.2011.2.25.3.40.50.282.40.1.1
        flex_ochPer24HHisEid OBJECT-TYPE
            SYNTAX PerformanceEventType
            MAX-ACCESS read-only
            STATUS current
            DESCRIPTION
                "perEid."
            ::= { flex_ochPer24HHisEntry 1 }

        -- 1.3.6.1.4.1.2011.2.25.3.40.50.282.40.1.2
        flex_ochPer24HHisParaLen OBJECT-TYPE
            SYNTAX INTEGER
            MAX-ACCESS read-only
            STATUS current
            DESCRIPTION
                "perParaLen."
            ::= { flex_ochPer24HHisEntry 2 }

        -- 1.3.6.1.4.1.2011.2.25.3.40.50.282.40.1.3
        flex_ochPer24HHisPara OBJECT-TYPE
            SYNTAX OCTET STRING (SIZE (0..100))
            MAX-ACCESS read-only
            STATUS current
            DESCRIPTION
                "perPara."
            ::= { flex_ochPer24HHisEntry 3 }

        -- 1.3.6.1.4.1.2011.2.25.3.40.50.282.40.1.4
        flex_ochPer24HHisMonValue OBJECT-TYPE
            SYNTAX OCTET STRING (SIZE (0..100))
            MAX-ACCESS read-only
            STATUS current
            DESCRIPTION
                "perMonValue."
            ::= { flex_ochPer24HHisEntry 4 }

        -- 1.3.6.1.4.1.2011.2.25.3.40.50.282.40.1.5
        flex_ochPer24HHisDateTimeStart OBJECT-TYPE
            SYNTAX DateAndTime
            MAX-ACCESS read-only
            STATUS current
            DESCRIPTION
                "perDateTimeStart. "
            ::= { flex_ochPer24HHisEntry 5 }

        -- 1.3.6.1.4.1.2011.2.25.3.40.50.282.40.1.6
        flex_ochPer24HHisDateTimeEnd OBJECT-TYPE
            SYNTAX DateAndTime
            MAX-ACCESS read-only
            STATUS current
            DESCRIPTION
                "perDateTimeEnd. "
            ::= { flex_ochPer24HHisEntry 6 }

        -- 1.3.6.1.4.1.2011.2.25.3.40.50.282.40.1.7
        flex_ochPer24HHisVldty OBJECT-TYPE
            SYNTAX INTEGER
            MAX-ACCESS read-only
            STATUS current
            DESCRIPTION
                "perVldty. "
            ::= { flex_ochPer24HHisEntry 7 }



-- Alarm data
      -- 1.3.6.1.4.1.2011.2.25.3.40.50.168
      odu0_path OBJECT IDENTIFIER ::={ optixGlobalNGWDM 168 }


-- -------------------------------------------------------------------------
-- Perfomance 15-MIN Current Data Table (RTRV-PER-<MOD2>)
-- -------------------------------------------------------------------------
        -- 1.3.6.1.4.1.2011.2.25.3.40.50.168.10
        odu0_pathPer15MCurTable OBJECT-TYPE
          SYNTAX SEQUENCE OF Odu0_pathPer15MCurEntry
          MAX-ACCESS not-accessible
          STATUS current
          DESCRIPTION
              "odu0_pathPer15MCur."
          ::= { odu0_path 10 }

        -- 1.3.6.1.4.1.2011.2.25.3.40.50.168.10.1
        odu0_pathPer15MCurEntry OBJECT-TYPE
            SYNTAX Odu0_pathPer15MCurEntry
            MAX-ACCESS not-accessible
            STATUS current
            DESCRIPTION
              "odu0_pathPer15MCur."
            INDEX { odu0_pathPer15MCurEid, odu0_pathPer15MCurPara }
            ::= { odu0_pathPer15MCurTable 1 }

        Odu0_pathPer15MCurEntry ::=
            SEQUENCE {
                odu0_pathPer15MCurEid
                    PerformanceEventType,
                odu0_pathPer15MCurMonValue
                    OCTET STRING,
                odu0_pathPer15MCurVldty
                    INTEGER,
                odu0_pathPer15MCurDateTime
                    DateAndTime,
                odu0_pathPer15MCurParaLen
                    INTEGER,
                odu0_pathPer15MCurPara
                    OCTET STRING
            }

        -- 1.3.6.1.4.1.2011.2.25.3.40.50.168.10.1.1
        odu0_pathPer15MCurEid OBJECT-TYPE
            SYNTAX PerformanceEventType
            MAX-ACCESS read-only
            STATUS current
            DESCRIPTION
                "perEid."
            ::= { odu0_pathPer15MCurEntry 1 }

        -- 1.3.6.1.4.1.2011.2.25.3.40.50.168.10.1.2
        odu0_pathPer15MCurMonValue OBJECT-TYPE
            SYNTAX OCTET STRING (SIZE (0..100))
            MAX-ACCESS read-only
            STATUS current
            DESCRIPTION
                "perMonValue."
            ::= { odu0_pathPer15MCurEntry 2 }

        -- 1.3.6.1.4.1.2011.2.25.3.40.50.168.10.1.3
        odu0_pathPer15MCurVldty OBJECT-TYPE
            SYNTAX INTEGER
            MAX-ACCESS read-only
            STATUS current
            DESCRIPTION
                "perVldty. "
            ::= { odu0_pathPer15MCurEntry 3 }

        -- 1.3.6.1.4.1.2011.2.25.3.40.50.168.10.1.4
        odu0_pathPer15MCurDateTime OBJECT-TYPE
            SYNTAX DateAndTime
            MAX-ACCESS read-only
            STATUS current
            DESCRIPTION
                "perDateTime. "
            ::= { odu0_pathPer15MCurEntry 4 }

        -- 1.3.6.1.4.1.2011.2.25.3.40.50.168.10.1.5
        odu0_pathPer15MCurParaLen OBJECT-TYPE
            SYNTAX INTEGER
            MAX-ACCESS read-only
            STATUS current
            DESCRIPTION
                "perParaLen."
            ::= { odu0_pathPer15MCurEntry 5 }

        -- 1.3.6.1.4.1.2011.2.25.3.40.50.168.10.1.6
        odu0_pathPer15MCurPara OBJECT-TYPE
            SYNTAX OCTET STRING (SIZE (0..100))
            MAX-ACCESS read-only
            STATUS current
            DESCRIPTION
                "perPara."
            ::= { odu0_pathPer15MCurEntry 6 }




-- -------------------------------------------------------------------------
-- Perfomance 15-MIN History Data Table (RTRV-PER-<MOD2>)
-- -------------------------------------------------------------------------
        -- 1.3.6.1.4.1.2011.2.25.3.40.50.168.20
        odu0_pathPer15MHisTable OBJECT-TYPE
          SYNTAX SEQUENCE OF Odu0_pathPer15MHisEntry
          MAX-ACCESS not-accessible
          STATUS current
          DESCRIPTION
              "odu0_pathPer15MHis."
          ::= { odu0_path 20 }

        -- 1.3.6.1.4.1.2011.2.25.3.40.50.168.20.1
        odu0_pathPer15MHisEntry OBJECT-TYPE
            SYNTAX Odu0_pathPer15MHisEntry
            MAX-ACCESS not-accessible
            STATUS current
            DESCRIPTION
                "odu0_pathPer15MHis."
            INDEX {odu0_pathPer15MHisEid, odu0_pathPer15MHisParaLen, odu0_pathPer15MHisPara, odu0_pathPer15MHisDateTimeStart, odu0_pathPer15MHisDateTimeEnd}
            ::= { odu0_pathPer15MHisTable 1 }

        Odu0_pathPer15MHisEntry ::=
            SEQUENCE {
                odu0_pathPer15MHisEid
                    PerformanceEventType,
                odu0_pathPer15MHisParaLen
                    INTEGER,
                odu0_pathPer15MHisPara
                    OCTET STRING,
                odu0_pathPer15MHisMonValue
                    OCTET STRING,
                odu0_pathPer15MHisDateTimeStart
                    DateAndTime,
                odu0_pathPer15MHisDateTimeEnd
                    DateAndTime,
                odu0_pathPer15MHisVldty
                    INTEGER,
             }

        -- 1.3.6.1.4.1.2011.2.25.3.40.50.168.20.1.1
        odu0_pathPer15MHisEid OBJECT-TYPE
            SYNTAX PerformanceEventType
            MAX-ACCESS read-only
            STATUS current
            DESCRIPTION
                "perEid."
            ::= { odu0_pathPer15MHisEntry 1 }

        -- 1.3.6.1.4.1.2011.2.25.3.40.50.168.20.1.2
        odu0_pathPer15MHisParaLen OBJECT-TYPE
            SYNTAX INTEGER
            MAX-ACCESS read-only
            STATUS current
            DESCRIPTION
                "perParaLen."
            ::= { odu0_pathPer15MHisEntry 2 }

        -- 1.3.6.1.4.1.2011.2.25.3.40.50.168.20.1.3
        odu0_pathPer15MHisPara OBJECT-TYPE
            SYNTAX OCTET STRING (SIZE (0..100))
            MAX-ACCESS read-only
            STATUS current
            DESCRIPTION
                "perPara."
            ::= { odu0_pathPer15MHisEntry 3 }

        -- 1.3.6.1.4.1.2011.2.25.3.40.50.168.20.1.4
        odu0_pathPer15MHisMonValue OBJECT-TYPE
            SYNTAX OCTET STRING (SIZE (0..100))
            MAX-ACCESS read-only
            STATUS current
            DESCRIPTION
                "perMonValue."
            ::= { odu0_pathPer15MHisEntry 4 }

        -- 1.3.6.1.4.1.2011.2.25.3.40.50.168.20.1.5
        odu0_pathPer15MHisDateTimeStart OBJECT-TYPE
            SYNTAX DateAndTime
            MAX-ACCESS read-only
            STATUS current
            DESCRIPTION
                "perDateTimeStart. "
            ::= { odu0_pathPer15MHisEntry 5 }

        -- 1.3.6.1.4.1.2011.2.25.3.40.50.168.20.1.6
        odu0_pathPer15MHisDateTimeEnd OBJECT-TYPE
            SYNTAX DateAndTime
            MAX-ACCESS read-only
            STATUS current
            DESCRIPTION
                "perDateTimeEnd. "
            ::= { odu0_pathPer15MHisEntry 6 }

        -- 1.3.6.1.4.1.2011.2.25.3.40.50.168.20.1.7
        odu0_pathPer15MHisVldty OBJECT-TYPE
            SYNTAX INTEGER
            MAX-ACCESS read-only
            STATUS current
            DESCRIPTION
                "perVldty. "
            ::= { odu0_pathPer15MHisEntry 7 }




-- -------------------------------------------------------------------------
-- Perfomance 24-HOUR Current Data Table (RTRV-PER-<MOD2>)
-- -------------------------------------------------------------------------
        -- 1.3.6.1.4.1.2011.2.25.3.40.50.168.30
        odu0_pathPer24HCurTable OBJECT-TYPE
          SYNTAX SEQUENCE OF Odu0_pathPer24HCurEntry
          MAX-ACCESS not-accessible
          STATUS current
          DESCRIPTION
              "odu0_pathPer24HCur."
          ::= { odu0_path 30 }

        -- 1.3.6.1.4.1.2011.2.25.3.40.50.168.30.1
        odu0_pathPer24HCurEntry OBJECT-TYPE
            SYNTAX Odu0_pathPer24HCurEntry
            MAX-ACCESS not-accessible
            STATUS current
            DESCRIPTION
              "odu0_pathPer24HCur."
            INDEX { odu0_pathPer24HCurEid, odu0_pathPer24HCurPara }
            ::= { odu0_pathPer24HCurTable 1 }

        Odu0_pathPer24HCurEntry ::=
            SEQUENCE {
                odu0_pathPer24HCurEid
                    PerformanceEventType,
                odu0_pathPer24HCurMonValue
                    OCTET STRING,
                odu0_pathPer24HCurVldty
                    INTEGER,
                odu0_pathPer24HCurDateTime
                    DateAndTime,
                odu0_pathPer24HCurParaLen
                    INTEGER,
                odu0_pathPer24HCurPara
                    OCTET STRING
            }

        -- 1.3.6.1.4.1.2011.2.25.3.40.50.168.30.1.1
        odu0_pathPer24HCurEid OBJECT-TYPE
            SYNTAX PerformanceEventType
            MAX-ACCESS read-only
            STATUS current
            DESCRIPTION
                "perEid."
            ::= { odu0_pathPer24HCurEntry 1 }

        -- 1.3.6.1.4.1.2011.2.25.3.40.50.168.30.1.2
        odu0_pathPer24HCurMonValue OBJECT-TYPE
            SYNTAX OCTET STRING (SIZE (0..100))
            MAX-ACCESS read-only
            STATUS current
            DESCRIPTION
                "perMonValue."
            ::= { odu0_pathPer24HCurEntry 2 }

        -- 1.3.6.1.4.1.2011.2.25.3.40.50.168.30.1.3
        odu0_pathPer24HCurVldty OBJECT-TYPE
            SYNTAX INTEGER
            MAX-ACCESS read-only
            STATUS current
            DESCRIPTION
                "perVldty. "
            ::= { odu0_pathPer24HCurEntry 3 }

        -- 1.3.6.1.4.1.2011.2.25.3.40.50.168.30.1.4
        odu0_pathPer24HCurDateTime OBJECT-TYPE
            SYNTAX DateAndTime
            MAX-ACCESS read-only
            STATUS current
            DESCRIPTION
                "perDateTime. "
            ::= { odu0_pathPer24HCurEntry 4 }

        -- 1.3.6.1.4.1.2011.2.25.3.40.50.168.30.1.5
        odu0_pathPer24HCurParaLen OBJECT-TYPE
            SYNTAX INTEGER
            MAX-ACCESS read-only
            STATUS current
            DESCRIPTION
                "perParaLen."
            ::= { odu0_pathPer24HCurEntry 5 }

        -- 1.3.6.1.4.1.2011.2.25.3.40.50.168.30.1.6
        odu0_pathPer24HCurPara OBJECT-TYPE
            SYNTAX OCTET STRING (SIZE (0..100))
            MAX-ACCESS read-only
            STATUS current
            DESCRIPTION
                "perPara."
            ::= { odu0_pathPer24HCurEntry 6 }




-- -------------------------------------------------------------------------
-- Perfomance 24-HOUR History Data Table (RTRV-PER-<MOD2>)
-- -------------------------------------------------------------------------
        -- 1.3.6.1.4.1.2011.2.25.3.40.50.168.40
        odu0_pathPer24HHisTable OBJECT-TYPE
          SYNTAX SEQUENCE OF Odu0_pathPer24HHisEntry
          MAX-ACCESS not-accessible
          STATUS current
          DESCRIPTION
              "odu0_pathPer24HHis."
          ::= { odu0_path 40 }

        -- 1.3.6.1.4.1.2011.2.25.3.40.50.168.40.1
        odu0_pathPer24HHisEntry OBJECT-TYPE
            SYNTAX Odu0_pathPer24HHisEntry
            MAX-ACCESS not-accessible
            STATUS current
            DESCRIPTION
                "odu0_pathPer24HHis."
            INDEX {odu0_pathPer24HHisEid, odu0_pathPer24HHisParaLen, odu0_pathPer24HHisPara, odu0_pathPer24HHisDateTimeStart, odu0_pathPer24HHisDateTimeEnd}
            ::= { odu0_pathPer24HHisTable 1 }

        Odu0_pathPer24HHisEntry ::=
            SEQUENCE {
                odu0_pathPer24HHisEid
                    PerformanceEventType,
                odu0_pathPer24HHisParaLen
                    INTEGER,
                odu0_pathPer24HHisPara
                    OCTET STRING,
                odu0_pathPer24HHisMonValue
                    OCTET STRING,
                odu0_pathPer24HHisDateTimeStart
                    DateAndTime,
                odu0_pathPer24HHisDateTimeEnd
                    DateAndTime,
                odu0_pathPer24HHisVldty
                    INTEGER,
             }

        -- 1.3.6.1.4.1.2011.2.25.3.40.50.168.40.1.1
        odu0_pathPer24HHisEid OBJECT-TYPE
            SYNTAX PerformanceEventType
            MAX-ACCESS read-only
            STATUS current
            DESCRIPTION
                "perEid."
            ::= { odu0_pathPer24HHisEntry 1 }

        -- 1.3.6.1.4.1.2011.2.25.3.40.50.168.40.1.2
        odu0_pathPer24HHisParaLen OBJECT-TYPE
            SYNTAX INTEGER
            MAX-ACCESS read-only
            STATUS current
            DESCRIPTION
                "perParaLen."
            ::= { odu0_pathPer24HHisEntry 2 }

        -- 1.3.6.1.4.1.2011.2.25.3.40.50.168.40.1.3
        odu0_pathPer24HHisPara OBJECT-TYPE
            SYNTAX OCTET STRING (SIZE (0..100))
            MAX-ACCESS read-only
            STATUS current
            DESCRIPTION
                "perPara."
            ::= { odu0_pathPer24HHisEntry 3 }

        -- 1.3.6.1.4.1.2011.2.25.3.40.50.168.40.1.4
        odu0_pathPer24HHisMonValue OBJECT-TYPE
            SYNTAX OCTET STRING (SIZE (0..100))
            MAX-ACCESS read-only
            STATUS current
            DESCRIPTION
                "perMonValue."
            ::= { odu0_pathPer24HHisEntry 4 }

        -- 1.3.6.1.4.1.2011.2.25.3.40.50.168.40.1.5
        odu0_pathPer24HHisDateTimeStart OBJECT-TYPE
            SYNTAX DateAndTime
            MAX-ACCESS read-only
            STATUS current
            DESCRIPTION
                "perDateTimeStart. "
            ::= { odu0_pathPer24HHisEntry 5 }

        -- 1.3.6.1.4.1.2011.2.25.3.40.50.168.40.1.6
        odu0_pathPer24HHisDateTimeEnd OBJECT-TYPE
            SYNTAX DateAndTime
            MAX-ACCESS read-only
            STATUS current
            DESCRIPTION
                "perDateTimeEnd. "
            ::= { odu0_pathPer24HHisEntry 6 }

        -- 1.3.6.1.4.1.2011.2.25.3.40.50.168.40.1.7
        odu0_pathPer24HHisVldty OBJECT-TYPE
            SYNTAX INTEGER
            MAX-ACCESS read-only
            STATUS current
            DESCRIPTION
                "perVldty. "
            ::= { odu0_pathPer24HHisEntry 7 }




-- Alarm data
      -- 1.3.6.1.4.1.2011.2.25.3.40.50.169
      otu0_path OBJECT IDENTIFIER ::={ optixGlobalNGWDM 169 }


-- -------------------------------------------------------------------------
-- Perfomance 15-MIN Current Data Table (RTRV-PER-<MOD2>)
-- -------------------------------------------------------------------------
        -- 1.3.6.1.4.1.2011.2.25.3.40.50.169.10
        otu0_pathPer15MCurTable OBJECT-TYPE
          SYNTAX SEQUENCE OF Otu0_pathPer15MCurEntry
          MAX-ACCESS not-accessible
          STATUS current
          DESCRIPTION
              "otu0_pathPer15MCur."
          ::= { otu0_path 10 }

        -- 1.3.6.1.4.1.2011.2.25.3.40.50.169.10.1
        otu0_pathPer15MCurEntry OBJECT-TYPE
            SYNTAX Otu0_pathPer15MCurEntry
            MAX-ACCESS not-accessible
            STATUS current
            DESCRIPTION
              "otu0_pathPer15MCur."
            INDEX { otu0_pathPer15MCurEid, otu0_pathPer15MCurPara }
            ::= { otu0_pathPer15MCurTable 1 }

        Otu0_pathPer15MCurEntry ::=
            SEQUENCE {
                otu0_pathPer15MCurEid
                    PerformanceEventType,
                otu0_pathPer15MCurMonValue
                    OCTET STRING,
                otu0_pathPer15MCurVldty
                    INTEGER,
                otu0_pathPer15MCurDateTime
                    DateAndTime,
                otu0_pathPer15MCurParaLen
                    INTEGER,
                otu0_pathPer15MCurPara
                    OCTET STRING
            }

        -- 1.3.6.1.4.1.2011.2.25.3.40.50.169.10.1.1
        otu0_pathPer15MCurEid OBJECT-TYPE
            SYNTAX PerformanceEventType
            MAX-ACCESS read-only
            STATUS current
            DESCRIPTION
                "perEid."
            ::= { otu0_pathPer15MCurEntry 1 }

        -- 1.3.6.1.4.1.2011.2.25.3.40.50.169.10.1.2
        otu0_pathPer15MCurMonValue OBJECT-TYPE
            SYNTAX OCTET STRING (SIZE (0..100))
            MAX-ACCESS read-only
            STATUS current
            DESCRIPTION
                "perMonValue."
            ::= { otu0_pathPer15MCurEntry 2 }

        -- 1.3.6.1.4.1.2011.2.25.3.40.50.169.10.1.3
        otu0_pathPer15MCurVldty OBJECT-TYPE
            SYNTAX INTEGER
            MAX-ACCESS read-only
            STATUS current
            DESCRIPTION
                "perVldty. "
            ::= { otu0_pathPer15MCurEntry 3 }

        -- 1.3.6.1.4.1.2011.2.25.3.40.50.169.10.1.4
        otu0_pathPer15MCurDateTime OBJECT-TYPE
            SYNTAX DateAndTime
            MAX-ACCESS read-only
            STATUS current
            DESCRIPTION
                "perDateTime. "
            ::= { otu0_pathPer15MCurEntry 4 }

        -- 1.3.6.1.4.1.2011.2.25.3.40.50.169.10.1.5
        otu0_pathPer15MCurParaLen OBJECT-TYPE
            SYNTAX INTEGER
            MAX-ACCESS read-only
            STATUS current
            DESCRIPTION
                "perParaLen."
            ::= { otu0_pathPer15MCurEntry 5 }

        -- 1.3.6.1.4.1.2011.2.25.3.40.50.169.10.1.6
        otu0_pathPer15MCurPara OBJECT-TYPE
            SYNTAX OCTET STRING (SIZE (0..100))
            MAX-ACCESS read-only
            STATUS current
            DESCRIPTION
                "perPara."
            ::= { otu0_pathPer15MCurEntry 6 }




-- -------------------------------------------------------------------------
-- Perfomance 15-MIN History Data Table (RTRV-PER-<MOD2>)
-- -------------------------------------------------------------------------
        -- 1.3.6.1.4.1.2011.2.25.3.40.50.169.20
        otu0_pathPer15MHisTable OBJECT-TYPE
          SYNTAX SEQUENCE OF Otu0_pathPer15MHisEntry
          MAX-ACCESS not-accessible
          STATUS current
          DESCRIPTION
              "otu0_pathPer15MHis."
          ::= { otu0_path 20 }

        -- 1.3.6.1.4.1.2011.2.25.3.40.50.169.20.1
        otu0_pathPer15MHisEntry OBJECT-TYPE
            SYNTAX Otu0_pathPer15MHisEntry
            MAX-ACCESS not-accessible
            STATUS current
            DESCRIPTION
                "otu0_pathPer15MHis."
            INDEX {otu0_pathPer15MHisEid, otu0_pathPer15MHisParaLen, otu0_pathPer15MHisPara, otu0_pathPer15MHisDateTimeStart, otu0_pathPer15MHisDateTimeEnd}
            ::= { otu0_pathPer15MHisTable 1 }

        Otu0_pathPer15MHisEntry ::=
            SEQUENCE {
                otu0_pathPer15MHisEid
                    PerformanceEventType,
                otu0_pathPer15MHisParaLen
                    INTEGER,
                otu0_pathPer15MHisPara
                    OCTET STRING,
                otu0_pathPer15MHisMonValue
                    OCTET STRING,
                otu0_pathPer15MHisDateTimeStart
                    DateAndTime,
                otu0_pathPer15MHisDateTimeEnd
                    DateAndTime,
                otu0_pathPer15MHisVldty
                    INTEGER,
             }

        -- 1.3.6.1.4.1.2011.2.25.3.40.50.169.20.1.1
        otu0_pathPer15MHisEid OBJECT-TYPE
            SYNTAX PerformanceEventType
            MAX-ACCESS read-only
            STATUS current
            DESCRIPTION
                "perEid."
            ::= { otu0_pathPer15MHisEntry 1 }

        -- 1.3.6.1.4.1.2011.2.25.3.40.50.169.20.1.2
        otu0_pathPer15MHisParaLen OBJECT-TYPE
            SYNTAX INTEGER
            MAX-ACCESS read-only
            STATUS current
            DESCRIPTION
                "perParaLen."
            ::= { otu0_pathPer15MHisEntry 2 }

        -- 1.3.6.1.4.1.2011.2.25.3.40.50.169.20.1.3
        otu0_pathPer15MHisPara OBJECT-TYPE
            SYNTAX OCTET STRING (SIZE (0..100))
            MAX-ACCESS read-only
            STATUS current
            DESCRIPTION
                "perPara."
            ::= { otu0_pathPer15MHisEntry 3 }

        -- 1.3.6.1.4.1.2011.2.25.3.40.50.169.20.1.4
        otu0_pathPer15MHisMonValue OBJECT-TYPE
            SYNTAX OCTET STRING (SIZE (0..100))
            MAX-ACCESS read-only
            STATUS current
            DESCRIPTION
                "perMonValue."
            ::= { otu0_pathPer15MHisEntry 4 }

        -- 1.3.6.1.4.1.2011.2.25.3.40.50.169.20.1.5
        otu0_pathPer15MHisDateTimeStart OBJECT-TYPE
            SYNTAX DateAndTime
            MAX-ACCESS read-only
            STATUS current
            DESCRIPTION
                "perDateTimeStart. "
            ::= { otu0_pathPer15MHisEntry 5 }

        -- 1.3.6.1.4.1.2011.2.25.3.40.50.169.20.1.6
        otu0_pathPer15MHisDateTimeEnd OBJECT-TYPE
            SYNTAX DateAndTime
            MAX-ACCESS read-only
            STATUS current
            DESCRIPTION
                "perDateTimeEnd. "
            ::= { otu0_pathPer15MHisEntry 6 }

        -- 1.3.6.1.4.1.2011.2.25.3.40.50.169.20.1.7
        otu0_pathPer15MHisVldty OBJECT-TYPE
            SYNTAX INTEGER
            MAX-ACCESS read-only
            STATUS current
            DESCRIPTION
                "perVldty. "
            ::= { otu0_pathPer15MHisEntry 7 }




-- -------------------------------------------------------------------------
-- Perfomance 24-HOUR Current Data Table (RTRV-PER-<MOD2>)
-- -------------------------------------------------------------------------
        -- 1.3.6.1.4.1.2011.2.25.3.40.50.169.30
        otu0_pathPer24HCurTable OBJECT-TYPE
          SYNTAX SEQUENCE OF Otu0_pathPer24HCurEntry
          MAX-ACCESS not-accessible
          STATUS current
          DESCRIPTION
              "otu0_pathPer24HCur."
          ::= { otu0_path 30 }

        -- 1.3.6.1.4.1.2011.2.25.3.40.50.169.30.1
        otu0_pathPer24HCurEntry OBJECT-TYPE
            SYNTAX Otu0_pathPer24HCurEntry
            MAX-ACCESS not-accessible
            STATUS current
            DESCRIPTION
              "otu0_pathPer24HCur."
            INDEX { otu0_pathPer24HCurEid, otu0_pathPer24HCurPara }
            ::= { otu0_pathPer24HCurTable 1 }

        Otu0_pathPer24HCurEntry ::=
            SEQUENCE {
                otu0_pathPer24HCurEid
                    PerformanceEventType,
                otu0_pathPer24HCurMonValue
                    OCTET STRING,
                otu0_pathPer24HCurVldty
                    INTEGER,
                otu0_pathPer24HCurDateTime
                    DateAndTime,
                otu0_pathPer24HCurParaLen
                    INTEGER,
                otu0_pathPer24HCurPara
                    OCTET STRING
            }

        -- 1.3.6.1.4.1.2011.2.25.3.40.50.169.30.1.1
        otu0_pathPer24HCurEid OBJECT-TYPE
            SYNTAX PerformanceEventType
            MAX-ACCESS read-only
            STATUS current
            DESCRIPTION
                "perEid."
            ::= { otu0_pathPer24HCurEntry 1 }

        -- 1.3.6.1.4.1.2011.2.25.3.40.50.169.30.1.2
        otu0_pathPer24HCurMonValue OBJECT-TYPE
            SYNTAX OCTET STRING (SIZE (0..100))
            MAX-ACCESS read-only
            STATUS current
            DESCRIPTION
                "perMonValue."
            ::= { otu0_pathPer24HCurEntry 2 }

        -- 1.3.6.1.4.1.2011.2.25.3.40.50.169.30.1.3
        otu0_pathPer24HCurVldty OBJECT-TYPE
            SYNTAX INTEGER
            MAX-ACCESS read-only
            STATUS current
            DESCRIPTION
                "perVldty. "
            ::= { otu0_pathPer24HCurEntry 3 }

        -- 1.3.6.1.4.1.2011.2.25.3.40.50.169.30.1.4
        otu0_pathPer24HCurDateTime OBJECT-TYPE
            SYNTAX DateAndTime
            MAX-ACCESS read-only
            STATUS current
            DESCRIPTION
                "perDateTime. "
            ::= { otu0_pathPer24HCurEntry 4 }

        -- 1.3.6.1.4.1.2011.2.25.3.40.50.169.30.1.5
        otu0_pathPer24HCurParaLen OBJECT-TYPE
            SYNTAX INTEGER
            MAX-ACCESS read-only
            STATUS current
            DESCRIPTION
                "perParaLen."
            ::= { otu0_pathPer24HCurEntry 5 }

        -- 1.3.6.1.4.1.2011.2.25.3.40.50.169.30.1.6
        otu0_pathPer24HCurPara OBJECT-TYPE
            SYNTAX OCTET STRING (SIZE (0..100))
            MAX-ACCESS read-only
            STATUS current
            DESCRIPTION
                "perPara."
            ::= { otu0_pathPer24HCurEntry 6 }




-- -------------------------------------------------------------------------
-- Perfomance 24-HOUR History Data Table (RTRV-PER-<MOD2>)
-- -------------------------------------------------------------------------
        -- 1.3.6.1.4.1.2011.2.25.3.40.50.169.40
        otu0_pathPer24HHisTable OBJECT-TYPE
          SYNTAX SEQUENCE OF Otu0_pathPer24HHisEntry
          MAX-ACCESS not-accessible
          STATUS current
          DESCRIPTION
              "otu0_pathPer24HHis."
          ::= { otu0_path 40 }

        -- 1.3.6.1.4.1.2011.2.25.3.40.50.169.40.1
        otu0_pathPer24HHisEntry OBJECT-TYPE
            SYNTAX Otu0_pathPer24HHisEntry
            MAX-ACCESS not-accessible
            STATUS current
            DESCRIPTION
                "otu0_pathPer24HHis."
            INDEX {otu0_pathPer24HHisEid, otu0_pathPer24HHisParaLen, otu0_pathPer24HHisPara, otu0_pathPer24HHisDateTimeStart, otu0_pathPer24HHisDateTimeEnd}
            ::= { otu0_pathPer24HHisTable 1 }

        Otu0_pathPer24HHisEntry ::=
            SEQUENCE {
                otu0_pathPer24HHisEid
                    PerformanceEventType,
                otu0_pathPer24HHisParaLen
                    INTEGER,
                otu0_pathPer24HHisPara
                    OCTET STRING,
                otu0_pathPer24HHisMonValue
                    OCTET STRING,
                otu0_pathPer24HHisDateTimeStart
                    DateAndTime,
                otu0_pathPer24HHisDateTimeEnd
                    DateAndTime,
                otu0_pathPer24HHisVldty
                    INTEGER,
             }

        -- 1.3.6.1.4.1.2011.2.25.3.40.50.169.40.1.1
        otu0_pathPer24HHisEid OBJECT-TYPE
            SYNTAX PerformanceEventType
            MAX-ACCESS read-only
            STATUS current
            DESCRIPTION
                "perEid."
            ::= { otu0_pathPer24HHisEntry 1 }

        -- 1.3.6.1.4.1.2011.2.25.3.40.50.169.40.1.2
        otu0_pathPer24HHisParaLen OBJECT-TYPE
            SYNTAX INTEGER
            MAX-ACCESS read-only
            STATUS current
            DESCRIPTION
                "perParaLen."
            ::= { otu0_pathPer24HHisEntry 2 }

        -- 1.3.6.1.4.1.2011.2.25.3.40.50.169.40.1.3
        otu0_pathPer24HHisPara OBJECT-TYPE
            SYNTAX OCTET STRING (SIZE (0..100))
            MAX-ACCESS read-only
            STATUS current
            DESCRIPTION
                "perPara."
            ::= { otu0_pathPer24HHisEntry 3 }

        -- 1.3.6.1.4.1.2011.2.25.3.40.50.169.40.1.4
        otu0_pathPer24HHisMonValue OBJECT-TYPE
            SYNTAX OCTET STRING (SIZE (0..100))
            MAX-ACCESS read-only
            STATUS current
            DESCRIPTION
                "perMonValue."
            ::= { otu0_pathPer24HHisEntry 4 }

        -- 1.3.6.1.4.1.2011.2.25.3.40.50.169.40.1.5
        otu0_pathPer24HHisDateTimeStart OBJECT-TYPE
            SYNTAX DateAndTime
            MAX-ACCESS read-only
            STATUS current
            DESCRIPTION
                "perDateTimeStart. "
            ::= { otu0_pathPer24HHisEntry 5 }

        -- 1.3.6.1.4.1.2011.2.25.3.40.50.169.40.1.6
        otu0_pathPer24HHisDateTimeEnd OBJECT-TYPE
            SYNTAX DateAndTime
            MAX-ACCESS read-only
            STATUS current
            DESCRIPTION
                "perDateTimeEnd. "
            ::= { otu0_pathPer24HHisEntry 6 }

        -- 1.3.6.1.4.1.2011.2.25.3.40.50.169.40.1.7
        otu0_pathPer24HHisVldty OBJECT-TYPE
            SYNTAX INTEGER
            MAX-ACCESS read-only
            STATUS current
            DESCRIPTION
                "perVldty. "
            ::= { otu0_pathPer24HHisEntry 7 }


-- Alarm data
      -- 1.3.6.1.4.1.2011.2.25.3.40.50.191
      odu4_tcm1 OBJECT IDENTIFIER ::={ optixGlobalNGWDM 191 }


-- -------------------------------------------------------------------------
-- Perfomance 15-MIN Current Data Table (RTRV-PER-<MOD2>)
-- -------------------------------------------------------------------------
        -- 1.3.6.1.4.1.2011.2.25.3.40.50.191.10
        odu4_tcm1Per15MCurTable OBJECT-TYPE
          SYNTAX SEQUENCE OF Odu4_tcm1Per15MCurEntry
          MAX-ACCESS not-accessible
          STATUS current
          DESCRIPTION
              "odu4_tcm1Per15MCur."
          ::= { odu4_tcm1 10 }

        -- 1.3.6.1.4.1.2011.2.25.3.40.50.191.10.1
        odu4_tcm1Per15MCurEntry OBJECT-TYPE
            SYNTAX Odu4_tcm1Per15MCurEntry
            MAX-ACCESS not-accessible
            STATUS current
            DESCRIPTION
              "odu4_tcm1Per15MCur."
            INDEX { odu4_tcm1Per15MCurEid, odu4_tcm1Per15MCurPara }
            ::= { odu4_tcm1Per15MCurTable 1 }

        Odu4_tcm1Per15MCurEntry ::=
            SEQUENCE {
                odu4_tcm1Per15MCurEid
                    PerformanceEventType,
                odu4_tcm1Per15MCurMonValue
                    OCTET STRING,
                odu4_tcm1Per15MCurVldty
                    INTEGER,
                odu4_tcm1Per15MCurDateTime
                    DateAndTime,
                odu4_tcm1Per15MCurParaLen
                    INTEGER,
                odu4_tcm1Per15MCurPara
                    OCTET STRING
            }

        -- 1.3.6.1.4.1.2011.2.25.3.40.50.191.10.1.1
        odu4_tcm1Per15MCurEid OBJECT-TYPE
            SYNTAX PerformanceEventType
            MAX-ACCESS read-only
            STATUS current
            DESCRIPTION
                "perEid."
            ::= { odu4_tcm1Per15MCurEntry 1 }

        -- 1.3.6.1.4.1.2011.2.25.3.40.50.191.10.1.2
        odu4_tcm1Per15MCurMonValue OBJECT-TYPE
            SYNTAX OCTET STRING (SIZE (0..100))
            MAX-ACCESS read-only
            STATUS current
            DESCRIPTION
                "perMonValue."
            ::= { odu4_tcm1Per15MCurEntry 2 }

        -- 1.3.6.1.4.1.2011.2.25.3.40.50.191.10.1.3
        odu4_tcm1Per15MCurVldty OBJECT-TYPE
            SYNTAX INTEGER
            MAX-ACCESS read-only
            STATUS current
            DESCRIPTION
                "perVldty. "
            ::= { odu4_tcm1Per15MCurEntry 3 }

        -- 1.3.6.1.4.1.2011.2.25.3.40.50.191.10.1.4
        odu4_tcm1Per15MCurDateTime OBJECT-TYPE
            SYNTAX DateAndTime
            MAX-ACCESS read-only
            STATUS current
            DESCRIPTION
                "perDateTime. "
            ::= { odu4_tcm1Per15MCurEntry 4 }

        -- 1.3.6.1.4.1.2011.2.25.3.40.50.191.10.1.5
        odu4_tcm1Per15MCurParaLen OBJECT-TYPE
            SYNTAX INTEGER
            MAX-ACCESS read-only
            STATUS current
            DESCRIPTION
                "perParaLen."
            ::= { odu4_tcm1Per15MCurEntry 5 }

        -- 1.3.6.1.4.1.2011.2.25.3.40.50.191.10.1.6
        odu4_tcm1Per15MCurPara OBJECT-TYPE
            SYNTAX OCTET STRING (SIZE (0..100))
            MAX-ACCESS read-only
            STATUS current
            DESCRIPTION
                "perPara."
            ::= { odu4_tcm1Per15MCurEntry 6 }




-- -------------------------------------------------------------------------
-- Perfomance 15-MIN History Data Table (RTRV-PER-<MOD2>)
-- -------------------------------------------------------------------------
        -- 1.3.6.1.4.1.2011.2.25.3.40.50.191.20
        odu4_tcm1Per15MHisTable OBJECT-TYPE
          SYNTAX SEQUENCE OF Odu4_tcm1Per15MHisEntry
          MAX-ACCESS not-accessible
          STATUS current
          DESCRIPTION
              "odu4_tcm1Per15MHis."
          ::= { odu4_tcm1 20 }

        -- 1.3.6.1.4.1.2011.2.25.3.40.50.191.20.1
        odu4_tcm1Per15MHisEntry OBJECT-TYPE
            SYNTAX Odu4_tcm1Per15MHisEntry
            MAX-ACCESS not-accessible
            STATUS current
            DESCRIPTION
                "odu4_tcm1Per15MHis."
            INDEX {odu4_tcm1Per15MHisEid, odu4_tcm1Per15MHisParaLen, odu4_tcm1Per15MHisPara, odu4_tcm1Per15MHisDateTimeStart, odu4_tcm1Per15MHisDateTimeEnd}
            ::= { odu4_tcm1Per15MHisTable 1 }

        Odu4_tcm1Per15MHisEntry ::=
            SEQUENCE {
                odu4_tcm1Per15MHisEid
                    PerformanceEventType,
                odu4_tcm1Per15MHisParaLen
                    INTEGER,
                odu4_tcm1Per15MHisPara
                    OCTET STRING,
                odu4_tcm1Per15MHisMonValue
                    OCTET STRING,
                odu4_tcm1Per15MHisDateTimeStart
                    DateAndTime,
                odu4_tcm1Per15MHisDateTimeEnd
                    DateAndTime,
                odu4_tcm1Per15MHisVldty
                    INTEGER,
             }

        -- 1.3.6.1.4.1.2011.2.25.3.40.50.191.20.1.1
        odu4_tcm1Per15MHisEid OBJECT-TYPE
            SYNTAX PerformanceEventType
            MAX-ACCESS read-only
            STATUS current
            DESCRIPTION
                "perEid."
            ::= { odu4_tcm1Per15MHisEntry 1 }

        -- 1.3.6.1.4.1.2011.2.25.3.40.50.191.20.1.2
        odu4_tcm1Per15MHisParaLen OBJECT-TYPE
            SYNTAX INTEGER
            MAX-ACCESS read-only
            STATUS current
            DESCRIPTION
                "perParaLen."
            ::= { odu4_tcm1Per15MHisEntry 2 }

        -- 1.3.6.1.4.1.2011.2.25.3.40.50.191.20.1.3
        odu4_tcm1Per15MHisPara OBJECT-TYPE
            SYNTAX OCTET STRING (SIZE (0..100))
            MAX-ACCESS read-only
            STATUS current
            DESCRIPTION
                "perPara."
            ::= { odu4_tcm1Per15MHisEntry 3 }

        -- 1.3.6.1.4.1.2011.2.25.3.40.50.191.20.1.4
        odu4_tcm1Per15MHisMonValue OBJECT-TYPE
            SYNTAX OCTET STRING (SIZE (0..100))
            MAX-ACCESS read-only
            STATUS current
            DESCRIPTION
                "perMonValue."
            ::= { odu4_tcm1Per15MHisEntry 4 }

        -- 1.3.6.1.4.1.2011.2.25.3.40.50.191.20.1.5
        odu4_tcm1Per15MHisDateTimeStart OBJECT-TYPE
            SYNTAX DateAndTime
            MAX-ACCESS read-only
            STATUS current
            DESCRIPTION
                "perDateTimeStart. "
            ::= { odu4_tcm1Per15MHisEntry 5 }

        -- 1.3.6.1.4.1.2011.2.25.3.40.50.191.20.1.6
        odu4_tcm1Per15MHisDateTimeEnd OBJECT-TYPE
            SYNTAX DateAndTime
            MAX-ACCESS read-only
            STATUS current
            DESCRIPTION
                "perDateTimeEnd. "
            ::= { odu4_tcm1Per15MHisEntry 6 }

        -- 1.3.6.1.4.1.2011.2.25.3.40.50.191.20.1.7
        odu4_tcm1Per15MHisVldty OBJECT-TYPE
            SYNTAX INTEGER
            MAX-ACCESS read-only
            STATUS current
            DESCRIPTION
                "perVldty. "
            ::= { odu4_tcm1Per15MHisEntry 7 }




-- -------------------------------------------------------------------------
-- Perfomance 24-HOUR Current Data Table (RTRV-PER-<MOD2>)
-- -------------------------------------------------------------------------
        -- 1.3.6.1.4.1.2011.2.25.3.40.50.191.30
        odu4_tcm1Per24HCurTable OBJECT-TYPE
          SYNTAX SEQUENCE OF Odu4_tcm1Per24HCurEntry
          MAX-ACCESS not-accessible
          STATUS current
          DESCRIPTION
              "odu4_tcm1Per24HCur."
          ::= { odu4_tcm1 30 }

        -- 1.3.6.1.4.1.2011.2.25.3.40.50.191.30.1
        odu4_tcm1Per24HCurEntry OBJECT-TYPE
            SYNTAX Odu4_tcm1Per24HCurEntry
            MAX-ACCESS not-accessible
            STATUS current
            DESCRIPTION
              "odu4_tcm1Per24HCur."
            INDEX { odu4_tcm1Per24HCurEid, odu4_tcm1Per24HCurPara }
            ::= { odu4_tcm1Per24HCurTable 1 }

        Odu4_tcm1Per24HCurEntry ::=
            SEQUENCE {
                odu4_tcm1Per24HCurEid
                    PerformanceEventType,
                odu4_tcm1Per24HCurMonValue
                    OCTET STRING,
                odu4_tcm1Per24HCurVldty
                    INTEGER,
                odu4_tcm1Per24HCurDateTime
                    DateAndTime,
                odu4_tcm1Per24HCurParaLen
                    INTEGER,
                odu4_tcm1Per24HCurPara
                    OCTET STRING
            }

        -- 1.3.6.1.4.1.2011.2.25.3.40.50.191.30.1.1
        odu4_tcm1Per24HCurEid OBJECT-TYPE
            SYNTAX PerformanceEventType
            MAX-ACCESS read-only
            STATUS current
            DESCRIPTION
                "perEid."
            ::= { odu4_tcm1Per24HCurEntry 1 }

        -- 1.3.6.1.4.1.2011.2.25.3.40.50.191.30.1.2
        odu4_tcm1Per24HCurMonValue OBJECT-TYPE
            SYNTAX OCTET STRING (SIZE (0..100))
            MAX-ACCESS read-only
            STATUS current
            DESCRIPTION
                "perMonValue."
            ::= { odu4_tcm1Per24HCurEntry 2 }

        -- 1.3.6.1.4.1.2011.2.25.3.40.50.191.30.1.3
        odu4_tcm1Per24HCurVldty OBJECT-TYPE
            SYNTAX INTEGER
            MAX-ACCESS read-only
            STATUS current
            DESCRIPTION
                "perVldty. "
            ::= { odu4_tcm1Per24HCurEntry 3 }

        -- 1.3.6.1.4.1.2011.2.25.3.40.50.191.30.1.4
        odu4_tcm1Per24HCurDateTime OBJECT-TYPE
            SYNTAX DateAndTime
            MAX-ACCESS read-only
            STATUS current
            DESCRIPTION
                "perDateTime. "
            ::= { odu4_tcm1Per24HCurEntry 4 }

        -- 1.3.6.1.4.1.2011.2.25.3.40.50.191.30.1.5
        odu4_tcm1Per24HCurParaLen OBJECT-TYPE
            SYNTAX INTEGER
            MAX-ACCESS read-only
            STATUS current
            DESCRIPTION
                "perParaLen."
            ::= { odu4_tcm1Per24HCurEntry 5 }

        -- 1.3.6.1.4.1.2011.2.25.3.40.50.191.30.1.6
        odu4_tcm1Per24HCurPara OBJECT-TYPE
            SYNTAX OCTET STRING (SIZE (0..100))
            MAX-ACCESS read-only
            STATUS current
            DESCRIPTION
                "perPara."
            ::= { odu4_tcm1Per24HCurEntry 6 }




-- -------------------------------------------------------------------------
-- Perfomance 24-HOUR History Data Table (RTRV-PER-<MOD2>)
-- -------------------------------------------------------------------------
        -- 1.3.6.1.4.1.2011.2.25.3.40.50.191.40
        odu4_tcm1Per24HHisTable OBJECT-TYPE
          SYNTAX SEQUENCE OF Odu4_tcm1Per24HHisEntry
          MAX-ACCESS not-accessible
          STATUS current
          DESCRIPTION
              "odu4_tcm1Per24HHis."
          ::= { odu4_tcm1 40 }

        -- 1.3.6.1.4.1.2011.2.25.3.40.50.191.40.1
        odu4_tcm1Per24HHisEntry OBJECT-TYPE
            SYNTAX Odu4_tcm1Per24HHisEntry
            MAX-ACCESS not-accessible
            STATUS current
            DESCRIPTION
                "odu4_tcm1Per24HHis."
            INDEX {odu4_tcm1Per24HHisEid, odu4_tcm1Per24HHisParaLen, odu4_tcm1Per24HHisPara, odu4_tcm1Per24HHisDateTimeStart, odu4_tcm1Per24HHisDateTimeEnd}
            ::= { odu4_tcm1Per24HHisTable 1 }

        Odu4_tcm1Per24HHisEntry ::=
            SEQUENCE {
                odu4_tcm1Per24HHisEid
                    PerformanceEventType,
                odu4_tcm1Per24HHisParaLen
                    INTEGER,
                odu4_tcm1Per24HHisPara
                    OCTET STRING,
                odu4_tcm1Per24HHisMonValue
                    OCTET STRING,
                odu4_tcm1Per24HHisDateTimeStart
                    DateAndTime,
                odu4_tcm1Per24HHisDateTimeEnd
                    DateAndTime,
                odu4_tcm1Per24HHisVldty
                    INTEGER,
             }

        -- 1.3.6.1.4.1.2011.2.25.3.40.50.191.40.1.1
        odu4_tcm1Per24HHisEid OBJECT-TYPE
            SYNTAX PerformanceEventType
            MAX-ACCESS read-only
            STATUS current
            DESCRIPTION
                "perEid."
            ::= { odu4_tcm1Per24HHisEntry 1 }

        -- 1.3.6.1.4.1.2011.2.25.3.40.50.191.40.1.2
        odu4_tcm1Per24HHisParaLen OBJECT-TYPE
            SYNTAX INTEGER
            MAX-ACCESS read-only
            STATUS current
            DESCRIPTION
                "perParaLen."
            ::= { odu4_tcm1Per24HHisEntry 2 }

        -- 1.3.6.1.4.1.2011.2.25.3.40.50.191.40.1.3
        odu4_tcm1Per24HHisPara OBJECT-TYPE
            SYNTAX OCTET STRING (SIZE (0..100))
            MAX-ACCESS read-only
            STATUS current
            DESCRIPTION
                "perPara."
            ::= { odu4_tcm1Per24HHisEntry 3 }

        -- 1.3.6.1.4.1.2011.2.25.3.40.50.191.40.1.4
        odu4_tcm1Per24HHisMonValue OBJECT-TYPE
            SYNTAX OCTET STRING (SIZE (0..100))
            MAX-ACCESS read-only
            STATUS current
            DESCRIPTION
                "perMonValue."
            ::= { odu4_tcm1Per24HHisEntry 4 }

        -- 1.3.6.1.4.1.2011.2.25.3.40.50.191.40.1.5
        odu4_tcm1Per24HHisDateTimeStart OBJECT-TYPE
            SYNTAX DateAndTime
            MAX-ACCESS read-only
            STATUS current
            DESCRIPTION
                "perDateTimeStart. "
            ::= { odu4_tcm1Per24HHisEntry 5 }

        -- 1.3.6.1.4.1.2011.2.25.3.40.50.191.40.1.6
        odu4_tcm1Per24HHisDateTimeEnd OBJECT-TYPE
            SYNTAX DateAndTime
            MAX-ACCESS read-only
            STATUS current
            DESCRIPTION
                "perDateTimeEnd. "
            ::= { odu4_tcm1Per24HHisEntry 6 }

        -- 1.3.6.1.4.1.2011.2.25.3.40.50.191.40.1.7
        odu4_tcm1Per24HHisVldty OBJECT-TYPE
            SYNTAX INTEGER
            MAX-ACCESS read-only
            STATUS current
            DESCRIPTION
                "perVldty. "
            ::= { odu4_tcm1Per24HHisEntry 7 }




-- Alarm data
      -- 1.3.6.1.4.1.2011.2.25.3.40.50.192
      odu4_tcm2 OBJECT IDENTIFIER ::={ optixGlobalNGWDM 192 }


-- -------------------------------------------------------------------------
-- Perfomance 15-MIN Current Data Table (RTRV-PER-<MOD2>)
-- -------------------------------------------------------------------------
        -- 1.3.6.1.4.1.2011.2.25.3.40.50.192.10
        odu4_tcm2Per15MCurTable OBJECT-TYPE
          SYNTAX SEQUENCE OF Odu4_tcm2Per15MCurEntry
          MAX-ACCESS not-accessible
          STATUS current
          DESCRIPTION
              "odu4_tcm2Per15MCur."
          ::= { odu4_tcm2 10 }

        -- 1.3.6.1.4.1.2011.2.25.3.40.50.192.10.1
        odu4_tcm2Per15MCurEntry OBJECT-TYPE
            SYNTAX Odu4_tcm2Per15MCurEntry
            MAX-ACCESS not-accessible
            STATUS current
            DESCRIPTION
              "odu4_tcm2Per15MCur."
            INDEX { odu4_tcm2Per15MCurEid, odu4_tcm2Per15MCurPara }
            ::= { odu4_tcm2Per15MCurTable 1 }

        Odu4_tcm2Per15MCurEntry ::=
            SEQUENCE {
                odu4_tcm2Per15MCurEid
                    PerformanceEventType,
                odu4_tcm2Per15MCurMonValue
                    OCTET STRING,
                odu4_tcm2Per15MCurVldty
                    INTEGER,
                odu4_tcm2Per15MCurDateTime
                    DateAndTime,
                odu4_tcm2Per15MCurParaLen
                    INTEGER,
                odu4_tcm2Per15MCurPara
                    OCTET STRING
            }

        -- 1.3.6.1.4.1.2011.2.25.3.40.50.192.10.1.1
        odu4_tcm2Per15MCurEid OBJECT-TYPE
            SYNTAX PerformanceEventType
            MAX-ACCESS read-only
            STATUS current
            DESCRIPTION
                "perEid."
            ::= { odu4_tcm2Per15MCurEntry 1 }

        -- 1.3.6.1.4.1.2011.2.25.3.40.50.192.10.1.2
        odu4_tcm2Per15MCurMonValue OBJECT-TYPE
            SYNTAX OCTET STRING (SIZE (0..100))
            MAX-ACCESS read-only
            STATUS current
            DESCRIPTION
                "perMonValue."
            ::= { odu4_tcm2Per15MCurEntry 2 }

        -- 1.3.6.1.4.1.2011.2.25.3.40.50.192.10.1.3
        odu4_tcm2Per15MCurVldty OBJECT-TYPE
            SYNTAX INTEGER
            MAX-ACCESS read-only
            STATUS current
            DESCRIPTION
                "perVldty. "
            ::= { odu4_tcm2Per15MCurEntry 3 }

        -- 1.3.6.1.4.1.2011.2.25.3.40.50.192.10.1.4
        odu4_tcm2Per15MCurDateTime OBJECT-TYPE
            SYNTAX DateAndTime
            MAX-ACCESS read-only
            STATUS current
            DESCRIPTION
                "perDateTime. "
            ::= { odu4_tcm2Per15MCurEntry 4 }

        -- 1.3.6.1.4.1.2011.2.25.3.40.50.192.10.1.5
        odu4_tcm2Per15MCurParaLen OBJECT-TYPE
            SYNTAX INTEGER
            MAX-ACCESS read-only
            STATUS current
            DESCRIPTION
                "perParaLen."
            ::= { odu4_tcm2Per15MCurEntry 5 }

        -- 1.3.6.1.4.1.2011.2.25.3.40.50.192.10.1.6
        odu4_tcm2Per15MCurPara OBJECT-TYPE
            SYNTAX OCTET STRING (SIZE (0..100))
            MAX-ACCESS read-only
            STATUS current
            DESCRIPTION
                "perPara."
            ::= { odu4_tcm2Per15MCurEntry 6 }




-- -------------------------------------------------------------------------
-- Perfomance 15-MIN History Data Table (RTRV-PER-<MOD2>)
-- -------------------------------------------------------------------------
        -- 1.3.6.1.4.1.2011.2.25.3.40.50.192.20
        odu4_tcm2Per15MHisTable OBJECT-TYPE
          SYNTAX SEQUENCE OF Odu4_tcm2Per15MHisEntry
          MAX-ACCESS not-accessible
          STATUS current
          DESCRIPTION
              "odu4_tcm2Per15MHis."
          ::= { odu4_tcm2 20 }

        -- 1.3.6.1.4.1.2011.2.25.3.40.50.192.20.1
        odu4_tcm2Per15MHisEntry OBJECT-TYPE
            SYNTAX Odu4_tcm2Per15MHisEntry
            MAX-ACCESS not-accessible
            STATUS current
            DESCRIPTION
                "odu4_tcm2Per15MHis."
            INDEX {odu4_tcm2Per15MHisEid, odu4_tcm2Per15MHisParaLen, odu4_tcm2Per15MHisPara, odu4_tcm2Per15MHisDateTimeStart, odu4_tcm2Per15MHisDateTimeEnd}
            ::= { odu4_tcm2Per15MHisTable 1 }

        Odu4_tcm2Per15MHisEntry ::=
            SEQUENCE {
                odu4_tcm2Per15MHisEid
                    PerformanceEventType,
                odu4_tcm2Per15MHisParaLen
                    INTEGER,
                odu4_tcm2Per15MHisPara
                    OCTET STRING,
                odu4_tcm2Per15MHisMonValue
                    OCTET STRING,
                odu4_tcm2Per15MHisDateTimeStart
                    DateAndTime,
                odu4_tcm2Per15MHisDateTimeEnd
                    DateAndTime,
                odu4_tcm2Per15MHisVldty
                    INTEGER,
             }

        -- 1.3.6.1.4.1.2011.2.25.3.40.50.192.20.1.1
        odu4_tcm2Per15MHisEid OBJECT-TYPE
            SYNTAX PerformanceEventType
            MAX-ACCESS read-only
            STATUS current
            DESCRIPTION
                "perEid."
            ::= { odu4_tcm2Per15MHisEntry 1 }

        -- 1.3.6.1.4.1.2011.2.25.3.40.50.192.20.1.2
        odu4_tcm2Per15MHisParaLen OBJECT-TYPE
            SYNTAX INTEGER
            MAX-ACCESS read-only
            STATUS current
            DESCRIPTION
                "perParaLen."
            ::= { odu4_tcm2Per15MHisEntry 2 }

        -- 1.3.6.1.4.1.2011.2.25.3.40.50.192.20.1.3
        odu4_tcm2Per15MHisPara OBJECT-TYPE
            SYNTAX OCTET STRING (SIZE (0..100))
            MAX-ACCESS read-only
            STATUS current
            DESCRIPTION
                "perPara."
            ::= { odu4_tcm2Per15MHisEntry 3 }

        -- 1.3.6.1.4.1.2011.2.25.3.40.50.192.20.1.4
        odu4_tcm2Per15MHisMonValue OBJECT-TYPE
            SYNTAX OCTET STRING (SIZE (0..100))
            MAX-ACCESS read-only
            STATUS current
            DESCRIPTION
                "perMonValue."
            ::= { odu4_tcm2Per15MHisEntry 4 }

        -- 1.3.6.1.4.1.2011.2.25.3.40.50.192.20.1.5
        odu4_tcm2Per15MHisDateTimeStart OBJECT-TYPE
            SYNTAX DateAndTime
            MAX-ACCESS read-only
            STATUS current
            DESCRIPTION
                "perDateTimeStart. "
            ::= { odu4_tcm2Per15MHisEntry 5 }

        -- 1.3.6.1.4.1.2011.2.25.3.40.50.192.20.1.6
        odu4_tcm2Per15MHisDateTimeEnd OBJECT-TYPE
            SYNTAX DateAndTime
            MAX-ACCESS read-only
            STATUS current
            DESCRIPTION
                "perDateTimeEnd. "
            ::= { odu4_tcm2Per15MHisEntry 6 }

        -- 1.3.6.1.4.1.2011.2.25.3.40.50.192.20.1.7
        odu4_tcm2Per15MHisVldty OBJECT-TYPE
            SYNTAX INTEGER
            MAX-ACCESS read-only
            STATUS current
            DESCRIPTION
                "perVldty. "
            ::= { odu4_tcm2Per15MHisEntry 7 }




-- -------------------------------------------------------------------------
-- Perfomance 24-HOUR Current Data Table (RTRV-PER-<MOD2>)
-- -------------------------------------------------------------------------
        -- 1.3.6.1.4.1.2011.2.25.3.40.50.192.30
        odu4_tcm2Per24HCurTable OBJECT-TYPE
          SYNTAX SEQUENCE OF Odu4_tcm2Per24HCurEntry
          MAX-ACCESS not-accessible
          STATUS current
          DESCRIPTION
              "odu4_tcm2Per24HCur."
          ::= { odu4_tcm2 30 }

        -- 1.3.6.1.4.1.2011.2.25.3.40.50.192.30.1
        odu4_tcm2Per24HCurEntry OBJECT-TYPE
            SYNTAX Odu4_tcm2Per24HCurEntry
            MAX-ACCESS not-accessible
            STATUS current
            DESCRIPTION
              "odu4_tcm2Per24HCur."
            INDEX { odu4_tcm2Per24HCurEid, odu4_tcm2Per24HCurPara }
            ::= { odu4_tcm2Per24HCurTable 1 }

        Odu4_tcm2Per24HCurEntry ::=
            SEQUENCE {
                odu4_tcm2Per24HCurEid
                    PerformanceEventType,
                odu4_tcm2Per24HCurMonValue
                    OCTET STRING,
                odu4_tcm2Per24HCurVldty
                    INTEGER,
                odu4_tcm2Per24HCurDateTime
                    DateAndTime,
                odu4_tcm2Per24HCurParaLen
                    INTEGER,
                odu4_tcm2Per24HCurPara
                    OCTET STRING
            }

        -- 1.3.6.1.4.1.2011.2.25.3.40.50.192.30.1.1
        odu4_tcm2Per24HCurEid OBJECT-TYPE
            SYNTAX PerformanceEventType
            MAX-ACCESS read-only
            STATUS current
            DESCRIPTION
                "perEid."
            ::= { odu4_tcm2Per24HCurEntry 1 }

        -- 1.3.6.1.4.1.2011.2.25.3.40.50.192.30.1.2
        odu4_tcm2Per24HCurMonValue OBJECT-TYPE
            SYNTAX OCTET STRING (SIZE (0..100))
            MAX-ACCESS read-only
            STATUS current
            DESCRIPTION
                "perMonValue."
            ::= { odu4_tcm2Per24HCurEntry 2 }

        -- 1.3.6.1.4.1.2011.2.25.3.40.50.192.30.1.3
        odu4_tcm2Per24HCurVldty OBJECT-TYPE
            SYNTAX INTEGER
            MAX-ACCESS read-only
            STATUS current
            DESCRIPTION
                "perVldty. "
            ::= { odu4_tcm2Per24HCurEntry 3 }

        -- 1.3.6.1.4.1.2011.2.25.3.40.50.192.30.1.4
        odu4_tcm2Per24HCurDateTime OBJECT-TYPE
            SYNTAX DateAndTime
            MAX-ACCESS read-only
            STATUS current
            DESCRIPTION
                "perDateTime. "
            ::= { odu4_tcm2Per24HCurEntry 4 }

        -- 1.3.6.1.4.1.2011.2.25.3.40.50.192.30.1.5
        odu4_tcm2Per24HCurParaLen OBJECT-TYPE
            SYNTAX INTEGER
            MAX-ACCESS read-only
            STATUS current
            DESCRIPTION
                "perParaLen."
            ::= { odu4_tcm2Per24HCurEntry 5 }

        -- 1.3.6.1.4.1.2011.2.25.3.40.50.192.30.1.6
        odu4_tcm2Per24HCurPara OBJECT-TYPE
            SYNTAX OCTET STRING (SIZE (0..100))
            MAX-ACCESS read-only
            STATUS current
            DESCRIPTION
                "perPara."
            ::= { odu4_tcm2Per24HCurEntry 6 }




-- -------------------------------------------------------------------------
-- Perfomance 24-HOUR History Data Table (RTRV-PER-<MOD2>)
-- -------------------------------------------------------------------------
        -- 1.3.6.1.4.1.2011.2.25.3.40.50.192.40
        odu4_tcm2Per24HHisTable OBJECT-TYPE
          SYNTAX SEQUENCE OF Odu4_tcm2Per24HHisEntry
          MAX-ACCESS not-accessible
          STATUS current
          DESCRIPTION
              "odu4_tcm2Per24HHis."
          ::= { odu4_tcm2 40 }

        -- 1.3.6.1.4.1.2011.2.25.3.40.50.192.40.1
        odu4_tcm2Per24HHisEntry OBJECT-TYPE
            SYNTAX Odu4_tcm2Per24HHisEntry
            MAX-ACCESS not-accessible
            STATUS current
            DESCRIPTION
                "odu4_tcm2Per24HHis."
            INDEX {odu4_tcm2Per24HHisEid, odu4_tcm2Per24HHisParaLen, odu4_tcm2Per24HHisPara, odu4_tcm2Per24HHisDateTimeStart, odu4_tcm2Per24HHisDateTimeEnd}
            ::= { odu4_tcm2Per24HHisTable 1 }

        Odu4_tcm2Per24HHisEntry ::=
            SEQUENCE {
                odu4_tcm2Per24HHisEid
                    PerformanceEventType,
                odu4_tcm2Per24HHisParaLen
                    INTEGER,
                odu4_tcm2Per24HHisPara
                    OCTET STRING,
                odu4_tcm2Per24HHisMonValue
                    OCTET STRING,
                odu4_tcm2Per24HHisDateTimeStart
                    DateAndTime,
                odu4_tcm2Per24HHisDateTimeEnd
                    DateAndTime,
                odu4_tcm2Per24HHisVldty
                    INTEGER,
             }

        -- 1.3.6.1.4.1.2011.2.25.3.40.50.192.40.1.1
        odu4_tcm2Per24HHisEid OBJECT-TYPE
            SYNTAX PerformanceEventType
            MAX-ACCESS read-only
            STATUS current
            DESCRIPTION
                "perEid."
            ::= { odu4_tcm2Per24HHisEntry 1 }

        -- 1.3.6.1.4.1.2011.2.25.3.40.50.192.40.1.2
        odu4_tcm2Per24HHisParaLen OBJECT-TYPE
            SYNTAX INTEGER
            MAX-ACCESS read-only
            STATUS current
            DESCRIPTION
                "perParaLen."
            ::= { odu4_tcm2Per24HHisEntry 2 }

        -- 1.3.6.1.4.1.2011.2.25.3.40.50.192.40.1.3
        odu4_tcm2Per24HHisPara OBJECT-TYPE
            SYNTAX OCTET STRING (SIZE (0..100))
            MAX-ACCESS read-only
            STATUS current
            DESCRIPTION
                "perPara."
            ::= { odu4_tcm2Per24HHisEntry 3 }

        -- 1.3.6.1.4.1.2011.2.25.3.40.50.192.40.1.4
        odu4_tcm2Per24HHisMonValue OBJECT-TYPE
            SYNTAX OCTET STRING (SIZE (0..100))
            MAX-ACCESS read-only
            STATUS current
            DESCRIPTION
                "perMonValue."
            ::= { odu4_tcm2Per24HHisEntry 4 }

        -- 1.3.6.1.4.1.2011.2.25.3.40.50.192.40.1.5
        odu4_tcm2Per24HHisDateTimeStart OBJECT-TYPE
            SYNTAX DateAndTime
            MAX-ACCESS read-only
            STATUS current
            DESCRIPTION
                "perDateTimeStart. "
            ::= { odu4_tcm2Per24HHisEntry 5 }

        -- 1.3.6.1.4.1.2011.2.25.3.40.50.192.40.1.6
        odu4_tcm2Per24HHisDateTimeEnd OBJECT-TYPE
            SYNTAX DateAndTime
            MAX-ACCESS read-only
            STATUS current
            DESCRIPTION
                "perDateTimeEnd. "
            ::= { odu4_tcm2Per24HHisEntry 6 }

        -- 1.3.6.1.4.1.2011.2.25.3.40.50.192.40.1.7
        odu4_tcm2Per24HHisVldty OBJECT-TYPE
            SYNTAX INTEGER
            MAX-ACCESS read-only
            STATUS current
            DESCRIPTION
                "perVldty. "
            ::= { odu4_tcm2Per24HHisEntry 7 }




-- Alarm data
      -- 1.3.6.1.4.1.2011.2.25.3.40.50.193
      odu4_tcm3 OBJECT IDENTIFIER ::={ optixGlobalNGWDM 193 }


-- -------------------------------------------------------------------------
-- Perfomance 15-MIN Current Data Table (RTRV-PER-<MOD2>)
-- -------------------------------------------------------------------------
        -- 1.3.6.1.4.1.2011.2.25.3.40.50.193.10
        odu4_tcm3Per15MCurTable OBJECT-TYPE
          SYNTAX SEQUENCE OF Odu4_tcm3Per15MCurEntry
          MAX-ACCESS not-accessible
          STATUS current
          DESCRIPTION
              "odu4_tcm3Per15MCur."
          ::= { odu4_tcm3 10 }

        -- 1.3.6.1.4.1.2011.2.25.3.40.50.193.10.1
        odu4_tcm3Per15MCurEntry OBJECT-TYPE
            SYNTAX Odu4_tcm3Per15MCurEntry
            MAX-ACCESS not-accessible
            STATUS current
            DESCRIPTION
              "odu4_tcm3Per15MCur."
            INDEX { odu4_tcm3Per15MCurEid, odu4_tcm3Per15MCurPara }
            ::= { odu4_tcm3Per15MCurTable 1 }

        Odu4_tcm3Per15MCurEntry ::=
            SEQUENCE {
                odu4_tcm3Per15MCurEid
                    PerformanceEventType,
                odu4_tcm3Per15MCurMonValue
                    OCTET STRING,
                odu4_tcm3Per15MCurVldty
                    INTEGER,
                odu4_tcm3Per15MCurDateTime
                    DateAndTime,
                odu4_tcm3Per15MCurParaLen
                    INTEGER,
                odu4_tcm3Per15MCurPara
                    OCTET STRING
            }

        -- 1.3.6.1.4.1.2011.2.25.3.40.50.193.10.1.1
        odu4_tcm3Per15MCurEid OBJECT-TYPE
            SYNTAX PerformanceEventType
            MAX-ACCESS read-only
            STATUS current
            DESCRIPTION
                "perEid."
            ::= { odu4_tcm3Per15MCurEntry 1 }

        -- 1.3.6.1.4.1.2011.2.25.3.40.50.193.10.1.2
        odu4_tcm3Per15MCurMonValue OBJECT-TYPE
            SYNTAX OCTET STRING (SIZE (0..100))
            MAX-ACCESS read-only
            STATUS current
            DESCRIPTION
                "perMonValue."
            ::= { odu4_tcm3Per15MCurEntry 2 }

        -- 1.3.6.1.4.1.2011.2.25.3.40.50.193.10.1.3
        odu4_tcm3Per15MCurVldty OBJECT-TYPE
            SYNTAX INTEGER
            MAX-ACCESS read-only
            STATUS current
            DESCRIPTION
                "perVldty. "
            ::= { odu4_tcm3Per15MCurEntry 3 }

        -- 1.3.6.1.4.1.2011.2.25.3.40.50.193.10.1.4
        odu4_tcm3Per15MCurDateTime OBJECT-TYPE
            SYNTAX DateAndTime
            MAX-ACCESS read-only
            STATUS current
            DESCRIPTION
                "perDateTime. "
            ::= { odu4_tcm3Per15MCurEntry 4 }

        -- 1.3.6.1.4.1.2011.2.25.3.40.50.193.10.1.5
        odu4_tcm3Per15MCurParaLen OBJECT-TYPE
            SYNTAX INTEGER
            MAX-ACCESS read-only
            STATUS current
            DESCRIPTION
                "perParaLen."
            ::= { odu4_tcm3Per15MCurEntry 5 }

        -- 1.3.6.1.4.1.2011.2.25.3.40.50.193.10.1.6
        odu4_tcm3Per15MCurPara OBJECT-TYPE
            SYNTAX OCTET STRING (SIZE (0..100))
            MAX-ACCESS read-only
            STATUS current
            DESCRIPTION
                "perPara."
            ::= { odu4_tcm3Per15MCurEntry 6 }




-- -------------------------------------------------------------------------
-- Perfomance 15-MIN History Data Table (RTRV-PER-<MOD2>)
-- -------------------------------------------------------------------------
        -- 1.3.6.1.4.1.2011.2.25.3.40.50.193.20
        odu4_tcm3Per15MHisTable OBJECT-TYPE
          SYNTAX SEQUENCE OF Odu4_tcm3Per15MHisEntry
          MAX-ACCESS not-accessible
          STATUS current
          DESCRIPTION
              "odu4_tcm3Per15MHis."
          ::= { odu4_tcm3 20 }

        -- 1.3.6.1.4.1.2011.2.25.3.40.50.193.20.1
        odu4_tcm3Per15MHisEntry OBJECT-TYPE
            SYNTAX Odu4_tcm3Per15MHisEntry
            MAX-ACCESS not-accessible
            STATUS current
            DESCRIPTION
                "odu4_tcm3Per15MHis."
            INDEX {odu4_tcm3Per15MHisEid, odu4_tcm3Per15MHisParaLen, odu4_tcm3Per15MHisPara, odu4_tcm3Per15MHisDateTimeStart, odu4_tcm3Per15MHisDateTimeEnd}
            ::= { odu4_tcm3Per15MHisTable 1 }

        Odu4_tcm3Per15MHisEntry ::=
            SEQUENCE {
                odu4_tcm3Per15MHisEid
                    PerformanceEventType,
                odu4_tcm3Per15MHisParaLen
                    INTEGER,
                odu4_tcm3Per15MHisPara
                    OCTET STRING,
                odu4_tcm3Per15MHisMonValue
                    OCTET STRING,
                odu4_tcm3Per15MHisDateTimeStart
                    DateAndTime,
                odu4_tcm3Per15MHisDateTimeEnd
                    DateAndTime,
                odu4_tcm3Per15MHisVldty
                    INTEGER,
             }

        -- 1.3.6.1.4.1.2011.2.25.3.40.50.193.20.1.1
        odu4_tcm3Per15MHisEid OBJECT-TYPE
            SYNTAX PerformanceEventType
            MAX-ACCESS read-only
            STATUS current
            DESCRIPTION
                "perEid."
            ::= { odu4_tcm3Per15MHisEntry 1 }

        -- 1.3.6.1.4.1.2011.2.25.3.40.50.193.20.1.2
        odu4_tcm3Per15MHisParaLen OBJECT-TYPE
            SYNTAX INTEGER
            MAX-ACCESS read-only
            STATUS current
            DESCRIPTION
                "perParaLen."
            ::= { odu4_tcm3Per15MHisEntry 2 }

        -- 1.3.6.1.4.1.2011.2.25.3.40.50.193.20.1.3
        odu4_tcm3Per15MHisPara OBJECT-TYPE
            SYNTAX OCTET STRING (SIZE (0..100))
            MAX-ACCESS read-only
            STATUS current
            DESCRIPTION
                "perPara."
            ::= { odu4_tcm3Per15MHisEntry 3 }

        -- 1.3.6.1.4.1.2011.2.25.3.40.50.193.20.1.4
        odu4_tcm3Per15MHisMonValue OBJECT-TYPE
            SYNTAX OCTET STRING (SIZE (0..100))
            MAX-ACCESS read-only
            STATUS current
            DESCRIPTION
                "perMonValue."
            ::= { odu4_tcm3Per15MHisEntry 4 }

        -- 1.3.6.1.4.1.2011.2.25.3.40.50.193.20.1.5
        odu4_tcm3Per15MHisDateTimeStart OBJECT-TYPE
            SYNTAX DateAndTime
            MAX-ACCESS read-only
            STATUS current
            DESCRIPTION
                "perDateTimeStart. "
            ::= { odu4_tcm3Per15MHisEntry 5 }

        -- 1.3.6.1.4.1.2011.2.25.3.40.50.193.20.1.6
        odu4_tcm3Per15MHisDateTimeEnd OBJECT-TYPE
            SYNTAX DateAndTime
            MAX-ACCESS read-only
            STATUS current
            DESCRIPTION
                "perDateTimeEnd. "
            ::= { odu4_tcm3Per15MHisEntry 6 }

        -- 1.3.6.1.4.1.2011.2.25.3.40.50.193.20.1.7
        odu4_tcm3Per15MHisVldty OBJECT-TYPE
            SYNTAX INTEGER
            MAX-ACCESS read-only
            STATUS current
            DESCRIPTION
                "perVldty. "
            ::= { odu4_tcm3Per15MHisEntry 7 }




-- -------------------------------------------------------------------------
-- Perfomance 24-HOUR Current Data Table (RTRV-PER-<MOD2>)
-- -------------------------------------------------------------------------
        -- 1.3.6.1.4.1.2011.2.25.3.40.50.193.30
        odu4_tcm3Per24HCurTable OBJECT-TYPE
          SYNTAX SEQUENCE OF Odu4_tcm3Per24HCurEntry
          MAX-ACCESS not-accessible
          STATUS current
          DESCRIPTION
              "odu4_tcm3Per24HCur."
          ::= { odu4_tcm3 30 }

        -- 1.3.6.1.4.1.2011.2.25.3.40.50.193.30.1
        odu4_tcm3Per24HCurEntry OBJECT-TYPE
            SYNTAX Odu4_tcm3Per24HCurEntry
            MAX-ACCESS not-accessible
            STATUS current
            DESCRIPTION
              "odu4_tcm3Per24HCur."
            INDEX { odu4_tcm3Per24HCurEid, odu4_tcm3Per24HCurPara }
            ::= { odu4_tcm3Per24HCurTable 1 }

        Odu4_tcm3Per24HCurEntry ::=
            SEQUENCE {
                odu4_tcm3Per24HCurEid
                    PerformanceEventType,
                odu4_tcm3Per24HCurMonValue
                    OCTET STRING,
                odu4_tcm3Per24HCurVldty
                    INTEGER,
                odu4_tcm3Per24HCurDateTime
                    DateAndTime,
                odu4_tcm3Per24HCurParaLen
                    INTEGER,
                odu4_tcm3Per24HCurPara
                    OCTET STRING
            }

        -- 1.3.6.1.4.1.2011.2.25.3.40.50.193.30.1.1
        odu4_tcm3Per24HCurEid OBJECT-TYPE
            SYNTAX PerformanceEventType
            MAX-ACCESS read-only
            STATUS current
            DESCRIPTION
                "perEid."
            ::= { odu4_tcm3Per24HCurEntry 1 }

        -- 1.3.6.1.4.1.2011.2.25.3.40.50.193.30.1.2
        odu4_tcm3Per24HCurMonValue OBJECT-TYPE
            SYNTAX OCTET STRING (SIZE (0..100))
            MAX-ACCESS read-only
            STATUS current
            DESCRIPTION
                "perMonValue."
            ::= { odu4_tcm3Per24HCurEntry 2 }

        -- 1.3.6.1.4.1.2011.2.25.3.40.50.193.30.1.3
        odu4_tcm3Per24HCurVldty OBJECT-TYPE
            SYNTAX INTEGER
            MAX-ACCESS read-only
            STATUS current
            DESCRIPTION
                "perVldty. "
            ::= { odu4_tcm3Per24HCurEntry 3 }

        -- 1.3.6.1.4.1.2011.2.25.3.40.50.193.30.1.4
        odu4_tcm3Per24HCurDateTime OBJECT-TYPE
            SYNTAX DateAndTime
            MAX-ACCESS read-only
            STATUS current
            DESCRIPTION
                "perDateTime. "
            ::= { odu4_tcm3Per24HCurEntry 4 }

        -- 1.3.6.1.4.1.2011.2.25.3.40.50.193.30.1.5
        odu4_tcm3Per24HCurParaLen OBJECT-TYPE
            SYNTAX INTEGER
            MAX-ACCESS read-only
            STATUS current
            DESCRIPTION
                "perParaLen."
            ::= { odu4_tcm3Per24HCurEntry 5 }

        -- 1.3.6.1.4.1.2011.2.25.3.40.50.193.30.1.6
        odu4_tcm3Per24HCurPara OBJECT-TYPE
            SYNTAX OCTET STRING (SIZE (0..100))
            MAX-ACCESS read-only
            STATUS current
            DESCRIPTION
                "perPara."
            ::= { odu4_tcm3Per24HCurEntry 6 }




-- -------------------------------------------------------------------------
-- Perfomance 24-HOUR History Data Table (RTRV-PER-<MOD2>)
-- -------------------------------------------------------------------------
        -- 1.3.6.1.4.1.2011.2.25.3.40.50.193.40
        odu4_tcm3Per24HHisTable OBJECT-TYPE
          SYNTAX SEQUENCE OF Odu4_tcm3Per24HHisEntry
          MAX-ACCESS not-accessible
          STATUS current
          DESCRIPTION
              "odu4_tcm3Per24HHis."
          ::= { odu4_tcm3 40 }

        -- 1.3.6.1.4.1.2011.2.25.3.40.50.193.40.1
        odu4_tcm3Per24HHisEntry OBJECT-TYPE
            SYNTAX Odu4_tcm3Per24HHisEntry
            MAX-ACCESS not-accessible
            STATUS current
            DESCRIPTION
                "odu4_tcm3Per24HHis."
            INDEX {odu4_tcm3Per24HHisEid, odu4_tcm3Per24HHisParaLen, odu4_tcm3Per24HHisPara, odu4_tcm3Per24HHisDateTimeStart, odu4_tcm3Per24HHisDateTimeEnd}
            ::= { odu4_tcm3Per24HHisTable 1 }

        Odu4_tcm3Per24HHisEntry ::=
            SEQUENCE {
                odu4_tcm3Per24HHisEid
                    PerformanceEventType,
                odu4_tcm3Per24HHisParaLen
                    INTEGER,
                odu4_tcm3Per24HHisPara
                    OCTET STRING,
                odu4_tcm3Per24HHisMonValue
                    OCTET STRING,
                odu4_tcm3Per24HHisDateTimeStart
                    DateAndTime,
                odu4_tcm3Per24HHisDateTimeEnd
                    DateAndTime,
                odu4_tcm3Per24HHisVldty
                    INTEGER,
             }

        -- 1.3.6.1.4.1.2011.2.25.3.40.50.193.40.1.1
        odu4_tcm3Per24HHisEid OBJECT-TYPE
            SYNTAX PerformanceEventType
            MAX-ACCESS read-only
            STATUS current
            DESCRIPTION
                "perEid."
            ::= { odu4_tcm3Per24HHisEntry 1 }

        -- 1.3.6.1.4.1.2011.2.25.3.40.50.193.40.1.2
        odu4_tcm3Per24HHisParaLen OBJECT-TYPE
            SYNTAX INTEGER
            MAX-ACCESS read-only
            STATUS current
            DESCRIPTION
                "perParaLen."
            ::= { odu4_tcm3Per24HHisEntry 2 }

        -- 1.3.6.1.4.1.2011.2.25.3.40.50.193.40.1.3
        odu4_tcm3Per24HHisPara OBJECT-TYPE
            SYNTAX OCTET STRING (SIZE (0..100))
            MAX-ACCESS read-only
            STATUS current
            DESCRIPTION
                "perPara."
            ::= { odu4_tcm3Per24HHisEntry 3 }

        -- 1.3.6.1.4.1.2011.2.25.3.40.50.193.40.1.4
        odu4_tcm3Per24HHisMonValue OBJECT-TYPE
            SYNTAX OCTET STRING (SIZE (0..100))
            MAX-ACCESS read-only
            STATUS current
            DESCRIPTION
                "perMonValue."
            ::= { odu4_tcm3Per24HHisEntry 4 }

        -- 1.3.6.1.4.1.2011.2.25.3.40.50.193.40.1.5
        odu4_tcm3Per24HHisDateTimeStart OBJECT-TYPE
            SYNTAX DateAndTime
            MAX-ACCESS read-only
            STATUS current
            DESCRIPTION
                "perDateTimeStart. "
            ::= { odu4_tcm3Per24HHisEntry 5 }

        -- 1.3.6.1.4.1.2011.2.25.3.40.50.193.40.1.6
        odu4_tcm3Per24HHisDateTimeEnd OBJECT-TYPE
            SYNTAX DateAndTime
            MAX-ACCESS read-only
            STATUS current
            DESCRIPTION
                "perDateTimeEnd. "
            ::= { odu4_tcm3Per24HHisEntry 6 }

        -- 1.3.6.1.4.1.2011.2.25.3.40.50.193.40.1.7
        odu4_tcm3Per24HHisVldty OBJECT-TYPE
            SYNTAX INTEGER
            MAX-ACCESS read-only
            STATUS current
            DESCRIPTION
                "perVldty. "
            ::= { odu4_tcm3Per24HHisEntry 7 }




-- Alarm data
      -- 1.3.6.1.4.1.2011.2.25.3.40.50.194
      odu4_tcm4 OBJECT IDENTIFIER ::={ optixGlobalNGWDM 194 }


-- -------------------------------------------------------------------------
-- Perfomance 15-MIN Current Data Table (RTRV-PER-<MOD2>)
-- -------------------------------------------------------------------------
        -- 1.3.6.1.4.1.2011.2.25.3.40.50.194.10
        odu4_tcm4Per15MCurTable OBJECT-TYPE
          SYNTAX SEQUENCE OF Odu4_tcm4Per15MCurEntry
          MAX-ACCESS not-accessible
          STATUS current
          DESCRIPTION
              "odu4_tcm4Per15MCur."
          ::= { odu4_tcm4 10 }

        -- 1.3.6.1.4.1.2011.2.25.3.40.50.194.10.1
        odu4_tcm4Per15MCurEntry OBJECT-TYPE
            SYNTAX Odu4_tcm4Per15MCurEntry
            MAX-ACCESS not-accessible
            STATUS current
            DESCRIPTION
              "odu4_tcm4Per15MCur."
            INDEX { odu4_tcm4Per15MCurEid, odu4_tcm4Per15MCurPara }
            ::= { odu4_tcm4Per15MCurTable 1 }

        Odu4_tcm4Per15MCurEntry ::=
            SEQUENCE {
                odu4_tcm4Per15MCurEid
                    PerformanceEventType,
                odu4_tcm4Per15MCurMonValue
                    OCTET STRING,
                odu4_tcm4Per15MCurVldty
                    INTEGER,
                odu4_tcm4Per15MCurDateTime
                    DateAndTime,
                odu4_tcm4Per15MCurParaLen
                    INTEGER,
                odu4_tcm4Per15MCurPara
                    OCTET STRING
            }

        -- 1.3.6.1.4.1.2011.2.25.3.40.50.194.10.1.1
        odu4_tcm4Per15MCurEid OBJECT-TYPE
            SYNTAX PerformanceEventType
            MAX-ACCESS read-only
            STATUS current
            DESCRIPTION
                "perEid."
            ::= { odu4_tcm4Per15MCurEntry 1 }

        -- 1.3.6.1.4.1.2011.2.25.3.40.50.194.10.1.2
        odu4_tcm4Per15MCurMonValue OBJECT-TYPE
            SYNTAX OCTET STRING (SIZE (0..100))
            MAX-ACCESS read-only
            STATUS current
            DESCRIPTION
                "perMonValue."
            ::= { odu4_tcm4Per15MCurEntry 2 }

        -- 1.3.6.1.4.1.2011.2.25.3.40.50.194.10.1.3
        odu4_tcm4Per15MCurVldty OBJECT-TYPE
            SYNTAX INTEGER
            MAX-ACCESS read-only
            STATUS current
            DESCRIPTION
                "perVldty. "
            ::= { odu4_tcm4Per15MCurEntry 3 }

        -- 1.3.6.1.4.1.2011.2.25.3.40.50.194.10.1.4
        odu4_tcm4Per15MCurDateTime OBJECT-TYPE
            SYNTAX DateAndTime
            MAX-ACCESS read-only
            STATUS current
            DESCRIPTION
                "perDateTime. "
            ::= { odu4_tcm4Per15MCurEntry 4 }

        -- 1.3.6.1.4.1.2011.2.25.3.40.50.194.10.1.5
        odu4_tcm4Per15MCurParaLen OBJECT-TYPE
            SYNTAX INTEGER
            MAX-ACCESS read-only
            STATUS current
            DESCRIPTION
                "perParaLen."
            ::= { odu4_tcm4Per15MCurEntry 5 }

        -- 1.3.6.1.4.1.2011.2.25.3.40.50.194.10.1.6
        odu4_tcm4Per15MCurPara OBJECT-TYPE
            SYNTAX OCTET STRING (SIZE (0..100))
            MAX-ACCESS read-only
            STATUS current
            DESCRIPTION
                "perPara."
            ::= { odu4_tcm4Per15MCurEntry 6 }




-- -------------------------------------------------------------------------
-- Perfomance 15-MIN History Data Table (RTRV-PER-<MOD2>)
-- -------------------------------------------------------------------------
        -- 1.3.6.1.4.1.2011.2.25.3.40.50.194.20
        odu4_tcm4Per15MHisTable OBJECT-TYPE
          SYNTAX SEQUENCE OF Odu4_tcm4Per15MHisEntry
          MAX-ACCESS not-accessible
          STATUS current
          DESCRIPTION
              "odu4_tcm4Per15MHis."
          ::= { odu4_tcm4 20 }

        -- 1.3.6.1.4.1.2011.2.25.3.40.50.194.20.1
        odu4_tcm4Per15MHisEntry OBJECT-TYPE
            SYNTAX Odu4_tcm4Per15MHisEntry
            MAX-ACCESS not-accessible
            STATUS current
            DESCRIPTION
                "odu4_tcm4Per15MHis."
            INDEX {odu4_tcm4Per15MHisEid, odu4_tcm4Per15MHisParaLen, odu4_tcm4Per15MHisPara, odu4_tcm4Per15MHisDateTimeStart, odu4_tcm4Per15MHisDateTimeEnd}
            ::= { odu4_tcm4Per15MHisTable 1 }

        Odu4_tcm4Per15MHisEntry ::=
            SEQUENCE {
                odu4_tcm4Per15MHisEid
                    PerformanceEventType,
                odu4_tcm4Per15MHisParaLen
                    INTEGER,
                odu4_tcm4Per15MHisPara
                    OCTET STRING,
                odu4_tcm4Per15MHisMonValue
                    OCTET STRING,
                odu4_tcm4Per15MHisDateTimeStart
                    DateAndTime,
                odu4_tcm4Per15MHisDateTimeEnd
                    DateAndTime,
                odu4_tcm4Per15MHisVldty
                    INTEGER,
             }

        -- 1.3.6.1.4.1.2011.2.25.3.40.50.194.20.1.1
        odu4_tcm4Per15MHisEid OBJECT-TYPE
            SYNTAX PerformanceEventType
            MAX-ACCESS read-only
            STATUS current
            DESCRIPTION
                "perEid."
            ::= { odu4_tcm4Per15MHisEntry 1 }

        -- 1.3.6.1.4.1.2011.2.25.3.40.50.194.20.1.2
        odu4_tcm4Per15MHisParaLen OBJECT-TYPE
            SYNTAX INTEGER
            MAX-ACCESS read-only
            STATUS current
            DESCRIPTION
                "perParaLen."
            ::= { odu4_tcm4Per15MHisEntry 2 }

        -- 1.3.6.1.4.1.2011.2.25.3.40.50.194.20.1.3
        odu4_tcm4Per15MHisPara OBJECT-TYPE
            SYNTAX OCTET STRING (SIZE (0..100))
            MAX-ACCESS read-only
            STATUS current
            DESCRIPTION
                "perPara."
            ::= { odu4_tcm4Per15MHisEntry 3 }

        -- 1.3.6.1.4.1.2011.2.25.3.40.50.194.20.1.4
        odu4_tcm4Per15MHisMonValue OBJECT-TYPE
            SYNTAX OCTET STRING (SIZE (0..100))
            MAX-ACCESS read-only
            STATUS current
            DESCRIPTION
                "perMonValue."
            ::= { odu4_tcm4Per15MHisEntry 4 }

        -- 1.3.6.1.4.1.2011.2.25.3.40.50.194.20.1.5
        odu4_tcm4Per15MHisDateTimeStart OBJECT-TYPE
            SYNTAX DateAndTime
            MAX-ACCESS read-only
            STATUS current
            DESCRIPTION
                "perDateTimeStart. "
            ::= { odu4_tcm4Per15MHisEntry 5 }

        -- 1.3.6.1.4.1.2011.2.25.3.40.50.194.20.1.6
        odu4_tcm4Per15MHisDateTimeEnd OBJECT-TYPE
            SYNTAX DateAndTime
            MAX-ACCESS read-only
            STATUS current
            DESCRIPTION
                "perDateTimeEnd. "
            ::= { odu4_tcm4Per15MHisEntry 6 }

        -- 1.3.6.1.4.1.2011.2.25.3.40.50.194.20.1.7
        odu4_tcm4Per15MHisVldty OBJECT-TYPE
            SYNTAX INTEGER
            MAX-ACCESS read-only
            STATUS current
            DESCRIPTION
                "perVldty. "
            ::= { odu4_tcm4Per15MHisEntry 7 }




-- -------------------------------------------------------------------------
-- Perfomance 24-HOUR Current Data Table (RTRV-PER-<MOD2>)
-- -------------------------------------------------------------------------
        -- 1.3.6.1.4.1.2011.2.25.3.40.50.194.30
        odu4_tcm4Per24HCurTable OBJECT-TYPE
          SYNTAX SEQUENCE OF Odu4_tcm4Per24HCurEntry
          MAX-ACCESS not-accessible
          STATUS current
          DESCRIPTION
              "odu4_tcm4Per24HCur."
          ::= { odu4_tcm4 30 }

        -- 1.3.6.1.4.1.2011.2.25.3.40.50.194.30.1
        odu4_tcm4Per24HCurEntry OBJECT-TYPE
            SYNTAX Odu4_tcm4Per24HCurEntry
            MAX-ACCESS not-accessible
            STATUS current
            DESCRIPTION
              "odu4_tcm4Per24HCur."
            INDEX { odu4_tcm4Per24HCurEid, odu4_tcm4Per24HCurPara }
            ::= { odu4_tcm4Per24HCurTable 1 }

        Odu4_tcm4Per24HCurEntry ::=
            SEQUENCE {
                odu4_tcm4Per24HCurEid
                    PerformanceEventType,
                odu4_tcm4Per24HCurMonValue
                    OCTET STRING,
                odu4_tcm4Per24HCurVldty
                    INTEGER,
                odu4_tcm4Per24HCurDateTime
                    DateAndTime,
                odu4_tcm4Per24HCurParaLen
                    INTEGER,
                odu4_tcm4Per24HCurPara
                    OCTET STRING
            }

        -- 1.3.6.1.4.1.2011.2.25.3.40.50.194.30.1.1
        odu4_tcm4Per24HCurEid OBJECT-TYPE
            SYNTAX PerformanceEventType
            MAX-ACCESS read-only
            STATUS current
            DESCRIPTION
                "perEid."
            ::= { odu4_tcm4Per24HCurEntry 1 }

        -- 1.3.6.1.4.1.2011.2.25.3.40.50.194.30.1.2
        odu4_tcm4Per24HCurMonValue OBJECT-TYPE
            SYNTAX OCTET STRING (SIZE (0..100))
            MAX-ACCESS read-only
            STATUS current
            DESCRIPTION
                "perMonValue."
            ::= { odu4_tcm4Per24HCurEntry 2 }

        -- 1.3.6.1.4.1.2011.2.25.3.40.50.194.30.1.3
        odu4_tcm4Per24HCurVldty OBJECT-TYPE
            SYNTAX INTEGER
            MAX-ACCESS read-only
            STATUS current
            DESCRIPTION
                "perVldty. "
            ::= { odu4_tcm4Per24HCurEntry 3 }

        -- 1.3.6.1.4.1.2011.2.25.3.40.50.194.30.1.4
        odu4_tcm4Per24HCurDateTime OBJECT-TYPE
            SYNTAX DateAndTime
            MAX-ACCESS read-only
            STATUS current
            DESCRIPTION
                "perDateTime. "
            ::= { odu4_tcm4Per24HCurEntry 4 }

        -- 1.3.6.1.4.1.2011.2.25.3.40.50.194.30.1.5
        odu4_tcm4Per24HCurParaLen OBJECT-TYPE
            SYNTAX INTEGER
            MAX-ACCESS read-only
            STATUS current
            DESCRIPTION
                "perParaLen."
            ::= { odu4_tcm4Per24HCurEntry 5 }

        -- 1.3.6.1.4.1.2011.2.25.3.40.50.194.30.1.6
        odu4_tcm4Per24HCurPara OBJECT-TYPE
            SYNTAX OCTET STRING (SIZE (0..100))
            MAX-ACCESS read-only
            STATUS current
            DESCRIPTION
                "perPara."
            ::= { odu4_tcm4Per24HCurEntry 6 }




-- -------------------------------------------------------------------------
-- Perfomance 24-HOUR History Data Table (RTRV-PER-<MOD2>)
-- -------------------------------------------------------------------------
        -- 1.3.6.1.4.1.2011.2.25.3.40.50.194.40
        odu4_tcm4Per24HHisTable OBJECT-TYPE
          SYNTAX SEQUENCE OF Odu4_tcm4Per24HHisEntry
          MAX-ACCESS not-accessible
          STATUS current
          DESCRIPTION
              "odu4_tcm4Per24HHis."
          ::= { odu4_tcm4 40 }

        -- 1.3.6.1.4.1.2011.2.25.3.40.50.194.40.1
        odu4_tcm4Per24HHisEntry OBJECT-TYPE
            SYNTAX Odu4_tcm4Per24HHisEntry
            MAX-ACCESS not-accessible
            STATUS current
            DESCRIPTION
                "odu4_tcm4Per24HHis."
            INDEX {odu4_tcm4Per24HHisEid, odu4_tcm4Per24HHisParaLen, odu4_tcm4Per24HHisPara, odu4_tcm4Per24HHisDateTimeStart, odu4_tcm4Per24HHisDateTimeEnd}
            ::= { odu4_tcm4Per24HHisTable 1 }

        Odu4_tcm4Per24HHisEntry ::=
            SEQUENCE {
                odu4_tcm4Per24HHisEid
                    PerformanceEventType,
                odu4_tcm4Per24HHisParaLen
                    INTEGER,
                odu4_tcm4Per24HHisPara
                    OCTET STRING,
                odu4_tcm4Per24HHisMonValue
                    OCTET STRING,
                odu4_tcm4Per24HHisDateTimeStart
                    DateAndTime,
                odu4_tcm4Per24HHisDateTimeEnd
                    DateAndTime,
                odu4_tcm4Per24HHisVldty
                    INTEGER,
             }

        -- 1.3.6.1.4.1.2011.2.25.3.40.50.194.40.1.1
        odu4_tcm4Per24HHisEid OBJECT-TYPE
            SYNTAX PerformanceEventType
            MAX-ACCESS read-only
            STATUS current
            DESCRIPTION
                "perEid."
            ::= { odu4_tcm4Per24HHisEntry 1 }

        -- 1.3.6.1.4.1.2011.2.25.3.40.50.194.40.1.2
        odu4_tcm4Per24HHisParaLen OBJECT-TYPE
            SYNTAX INTEGER
            MAX-ACCESS read-only
            STATUS current
            DESCRIPTION
                "perParaLen."
            ::= { odu4_tcm4Per24HHisEntry 2 }

        -- 1.3.6.1.4.1.2011.2.25.3.40.50.194.40.1.3
        odu4_tcm4Per24HHisPara OBJECT-TYPE
            SYNTAX OCTET STRING (SIZE (0..100))
            MAX-ACCESS read-only
            STATUS current
            DESCRIPTION
                "perPara."
            ::= { odu4_tcm4Per24HHisEntry 3 }

        -- 1.3.6.1.4.1.2011.2.25.3.40.50.194.40.1.4
        odu4_tcm4Per24HHisMonValue OBJECT-TYPE
            SYNTAX OCTET STRING (SIZE (0..100))
            MAX-ACCESS read-only
            STATUS current
            DESCRIPTION
                "perMonValue."
            ::= { odu4_tcm4Per24HHisEntry 4 }

        -- 1.3.6.1.4.1.2011.2.25.3.40.50.194.40.1.5
        odu4_tcm4Per24HHisDateTimeStart OBJECT-TYPE
            SYNTAX DateAndTime
            MAX-ACCESS read-only
            STATUS current
            DESCRIPTION
                "perDateTimeStart. "
            ::= { odu4_tcm4Per24HHisEntry 5 }

        -- 1.3.6.1.4.1.2011.2.25.3.40.50.194.40.1.6
        odu4_tcm4Per24HHisDateTimeEnd OBJECT-TYPE
            SYNTAX DateAndTime
            MAX-ACCESS read-only
            STATUS current
            DESCRIPTION
                "perDateTimeEnd. "
            ::= { odu4_tcm4Per24HHisEntry 6 }

        -- 1.3.6.1.4.1.2011.2.25.3.40.50.194.40.1.7
        odu4_tcm4Per24HHisVldty OBJECT-TYPE
            SYNTAX INTEGER
            MAX-ACCESS read-only
            STATUS current
            DESCRIPTION
                "perVldty. "
            ::= { odu4_tcm4Per24HHisEntry 7 }




-- Alarm data
      -- 1.3.6.1.4.1.2011.2.25.3.40.50.195
      odu4_tcm5 OBJECT IDENTIFIER ::={ optixGlobalNGWDM 195 }


-- -------------------------------------------------------------------------
-- Perfomance 15-MIN Current Data Table (RTRV-PER-<MOD2>)
-- -------------------------------------------------------------------------
        -- 1.3.6.1.4.1.2011.2.25.3.40.50.195.10
        odu4_tcm5Per15MCurTable OBJECT-TYPE
          SYNTAX SEQUENCE OF Odu4_tcm5Per15MCurEntry
          MAX-ACCESS not-accessible
          STATUS current
          DESCRIPTION
              "odu4_tcm5Per15MCur."
          ::= { odu4_tcm5 10 }

        -- 1.3.6.1.4.1.2011.2.25.3.40.50.195.10.1
        odu4_tcm5Per15MCurEntry OBJECT-TYPE
            SYNTAX Odu4_tcm5Per15MCurEntry
            MAX-ACCESS not-accessible
            STATUS current
            DESCRIPTION
              "odu4_tcm5Per15MCur."
            INDEX { odu4_tcm5Per15MCurEid, odu4_tcm5Per15MCurPara }
            ::= { odu4_tcm5Per15MCurTable 1 }

        Odu4_tcm5Per15MCurEntry ::=
            SEQUENCE {
                odu4_tcm5Per15MCurEid
                    PerformanceEventType,
                odu4_tcm5Per15MCurMonValue
                    OCTET STRING,
                odu4_tcm5Per15MCurVldty
                    INTEGER,
                odu4_tcm5Per15MCurDateTime
                    DateAndTime,
                odu4_tcm5Per15MCurParaLen
                    INTEGER,
                odu4_tcm5Per15MCurPara
                    OCTET STRING
            }

        -- 1.3.6.1.4.1.2011.2.25.3.40.50.195.10.1.1
        odu4_tcm5Per15MCurEid OBJECT-TYPE
            SYNTAX PerformanceEventType
            MAX-ACCESS read-only
            STATUS current
            DESCRIPTION
                "perEid."
            ::= { odu4_tcm5Per15MCurEntry 1 }

        -- 1.3.6.1.4.1.2011.2.25.3.40.50.195.10.1.2
        odu4_tcm5Per15MCurMonValue OBJECT-TYPE
            SYNTAX OCTET STRING (SIZE (0..100))
            MAX-ACCESS read-only
            STATUS current
            DESCRIPTION
                "perMonValue."
            ::= { odu4_tcm5Per15MCurEntry 2 }

        -- 1.3.6.1.4.1.2011.2.25.3.40.50.195.10.1.3
        odu4_tcm5Per15MCurVldty OBJECT-TYPE
            SYNTAX INTEGER
            MAX-ACCESS read-only
            STATUS current
            DESCRIPTION
                "perVldty. "
            ::= { odu4_tcm5Per15MCurEntry 3 }

        -- 1.3.6.1.4.1.2011.2.25.3.40.50.195.10.1.4
        odu4_tcm5Per15MCurDateTime OBJECT-TYPE
            SYNTAX DateAndTime
            MAX-ACCESS read-only
            STATUS current
            DESCRIPTION
                "perDateTime. "
            ::= { odu4_tcm5Per15MCurEntry 4 }

        -- 1.3.6.1.4.1.2011.2.25.3.40.50.195.10.1.5
        odu4_tcm5Per15MCurParaLen OBJECT-TYPE
            SYNTAX INTEGER
            MAX-ACCESS read-only
            STATUS current
            DESCRIPTION
                "perParaLen."
            ::= { odu4_tcm5Per15MCurEntry 5 }

        -- 1.3.6.1.4.1.2011.2.25.3.40.50.195.10.1.6
        odu4_tcm5Per15MCurPara OBJECT-TYPE
            SYNTAX OCTET STRING (SIZE (0..100))
            MAX-ACCESS read-only
            STATUS current
            DESCRIPTION
                "perPara."
            ::= { odu4_tcm5Per15MCurEntry 6 }




-- -------------------------------------------------------------------------
-- Perfomance 15-MIN History Data Table (RTRV-PER-<MOD2>)
-- -------------------------------------------------------------------------
        -- 1.3.6.1.4.1.2011.2.25.3.40.50.195.20
        odu4_tcm5Per15MHisTable OBJECT-TYPE
          SYNTAX SEQUENCE OF Odu4_tcm5Per15MHisEntry
          MAX-ACCESS not-accessible
          STATUS current
          DESCRIPTION
              "odu4_tcm5Per15MHis."
          ::= { odu4_tcm5 20 }

        -- 1.3.6.1.4.1.2011.2.25.3.40.50.195.20.1
        odu4_tcm5Per15MHisEntry OBJECT-TYPE
            SYNTAX Odu4_tcm5Per15MHisEntry
            MAX-ACCESS not-accessible
            STATUS current
            DESCRIPTION
                "odu4_tcm5Per15MHis."
            INDEX {odu4_tcm5Per15MHisEid, odu4_tcm5Per15MHisParaLen, odu4_tcm5Per15MHisPara, odu4_tcm5Per15MHisDateTimeStart, odu4_tcm5Per15MHisDateTimeEnd}
            ::= { odu4_tcm5Per15MHisTable 1 }

        Odu4_tcm5Per15MHisEntry ::=
            SEQUENCE {
                odu4_tcm5Per15MHisEid
                    PerformanceEventType,
                odu4_tcm5Per15MHisParaLen
                    INTEGER,
                odu4_tcm5Per15MHisPara
                    OCTET STRING,
                odu4_tcm5Per15MHisMonValue
                    OCTET STRING,
                odu4_tcm5Per15MHisDateTimeStart
                    DateAndTime,
                odu4_tcm5Per15MHisDateTimeEnd
                    DateAndTime,
                odu4_tcm5Per15MHisVldty
                    INTEGER,
             }

        -- 1.3.6.1.4.1.2011.2.25.3.40.50.195.20.1.1
        odu4_tcm5Per15MHisEid OBJECT-TYPE
            SYNTAX PerformanceEventType
            MAX-ACCESS read-only
            STATUS current
            DESCRIPTION
                "perEid."
            ::= { odu4_tcm5Per15MHisEntry 1 }

        -- 1.3.6.1.4.1.2011.2.25.3.40.50.195.20.1.2
        odu4_tcm5Per15MHisParaLen OBJECT-TYPE
            SYNTAX INTEGER
            MAX-ACCESS read-only
            STATUS current
            DESCRIPTION
                "perParaLen."
            ::= { odu4_tcm5Per15MHisEntry 2 }

        -- 1.3.6.1.4.1.2011.2.25.3.40.50.195.20.1.3
        odu4_tcm5Per15MHisPara OBJECT-TYPE
            SYNTAX OCTET STRING (SIZE (0..100))
            MAX-ACCESS read-only
            STATUS current
            DESCRIPTION
                "perPara."
            ::= { odu4_tcm5Per15MHisEntry 3 }

        -- 1.3.6.1.4.1.2011.2.25.3.40.50.195.20.1.4
        odu4_tcm5Per15MHisMonValue OBJECT-TYPE
            SYNTAX OCTET STRING (SIZE (0..100))
            MAX-ACCESS read-only
            STATUS current
            DESCRIPTION
                "perMonValue."
            ::= { odu4_tcm5Per15MHisEntry 4 }

        -- 1.3.6.1.4.1.2011.2.25.3.40.50.195.20.1.5
        odu4_tcm5Per15MHisDateTimeStart OBJECT-TYPE
            SYNTAX DateAndTime
            MAX-ACCESS read-only
            STATUS current
            DESCRIPTION
                "perDateTimeStart. "
            ::= { odu4_tcm5Per15MHisEntry 5 }

        -- 1.3.6.1.4.1.2011.2.25.3.40.50.195.20.1.6
        odu4_tcm5Per15MHisDateTimeEnd OBJECT-TYPE
            SYNTAX DateAndTime
            MAX-ACCESS read-only
            STATUS current
            DESCRIPTION
                "perDateTimeEnd. "
            ::= { odu4_tcm5Per15MHisEntry 6 }

        -- 1.3.6.1.4.1.2011.2.25.3.40.50.195.20.1.7
        odu4_tcm5Per15MHisVldty OBJECT-TYPE
            SYNTAX INTEGER
            MAX-ACCESS read-only
            STATUS current
            DESCRIPTION
                "perVldty. "
            ::= { odu4_tcm5Per15MHisEntry 7 }




-- -------------------------------------------------------------------------
-- Perfomance 24-HOUR Current Data Table (RTRV-PER-<MOD2>)
-- -------------------------------------------------------------------------
        -- 1.3.6.1.4.1.2011.2.25.3.40.50.195.30
        odu4_tcm5Per24HCurTable OBJECT-TYPE
          SYNTAX SEQUENCE OF Odu4_tcm5Per24HCurEntry
          MAX-ACCESS not-accessible
          STATUS current
          DESCRIPTION
              "odu4_tcm5Per24HCur."
          ::= { odu4_tcm5 30 }

        -- 1.3.6.1.4.1.2011.2.25.3.40.50.195.30.1
        odu4_tcm5Per24HCurEntry OBJECT-TYPE
            SYNTAX Odu4_tcm5Per24HCurEntry
            MAX-ACCESS not-accessible
            STATUS current
            DESCRIPTION
              "odu4_tcm5Per24HCur."
            INDEX { odu4_tcm5Per24HCurEid, odu4_tcm5Per24HCurPara }
            ::= { odu4_tcm5Per24HCurTable 1 }

        Odu4_tcm5Per24HCurEntry ::=
            SEQUENCE {
                odu4_tcm5Per24HCurEid
                    PerformanceEventType,
                odu4_tcm5Per24HCurMonValue
                    OCTET STRING,
                odu4_tcm5Per24HCurVldty
                    INTEGER,
                odu4_tcm5Per24HCurDateTime
                    DateAndTime,
                odu4_tcm5Per24HCurParaLen
                    INTEGER,
                odu4_tcm5Per24HCurPara
                    OCTET STRING
            }

        -- 1.3.6.1.4.1.2011.2.25.3.40.50.195.30.1.1
        odu4_tcm5Per24HCurEid OBJECT-TYPE
            SYNTAX PerformanceEventType
            MAX-ACCESS read-only
            STATUS current
            DESCRIPTION
                "perEid."
            ::= { odu4_tcm5Per24HCurEntry 1 }

        -- 1.3.6.1.4.1.2011.2.25.3.40.50.195.30.1.2
        odu4_tcm5Per24HCurMonValue OBJECT-TYPE
            SYNTAX OCTET STRING (SIZE (0..100))
            MAX-ACCESS read-only
            STATUS current
            DESCRIPTION
                "perMonValue."
            ::= { odu4_tcm5Per24HCurEntry 2 }

        -- 1.3.6.1.4.1.2011.2.25.3.40.50.195.30.1.3
        odu4_tcm5Per24HCurVldty OBJECT-TYPE
            SYNTAX INTEGER
            MAX-ACCESS read-only
            STATUS current
            DESCRIPTION
                "perVldty. "
            ::= { odu4_tcm5Per24HCurEntry 3 }

        -- 1.3.6.1.4.1.2011.2.25.3.40.50.195.30.1.4
        odu4_tcm5Per24HCurDateTime OBJECT-TYPE
            SYNTAX DateAndTime
            MAX-ACCESS read-only
            STATUS current
            DESCRIPTION
                "perDateTime. "
            ::= { odu4_tcm5Per24HCurEntry 4 }

        -- 1.3.6.1.4.1.2011.2.25.3.40.50.195.30.1.5
        odu4_tcm5Per24HCurParaLen OBJECT-TYPE
            SYNTAX INTEGER
            MAX-ACCESS read-only
            STATUS current
            DESCRIPTION
                "perParaLen."
            ::= { odu4_tcm5Per24HCurEntry 5 }

        -- 1.3.6.1.4.1.2011.2.25.3.40.50.195.30.1.6
        odu4_tcm5Per24HCurPara OBJECT-TYPE
            SYNTAX OCTET STRING (SIZE (0..100))
            MAX-ACCESS read-only
            STATUS current
            DESCRIPTION
                "perPara."
            ::= { odu4_tcm5Per24HCurEntry 6 }




-- -------------------------------------------------------------------------
-- Perfomance 24-HOUR History Data Table (RTRV-PER-<MOD2>)
-- -------------------------------------------------------------------------
        -- 1.3.6.1.4.1.2011.2.25.3.40.50.195.40
        odu4_tcm5Per24HHisTable OBJECT-TYPE
          SYNTAX SEQUENCE OF Odu4_tcm5Per24HHisEntry
          MAX-ACCESS not-accessible
          STATUS current
          DESCRIPTION
              "odu4_tcm5Per24HHis."
          ::= { odu4_tcm5 40 }

        -- 1.3.6.1.4.1.2011.2.25.3.40.50.195.40.1
        odu4_tcm5Per24HHisEntry OBJECT-TYPE
            SYNTAX Odu4_tcm5Per24HHisEntry
            MAX-ACCESS not-accessible
            STATUS current
            DESCRIPTION
                "odu4_tcm5Per24HHis."
            INDEX {odu4_tcm5Per24HHisEid, odu4_tcm5Per24HHisParaLen, odu4_tcm5Per24HHisPara, odu4_tcm5Per24HHisDateTimeStart, odu4_tcm5Per24HHisDateTimeEnd}
            ::= { odu4_tcm5Per24HHisTable 1 }

        Odu4_tcm5Per24HHisEntry ::=
            SEQUENCE {
                odu4_tcm5Per24HHisEid
                    PerformanceEventType,
                odu4_tcm5Per24HHisParaLen
                    INTEGER,
                odu4_tcm5Per24HHisPara
                    OCTET STRING,
                odu4_tcm5Per24HHisMonValue
                    OCTET STRING,
                odu4_tcm5Per24HHisDateTimeStart
                    DateAndTime,
                odu4_tcm5Per24HHisDateTimeEnd
                    DateAndTime,
                odu4_tcm5Per24HHisVldty
                    INTEGER,
             }

        -- 1.3.6.1.4.1.2011.2.25.3.40.50.195.40.1.1
        odu4_tcm5Per24HHisEid OBJECT-TYPE
            SYNTAX PerformanceEventType
            MAX-ACCESS read-only
            STATUS current
            DESCRIPTION
                "perEid."
            ::= { odu4_tcm5Per24HHisEntry 1 }

        -- 1.3.6.1.4.1.2011.2.25.3.40.50.195.40.1.2
        odu4_tcm5Per24HHisParaLen OBJECT-TYPE
            SYNTAX INTEGER
            MAX-ACCESS read-only
            STATUS current
            DESCRIPTION
                "perParaLen."
            ::= { odu4_tcm5Per24HHisEntry 2 }

        -- 1.3.6.1.4.1.2011.2.25.3.40.50.195.40.1.3
        odu4_tcm5Per24HHisPara OBJECT-TYPE
            SYNTAX OCTET STRING (SIZE (0..100))
            MAX-ACCESS read-only
            STATUS current
            DESCRIPTION
                "perPara."
            ::= { odu4_tcm5Per24HHisEntry 3 }

        -- 1.3.6.1.4.1.2011.2.25.3.40.50.195.40.1.4
        odu4_tcm5Per24HHisMonValue OBJECT-TYPE
            SYNTAX OCTET STRING (SIZE (0..100))
            MAX-ACCESS read-only
            STATUS current
            DESCRIPTION
                "perMonValue."
            ::= { odu4_tcm5Per24HHisEntry 4 }

        -- 1.3.6.1.4.1.2011.2.25.3.40.50.195.40.1.5
        odu4_tcm5Per24HHisDateTimeStart OBJECT-TYPE
            SYNTAX DateAndTime
            MAX-ACCESS read-only
            STATUS current
            DESCRIPTION
                "perDateTimeStart. "
            ::= { odu4_tcm5Per24HHisEntry 5 }

        -- 1.3.6.1.4.1.2011.2.25.3.40.50.195.40.1.6
        odu4_tcm5Per24HHisDateTimeEnd OBJECT-TYPE
            SYNTAX DateAndTime
            MAX-ACCESS read-only
            STATUS current
            DESCRIPTION
                "perDateTimeEnd. "
            ::= { odu4_tcm5Per24HHisEntry 6 }

        -- 1.3.6.1.4.1.2011.2.25.3.40.50.195.40.1.7
        odu4_tcm5Per24HHisVldty OBJECT-TYPE
            SYNTAX INTEGER
            MAX-ACCESS read-only
            STATUS current
            DESCRIPTION
                "perVldty. "
            ::= { odu4_tcm5Per24HHisEntry 7 }




-- Alarm data
      -- 1.3.6.1.4.1.2011.2.25.3.40.50.196
      odu4_tcm6 OBJECT IDENTIFIER ::={ optixGlobalNGWDM 196 }


-- -------------------------------------------------------------------------
-- Perfomance 15-MIN Current Data Table (RTRV-PER-<MOD2>)
-- -------------------------------------------------------------------------
        -- 1.3.6.1.4.1.2011.2.25.3.40.50.196.10
        odu4_tcm6Per15MCurTable OBJECT-TYPE
          SYNTAX SEQUENCE OF Odu4_tcm6Per15MCurEntry
          MAX-ACCESS not-accessible
          STATUS current
          DESCRIPTION
              "odu4_tcm6Per15MCur."
          ::= { odu4_tcm6 10 }

        -- 1.3.6.1.4.1.2011.2.25.3.40.50.196.10.1
        odu4_tcm6Per15MCurEntry OBJECT-TYPE
            SYNTAX Odu4_tcm6Per15MCurEntry
            MAX-ACCESS not-accessible
            STATUS current
            DESCRIPTION
              "odu4_tcm6Per15MCur."
            INDEX { odu4_tcm6Per15MCurEid, odu4_tcm6Per15MCurPara }
            ::= { odu4_tcm6Per15MCurTable 1 }

        Odu4_tcm6Per15MCurEntry ::=
            SEQUENCE {
                odu4_tcm6Per15MCurEid
                    PerformanceEventType,
                odu4_tcm6Per15MCurMonValue
                    OCTET STRING,
                odu4_tcm6Per15MCurVldty
                    INTEGER,
                odu4_tcm6Per15MCurDateTime
                    DateAndTime,
                odu4_tcm6Per15MCurParaLen
                    INTEGER,
                odu4_tcm6Per15MCurPara
                    OCTET STRING
            }

        -- 1.3.6.1.4.1.2011.2.25.3.40.50.196.10.1.1
        odu4_tcm6Per15MCurEid OBJECT-TYPE
            SYNTAX PerformanceEventType
            MAX-ACCESS read-only
            STATUS current
            DESCRIPTION
                "perEid."
            ::= { odu4_tcm6Per15MCurEntry 1 }

        -- 1.3.6.1.4.1.2011.2.25.3.40.50.196.10.1.2
        odu4_tcm6Per15MCurMonValue OBJECT-TYPE
            SYNTAX OCTET STRING (SIZE (0..100))
            MAX-ACCESS read-only
            STATUS current
            DESCRIPTION
                "perMonValue."
            ::= { odu4_tcm6Per15MCurEntry 2 }

        -- 1.3.6.1.4.1.2011.2.25.3.40.50.196.10.1.3
        odu4_tcm6Per15MCurVldty OBJECT-TYPE
            SYNTAX INTEGER
            MAX-ACCESS read-only
            STATUS current
            DESCRIPTION
                "perVldty. "
            ::= { odu4_tcm6Per15MCurEntry 3 }

        -- 1.3.6.1.4.1.2011.2.25.3.40.50.196.10.1.4
        odu4_tcm6Per15MCurDateTime OBJECT-TYPE
            SYNTAX DateAndTime
            MAX-ACCESS read-only
            STATUS current
            DESCRIPTION
                "perDateTime. "
            ::= { odu4_tcm6Per15MCurEntry 4 }

        -- 1.3.6.1.4.1.2011.2.25.3.40.50.196.10.1.5
        odu4_tcm6Per15MCurParaLen OBJECT-TYPE
            SYNTAX INTEGER
            MAX-ACCESS read-only
            STATUS current
            DESCRIPTION
                "perParaLen."
            ::= { odu4_tcm6Per15MCurEntry 5 }

        -- 1.3.6.1.4.1.2011.2.25.3.40.50.196.10.1.6
        odu4_tcm6Per15MCurPara OBJECT-TYPE
            SYNTAX OCTET STRING (SIZE (0..100))
            MAX-ACCESS read-only
            STATUS current
            DESCRIPTION
                "perPara."
            ::= { odu4_tcm6Per15MCurEntry 6 }




-- -------------------------------------------------------------------------
-- Perfomance 15-MIN History Data Table (RTRV-PER-<MOD2>)
-- -------------------------------------------------------------------------
        -- 1.3.6.1.4.1.2011.2.25.3.40.50.196.20
        odu4_tcm6Per15MHisTable OBJECT-TYPE
          SYNTAX SEQUENCE OF Odu4_tcm6Per15MHisEntry
          MAX-ACCESS not-accessible
          STATUS current
          DESCRIPTION
              "odu4_tcm6Per15MHis."
          ::= { odu4_tcm6 20 }

        -- 1.3.6.1.4.1.2011.2.25.3.40.50.196.20.1
        odu4_tcm6Per15MHisEntry OBJECT-TYPE
            SYNTAX Odu4_tcm6Per15MHisEntry
            MAX-ACCESS not-accessible
            STATUS current
            DESCRIPTION
                "odu4_tcm6Per15MHis."
            INDEX {odu4_tcm6Per15MHisEid, odu4_tcm6Per15MHisParaLen, odu4_tcm6Per15MHisPara, odu4_tcm6Per15MHisDateTimeStart, odu4_tcm6Per15MHisDateTimeEnd}
            ::= { odu4_tcm6Per15MHisTable 1 }

        Odu4_tcm6Per15MHisEntry ::=
            SEQUENCE {
                odu4_tcm6Per15MHisEid
                    PerformanceEventType,
                odu4_tcm6Per15MHisParaLen
                    INTEGER,
                odu4_tcm6Per15MHisPara
                    OCTET STRING,
                odu4_tcm6Per15MHisMonValue
                    OCTET STRING,
                odu4_tcm6Per15MHisDateTimeStart
                    DateAndTime,
                odu4_tcm6Per15MHisDateTimeEnd
                    DateAndTime,
                odu4_tcm6Per15MHisVldty
                    INTEGER,
             }

        -- 1.3.6.1.4.1.2011.2.25.3.40.50.196.20.1.1
        odu4_tcm6Per15MHisEid OBJECT-TYPE
            SYNTAX PerformanceEventType
            MAX-ACCESS read-only
            STATUS current
            DESCRIPTION
                "perEid."
            ::= { odu4_tcm6Per15MHisEntry 1 }

        -- 1.3.6.1.4.1.2011.2.25.3.40.50.196.20.1.2
        odu4_tcm6Per15MHisParaLen OBJECT-TYPE
            SYNTAX INTEGER
            MAX-ACCESS read-only
            STATUS current
            DESCRIPTION
                "perParaLen."
            ::= { odu4_tcm6Per15MHisEntry 2 }

        -- 1.3.6.1.4.1.2011.2.25.3.40.50.196.20.1.3
        odu4_tcm6Per15MHisPara OBJECT-TYPE
            SYNTAX OCTET STRING (SIZE (0..100))
            MAX-ACCESS read-only
            STATUS current
            DESCRIPTION
                "perPara."
            ::= { odu4_tcm6Per15MHisEntry 3 }

        -- 1.3.6.1.4.1.2011.2.25.3.40.50.196.20.1.4
        odu4_tcm6Per15MHisMonValue OBJECT-TYPE
            SYNTAX OCTET STRING (SIZE (0..100))
            MAX-ACCESS read-only
            STATUS current
            DESCRIPTION
                "perMonValue."
            ::= { odu4_tcm6Per15MHisEntry 4 }

        -- 1.3.6.1.4.1.2011.2.25.3.40.50.196.20.1.5
        odu4_tcm6Per15MHisDateTimeStart OBJECT-TYPE
            SYNTAX DateAndTime
            MAX-ACCESS read-only
            STATUS current
            DESCRIPTION
                "perDateTimeStart. "
            ::= { odu4_tcm6Per15MHisEntry 5 }

        -- 1.3.6.1.4.1.2011.2.25.3.40.50.196.20.1.6
        odu4_tcm6Per15MHisDateTimeEnd OBJECT-TYPE
            SYNTAX DateAndTime
            MAX-ACCESS read-only
            STATUS current
            DESCRIPTION
                "perDateTimeEnd. "
            ::= { odu4_tcm6Per15MHisEntry 6 }

        -- 1.3.6.1.4.1.2011.2.25.3.40.50.196.20.1.7
        odu4_tcm6Per15MHisVldty OBJECT-TYPE
            SYNTAX INTEGER
            MAX-ACCESS read-only
            STATUS current
            DESCRIPTION
                "perVldty. "
            ::= { odu4_tcm6Per15MHisEntry 7 }




-- -------------------------------------------------------------------------
-- Perfomance 24-HOUR Current Data Table (RTRV-PER-<MOD2>)
-- -------------------------------------------------------------------------
        -- 1.3.6.1.4.1.2011.2.25.3.40.50.196.30
        odu4_tcm6Per24HCurTable OBJECT-TYPE
          SYNTAX SEQUENCE OF Odu4_tcm6Per24HCurEntry
          MAX-ACCESS not-accessible
          STATUS current
          DESCRIPTION
              "odu4_tcm6Per24HCur."
          ::= { odu4_tcm6 30 }

        -- 1.3.6.1.4.1.2011.2.25.3.40.50.196.30.1
        odu4_tcm6Per24HCurEntry OBJECT-TYPE
            SYNTAX Odu4_tcm6Per24HCurEntry
            MAX-ACCESS not-accessible
            STATUS current
            DESCRIPTION
              "odu4_tcm6Per24HCur."
            INDEX { odu4_tcm6Per24HCurEid, odu4_tcm6Per24HCurPara }
            ::= { odu4_tcm6Per24HCurTable 1 }

        Odu4_tcm6Per24HCurEntry ::=
            SEQUENCE {
                odu4_tcm6Per24HCurEid
                    PerformanceEventType,
                odu4_tcm6Per24HCurMonValue
                    OCTET STRING,
                odu4_tcm6Per24HCurVldty
                    INTEGER,
                odu4_tcm6Per24HCurDateTime
                    DateAndTime,
                odu4_tcm6Per24HCurParaLen
                    INTEGER,
                odu4_tcm6Per24HCurPara
                    OCTET STRING
            }

        -- 1.3.6.1.4.1.2011.2.25.3.40.50.196.30.1.1
        odu4_tcm6Per24HCurEid OBJECT-TYPE
            SYNTAX PerformanceEventType
            MAX-ACCESS read-only
            STATUS current
            DESCRIPTION
                "perEid."
            ::= { odu4_tcm6Per24HCurEntry 1 }

        -- 1.3.6.1.4.1.2011.2.25.3.40.50.196.30.1.2
        odu4_tcm6Per24HCurMonValue OBJECT-TYPE
            SYNTAX OCTET STRING (SIZE (0..100))
            MAX-ACCESS read-only
            STATUS current
            DESCRIPTION
                "perMonValue."
            ::= { odu4_tcm6Per24HCurEntry 2 }

        -- 1.3.6.1.4.1.2011.2.25.3.40.50.196.30.1.3
        odu4_tcm6Per24HCurVldty OBJECT-TYPE
            SYNTAX INTEGER
            MAX-ACCESS read-only
            STATUS current
            DESCRIPTION
                "perVldty. "
            ::= { odu4_tcm6Per24HCurEntry 3 }

        -- 1.3.6.1.4.1.2011.2.25.3.40.50.196.30.1.4
        odu4_tcm6Per24HCurDateTime OBJECT-TYPE
            SYNTAX DateAndTime
            MAX-ACCESS read-only
            STATUS current
            DESCRIPTION
                "perDateTime. "
            ::= { odu4_tcm6Per24HCurEntry 4 }

        -- 1.3.6.1.4.1.2011.2.25.3.40.50.196.30.1.5
        odu4_tcm6Per24HCurParaLen OBJECT-TYPE
            SYNTAX INTEGER
            MAX-ACCESS read-only
            STATUS current
            DESCRIPTION
                "perParaLen."
            ::= { odu4_tcm6Per24HCurEntry 5 }

        -- 1.3.6.1.4.1.2011.2.25.3.40.50.196.30.1.6
        odu4_tcm6Per24HCurPara OBJECT-TYPE
            SYNTAX OCTET STRING (SIZE (0..100))
            MAX-ACCESS read-only
            STATUS current
            DESCRIPTION
                "perPara."
            ::= { odu4_tcm6Per24HCurEntry 6 }




-- -------------------------------------------------------------------------
-- Perfomance 24-HOUR History Data Table (RTRV-PER-<MOD2>)
-- -------------------------------------------------------------------------
        -- 1.3.6.1.4.1.2011.2.25.3.40.50.196.40
        odu4_tcm6Per24HHisTable OBJECT-TYPE
          SYNTAX SEQUENCE OF Odu4_tcm6Per24HHisEntry
          MAX-ACCESS not-accessible
          STATUS current
          DESCRIPTION
              "odu4_tcm6Per24HHis."
          ::= { odu4_tcm6 40 }

        -- 1.3.6.1.4.1.2011.2.25.3.40.50.196.40.1
        odu4_tcm6Per24HHisEntry OBJECT-TYPE
            SYNTAX Odu4_tcm6Per24HHisEntry
            MAX-ACCESS not-accessible
            STATUS current
            DESCRIPTION
                "odu4_tcm6Per24HHis."
            INDEX {odu4_tcm6Per24HHisEid, odu4_tcm6Per24HHisParaLen, odu4_tcm6Per24HHisPara, odu4_tcm6Per24HHisDateTimeStart, odu4_tcm6Per24HHisDateTimeEnd}
            ::= { odu4_tcm6Per24HHisTable 1 }

        Odu4_tcm6Per24HHisEntry ::=
            SEQUENCE {
                odu4_tcm6Per24HHisEid
                    PerformanceEventType,
                odu4_tcm6Per24HHisParaLen
                    INTEGER,
                odu4_tcm6Per24HHisPara
                    OCTET STRING,
                odu4_tcm6Per24HHisMonValue
                    OCTET STRING,
                odu4_tcm6Per24HHisDateTimeStart
                    DateAndTime,
                odu4_tcm6Per24HHisDateTimeEnd
                    DateAndTime,
                odu4_tcm6Per24HHisVldty
                    INTEGER,
             }

        -- 1.3.6.1.4.1.2011.2.25.3.40.50.196.40.1.1
        odu4_tcm6Per24HHisEid OBJECT-TYPE
            SYNTAX PerformanceEventType
            MAX-ACCESS read-only
            STATUS current
            DESCRIPTION
                "perEid."
            ::= { odu4_tcm6Per24HHisEntry 1 }

        -- 1.3.6.1.4.1.2011.2.25.3.40.50.196.40.1.2
        odu4_tcm6Per24HHisParaLen OBJECT-TYPE
            SYNTAX INTEGER
            MAX-ACCESS read-only
            STATUS current
            DESCRIPTION
                "perParaLen."
            ::= { odu4_tcm6Per24HHisEntry 2 }

        -- 1.3.6.1.4.1.2011.2.25.3.40.50.196.40.1.3
        odu4_tcm6Per24HHisPara OBJECT-TYPE
            SYNTAX OCTET STRING (SIZE (0..100))
            MAX-ACCESS read-only
            STATUS current
            DESCRIPTION
                "perPara."
            ::= { odu4_tcm6Per24HHisEntry 3 }

        -- 1.3.6.1.4.1.2011.2.25.3.40.50.196.40.1.4
        odu4_tcm6Per24HHisMonValue OBJECT-TYPE
            SYNTAX OCTET STRING (SIZE (0..100))
            MAX-ACCESS read-only
            STATUS current
            DESCRIPTION
                "perMonValue."
            ::= { odu4_tcm6Per24HHisEntry 4 }

        -- 1.3.6.1.4.1.2011.2.25.3.40.50.196.40.1.5
        odu4_tcm6Per24HHisDateTimeStart OBJECT-TYPE
            SYNTAX DateAndTime
            MAX-ACCESS read-only
            STATUS current
            DESCRIPTION
                "perDateTimeStart. "
            ::= { odu4_tcm6Per24HHisEntry 5 }

        -- 1.3.6.1.4.1.2011.2.25.3.40.50.196.40.1.6
        odu4_tcm6Per24HHisDateTimeEnd OBJECT-TYPE
            SYNTAX DateAndTime
            MAX-ACCESS read-only
            STATUS current
            DESCRIPTION
                "perDateTimeEnd. "
            ::= { odu4_tcm6Per24HHisEntry 6 }

        -- 1.3.6.1.4.1.2011.2.25.3.40.50.196.40.1.7
        odu4_tcm6Per24HHisVldty OBJECT-TYPE
            SYNTAX INTEGER
            MAX-ACCESS read-only
            STATUS current
            DESCRIPTION
                "perVldty. "
            ::= { odu4_tcm6Per24HHisEntry 7 }




-- Alarm data
      -- 1.3.6.1.4.1.2011.2.25.3.40.50.202
      oduflex_path OBJECT IDENTIFIER ::={ optixGlobalNGWDM 202 }


-- -------------------------------------------------------------------------
-- Perfomance 15-MIN Current Data Table (RTRV-PER-<MOD2>)
-- -------------------------------------------------------------------------
        -- 1.3.6.1.4.1.2011.2.25.3.40.50.202.10
        oduflex_pathPer15MCurTable OBJECT-TYPE
          SYNTAX SEQUENCE OF Oduflex_pathPer15MCurEntry
          MAX-ACCESS not-accessible
          STATUS current
          DESCRIPTION
              "oduflex_pathPer15MCur."
          ::= { oduflex_path 10 }

        -- 1.3.6.1.4.1.2011.2.25.3.40.50.202.10.1
        oduflex_pathPer15MCurEntry OBJECT-TYPE
            SYNTAX Oduflex_pathPer15MCurEntry
            MAX-ACCESS not-accessible
            STATUS current
            DESCRIPTION
              "oduflex_pathPer15MCur."
            INDEX { oduflex_pathPer15MCurEid, oduflex_pathPer15MCurPara }
            ::= { oduflex_pathPer15MCurTable 1 }

        Oduflex_pathPer15MCurEntry ::=
            SEQUENCE {
                oduflex_pathPer15MCurEid
                    PerformanceEventType,
                oduflex_pathPer15MCurMonValue
                    OCTET STRING,
                oduflex_pathPer15MCurVldty
                    INTEGER,
                oduflex_pathPer15MCurDateTime
                    DateAndTime,
                oduflex_pathPer15MCurParaLen
                    INTEGER,
                oduflex_pathPer15MCurPara
                    OCTET STRING
            }

        -- 1.3.6.1.4.1.2011.2.25.3.40.50.202.10.1.1
        oduflex_pathPer15MCurEid OBJECT-TYPE
            SYNTAX PerformanceEventType
            MAX-ACCESS read-only
            STATUS current
            DESCRIPTION
                "perEid."
            ::= { oduflex_pathPer15MCurEntry 1 }

        -- 1.3.6.1.4.1.2011.2.25.3.40.50.202.10.1.2
        oduflex_pathPer15MCurMonValue OBJECT-TYPE
            SYNTAX OCTET STRING (SIZE (0..100))
            MAX-ACCESS read-only
            STATUS current
            DESCRIPTION
                "perMonValue."
            ::= { oduflex_pathPer15MCurEntry 2 }

        -- 1.3.6.1.4.1.2011.2.25.3.40.50.202.10.1.3
        oduflex_pathPer15MCurVldty OBJECT-TYPE
            SYNTAX INTEGER
            MAX-ACCESS read-only
            STATUS current
            DESCRIPTION
                "perVldty. "
            ::= { oduflex_pathPer15MCurEntry 3 }

        -- 1.3.6.1.4.1.2011.2.25.3.40.50.202.10.1.4
        oduflex_pathPer15MCurDateTime OBJECT-TYPE
            SYNTAX DateAndTime
            MAX-ACCESS read-only
            STATUS current
            DESCRIPTION
                "perDateTime. "
            ::= { oduflex_pathPer15MCurEntry 4 }

        -- 1.3.6.1.4.1.2011.2.25.3.40.50.202.10.1.5
        oduflex_pathPer15MCurParaLen OBJECT-TYPE
            SYNTAX INTEGER
            MAX-ACCESS read-only
            STATUS current
            DESCRIPTION
                "perParaLen."
            ::= { oduflex_pathPer15MCurEntry 5 }

        -- 1.3.6.1.4.1.2011.2.25.3.40.50.202.10.1.6
        oduflex_pathPer15MCurPara OBJECT-TYPE
            SYNTAX OCTET STRING (SIZE (0..100))
            MAX-ACCESS read-only
            STATUS current
            DESCRIPTION
                "perPara."
            ::= { oduflex_pathPer15MCurEntry 6 }




-- -------------------------------------------------------------------------
-- Perfomance 15-MIN History Data Table (RTRV-PER-<MOD2>)
-- -------------------------------------------------------------------------
        -- 1.3.6.1.4.1.2011.2.25.3.40.50.202.20
        oduflex_pathPer15MHisTable OBJECT-TYPE
          SYNTAX SEQUENCE OF Oduflex_pathPer15MHisEntry
          MAX-ACCESS not-accessible
          STATUS current
          DESCRIPTION
              "oduflex_pathPer15MHis."
          ::= { oduflex_path 20 }

        -- 1.3.6.1.4.1.2011.2.25.3.40.50.202.20.1
        oduflex_pathPer15MHisEntry OBJECT-TYPE
            SYNTAX Oduflex_pathPer15MHisEntry
            MAX-ACCESS not-accessible
            STATUS current
            DESCRIPTION
                "oduflex_pathPer15MHis."
            INDEX {oduflex_pathPer15MHisEid, oduflex_pathPer15MHisParaLen, oduflex_pathPer15MHisPara, oduflex_pathPer15MHisDateTimeStart, oduflex_pathPer15MHisDateTimeEnd}
            ::= { oduflex_pathPer15MHisTable 1 }

        Oduflex_pathPer15MHisEntry ::=
            SEQUENCE {
                oduflex_pathPer15MHisEid
                    PerformanceEventType,
                oduflex_pathPer15MHisParaLen
                    INTEGER,
                oduflex_pathPer15MHisPara
                    OCTET STRING,
                oduflex_pathPer15MHisMonValue
                    OCTET STRING,
                oduflex_pathPer15MHisDateTimeStart
                    DateAndTime,
                oduflex_pathPer15MHisDateTimeEnd
                    DateAndTime,
                oduflex_pathPer15MHisVldty
                    INTEGER,
             }

        -- 1.3.6.1.4.1.2011.2.25.3.40.50.202.20.1.1
        oduflex_pathPer15MHisEid OBJECT-TYPE
            SYNTAX PerformanceEventType
            MAX-ACCESS read-only
            STATUS current
            DESCRIPTION
                "perEid."
            ::= { oduflex_pathPer15MHisEntry 1 }

        -- 1.3.6.1.4.1.2011.2.25.3.40.50.202.20.1.2
        oduflex_pathPer15MHisParaLen OBJECT-TYPE
            SYNTAX INTEGER
            MAX-ACCESS read-only
            STATUS current
            DESCRIPTION
                "perParaLen."
            ::= { oduflex_pathPer15MHisEntry 2 }

        -- 1.3.6.1.4.1.2011.2.25.3.40.50.202.20.1.3
        oduflex_pathPer15MHisPara OBJECT-TYPE
            SYNTAX OCTET STRING (SIZE (0..100))
            MAX-ACCESS read-only
            STATUS current
            DESCRIPTION
                "perPara."
            ::= { oduflex_pathPer15MHisEntry 3 }

        -- 1.3.6.1.4.1.2011.2.25.3.40.50.202.20.1.4
        oduflex_pathPer15MHisMonValue OBJECT-TYPE
            SYNTAX OCTET STRING (SIZE (0..100))
            MAX-ACCESS read-only
            STATUS current
            DESCRIPTION
                "perMonValue."
            ::= { oduflex_pathPer15MHisEntry 4 }

        -- 1.3.6.1.4.1.2011.2.25.3.40.50.202.20.1.5
        oduflex_pathPer15MHisDateTimeStart OBJECT-TYPE
            SYNTAX DateAndTime
            MAX-ACCESS read-only
            STATUS current
            DESCRIPTION
                "perDateTimeStart. "
            ::= { oduflex_pathPer15MHisEntry 5 }

        -- 1.3.6.1.4.1.2011.2.25.3.40.50.202.20.1.6
        oduflex_pathPer15MHisDateTimeEnd OBJECT-TYPE
            SYNTAX DateAndTime
            MAX-ACCESS read-only
            STATUS current
            DESCRIPTION
                "perDateTimeEnd. "
            ::= { oduflex_pathPer15MHisEntry 6 }

        -- 1.3.6.1.4.1.2011.2.25.3.40.50.202.20.1.7
        oduflex_pathPer15MHisVldty OBJECT-TYPE
            SYNTAX INTEGER
            MAX-ACCESS read-only
            STATUS current
            DESCRIPTION
                "perVldty. "
            ::= { oduflex_pathPer15MHisEntry 7 }




-- -------------------------------------------------------------------------
-- Perfomance 24-HOUR Current Data Table (RTRV-PER-<MOD2>)
-- -------------------------------------------------------------------------
        -- 1.3.6.1.4.1.2011.2.25.3.40.50.202.30
        oduflex_pathPer24HCurTable OBJECT-TYPE
          SYNTAX SEQUENCE OF Oduflex_pathPer24HCurEntry
          MAX-ACCESS not-accessible
          STATUS current
          DESCRIPTION
              "oduflex_pathPer24HCur."
          ::= { oduflex_path 30 }

        -- 1.3.6.1.4.1.2011.2.25.3.40.50.202.30.1
        oduflex_pathPer24HCurEntry OBJECT-TYPE
            SYNTAX Oduflex_pathPer24HCurEntry
            MAX-ACCESS not-accessible
            STATUS current
            DESCRIPTION
              "oduflex_pathPer24HCur."
            INDEX { oduflex_pathPer24HCurEid, oduflex_pathPer24HCurPara }
            ::= { oduflex_pathPer24HCurTable 1 }

        Oduflex_pathPer24HCurEntry ::=
            SEQUENCE {
                oduflex_pathPer24HCurEid
                    PerformanceEventType,
                oduflex_pathPer24HCurMonValue
                    OCTET STRING,
                oduflex_pathPer24HCurVldty
                    INTEGER,
                oduflex_pathPer24HCurDateTime
                    DateAndTime,
                oduflex_pathPer24HCurParaLen
                    INTEGER,
                oduflex_pathPer24HCurPara
                    OCTET STRING
            }

        -- 1.3.6.1.4.1.2011.2.25.3.40.50.202.30.1.1
        oduflex_pathPer24HCurEid OBJECT-TYPE
            SYNTAX PerformanceEventType
            MAX-ACCESS read-only
            STATUS current
            DESCRIPTION
                "perEid."
            ::= { oduflex_pathPer24HCurEntry 1 }

        -- 1.3.6.1.4.1.2011.2.25.3.40.50.202.30.1.2
        oduflex_pathPer24HCurMonValue OBJECT-TYPE
            SYNTAX OCTET STRING (SIZE (0..100))
            MAX-ACCESS read-only
            STATUS current
            DESCRIPTION
                "perMonValue."
            ::= { oduflex_pathPer24HCurEntry 2 }

        -- 1.3.6.1.4.1.2011.2.25.3.40.50.202.30.1.3
        oduflex_pathPer24HCurVldty OBJECT-TYPE
            SYNTAX INTEGER
            MAX-ACCESS read-only
            STATUS current
            DESCRIPTION
                "perVldty. "
            ::= { oduflex_pathPer24HCurEntry 3 }

        -- 1.3.6.1.4.1.2011.2.25.3.40.50.202.30.1.4
        oduflex_pathPer24HCurDateTime OBJECT-TYPE
            SYNTAX DateAndTime
            MAX-ACCESS read-only
            STATUS current
            DESCRIPTION
                "perDateTime. "
            ::= { oduflex_pathPer24HCurEntry 4 }

        -- 1.3.6.1.4.1.2011.2.25.3.40.50.202.30.1.5
        oduflex_pathPer24HCurParaLen OBJECT-TYPE
            SYNTAX INTEGER
            MAX-ACCESS read-only
            STATUS current
            DESCRIPTION
                "perParaLen."
            ::= { oduflex_pathPer24HCurEntry 5 }

        -- 1.3.6.1.4.1.2011.2.25.3.40.50.202.30.1.6
        oduflex_pathPer24HCurPara OBJECT-TYPE
            SYNTAX OCTET STRING (SIZE (0..100))
            MAX-ACCESS read-only
            STATUS current
            DESCRIPTION
                "perPara."
            ::= { oduflex_pathPer24HCurEntry 6 }




-- -------------------------------------------------------------------------
-- Perfomance 24-HOUR History Data Table (RTRV-PER-<MOD2>)
-- -------------------------------------------------------------------------
        -- 1.3.6.1.4.1.2011.2.25.3.40.50.202.40
        oduflex_pathPer24HHisTable OBJECT-TYPE
          SYNTAX SEQUENCE OF Oduflex_pathPer24HHisEntry
          MAX-ACCESS not-accessible
          STATUS current
          DESCRIPTION
              "oduflex_pathPer24HHis."
          ::= { oduflex_path 40 }

        -- 1.3.6.1.4.1.2011.2.25.3.40.50.202.40.1
        oduflex_pathPer24HHisEntry OBJECT-TYPE
            SYNTAX Oduflex_pathPer24HHisEntry
            MAX-ACCESS not-accessible
            STATUS current
            DESCRIPTION
                "oduflex_pathPer24HHis."
            INDEX {oduflex_pathPer24HHisEid, oduflex_pathPer24HHisParaLen, oduflex_pathPer24HHisPara, oduflex_pathPer24HHisDateTimeStart, oduflex_pathPer24HHisDateTimeEnd}
            ::= { oduflex_pathPer24HHisTable 1 }

        Oduflex_pathPer24HHisEntry ::=
            SEQUENCE {
                oduflex_pathPer24HHisEid
                    PerformanceEventType,
                oduflex_pathPer24HHisParaLen
                    INTEGER,
                oduflex_pathPer24HHisPara
                    OCTET STRING,
                oduflex_pathPer24HHisMonValue
                    OCTET STRING,
                oduflex_pathPer24HHisDateTimeStart
                    DateAndTime,
                oduflex_pathPer24HHisDateTimeEnd
                    DateAndTime,
                oduflex_pathPer24HHisVldty
                    INTEGER,
             }

        -- 1.3.6.1.4.1.2011.2.25.3.40.50.202.40.1.1
        oduflex_pathPer24HHisEid OBJECT-TYPE
            SYNTAX PerformanceEventType
            MAX-ACCESS read-only
            STATUS current
            DESCRIPTION
                "perEid."
            ::= { oduflex_pathPer24HHisEntry 1 }

        -- 1.3.6.1.4.1.2011.2.25.3.40.50.202.40.1.2
        oduflex_pathPer24HHisParaLen OBJECT-TYPE
            SYNTAX INTEGER
            MAX-ACCESS read-only
            STATUS current
            DESCRIPTION
                "perParaLen."
            ::= { oduflex_pathPer24HHisEntry 2 }

        -- 1.3.6.1.4.1.2011.2.25.3.40.50.202.40.1.3
        oduflex_pathPer24HHisPara OBJECT-TYPE
            SYNTAX OCTET STRING (SIZE (0..100))
            MAX-ACCESS read-only
            STATUS current
            DESCRIPTION
                "perPara."
            ::= { oduflex_pathPer24HHisEntry 3 }

        -- 1.3.6.1.4.1.2011.2.25.3.40.50.202.40.1.4
        oduflex_pathPer24HHisMonValue OBJECT-TYPE
            SYNTAX OCTET STRING (SIZE (0..100))
            MAX-ACCESS read-only
            STATUS current
            DESCRIPTION
                "perMonValue."
            ::= { oduflex_pathPer24HHisEntry 4 }

        -- 1.3.6.1.4.1.2011.2.25.3.40.50.202.40.1.5
        oduflex_pathPer24HHisDateTimeStart OBJECT-TYPE
            SYNTAX DateAndTime
            MAX-ACCESS read-only
            STATUS current
            DESCRIPTION
                "perDateTimeStart. "
            ::= { oduflex_pathPer24HHisEntry 5 }

        -- 1.3.6.1.4.1.2011.2.25.3.40.50.202.40.1.6
        oduflex_pathPer24HHisDateTimeEnd OBJECT-TYPE
            SYNTAX DateAndTime
            MAX-ACCESS read-only
            STATUS current
            DESCRIPTION
                "perDateTimeEnd. "
            ::= { oduflex_pathPer24HHisEntry 6 }

        -- 1.3.6.1.4.1.2011.2.25.3.40.50.202.40.1.7
        oduflex_pathPer24HHisVldty OBJECT-TYPE
            SYNTAX INTEGER
            MAX-ACCESS read-only
            STATUS current
            DESCRIPTION
                "perVldty. "
            ::= { oduflex_pathPer24HHisEntry 7 }




-- Alarm data
      -- 1.3.6.1.4.1.2011.2.25.3.40.50.203
      odu0_tcm1 OBJECT IDENTIFIER ::={ optixGlobalNGWDM 203 }


-- -------------------------------------------------------------------------
-- Perfomance 15-MIN Current Data Table (RTRV-PER-<MOD2>)
-- -------------------------------------------------------------------------
        -- 1.3.6.1.4.1.2011.2.25.3.40.50.203.10
        odu0_tcm1Per15MCurTable OBJECT-TYPE
          SYNTAX SEQUENCE OF Odu0_tcm1Per15MCurEntry
          MAX-ACCESS not-accessible
          STATUS current
          DESCRIPTION
              "odu0_tcm1Per15MCur."
          ::= { odu0_tcm1 10 }

        -- 1.3.6.1.4.1.2011.2.25.3.40.50.203.10.1
        odu0_tcm1Per15MCurEntry OBJECT-TYPE
            SYNTAX Odu0_tcm1Per15MCurEntry
            MAX-ACCESS not-accessible
            STATUS current
            DESCRIPTION
              "odu0_tcm1Per15MCur."
            INDEX { odu0_tcm1Per15MCurEid, odu0_tcm1Per15MCurPara }
            ::= { odu0_tcm1Per15MCurTable 1 }

        Odu0_tcm1Per15MCurEntry ::=
            SEQUENCE {
                odu0_tcm1Per15MCurEid
                    PerformanceEventType,
                odu0_tcm1Per15MCurMonValue
                    OCTET STRING,
                odu0_tcm1Per15MCurVldty
                    INTEGER,
                odu0_tcm1Per15MCurDateTime
                    DateAndTime,
                odu0_tcm1Per15MCurParaLen
                    INTEGER,
                odu0_tcm1Per15MCurPara
                    OCTET STRING
            }

        -- 1.3.6.1.4.1.2011.2.25.3.40.50.203.10.1.1
        odu0_tcm1Per15MCurEid OBJECT-TYPE
            SYNTAX PerformanceEventType
            MAX-ACCESS read-only
            STATUS current
            DESCRIPTION
                "perEid."
            ::= { odu0_tcm1Per15MCurEntry 1 }

        -- 1.3.6.1.4.1.2011.2.25.3.40.50.203.10.1.2
        odu0_tcm1Per15MCurMonValue OBJECT-TYPE
            SYNTAX OCTET STRING (SIZE (0..100))
            MAX-ACCESS read-only
            STATUS current
            DESCRIPTION
                "perMonValue."
            ::= { odu0_tcm1Per15MCurEntry 2 }

        -- 1.3.6.1.4.1.2011.2.25.3.40.50.203.10.1.3
        odu0_tcm1Per15MCurVldty OBJECT-TYPE
            SYNTAX INTEGER
            MAX-ACCESS read-only
            STATUS current
            DESCRIPTION
                "perVldty. "
            ::= { odu0_tcm1Per15MCurEntry 3 }

        -- 1.3.6.1.4.1.2011.2.25.3.40.50.203.10.1.4
        odu0_tcm1Per15MCurDateTime OBJECT-TYPE
            SYNTAX DateAndTime
            MAX-ACCESS read-only
            STATUS current
            DESCRIPTION
                "perDateTime. "
            ::= { odu0_tcm1Per15MCurEntry 4 }

        -- 1.3.6.1.4.1.2011.2.25.3.40.50.203.10.1.5
        odu0_tcm1Per15MCurParaLen OBJECT-TYPE
            SYNTAX INTEGER
            MAX-ACCESS read-only
            STATUS current
            DESCRIPTION
                "perParaLen."
            ::= { odu0_tcm1Per15MCurEntry 5 }

        -- 1.3.6.1.4.1.2011.2.25.3.40.50.203.10.1.6
        odu0_tcm1Per15MCurPara OBJECT-TYPE
            SYNTAX OCTET STRING (SIZE (0..100))
            MAX-ACCESS read-only
            STATUS current
            DESCRIPTION
                "perPara."
            ::= { odu0_tcm1Per15MCurEntry 6 }




-- -------------------------------------------------------------------------
-- Perfomance 15-MIN History Data Table (RTRV-PER-<MOD2>)
-- -------------------------------------------------------------------------
        -- 1.3.6.1.4.1.2011.2.25.3.40.50.203.20
        odu0_tcm1Per15MHisTable OBJECT-TYPE
          SYNTAX SEQUENCE OF Odu0_tcm1Per15MHisEntry
          MAX-ACCESS not-accessible
          STATUS current
          DESCRIPTION
              "odu0_tcm1Per15MHis."
          ::= { odu0_tcm1 20 }

        -- 1.3.6.1.4.1.2011.2.25.3.40.50.203.20.1
        odu0_tcm1Per15MHisEntry OBJECT-TYPE
            SYNTAX Odu0_tcm1Per15MHisEntry
            MAX-ACCESS not-accessible
            STATUS current
            DESCRIPTION
                "odu0_tcm1Per15MHis."
            INDEX {odu0_tcm1Per15MHisEid, odu0_tcm1Per15MHisParaLen, odu0_tcm1Per15MHisPara, odu0_tcm1Per15MHisDateTimeStart, odu0_tcm1Per15MHisDateTimeEnd}
            ::= { odu0_tcm1Per15MHisTable 1 }

        Odu0_tcm1Per15MHisEntry ::=
            SEQUENCE {
                odu0_tcm1Per15MHisEid
                    PerformanceEventType,
                odu0_tcm1Per15MHisParaLen
                    INTEGER,
                odu0_tcm1Per15MHisPara
                    OCTET STRING,
                odu0_tcm1Per15MHisMonValue
                    OCTET STRING,
                odu0_tcm1Per15MHisDateTimeStart
                    DateAndTime,
                odu0_tcm1Per15MHisDateTimeEnd
                    DateAndTime,
                odu0_tcm1Per15MHisVldty
                    INTEGER,
             }

        -- 1.3.6.1.4.1.2011.2.25.3.40.50.203.20.1.1
        odu0_tcm1Per15MHisEid OBJECT-TYPE
            SYNTAX PerformanceEventType
            MAX-ACCESS read-only
            STATUS current
            DESCRIPTION
                "perEid."
            ::= { odu0_tcm1Per15MHisEntry 1 }

        -- 1.3.6.1.4.1.2011.2.25.3.40.50.203.20.1.2
        odu0_tcm1Per15MHisParaLen OBJECT-TYPE
            SYNTAX INTEGER
            MAX-ACCESS read-only
            STATUS current
            DESCRIPTION
                "perParaLen."
            ::= { odu0_tcm1Per15MHisEntry 2 }

        -- 1.3.6.1.4.1.2011.2.25.3.40.50.203.20.1.3
        odu0_tcm1Per15MHisPara OBJECT-TYPE
            SYNTAX OCTET STRING (SIZE (0..100))
            MAX-ACCESS read-only
            STATUS current
            DESCRIPTION
                "perPara."
            ::= { odu0_tcm1Per15MHisEntry 3 }

        -- 1.3.6.1.4.1.2011.2.25.3.40.50.203.20.1.4
        odu0_tcm1Per15MHisMonValue OBJECT-TYPE
            SYNTAX OCTET STRING (SIZE (0..100))
            MAX-ACCESS read-only
            STATUS current
            DESCRIPTION
                "perMonValue."
            ::= { odu0_tcm1Per15MHisEntry 4 }

        -- 1.3.6.1.4.1.2011.2.25.3.40.50.203.20.1.5
        odu0_tcm1Per15MHisDateTimeStart OBJECT-TYPE
            SYNTAX DateAndTime
            MAX-ACCESS read-only
            STATUS current
            DESCRIPTION
                "perDateTimeStart. "
            ::= { odu0_tcm1Per15MHisEntry 5 }

        -- 1.3.6.1.4.1.2011.2.25.3.40.50.203.20.1.6
        odu0_tcm1Per15MHisDateTimeEnd OBJECT-TYPE
            SYNTAX DateAndTime
            MAX-ACCESS read-only
            STATUS current
            DESCRIPTION
                "perDateTimeEnd. "
            ::= { odu0_tcm1Per15MHisEntry 6 }

        -- 1.3.6.1.4.1.2011.2.25.3.40.50.203.20.1.7
        odu0_tcm1Per15MHisVldty OBJECT-TYPE
            SYNTAX INTEGER
            MAX-ACCESS read-only
            STATUS current
            DESCRIPTION
                "perVldty. "
            ::= { odu0_tcm1Per15MHisEntry 7 }




-- -------------------------------------------------------------------------
-- Perfomance 24-HOUR Current Data Table (RTRV-PER-<MOD2>)
-- -------------------------------------------------------------------------
        -- 1.3.6.1.4.1.2011.2.25.3.40.50.203.30
        odu0_tcm1Per24HCurTable OBJECT-TYPE
          SYNTAX SEQUENCE OF Odu0_tcm1Per24HCurEntry
          MAX-ACCESS not-accessible
          STATUS current
          DESCRIPTION
              "odu0_tcm1Per24HCur."
          ::= { odu0_tcm1 30 }

        -- 1.3.6.1.4.1.2011.2.25.3.40.50.203.30.1
        odu0_tcm1Per24HCurEntry OBJECT-TYPE
            SYNTAX Odu0_tcm1Per24HCurEntry
            MAX-ACCESS not-accessible
            STATUS current
            DESCRIPTION
              "odu0_tcm1Per24HCur."
            INDEX { odu0_tcm1Per24HCurEid, odu0_tcm1Per24HCurPara }
            ::= { odu0_tcm1Per24HCurTable 1 }

        Odu0_tcm1Per24HCurEntry ::=
            SEQUENCE {
                odu0_tcm1Per24HCurEid
                    PerformanceEventType,
                odu0_tcm1Per24HCurMonValue
                    OCTET STRING,
                odu0_tcm1Per24HCurVldty
                    INTEGER,
                odu0_tcm1Per24HCurDateTime
                    DateAndTime,
                odu0_tcm1Per24HCurParaLen
                    INTEGER,
                odu0_tcm1Per24HCurPara
                    OCTET STRING
            }

        -- 1.3.6.1.4.1.2011.2.25.3.40.50.203.30.1.1
        odu0_tcm1Per24HCurEid OBJECT-TYPE
            SYNTAX PerformanceEventType
            MAX-ACCESS read-only
            STATUS current
            DESCRIPTION
                "perEid."
            ::= { odu0_tcm1Per24HCurEntry 1 }

        -- 1.3.6.1.4.1.2011.2.25.3.40.50.203.30.1.2
        odu0_tcm1Per24HCurMonValue OBJECT-TYPE
            SYNTAX OCTET STRING (SIZE (0..100))
            MAX-ACCESS read-only
            STATUS current
            DESCRIPTION
                "perMonValue."
            ::= { odu0_tcm1Per24HCurEntry 2 }

        -- 1.3.6.1.4.1.2011.2.25.3.40.50.203.30.1.3
        odu0_tcm1Per24HCurVldty OBJECT-TYPE
            SYNTAX INTEGER
            MAX-ACCESS read-only
            STATUS current
            DESCRIPTION
                "perVldty. "
            ::= { odu0_tcm1Per24HCurEntry 3 }

        -- 1.3.6.1.4.1.2011.2.25.3.40.50.203.30.1.4
        odu0_tcm1Per24HCurDateTime OBJECT-TYPE
            SYNTAX DateAndTime
            MAX-ACCESS read-only
            STATUS current
            DESCRIPTION
                "perDateTime. "
            ::= { odu0_tcm1Per24HCurEntry 4 }

        -- 1.3.6.1.4.1.2011.2.25.3.40.50.203.30.1.5
        odu0_tcm1Per24HCurParaLen OBJECT-TYPE
            SYNTAX INTEGER
            MAX-ACCESS read-only
            STATUS current
            DESCRIPTION
                "perParaLen."
            ::= { odu0_tcm1Per24HCurEntry 5 }

        -- 1.3.6.1.4.1.2011.2.25.3.40.50.203.30.1.6
        odu0_tcm1Per24HCurPara OBJECT-TYPE
            SYNTAX OCTET STRING (SIZE (0..100))
            MAX-ACCESS read-only
            STATUS current
            DESCRIPTION
                "perPara."
            ::= { odu0_tcm1Per24HCurEntry 6 }




-- -------------------------------------------------------------------------
-- Perfomance 24-HOUR History Data Table (RTRV-PER-<MOD2>)
-- -------------------------------------------------------------------------
        -- 1.3.6.1.4.1.2011.2.25.3.40.50.203.40
        odu0_tcm1Per24HHisTable OBJECT-TYPE
          SYNTAX SEQUENCE OF Odu0_tcm1Per24HHisEntry
          MAX-ACCESS not-accessible
          STATUS current
          DESCRIPTION
              "odu0_tcm1Per24HHis."
          ::= { odu0_tcm1 40 }

        -- 1.3.6.1.4.1.2011.2.25.3.40.50.203.40.1
        odu0_tcm1Per24HHisEntry OBJECT-TYPE
            SYNTAX Odu0_tcm1Per24HHisEntry
            MAX-ACCESS not-accessible
            STATUS current
            DESCRIPTION
                "odu0_tcm1Per24HHis."
            INDEX {odu0_tcm1Per24HHisEid, odu0_tcm1Per24HHisParaLen, odu0_tcm1Per24HHisPara, odu0_tcm1Per24HHisDateTimeStart, odu0_tcm1Per24HHisDateTimeEnd}
            ::= { odu0_tcm1Per24HHisTable 1 }

        Odu0_tcm1Per24HHisEntry ::=
            SEQUENCE {
                odu0_tcm1Per24HHisEid
                    PerformanceEventType,
                odu0_tcm1Per24HHisParaLen
                    INTEGER,
                odu0_tcm1Per24HHisPara
                    OCTET STRING,
                odu0_tcm1Per24HHisMonValue
                    OCTET STRING,
                odu0_tcm1Per24HHisDateTimeStart
                    DateAndTime,
                odu0_tcm1Per24HHisDateTimeEnd
                    DateAndTime,
                odu0_tcm1Per24HHisVldty
                    INTEGER,
             }

        -- 1.3.6.1.4.1.2011.2.25.3.40.50.203.40.1.1
        odu0_tcm1Per24HHisEid OBJECT-TYPE
            SYNTAX PerformanceEventType
            MAX-ACCESS read-only
            STATUS current
            DESCRIPTION
                "perEid."
            ::= { odu0_tcm1Per24HHisEntry 1 }

        -- 1.3.6.1.4.1.2011.2.25.3.40.50.203.40.1.2
        odu0_tcm1Per24HHisParaLen OBJECT-TYPE
            SYNTAX INTEGER
            MAX-ACCESS read-only
            STATUS current
            DESCRIPTION
                "perParaLen."
            ::= { odu0_tcm1Per24HHisEntry 2 }

        -- 1.3.6.1.4.1.2011.2.25.3.40.50.203.40.1.3
        odu0_tcm1Per24HHisPara OBJECT-TYPE
            SYNTAX OCTET STRING (SIZE (0..100))
            MAX-ACCESS read-only
            STATUS current
            DESCRIPTION
                "perPara."
            ::= { odu0_tcm1Per24HHisEntry 3 }

        -- 1.3.6.1.4.1.2011.2.25.3.40.50.203.40.1.4
        odu0_tcm1Per24HHisMonValue OBJECT-TYPE
            SYNTAX OCTET STRING (SIZE (0..100))
            MAX-ACCESS read-only
            STATUS current
            DESCRIPTION
                "perMonValue."
            ::= { odu0_tcm1Per24HHisEntry 4 }

        -- 1.3.6.1.4.1.2011.2.25.3.40.50.203.40.1.5
        odu0_tcm1Per24HHisDateTimeStart OBJECT-TYPE
            SYNTAX DateAndTime
            MAX-ACCESS read-only
            STATUS current
            DESCRIPTION
                "perDateTimeStart. "
            ::= { odu0_tcm1Per24HHisEntry 5 }

        -- 1.3.6.1.4.1.2011.2.25.3.40.50.203.40.1.6
        odu0_tcm1Per24HHisDateTimeEnd OBJECT-TYPE
            SYNTAX DateAndTime
            MAX-ACCESS read-only
            STATUS current
            DESCRIPTION
                "perDateTimeEnd. "
            ::= { odu0_tcm1Per24HHisEntry 6 }

        -- 1.3.6.1.4.1.2011.2.25.3.40.50.203.40.1.7
        odu0_tcm1Per24HHisVldty OBJECT-TYPE
            SYNTAX INTEGER
            MAX-ACCESS read-only
            STATUS current
            DESCRIPTION
                "perVldty. "
            ::= { odu0_tcm1Per24HHisEntry 7 }




-- Alarm data
      -- 1.3.6.1.4.1.2011.2.25.3.40.50.204
      odu0_tcm2 OBJECT IDENTIFIER ::={ optixGlobalNGWDM 204 }


-- -------------------------------------------------------------------------
-- Perfomance 15-MIN Current Data Table (RTRV-PER-<MOD2>)
-- -------------------------------------------------------------------------
        -- 1.3.6.1.4.1.2011.2.25.3.40.50.204.10
        odu0_tcm2Per15MCurTable OBJECT-TYPE
          SYNTAX SEQUENCE OF Odu0_tcm2Per15MCurEntry
          MAX-ACCESS not-accessible
          STATUS current
          DESCRIPTION
              "odu0_tcm2Per15MCur."
          ::= { odu0_tcm2 10 }

        -- 1.3.6.1.4.1.2011.2.25.3.40.50.204.10.1
        odu0_tcm2Per15MCurEntry OBJECT-TYPE
            SYNTAX Odu0_tcm2Per15MCurEntry
            MAX-ACCESS not-accessible
            STATUS current
            DESCRIPTION
              "odu0_tcm2Per15MCur."
            INDEX { odu0_tcm2Per15MCurEid, odu0_tcm2Per15MCurPara }
            ::= { odu0_tcm2Per15MCurTable 1 }

        Odu0_tcm2Per15MCurEntry ::=
            SEQUENCE {
                odu0_tcm2Per15MCurEid
                    PerformanceEventType,
                odu0_tcm2Per15MCurMonValue
                    OCTET STRING,
                odu0_tcm2Per15MCurVldty
                    INTEGER,
                odu0_tcm2Per15MCurDateTime
                    DateAndTime,
                odu0_tcm2Per15MCurParaLen
                    INTEGER,
                odu0_tcm2Per15MCurPara
                    OCTET STRING
            }

        -- 1.3.6.1.4.1.2011.2.25.3.40.50.204.10.1.1
        odu0_tcm2Per15MCurEid OBJECT-TYPE
            SYNTAX PerformanceEventType
            MAX-ACCESS read-only
            STATUS current
            DESCRIPTION
                "perEid."
            ::= { odu0_tcm2Per15MCurEntry 1 }

        -- 1.3.6.1.4.1.2011.2.25.3.40.50.204.10.1.2
        odu0_tcm2Per15MCurMonValue OBJECT-TYPE
            SYNTAX OCTET STRING (SIZE (0..100))
            MAX-ACCESS read-only
            STATUS current
            DESCRIPTION
                "perMonValue."
            ::= { odu0_tcm2Per15MCurEntry 2 }

        -- 1.3.6.1.4.1.2011.2.25.3.40.50.204.10.1.3
        odu0_tcm2Per15MCurVldty OBJECT-TYPE
            SYNTAX INTEGER
            MAX-ACCESS read-only
            STATUS current
            DESCRIPTION
                "perVldty. "
            ::= { odu0_tcm2Per15MCurEntry 3 }

        -- 1.3.6.1.4.1.2011.2.25.3.40.50.204.10.1.4
        odu0_tcm2Per15MCurDateTime OBJECT-TYPE
            SYNTAX DateAndTime
            MAX-ACCESS read-only
            STATUS current
            DESCRIPTION
                "perDateTime. "
            ::= { odu0_tcm2Per15MCurEntry 4 }

        -- 1.3.6.1.4.1.2011.2.25.3.40.50.204.10.1.5
        odu0_tcm2Per15MCurParaLen OBJECT-TYPE
            SYNTAX INTEGER
            MAX-ACCESS read-only
            STATUS current
            DESCRIPTION
                "perParaLen."
            ::= { odu0_tcm2Per15MCurEntry 5 }

        -- 1.3.6.1.4.1.2011.2.25.3.40.50.204.10.1.6
        odu0_tcm2Per15MCurPara OBJECT-TYPE
            SYNTAX OCTET STRING (SIZE (0..100))
            MAX-ACCESS read-only
            STATUS current
            DESCRIPTION
                "perPara."
            ::= { odu0_tcm2Per15MCurEntry 6 }




-- -------------------------------------------------------------------------
-- Perfomance 15-MIN History Data Table (RTRV-PER-<MOD2>)
-- -------------------------------------------------------------------------
        -- 1.3.6.1.4.1.2011.2.25.3.40.50.204.20
        odu0_tcm2Per15MHisTable OBJECT-TYPE
          SYNTAX SEQUENCE OF Odu0_tcm2Per15MHisEntry
          MAX-ACCESS not-accessible
          STATUS current
          DESCRIPTION
              "odu0_tcm2Per15MHis."
          ::= { odu0_tcm2 20 }

        -- 1.3.6.1.4.1.2011.2.25.3.40.50.204.20.1
        odu0_tcm2Per15MHisEntry OBJECT-TYPE
            SYNTAX Odu0_tcm2Per15MHisEntry
            MAX-ACCESS not-accessible
            STATUS current
            DESCRIPTION
                "odu0_tcm2Per15MHis."
            INDEX {odu0_tcm2Per15MHisEid, odu0_tcm2Per15MHisParaLen, odu0_tcm2Per15MHisPara, odu0_tcm2Per15MHisDateTimeStart, odu0_tcm2Per15MHisDateTimeEnd}
            ::= { odu0_tcm2Per15MHisTable 1 }

        Odu0_tcm2Per15MHisEntry ::=
            SEQUENCE {
                odu0_tcm2Per15MHisEid
                    PerformanceEventType,
                odu0_tcm2Per15MHisParaLen
                    INTEGER,
                odu0_tcm2Per15MHisPara
                    OCTET STRING,
                odu0_tcm2Per15MHisMonValue
                    OCTET STRING,
                odu0_tcm2Per15MHisDateTimeStart
                    DateAndTime,
                odu0_tcm2Per15MHisDateTimeEnd
                    DateAndTime,
                odu0_tcm2Per15MHisVldty
                    INTEGER,
             }

        -- 1.3.6.1.4.1.2011.2.25.3.40.50.204.20.1.1
        odu0_tcm2Per15MHisEid OBJECT-TYPE
            SYNTAX PerformanceEventType
            MAX-ACCESS read-only
            STATUS current
            DESCRIPTION
                "perEid."
            ::= { odu0_tcm2Per15MHisEntry 1 }

        -- 1.3.6.1.4.1.2011.2.25.3.40.50.204.20.1.2
        odu0_tcm2Per15MHisParaLen OBJECT-TYPE
            SYNTAX INTEGER
            MAX-ACCESS read-only
            STATUS current
            DESCRIPTION
                "perParaLen."
            ::= { odu0_tcm2Per15MHisEntry 2 }

        -- 1.3.6.1.4.1.2011.2.25.3.40.50.204.20.1.3
        odu0_tcm2Per15MHisPara OBJECT-TYPE
            SYNTAX OCTET STRING (SIZE (0..100))
            MAX-ACCESS read-only
            STATUS current
            DESCRIPTION
                "perPara."
            ::= { odu0_tcm2Per15MHisEntry 3 }

        -- 1.3.6.1.4.1.2011.2.25.3.40.50.204.20.1.4
        odu0_tcm2Per15MHisMonValue OBJECT-TYPE
            SYNTAX OCTET STRING (SIZE (0..100))
            MAX-ACCESS read-only
            STATUS current
            DESCRIPTION
                "perMonValue."
            ::= { odu0_tcm2Per15MHisEntry 4 }

        -- 1.3.6.1.4.1.2011.2.25.3.40.50.204.20.1.5
        odu0_tcm2Per15MHisDateTimeStart OBJECT-TYPE
            SYNTAX DateAndTime
            MAX-ACCESS read-only
            STATUS current
            DESCRIPTION
                "perDateTimeStart. "
            ::= { odu0_tcm2Per15MHisEntry 5 }

        -- 1.3.6.1.4.1.2011.2.25.3.40.50.204.20.1.6
        odu0_tcm2Per15MHisDateTimeEnd OBJECT-TYPE
            SYNTAX DateAndTime
            MAX-ACCESS read-only
            STATUS current
            DESCRIPTION
                "perDateTimeEnd. "
            ::= { odu0_tcm2Per15MHisEntry 6 }

        -- 1.3.6.1.4.1.2011.2.25.3.40.50.204.20.1.7
        odu0_tcm2Per15MHisVldty OBJECT-TYPE
            SYNTAX INTEGER
            MAX-ACCESS read-only
            STATUS current
            DESCRIPTION
                "perVldty. "
            ::= { odu0_tcm2Per15MHisEntry 7 }




-- -------------------------------------------------------------------------
-- Perfomance 24-HOUR Current Data Table (RTRV-PER-<MOD2>)
-- -------------------------------------------------------------------------
        -- 1.3.6.1.4.1.2011.2.25.3.40.50.204.30
        odu0_tcm2Per24HCurTable OBJECT-TYPE
          SYNTAX SEQUENCE OF Odu0_tcm2Per24HCurEntry
          MAX-ACCESS not-accessible
          STATUS current
          DESCRIPTION
              "odu0_tcm2Per24HCur."
          ::= { odu0_tcm2 30 }

        -- 1.3.6.1.4.1.2011.2.25.3.40.50.204.30.1
        odu0_tcm2Per24HCurEntry OBJECT-TYPE
            SYNTAX Odu0_tcm2Per24HCurEntry
            MAX-ACCESS not-accessible
            STATUS current
            DESCRIPTION
              "odu0_tcm2Per24HCur."
            INDEX { odu0_tcm2Per24HCurEid, odu0_tcm2Per24HCurPara }
            ::= { odu0_tcm2Per24HCurTable 1 }

        Odu0_tcm2Per24HCurEntry ::=
            SEQUENCE {
                odu0_tcm2Per24HCurEid
                    PerformanceEventType,
                odu0_tcm2Per24HCurMonValue
                    OCTET STRING,
                odu0_tcm2Per24HCurVldty
                    INTEGER,
                odu0_tcm2Per24HCurDateTime
                    DateAndTime,
                odu0_tcm2Per24HCurParaLen
                    INTEGER,
                odu0_tcm2Per24HCurPara
                    OCTET STRING
            }

        -- 1.3.6.1.4.1.2011.2.25.3.40.50.204.30.1.1
        odu0_tcm2Per24HCurEid OBJECT-TYPE
            SYNTAX PerformanceEventType
            MAX-ACCESS read-only
            STATUS current
            DESCRIPTION
                "perEid."
            ::= { odu0_tcm2Per24HCurEntry 1 }

        -- 1.3.6.1.4.1.2011.2.25.3.40.50.204.30.1.2
        odu0_tcm2Per24HCurMonValue OBJECT-TYPE
            SYNTAX OCTET STRING (SIZE (0..100))
            MAX-ACCESS read-only
            STATUS current
            DESCRIPTION
                "perMonValue."
            ::= { odu0_tcm2Per24HCurEntry 2 }

        -- 1.3.6.1.4.1.2011.2.25.3.40.50.204.30.1.3
        odu0_tcm2Per24HCurVldty OBJECT-TYPE
            SYNTAX INTEGER
            MAX-ACCESS read-only
            STATUS current
            DESCRIPTION
                "perVldty. "
            ::= { odu0_tcm2Per24HCurEntry 3 }

        -- 1.3.6.1.4.1.2011.2.25.3.40.50.204.30.1.4
        odu0_tcm2Per24HCurDateTime OBJECT-TYPE
            SYNTAX DateAndTime
            MAX-ACCESS read-only
            STATUS current
            DESCRIPTION
                "perDateTime. "
            ::= { odu0_tcm2Per24HCurEntry 4 }

        -- 1.3.6.1.4.1.2011.2.25.3.40.50.204.30.1.5
        odu0_tcm2Per24HCurParaLen OBJECT-TYPE
            SYNTAX INTEGER
            MAX-ACCESS read-only
            STATUS current
            DESCRIPTION
                "perParaLen."
            ::= { odu0_tcm2Per24HCurEntry 5 }

        -- 1.3.6.1.4.1.2011.2.25.3.40.50.204.30.1.6
        odu0_tcm2Per24HCurPara OBJECT-TYPE
            SYNTAX OCTET STRING (SIZE (0..100))
            MAX-ACCESS read-only
            STATUS current
            DESCRIPTION
                "perPara."
            ::= { odu0_tcm2Per24HCurEntry 6 }




-- -------------------------------------------------------------------------
-- Perfomance 24-HOUR History Data Table (RTRV-PER-<MOD2>)
-- -------------------------------------------------------------------------
        -- 1.3.6.1.4.1.2011.2.25.3.40.50.204.40
        odu0_tcm2Per24HHisTable OBJECT-TYPE
          SYNTAX SEQUENCE OF Odu0_tcm2Per24HHisEntry
          MAX-ACCESS not-accessible
          STATUS current
          DESCRIPTION
              "odu0_tcm2Per24HHis."
          ::= { odu0_tcm2 40 }

        -- 1.3.6.1.4.1.2011.2.25.3.40.50.204.40.1
        odu0_tcm2Per24HHisEntry OBJECT-TYPE
            SYNTAX Odu0_tcm2Per24HHisEntry
            MAX-ACCESS not-accessible
            STATUS current
            DESCRIPTION
                "odu0_tcm2Per24HHis."
            INDEX {odu0_tcm2Per24HHisEid, odu0_tcm2Per24HHisParaLen, odu0_tcm2Per24HHisPara, odu0_tcm2Per24HHisDateTimeStart, odu0_tcm2Per24HHisDateTimeEnd}
            ::= { odu0_tcm2Per24HHisTable 1 }

        Odu0_tcm2Per24HHisEntry ::=
            SEQUENCE {
                odu0_tcm2Per24HHisEid
                    PerformanceEventType,
                odu0_tcm2Per24HHisParaLen
                    INTEGER,
                odu0_tcm2Per24HHisPara
                    OCTET STRING,
                odu0_tcm2Per24HHisMonValue
                    OCTET STRING,
                odu0_tcm2Per24HHisDateTimeStart
                    DateAndTime,
                odu0_tcm2Per24HHisDateTimeEnd
                    DateAndTime,
                odu0_tcm2Per24HHisVldty
                    INTEGER,
             }

        -- 1.3.6.1.4.1.2011.2.25.3.40.50.204.40.1.1
        odu0_tcm2Per24HHisEid OBJECT-TYPE
            SYNTAX PerformanceEventType
            MAX-ACCESS read-only
            STATUS current
            DESCRIPTION
                "perEid."
            ::= { odu0_tcm2Per24HHisEntry 1 }

        -- 1.3.6.1.4.1.2011.2.25.3.40.50.204.40.1.2
        odu0_tcm2Per24HHisParaLen OBJECT-TYPE
            SYNTAX INTEGER
            MAX-ACCESS read-only
            STATUS current
            DESCRIPTION
                "perParaLen."
            ::= { odu0_tcm2Per24HHisEntry 2 }

        -- 1.3.6.1.4.1.2011.2.25.3.40.50.204.40.1.3
        odu0_tcm2Per24HHisPara OBJECT-TYPE
            SYNTAX OCTET STRING (SIZE (0..100))
            MAX-ACCESS read-only
            STATUS current
            DESCRIPTION
                "perPara."
            ::= { odu0_tcm2Per24HHisEntry 3 }

        -- 1.3.6.1.4.1.2011.2.25.3.40.50.204.40.1.4
        odu0_tcm2Per24HHisMonValue OBJECT-TYPE
            SYNTAX OCTET STRING (SIZE (0..100))
            MAX-ACCESS read-only
            STATUS current
            DESCRIPTION
                "perMonValue."
            ::= { odu0_tcm2Per24HHisEntry 4 }

        -- 1.3.6.1.4.1.2011.2.25.3.40.50.204.40.1.5
        odu0_tcm2Per24HHisDateTimeStart OBJECT-TYPE
            SYNTAX DateAndTime
            MAX-ACCESS read-only
            STATUS current
            DESCRIPTION
                "perDateTimeStart. "
            ::= { odu0_tcm2Per24HHisEntry 5 }

        -- 1.3.6.1.4.1.2011.2.25.3.40.50.204.40.1.6
        odu0_tcm2Per24HHisDateTimeEnd OBJECT-TYPE
            SYNTAX DateAndTime
            MAX-ACCESS read-only
            STATUS current
            DESCRIPTION
                "perDateTimeEnd. "
            ::= { odu0_tcm2Per24HHisEntry 6 }

        -- 1.3.6.1.4.1.2011.2.25.3.40.50.204.40.1.7
        odu0_tcm2Per24HHisVldty OBJECT-TYPE
            SYNTAX INTEGER
            MAX-ACCESS read-only
            STATUS current
            DESCRIPTION
                "perVldty. "
            ::= { odu0_tcm2Per24HHisEntry 7 }




-- Alarm data
      -- 1.3.6.1.4.1.2011.2.25.3.40.50.205
      odu0_tcm3 OBJECT IDENTIFIER ::={ optixGlobalNGWDM 205 }


-- -------------------------------------------------------------------------
-- Perfomance 15-MIN Current Data Table (RTRV-PER-<MOD2>)
-- -------------------------------------------------------------------------
        -- 1.3.6.1.4.1.2011.2.25.3.40.50.205.10
        odu0_tcm3Per15MCurTable OBJECT-TYPE
          SYNTAX SEQUENCE OF Odu0_tcm3Per15MCurEntry
          MAX-ACCESS not-accessible
          STATUS current
          DESCRIPTION
              "odu0_tcm3Per15MCur."
          ::= { odu0_tcm3 10 }

        -- 1.3.6.1.4.1.2011.2.25.3.40.50.205.10.1
        odu0_tcm3Per15MCurEntry OBJECT-TYPE
            SYNTAX Odu0_tcm3Per15MCurEntry
            MAX-ACCESS not-accessible
            STATUS current
            DESCRIPTION
              "odu0_tcm3Per15MCur."
            INDEX { odu0_tcm3Per15MCurEid, odu0_tcm3Per15MCurPara }
            ::= { odu0_tcm3Per15MCurTable 1 }

        Odu0_tcm3Per15MCurEntry ::=
            SEQUENCE {
                odu0_tcm3Per15MCurEid
                    PerformanceEventType,
                odu0_tcm3Per15MCurMonValue
                    OCTET STRING,
                odu0_tcm3Per15MCurVldty
                    INTEGER,
                odu0_tcm3Per15MCurDateTime
                    DateAndTime,
                odu0_tcm3Per15MCurParaLen
                    INTEGER,
                odu0_tcm3Per15MCurPara
                    OCTET STRING
            }

        -- 1.3.6.1.4.1.2011.2.25.3.40.50.205.10.1.1
        odu0_tcm3Per15MCurEid OBJECT-TYPE
            SYNTAX PerformanceEventType
            MAX-ACCESS read-only
            STATUS current
            DESCRIPTION
                "perEid."
            ::= { odu0_tcm3Per15MCurEntry 1 }

        -- 1.3.6.1.4.1.2011.2.25.3.40.50.205.10.1.2
        odu0_tcm3Per15MCurMonValue OBJECT-TYPE
            SYNTAX OCTET STRING (SIZE (0..100))
            MAX-ACCESS read-only
            STATUS current
            DESCRIPTION
                "perMonValue."
            ::= { odu0_tcm3Per15MCurEntry 2 }

        -- 1.3.6.1.4.1.2011.2.25.3.40.50.205.10.1.3
        odu0_tcm3Per15MCurVldty OBJECT-TYPE
            SYNTAX INTEGER
            MAX-ACCESS read-only
            STATUS current
            DESCRIPTION
                "perVldty. "
            ::= { odu0_tcm3Per15MCurEntry 3 }

        -- 1.3.6.1.4.1.2011.2.25.3.40.50.205.10.1.4
        odu0_tcm3Per15MCurDateTime OBJECT-TYPE
            SYNTAX DateAndTime
            MAX-ACCESS read-only
            STATUS current
            DESCRIPTION
                "perDateTime. "
            ::= { odu0_tcm3Per15MCurEntry 4 }

        -- 1.3.6.1.4.1.2011.2.25.3.40.50.205.10.1.5
        odu0_tcm3Per15MCurParaLen OBJECT-TYPE
            SYNTAX INTEGER
            MAX-ACCESS read-only
            STATUS current
            DESCRIPTION
                "perParaLen."
            ::= { odu0_tcm3Per15MCurEntry 5 }

        -- 1.3.6.1.4.1.2011.2.25.3.40.50.205.10.1.6
        odu0_tcm3Per15MCurPara OBJECT-TYPE
            SYNTAX OCTET STRING (SIZE (0..100))
            MAX-ACCESS read-only
            STATUS current
            DESCRIPTION
                "perPara."
            ::= { odu0_tcm3Per15MCurEntry 6 }




-- -------------------------------------------------------------------------
-- Perfomance 15-MIN History Data Table (RTRV-PER-<MOD2>)
-- -------------------------------------------------------------------------
        -- 1.3.6.1.4.1.2011.2.25.3.40.50.205.20
        odu0_tcm3Per15MHisTable OBJECT-TYPE
          SYNTAX SEQUENCE OF Odu0_tcm3Per15MHisEntry
          MAX-ACCESS not-accessible
          STATUS current
          DESCRIPTION
              "odu0_tcm3Per15MHis."
          ::= { odu0_tcm3 20 }

        -- 1.3.6.1.4.1.2011.2.25.3.40.50.205.20.1
        odu0_tcm3Per15MHisEntry OBJECT-TYPE
            SYNTAX Odu0_tcm3Per15MHisEntry
            MAX-ACCESS not-accessible
            STATUS current
            DESCRIPTION
                "odu0_tcm3Per15MHis."
            INDEX {odu0_tcm3Per15MHisEid, odu0_tcm3Per15MHisParaLen, odu0_tcm3Per15MHisPara, odu0_tcm3Per15MHisDateTimeStart, odu0_tcm3Per15MHisDateTimeEnd}
            ::= { odu0_tcm3Per15MHisTable 1 }

        Odu0_tcm3Per15MHisEntry ::=
            SEQUENCE {
                odu0_tcm3Per15MHisEid
                    PerformanceEventType,
                odu0_tcm3Per15MHisParaLen
                    INTEGER,
                odu0_tcm3Per15MHisPara
                    OCTET STRING,
                odu0_tcm3Per15MHisMonValue
                    OCTET STRING,
                odu0_tcm3Per15MHisDateTimeStart
                    DateAndTime,
                odu0_tcm3Per15MHisDateTimeEnd
                    DateAndTime,
                odu0_tcm3Per15MHisVldty
                    INTEGER,
             }

        -- 1.3.6.1.4.1.2011.2.25.3.40.50.205.20.1.1
        odu0_tcm3Per15MHisEid OBJECT-TYPE
            SYNTAX PerformanceEventType
            MAX-ACCESS read-only
            STATUS current
            DESCRIPTION
                "perEid."
            ::= { odu0_tcm3Per15MHisEntry 1 }

        -- 1.3.6.1.4.1.2011.2.25.3.40.50.205.20.1.2
        odu0_tcm3Per15MHisParaLen OBJECT-TYPE
            SYNTAX INTEGER
            MAX-ACCESS read-only
            STATUS current
            DESCRIPTION
                "perParaLen."
            ::= { odu0_tcm3Per15MHisEntry 2 }

        -- 1.3.6.1.4.1.2011.2.25.3.40.50.205.20.1.3
        odu0_tcm3Per15MHisPara OBJECT-TYPE
            SYNTAX OCTET STRING (SIZE (0..100))
            MAX-ACCESS read-only
            STATUS current
            DESCRIPTION
                "perPara."
            ::= { odu0_tcm3Per15MHisEntry 3 }

        -- 1.3.6.1.4.1.2011.2.25.3.40.50.205.20.1.4
        odu0_tcm3Per15MHisMonValue OBJECT-TYPE
            SYNTAX OCTET STRING (SIZE (0..100))
            MAX-ACCESS read-only
            STATUS current
            DESCRIPTION
                "perMonValue."
            ::= { odu0_tcm3Per15MHisEntry 4 }

        -- 1.3.6.1.4.1.2011.2.25.3.40.50.205.20.1.5
        odu0_tcm3Per15MHisDateTimeStart OBJECT-TYPE
            SYNTAX DateAndTime
            MAX-ACCESS read-only
            STATUS current
            DESCRIPTION
                "perDateTimeStart. "
            ::= { odu0_tcm3Per15MHisEntry 5 }

        -- 1.3.6.1.4.1.2011.2.25.3.40.50.205.20.1.6
        odu0_tcm3Per15MHisDateTimeEnd OBJECT-TYPE
            SYNTAX DateAndTime
            MAX-ACCESS read-only
            STATUS current
            DESCRIPTION
                "perDateTimeEnd. "
            ::= { odu0_tcm3Per15MHisEntry 6 }

        -- 1.3.6.1.4.1.2011.2.25.3.40.50.205.20.1.7
        odu0_tcm3Per15MHisVldty OBJECT-TYPE
            SYNTAX INTEGER
            MAX-ACCESS read-only
            STATUS current
            DESCRIPTION
                "perVldty. "
            ::= { odu0_tcm3Per15MHisEntry 7 }




-- -------------------------------------------------------------------------
-- Perfomance 24-HOUR Current Data Table (RTRV-PER-<MOD2>)
-- -------------------------------------------------------------------------
        -- 1.3.6.1.4.1.2011.2.25.3.40.50.205.30
        odu0_tcm3Per24HCurTable OBJECT-TYPE
          SYNTAX SEQUENCE OF Odu0_tcm3Per24HCurEntry
          MAX-ACCESS not-accessible
          STATUS current
          DESCRIPTION
              "odu0_tcm3Per24HCur."
          ::= { odu0_tcm3 30 }

        -- 1.3.6.1.4.1.2011.2.25.3.40.50.205.30.1
        odu0_tcm3Per24HCurEntry OBJECT-TYPE
            SYNTAX Odu0_tcm3Per24HCurEntry
            MAX-ACCESS not-accessible
            STATUS current
            DESCRIPTION
              "odu0_tcm3Per24HCur."
            INDEX { odu0_tcm3Per24HCurEid, odu0_tcm3Per24HCurPara }
            ::= { odu0_tcm3Per24HCurTable 1 }

        Odu0_tcm3Per24HCurEntry ::=
            SEQUENCE {
                odu0_tcm3Per24HCurEid
                    PerformanceEventType,
                odu0_tcm3Per24HCurMonValue
                    OCTET STRING,
                odu0_tcm3Per24HCurVldty
                    INTEGER,
                odu0_tcm3Per24HCurDateTime
                    DateAndTime,
                odu0_tcm3Per24HCurParaLen
                    INTEGER,
                odu0_tcm3Per24HCurPara
                    OCTET STRING
            }

        -- 1.3.6.1.4.1.2011.2.25.3.40.50.205.30.1.1
        odu0_tcm3Per24HCurEid OBJECT-TYPE
            SYNTAX PerformanceEventType
            MAX-ACCESS read-only
            STATUS current
            DESCRIPTION
                "perEid."
            ::= { odu0_tcm3Per24HCurEntry 1 }

        -- 1.3.6.1.4.1.2011.2.25.3.40.50.205.30.1.2
        odu0_tcm3Per24HCurMonValue OBJECT-TYPE
            SYNTAX OCTET STRING (SIZE (0..100))
            MAX-ACCESS read-only
            STATUS current
            DESCRIPTION
                "perMonValue."
            ::= { odu0_tcm3Per24HCurEntry 2 }

        -- 1.3.6.1.4.1.2011.2.25.3.40.50.205.30.1.3
        odu0_tcm3Per24HCurVldty OBJECT-TYPE
            SYNTAX INTEGER
            MAX-ACCESS read-only
            STATUS current
            DESCRIPTION
                "perVldty. "
            ::= { odu0_tcm3Per24HCurEntry 3 }

        -- 1.3.6.1.4.1.2011.2.25.3.40.50.205.30.1.4
        odu0_tcm3Per24HCurDateTime OBJECT-TYPE
            SYNTAX DateAndTime
            MAX-ACCESS read-only
            STATUS current
            DESCRIPTION
                "perDateTime. "
            ::= { odu0_tcm3Per24HCurEntry 4 }

        -- 1.3.6.1.4.1.2011.2.25.3.40.50.205.30.1.5
        odu0_tcm3Per24HCurParaLen OBJECT-TYPE
            SYNTAX INTEGER
            MAX-ACCESS read-only
            STATUS current
            DESCRIPTION
                "perParaLen."
            ::= { odu0_tcm3Per24HCurEntry 5 }

        -- 1.3.6.1.4.1.2011.2.25.3.40.50.205.30.1.6
        odu0_tcm3Per24HCurPara OBJECT-TYPE
            SYNTAX OCTET STRING (SIZE (0..100))
            MAX-ACCESS read-only
            STATUS current
            DESCRIPTION
                "perPara."
            ::= { odu0_tcm3Per24HCurEntry 6 }




-- -------------------------------------------------------------------------
-- Perfomance 24-HOUR History Data Table (RTRV-PER-<MOD2>)
-- -------------------------------------------------------------------------
        -- 1.3.6.1.4.1.2011.2.25.3.40.50.205.40
        odu0_tcm3Per24HHisTable OBJECT-TYPE
          SYNTAX SEQUENCE OF Odu0_tcm3Per24HHisEntry
          MAX-ACCESS not-accessible
          STATUS current
          DESCRIPTION
              "odu0_tcm3Per24HHis."
          ::= { odu0_tcm3 40 }

        -- 1.3.6.1.4.1.2011.2.25.3.40.50.205.40.1
        odu0_tcm3Per24HHisEntry OBJECT-TYPE
            SYNTAX Odu0_tcm3Per24HHisEntry
            MAX-ACCESS not-accessible
            STATUS current
            DESCRIPTION
                "odu0_tcm3Per24HHis."
            INDEX {odu0_tcm3Per24HHisEid, odu0_tcm3Per24HHisParaLen, odu0_tcm3Per24HHisPara, odu0_tcm3Per24HHisDateTimeStart, odu0_tcm3Per24HHisDateTimeEnd}
            ::= { odu0_tcm3Per24HHisTable 1 }

        Odu0_tcm3Per24HHisEntry ::=
            SEQUENCE {
                odu0_tcm3Per24HHisEid
                    PerformanceEventType,
                odu0_tcm3Per24HHisParaLen
                    INTEGER,
                odu0_tcm3Per24HHisPara
                    OCTET STRING,
                odu0_tcm3Per24HHisMonValue
                    OCTET STRING,
                odu0_tcm3Per24HHisDateTimeStart
                    DateAndTime,
                odu0_tcm3Per24HHisDateTimeEnd
                    DateAndTime,
                odu0_tcm3Per24HHisVldty
                    INTEGER,
             }

        -- 1.3.6.1.4.1.2011.2.25.3.40.50.205.40.1.1
        odu0_tcm3Per24HHisEid OBJECT-TYPE
            SYNTAX PerformanceEventType
            MAX-ACCESS read-only
            STATUS current
            DESCRIPTION
                "perEid."
            ::= { odu0_tcm3Per24HHisEntry 1 }

        -- 1.3.6.1.4.1.2011.2.25.3.40.50.205.40.1.2
        odu0_tcm3Per24HHisParaLen OBJECT-TYPE
            SYNTAX INTEGER
            MAX-ACCESS read-only
            STATUS current
            DESCRIPTION
                "perParaLen."
            ::= { odu0_tcm3Per24HHisEntry 2 }

        -- 1.3.6.1.4.1.2011.2.25.3.40.50.205.40.1.3
        odu0_tcm3Per24HHisPara OBJECT-TYPE
            SYNTAX OCTET STRING (SIZE (0..100))
            MAX-ACCESS read-only
            STATUS current
            DESCRIPTION
                "perPara."
            ::= { odu0_tcm3Per24HHisEntry 3 }

        -- 1.3.6.1.4.1.2011.2.25.3.40.50.205.40.1.4
        odu0_tcm3Per24HHisMonValue OBJECT-TYPE
            SYNTAX OCTET STRING (SIZE (0..100))
            MAX-ACCESS read-only
            STATUS current
            DESCRIPTION
                "perMonValue."
            ::= { odu0_tcm3Per24HHisEntry 4 }

        -- 1.3.6.1.4.1.2011.2.25.3.40.50.205.40.1.5
        odu0_tcm3Per24HHisDateTimeStart OBJECT-TYPE
            SYNTAX DateAndTime
            MAX-ACCESS read-only
            STATUS current
            DESCRIPTION
                "perDateTimeStart. "
            ::= { odu0_tcm3Per24HHisEntry 5 }

        -- 1.3.6.1.4.1.2011.2.25.3.40.50.205.40.1.6
        odu0_tcm3Per24HHisDateTimeEnd OBJECT-TYPE
            SYNTAX DateAndTime
            MAX-ACCESS read-only
            STATUS current
            DESCRIPTION
                "perDateTimeEnd. "
            ::= { odu0_tcm3Per24HHisEntry 6 }

        -- 1.3.6.1.4.1.2011.2.25.3.40.50.205.40.1.7
        odu0_tcm3Per24HHisVldty OBJECT-TYPE
            SYNTAX INTEGER
            MAX-ACCESS read-only
            STATUS current
            DESCRIPTION
                "perVldty. "
            ::= { odu0_tcm3Per24HHisEntry 7 }




-- Alarm data
      -- 1.3.6.1.4.1.2011.2.25.3.40.50.206
      odu0_tcm4 OBJECT IDENTIFIER ::={ optixGlobalNGWDM 206 }


-- -------------------------------------------------------------------------
-- Perfomance 15-MIN Current Data Table (RTRV-PER-<MOD2>)
-- -------------------------------------------------------------------------
        -- 1.3.6.1.4.1.2011.2.25.3.40.50.206.10
        odu0_tcm4Per15MCurTable OBJECT-TYPE
          SYNTAX SEQUENCE OF Odu0_tcm4Per15MCurEntry
          MAX-ACCESS not-accessible
          STATUS current
          DESCRIPTION
              "odu0_tcm4Per15MCur."
          ::= { odu0_tcm4 10 }

        -- 1.3.6.1.4.1.2011.2.25.3.40.50.206.10.1
        odu0_tcm4Per15MCurEntry OBJECT-TYPE
            SYNTAX Odu0_tcm4Per15MCurEntry
            MAX-ACCESS not-accessible
            STATUS current
            DESCRIPTION
              "odu0_tcm4Per15MCur."
            INDEX { odu0_tcm4Per15MCurEid, odu0_tcm4Per15MCurPara }
            ::= { odu0_tcm4Per15MCurTable 1 }

        Odu0_tcm4Per15MCurEntry ::=
            SEQUENCE {
                odu0_tcm4Per15MCurEid
                    PerformanceEventType,
                odu0_tcm4Per15MCurMonValue
                    OCTET STRING,
                odu0_tcm4Per15MCurVldty
                    INTEGER,
                odu0_tcm4Per15MCurDateTime
                    DateAndTime,
                odu0_tcm4Per15MCurParaLen
                    INTEGER,
                odu0_tcm4Per15MCurPara
                    OCTET STRING
            }

        -- 1.3.6.1.4.1.2011.2.25.3.40.50.206.10.1.1
        odu0_tcm4Per15MCurEid OBJECT-TYPE
            SYNTAX PerformanceEventType
            MAX-ACCESS read-only
            STATUS current
            DESCRIPTION
                "perEid."
            ::= { odu0_tcm4Per15MCurEntry 1 }

        -- 1.3.6.1.4.1.2011.2.25.3.40.50.206.10.1.2
        odu0_tcm4Per15MCurMonValue OBJECT-TYPE
            SYNTAX OCTET STRING (SIZE (0..100))
            MAX-ACCESS read-only
            STATUS current
            DESCRIPTION
                "perMonValue."
            ::= { odu0_tcm4Per15MCurEntry 2 }

        -- 1.3.6.1.4.1.2011.2.25.3.40.50.206.10.1.3
        odu0_tcm4Per15MCurVldty OBJECT-TYPE
            SYNTAX INTEGER
            MAX-ACCESS read-only
            STATUS current
            DESCRIPTION
                "perVldty. "
            ::= { odu0_tcm4Per15MCurEntry 3 }

        -- 1.3.6.1.4.1.2011.2.25.3.40.50.206.10.1.4
        odu0_tcm4Per15MCurDateTime OBJECT-TYPE
            SYNTAX DateAndTime
            MAX-ACCESS read-only
            STATUS current
            DESCRIPTION
                "perDateTime. "
            ::= { odu0_tcm4Per15MCurEntry 4 }

        -- 1.3.6.1.4.1.2011.2.25.3.40.50.206.10.1.5
        odu0_tcm4Per15MCurParaLen OBJECT-TYPE
            SYNTAX INTEGER
            MAX-ACCESS read-only
            STATUS current
            DESCRIPTION
                "perParaLen."
            ::= { odu0_tcm4Per15MCurEntry 5 }

        -- 1.3.6.1.4.1.2011.2.25.3.40.50.206.10.1.6
        odu0_tcm4Per15MCurPara OBJECT-TYPE
            SYNTAX OCTET STRING (SIZE (0..100))
            MAX-ACCESS read-only
            STATUS current
            DESCRIPTION
                "perPara."
            ::= { odu0_tcm4Per15MCurEntry 6 }




-- -------------------------------------------------------------------------
-- Perfomance 15-MIN History Data Table (RTRV-PER-<MOD2>)
-- -------------------------------------------------------------------------
        -- 1.3.6.1.4.1.2011.2.25.3.40.50.206.20
        odu0_tcm4Per15MHisTable OBJECT-TYPE
          SYNTAX SEQUENCE OF Odu0_tcm4Per15MHisEntry
          MAX-ACCESS not-accessible
          STATUS current
          DESCRIPTION
              "odu0_tcm4Per15MHis."
          ::= { odu0_tcm4 20 }

        -- 1.3.6.1.4.1.2011.2.25.3.40.50.206.20.1
        odu0_tcm4Per15MHisEntry OBJECT-TYPE
            SYNTAX Odu0_tcm4Per15MHisEntry
            MAX-ACCESS not-accessible
            STATUS current
            DESCRIPTION
                "odu0_tcm4Per15MHis."
            INDEX {odu0_tcm4Per15MHisEid, odu0_tcm4Per15MHisParaLen, odu0_tcm4Per15MHisPara, odu0_tcm4Per15MHisDateTimeStart, odu0_tcm4Per15MHisDateTimeEnd}
            ::= { odu0_tcm4Per15MHisTable 1 }

        Odu0_tcm4Per15MHisEntry ::=
            SEQUENCE {
                odu0_tcm4Per15MHisEid
                    PerformanceEventType,
                odu0_tcm4Per15MHisParaLen
                    INTEGER,
                odu0_tcm4Per15MHisPara
                    OCTET STRING,
                odu0_tcm4Per15MHisMonValue
                    OCTET STRING,
                odu0_tcm4Per15MHisDateTimeStart
                    DateAndTime,
                odu0_tcm4Per15MHisDateTimeEnd
                    DateAndTime,
                odu0_tcm4Per15MHisVldty
                    INTEGER,
             }

        -- 1.3.6.1.4.1.2011.2.25.3.40.50.206.20.1.1
        odu0_tcm4Per15MHisEid OBJECT-TYPE
            SYNTAX PerformanceEventType
            MAX-ACCESS read-only
            STATUS current
            DESCRIPTION
                "perEid."
            ::= { odu0_tcm4Per15MHisEntry 1 }

        -- 1.3.6.1.4.1.2011.2.25.3.40.50.206.20.1.2
        odu0_tcm4Per15MHisParaLen OBJECT-TYPE
            SYNTAX INTEGER
            MAX-ACCESS read-only
            STATUS current
            DESCRIPTION
                "perParaLen."
            ::= { odu0_tcm4Per15MHisEntry 2 }

        -- 1.3.6.1.4.1.2011.2.25.3.40.50.206.20.1.3
        odu0_tcm4Per15MHisPara OBJECT-TYPE
            SYNTAX OCTET STRING (SIZE (0..100))
            MAX-ACCESS read-only
            STATUS current
            DESCRIPTION
                "perPara."
            ::= { odu0_tcm4Per15MHisEntry 3 }

        -- 1.3.6.1.4.1.2011.2.25.3.40.50.206.20.1.4
        odu0_tcm4Per15MHisMonValue OBJECT-TYPE
            SYNTAX OCTET STRING (SIZE (0..100))
            MAX-ACCESS read-only
            STATUS current
            DESCRIPTION
                "perMonValue."
            ::= { odu0_tcm4Per15MHisEntry 4 }

        -- 1.3.6.1.4.1.2011.2.25.3.40.50.206.20.1.5
        odu0_tcm4Per15MHisDateTimeStart OBJECT-TYPE
            SYNTAX DateAndTime
            MAX-ACCESS read-only
            STATUS current
            DESCRIPTION
                "perDateTimeStart. "
            ::= { odu0_tcm4Per15MHisEntry 5 }

        -- 1.3.6.1.4.1.2011.2.25.3.40.50.206.20.1.6
        odu0_tcm4Per15MHisDateTimeEnd OBJECT-TYPE
            SYNTAX DateAndTime
            MAX-ACCESS read-only
            STATUS current
            DESCRIPTION
                "perDateTimeEnd. "
            ::= { odu0_tcm4Per15MHisEntry 6 }

        -- 1.3.6.1.4.1.2011.2.25.3.40.50.206.20.1.7
        odu0_tcm4Per15MHisVldty OBJECT-TYPE
            SYNTAX INTEGER
            MAX-ACCESS read-only
            STATUS current
            DESCRIPTION
                "perVldty. "
            ::= { odu0_tcm4Per15MHisEntry 7 }




-- -------------------------------------------------------------------------
-- Perfomance 24-HOUR Current Data Table (RTRV-PER-<MOD2>)
-- -------------------------------------------------------------------------
        -- 1.3.6.1.4.1.2011.2.25.3.40.50.206.30
        odu0_tcm4Per24HCurTable OBJECT-TYPE
          SYNTAX SEQUENCE OF Odu0_tcm4Per24HCurEntry
          MAX-ACCESS not-accessible
          STATUS current
          DESCRIPTION
              "odu0_tcm4Per24HCur."
          ::= { odu0_tcm4 30 }

        -- 1.3.6.1.4.1.2011.2.25.3.40.50.206.30.1
        odu0_tcm4Per24HCurEntry OBJECT-TYPE
            SYNTAX Odu0_tcm4Per24HCurEntry
            MAX-ACCESS not-accessible
            STATUS current
            DESCRIPTION
              "odu0_tcm4Per24HCur."
            INDEX { odu0_tcm4Per24HCurEid, odu0_tcm4Per24HCurPara }
            ::= { odu0_tcm4Per24HCurTable 1 }

        Odu0_tcm4Per24HCurEntry ::=
            SEQUENCE {
                odu0_tcm4Per24HCurEid
                    PerformanceEventType,
                odu0_tcm4Per24HCurMonValue
                    OCTET STRING,
                odu0_tcm4Per24HCurVldty
                    INTEGER,
                odu0_tcm4Per24HCurDateTime
                    DateAndTime,
                odu0_tcm4Per24HCurParaLen
                    INTEGER,
                odu0_tcm4Per24HCurPara
                    OCTET STRING
            }

        -- 1.3.6.1.4.1.2011.2.25.3.40.50.206.30.1.1
        odu0_tcm4Per24HCurEid OBJECT-TYPE
            SYNTAX PerformanceEventType
            MAX-ACCESS read-only
            STATUS current
            DESCRIPTION
                "perEid."
            ::= { odu0_tcm4Per24HCurEntry 1 }

        -- 1.3.6.1.4.1.2011.2.25.3.40.50.206.30.1.2
        odu0_tcm4Per24HCurMonValue OBJECT-TYPE
            SYNTAX OCTET STRING (SIZE (0..100))
            MAX-ACCESS read-only
            STATUS current
            DESCRIPTION
                "perMonValue."
            ::= { odu0_tcm4Per24HCurEntry 2 }

        -- 1.3.6.1.4.1.2011.2.25.3.40.50.206.30.1.3
        odu0_tcm4Per24HCurVldty OBJECT-TYPE
            SYNTAX INTEGER
            MAX-ACCESS read-only
            STATUS current
            DESCRIPTION
                "perVldty. "
            ::= { odu0_tcm4Per24HCurEntry 3 }

        -- 1.3.6.1.4.1.2011.2.25.3.40.50.206.30.1.4
        odu0_tcm4Per24HCurDateTime OBJECT-TYPE
            SYNTAX DateAndTime
            MAX-ACCESS read-only
            STATUS current
            DESCRIPTION
                "perDateTime. "
            ::= { odu0_tcm4Per24HCurEntry 4 }

        -- 1.3.6.1.4.1.2011.2.25.3.40.50.206.30.1.5
        odu0_tcm4Per24HCurParaLen OBJECT-TYPE
            SYNTAX INTEGER
            MAX-ACCESS read-only
            STATUS current
            DESCRIPTION
                "perParaLen."
            ::= { odu0_tcm4Per24HCurEntry 5 }

        -- 1.3.6.1.4.1.2011.2.25.3.40.50.206.30.1.6
        odu0_tcm4Per24HCurPara OBJECT-TYPE
            SYNTAX OCTET STRING (SIZE (0..100))
            MAX-ACCESS read-only
            STATUS current
            DESCRIPTION
                "perPara."
            ::= { odu0_tcm4Per24HCurEntry 6 }




-- -------------------------------------------------------------------------
-- Perfomance 24-HOUR History Data Table (RTRV-PER-<MOD2>)
-- -------------------------------------------------------------------------
        -- 1.3.6.1.4.1.2011.2.25.3.40.50.206.40
        odu0_tcm4Per24HHisTable OBJECT-TYPE
          SYNTAX SEQUENCE OF Odu0_tcm4Per24HHisEntry
          MAX-ACCESS not-accessible
          STATUS current
          DESCRIPTION
              "odu0_tcm4Per24HHis."
          ::= { odu0_tcm4 40 }

        -- 1.3.6.1.4.1.2011.2.25.3.40.50.206.40.1
        odu0_tcm4Per24HHisEntry OBJECT-TYPE
            SYNTAX Odu0_tcm4Per24HHisEntry
            MAX-ACCESS not-accessible
            STATUS current
            DESCRIPTION
                "odu0_tcm4Per24HHis."
            INDEX {odu0_tcm4Per24HHisEid, odu0_tcm4Per24HHisParaLen, odu0_tcm4Per24HHisPara, odu0_tcm4Per24HHisDateTimeStart, odu0_tcm4Per24HHisDateTimeEnd}
            ::= { odu0_tcm4Per24HHisTable 1 }

        Odu0_tcm4Per24HHisEntry ::=
            SEQUENCE {
                odu0_tcm4Per24HHisEid
                    PerformanceEventType,
                odu0_tcm4Per24HHisParaLen
                    INTEGER,
                odu0_tcm4Per24HHisPara
                    OCTET STRING,
                odu0_tcm4Per24HHisMonValue
                    OCTET STRING,
                odu0_tcm4Per24HHisDateTimeStart
                    DateAndTime,
                odu0_tcm4Per24HHisDateTimeEnd
                    DateAndTime,
                odu0_tcm4Per24HHisVldty
                    INTEGER,
             }

        -- 1.3.6.1.4.1.2011.2.25.3.40.50.206.40.1.1
        odu0_tcm4Per24HHisEid OBJECT-TYPE
            SYNTAX PerformanceEventType
            MAX-ACCESS read-only
            STATUS current
            DESCRIPTION
                "perEid."
            ::= { odu0_tcm4Per24HHisEntry 1 }

        -- 1.3.6.1.4.1.2011.2.25.3.40.50.206.40.1.2
        odu0_tcm4Per24HHisParaLen OBJECT-TYPE
            SYNTAX INTEGER
            MAX-ACCESS read-only
            STATUS current
            DESCRIPTION
                "perParaLen."
            ::= { odu0_tcm4Per24HHisEntry 2 }

        -- 1.3.6.1.4.1.2011.2.25.3.40.50.206.40.1.3
        odu0_tcm4Per24HHisPara OBJECT-TYPE
            SYNTAX OCTET STRING (SIZE (0..100))
            MAX-ACCESS read-only
            STATUS current
            DESCRIPTION
                "perPara."
            ::= { odu0_tcm4Per24HHisEntry 3 }

        -- 1.3.6.1.4.1.2011.2.25.3.40.50.206.40.1.4
        odu0_tcm4Per24HHisMonValue OBJECT-TYPE
            SYNTAX OCTET STRING (SIZE (0..100))
            MAX-ACCESS read-only
            STATUS current
            DESCRIPTION
                "perMonValue."
            ::= { odu0_tcm4Per24HHisEntry 4 }

        -- 1.3.6.1.4.1.2011.2.25.3.40.50.206.40.1.5
        odu0_tcm4Per24HHisDateTimeStart OBJECT-TYPE
            SYNTAX DateAndTime
            MAX-ACCESS read-only
            STATUS current
            DESCRIPTION
                "perDateTimeStart. "
            ::= { odu0_tcm4Per24HHisEntry 5 }

        -- 1.3.6.1.4.1.2011.2.25.3.40.50.206.40.1.6
        odu0_tcm4Per24HHisDateTimeEnd OBJECT-TYPE
            SYNTAX DateAndTime
            MAX-ACCESS read-only
            STATUS current
            DESCRIPTION
                "perDateTimeEnd. "
            ::= { odu0_tcm4Per24HHisEntry 6 }

        -- 1.3.6.1.4.1.2011.2.25.3.40.50.206.40.1.7
        odu0_tcm4Per24HHisVldty OBJECT-TYPE
            SYNTAX INTEGER
            MAX-ACCESS read-only
            STATUS current
            DESCRIPTION
                "perVldty. "
            ::= { odu0_tcm4Per24HHisEntry 7 }




-- Alarm data
      -- 1.3.6.1.4.1.2011.2.25.3.40.50.207
      odu0_tcm5 OBJECT IDENTIFIER ::={ optixGlobalNGWDM 207 }


-- -------------------------------------------------------------------------
-- Perfomance 15-MIN Current Data Table (RTRV-PER-<MOD2>)
-- -------------------------------------------------------------------------
        -- 1.3.6.1.4.1.2011.2.25.3.40.50.207.10
        odu0_tcm5Per15MCurTable OBJECT-TYPE
          SYNTAX SEQUENCE OF Odu0_tcm5Per15MCurEntry
          MAX-ACCESS not-accessible
          STATUS current
          DESCRIPTION
              "odu0_tcm5Per15MCur."
          ::= { odu0_tcm5 10 }

        -- 1.3.6.1.4.1.2011.2.25.3.40.50.207.10.1
        odu0_tcm5Per15MCurEntry OBJECT-TYPE
            SYNTAX Odu0_tcm5Per15MCurEntry
            MAX-ACCESS not-accessible
            STATUS current
            DESCRIPTION
              "odu0_tcm5Per15MCur."
            INDEX { odu0_tcm5Per15MCurEid, odu0_tcm5Per15MCurPara }
            ::= { odu0_tcm5Per15MCurTable 1 }

        Odu0_tcm5Per15MCurEntry ::=
            SEQUENCE {
                odu0_tcm5Per15MCurEid
                    PerformanceEventType,
                odu0_tcm5Per15MCurMonValue
                    OCTET STRING,
                odu0_tcm5Per15MCurVldty
                    INTEGER,
                odu0_tcm5Per15MCurDateTime
                    DateAndTime,
                odu0_tcm5Per15MCurParaLen
                    INTEGER,
                odu0_tcm5Per15MCurPara
                    OCTET STRING
            }

        -- 1.3.6.1.4.1.2011.2.25.3.40.50.207.10.1.1
        odu0_tcm5Per15MCurEid OBJECT-TYPE
            SYNTAX PerformanceEventType
            MAX-ACCESS read-only
            STATUS current
            DESCRIPTION
                "perEid."
            ::= { odu0_tcm5Per15MCurEntry 1 }

        -- 1.3.6.1.4.1.2011.2.25.3.40.50.207.10.1.2
        odu0_tcm5Per15MCurMonValue OBJECT-TYPE
            SYNTAX OCTET STRING (SIZE (0..100))
            MAX-ACCESS read-only
            STATUS current
            DESCRIPTION
                "perMonValue."
            ::= { odu0_tcm5Per15MCurEntry 2 }

        -- 1.3.6.1.4.1.2011.2.25.3.40.50.207.10.1.3
        odu0_tcm5Per15MCurVldty OBJECT-TYPE
            SYNTAX INTEGER
            MAX-ACCESS read-only
            STATUS current
            DESCRIPTION
                "perVldty. "
            ::= { odu0_tcm5Per15MCurEntry 3 }

        -- 1.3.6.1.4.1.2011.2.25.3.40.50.207.10.1.4
        odu0_tcm5Per15MCurDateTime OBJECT-TYPE
            SYNTAX DateAndTime
            MAX-ACCESS read-only
            STATUS current
            DESCRIPTION
                "perDateTime. "
            ::= { odu0_tcm5Per15MCurEntry 4 }

        -- 1.3.6.1.4.1.2011.2.25.3.40.50.207.10.1.5
        odu0_tcm5Per15MCurParaLen OBJECT-TYPE
            SYNTAX INTEGER
            MAX-ACCESS read-only
            STATUS current
            DESCRIPTION
                "perParaLen."
            ::= { odu0_tcm5Per15MCurEntry 5 }

        -- 1.3.6.1.4.1.2011.2.25.3.40.50.207.10.1.6
        odu0_tcm5Per15MCurPara OBJECT-TYPE
            SYNTAX OCTET STRING (SIZE (0..100))
            MAX-ACCESS read-only
            STATUS current
            DESCRIPTION
                "perPara."
            ::= { odu0_tcm5Per15MCurEntry 6 }




-- -------------------------------------------------------------------------
-- Perfomance 15-MIN History Data Table (RTRV-PER-<MOD2>)
-- -------------------------------------------------------------------------
        -- 1.3.6.1.4.1.2011.2.25.3.40.50.207.20
        odu0_tcm5Per15MHisTable OBJECT-TYPE
          SYNTAX SEQUENCE OF Odu0_tcm5Per15MHisEntry
          MAX-ACCESS not-accessible
          STATUS current
          DESCRIPTION
              "odu0_tcm5Per15MHis."
          ::= { odu0_tcm5 20 }

        -- 1.3.6.1.4.1.2011.2.25.3.40.50.207.20.1
        odu0_tcm5Per15MHisEntry OBJECT-TYPE
            SYNTAX Odu0_tcm5Per15MHisEntry
            MAX-ACCESS not-accessible
            STATUS current
            DESCRIPTION
                "odu0_tcm5Per15MHis."
            INDEX {odu0_tcm5Per15MHisEid, odu0_tcm5Per15MHisParaLen, odu0_tcm5Per15MHisPara, odu0_tcm5Per15MHisDateTimeStart, odu0_tcm5Per15MHisDateTimeEnd}
            ::= { odu0_tcm5Per15MHisTable 1 }

        Odu0_tcm5Per15MHisEntry ::=
            SEQUENCE {
                odu0_tcm5Per15MHisEid
                    PerformanceEventType,
                odu0_tcm5Per15MHisParaLen
                    INTEGER,
                odu0_tcm5Per15MHisPara
                    OCTET STRING,
                odu0_tcm5Per15MHisMonValue
                    OCTET STRING,
                odu0_tcm5Per15MHisDateTimeStart
                    DateAndTime,
                odu0_tcm5Per15MHisDateTimeEnd
                    DateAndTime,
                odu0_tcm5Per15MHisVldty
                    INTEGER,
             }

        -- 1.3.6.1.4.1.2011.2.25.3.40.50.207.20.1.1
        odu0_tcm5Per15MHisEid OBJECT-TYPE
            SYNTAX PerformanceEventType
            MAX-ACCESS read-only
            STATUS current
            DESCRIPTION
                "perEid."
            ::= { odu0_tcm5Per15MHisEntry 1 }

        -- 1.3.6.1.4.1.2011.2.25.3.40.50.207.20.1.2
        odu0_tcm5Per15MHisParaLen OBJECT-TYPE
            SYNTAX INTEGER
            MAX-ACCESS read-only
            STATUS current
            DESCRIPTION
                "perParaLen."
            ::= { odu0_tcm5Per15MHisEntry 2 }

        -- 1.3.6.1.4.1.2011.2.25.3.40.50.207.20.1.3
        odu0_tcm5Per15MHisPara OBJECT-TYPE
            SYNTAX OCTET STRING (SIZE (0..100))
            MAX-ACCESS read-only
            STATUS current
            DESCRIPTION
                "perPara."
            ::= { odu0_tcm5Per15MHisEntry 3 }

        -- 1.3.6.1.4.1.2011.2.25.3.40.50.207.20.1.4
        odu0_tcm5Per15MHisMonValue OBJECT-TYPE
            SYNTAX OCTET STRING (SIZE (0..100))
            MAX-ACCESS read-only
            STATUS current
            DESCRIPTION
                "perMonValue."
            ::= { odu0_tcm5Per15MHisEntry 4 }

        -- 1.3.6.1.4.1.2011.2.25.3.40.50.207.20.1.5
        odu0_tcm5Per15MHisDateTimeStart OBJECT-TYPE
            SYNTAX DateAndTime
            MAX-ACCESS read-only
            STATUS current
            DESCRIPTION
                "perDateTimeStart. "
            ::= { odu0_tcm5Per15MHisEntry 5 }

        -- 1.3.6.1.4.1.2011.2.25.3.40.50.207.20.1.6
        odu0_tcm5Per15MHisDateTimeEnd OBJECT-TYPE
            SYNTAX DateAndTime
            MAX-ACCESS read-only
            STATUS current
            DESCRIPTION
                "perDateTimeEnd. "
            ::= { odu0_tcm5Per15MHisEntry 6 }

        -- 1.3.6.1.4.1.2011.2.25.3.40.50.207.20.1.7
        odu0_tcm5Per15MHisVldty OBJECT-TYPE
            SYNTAX INTEGER
            MAX-ACCESS read-only
            STATUS current
            DESCRIPTION
                "perVldty. "
            ::= { odu0_tcm5Per15MHisEntry 7 }




-- -------------------------------------------------------------------------
-- Perfomance 24-HOUR Current Data Table (RTRV-PER-<MOD2>)
-- -------------------------------------------------------------------------
        -- 1.3.6.1.4.1.2011.2.25.3.40.50.207.30
        odu0_tcm5Per24HCurTable OBJECT-TYPE
          SYNTAX SEQUENCE OF Odu0_tcm5Per24HCurEntry
          MAX-ACCESS not-accessible
          STATUS current
          DESCRIPTION
              "odu0_tcm5Per24HCur."
          ::= { odu0_tcm5 30 }

        -- 1.3.6.1.4.1.2011.2.25.3.40.50.207.30.1
        odu0_tcm5Per24HCurEntry OBJECT-TYPE
            SYNTAX Odu0_tcm5Per24HCurEntry
            MAX-ACCESS not-accessible
            STATUS current
            DESCRIPTION
              "odu0_tcm5Per24HCur."
            INDEX { odu0_tcm5Per24HCurEid, odu0_tcm5Per24HCurPara }
            ::= { odu0_tcm5Per24HCurTable 1 }

        Odu0_tcm5Per24HCurEntry ::=
            SEQUENCE {
                odu0_tcm5Per24HCurEid
                    PerformanceEventType,
                odu0_tcm5Per24HCurMonValue
                    OCTET STRING,
                odu0_tcm5Per24HCurVldty
                    INTEGER,
                odu0_tcm5Per24HCurDateTime
                    DateAndTime,
                odu0_tcm5Per24HCurParaLen
                    INTEGER,
                odu0_tcm5Per24HCurPara
                    OCTET STRING
            }

        -- 1.3.6.1.4.1.2011.2.25.3.40.50.207.30.1.1
        odu0_tcm5Per24HCurEid OBJECT-TYPE
            SYNTAX PerformanceEventType
            MAX-ACCESS read-only
            STATUS current
            DESCRIPTION
                "perEid."
            ::= { odu0_tcm5Per24HCurEntry 1 }

        -- 1.3.6.1.4.1.2011.2.25.3.40.50.207.30.1.2
        odu0_tcm5Per24HCurMonValue OBJECT-TYPE
            SYNTAX OCTET STRING (SIZE (0..100))
            MAX-ACCESS read-only
            STATUS current
            DESCRIPTION
                "perMonValue."
            ::= { odu0_tcm5Per24HCurEntry 2 }

        -- 1.3.6.1.4.1.2011.2.25.3.40.50.207.30.1.3
        odu0_tcm5Per24HCurVldty OBJECT-TYPE
            SYNTAX INTEGER
            MAX-ACCESS read-only
            STATUS current
            DESCRIPTION
                "perVldty. "
            ::= { odu0_tcm5Per24HCurEntry 3 }

        -- 1.3.6.1.4.1.2011.2.25.3.40.50.207.30.1.4
        odu0_tcm5Per24HCurDateTime OBJECT-TYPE
            SYNTAX DateAndTime
            MAX-ACCESS read-only
            STATUS current
            DESCRIPTION
                "perDateTime. "
            ::= { odu0_tcm5Per24HCurEntry 4 }

        -- 1.3.6.1.4.1.2011.2.25.3.40.50.207.30.1.5
        odu0_tcm5Per24HCurParaLen OBJECT-TYPE
            SYNTAX INTEGER
            MAX-ACCESS read-only
            STATUS current
            DESCRIPTION
                "perParaLen."
            ::= { odu0_tcm5Per24HCurEntry 5 }

        -- 1.3.6.1.4.1.2011.2.25.3.40.50.207.30.1.6
        odu0_tcm5Per24HCurPara OBJECT-TYPE
            SYNTAX OCTET STRING (SIZE (0..100))
            MAX-ACCESS read-only
            STATUS current
            DESCRIPTION
                "perPara."
            ::= { odu0_tcm5Per24HCurEntry 6 }




-- -------------------------------------------------------------------------
-- Perfomance 24-HOUR History Data Table (RTRV-PER-<MOD2>)
-- -------------------------------------------------------------------------
        -- 1.3.6.1.4.1.2011.2.25.3.40.50.207.40
        odu0_tcm5Per24HHisTable OBJECT-TYPE
          SYNTAX SEQUENCE OF Odu0_tcm5Per24HHisEntry
          MAX-ACCESS not-accessible
          STATUS current
          DESCRIPTION
              "odu0_tcm5Per24HHis."
          ::= { odu0_tcm5 40 }

        -- 1.3.6.1.4.1.2011.2.25.3.40.50.207.40.1
        odu0_tcm5Per24HHisEntry OBJECT-TYPE
            SYNTAX Odu0_tcm5Per24HHisEntry
            MAX-ACCESS not-accessible
            STATUS current
            DESCRIPTION
                "odu0_tcm5Per24HHis."
            INDEX {odu0_tcm5Per24HHisEid, odu0_tcm5Per24HHisParaLen, odu0_tcm5Per24HHisPara, odu0_tcm5Per24HHisDateTimeStart, odu0_tcm5Per24HHisDateTimeEnd}
            ::= { odu0_tcm5Per24HHisTable 1 }

        Odu0_tcm5Per24HHisEntry ::=
            SEQUENCE {
                odu0_tcm5Per24HHisEid
                    PerformanceEventType,
                odu0_tcm5Per24HHisParaLen
                    INTEGER,
                odu0_tcm5Per24HHisPara
                    OCTET STRING,
                odu0_tcm5Per24HHisMonValue
                    OCTET STRING,
                odu0_tcm5Per24HHisDateTimeStart
                    DateAndTime,
                odu0_tcm5Per24HHisDateTimeEnd
                    DateAndTime,
                odu0_tcm5Per24HHisVldty
                    INTEGER,
             }

        -- 1.3.6.1.4.1.2011.2.25.3.40.50.207.40.1.1
        odu0_tcm5Per24HHisEid OBJECT-TYPE
            SYNTAX PerformanceEventType
            MAX-ACCESS read-only
            STATUS current
            DESCRIPTION
                "perEid."
            ::= { odu0_tcm5Per24HHisEntry 1 }

        -- 1.3.6.1.4.1.2011.2.25.3.40.50.207.40.1.2
        odu0_tcm5Per24HHisParaLen OBJECT-TYPE
            SYNTAX INTEGER
            MAX-ACCESS read-only
            STATUS current
            DESCRIPTION
                "perParaLen."
            ::= { odu0_tcm5Per24HHisEntry 2 }

        -- 1.3.6.1.4.1.2011.2.25.3.40.50.207.40.1.3
        odu0_tcm5Per24HHisPara OBJECT-TYPE
            SYNTAX OCTET STRING (SIZE (0..100))
            MAX-ACCESS read-only
            STATUS current
            DESCRIPTION
                "perPara."
            ::= { odu0_tcm5Per24HHisEntry 3 }

        -- 1.3.6.1.4.1.2011.2.25.3.40.50.207.40.1.4
        odu0_tcm5Per24HHisMonValue OBJECT-TYPE
            SYNTAX OCTET STRING (SIZE (0..100))
            MAX-ACCESS read-only
            STATUS current
            DESCRIPTION
                "perMonValue."
            ::= { odu0_tcm5Per24HHisEntry 4 }

        -- 1.3.6.1.4.1.2011.2.25.3.40.50.207.40.1.5
        odu0_tcm5Per24HHisDateTimeStart OBJECT-TYPE
            SYNTAX DateAndTime
            MAX-ACCESS read-only
            STATUS current
            DESCRIPTION
                "perDateTimeStart. "
            ::= { odu0_tcm5Per24HHisEntry 5 }

        -- 1.3.6.1.4.1.2011.2.25.3.40.50.207.40.1.6
        odu0_tcm5Per24HHisDateTimeEnd OBJECT-TYPE
            SYNTAX DateAndTime
            MAX-ACCESS read-only
            STATUS current
            DESCRIPTION
                "perDateTimeEnd. "
            ::= { odu0_tcm5Per24HHisEntry 6 }

        -- 1.3.6.1.4.1.2011.2.25.3.40.50.207.40.1.7
        odu0_tcm5Per24HHisVldty OBJECT-TYPE
            SYNTAX INTEGER
            MAX-ACCESS read-only
            STATUS current
            DESCRIPTION
                "perVldty. "
            ::= { odu0_tcm5Per24HHisEntry 7 }




-- Alarm data
      -- 1.3.6.1.4.1.2011.2.25.3.40.50.208
      odu0_tcm6 OBJECT IDENTIFIER ::={ optixGlobalNGWDM 208 }


-- -------------------------------------------------------------------------
-- Perfomance 15-MIN Current Data Table (RTRV-PER-<MOD2>)
-- -------------------------------------------------------------------------
        -- 1.3.6.1.4.1.2011.2.25.3.40.50.208.10
        odu0_tcm6Per15MCurTable OBJECT-TYPE
          SYNTAX SEQUENCE OF Odu0_tcm6Per15MCurEntry
          MAX-ACCESS not-accessible
          STATUS current
          DESCRIPTION
              "odu0_tcm6Per15MCur."
          ::= { odu0_tcm6 10 }

        -- 1.3.6.1.4.1.2011.2.25.3.40.50.208.10.1
        odu0_tcm6Per15MCurEntry OBJECT-TYPE
            SYNTAX Odu0_tcm6Per15MCurEntry
            MAX-ACCESS not-accessible
            STATUS current
            DESCRIPTION
              "odu0_tcm6Per15MCur."
            INDEX { odu0_tcm6Per15MCurEid, odu0_tcm6Per15MCurPara }
            ::= { odu0_tcm6Per15MCurTable 1 }

        Odu0_tcm6Per15MCurEntry ::=
            SEQUENCE {
                odu0_tcm6Per15MCurEid
                    PerformanceEventType,
                odu0_tcm6Per15MCurMonValue
                    OCTET STRING,
                odu0_tcm6Per15MCurVldty
                    INTEGER,
                odu0_tcm6Per15MCurDateTime
                    DateAndTime,
                odu0_tcm6Per15MCurParaLen
                    INTEGER,
                odu0_tcm6Per15MCurPara
                    OCTET STRING
            }

        -- 1.3.6.1.4.1.2011.2.25.3.40.50.208.10.1.1
        odu0_tcm6Per15MCurEid OBJECT-TYPE
            SYNTAX PerformanceEventType
            MAX-ACCESS read-only
            STATUS current
            DESCRIPTION
                "perEid."
            ::= { odu0_tcm6Per15MCurEntry 1 }

        -- 1.3.6.1.4.1.2011.2.25.3.40.50.208.10.1.2
        odu0_tcm6Per15MCurMonValue OBJECT-TYPE
            SYNTAX OCTET STRING (SIZE (0..100))
            MAX-ACCESS read-only
            STATUS current
            DESCRIPTION
                "perMonValue."
            ::= { odu0_tcm6Per15MCurEntry 2 }

        -- 1.3.6.1.4.1.2011.2.25.3.40.50.208.10.1.3
        odu0_tcm6Per15MCurVldty OBJECT-TYPE
            SYNTAX INTEGER
            MAX-ACCESS read-only
            STATUS current
            DESCRIPTION
                "perVldty. "
            ::= { odu0_tcm6Per15MCurEntry 3 }

        -- 1.3.6.1.4.1.2011.2.25.3.40.50.208.10.1.4
        odu0_tcm6Per15MCurDateTime OBJECT-TYPE
            SYNTAX DateAndTime
            MAX-ACCESS read-only
            STATUS current
            DESCRIPTION
                "perDateTime. "
            ::= { odu0_tcm6Per15MCurEntry 4 }

        -- 1.3.6.1.4.1.2011.2.25.3.40.50.208.10.1.5
        odu0_tcm6Per15MCurParaLen OBJECT-TYPE
            SYNTAX INTEGER
            MAX-ACCESS read-only
            STATUS current
            DESCRIPTION
                "perParaLen."
            ::= { odu0_tcm6Per15MCurEntry 5 }

        -- 1.3.6.1.4.1.2011.2.25.3.40.50.208.10.1.6
        odu0_tcm6Per15MCurPara OBJECT-TYPE
            SYNTAX OCTET STRING (SIZE (0..100))
            MAX-ACCESS read-only
            STATUS current
            DESCRIPTION
                "perPara."
            ::= { odu0_tcm6Per15MCurEntry 6 }




-- -------------------------------------------------------------------------
-- Perfomance 15-MIN History Data Table (RTRV-PER-<MOD2>)
-- -------------------------------------------------------------------------
        -- 1.3.6.1.4.1.2011.2.25.3.40.50.208.20
        odu0_tcm6Per15MHisTable OBJECT-TYPE
          SYNTAX SEQUENCE OF Odu0_tcm6Per15MHisEntry
          MAX-ACCESS not-accessible
          STATUS current
          DESCRIPTION
              "odu0_tcm6Per15MHis."
          ::= { odu0_tcm6 20 }

        -- 1.3.6.1.4.1.2011.2.25.3.40.50.208.20.1
        odu0_tcm6Per15MHisEntry OBJECT-TYPE
            SYNTAX Odu0_tcm6Per15MHisEntry
            MAX-ACCESS not-accessible
            STATUS current
            DESCRIPTION
                "odu0_tcm6Per15MHis."
            INDEX {odu0_tcm6Per15MHisEid, odu0_tcm6Per15MHisParaLen, odu0_tcm6Per15MHisPara, odu0_tcm6Per15MHisDateTimeStart, odu0_tcm6Per15MHisDateTimeEnd}
            ::= { odu0_tcm6Per15MHisTable 1 }

        Odu0_tcm6Per15MHisEntry ::=
            SEQUENCE {
                odu0_tcm6Per15MHisEid
                    PerformanceEventType,
                odu0_tcm6Per15MHisParaLen
                    INTEGER,
                odu0_tcm6Per15MHisPara
                    OCTET STRING,
                odu0_tcm6Per15MHisMonValue
                    OCTET STRING,
                odu0_tcm6Per15MHisDateTimeStart
                    DateAndTime,
                odu0_tcm6Per15MHisDateTimeEnd
                    DateAndTime,
                odu0_tcm6Per15MHisVldty
                    INTEGER,
             }

        -- 1.3.6.1.4.1.2011.2.25.3.40.50.208.20.1.1
        odu0_tcm6Per15MHisEid OBJECT-TYPE
            SYNTAX PerformanceEventType
            MAX-ACCESS read-only
            STATUS current
            DESCRIPTION
                "perEid."
            ::= { odu0_tcm6Per15MHisEntry 1 }

        -- 1.3.6.1.4.1.2011.2.25.3.40.50.208.20.1.2
        odu0_tcm6Per15MHisParaLen OBJECT-TYPE
            SYNTAX INTEGER
            MAX-ACCESS read-only
            STATUS current
            DESCRIPTION
                "perParaLen."
            ::= { odu0_tcm6Per15MHisEntry 2 }

        -- 1.3.6.1.4.1.2011.2.25.3.40.50.208.20.1.3
        odu0_tcm6Per15MHisPara OBJECT-TYPE
            SYNTAX OCTET STRING (SIZE (0..100))
            MAX-ACCESS read-only
            STATUS current
            DESCRIPTION
                "perPara."
            ::= { odu0_tcm6Per15MHisEntry 3 }

        -- 1.3.6.1.4.1.2011.2.25.3.40.50.208.20.1.4
        odu0_tcm6Per15MHisMonValue OBJECT-TYPE
            SYNTAX OCTET STRING (SIZE (0..100))
            MAX-ACCESS read-only
            STATUS current
            DESCRIPTION
                "perMonValue."
            ::= { odu0_tcm6Per15MHisEntry 4 }

        -- 1.3.6.1.4.1.2011.2.25.3.40.50.208.20.1.5
        odu0_tcm6Per15MHisDateTimeStart OBJECT-TYPE
            SYNTAX DateAndTime
            MAX-ACCESS read-only
            STATUS current
            DESCRIPTION
                "perDateTimeStart. "
            ::= { odu0_tcm6Per15MHisEntry 5 }

        -- 1.3.6.1.4.1.2011.2.25.3.40.50.208.20.1.6
        odu0_tcm6Per15MHisDateTimeEnd OBJECT-TYPE
            SYNTAX DateAndTime
            MAX-ACCESS read-only
            STATUS current
            DESCRIPTION
                "perDateTimeEnd. "
            ::= { odu0_tcm6Per15MHisEntry 6 }

        -- 1.3.6.1.4.1.2011.2.25.3.40.50.208.20.1.7
        odu0_tcm6Per15MHisVldty OBJECT-TYPE
            SYNTAX INTEGER
            MAX-ACCESS read-only
            STATUS current
            DESCRIPTION
                "perVldty. "
            ::= { odu0_tcm6Per15MHisEntry 7 }




-- -------------------------------------------------------------------------
-- Perfomance 24-HOUR Current Data Table (RTRV-PER-<MOD2>)
-- -------------------------------------------------------------------------
        -- 1.3.6.1.4.1.2011.2.25.3.40.50.208.30
        odu0_tcm6Per24HCurTable OBJECT-TYPE
          SYNTAX SEQUENCE OF Odu0_tcm6Per24HCurEntry
          MAX-ACCESS not-accessible
          STATUS current
          DESCRIPTION
              "odu0_tcm6Per24HCur."
          ::= { odu0_tcm6 30 }

        -- 1.3.6.1.4.1.2011.2.25.3.40.50.208.30.1
        odu0_tcm6Per24HCurEntry OBJECT-TYPE
            SYNTAX Odu0_tcm6Per24HCurEntry
            MAX-ACCESS not-accessible
            STATUS current
            DESCRIPTION
              "odu0_tcm6Per24HCur."
            INDEX { odu0_tcm6Per24HCurEid, odu0_tcm6Per24HCurPara }
            ::= { odu0_tcm6Per24HCurTable 1 }

        Odu0_tcm6Per24HCurEntry ::=
            SEQUENCE {
                odu0_tcm6Per24HCurEid
                    PerformanceEventType,
                odu0_tcm6Per24HCurMonValue
                    OCTET STRING,
                odu0_tcm6Per24HCurVldty
                    INTEGER,
                odu0_tcm6Per24HCurDateTime
                    DateAndTime,
                odu0_tcm6Per24HCurParaLen
                    INTEGER,
                odu0_tcm6Per24HCurPara
                    OCTET STRING
            }

        -- 1.3.6.1.4.1.2011.2.25.3.40.50.208.30.1.1
        odu0_tcm6Per24HCurEid OBJECT-TYPE
            SYNTAX PerformanceEventType
            MAX-ACCESS read-only
            STATUS current
            DESCRIPTION
                "perEid."
            ::= { odu0_tcm6Per24HCurEntry 1 }

        -- 1.3.6.1.4.1.2011.2.25.3.40.50.208.30.1.2
        odu0_tcm6Per24HCurMonValue OBJECT-TYPE
            SYNTAX OCTET STRING (SIZE (0..100))
            MAX-ACCESS read-only
            STATUS current
            DESCRIPTION
                "perMonValue."
            ::= { odu0_tcm6Per24HCurEntry 2 }

        -- 1.3.6.1.4.1.2011.2.25.3.40.50.208.30.1.3
        odu0_tcm6Per24HCurVldty OBJECT-TYPE
            SYNTAX INTEGER
            MAX-ACCESS read-only
            STATUS current
            DESCRIPTION
                "perVldty. "
            ::= { odu0_tcm6Per24HCurEntry 3 }

        -- 1.3.6.1.4.1.2011.2.25.3.40.50.208.30.1.4
        odu0_tcm6Per24HCurDateTime OBJECT-TYPE
            SYNTAX DateAndTime
            MAX-ACCESS read-only
            STATUS current
            DESCRIPTION
                "perDateTime. "
            ::= { odu0_tcm6Per24HCurEntry 4 }

        -- 1.3.6.1.4.1.2011.2.25.3.40.50.208.30.1.5
        odu0_tcm6Per24HCurParaLen OBJECT-TYPE
            SYNTAX INTEGER
            MAX-ACCESS read-only
            STATUS current
            DESCRIPTION
                "perParaLen."
            ::= { odu0_tcm6Per24HCurEntry 5 }

        -- 1.3.6.1.4.1.2011.2.25.3.40.50.208.30.1.6
        odu0_tcm6Per24HCurPara OBJECT-TYPE
            SYNTAX OCTET STRING (SIZE (0..100))
            MAX-ACCESS read-only
            STATUS current
            DESCRIPTION
                "perPara."
            ::= { odu0_tcm6Per24HCurEntry 6 }




-- -------------------------------------------------------------------------
-- Perfomance 24-HOUR History Data Table (RTRV-PER-<MOD2>)
-- -------------------------------------------------------------------------
        -- 1.3.6.1.4.1.2011.2.25.3.40.50.208.40
        odu0_tcm6Per24HHisTable OBJECT-TYPE
          SYNTAX SEQUENCE OF Odu0_tcm6Per24HHisEntry
          MAX-ACCESS not-accessible
          STATUS current
          DESCRIPTION
              "odu0_tcm6Per24HHis."
          ::= { odu0_tcm6 40 }

        -- 1.3.6.1.4.1.2011.2.25.3.40.50.208.40.1
        odu0_tcm6Per24HHisEntry OBJECT-TYPE
            SYNTAX Odu0_tcm6Per24HHisEntry
            MAX-ACCESS not-accessible
            STATUS current
            DESCRIPTION
                "odu0_tcm6Per24HHis."
            INDEX {odu0_tcm6Per24HHisEid, odu0_tcm6Per24HHisParaLen, odu0_tcm6Per24HHisPara, odu0_tcm6Per24HHisDateTimeStart, odu0_tcm6Per24HHisDateTimeEnd}
            ::= { odu0_tcm6Per24HHisTable 1 }

        Odu0_tcm6Per24HHisEntry ::=
            SEQUENCE {
                odu0_tcm6Per24HHisEid
                    PerformanceEventType,
                odu0_tcm6Per24HHisParaLen
                    INTEGER,
                odu0_tcm6Per24HHisPara
                    OCTET STRING,
                odu0_tcm6Per24HHisMonValue
                    OCTET STRING,
                odu0_tcm6Per24HHisDateTimeStart
                    DateAndTime,
                odu0_tcm6Per24HHisDateTimeEnd
                    DateAndTime,
                odu0_tcm6Per24HHisVldty
                    INTEGER,
             }

        -- 1.3.6.1.4.1.2011.2.25.3.40.50.208.40.1.1
        odu0_tcm6Per24HHisEid OBJECT-TYPE
            SYNTAX PerformanceEventType
            MAX-ACCESS read-only
            STATUS current
            DESCRIPTION
                "perEid."
            ::= { odu0_tcm6Per24HHisEntry 1 }

        -- 1.3.6.1.4.1.2011.2.25.3.40.50.208.40.1.2
        odu0_tcm6Per24HHisParaLen OBJECT-TYPE
            SYNTAX INTEGER
            MAX-ACCESS read-only
            STATUS current
            DESCRIPTION
                "perParaLen."
            ::= { odu0_tcm6Per24HHisEntry 2 }

        -- 1.3.6.1.4.1.2011.2.25.3.40.50.208.40.1.3
        odu0_tcm6Per24HHisPara OBJECT-TYPE
            SYNTAX OCTET STRING (SIZE (0..100))
            MAX-ACCESS read-only
            STATUS current
            DESCRIPTION
                "perPara."
            ::= { odu0_tcm6Per24HHisEntry 3 }

        -- 1.3.6.1.4.1.2011.2.25.3.40.50.208.40.1.4
        odu0_tcm6Per24HHisMonValue OBJECT-TYPE
            SYNTAX OCTET STRING (SIZE (0..100))
            MAX-ACCESS read-only
            STATUS current
            DESCRIPTION
                "perMonValue."
            ::= { odu0_tcm6Per24HHisEntry 4 }

        -- 1.3.6.1.4.1.2011.2.25.3.40.50.208.40.1.5
        odu0_tcm6Per24HHisDateTimeStart OBJECT-TYPE
            SYNTAX DateAndTime
            MAX-ACCESS read-only
            STATUS current
            DESCRIPTION
                "perDateTimeStart. "
            ::= { odu0_tcm6Per24HHisEntry 5 }

        -- 1.3.6.1.4.1.2011.2.25.3.40.50.208.40.1.6
        odu0_tcm6Per24HHisDateTimeEnd OBJECT-TYPE
            SYNTAX DateAndTime
            MAX-ACCESS read-only
            STATUS current
            DESCRIPTION
                "perDateTimeEnd. "
            ::= { odu0_tcm6Per24HHisEntry 6 }

        -- 1.3.6.1.4.1.2011.2.25.3.40.50.208.40.1.7
        odu0_tcm6Per24HHisVldty OBJECT-TYPE
            SYNTAX INTEGER
            MAX-ACCESS read-only
            STATUS current
            DESCRIPTION
                "perVldty. "
            ::= { odu0_tcm6Per24HHisEntry 7 }




-- Alarm data
      -- 1.3.6.1.4.1.2011.2.25.3.40.50.234
      oduflex_tcm1 OBJECT IDENTIFIER ::={ optixGlobalNGWDM 234 }


-- -------------------------------------------------------------------------
-- Perfomance 15-MIN Current Data Table (RTRV-PER-<MOD2>)
-- -------------------------------------------------------------------------
        -- 1.3.6.1.4.1.2011.2.25.3.40.50.234.10
        oduflex_tcm1Per15MCurTable OBJECT-TYPE
          SYNTAX SEQUENCE OF Oduflex_tcm1Per15MCurEntry
          MAX-ACCESS not-accessible
          STATUS current
          DESCRIPTION
              "oduflex_tcm1Per15MCur."
          ::= { oduflex_tcm1 10 }

        -- 1.3.6.1.4.1.2011.2.25.3.40.50.234.10.1
        oduflex_tcm1Per15MCurEntry OBJECT-TYPE
            SYNTAX Oduflex_tcm1Per15MCurEntry
            MAX-ACCESS not-accessible
            STATUS current
            DESCRIPTION
              "oduflex_tcm1Per15MCur."
            INDEX { oduflex_tcm1Per15MCurEid, oduflex_tcm1Per15MCurPara }
            ::= { oduflex_tcm1Per15MCurTable 1 }

        Oduflex_tcm1Per15MCurEntry ::=
            SEQUENCE {
                oduflex_tcm1Per15MCurEid
                    PerformanceEventType,
                oduflex_tcm1Per15MCurMonValue
                    OCTET STRING,
                oduflex_tcm1Per15MCurVldty
                    INTEGER,
                oduflex_tcm1Per15MCurDateTime
                    DateAndTime,
                oduflex_tcm1Per15MCurParaLen
                    INTEGER,
                oduflex_tcm1Per15MCurPara
                    OCTET STRING
            }

        -- 1.3.6.1.4.1.2011.2.25.3.40.50.234.10.1.1
        oduflex_tcm1Per15MCurEid OBJECT-TYPE
            SYNTAX PerformanceEventType
            MAX-ACCESS read-only
            STATUS current
            DESCRIPTION
                "perEid."
            ::= { oduflex_tcm1Per15MCurEntry 1 }

        -- 1.3.6.1.4.1.2011.2.25.3.40.50.234.10.1.2
        oduflex_tcm1Per15MCurMonValue OBJECT-TYPE
            SYNTAX OCTET STRING (SIZE (0..100))
            MAX-ACCESS read-only
            STATUS current
            DESCRIPTION
                "perMonValue."
            ::= { oduflex_tcm1Per15MCurEntry 2 }

        -- 1.3.6.1.4.1.2011.2.25.3.40.50.234.10.1.3
        oduflex_tcm1Per15MCurVldty OBJECT-TYPE
            SYNTAX INTEGER
            MAX-ACCESS read-only
            STATUS current
            DESCRIPTION
                "perVldty. "
            ::= { oduflex_tcm1Per15MCurEntry 3 }

        -- 1.3.6.1.4.1.2011.2.25.3.40.50.234.10.1.4
        oduflex_tcm1Per15MCurDateTime OBJECT-TYPE
            SYNTAX DateAndTime
            MAX-ACCESS read-only
            STATUS current
            DESCRIPTION
                "perDateTime. "
            ::= { oduflex_tcm1Per15MCurEntry 4 }

        -- 1.3.6.1.4.1.2011.2.25.3.40.50.234.10.1.5
        oduflex_tcm1Per15MCurParaLen OBJECT-TYPE
            SYNTAX INTEGER
            MAX-ACCESS read-only
            STATUS current
            DESCRIPTION
                "perParaLen."
            ::= { oduflex_tcm1Per15MCurEntry 5 }

        -- 1.3.6.1.4.1.2011.2.25.3.40.50.234.10.1.6
        oduflex_tcm1Per15MCurPara OBJECT-TYPE
            SYNTAX OCTET STRING (SIZE (0..100))
            MAX-ACCESS read-only
            STATUS current
            DESCRIPTION
                "perPara."
            ::= { oduflex_tcm1Per15MCurEntry 6 }




-- -------------------------------------------------------------------------
-- Perfomance 15-MIN History Data Table (RTRV-PER-<MOD2>)
-- -------------------------------------------------------------------------
        -- 1.3.6.1.4.1.2011.2.25.3.40.50.234.20
        oduflex_tcm1Per15MHisTable OBJECT-TYPE
          SYNTAX SEQUENCE OF Oduflex_tcm1Per15MHisEntry
          MAX-ACCESS not-accessible
          STATUS current
          DESCRIPTION
              "oduflex_tcm1Per15MHis."
          ::= { oduflex_tcm1 20 }

        -- 1.3.6.1.4.1.2011.2.25.3.40.50.234.20.1
        oduflex_tcm1Per15MHisEntry OBJECT-TYPE
            SYNTAX Oduflex_tcm1Per15MHisEntry
            MAX-ACCESS not-accessible
            STATUS current
            DESCRIPTION
                "oduflex_tcm1Per15MHis."
            INDEX {oduflex_tcm1Per15MHisEid, oduflex_tcm1Per15MHisParaLen, oduflex_tcm1Per15MHisPara, oduflex_tcm1Per15MHisDateTimeStart, oduflex_tcm1Per15MHisDateTimeEnd}
            ::= { oduflex_tcm1Per15MHisTable 1 }

        Oduflex_tcm1Per15MHisEntry ::=
            SEQUENCE {
                oduflex_tcm1Per15MHisEid
                    PerformanceEventType,
                oduflex_tcm1Per15MHisParaLen
                    INTEGER,
                oduflex_tcm1Per15MHisPara
                    OCTET STRING,
                oduflex_tcm1Per15MHisMonValue
                    OCTET STRING,
                oduflex_tcm1Per15MHisDateTimeStart
                    DateAndTime,
                oduflex_tcm1Per15MHisDateTimeEnd
                    DateAndTime,
                oduflex_tcm1Per15MHisVldty
                    INTEGER,
             }

        -- 1.3.6.1.4.1.2011.2.25.3.40.50.234.20.1.1
        oduflex_tcm1Per15MHisEid OBJECT-TYPE
            SYNTAX PerformanceEventType
            MAX-ACCESS read-only
            STATUS current
            DESCRIPTION
                "perEid."
            ::= { oduflex_tcm1Per15MHisEntry 1 }

        -- 1.3.6.1.4.1.2011.2.25.3.40.50.234.20.1.2
        oduflex_tcm1Per15MHisParaLen OBJECT-TYPE
            SYNTAX INTEGER
            MAX-ACCESS read-only
            STATUS current
            DESCRIPTION
                "perParaLen."
            ::= { oduflex_tcm1Per15MHisEntry 2 }

        -- 1.3.6.1.4.1.2011.2.25.3.40.50.234.20.1.3
        oduflex_tcm1Per15MHisPara OBJECT-TYPE
            SYNTAX OCTET STRING (SIZE (0..100))
            MAX-ACCESS read-only
            STATUS current
            DESCRIPTION
                "perPara."
            ::= { oduflex_tcm1Per15MHisEntry 3 }

        -- 1.3.6.1.4.1.2011.2.25.3.40.50.234.20.1.4
        oduflex_tcm1Per15MHisMonValue OBJECT-TYPE
            SYNTAX OCTET STRING (SIZE (0..100))
            MAX-ACCESS read-only
            STATUS current
            DESCRIPTION
                "perMonValue."
            ::= { oduflex_tcm1Per15MHisEntry 4 }

        -- 1.3.6.1.4.1.2011.2.25.3.40.50.234.20.1.5
        oduflex_tcm1Per15MHisDateTimeStart OBJECT-TYPE
            SYNTAX DateAndTime
            MAX-ACCESS read-only
            STATUS current
            DESCRIPTION
                "perDateTimeStart. "
            ::= { oduflex_tcm1Per15MHisEntry 5 }

        -- 1.3.6.1.4.1.2011.2.25.3.40.50.234.20.1.6
        oduflex_tcm1Per15MHisDateTimeEnd OBJECT-TYPE
            SYNTAX DateAndTime
            MAX-ACCESS read-only
            STATUS current
            DESCRIPTION
                "perDateTimeEnd. "
            ::= { oduflex_tcm1Per15MHisEntry 6 }

        -- 1.3.6.1.4.1.2011.2.25.3.40.50.234.20.1.7
        oduflex_tcm1Per15MHisVldty OBJECT-TYPE
            SYNTAX INTEGER
            MAX-ACCESS read-only
            STATUS current
            DESCRIPTION
                "perVldty. "
            ::= { oduflex_tcm1Per15MHisEntry 7 }




-- -------------------------------------------------------------------------
-- Perfomance 24-HOUR Current Data Table (RTRV-PER-<MOD2>)
-- -------------------------------------------------------------------------
        -- 1.3.6.1.4.1.2011.2.25.3.40.50.234.30
        oduflex_tcm1Per24HCurTable OBJECT-TYPE
          SYNTAX SEQUENCE OF Oduflex_tcm1Per24HCurEntry
          MAX-ACCESS not-accessible
          STATUS current
          DESCRIPTION
              "oduflex_tcm1Per24HCur."
          ::= { oduflex_tcm1 30 }

        -- 1.3.6.1.4.1.2011.2.25.3.40.50.234.30.1
        oduflex_tcm1Per24HCurEntry OBJECT-TYPE
            SYNTAX Oduflex_tcm1Per24HCurEntry
            MAX-ACCESS not-accessible
            STATUS current
            DESCRIPTION
              "oduflex_tcm1Per24HCur."
            INDEX { oduflex_tcm1Per24HCurEid, oduflex_tcm1Per24HCurPara }
            ::= { oduflex_tcm1Per24HCurTable 1 }

        Oduflex_tcm1Per24HCurEntry ::=
            SEQUENCE {
                oduflex_tcm1Per24HCurEid
                    PerformanceEventType,
                oduflex_tcm1Per24HCurMonValue
                    OCTET STRING,
                oduflex_tcm1Per24HCurVldty
                    INTEGER,
                oduflex_tcm1Per24HCurDateTime
                    DateAndTime,
                oduflex_tcm1Per24HCurParaLen
                    INTEGER,
                oduflex_tcm1Per24HCurPara
                    OCTET STRING
            }

        -- 1.3.6.1.4.1.2011.2.25.3.40.50.234.30.1.1
        oduflex_tcm1Per24HCurEid OBJECT-TYPE
            SYNTAX PerformanceEventType
            MAX-ACCESS read-only
            STATUS current
            DESCRIPTION
                "perEid."
            ::= { oduflex_tcm1Per24HCurEntry 1 }

        -- 1.3.6.1.4.1.2011.2.25.3.40.50.234.30.1.2
        oduflex_tcm1Per24HCurMonValue OBJECT-TYPE
            SYNTAX OCTET STRING (SIZE (0..100))
            MAX-ACCESS read-only
            STATUS current
            DESCRIPTION
                "perMonValue."
            ::= { oduflex_tcm1Per24HCurEntry 2 }

        -- 1.3.6.1.4.1.2011.2.25.3.40.50.234.30.1.3
        oduflex_tcm1Per24HCurVldty OBJECT-TYPE
            SYNTAX INTEGER
            MAX-ACCESS read-only
            STATUS current
            DESCRIPTION
                "perVldty. "
            ::= { oduflex_tcm1Per24HCurEntry 3 }

        -- 1.3.6.1.4.1.2011.2.25.3.40.50.234.30.1.4
        oduflex_tcm1Per24HCurDateTime OBJECT-TYPE
            SYNTAX DateAndTime
            MAX-ACCESS read-only
            STATUS current
            DESCRIPTION
                "perDateTime. "
            ::= { oduflex_tcm1Per24HCurEntry 4 }

        -- 1.3.6.1.4.1.2011.2.25.3.40.50.234.30.1.5
        oduflex_tcm1Per24HCurParaLen OBJECT-TYPE
            SYNTAX INTEGER
            MAX-ACCESS read-only
            STATUS current
            DESCRIPTION
                "perParaLen."
            ::= { oduflex_tcm1Per24HCurEntry 5 }

        -- 1.3.6.1.4.1.2011.2.25.3.40.50.234.30.1.6
        oduflex_tcm1Per24HCurPara OBJECT-TYPE
            SYNTAX OCTET STRING (SIZE (0..100))
            MAX-ACCESS read-only
            STATUS current
            DESCRIPTION
                "perPara."
            ::= { oduflex_tcm1Per24HCurEntry 6 }




-- -------------------------------------------------------------------------
-- Perfomance 24-HOUR History Data Table (RTRV-PER-<MOD2>)
-- -------------------------------------------------------------------------
        -- 1.3.6.1.4.1.2011.2.25.3.40.50.234.40
        oduflex_tcm1Per24HHisTable OBJECT-TYPE
          SYNTAX SEQUENCE OF Oduflex_tcm1Per24HHisEntry
          MAX-ACCESS not-accessible
          STATUS current
          DESCRIPTION
              "oduflex_tcm1Per24HHis."
          ::= { oduflex_tcm1 40 }

        -- 1.3.6.1.4.1.2011.2.25.3.40.50.234.40.1
        oduflex_tcm1Per24HHisEntry OBJECT-TYPE
            SYNTAX Oduflex_tcm1Per24HHisEntry
            MAX-ACCESS not-accessible
            STATUS current
            DESCRIPTION
                "oduflex_tcm1Per24HHis."
            INDEX {oduflex_tcm1Per24HHisEid, oduflex_tcm1Per24HHisParaLen, oduflex_tcm1Per24HHisPara, oduflex_tcm1Per24HHisDateTimeStart, oduflex_tcm1Per24HHisDateTimeEnd}
            ::= { oduflex_tcm1Per24HHisTable 1 }

        Oduflex_tcm1Per24HHisEntry ::=
            SEQUENCE {
                oduflex_tcm1Per24HHisEid
                    PerformanceEventType,
                oduflex_tcm1Per24HHisParaLen
                    INTEGER,
                oduflex_tcm1Per24HHisPara
                    OCTET STRING,
                oduflex_tcm1Per24HHisMonValue
                    OCTET STRING,
                oduflex_tcm1Per24HHisDateTimeStart
                    DateAndTime,
                oduflex_tcm1Per24HHisDateTimeEnd
                    DateAndTime,
                oduflex_tcm1Per24HHisVldty
                    INTEGER,
             }

        -- 1.3.6.1.4.1.2011.2.25.3.40.50.234.40.1.1
        oduflex_tcm1Per24HHisEid OBJECT-TYPE
            SYNTAX PerformanceEventType
            MAX-ACCESS read-only
            STATUS current
            DESCRIPTION
                "perEid."
            ::= { oduflex_tcm1Per24HHisEntry 1 }

        -- 1.3.6.1.4.1.2011.2.25.3.40.50.234.40.1.2
        oduflex_tcm1Per24HHisParaLen OBJECT-TYPE
            SYNTAX INTEGER
            MAX-ACCESS read-only
            STATUS current
            DESCRIPTION
                "perParaLen."
            ::= { oduflex_tcm1Per24HHisEntry 2 }

        -- 1.3.6.1.4.1.2011.2.25.3.40.50.234.40.1.3
        oduflex_tcm1Per24HHisPara OBJECT-TYPE
            SYNTAX OCTET STRING (SIZE (0..100))
            MAX-ACCESS read-only
            STATUS current
            DESCRIPTION
                "perPara."
            ::= { oduflex_tcm1Per24HHisEntry 3 }

        -- 1.3.6.1.4.1.2011.2.25.3.40.50.234.40.1.4
        oduflex_tcm1Per24HHisMonValue OBJECT-TYPE
            SYNTAX OCTET STRING (SIZE (0..100))
            MAX-ACCESS read-only
            STATUS current
            DESCRIPTION
                "perMonValue."
            ::= { oduflex_tcm1Per24HHisEntry 4 }

        -- 1.3.6.1.4.1.2011.2.25.3.40.50.234.40.1.5
        oduflex_tcm1Per24HHisDateTimeStart OBJECT-TYPE
            SYNTAX DateAndTime
            MAX-ACCESS read-only
            STATUS current
            DESCRIPTION
                "perDateTimeStart. "
            ::= { oduflex_tcm1Per24HHisEntry 5 }

        -- 1.3.6.1.4.1.2011.2.25.3.40.50.234.40.1.6
        oduflex_tcm1Per24HHisDateTimeEnd OBJECT-TYPE
            SYNTAX DateAndTime
            MAX-ACCESS read-only
            STATUS current
            DESCRIPTION
                "perDateTimeEnd. "
            ::= { oduflex_tcm1Per24HHisEntry 6 }

        -- 1.3.6.1.4.1.2011.2.25.3.40.50.234.40.1.7
        oduflex_tcm1Per24HHisVldty OBJECT-TYPE
            SYNTAX INTEGER
            MAX-ACCESS read-only
            STATUS current
            DESCRIPTION
                "perVldty. "
            ::= { oduflex_tcm1Per24HHisEntry 7 }




-- Alarm data
      -- 1.3.6.1.4.1.2011.2.25.3.40.50.235
      oduflex_tcm2 OBJECT IDENTIFIER ::={ optixGlobalNGWDM 235 }


-- -------------------------------------------------------------------------
-- Perfomance 15-MIN Current Data Table (RTRV-PER-<MOD2>)
-- -------------------------------------------------------------------------
        -- 1.3.6.1.4.1.2011.2.25.3.40.50.235.10
        oduflex_tcm2Per15MCurTable OBJECT-TYPE
          SYNTAX SEQUENCE OF Oduflex_tcm2Per15MCurEntry
          MAX-ACCESS not-accessible
          STATUS current
          DESCRIPTION
              "oduflex_tcm2Per15MCur."
          ::= { oduflex_tcm2 10 }

        -- 1.3.6.1.4.1.2011.2.25.3.40.50.235.10.1
        oduflex_tcm2Per15MCurEntry OBJECT-TYPE
            SYNTAX Oduflex_tcm2Per15MCurEntry
            MAX-ACCESS not-accessible
            STATUS current
            DESCRIPTION
              "oduflex_tcm2Per15MCur."
            INDEX { oduflex_tcm2Per15MCurEid, oduflex_tcm2Per15MCurPara }
            ::= { oduflex_tcm2Per15MCurTable 1 }

        Oduflex_tcm2Per15MCurEntry ::=
            SEQUENCE {
                oduflex_tcm2Per15MCurEid
                    PerformanceEventType,
                oduflex_tcm2Per15MCurMonValue
                    OCTET STRING,
                oduflex_tcm2Per15MCurVldty
                    INTEGER,
                oduflex_tcm2Per15MCurDateTime
                    DateAndTime,
                oduflex_tcm2Per15MCurParaLen
                    INTEGER,
                oduflex_tcm2Per15MCurPara
                    OCTET STRING
            }

        -- 1.3.6.1.4.1.2011.2.25.3.40.50.235.10.1.1
        oduflex_tcm2Per15MCurEid OBJECT-TYPE
            SYNTAX PerformanceEventType
            MAX-ACCESS read-only
            STATUS current
            DESCRIPTION
                "perEid."
            ::= { oduflex_tcm2Per15MCurEntry 1 }

        -- 1.3.6.1.4.1.2011.2.25.3.40.50.235.10.1.2
        oduflex_tcm2Per15MCurMonValue OBJECT-TYPE
            SYNTAX OCTET STRING (SIZE (0..100))
            MAX-ACCESS read-only
            STATUS current
            DESCRIPTION
                "perMonValue."
            ::= { oduflex_tcm2Per15MCurEntry 2 }

        -- 1.3.6.1.4.1.2011.2.25.3.40.50.235.10.1.3
        oduflex_tcm2Per15MCurVldty OBJECT-TYPE
            SYNTAX INTEGER
            MAX-ACCESS read-only
            STATUS current
            DESCRIPTION
                "perVldty. "
            ::= { oduflex_tcm2Per15MCurEntry 3 }

        -- 1.3.6.1.4.1.2011.2.25.3.40.50.235.10.1.4
        oduflex_tcm2Per15MCurDateTime OBJECT-TYPE
            SYNTAX DateAndTime
            MAX-ACCESS read-only
            STATUS current
            DESCRIPTION
                "perDateTime. "
            ::= { oduflex_tcm2Per15MCurEntry 4 }

        -- 1.3.6.1.4.1.2011.2.25.3.40.50.235.10.1.5
        oduflex_tcm2Per15MCurParaLen OBJECT-TYPE
            SYNTAX INTEGER
            MAX-ACCESS read-only
            STATUS current
            DESCRIPTION
                "perParaLen."
            ::= { oduflex_tcm2Per15MCurEntry 5 }

        -- 1.3.6.1.4.1.2011.2.25.3.40.50.235.10.1.6
        oduflex_tcm2Per15MCurPara OBJECT-TYPE
            SYNTAX OCTET STRING (SIZE (0..100))
            MAX-ACCESS read-only
            STATUS current
            DESCRIPTION
                "perPara."
            ::= { oduflex_tcm2Per15MCurEntry 6 }




-- -------------------------------------------------------------------------
-- Perfomance 15-MIN History Data Table (RTRV-PER-<MOD2>)
-- -------------------------------------------------------------------------
        -- 1.3.6.1.4.1.2011.2.25.3.40.50.235.20
        oduflex_tcm2Per15MHisTable OBJECT-TYPE
          SYNTAX SEQUENCE OF Oduflex_tcm2Per15MHisEntry
          MAX-ACCESS not-accessible
          STATUS current
          DESCRIPTION
              "oduflex_tcm2Per15MHis."
          ::= { oduflex_tcm2 20 }

        -- 1.3.6.1.4.1.2011.2.25.3.40.50.235.20.1
        oduflex_tcm2Per15MHisEntry OBJECT-TYPE
            SYNTAX Oduflex_tcm2Per15MHisEntry
            MAX-ACCESS not-accessible
            STATUS current
            DESCRIPTION
                "oduflex_tcm2Per15MHis."
            INDEX {oduflex_tcm2Per15MHisEid, oduflex_tcm2Per15MHisParaLen, oduflex_tcm2Per15MHisPara, oduflex_tcm2Per15MHisDateTimeStart, oduflex_tcm2Per15MHisDateTimeEnd}
            ::= { oduflex_tcm2Per15MHisTable 1 }

        Oduflex_tcm2Per15MHisEntry ::=
            SEQUENCE {
                oduflex_tcm2Per15MHisEid
                    PerformanceEventType,
                oduflex_tcm2Per15MHisParaLen
                    INTEGER,
                oduflex_tcm2Per15MHisPara
                    OCTET STRING,
                oduflex_tcm2Per15MHisMonValue
                    OCTET STRING,
                oduflex_tcm2Per15MHisDateTimeStart
                    DateAndTime,
                oduflex_tcm2Per15MHisDateTimeEnd
                    DateAndTime,
                oduflex_tcm2Per15MHisVldty
                    INTEGER,
             }

        -- 1.3.6.1.4.1.2011.2.25.3.40.50.235.20.1.1
        oduflex_tcm2Per15MHisEid OBJECT-TYPE
            SYNTAX PerformanceEventType
            MAX-ACCESS read-only
            STATUS current
            DESCRIPTION
                "perEid."
            ::= { oduflex_tcm2Per15MHisEntry 1 }

        -- 1.3.6.1.4.1.2011.2.25.3.40.50.235.20.1.2
        oduflex_tcm2Per15MHisParaLen OBJECT-TYPE
            SYNTAX INTEGER
            MAX-ACCESS read-only
            STATUS current
            DESCRIPTION
                "perParaLen."
            ::= { oduflex_tcm2Per15MHisEntry 2 }

        -- 1.3.6.1.4.1.2011.2.25.3.40.50.235.20.1.3
        oduflex_tcm2Per15MHisPara OBJECT-TYPE
            SYNTAX OCTET STRING (SIZE (0..100))
            MAX-ACCESS read-only
            STATUS current
            DESCRIPTION
                "perPara."
            ::= { oduflex_tcm2Per15MHisEntry 3 }

        -- 1.3.6.1.4.1.2011.2.25.3.40.50.235.20.1.4
        oduflex_tcm2Per15MHisMonValue OBJECT-TYPE
            SYNTAX OCTET STRING (SIZE (0..100))
            MAX-ACCESS read-only
            STATUS current
            DESCRIPTION
                "perMonValue."
            ::= { oduflex_tcm2Per15MHisEntry 4 }

        -- 1.3.6.1.4.1.2011.2.25.3.40.50.235.20.1.5
        oduflex_tcm2Per15MHisDateTimeStart OBJECT-TYPE
            SYNTAX DateAndTime
            MAX-ACCESS read-only
            STATUS current
            DESCRIPTION
                "perDateTimeStart. "
            ::= { oduflex_tcm2Per15MHisEntry 5 }

        -- 1.3.6.1.4.1.2011.2.25.3.40.50.235.20.1.6
        oduflex_tcm2Per15MHisDateTimeEnd OBJECT-TYPE
            SYNTAX DateAndTime
            MAX-ACCESS read-only
            STATUS current
            DESCRIPTION
                "perDateTimeEnd. "
            ::= { oduflex_tcm2Per15MHisEntry 6 }

        -- 1.3.6.1.4.1.2011.2.25.3.40.50.235.20.1.7
        oduflex_tcm2Per15MHisVldty OBJECT-TYPE
            SYNTAX INTEGER
            MAX-ACCESS read-only
            STATUS current
            DESCRIPTION
                "perVldty. "
            ::= { oduflex_tcm2Per15MHisEntry 7 }




-- -------------------------------------------------------------------------
-- Perfomance 24-HOUR Current Data Table (RTRV-PER-<MOD2>)
-- -------------------------------------------------------------------------
        -- 1.3.6.1.4.1.2011.2.25.3.40.50.235.30
        oduflex_tcm2Per24HCurTable OBJECT-TYPE
          SYNTAX SEQUENCE OF Oduflex_tcm2Per24HCurEntry
          MAX-ACCESS not-accessible
          STATUS current
          DESCRIPTION
              "oduflex_tcm2Per24HCur."
          ::= { oduflex_tcm2 30 }

        -- 1.3.6.1.4.1.2011.2.25.3.40.50.235.30.1
        oduflex_tcm2Per24HCurEntry OBJECT-TYPE
            SYNTAX Oduflex_tcm2Per24HCurEntry
            MAX-ACCESS not-accessible
            STATUS current
            DESCRIPTION
              "oduflex_tcm2Per24HCur."
            INDEX { oduflex_tcm2Per24HCurEid, oduflex_tcm2Per24HCurPara }
            ::= { oduflex_tcm2Per24HCurTable 1 }

        Oduflex_tcm2Per24HCurEntry ::=
            SEQUENCE {
                oduflex_tcm2Per24HCurEid
                    PerformanceEventType,
                oduflex_tcm2Per24HCurMonValue
                    OCTET STRING,
                oduflex_tcm2Per24HCurVldty
                    INTEGER,
                oduflex_tcm2Per24HCurDateTime
                    DateAndTime,
                oduflex_tcm2Per24HCurParaLen
                    INTEGER,
                oduflex_tcm2Per24HCurPara
                    OCTET STRING
            }

        -- 1.3.6.1.4.1.2011.2.25.3.40.50.235.30.1.1
        oduflex_tcm2Per24HCurEid OBJECT-TYPE
            SYNTAX PerformanceEventType
            MAX-ACCESS read-only
            STATUS current
            DESCRIPTION
                "perEid."
            ::= { oduflex_tcm2Per24HCurEntry 1 }

        -- 1.3.6.1.4.1.2011.2.25.3.40.50.235.30.1.2
        oduflex_tcm2Per24HCurMonValue OBJECT-TYPE
            SYNTAX OCTET STRING (SIZE (0..100))
            MAX-ACCESS read-only
            STATUS current
            DESCRIPTION
                "perMonValue."
            ::= { oduflex_tcm2Per24HCurEntry 2 }

        -- 1.3.6.1.4.1.2011.2.25.3.40.50.235.30.1.3
        oduflex_tcm2Per24HCurVldty OBJECT-TYPE
            SYNTAX INTEGER
            MAX-ACCESS read-only
            STATUS current
            DESCRIPTION
                "perVldty. "
            ::= { oduflex_tcm2Per24HCurEntry 3 }

        -- 1.3.6.1.4.1.2011.2.25.3.40.50.235.30.1.4
        oduflex_tcm2Per24HCurDateTime OBJECT-TYPE
            SYNTAX DateAndTime
            MAX-ACCESS read-only
            STATUS current
            DESCRIPTION
                "perDateTime. "
            ::= { oduflex_tcm2Per24HCurEntry 4 }

        -- 1.3.6.1.4.1.2011.2.25.3.40.50.235.30.1.5
        oduflex_tcm2Per24HCurParaLen OBJECT-TYPE
            SYNTAX INTEGER
            MAX-ACCESS read-only
            STATUS current
            DESCRIPTION
                "perParaLen."
            ::= { oduflex_tcm2Per24HCurEntry 5 }

        -- 1.3.6.1.4.1.2011.2.25.3.40.50.235.30.1.6
        oduflex_tcm2Per24HCurPara OBJECT-TYPE
            SYNTAX OCTET STRING (SIZE (0..100))
            MAX-ACCESS read-only
            STATUS current
            DESCRIPTION
                "perPara."
            ::= { oduflex_tcm2Per24HCurEntry 6 }




-- -------------------------------------------------------------------------
-- Perfomance 24-HOUR History Data Table (RTRV-PER-<MOD2>)
-- -------------------------------------------------------------------------
        -- 1.3.6.1.4.1.2011.2.25.3.40.50.235.40
        oduflex_tcm2Per24HHisTable OBJECT-TYPE
          SYNTAX SEQUENCE OF Oduflex_tcm2Per24HHisEntry
          MAX-ACCESS not-accessible
          STATUS current
          DESCRIPTION
              "oduflex_tcm2Per24HHis."
          ::= { oduflex_tcm2 40 }

        -- 1.3.6.1.4.1.2011.2.25.3.40.50.235.40.1
        oduflex_tcm2Per24HHisEntry OBJECT-TYPE
            SYNTAX Oduflex_tcm2Per24HHisEntry
            MAX-ACCESS not-accessible
            STATUS current
            DESCRIPTION
                "oduflex_tcm2Per24HHis."
            INDEX {oduflex_tcm2Per24HHisEid, oduflex_tcm2Per24HHisParaLen, oduflex_tcm2Per24HHisPara, oduflex_tcm2Per24HHisDateTimeStart, oduflex_tcm2Per24HHisDateTimeEnd}
            ::= { oduflex_tcm2Per24HHisTable 1 }

        Oduflex_tcm2Per24HHisEntry ::=
            SEQUENCE {
                oduflex_tcm2Per24HHisEid
                    PerformanceEventType,
                oduflex_tcm2Per24HHisParaLen
                    INTEGER,
                oduflex_tcm2Per24HHisPara
                    OCTET STRING,
                oduflex_tcm2Per24HHisMonValue
                    OCTET STRING,
                oduflex_tcm2Per24HHisDateTimeStart
                    DateAndTime,
                oduflex_tcm2Per24HHisDateTimeEnd
                    DateAndTime,
                oduflex_tcm2Per24HHisVldty
                    INTEGER,
             }

        -- 1.3.6.1.4.1.2011.2.25.3.40.50.235.40.1.1
        oduflex_tcm2Per24HHisEid OBJECT-TYPE
            SYNTAX PerformanceEventType
            MAX-ACCESS read-only
            STATUS current
            DESCRIPTION
                "perEid."
            ::= { oduflex_tcm2Per24HHisEntry 1 }

        -- 1.3.6.1.4.1.2011.2.25.3.40.50.235.40.1.2
        oduflex_tcm2Per24HHisParaLen OBJECT-TYPE
            SYNTAX INTEGER
            MAX-ACCESS read-only
            STATUS current
            DESCRIPTION
                "perParaLen."
            ::= { oduflex_tcm2Per24HHisEntry 2 }

        -- 1.3.6.1.4.1.2011.2.25.3.40.50.235.40.1.3
        oduflex_tcm2Per24HHisPara OBJECT-TYPE
            SYNTAX OCTET STRING (SIZE (0..100))
            MAX-ACCESS read-only
            STATUS current
            DESCRIPTION
                "perPara."
            ::= { oduflex_tcm2Per24HHisEntry 3 }

        -- 1.3.6.1.4.1.2011.2.25.3.40.50.235.40.1.4
        oduflex_tcm2Per24HHisMonValue OBJECT-TYPE
            SYNTAX OCTET STRING (SIZE (0..100))
            MAX-ACCESS read-only
            STATUS current
            DESCRIPTION
                "perMonValue."
            ::= { oduflex_tcm2Per24HHisEntry 4 }

        -- 1.3.6.1.4.1.2011.2.25.3.40.50.235.40.1.5
        oduflex_tcm2Per24HHisDateTimeStart OBJECT-TYPE
            SYNTAX DateAndTime
            MAX-ACCESS read-only
            STATUS current
            DESCRIPTION
                "perDateTimeStart. "
            ::= { oduflex_tcm2Per24HHisEntry 5 }

        -- 1.3.6.1.4.1.2011.2.25.3.40.50.235.40.1.6
        oduflex_tcm2Per24HHisDateTimeEnd OBJECT-TYPE
            SYNTAX DateAndTime
            MAX-ACCESS read-only
            STATUS current
            DESCRIPTION
                "perDateTimeEnd. "
            ::= { oduflex_tcm2Per24HHisEntry 6 }

        -- 1.3.6.1.4.1.2011.2.25.3.40.50.235.40.1.7
        oduflex_tcm2Per24HHisVldty OBJECT-TYPE
            SYNTAX INTEGER
            MAX-ACCESS read-only
            STATUS current
            DESCRIPTION
                "perVldty. "
            ::= { oduflex_tcm2Per24HHisEntry 7 }




-- Alarm data
      -- 1.3.6.1.4.1.2011.2.25.3.40.50.236
      oduflex_tcm3 OBJECT IDENTIFIER ::={ optixGlobalNGWDM 236 }


-- -------------------------------------------------------------------------
-- Perfomance 15-MIN Current Data Table (RTRV-PER-<MOD2>)
-- -------------------------------------------------------------------------
        -- 1.3.6.1.4.1.2011.2.25.3.40.50.236.10
        oduflex_tcm3Per15MCurTable OBJECT-TYPE
          SYNTAX SEQUENCE OF Oduflex_tcm3Per15MCurEntry
          MAX-ACCESS not-accessible
          STATUS current
          DESCRIPTION
              "oduflex_tcm3Per15MCur."
          ::= { oduflex_tcm3 10 }

        -- 1.3.6.1.4.1.2011.2.25.3.40.50.236.10.1
        oduflex_tcm3Per15MCurEntry OBJECT-TYPE
            SYNTAX Oduflex_tcm3Per15MCurEntry
            MAX-ACCESS not-accessible
            STATUS current
            DESCRIPTION
              "oduflex_tcm3Per15MCur."
            INDEX { oduflex_tcm3Per15MCurEid, oduflex_tcm3Per15MCurPara }
            ::= { oduflex_tcm3Per15MCurTable 1 }

        Oduflex_tcm3Per15MCurEntry ::=
            SEQUENCE {
                oduflex_tcm3Per15MCurEid
                    PerformanceEventType,
                oduflex_tcm3Per15MCurMonValue
                    OCTET STRING,
                oduflex_tcm3Per15MCurVldty
                    INTEGER,
                oduflex_tcm3Per15MCurDateTime
                    DateAndTime,
                oduflex_tcm3Per15MCurParaLen
                    INTEGER,
                oduflex_tcm3Per15MCurPara
                    OCTET STRING
            }

        -- 1.3.6.1.4.1.2011.2.25.3.40.50.236.10.1.1
        oduflex_tcm3Per15MCurEid OBJECT-TYPE
            SYNTAX PerformanceEventType
            MAX-ACCESS read-only
            STATUS current
            DESCRIPTION
                "perEid."
            ::= { oduflex_tcm3Per15MCurEntry 1 }

        -- 1.3.6.1.4.1.2011.2.25.3.40.50.236.10.1.2
        oduflex_tcm3Per15MCurMonValue OBJECT-TYPE
            SYNTAX OCTET STRING (SIZE (0..100))
            MAX-ACCESS read-only
            STATUS current
            DESCRIPTION
                "perMonValue."
            ::= { oduflex_tcm3Per15MCurEntry 2 }

        -- 1.3.6.1.4.1.2011.2.25.3.40.50.236.10.1.3
        oduflex_tcm3Per15MCurVldty OBJECT-TYPE
            SYNTAX INTEGER
            MAX-ACCESS read-only
            STATUS current
            DESCRIPTION
                "perVldty. "
            ::= { oduflex_tcm3Per15MCurEntry 3 }

        -- 1.3.6.1.4.1.2011.2.25.3.40.50.236.10.1.4
        oduflex_tcm3Per15MCurDateTime OBJECT-TYPE
            SYNTAX DateAndTime
            MAX-ACCESS read-only
            STATUS current
            DESCRIPTION
                "perDateTime. "
            ::= { oduflex_tcm3Per15MCurEntry 4 }

        -- 1.3.6.1.4.1.2011.2.25.3.40.50.236.10.1.5
        oduflex_tcm3Per15MCurParaLen OBJECT-TYPE
            SYNTAX INTEGER
            MAX-ACCESS read-only
            STATUS current
            DESCRIPTION
                "perParaLen."
            ::= { oduflex_tcm3Per15MCurEntry 5 }

        -- 1.3.6.1.4.1.2011.2.25.3.40.50.236.10.1.6
        oduflex_tcm3Per15MCurPara OBJECT-TYPE
            SYNTAX OCTET STRING (SIZE (0..100))
            MAX-ACCESS read-only
            STATUS current
            DESCRIPTION
                "perPara."
            ::= { oduflex_tcm3Per15MCurEntry 6 }




-- -------------------------------------------------------------------------
-- Perfomance 15-MIN History Data Table (RTRV-PER-<MOD2>)
-- -------------------------------------------------------------------------
        -- 1.3.6.1.4.1.2011.2.25.3.40.50.236.20
        oduflex_tcm3Per15MHisTable OBJECT-TYPE
          SYNTAX SEQUENCE OF Oduflex_tcm3Per15MHisEntry
          MAX-ACCESS not-accessible
          STATUS current
          DESCRIPTION
              "oduflex_tcm3Per15MHis."
          ::= { oduflex_tcm3 20 }

        -- 1.3.6.1.4.1.2011.2.25.3.40.50.236.20.1
        oduflex_tcm3Per15MHisEntry OBJECT-TYPE
            SYNTAX Oduflex_tcm3Per15MHisEntry
            MAX-ACCESS not-accessible
            STATUS current
            DESCRIPTION
                "oduflex_tcm3Per15MHis."
            INDEX {oduflex_tcm3Per15MHisEid, oduflex_tcm3Per15MHisParaLen, oduflex_tcm3Per15MHisPara, oduflex_tcm3Per15MHisDateTimeStart, oduflex_tcm3Per15MHisDateTimeEnd}
            ::= { oduflex_tcm3Per15MHisTable 1 }

        Oduflex_tcm3Per15MHisEntry ::=
            SEQUENCE {
                oduflex_tcm3Per15MHisEid
                    PerformanceEventType,
                oduflex_tcm3Per15MHisParaLen
                    INTEGER,
                oduflex_tcm3Per15MHisPara
                    OCTET STRING,
                oduflex_tcm3Per15MHisMonValue
                    OCTET STRING,
                oduflex_tcm3Per15MHisDateTimeStart
                    DateAndTime,
                oduflex_tcm3Per15MHisDateTimeEnd
                    DateAndTime,
                oduflex_tcm3Per15MHisVldty
                    INTEGER,
             }

        -- 1.3.6.1.4.1.2011.2.25.3.40.50.236.20.1.1
        oduflex_tcm3Per15MHisEid OBJECT-TYPE
            SYNTAX PerformanceEventType
            MAX-ACCESS read-only
            STATUS current
            DESCRIPTION
                "perEid."
            ::= { oduflex_tcm3Per15MHisEntry 1 }

        -- 1.3.6.1.4.1.2011.2.25.3.40.50.236.20.1.2
        oduflex_tcm3Per15MHisParaLen OBJECT-TYPE
            SYNTAX INTEGER
            MAX-ACCESS read-only
            STATUS current
            DESCRIPTION
                "perParaLen."
            ::= { oduflex_tcm3Per15MHisEntry 2 }

        -- 1.3.6.1.4.1.2011.2.25.3.40.50.236.20.1.3
        oduflex_tcm3Per15MHisPara OBJECT-TYPE
            SYNTAX OCTET STRING (SIZE (0..100))
            MAX-ACCESS read-only
            STATUS current
            DESCRIPTION
                "perPara."
            ::= { oduflex_tcm3Per15MHisEntry 3 }

        -- 1.3.6.1.4.1.2011.2.25.3.40.50.236.20.1.4
        oduflex_tcm3Per15MHisMonValue OBJECT-TYPE
            SYNTAX OCTET STRING (SIZE (0..100))
            MAX-ACCESS read-only
            STATUS current
            DESCRIPTION
                "perMonValue."
            ::= { oduflex_tcm3Per15MHisEntry 4 }

        -- 1.3.6.1.4.1.2011.2.25.3.40.50.236.20.1.5
        oduflex_tcm3Per15MHisDateTimeStart OBJECT-TYPE
            SYNTAX DateAndTime
            MAX-ACCESS read-only
            STATUS current
            DESCRIPTION
                "perDateTimeStart. "
            ::= { oduflex_tcm3Per15MHisEntry 5 }

        -- 1.3.6.1.4.1.2011.2.25.3.40.50.236.20.1.6
        oduflex_tcm3Per15MHisDateTimeEnd OBJECT-TYPE
            SYNTAX DateAndTime
            MAX-ACCESS read-only
            STATUS current
            DESCRIPTION
                "perDateTimeEnd. "
            ::= { oduflex_tcm3Per15MHisEntry 6 }

        -- 1.3.6.1.4.1.2011.2.25.3.40.50.236.20.1.7
        oduflex_tcm3Per15MHisVldty OBJECT-TYPE
            SYNTAX INTEGER
            MAX-ACCESS read-only
            STATUS current
            DESCRIPTION
                "perVldty. "
            ::= { oduflex_tcm3Per15MHisEntry 7 }




-- -------------------------------------------------------------------------
-- Perfomance 24-HOUR Current Data Table (RTRV-PER-<MOD2>)
-- -------------------------------------------------------------------------
        -- 1.3.6.1.4.1.2011.2.25.3.40.50.236.30
        oduflex_tcm3Per24HCurTable OBJECT-TYPE
          SYNTAX SEQUENCE OF Oduflex_tcm3Per24HCurEntry
          MAX-ACCESS not-accessible
          STATUS current
          DESCRIPTION
              "oduflex_tcm3Per24HCur."
          ::= { oduflex_tcm3 30 }

        -- 1.3.6.1.4.1.2011.2.25.3.40.50.236.30.1
        oduflex_tcm3Per24HCurEntry OBJECT-TYPE
            SYNTAX Oduflex_tcm3Per24HCurEntry
            MAX-ACCESS not-accessible
            STATUS current
            DESCRIPTION
              "oduflex_tcm3Per24HCur."
            INDEX { oduflex_tcm3Per24HCurEid, oduflex_tcm3Per24HCurPara }
            ::= { oduflex_tcm3Per24HCurTable 1 }

        Oduflex_tcm3Per24HCurEntry ::=
            SEQUENCE {
                oduflex_tcm3Per24HCurEid
                    PerformanceEventType,
                oduflex_tcm3Per24HCurMonValue
                    OCTET STRING,
                oduflex_tcm3Per24HCurVldty
                    INTEGER,
                oduflex_tcm3Per24HCurDateTime
                    DateAndTime,
                oduflex_tcm3Per24HCurParaLen
                    INTEGER,
                oduflex_tcm3Per24HCurPara
                    OCTET STRING
            }

        -- 1.3.6.1.4.1.2011.2.25.3.40.50.236.30.1.1
        oduflex_tcm3Per24HCurEid OBJECT-TYPE
            SYNTAX PerformanceEventType
            MAX-ACCESS read-only
            STATUS current
            DESCRIPTION
                "perEid."
            ::= { oduflex_tcm3Per24HCurEntry 1 }

        -- 1.3.6.1.4.1.2011.2.25.3.40.50.236.30.1.2
        oduflex_tcm3Per24HCurMonValue OBJECT-TYPE
            SYNTAX OCTET STRING (SIZE (0..100))
            MAX-ACCESS read-only
            STATUS current
            DESCRIPTION
                "perMonValue."
            ::= { oduflex_tcm3Per24HCurEntry 2 }

        -- 1.3.6.1.4.1.2011.2.25.3.40.50.236.30.1.3
        oduflex_tcm3Per24HCurVldty OBJECT-TYPE
            SYNTAX INTEGER
            MAX-ACCESS read-only
            STATUS current
            DESCRIPTION
                "perVldty. "
            ::= { oduflex_tcm3Per24HCurEntry 3 }

        -- 1.3.6.1.4.1.2011.2.25.3.40.50.236.30.1.4
        oduflex_tcm3Per24HCurDateTime OBJECT-TYPE
            SYNTAX DateAndTime
            MAX-ACCESS read-only
            STATUS current
            DESCRIPTION
                "perDateTime. "
            ::= { oduflex_tcm3Per24HCurEntry 4 }

        -- 1.3.6.1.4.1.2011.2.25.3.40.50.236.30.1.5
        oduflex_tcm3Per24HCurParaLen OBJECT-TYPE
            SYNTAX INTEGER
            MAX-ACCESS read-only
            STATUS current
            DESCRIPTION
                "perParaLen."
            ::= { oduflex_tcm3Per24HCurEntry 5 }

        -- 1.3.6.1.4.1.2011.2.25.3.40.50.236.30.1.6
        oduflex_tcm3Per24HCurPara OBJECT-TYPE
            SYNTAX OCTET STRING (SIZE (0..100))
            MAX-ACCESS read-only
            STATUS current
            DESCRIPTION
                "perPara."
            ::= { oduflex_tcm3Per24HCurEntry 6 }




-- -------------------------------------------------------------------------
-- Perfomance 24-HOUR History Data Table (RTRV-PER-<MOD2>)
-- -------------------------------------------------------------------------
        -- 1.3.6.1.4.1.2011.2.25.3.40.50.236.40
        oduflex_tcm3Per24HHisTable OBJECT-TYPE
          SYNTAX SEQUENCE OF Oduflex_tcm3Per24HHisEntry
          MAX-ACCESS not-accessible
          STATUS current
          DESCRIPTION
              "oduflex_tcm3Per24HHis."
          ::= { oduflex_tcm3 40 }

        -- 1.3.6.1.4.1.2011.2.25.3.40.50.236.40.1
        oduflex_tcm3Per24HHisEntry OBJECT-TYPE
            SYNTAX Oduflex_tcm3Per24HHisEntry
            MAX-ACCESS not-accessible
            STATUS current
            DESCRIPTION
                "oduflex_tcm3Per24HHis."
            INDEX {oduflex_tcm3Per24HHisEid, oduflex_tcm3Per24HHisParaLen, oduflex_tcm3Per24HHisPara, oduflex_tcm3Per24HHisDateTimeStart, oduflex_tcm3Per24HHisDateTimeEnd}
            ::= { oduflex_tcm3Per24HHisTable 1 }

        Oduflex_tcm3Per24HHisEntry ::=
            SEQUENCE {
                oduflex_tcm3Per24HHisEid
                    PerformanceEventType,
                oduflex_tcm3Per24HHisParaLen
                    INTEGER,
                oduflex_tcm3Per24HHisPara
                    OCTET STRING,
                oduflex_tcm3Per24HHisMonValue
                    OCTET STRING,
                oduflex_tcm3Per24HHisDateTimeStart
                    DateAndTime,
                oduflex_tcm3Per24HHisDateTimeEnd
                    DateAndTime,
                oduflex_tcm3Per24HHisVldty
                    INTEGER,
             }

        -- 1.3.6.1.4.1.2011.2.25.3.40.50.236.40.1.1
        oduflex_tcm3Per24HHisEid OBJECT-TYPE
            SYNTAX PerformanceEventType
            MAX-ACCESS read-only
            STATUS current
            DESCRIPTION
                "perEid."
            ::= { oduflex_tcm3Per24HHisEntry 1 }

        -- 1.3.6.1.4.1.2011.2.25.3.40.50.236.40.1.2
        oduflex_tcm3Per24HHisParaLen OBJECT-TYPE
            SYNTAX INTEGER
            MAX-ACCESS read-only
            STATUS current
            DESCRIPTION
                "perParaLen."
            ::= { oduflex_tcm3Per24HHisEntry 2 }

        -- 1.3.6.1.4.1.2011.2.25.3.40.50.236.40.1.3
        oduflex_tcm3Per24HHisPara OBJECT-TYPE
            SYNTAX OCTET STRING (SIZE (0..100))
            MAX-ACCESS read-only
            STATUS current
            DESCRIPTION
                "perPara."
            ::= { oduflex_tcm3Per24HHisEntry 3 }

        -- 1.3.6.1.4.1.2011.2.25.3.40.50.236.40.1.4
        oduflex_tcm3Per24HHisMonValue OBJECT-TYPE
            SYNTAX OCTET STRING (SIZE (0..100))
            MAX-ACCESS read-only
            STATUS current
            DESCRIPTION
                "perMonValue."
            ::= { oduflex_tcm3Per24HHisEntry 4 }

        -- 1.3.6.1.4.1.2011.2.25.3.40.50.236.40.1.5
        oduflex_tcm3Per24HHisDateTimeStart OBJECT-TYPE
            SYNTAX DateAndTime
            MAX-ACCESS read-only
            STATUS current
            DESCRIPTION
                "perDateTimeStart. "
            ::= { oduflex_tcm3Per24HHisEntry 5 }

        -- 1.3.6.1.4.1.2011.2.25.3.40.50.236.40.1.6
        oduflex_tcm3Per24HHisDateTimeEnd OBJECT-TYPE
            SYNTAX DateAndTime
            MAX-ACCESS read-only
            STATUS current
            DESCRIPTION
                "perDateTimeEnd. "
            ::= { oduflex_tcm3Per24HHisEntry 6 }

        -- 1.3.6.1.4.1.2011.2.25.3.40.50.236.40.1.7
        oduflex_tcm3Per24HHisVldty OBJECT-TYPE
            SYNTAX INTEGER
            MAX-ACCESS read-only
            STATUS current
            DESCRIPTION
                "perVldty. "
            ::= { oduflex_tcm3Per24HHisEntry 7 }




-- Alarm data
      -- 1.3.6.1.4.1.2011.2.25.3.40.50.237
      oduflex_tcm4 OBJECT IDENTIFIER ::={ optixGlobalNGWDM 237 }


-- -------------------------------------------------------------------------
-- Perfomance 15-MIN Current Data Table (RTRV-PER-<MOD2>)
-- -------------------------------------------------------------------------
        -- 1.3.6.1.4.1.2011.2.25.3.40.50.237.10
        oduflex_tcm4Per15MCurTable OBJECT-TYPE
          SYNTAX SEQUENCE OF Oduflex_tcm4Per15MCurEntry
          MAX-ACCESS not-accessible
          STATUS current
          DESCRIPTION
              "oduflex_tcm4Per15MCur."
          ::= { oduflex_tcm4 10 }

        -- 1.3.6.1.4.1.2011.2.25.3.40.50.237.10.1
        oduflex_tcm4Per15MCurEntry OBJECT-TYPE
            SYNTAX Oduflex_tcm4Per15MCurEntry
            MAX-ACCESS not-accessible
            STATUS current
            DESCRIPTION
              "oduflex_tcm4Per15MCur."
            INDEX { oduflex_tcm4Per15MCurEid, oduflex_tcm4Per15MCurPara }
            ::= { oduflex_tcm4Per15MCurTable 1 }

        Oduflex_tcm4Per15MCurEntry ::=
            SEQUENCE {
                oduflex_tcm4Per15MCurEid
                    PerformanceEventType,
                oduflex_tcm4Per15MCurMonValue
                    OCTET STRING,
                oduflex_tcm4Per15MCurVldty
                    INTEGER,
                oduflex_tcm4Per15MCurDateTime
                    DateAndTime,
                oduflex_tcm4Per15MCurParaLen
                    INTEGER,
                oduflex_tcm4Per15MCurPara
                    OCTET STRING
            }

        -- 1.3.6.1.4.1.2011.2.25.3.40.50.237.10.1.1
        oduflex_tcm4Per15MCurEid OBJECT-TYPE
            SYNTAX PerformanceEventType
            MAX-ACCESS read-only
            STATUS current
            DESCRIPTION
                "perEid."
            ::= { oduflex_tcm4Per15MCurEntry 1 }

        -- 1.3.6.1.4.1.2011.2.25.3.40.50.237.10.1.2
        oduflex_tcm4Per15MCurMonValue OBJECT-TYPE
            SYNTAX OCTET STRING (SIZE (0..100))
            MAX-ACCESS read-only
            STATUS current
            DESCRIPTION
                "perMonValue."
            ::= { oduflex_tcm4Per15MCurEntry 2 }

        -- 1.3.6.1.4.1.2011.2.25.3.40.50.237.10.1.3
        oduflex_tcm4Per15MCurVldty OBJECT-TYPE
            SYNTAX INTEGER
            MAX-ACCESS read-only
            STATUS current
            DESCRIPTION
                "perVldty. "
            ::= { oduflex_tcm4Per15MCurEntry 3 }

        -- 1.3.6.1.4.1.2011.2.25.3.40.50.237.10.1.4
        oduflex_tcm4Per15MCurDateTime OBJECT-TYPE
            SYNTAX DateAndTime
            MAX-ACCESS read-only
            STATUS current
            DESCRIPTION
                "perDateTime. "
            ::= { oduflex_tcm4Per15MCurEntry 4 }

        -- 1.3.6.1.4.1.2011.2.25.3.40.50.237.10.1.5
        oduflex_tcm4Per15MCurParaLen OBJECT-TYPE
            SYNTAX INTEGER
            MAX-ACCESS read-only
            STATUS current
            DESCRIPTION
                "perParaLen."
            ::= { oduflex_tcm4Per15MCurEntry 5 }

        -- 1.3.6.1.4.1.2011.2.25.3.40.50.237.10.1.6
        oduflex_tcm4Per15MCurPara OBJECT-TYPE
            SYNTAX OCTET STRING (SIZE (0..100))
            MAX-ACCESS read-only
            STATUS current
            DESCRIPTION
                "perPara."
            ::= { oduflex_tcm4Per15MCurEntry 6 }




-- -------------------------------------------------------------------------
-- Perfomance 15-MIN History Data Table (RTRV-PER-<MOD2>)
-- -------------------------------------------------------------------------
        -- 1.3.6.1.4.1.2011.2.25.3.40.50.237.20
        oduflex_tcm4Per15MHisTable OBJECT-TYPE
          SYNTAX SEQUENCE OF Oduflex_tcm4Per15MHisEntry
          MAX-ACCESS not-accessible
          STATUS current
          DESCRIPTION
              "oduflex_tcm4Per15MHis."
          ::= { oduflex_tcm4 20 }

        -- 1.3.6.1.4.1.2011.2.25.3.40.50.237.20.1
        oduflex_tcm4Per15MHisEntry OBJECT-TYPE
            SYNTAX Oduflex_tcm4Per15MHisEntry
            MAX-ACCESS not-accessible
            STATUS current
            DESCRIPTION
                "oduflex_tcm4Per15MHis."
            INDEX {oduflex_tcm4Per15MHisEid, oduflex_tcm4Per15MHisParaLen, oduflex_tcm4Per15MHisPara, oduflex_tcm4Per15MHisDateTimeStart, oduflex_tcm4Per15MHisDateTimeEnd}
            ::= { oduflex_tcm4Per15MHisTable 1 }

        Oduflex_tcm4Per15MHisEntry ::=
            SEQUENCE {
                oduflex_tcm4Per15MHisEid
                    PerformanceEventType,
                oduflex_tcm4Per15MHisParaLen
                    INTEGER,
                oduflex_tcm4Per15MHisPara
                    OCTET STRING,
                oduflex_tcm4Per15MHisMonValue
                    OCTET STRING,
                oduflex_tcm4Per15MHisDateTimeStart
                    DateAndTime,
                oduflex_tcm4Per15MHisDateTimeEnd
                    DateAndTime,
                oduflex_tcm4Per15MHisVldty
                    INTEGER,
             }

        -- 1.3.6.1.4.1.2011.2.25.3.40.50.237.20.1.1
        oduflex_tcm4Per15MHisEid OBJECT-TYPE
            SYNTAX PerformanceEventType
            MAX-ACCESS read-only
            STATUS current
            DESCRIPTION
                "perEid."
            ::= { oduflex_tcm4Per15MHisEntry 1 }

        -- 1.3.6.1.4.1.2011.2.25.3.40.50.237.20.1.2
        oduflex_tcm4Per15MHisParaLen OBJECT-TYPE
            SYNTAX INTEGER
            MAX-ACCESS read-only
            STATUS current
            DESCRIPTION
                "perParaLen."
            ::= { oduflex_tcm4Per15MHisEntry 2 }

        -- 1.3.6.1.4.1.2011.2.25.3.40.50.237.20.1.3
        oduflex_tcm4Per15MHisPara OBJECT-TYPE
            SYNTAX OCTET STRING (SIZE (0..100))
            MAX-ACCESS read-only
            STATUS current
            DESCRIPTION
                "perPara."
            ::= { oduflex_tcm4Per15MHisEntry 3 }

        -- 1.3.6.1.4.1.2011.2.25.3.40.50.237.20.1.4
        oduflex_tcm4Per15MHisMonValue OBJECT-TYPE
            SYNTAX OCTET STRING (SIZE (0..100))
            MAX-ACCESS read-only
            STATUS current
            DESCRIPTION
                "perMonValue."
            ::= { oduflex_tcm4Per15MHisEntry 4 }

        -- 1.3.6.1.4.1.2011.2.25.3.40.50.237.20.1.5
        oduflex_tcm4Per15MHisDateTimeStart OBJECT-TYPE
            SYNTAX DateAndTime
            MAX-ACCESS read-only
            STATUS current
            DESCRIPTION
                "perDateTimeStart. "
            ::= { oduflex_tcm4Per15MHisEntry 5 }

        -- 1.3.6.1.4.1.2011.2.25.3.40.50.237.20.1.6
        oduflex_tcm4Per15MHisDateTimeEnd OBJECT-TYPE
            SYNTAX DateAndTime
            MAX-ACCESS read-only
            STATUS current
            DESCRIPTION
                "perDateTimeEnd. "
            ::= { oduflex_tcm4Per15MHisEntry 6 }

        -- 1.3.6.1.4.1.2011.2.25.3.40.50.237.20.1.7
        oduflex_tcm4Per15MHisVldty OBJECT-TYPE
            SYNTAX INTEGER
            MAX-ACCESS read-only
            STATUS current
            DESCRIPTION
                "perVldty. "
            ::= { oduflex_tcm4Per15MHisEntry 7 }




-- -------------------------------------------------------------------------
-- Perfomance 24-HOUR Current Data Table (RTRV-PER-<MOD2>)
-- -------------------------------------------------------------------------
        -- 1.3.6.1.4.1.2011.2.25.3.40.50.237.30
        oduflex_tcm4Per24HCurTable OBJECT-TYPE
          SYNTAX SEQUENCE OF Oduflex_tcm4Per24HCurEntry
          MAX-ACCESS not-accessible
          STATUS current
          DESCRIPTION
              "oduflex_tcm4Per24HCur."
          ::= { oduflex_tcm4 30 }

        -- 1.3.6.1.4.1.2011.2.25.3.40.50.237.30.1
        oduflex_tcm4Per24HCurEntry OBJECT-TYPE
            SYNTAX Oduflex_tcm4Per24HCurEntry
            MAX-ACCESS not-accessible
            STATUS current
            DESCRIPTION
              "oduflex_tcm4Per24HCur."
            INDEX { oduflex_tcm4Per24HCurEid, oduflex_tcm4Per24HCurPara }
            ::= { oduflex_tcm4Per24HCurTable 1 }

        Oduflex_tcm4Per24HCurEntry ::=
            SEQUENCE {
                oduflex_tcm4Per24HCurEid
                    PerformanceEventType,
                oduflex_tcm4Per24HCurMonValue
                    OCTET STRING,
                oduflex_tcm4Per24HCurVldty
                    INTEGER,
                oduflex_tcm4Per24HCurDateTime
                    DateAndTime,
                oduflex_tcm4Per24HCurParaLen
                    INTEGER,
                oduflex_tcm4Per24HCurPara
                    OCTET STRING
            }

        -- 1.3.6.1.4.1.2011.2.25.3.40.50.237.30.1.1
        oduflex_tcm4Per24HCurEid OBJECT-TYPE
            SYNTAX PerformanceEventType
            MAX-ACCESS read-only
            STATUS current
            DESCRIPTION
                "perEid."
            ::= { oduflex_tcm4Per24HCurEntry 1 }

        -- 1.3.6.1.4.1.2011.2.25.3.40.50.237.30.1.2
        oduflex_tcm4Per24HCurMonValue OBJECT-TYPE
            SYNTAX OCTET STRING (SIZE (0..100))
            MAX-ACCESS read-only
            STATUS current
            DESCRIPTION
                "perMonValue."
            ::= { oduflex_tcm4Per24HCurEntry 2 }

        -- 1.3.6.1.4.1.2011.2.25.3.40.50.237.30.1.3
        oduflex_tcm4Per24HCurVldty OBJECT-TYPE
            SYNTAX INTEGER
            MAX-ACCESS read-only
            STATUS current
            DESCRIPTION
                "perVldty. "
            ::= { oduflex_tcm4Per24HCurEntry 3 }

        -- 1.3.6.1.4.1.2011.2.25.3.40.50.237.30.1.4
        oduflex_tcm4Per24HCurDateTime OBJECT-TYPE
            SYNTAX DateAndTime
            MAX-ACCESS read-only
            STATUS current
            DESCRIPTION
                "perDateTime. "
            ::= { oduflex_tcm4Per24HCurEntry 4 }

        -- 1.3.6.1.4.1.2011.2.25.3.40.50.237.30.1.5
        oduflex_tcm4Per24HCurParaLen OBJECT-TYPE
            SYNTAX INTEGER
            MAX-ACCESS read-only
            STATUS current
            DESCRIPTION
                "perParaLen."
            ::= { oduflex_tcm4Per24HCurEntry 5 }

        -- 1.3.6.1.4.1.2011.2.25.3.40.50.237.30.1.6
        oduflex_tcm4Per24HCurPara OBJECT-TYPE
            SYNTAX OCTET STRING (SIZE (0..100))
            MAX-ACCESS read-only
            STATUS current
            DESCRIPTION
                "perPara."
            ::= { oduflex_tcm4Per24HCurEntry 6 }




-- -------------------------------------------------------------------------
-- Perfomance 24-HOUR History Data Table (RTRV-PER-<MOD2>)
-- -------------------------------------------------------------------------
        -- 1.3.6.1.4.1.2011.2.25.3.40.50.237.40
        oduflex_tcm4Per24HHisTable OBJECT-TYPE
          SYNTAX SEQUENCE OF Oduflex_tcm4Per24HHisEntry
          MAX-ACCESS not-accessible
          STATUS current
          DESCRIPTION
              "oduflex_tcm4Per24HHis."
          ::= { oduflex_tcm4 40 }

        -- 1.3.6.1.4.1.2011.2.25.3.40.50.237.40.1
        oduflex_tcm4Per24HHisEntry OBJECT-TYPE
            SYNTAX Oduflex_tcm4Per24HHisEntry
            MAX-ACCESS not-accessible
            STATUS current
            DESCRIPTION
                "oduflex_tcm4Per24HHis."
            INDEX {oduflex_tcm4Per24HHisEid, oduflex_tcm4Per24HHisParaLen, oduflex_tcm4Per24HHisPara, oduflex_tcm4Per24HHisDateTimeStart, oduflex_tcm4Per24HHisDateTimeEnd}
            ::= { oduflex_tcm4Per24HHisTable 1 }

        Oduflex_tcm4Per24HHisEntry ::=
            SEQUENCE {
                oduflex_tcm4Per24HHisEid
                    PerformanceEventType,
                oduflex_tcm4Per24HHisParaLen
                    INTEGER,
                oduflex_tcm4Per24HHisPara
                    OCTET STRING,
                oduflex_tcm4Per24HHisMonValue
                    OCTET STRING,
                oduflex_tcm4Per24HHisDateTimeStart
                    DateAndTime,
                oduflex_tcm4Per24HHisDateTimeEnd
                    DateAndTime,
                oduflex_tcm4Per24HHisVldty
                    INTEGER,
             }

        -- 1.3.6.1.4.1.2011.2.25.3.40.50.237.40.1.1
        oduflex_tcm4Per24HHisEid OBJECT-TYPE
            SYNTAX PerformanceEventType
            MAX-ACCESS read-only
            STATUS current
            DESCRIPTION
                "perEid."
            ::= { oduflex_tcm4Per24HHisEntry 1 }

        -- 1.3.6.1.4.1.2011.2.25.3.40.50.237.40.1.2
        oduflex_tcm4Per24HHisParaLen OBJECT-TYPE
            SYNTAX INTEGER
            MAX-ACCESS read-only
            STATUS current
            DESCRIPTION
                "perParaLen."
            ::= { oduflex_tcm4Per24HHisEntry 2 }

        -- 1.3.6.1.4.1.2011.2.25.3.40.50.237.40.1.3
        oduflex_tcm4Per24HHisPara OBJECT-TYPE
            SYNTAX OCTET STRING (SIZE (0..100))
            MAX-ACCESS read-only
            STATUS current
            DESCRIPTION
                "perPara."
            ::= { oduflex_tcm4Per24HHisEntry 3 }

        -- 1.3.6.1.4.1.2011.2.25.3.40.50.237.40.1.4
        oduflex_tcm4Per24HHisMonValue OBJECT-TYPE
            SYNTAX OCTET STRING (SIZE (0..100))
            MAX-ACCESS read-only
            STATUS current
            DESCRIPTION
                "perMonValue."
            ::= { oduflex_tcm4Per24HHisEntry 4 }

        -- 1.3.6.1.4.1.2011.2.25.3.40.50.237.40.1.5
        oduflex_tcm4Per24HHisDateTimeStart OBJECT-TYPE
            SYNTAX DateAndTime
            MAX-ACCESS read-only
            STATUS current
            DESCRIPTION
                "perDateTimeStart. "
            ::= { oduflex_tcm4Per24HHisEntry 5 }

        -- 1.3.6.1.4.1.2011.2.25.3.40.50.237.40.1.6
        oduflex_tcm4Per24HHisDateTimeEnd OBJECT-TYPE
            SYNTAX DateAndTime
            MAX-ACCESS read-only
            STATUS current
            DESCRIPTION
                "perDateTimeEnd. "
            ::= { oduflex_tcm4Per24HHisEntry 6 }

        -- 1.3.6.1.4.1.2011.2.25.3.40.50.237.40.1.7
        oduflex_tcm4Per24HHisVldty OBJECT-TYPE
            SYNTAX INTEGER
            MAX-ACCESS read-only
            STATUS current
            DESCRIPTION
                "perVldty. "
            ::= { oduflex_tcm4Per24HHisEntry 7 }




-- Alarm data
      -- 1.3.6.1.4.1.2011.2.25.3.40.50.238
      oduflex_tcm5 OBJECT IDENTIFIER ::={ optixGlobalNGWDM 238 }


-- -------------------------------------------------------------------------
-- Perfomance 15-MIN Current Data Table (RTRV-PER-<MOD2>)
-- -------------------------------------------------------------------------
        -- 1.3.6.1.4.1.2011.2.25.3.40.50.238.10
        oduflex_tcm5Per15MCurTable OBJECT-TYPE
          SYNTAX SEQUENCE OF Oduflex_tcm5Per15MCurEntry
          MAX-ACCESS not-accessible
          STATUS current
          DESCRIPTION
              "oduflex_tcm5Per15MCur."
          ::= { oduflex_tcm5 10 }

        -- 1.3.6.1.4.1.2011.2.25.3.40.50.238.10.1
        oduflex_tcm5Per15MCurEntry OBJECT-TYPE
            SYNTAX Oduflex_tcm5Per15MCurEntry
            MAX-ACCESS not-accessible
            STATUS current
            DESCRIPTION
              "oduflex_tcm5Per15MCur."
            INDEX { oduflex_tcm5Per15MCurEid, oduflex_tcm5Per15MCurPara }
            ::= { oduflex_tcm5Per15MCurTable 1 }

        Oduflex_tcm5Per15MCurEntry ::=
            SEQUENCE {
                oduflex_tcm5Per15MCurEid
                    PerformanceEventType,
                oduflex_tcm5Per15MCurMonValue
                    OCTET STRING,
                oduflex_tcm5Per15MCurVldty
                    INTEGER,
                oduflex_tcm5Per15MCurDateTime
                    DateAndTime,
                oduflex_tcm5Per15MCurParaLen
                    INTEGER,
                oduflex_tcm5Per15MCurPara
                    OCTET STRING
            }

        -- 1.3.6.1.4.1.2011.2.25.3.40.50.238.10.1.1
        oduflex_tcm5Per15MCurEid OBJECT-TYPE
            SYNTAX PerformanceEventType
            MAX-ACCESS read-only
            STATUS current
            DESCRIPTION
                "perEid."
            ::= { oduflex_tcm5Per15MCurEntry 1 }

        -- 1.3.6.1.4.1.2011.2.25.3.40.50.238.10.1.2
        oduflex_tcm5Per15MCurMonValue OBJECT-TYPE
            SYNTAX OCTET STRING (SIZE (0..100))
            MAX-ACCESS read-only
            STATUS current
            DESCRIPTION
                "perMonValue."
            ::= { oduflex_tcm5Per15MCurEntry 2 }

        -- 1.3.6.1.4.1.2011.2.25.3.40.50.238.10.1.3
        oduflex_tcm5Per15MCurVldty OBJECT-TYPE
            SYNTAX INTEGER
            MAX-ACCESS read-only
            STATUS current
            DESCRIPTION
                "perVldty. "
            ::= { oduflex_tcm5Per15MCurEntry 3 }

        -- 1.3.6.1.4.1.2011.2.25.3.40.50.238.10.1.4
        oduflex_tcm5Per15MCurDateTime OBJECT-TYPE
            SYNTAX DateAndTime
            MAX-ACCESS read-only
            STATUS current
            DESCRIPTION
                "perDateTime. "
            ::= { oduflex_tcm5Per15MCurEntry 4 }

        -- 1.3.6.1.4.1.2011.2.25.3.40.50.238.10.1.5
        oduflex_tcm5Per15MCurParaLen OBJECT-TYPE
            SYNTAX INTEGER
            MAX-ACCESS read-only
            STATUS current
            DESCRIPTION
                "perParaLen."
            ::= { oduflex_tcm5Per15MCurEntry 5 }

        -- 1.3.6.1.4.1.2011.2.25.3.40.50.238.10.1.6
        oduflex_tcm5Per15MCurPara OBJECT-TYPE
            SYNTAX OCTET STRING (SIZE (0..100))
            MAX-ACCESS read-only
            STATUS current
            DESCRIPTION
                "perPara."
            ::= { oduflex_tcm5Per15MCurEntry 6 }




-- -------------------------------------------------------------------------
-- Perfomance 15-MIN History Data Table (RTRV-PER-<MOD2>)
-- -------------------------------------------------------------------------
        -- 1.3.6.1.4.1.2011.2.25.3.40.50.238.20
        oduflex_tcm5Per15MHisTable OBJECT-TYPE
          SYNTAX SEQUENCE OF Oduflex_tcm5Per15MHisEntry
          MAX-ACCESS not-accessible
          STATUS current
          DESCRIPTION
              "oduflex_tcm5Per15MHis."
          ::= { oduflex_tcm5 20 }

        -- 1.3.6.1.4.1.2011.2.25.3.40.50.238.20.1
        oduflex_tcm5Per15MHisEntry OBJECT-TYPE
            SYNTAX Oduflex_tcm5Per15MHisEntry
            MAX-ACCESS not-accessible
            STATUS current
            DESCRIPTION
                "oduflex_tcm5Per15MHis."
            INDEX {oduflex_tcm5Per15MHisEid, oduflex_tcm5Per15MHisParaLen, oduflex_tcm5Per15MHisPara, oduflex_tcm5Per15MHisDateTimeStart, oduflex_tcm5Per15MHisDateTimeEnd}
            ::= { oduflex_tcm5Per15MHisTable 1 }

        Oduflex_tcm5Per15MHisEntry ::=
            SEQUENCE {
                oduflex_tcm5Per15MHisEid
                    PerformanceEventType,
                oduflex_tcm5Per15MHisParaLen
                    INTEGER,
                oduflex_tcm5Per15MHisPara
                    OCTET STRING,
                oduflex_tcm5Per15MHisMonValue
                    OCTET STRING,
                oduflex_tcm5Per15MHisDateTimeStart
                    DateAndTime,
                oduflex_tcm5Per15MHisDateTimeEnd
                    DateAndTime,
                oduflex_tcm5Per15MHisVldty
                    INTEGER,
             }

        -- 1.3.6.1.4.1.2011.2.25.3.40.50.238.20.1.1
        oduflex_tcm5Per15MHisEid OBJECT-TYPE
            SYNTAX PerformanceEventType
            MAX-ACCESS read-only
            STATUS current
            DESCRIPTION
                "perEid."
            ::= { oduflex_tcm5Per15MHisEntry 1 }

        -- 1.3.6.1.4.1.2011.2.25.3.40.50.238.20.1.2
        oduflex_tcm5Per15MHisParaLen OBJECT-TYPE
            SYNTAX INTEGER
            MAX-ACCESS read-only
            STATUS current
            DESCRIPTION
                "perParaLen."
            ::= { oduflex_tcm5Per15MHisEntry 2 }

        -- 1.3.6.1.4.1.2011.2.25.3.40.50.238.20.1.3
        oduflex_tcm5Per15MHisPara OBJECT-TYPE
            SYNTAX OCTET STRING (SIZE (0..100))
            MAX-ACCESS read-only
            STATUS current
            DESCRIPTION
                "perPara."
            ::= { oduflex_tcm5Per15MHisEntry 3 }

        -- 1.3.6.1.4.1.2011.2.25.3.40.50.238.20.1.4
        oduflex_tcm5Per15MHisMonValue OBJECT-TYPE
            SYNTAX OCTET STRING (SIZE (0..100))
            MAX-ACCESS read-only
            STATUS current
            DESCRIPTION
                "perMonValue."
            ::= { oduflex_tcm5Per15MHisEntry 4 }

        -- 1.3.6.1.4.1.2011.2.25.3.40.50.238.20.1.5
        oduflex_tcm5Per15MHisDateTimeStart OBJECT-TYPE
            SYNTAX DateAndTime
            MAX-ACCESS read-only
            STATUS current
            DESCRIPTION
                "perDateTimeStart. "
            ::= { oduflex_tcm5Per15MHisEntry 5 }

        -- 1.3.6.1.4.1.2011.2.25.3.40.50.238.20.1.6
        oduflex_tcm5Per15MHisDateTimeEnd OBJECT-TYPE
            SYNTAX DateAndTime
            MAX-ACCESS read-only
            STATUS current
            DESCRIPTION
                "perDateTimeEnd. "
            ::= { oduflex_tcm5Per15MHisEntry 6 }

        -- 1.3.6.1.4.1.2011.2.25.3.40.50.238.20.1.7
        oduflex_tcm5Per15MHisVldty OBJECT-TYPE
            SYNTAX INTEGER
            MAX-ACCESS read-only
            STATUS current
            DESCRIPTION
                "perVldty. "
            ::= { oduflex_tcm5Per15MHisEntry 7 }




-- -------------------------------------------------------------------------
-- Perfomance 24-HOUR Current Data Table (RTRV-PER-<MOD2>)
-- -------------------------------------------------------------------------
        -- 1.3.6.1.4.1.2011.2.25.3.40.50.238.30
        oduflex_tcm5Per24HCurTable OBJECT-TYPE
          SYNTAX SEQUENCE OF Oduflex_tcm5Per24HCurEntry
          MAX-ACCESS not-accessible
          STATUS current
          DESCRIPTION
              "oduflex_tcm5Per24HCur."
          ::= { oduflex_tcm5 30 }

        -- 1.3.6.1.4.1.2011.2.25.3.40.50.238.30.1
        oduflex_tcm5Per24HCurEntry OBJECT-TYPE
            SYNTAX Oduflex_tcm5Per24HCurEntry
            MAX-ACCESS not-accessible
            STATUS current
            DESCRIPTION
              "oduflex_tcm5Per24HCur."
            INDEX { oduflex_tcm5Per24HCurEid, oduflex_tcm5Per24HCurPara }
            ::= { oduflex_tcm5Per24HCurTable 1 }

        Oduflex_tcm5Per24HCurEntry ::=
            SEQUENCE {
                oduflex_tcm5Per24HCurEid
                    PerformanceEventType,
                oduflex_tcm5Per24HCurMonValue
                    OCTET STRING,
                oduflex_tcm5Per24HCurVldty
                    INTEGER,
                oduflex_tcm5Per24HCurDateTime
                    DateAndTime,
                oduflex_tcm5Per24HCurParaLen
                    INTEGER,
                oduflex_tcm5Per24HCurPara
                    OCTET STRING
            }

        -- 1.3.6.1.4.1.2011.2.25.3.40.50.238.30.1.1
        oduflex_tcm5Per24HCurEid OBJECT-TYPE
            SYNTAX PerformanceEventType
            MAX-ACCESS read-only
            STATUS current
            DESCRIPTION
                "perEid."
            ::= { oduflex_tcm5Per24HCurEntry 1 }

        -- 1.3.6.1.4.1.2011.2.25.3.40.50.238.30.1.2
        oduflex_tcm5Per24HCurMonValue OBJECT-TYPE
            SYNTAX OCTET STRING (SIZE (0..100))
            MAX-ACCESS read-only
            STATUS current
            DESCRIPTION
                "perMonValue."
            ::= { oduflex_tcm5Per24HCurEntry 2 }

        -- 1.3.6.1.4.1.2011.2.25.3.40.50.238.30.1.3
        oduflex_tcm5Per24HCurVldty OBJECT-TYPE
            SYNTAX INTEGER
            MAX-ACCESS read-only
            STATUS current
            DESCRIPTION
                "perVldty. "
            ::= { oduflex_tcm5Per24HCurEntry 3 }

        -- 1.3.6.1.4.1.2011.2.25.3.40.50.238.30.1.4
        oduflex_tcm5Per24HCurDateTime OBJECT-TYPE
            SYNTAX DateAndTime
            MAX-ACCESS read-only
            STATUS current
            DESCRIPTION
                "perDateTime. "
            ::= { oduflex_tcm5Per24HCurEntry 4 }

        -- 1.3.6.1.4.1.2011.2.25.3.40.50.238.30.1.5
        oduflex_tcm5Per24HCurParaLen OBJECT-TYPE
            SYNTAX INTEGER
            MAX-ACCESS read-only
            STATUS current
            DESCRIPTION
                "perParaLen."
            ::= { oduflex_tcm5Per24HCurEntry 5 }

        -- 1.3.6.1.4.1.2011.2.25.3.40.50.238.30.1.6
        oduflex_tcm5Per24HCurPara OBJECT-TYPE
            SYNTAX OCTET STRING (SIZE (0..100))
            MAX-ACCESS read-only
            STATUS current
            DESCRIPTION
                "perPara."
            ::= { oduflex_tcm5Per24HCurEntry 6 }




-- -------------------------------------------------------------------------
-- Perfomance 24-HOUR History Data Table (RTRV-PER-<MOD2>)
-- -------------------------------------------------------------------------
        -- 1.3.6.1.4.1.2011.2.25.3.40.50.238.40
        oduflex_tcm5Per24HHisTable OBJECT-TYPE
          SYNTAX SEQUENCE OF Oduflex_tcm5Per24HHisEntry
          MAX-ACCESS not-accessible
          STATUS current
          DESCRIPTION
              "oduflex_tcm5Per24HHis."
          ::= { oduflex_tcm5 40 }

        -- 1.3.6.1.4.1.2011.2.25.3.40.50.238.40.1
        oduflex_tcm5Per24HHisEntry OBJECT-TYPE
            SYNTAX Oduflex_tcm5Per24HHisEntry
            MAX-ACCESS not-accessible
            STATUS current
            DESCRIPTION
                "oduflex_tcm5Per24HHis."
            INDEX {oduflex_tcm5Per24HHisEid, oduflex_tcm5Per24HHisParaLen, oduflex_tcm5Per24HHisPara, oduflex_tcm5Per24HHisDateTimeStart, oduflex_tcm5Per24HHisDateTimeEnd}
            ::= { oduflex_tcm5Per24HHisTable 1 }

        Oduflex_tcm5Per24HHisEntry ::=
            SEQUENCE {
                oduflex_tcm5Per24HHisEid
                    PerformanceEventType,
                oduflex_tcm5Per24HHisParaLen
                    INTEGER,
                oduflex_tcm5Per24HHisPara
                    OCTET STRING,
                oduflex_tcm5Per24HHisMonValue
                    OCTET STRING,
                oduflex_tcm5Per24HHisDateTimeStart
                    DateAndTime,
                oduflex_tcm5Per24HHisDateTimeEnd
                    DateAndTime,
                oduflex_tcm5Per24HHisVldty
                    INTEGER,
             }

        -- 1.3.6.1.4.1.2011.2.25.3.40.50.238.40.1.1
        oduflex_tcm5Per24HHisEid OBJECT-TYPE
            SYNTAX PerformanceEventType
            MAX-ACCESS read-only
            STATUS current
            DESCRIPTION
                "perEid."
            ::= { oduflex_tcm5Per24HHisEntry 1 }

        -- 1.3.6.1.4.1.2011.2.25.3.40.50.238.40.1.2
        oduflex_tcm5Per24HHisParaLen OBJECT-TYPE
            SYNTAX INTEGER
            MAX-ACCESS read-only
            STATUS current
            DESCRIPTION
                "perParaLen."
            ::= { oduflex_tcm5Per24HHisEntry 2 }

        -- 1.3.6.1.4.1.2011.2.25.3.40.50.238.40.1.3
        oduflex_tcm5Per24HHisPara OBJECT-TYPE
            SYNTAX OCTET STRING (SIZE (0..100))
            MAX-ACCESS read-only
            STATUS current
            DESCRIPTION
                "perPara."
            ::= { oduflex_tcm5Per24HHisEntry 3 }

        -- 1.3.6.1.4.1.2011.2.25.3.40.50.238.40.1.4
        oduflex_tcm5Per24HHisMonValue OBJECT-TYPE
            SYNTAX OCTET STRING (SIZE (0..100))
            MAX-ACCESS read-only
            STATUS current
            DESCRIPTION
                "perMonValue."
            ::= { oduflex_tcm5Per24HHisEntry 4 }

        -- 1.3.6.1.4.1.2011.2.25.3.40.50.238.40.1.5
        oduflex_tcm5Per24HHisDateTimeStart OBJECT-TYPE
            SYNTAX DateAndTime
            MAX-ACCESS read-only
            STATUS current
            DESCRIPTION
                "perDateTimeStart. "
            ::= { oduflex_tcm5Per24HHisEntry 5 }

        -- 1.3.6.1.4.1.2011.2.25.3.40.50.238.40.1.6
        oduflex_tcm5Per24HHisDateTimeEnd OBJECT-TYPE
            SYNTAX DateAndTime
            MAX-ACCESS read-only
            STATUS current
            DESCRIPTION
                "perDateTimeEnd. "
            ::= { oduflex_tcm5Per24HHisEntry 6 }

        -- 1.3.6.1.4.1.2011.2.25.3.40.50.238.40.1.7
        oduflex_tcm5Per24HHisVldty OBJECT-TYPE
            SYNTAX INTEGER
            MAX-ACCESS read-only
            STATUS current
            DESCRIPTION
                "perVldty. "
            ::= { oduflex_tcm5Per24HHisEntry 7 }




-- Alarm data
      -- 1.3.6.1.4.1.2011.2.25.3.40.50.239
      oduflex_tcm6 OBJECT IDENTIFIER ::={ optixGlobalNGWDM 239 }


-- -------------------------------------------------------------------------
-- Perfomance 15-MIN Current Data Table (RTRV-PER-<MOD2>)
-- -------------------------------------------------------------------------
        -- 1.3.6.1.4.1.2011.2.25.3.40.50.239.10
        oduflex_tcm6Per15MCurTable OBJECT-TYPE
          SYNTAX SEQUENCE OF Oduflex_tcm6Per15MCurEntry
          MAX-ACCESS not-accessible
          STATUS current
          DESCRIPTION
              "oduflex_tcm6Per15MCur."
          ::= { oduflex_tcm6 10 }

        -- 1.3.6.1.4.1.2011.2.25.3.40.50.239.10.1
        oduflex_tcm6Per15MCurEntry OBJECT-TYPE
            SYNTAX Oduflex_tcm6Per15MCurEntry
            MAX-ACCESS not-accessible
            STATUS current
            DESCRIPTION
              "oduflex_tcm6Per15MCur."
            INDEX { oduflex_tcm6Per15MCurEid, oduflex_tcm6Per15MCurPara }
            ::= { oduflex_tcm6Per15MCurTable 1 }

        Oduflex_tcm6Per15MCurEntry ::=
            SEQUENCE {
                oduflex_tcm6Per15MCurEid
                    PerformanceEventType,
                oduflex_tcm6Per15MCurMonValue
                    OCTET STRING,
                oduflex_tcm6Per15MCurVldty
                    INTEGER,
                oduflex_tcm6Per15MCurDateTime
                    DateAndTime,
                oduflex_tcm6Per15MCurParaLen
                    INTEGER,
                oduflex_tcm6Per15MCurPara
                    OCTET STRING
            }

        -- 1.3.6.1.4.1.2011.2.25.3.40.50.239.10.1.1
        oduflex_tcm6Per15MCurEid OBJECT-TYPE
            SYNTAX PerformanceEventType
            MAX-ACCESS read-only
            STATUS current
            DESCRIPTION
                "perEid."
            ::= { oduflex_tcm6Per15MCurEntry 1 }

        -- 1.3.6.1.4.1.2011.2.25.3.40.50.239.10.1.2
        oduflex_tcm6Per15MCurMonValue OBJECT-TYPE
            SYNTAX OCTET STRING (SIZE (0..100))
            MAX-ACCESS read-only
            STATUS current
            DESCRIPTION
                "perMonValue."
            ::= { oduflex_tcm6Per15MCurEntry 2 }

        -- 1.3.6.1.4.1.2011.2.25.3.40.50.239.10.1.3
        oduflex_tcm6Per15MCurVldty OBJECT-TYPE
            SYNTAX INTEGER
            MAX-ACCESS read-only
            STATUS current
            DESCRIPTION
                "perVldty. "
            ::= { oduflex_tcm6Per15MCurEntry 3 }

        -- 1.3.6.1.4.1.2011.2.25.3.40.50.239.10.1.4
        oduflex_tcm6Per15MCurDateTime OBJECT-TYPE
            SYNTAX DateAndTime
            MAX-ACCESS read-only
            STATUS current
            DESCRIPTION
                "perDateTime. "
            ::= { oduflex_tcm6Per15MCurEntry 4 }

        -- 1.3.6.1.4.1.2011.2.25.3.40.50.239.10.1.5
        oduflex_tcm6Per15MCurParaLen OBJECT-TYPE
            SYNTAX INTEGER
            MAX-ACCESS read-only
            STATUS current
            DESCRIPTION
                "perParaLen."
            ::= { oduflex_tcm6Per15MCurEntry 5 }

        -- 1.3.6.1.4.1.2011.2.25.3.40.50.239.10.1.6
        oduflex_tcm6Per15MCurPara OBJECT-TYPE
            SYNTAX OCTET STRING (SIZE (0..100))
            MAX-ACCESS read-only
            STATUS current
            DESCRIPTION
                "perPara."
            ::= { oduflex_tcm6Per15MCurEntry 6 }




-- -------------------------------------------------------------------------
-- Perfomance 15-MIN History Data Table (RTRV-PER-<MOD2>)
-- -------------------------------------------------------------------------
        -- 1.3.6.1.4.1.2011.2.25.3.40.50.239.20
        oduflex_tcm6Per15MHisTable OBJECT-TYPE
          SYNTAX SEQUENCE OF Oduflex_tcm6Per15MHisEntry
          MAX-ACCESS not-accessible
          STATUS current
          DESCRIPTION
              "oduflex_tcm6Per15MHis."
          ::= { oduflex_tcm6 20 }

        -- 1.3.6.1.4.1.2011.2.25.3.40.50.239.20.1
        oduflex_tcm6Per15MHisEntry OBJECT-TYPE
            SYNTAX Oduflex_tcm6Per15MHisEntry
            MAX-ACCESS not-accessible
            STATUS current
            DESCRIPTION
                "oduflex_tcm6Per15MHis."
            INDEX {oduflex_tcm6Per15MHisEid, oduflex_tcm6Per15MHisParaLen, oduflex_tcm6Per15MHisPara, oduflex_tcm6Per15MHisDateTimeStart, oduflex_tcm6Per15MHisDateTimeEnd}
            ::= { oduflex_tcm6Per15MHisTable 1 }

        Oduflex_tcm6Per15MHisEntry ::=
            SEQUENCE {
                oduflex_tcm6Per15MHisEid
                    PerformanceEventType,
                oduflex_tcm6Per15MHisParaLen
                    INTEGER,
                oduflex_tcm6Per15MHisPara
                    OCTET STRING,
                oduflex_tcm6Per15MHisMonValue
                    OCTET STRING,
                oduflex_tcm6Per15MHisDateTimeStart
                    DateAndTime,
                oduflex_tcm6Per15MHisDateTimeEnd
                    DateAndTime,
                oduflex_tcm6Per15MHisVldty
                    INTEGER,
             }

        -- 1.3.6.1.4.1.2011.2.25.3.40.50.239.20.1.1
        oduflex_tcm6Per15MHisEid OBJECT-TYPE
            SYNTAX PerformanceEventType
            MAX-ACCESS read-only
            STATUS current
            DESCRIPTION
                "perEid."
            ::= { oduflex_tcm6Per15MHisEntry 1 }

        -- 1.3.6.1.4.1.2011.2.25.3.40.50.239.20.1.2
        oduflex_tcm6Per15MHisParaLen OBJECT-TYPE
            SYNTAX INTEGER
            MAX-ACCESS read-only
            STATUS current
            DESCRIPTION
                "perParaLen."
            ::= { oduflex_tcm6Per15MHisEntry 2 }

        -- 1.3.6.1.4.1.2011.2.25.3.40.50.239.20.1.3
        oduflex_tcm6Per15MHisPara OBJECT-TYPE
            SYNTAX OCTET STRING (SIZE (0..100))
            MAX-ACCESS read-only
            STATUS current
            DESCRIPTION
                "perPara."
            ::= { oduflex_tcm6Per15MHisEntry 3 }

        -- 1.3.6.1.4.1.2011.2.25.3.40.50.239.20.1.4
        oduflex_tcm6Per15MHisMonValue OBJECT-TYPE
            SYNTAX OCTET STRING (SIZE (0..100))
            MAX-ACCESS read-only
            STATUS current
            DESCRIPTION
                "perMonValue."
            ::= { oduflex_tcm6Per15MHisEntry 4 }

        -- 1.3.6.1.4.1.2011.2.25.3.40.50.239.20.1.5
        oduflex_tcm6Per15MHisDateTimeStart OBJECT-TYPE
            SYNTAX DateAndTime
            MAX-ACCESS read-only
            STATUS current
            DESCRIPTION
                "perDateTimeStart. "
            ::= { oduflex_tcm6Per15MHisEntry 5 }

        -- 1.3.6.1.4.1.2011.2.25.3.40.50.239.20.1.6
        oduflex_tcm6Per15MHisDateTimeEnd OBJECT-TYPE
            SYNTAX DateAndTime
            MAX-ACCESS read-only
            STATUS current
            DESCRIPTION
                "perDateTimeEnd. "
            ::= { oduflex_tcm6Per15MHisEntry 6 }

        -- 1.3.6.1.4.1.2011.2.25.3.40.50.239.20.1.7
        oduflex_tcm6Per15MHisVldty OBJECT-TYPE
            SYNTAX INTEGER
            MAX-ACCESS read-only
            STATUS current
            DESCRIPTION
                "perVldty. "
            ::= { oduflex_tcm6Per15MHisEntry 7 }




-- -------------------------------------------------------------------------
-- Perfomance 24-HOUR Current Data Table (RTRV-PER-<MOD2>)
-- -------------------------------------------------------------------------
        -- 1.3.6.1.4.1.2011.2.25.3.40.50.239.30
        oduflex_tcm6Per24HCurTable OBJECT-TYPE
          SYNTAX SEQUENCE OF Oduflex_tcm6Per24HCurEntry
          MAX-ACCESS not-accessible
          STATUS current
          DESCRIPTION
              "oduflex_tcm6Per24HCur."
          ::= { oduflex_tcm6 30 }

        -- 1.3.6.1.4.1.2011.2.25.3.40.50.239.30.1
        oduflex_tcm6Per24HCurEntry OBJECT-TYPE
            SYNTAX Oduflex_tcm6Per24HCurEntry
            MAX-ACCESS not-accessible
            STATUS current
            DESCRIPTION
              "oduflex_tcm6Per24HCur."
            INDEX { oduflex_tcm6Per24HCurEid, oduflex_tcm6Per24HCurPara }
            ::= { oduflex_tcm6Per24HCurTable 1 }

        Oduflex_tcm6Per24HCurEntry ::=
            SEQUENCE {
                oduflex_tcm6Per24HCurEid
                    PerformanceEventType,
                oduflex_tcm6Per24HCurMonValue
                    OCTET STRING,
                oduflex_tcm6Per24HCurVldty
                    INTEGER,
                oduflex_tcm6Per24HCurDateTime
                    DateAndTime,
                oduflex_tcm6Per24HCurParaLen
                    INTEGER,
                oduflex_tcm6Per24HCurPara
                    OCTET STRING
            }

        -- 1.3.6.1.4.1.2011.2.25.3.40.50.239.30.1.1
        oduflex_tcm6Per24HCurEid OBJECT-TYPE
            SYNTAX PerformanceEventType
            MAX-ACCESS read-only
            STATUS current
            DESCRIPTION
                "perEid."
            ::= { oduflex_tcm6Per24HCurEntry 1 }

        -- 1.3.6.1.4.1.2011.2.25.3.40.50.239.30.1.2
        oduflex_tcm6Per24HCurMonValue OBJECT-TYPE
            SYNTAX OCTET STRING (SIZE (0..100))
            MAX-ACCESS read-only
            STATUS current
            DESCRIPTION
                "perMonValue."
            ::= { oduflex_tcm6Per24HCurEntry 2 }

        -- 1.3.6.1.4.1.2011.2.25.3.40.50.239.30.1.3
        oduflex_tcm6Per24HCurVldty OBJECT-TYPE
            SYNTAX INTEGER
            MAX-ACCESS read-only
            STATUS current
            DESCRIPTION
                "perVldty. "
            ::= { oduflex_tcm6Per24HCurEntry 3 }

        -- 1.3.6.1.4.1.2011.2.25.3.40.50.239.30.1.4
        oduflex_tcm6Per24HCurDateTime OBJECT-TYPE
            SYNTAX DateAndTime
            MAX-ACCESS read-only
            STATUS current
            DESCRIPTION
                "perDateTime. "
            ::= { oduflex_tcm6Per24HCurEntry 4 }

        -- 1.3.6.1.4.1.2011.2.25.3.40.50.239.30.1.5
        oduflex_tcm6Per24HCurParaLen OBJECT-TYPE
            SYNTAX INTEGER
            MAX-ACCESS read-only
            STATUS current
            DESCRIPTION
                "perParaLen."
            ::= { oduflex_tcm6Per24HCurEntry 5 }

        -- 1.3.6.1.4.1.2011.2.25.3.40.50.239.30.1.6
        oduflex_tcm6Per24HCurPara OBJECT-TYPE
            SYNTAX OCTET STRING (SIZE (0..100))
            MAX-ACCESS read-only
            STATUS current
            DESCRIPTION
                "perPara."
            ::= { oduflex_tcm6Per24HCurEntry 6 }




-- -------------------------------------------------------------------------
-- Perfomance 24-HOUR History Data Table (RTRV-PER-<MOD2>)
-- -------------------------------------------------------------------------
        -- 1.3.6.1.4.1.2011.2.25.3.40.50.239.40
        oduflex_tcm6Per24HHisTable OBJECT-TYPE
          SYNTAX SEQUENCE OF Oduflex_tcm6Per24HHisEntry
          MAX-ACCESS not-accessible
          STATUS current
          DESCRIPTION
              "oduflex_tcm6Per24HHis."
          ::= { oduflex_tcm6 40 }

        -- 1.3.6.1.4.1.2011.2.25.3.40.50.239.40.1
        oduflex_tcm6Per24HHisEntry OBJECT-TYPE
            SYNTAX Oduflex_tcm6Per24HHisEntry
            MAX-ACCESS not-accessible
            STATUS current
            DESCRIPTION
                "oduflex_tcm6Per24HHis."
            INDEX {oduflex_tcm6Per24HHisEid, oduflex_tcm6Per24HHisParaLen, oduflex_tcm6Per24HHisPara, oduflex_tcm6Per24HHisDateTimeStart, oduflex_tcm6Per24HHisDateTimeEnd}
            ::= { oduflex_tcm6Per24HHisTable 1 }

        Oduflex_tcm6Per24HHisEntry ::=
            SEQUENCE {
                oduflex_tcm6Per24HHisEid
                    PerformanceEventType,
                oduflex_tcm6Per24HHisParaLen
                    INTEGER,
                oduflex_tcm6Per24HHisPara
                    OCTET STRING,
                oduflex_tcm6Per24HHisMonValue
                    OCTET STRING,
                oduflex_tcm6Per24HHisDateTimeStart
                    DateAndTime,
                oduflex_tcm6Per24HHisDateTimeEnd
                    DateAndTime,
                oduflex_tcm6Per24HHisVldty
                    INTEGER,
             }

        -- 1.3.6.1.4.1.2011.2.25.3.40.50.239.40.1.1
        oduflex_tcm6Per24HHisEid OBJECT-TYPE
            SYNTAX PerformanceEventType
            MAX-ACCESS read-only
            STATUS current
            DESCRIPTION
                "perEid."
            ::= { oduflex_tcm6Per24HHisEntry 1 }

        -- 1.3.6.1.4.1.2011.2.25.3.40.50.239.40.1.2
        oduflex_tcm6Per24HHisParaLen OBJECT-TYPE
            SYNTAX INTEGER
            MAX-ACCESS read-only
            STATUS current
            DESCRIPTION
                "perParaLen."
            ::= { oduflex_tcm6Per24HHisEntry 2 }

        -- 1.3.6.1.4.1.2011.2.25.3.40.50.239.40.1.3
        oduflex_tcm6Per24HHisPara OBJECT-TYPE
            SYNTAX OCTET STRING (SIZE (0..100))
            MAX-ACCESS read-only
            STATUS current
            DESCRIPTION
                "perPara."
            ::= { oduflex_tcm6Per24HHisEntry 3 }

        -- 1.3.6.1.4.1.2011.2.25.3.40.50.239.40.1.4
        oduflex_tcm6Per24HHisMonValue OBJECT-TYPE
            SYNTAX OCTET STRING (SIZE (0..100))
            MAX-ACCESS read-only
            STATUS current
            DESCRIPTION
                "perMonValue."
            ::= { oduflex_tcm6Per24HHisEntry 4 }

        -- 1.3.6.1.4.1.2011.2.25.3.40.50.239.40.1.5
        oduflex_tcm6Per24HHisDateTimeStart OBJECT-TYPE
            SYNTAX DateAndTime
            MAX-ACCESS read-only
            STATUS current
            DESCRIPTION
                "perDateTimeStart. "
            ::= { oduflex_tcm6Per24HHisEntry 5 }

        -- 1.3.6.1.4.1.2011.2.25.3.40.50.239.40.1.6
        oduflex_tcm6Per24HHisDateTimeEnd OBJECT-TYPE
            SYNTAX DateAndTime
            MAX-ACCESS read-only
            STATUS current
            DESCRIPTION
                "perDateTimeEnd. "
            ::= { oduflex_tcm6Per24HHisEntry 6 }

        -- 1.3.6.1.4.1.2011.2.25.3.40.50.239.40.1.7
        oduflex_tcm6Per24HHisVldty OBJECT-TYPE
            SYNTAX INTEGER
            MAX-ACCESS read-only
            STATUS current
            DESCRIPTION
                "perVldty. "
            ::= { oduflex_tcm6Per24HHisEntry 7 }





--  Alarm data
        -- 1.3.6.1.4.1.2011.2.25.3.40.50.76
        new_board OBJECT IDENTIFIER ::= { optixGlobalNGWDM 76 }

-- -------------------------------------------------------------------------
-- Perfomance 15-MIN Current Data Table (RTRV-PER-<MOD2>)
-- -------------------------------------------------------------------------
        -- 1.3.6.1.4.1.2011.2.25.3.40.50.76.10
        new_boardPer15mCurTable OBJECT-TYPE
            SYNTAX SEQUENCE OF New_boardPer15mCurEntry
            MAX-ACCESS not-accessible
            STATUS current
            DESCRIPTION
                "new_boardPer15mCur."
            ::= { new_board 10 }

        -- 1.3.6.1.4.1.2011.2.25.3.40.50.76.10.1
        new_boardPer15mCurEntry OBJECT-TYPE
            SYNTAX New_boardPer15mCurEntry
            MAX-ACCESS not-accessible
            STATUS current
            DESCRIPTION
                "new_boardPer15mCur."
            INDEX {new_boardPer15mCurEid, new_boardPer15mCurPara}
            ::= { new_boardPer15mCurTable 1 }

        New_boardPer15mCurEntry ::=
            SEQUENCE {
                new_boardPer15mCurEid
                    PerformanceEventType,
                new_boardPer15mCurMonValue
                    OCTET STRING,
                new_boardPer15mCurVldty
                    INTEGER,
                new_boardPer15mCurDateTime
                    DateAndTime,
                new_boardPer15mCurParaLen
                    INTEGER,
                new_boardPer15mCurPara
                    OCTET STRING
             }

        -- 1.3.6.1.4.1.2011.2.25.3.40.50.76.10.1.1
        new_boardPer15mCurEid OBJECT-TYPE
            SYNTAX PerformanceEventType
            MAX-ACCESS read-only
            STATUS current
            DESCRIPTION
                "perEid."
            ::= { new_boardPer15mCurEntry 1 }

        -- 1.3.6.1.4.1.2011.2.25.3.40.50.76.10.1.2
        new_boardPer15mCurMonValue OBJECT-TYPE
            SYNTAX OCTET STRING (SIZE (0..100))
            MAX-ACCESS read-only
            STATUS current
            DESCRIPTION
                "perMonValue."
            ::= { new_boardPer15mCurEntry 2 }

        -- 1.3.6.1.4.1.2011.2.25.3.40.50.76.10.3
        new_boardPer15mCurVldty OBJECT-TYPE
            SYNTAX INTEGER
            MAX-ACCESS read-only
            STATUS current
            DESCRIPTION
                "perVldty. "
            ::= { new_boardPer15mCurEntry 3 }

        -- 1.3.6.1.4.1.2011.2.25.3.40.50.76.10.1.4
        new_boardPer15mCurDateTime OBJECT-TYPE
            SYNTAX DateAndTime
            MAX-ACCESS read-only
            STATUS current
            DESCRIPTION
                "perDateTime. "
            ::= { new_boardPer15mCurEntry 4 }

        -- 1.3.6.1.4.1.2011.2.25.3.40.50.76.10.1.5
        new_boardPer15mCurParaLen OBJECT-TYPE
            SYNTAX INTEGER
            MAX-ACCESS read-only
            STATUS current
            DESCRIPTION
                "perParaLen."
            ::= { new_boardPer15mCurEntry 5 }

        -- 1.3.6.1.4.1.2011.2.25.3.40.50.76.10.1.6
        new_boardPer15mCurPara OBJECT-TYPE
            SYNTAX OCTET STRING (SIZE (0..100))
            MAX-ACCESS read-only
            STATUS current
            DESCRIPTION
                "perPara."
            ::= { new_boardPer15mCurEntry 6 }


-- -------------------------------------------------------------------------
-- Perfomance 15-MIN History Data Table (RTRV-PER-<MOD2>)
-- -------------------------------------------------------------------------
        new_boardPer15MHisTable OBJECT-TYPE
            SYNTAX SEQUENCE OF New_boardPer15MHisEntry
            MAX-ACCESS not-accessible
            STATUS current
            DESCRIPTION
                "new_boardPer15MHis."
            ::= { new_board 20 }


        new_boardPer15MHisEntry OBJECT-TYPE
            SYNTAX New_boardPer15MHisEntry
            MAX-ACCESS not-accessible
            STATUS current
            DESCRIPTION
                "new_boardPer15MHis."
            INDEX {new_boardPer15MHisEid, new_boardPer15MHisParaLen, new_boardPer15MHisPara, new_boardPer15MHisDateTimeStart, new_boardPer15MHisDateTimeEnd}
            ::= { new_boardPer15MHisTable 1 }

        New_boardPer15MHisEntry ::=
            SEQUENCE {
                new_boardPer15MHisEid
                    PerformanceEventType,
                new_boardPer15MHisParaLen
                    INTEGER,
                new_boardPer15MHisPara
                    OCTET STRING,
                new_boardPer15MHisMonValue
                    OCTET STRING,
                new_boardPer15MHisDateTimeStart
                    DateAndTime,
                new_boardPer15MHisDateTimeEnd
                    DateAndTime,
                new_boardPer15MHisVldty
                    INTEGER,
             }

        new_boardPer15MHisEid OBJECT-TYPE
            SYNTAX PerformanceEventType
            MAX-ACCESS read-only
            STATUS current
            DESCRIPTION
                "perEid."
            ::= { new_boardPer15MHisEntry 1 }

        new_boardPer15MHisParaLen OBJECT-TYPE
            SYNTAX INTEGER
            MAX-ACCESS read-only
            STATUS current
            DESCRIPTION
                "perParaLen."
            ::= { new_boardPer15MHisEntry 2 }


        new_boardPer15MHisPara OBJECT-TYPE
            SYNTAX OCTET STRING (SIZE (0..100))
            MAX-ACCESS read-only
            STATUS current
            DESCRIPTION
                "perPara."
            ::= { new_boardPer15MHisEntry 3 }



        new_boardPer15MHisMonValue OBJECT-TYPE
            SYNTAX OCTET STRING (SIZE (0..100))
            MAX-ACCESS read-only
            STATUS current
            DESCRIPTION
                "perMonValue."
            ::= { new_boardPer15MHisEntry 4 }



        new_boardPer15MHisDateTimeStart OBJECT-TYPE
            SYNTAX DateAndTime
            MAX-ACCESS read-only
            STATUS current
            DESCRIPTION
                "perDateTimeStart. "
            ::= { new_boardPer15MHisEntry 5 }

        new_boardPer15MHisDateTimeEnd OBJECT-TYPE
            SYNTAX DateAndTime
            MAX-ACCESS read-only
            STATUS current
            DESCRIPTION
                "perDateTimeEnd. "
            ::= { new_boardPer15MHisEntry 6 }


        new_boardPer15MHisVldty OBJECT-TYPE
            SYNTAX INTEGER
            MAX-ACCESS read-only
            STATUS current
            DESCRIPTION
                "perVldty. "
            ::= { new_boardPer15MHisEntry 7 }


-- -------------------------------------------------------------------------
-- Perfomance 24-HOUR Current Data Table (RTRV-PER-<MOD2>)
-- -------------------------------------------------------------------------
        new_boardPer24HCurTable OBJECT-TYPE
            SYNTAX SEQUENCE OF New_boardPer24HCurEntry
            MAX-ACCESS not-accessible
            STATUS current
            DESCRIPTION
                "new_boardPer24HCur."
            ::= { new_board 30 }


        new_boardPer24HCurEntry OBJECT-TYPE
            SYNTAX New_boardPer24HCurEntry
            MAX-ACCESS not-accessible
            STATUS current
            DESCRIPTION
                "new_boardPer24HCur."
            INDEX {new_boardPer24HCurEid, new_boardPer24HCurPara}
            ::= { new_boardPer24HCurTable 1 }

        New_boardPer24HCurEntry ::=
            SEQUENCE {
                new_boardPer24HCurEid
                    PerformanceEventType,
                new_boardPer24HCurMonValue
                    OCTET STRING,
                new_boardPer24HCurVldty
                    INTEGER,
                new_boardPer24HCurDateTime
                    DateAndTime,
                new_boardPer24HCurParaLen
                    INTEGER,
                new_boardPer24HCurPara
                    OCTET STRING
             }


        new_boardPer24HCurEid OBJECT-TYPE
            SYNTAX PerformanceEventType
            MAX-ACCESS read-only
            STATUS current
            DESCRIPTION
                "perEid."
            ::= { new_boardPer24HCurEntry 1 }


        new_boardPer24HCurMonValue OBJECT-TYPE
            SYNTAX OCTET STRING (SIZE (0..100))
            MAX-ACCESS read-only
            STATUS current
            DESCRIPTION
                "perMonValue."
            ::= { new_boardPer24HCurEntry 2 }


        new_boardPer24HCurVldty OBJECT-TYPE
            SYNTAX INTEGER
            MAX-ACCESS read-only
            STATUS current
            DESCRIPTION
                "perVldty. "
            ::= { new_boardPer24HCurEntry 3 }


        new_boardPer24HCurDateTime OBJECT-TYPE
            SYNTAX DateAndTime
            MAX-ACCESS read-only
            STATUS current
            DESCRIPTION
                "perDateTime. "
            ::= { new_boardPer24HCurEntry 4 }


        new_boardPer24HCurParaLen OBJECT-TYPE
            SYNTAX INTEGER
            MAX-ACCESS read-only
            STATUS current
            DESCRIPTION
                "perParaLen."
            ::= { new_boardPer24HCurEntry 5 }


        new_boardPer24HCurPara OBJECT-TYPE
            SYNTAX OCTET STRING (SIZE (0..100))
            MAX-ACCESS read-only
            STATUS current
            DESCRIPTION
                "perPara."
            ::= { new_boardPer24HCurEntry 6 }


-- -------------------------------------------------------------------------
-- Perfomance 24-HOUR History Data Table (RTRV-PER-<MOD2>)
-- -------------------------------------------------------------------------
        new_boardPer24HHisTable OBJECT-TYPE
            SYNTAX SEQUENCE OF New_boardPer24HHisEntry
            MAX-ACCESS not-accessible
            STATUS current
            DESCRIPTION
                "new_boardPer24HHis."
            ::= { new_board 40 }


        new_boardPer24HHisEntry OBJECT-TYPE
            SYNTAX New_boardPer24HHisEntry
            MAX-ACCESS not-accessible
            STATUS current
            DESCRIPTION
                "new_boardPer24HHis."
            INDEX {new_boardPer24HHisEid, new_boardPer24HHisParaLen, new_boardPer24HHisPara, new_boardPer24HHisDateTimeStart, new_boardPer24HHisDateTimeEnd}
            ::= { new_boardPer24HHisTable 1 }

        New_boardPer24HHisEntry ::=
            SEQUENCE {
                new_boardPer24HHisEid
                    PerformanceEventType,
              new_boardPer24HHisParaLen
                    INTEGER,
                new_boardPer24HHisPara
                    OCTET STRING,
                new_boardPer24HHisMonValue
                    OCTET STRING,
                new_boardPer24HHisDateTimeStart
                    DateAndTime,
                new_boardPer24HHisDateTimeEnd
                    DateAndTime,
                new_boardPer24HHisVldty
                    INTEGER,
             }

        new_boardPer24HHisEid OBJECT-TYPE
            SYNTAX PerformanceEventType
            MAX-ACCESS read-only
            STATUS current
            DESCRIPTION
                "perEid."
            ::= { new_boardPer24HHisEntry 1 }

        new_boardPer24HHisParaLen OBJECT-TYPE
            SYNTAX INTEGER
            MAX-ACCESS read-only
            STATUS current
            DESCRIPTION
                "perParaLen."
            ::= { new_boardPer24HHisEntry 2 }


        new_boardPer24HHisPara OBJECT-TYPE
            SYNTAX OCTET STRING (SIZE (0..100))
            MAX-ACCESS read-only
            STATUS current
            DESCRIPTION
                "perPara."
            ::= { new_boardPer24HHisEntry 3 }



        new_boardPer24HHisMonValue OBJECT-TYPE
            SYNTAX OCTET STRING (SIZE (0..100))
            MAX-ACCESS read-only
            STATUS current
            DESCRIPTION
                "perMonValue."
            ::= { new_boardPer24HHisEntry 4 }



        new_boardPer24HHisDateTimeStart OBJECT-TYPE
            SYNTAX DateAndTime
            MAX-ACCESS read-only
            STATUS current
            DESCRIPTION
                "perDateTimeStart. "
            ::= { new_boardPer24HHisEntry 5 }

        new_boardPer24HHisDateTimeEnd OBJECT-TYPE
            SYNTAX DateAndTime
            MAX-ACCESS read-only
            STATUS current
            DESCRIPTION
                "perDateTimeEnd. "
            ::= { new_boardPer24HHisEntry 6 }


        new_boardPer24HHisVldty OBJECT-TYPE
            SYNTAX INTEGER
            MAX-ACCESS read-only
            STATUS current
            DESCRIPTION
                "perVldty. "
            ::= { new_boardPer24HHisEntry 7 }

--  Alarm data
        -- 1.3.6.1.4.1.2011.2.25.3.40.50.79
        new_power_board OBJECT IDENTIFIER ::= { optixGlobalNGWDM 79 }

-- -------------------------------------------------------------------------
-- Perfomance 15-MIN Current Data Table (RTRV-PER-<MOD2>)
-- -------------------------------------------------------------------------
        -- 1.3.6.1.4.1.2011.2.25.3.40.50.79.10
        new_power_boardPer15mCurTable OBJECT-TYPE
            SYNTAX SEQUENCE OF New_power_boardPer15mCurEntry
            MAX-ACCESS not-accessible
            STATUS current
            DESCRIPTION
                "new_power_boardPer15mCur."
            ::= { new_power_board 10 }

        -- 1.3.6.1.4.1.2011.2.25.3.40.50.79.10.1
        new_power_boardPer15mCurEntry OBJECT-TYPE
            SYNTAX New_power_boardPer15mCurEntry
            MAX-ACCESS not-accessible
            STATUS current
            DESCRIPTION
                "new_power_boardPer15mCur."
            INDEX {new_power_boardPer15mCurEid, new_power_boardPer15mCurPara}
            ::= { new_power_boardPer15mCurTable 1 }

        New_power_boardPer15mCurEntry ::=
            SEQUENCE {
                new_power_boardPer15mCurEid
                    PerformanceEventType,
                new_power_boardPer15mCurMonValue
                    OCTET STRING,
                new_power_boardPer15mCurVldty
                    INTEGER,
                new_power_boardPer15mCurDateTime
                    DateAndTime,
                new_power_boardPer15mCurParaLen
                    INTEGER,
                new_power_boardPer15mCurPara
                    OCTET STRING
             }

        -- 1.3.6.1.4.1.2011.2.25.3.40.50.79.10.1.1
        new_power_boardPer15mCurEid OBJECT-TYPE
            SYNTAX PerformanceEventType
            MAX-ACCESS read-only
            STATUS current
            DESCRIPTION
                "perEid."
            ::= { new_power_boardPer15mCurEntry 1 }

        -- 1.3.6.1.4.1.2011.2.25.3.40.50.79.10.1.2
        new_power_boardPer15mCurMonValue OBJECT-TYPE
            SYNTAX OCTET STRING (SIZE (0..100))
            MAX-ACCESS read-only
            STATUS current
            DESCRIPTION
                "perMonValue."
            ::= { new_power_boardPer15mCurEntry 2 }

        -- 1.3.6.1.4.1.2011.2.25.3.40.50.79.10.3
        new_power_boardPer15mCurVldty OBJECT-TYPE
            SYNTAX INTEGER
            MAX-ACCESS read-only
            STATUS current
            DESCRIPTION
                "perVldty. "
            ::= { new_power_boardPer15mCurEntry 3 }

        -- 1.3.6.1.4.1.2011.2.25.3.40.50.79.10.1.4
        new_power_boardPer15mCurDateTime OBJECT-TYPE
            SYNTAX DateAndTime
            MAX-ACCESS read-only
            STATUS current
            DESCRIPTION
                "perDateTime. "
            ::= { new_power_boardPer15mCurEntry 4 }

        -- 1.3.6.1.4.1.2011.2.25.3.40.50.79.10.1.5
        new_power_boardPer15mCurParaLen OBJECT-TYPE
            SYNTAX INTEGER
            MAX-ACCESS read-only
            STATUS current
            DESCRIPTION
                "perParaLen."
            ::= { new_power_boardPer15mCurEntry 5 }

        -- 1.3.6.1.4.1.2011.2.25.3.40.50.79.10.1.6
        new_power_boardPer15mCurPara OBJECT-TYPE
            SYNTAX OCTET STRING (SIZE (0..100))
            MAX-ACCESS read-only
            STATUS current
            DESCRIPTION
                "perPara."
            ::= { new_power_boardPer15mCurEntry 6 }


-- -------------------------------------------------------------------------
-- Perfomance 15-MIN History Data Table (RTRV-PER-<MOD2>)
-- -------------------------------------------------------------------------
        new_power_boardPer15MHisTable OBJECT-TYPE
            SYNTAX SEQUENCE OF New_power_boardPer15MHisEntry
            MAX-ACCESS not-accessible
            STATUS current
            DESCRIPTION
                "new_power_boardPer15MHis."
            ::= { new_power_board 20 }


        new_power_boardPer15MHisEntry OBJECT-TYPE
            SYNTAX New_power_boardPer15MHisEntry
            MAX-ACCESS not-accessible
            STATUS current
            DESCRIPTION
                "new_power_boardPer15MHis."
            INDEX {new_power_boardPer15MHisEid, new_power_boardPer15MHisParaLen, new_power_boardPer15MHisPara, new_power_boardPer15MHisDateTimeStart, new_power_boardPer15MHisDateTimeEnd}
            ::= { new_power_boardPer15MHisTable 1 }

        New_power_boardPer15MHisEntry ::=
            SEQUENCE {
                new_power_boardPer15MHisEid
                    PerformanceEventType,
                new_power_boardPer15MHisParaLen
                    INTEGER,
                new_power_boardPer15MHisPara
                    OCTET STRING,
                new_power_boardPer15MHisMonValue
                    OCTET STRING,
                new_power_boardPer15MHisDateTimeStart
                    DateAndTime,
                new_power_boardPer15MHisDateTimeEnd
                    DateAndTime,
                new_power_boardPer15MHisVldty
                    INTEGER,
             }

        new_power_boardPer15MHisEid OBJECT-TYPE
            SYNTAX PerformanceEventType
            MAX-ACCESS read-only
            STATUS current
            DESCRIPTION
                "perEid."
            ::= { new_power_boardPer15MHisEntry 1 }

        new_power_boardPer15MHisParaLen OBJECT-TYPE
            SYNTAX INTEGER
            MAX-ACCESS read-only
            STATUS current
            DESCRIPTION
                "perParaLen."
            ::= { new_power_boardPer15MHisEntry 2 }


        new_power_boardPer15MHisPara OBJECT-TYPE
            SYNTAX OCTET STRING (SIZE (0..100))
            MAX-ACCESS read-only
            STATUS current
            DESCRIPTION
                "perPara."
            ::= { new_power_boardPer15MHisEntry 3 }



        new_power_boardPer15MHisMonValue OBJECT-TYPE
            SYNTAX OCTET STRING (SIZE (0..100))
            MAX-ACCESS read-only
            STATUS current
            DESCRIPTION
                "perMonValue."
            ::= { new_power_boardPer15MHisEntry 4 }



        new_power_boardPer15MHisDateTimeStart OBJECT-TYPE
            SYNTAX DateAndTime
            MAX-ACCESS read-only
            STATUS current
            DESCRIPTION
                "perDateTimeStart. "
            ::= { new_power_boardPer15MHisEntry 5 }

        new_power_boardPer15MHisDateTimeEnd OBJECT-TYPE
            SYNTAX DateAndTime
            MAX-ACCESS read-only
            STATUS current
            DESCRIPTION
                "perDateTimeEnd. "
            ::= { new_power_boardPer15MHisEntry 6 }


        new_power_boardPer15MHisVldty OBJECT-TYPE
            SYNTAX INTEGER
            MAX-ACCESS read-only
            STATUS current
            DESCRIPTION
                "perVldty. "
            ::= { new_power_boardPer15MHisEntry 7 }


-- -------------------------------------------------------------------------
-- Perfomance 24-HOUR Current Data Table (RTRV-PER-<MOD2>)
-- -------------------------------------------------------------------------
        new_power_boardPer24HCurTable OBJECT-TYPE
            SYNTAX SEQUENCE OF New_power_boardPer24HCurEntry
            MAX-ACCESS not-accessible
            STATUS current
            DESCRIPTION
                "new_power_boardPer24HCur."
            ::= { new_power_board 30 }


        new_power_boardPer24HCurEntry OBJECT-TYPE
            SYNTAX New_power_boardPer24HCurEntry
            MAX-ACCESS not-accessible
            STATUS current
            DESCRIPTION
                "new_power_boardPer24HCur."
            INDEX {new_power_boardPer24HCurEid, new_power_boardPer24HCurPara}
            ::= { new_power_boardPer24HCurTable 1 }

        New_power_boardPer24HCurEntry ::=
            SEQUENCE {
                new_power_boardPer24HCurEid
                    PerformanceEventType,
                new_power_boardPer24HCurMonValue
                    OCTET STRING,
                new_power_boardPer24HCurVldty
                    INTEGER,
                new_power_boardPer24HCurDateTime
                    DateAndTime,
                new_power_boardPer24HCurParaLen
                    INTEGER,
                new_power_boardPer24HCurPara
                    OCTET STRING
             }


        new_power_boardPer24HCurEid OBJECT-TYPE
            SYNTAX PerformanceEventType
            MAX-ACCESS read-only
            STATUS current
            DESCRIPTION
                "perEid."
            ::= { new_power_boardPer24HCurEntry 1 }


        new_power_boardPer24HCurMonValue OBJECT-TYPE
            SYNTAX OCTET STRING (SIZE (0..100))
            MAX-ACCESS read-only
            STATUS current
            DESCRIPTION
                "perMonValue."
            ::= { new_power_boardPer24HCurEntry 2 }


        new_power_boardPer24HCurVldty OBJECT-TYPE
            SYNTAX INTEGER
            MAX-ACCESS read-only
            STATUS current
            DESCRIPTION
                "perVldty. "
            ::= { new_power_boardPer24HCurEntry 3 }


        new_power_boardPer24HCurDateTime OBJECT-TYPE
            SYNTAX DateAndTime
            MAX-ACCESS read-only
            STATUS current
            DESCRIPTION
                "perDateTime. "
            ::= { new_power_boardPer24HCurEntry 4 }


        new_power_boardPer24HCurParaLen OBJECT-TYPE
            SYNTAX INTEGER
            MAX-ACCESS read-only
            STATUS current
            DESCRIPTION
                "perParaLen."
            ::= { new_power_boardPer24HCurEntry 5 }


        new_power_boardPer24HCurPara OBJECT-TYPE
            SYNTAX OCTET STRING (SIZE (0..100))
            MAX-ACCESS read-only
            STATUS current
            DESCRIPTION
                "perPara."
            ::= { new_power_boardPer24HCurEntry 6 }


-- -------------------------------------------------------------------------
-- Perfomance 24-HOUR History Data Table (RTRV-PER-<MOD2>)
-- -------------------------------------------------------------------------
        new_power_boardPer24HHisTable OBJECT-TYPE
            SYNTAX SEQUENCE OF New_power_boardPer24HHisEntry
            MAX-ACCESS not-accessible
            STATUS current
            DESCRIPTION
                "new_power_boardPer24HHis."
            ::= { new_power_board 40 }


        new_power_boardPer24HHisEntry OBJECT-TYPE
            SYNTAX New_power_boardPer24HHisEntry
            MAX-ACCESS not-accessible
            STATUS current
            DESCRIPTION
                "new_power_boardPer24HHis."
            INDEX {new_power_boardPer24HHisEid, new_power_boardPer24HHisParaLen, new_power_boardPer24HHisPara, new_power_boardPer24HHisDateTimeStart, new_power_boardPer24HHisDateTimeEnd}
            ::= { new_power_boardPer24HHisTable 1 }

        New_power_boardPer24HHisEntry ::=
            SEQUENCE {
                new_power_boardPer24HHisEid
                    PerformanceEventType,
                new_power_boardPer24HHisParaLen
                    INTEGER,
                new_power_boardPer24HHisPara
                    OCTET STRING,
                new_power_boardPer24HHisMonValue
                    OCTET STRING,
                new_power_boardPer24HHisDateTimeStart
                    DateAndTime,
                new_power_boardPer24HHisDateTimeEnd
                    DateAndTime,
                new_power_boardPer24HHisVldty
                    INTEGER,
             }

        new_power_boardPer24HHisEid OBJECT-TYPE
            SYNTAX PerformanceEventType
            MAX-ACCESS read-only
            STATUS current
            DESCRIPTION
                "perEid."
            ::= { new_power_boardPer24HHisEntry 1 }

        new_power_boardPer24HHisParaLen OBJECT-TYPE
            SYNTAX INTEGER
            MAX-ACCESS read-only
            STATUS current
            DESCRIPTION
                "perParaLen."
            ::= { new_power_boardPer24HHisEntry 2 }


        new_power_boardPer24HHisPara OBJECT-TYPE
            SYNTAX OCTET STRING (SIZE (0..100))
            MAX-ACCESS read-only
            STATUS current
            DESCRIPTION
                "perPara."
            ::= { new_power_boardPer24HHisEntry 3 }



        new_power_boardPer24HHisMonValue OBJECT-TYPE
            SYNTAX OCTET STRING (SIZE (0..100))
            MAX-ACCESS read-only
            STATUS current
            DESCRIPTION
                "perMonValue."
            ::= { new_power_boardPer24HHisEntry 4 }



        new_power_boardPer24HHisDateTimeStart OBJECT-TYPE
            SYNTAX DateAndTime
            MAX-ACCESS read-only
            STATUS current
            DESCRIPTION
                "perDateTimeStart. "
            ::= { new_power_boardPer24HHisEntry 5 }

        new_power_boardPer24HHisDateTimeEnd OBJECT-TYPE
            SYNTAX DateAndTime
            MAX-ACCESS read-only
            STATUS current
            DESCRIPTION
                "perDateTimeEnd. "
            ::= { new_power_boardPer24HHisEntry 6 }


        new_power_boardPer24HHisVldty OBJECT-TYPE
            SYNTAX INTEGER
            MAX-ACCESS read-only
            STATUS current
            DESCRIPTION
                "perVldty. "
            ::= { new_power_boardPer24HHisEntry 7 }

--  Alarm data
        -- 1.3.6.1.4.1.2011.2.25.3.40.50.78
        new_fan_board OBJECT IDENTIFIER ::= { optixGlobalNGWDM 78 }

-- -------------------------------------------------------------------------
-- Perfomance 15-MIN Current Data Table (RTRV-PER-<MOD2>)
-- -------------------------------------------------------------------------
        -- 1.3.6.1.4.1.2011.2.25.3.40.50.78.10
        new_fan_boardPer15mCurTable OBJECT-TYPE
            SYNTAX SEQUENCE OF New_fan_boardPer15mCurEntry
            MAX-ACCESS not-accessible
            STATUS current
            DESCRIPTION
                "new_fan_boardPer15mCur."
            ::= { new_fan_board 10 }

        -- 1.3.6.1.4.1.2011.2.25.3.40.50.78.10.1
        new_fan_boardPer15mCurEntry OBJECT-TYPE
            SYNTAX New_fan_boardPer15mCurEntry
            MAX-ACCESS not-accessible
            STATUS current
            DESCRIPTION
                "new_fan_boardPer15mCur."
            INDEX {new_fan_boardPer15mCurEid, new_fan_boardPer15mCurPara}
            ::= { new_fan_boardPer15mCurTable 1 }

        New_fan_boardPer15mCurEntry ::=
            SEQUENCE {
                new_fan_boardPer15mCurEid
                    PerformanceEventType,
                new_fan_boardPer15mCurMonValue
                    OCTET STRING,
                new_fan_boardPer15mCurVldty
                    INTEGER,
                new_fan_boardPer15mCurDateTime
                    DateAndTime,
                new_fan_boardPer15mCurParaLen
                    INTEGER,
                new_fan_boardPer15mCurPara
                    OCTET STRING
             }

        -- 1.3.6.1.4.1.2011.2.25.3.40.50.78.10.1.1
        new_fan_boardPer15mCurEid OBJECT-TYPE
            SYNTAX PerformanceEventType
            MAX-ACCESS read-only
            STATUS current
            DESCRIPTION
                "perEid."
            ::= { new_fan_boardPer15mCurEntry 1 }

        -- 1.3.6.1.4.1.2011.2.25.3.40.50.78.10.1.2
        new_fan_boardPer15mCurMonValue OBJECT-TYPE
            SYNTAX OCTET STRING (SIZE (0..100))
            MAX-ACCESS read-only
            STATUS current
            DESCRIPTION
                "perMonValue."
            ::= { new_fan_boardPer15mCurEntry 2 }

        -- 1.3.6.1.4.1.2011.2.25.3.40.50.78.10.3
        new_fan_boardPer15mCurVldty OBJECT-TYPE
            SYNTAX INTEGER
            MAX-ACCESS read-only
            STATUS current
            DESCRIPTION
                "perVldty. "
            ::= { new_fan_boardPer15mCurEntry 3 }

        -- 1.3.6.1.4.1.2011.2.25.3.40.50.78.10.1.4
        new_fan_boardPer15mCurDateTime OBJECT-TYPE
            SYNTAX DateAndTime
            MAX-ACCESS read-only
            STATUS current
            DESCRIPTION
                "perDateTime. "
            ::= { new_fan_boardPer15mCurEntry 4 }

        -- 1.3.6.1.4.1.2011.2.25.3.40.50.78.10.1.5
        new_fan_boardPer15mCurParaLen OBJECT-TYPE
            SYNTAX INTEGER
            MAX-ACCESS read-only
            STATUS current
            DESCRIPTION
                "perParaLen."
            ::= { new_fan_boardPer15mCurEntry 5 }

        -- 1.3.6.1.4.1.2011.2.25.3.40.50.78.10.1.6
        new_fan_boardPer15mCurPara OBJECT-TYPE
            SYNTAX OCTET STRING (SIZE (0..100))
            MAX-ACCESS read-only
            STATUS current
            DESCRIPTION
                "perPara."
            ::= { new_fan_boardPer15mCurEntry 6 }


-- -------------------------------------------------------------------------
-- Perfomance 15-MIN History Data Table (RTRV-PER-<MOD2>)
-- -------------------------------------------------------------------------
        new_fan_boardPer15MHisTable OBJECT-TYPE
            SYNTAX SEQUENCE OF New_fan_boardPer15MHisEntry
            MAX-ACCESS not-accessible
            STATUS current
            DESCRIPTION
                "new_fan_boardPer15MHis."
            ::= { new_fan_board 20 }


        new_fan_boardPer15MHisEntry OBJECT-TYPE
            SYNTAX New_fan_boardPer15MHisEntry
            MAX-ACCESS not-accessible
            STATUS current
            DESCRIPTION
                "new_fan_boardPer15MHis."
            INDEX {new_fan_boardPer15MHisEid, new_fan_boardPer15MHisParaLen, new_fan_boardPer15MHisPara, new_fan_boardPer15MHisDateTimeStart, new_fan_boardPer15MHisDateTimeEnd}
            ::= { new_fan_boardPer15MHisTable 1 }

        New_fan_boardPer15MHisEntry ::=
            SEQUENCE {
                new_fan_boardPer15MHisEid
                    PerformanceEventType,
                new_fan_boardPer15MHisParaLen
                    INTEGER,
                new_fan_boardPer15MHisPara
                    OCTET STRING,
                new_fan_boardPer15MHisMonValue
                    OCTET STRING,
                new_fan_boardPer15MHisDateTimeStart
                    DateAndTime,
                new_fan_boardPer15MHisDateTimeEnd
                    DateAndTime,
                new_fan_boardPer15MHisVldty
                    INTEGER,
             }

        new_fan_boardPer15MHisEid OBJECT-TYPE
            SYNTAX PerformanceEventType
            MAX-ACCESS read-only
            STATUS current
            DESCRIPTION
                "perEid."
            ::= { new_fan_boardPer15MHisEntry 1 }

        new_fan_boardPer15MHisParaLen OBJECT-TYPE
            SYNTAX INTEGER
            MAX-ACCESS read-only
            STATUS current
            DESCRIPTION
                "perParaLen."
            ::= { new_fan_boardPer15MHisEntry 2 }


        new_fan_boardPer15MHisPara OBJECT-TYPE
            SYNTAX OCTET STRING (SIZE (0..100))
            MAX-ACCESS read-only
            STATUS current
            DESCRIPTION
                "perPara."
            ::= { new_fan_boardPer15MHisEntry 3 }



        new_fan_boardPer15MHisMonValue OBJECT-TYPE
            SYNTAX OCTET STRING (SIZE (0..100))
            MAX-ACCESS read-only
            STATUS current
            DESCRIPTION
                "perMonValue."
            ::= { new_fan_boardPer15MHisEntry 4 }



        new_fan_boardPer15MHisDateTimeStart OBJECT-TYPE
            SYNTAX DateAndTime
            MAX-ACCESS read-only
            STATUS current
            DESCRIPTION
                "perDateTimeStart. "
            ::= { new_fan_boardPer15MHisEntry 5 }

        new_fan_boardPer15MHisDateTimeEnd OBJECT-TYPE
            SYNTAX DateAndTime
            MAX-ACCESS read-only
            STATUS current
            DESCRIPTION
                "perDateTimeEnd. "
            ::= { new_fan_boardPer15MHisEntry 6 }


        new_fan_boardPer15MHisVldty OBJECT-TYPE
            SYNTAX INTEGER
            MAX-ACCESS read-only
            STATUS current
            DESCRIPTION
                "perVldty. "
            ::= { new_fan_boardPer15MHisEntry 7 }


-- -------------------------------------------------------------------------
-- Perfomance 24-HOUR Current Data Table (RTRV-PER-<MOD2>)
-- -------------------------------------------------------------------------
        new_fan_boardPer24HCurTable OBJECT-TYPE
            SYNTAX SEQUENCE OF New_fan_boardPer24HCurEntry
            MAX-ACCESS not-accessible
            STATUS current
            DESCRIPTION
                "new_fan_boardPer24HCur."
            ::= { new_fan_board 30 }


        new_fan_boardPer24HCurEntry OBJECT-TYPE
            SYNTAX New_fan_boardPer24HCurEntry
            MAX-ACCESS not-accessible
            STATUS current
            DESCRIPTION
                "new_fan_boardPer24HCur."
            INDEX {new_fan_boardPer24HCurEid, new_fan_boardPer24HCurPara}
            ::= { new_fan_boardPer24HCurTable 1 }

        New_fan_boardPer24HCurEntry ::=
            SEQUENCE {
                new_fan_boardPer24HCurEid
                    PerformanceEventType,
                new_fan_boardPer24HCurMonValue
                    OCTET STRING,
                new_fan_boardPer24HCurVldty
                    INTEGER,
                new_fan_boardPer24HCurDateTime
                    DateAndTime,
                new_fan_boardPer24HCurParaLen
                    INTEGER,
                new_fan_boardPer24HCurPara
                    OCTET STRING
             }


        new_fan_boardPer24HCurEid OBJECT-TYPE
            SYNTAX PerformanceEventType
            MAX-ACCESS read-only
            STATUS current
            DESCRIPTION
                "perEid."
            ::= { new_fan_boardPer24HCurEntry 1 }


        new_fan_boardPer24HCurMonValue OBJECT-TYPE
            SYNTAX OCTET STRING (SIZE (0..100))
            MAX-ACCESS read-only
            STATUS current
            DESCRIPTION
                "perMonValue."
            ::= { new_fan_boardPer24HCurEntry 2 }


        new_fan_boardPer24HCurVldty OBJECT-TYPE
            SYNTAX INTEGER
            MAX-ACCESS read-only
            STATUS current
            DESCRIPTION
                "perVldty. "
            ::= { new_fan_boardPer24HCurEntry 3 }


        new_fan_boardPer24HCurDateTime OBJECT-TYPE
            SYNTAX DateAndTime
            MAX-ACCESS read-only
            STATUS current
            DESCRIPTION
                "perDateTime. "
            ::= { new_fan_boardPer24HCurEntry 4 }


        new_fan_boardPer24HCurParaLen OBJECT-TYPE
            SYNTAX INTEGER
            MAX-ACCESS read-only
            STATUS current
            DESCRIPTION
                "perParaLen."
            ::= { new_fan_boardPer24HCurEntry 5 }


        new_fan_boardPer24HCurPara OBJECT-TYPE
            SYNTAX OCTET STRING (SIZE (0..100))
            MAX-ACCESS read-only
            STATUS current
            DESCRIPTION
                "perPara."
            ::= { new_fan_boardPer24HCurEntry 6 }


-- -------------------------------------------------------------------------
-- Perfomance 24-HOUR History Data Table (RTRV-PER-<MOD2>)
-- -------------------------------------------------------------------------
        new_fan_boardPer24HHisTable OBJECT-TYPE
            SYNTAX SEQUENCE OF New_fan_boardPer24HHisEntry
            MAX-ACCESS not-accessible
            STATUS current
            DESCRIPTION
                "new_fan_boardPer24HHis."
            ::= { new_fan_board 40 }


        new_fan_boardPer24HHisEntry OBJECT-TYPE
            SYNTAX New_fan_boardPer24HHisEntry
            MAX-ACCESS not-accessible
            STATUS current
            DESCRIPTION
                "new_fan_boardPer24HHis."
            INDEX {new_fan_boardPer24HHisEid, new_fan_boardPer24HHisParaLen, new_fan_boardPer24HHisPara, new_fan_boardPer24HHisDateTimeStart, new_fan_boardPer24HHisDateTimeEnd}
            ::= { new_fan_boardPer24HHisTable 1 }

        New_fan_boardPer24HHisEntry ::=
            SEQUENCE {
                new_fan_boardPer24HHisEid
                    PerformanceEventType,
                new_fan_boardPer24HHisParaLen
                    INTEGER,
                new_fan_boardPer24HHisPara
                    OCTET STRING,
                new_fan_boardPer24HHisMonValue
                    OCTET STRING,
                new_fan_boardPer24HHisDateTimeStart
                    DateAndTime,
                new_fan_boardPer24HHisDateTimeEnd
                    DateAndTime,
                new_fan_boardPer24HHisVldty
                    INTEGER,
             }

        new_fan_boardPer24HHisEid OBJECT-TYPE
            SYNTAX PerformanceEventType
            MAX-ACCESS read-only
            STATUS current
            DESCRIPTION
                "perEid."
            ::= { new_fan_boardPer24HHisEntry 1 }

        new_fan_boardPer24HHisParaLen OBJECT-TYPE
            SYNTAX INTEGER
            MAX-ACCESS read-only
            STATUS current
            DESCRIPTION
                "perParaLen."
            ::= { new_fan_boardPer24HHisEntry 2 }


        new_fan_boardPer24HHisPara OBJECT-TYPE
            SYNTAX OCTET STRING (SIZE (0..100))
            MAX-ACCESS read-only
            STATUS current
            DESCRIPTION
                "perPara."
            ::= { new_fan_boardPer24HHisEntry 3 }



        new_fan_boardPer24HHisMonValue OBJECT-TYPE
            SYNTAX OCTET STRING (SIZE (0..100))
            MAX-ACCESS read-only
            STATUS current
            DESCRIPTION
                "perMonValue."
            ::= { new_fan_boardPer24HHisEntry 4 }



        new_fan_boardPer24HHisDateTimeStart OBJECT-TYPE
            SYNTAX DateAndTime
            MAX-ACCESS read-only
            STATUS current
            DESCRIPTION
                "perDateTimeStart. "
            ::= { new_fan_boardPer24HHisEntry 5 }

        new_fan_boardPer24HHisDateTimeEnd OBJECT-TYPE
            SYNTAX DateAndTime
            MAX-ACCESS read-only
            STATUS current
            DESCRIPTION
                "perDateTimeEnd. "
            ::= { new_fan_boardPer24HHisEntry 6 }


        new_fan_boardPer24HHisVldty OBJECT-TYPE
            SYNTAX INTEGER
            MAX-ACCESS read-only
            STATUS current
            DESCRIPTION
                "perVldty. "
            ::= { new_fan_boardPer24HHisEntry 7 }

--  Alarm data
        -- 1.3.6.1.4.1.2011.2.25.3.40.50.119
        laser_group OBJECT IDENTIFIER ::= { optixGlobalNGWDM 119 }

-- -------------------------------------------------------------------------
-- Perfomance 15-MIN Current Data Table (RTRV-PER-<MOD2>)
-- -------------------------------------------------------------------------
        -- 1.3.6.1.4.1.2011.2.25.3.40.50.119.10
        laser_groupPer15mCurTable OBJECT-TYPE
            SYNTAX SEQUENCE OF Laser_groupPer15mCurEntry
            MAX-ACCESS not-accessible
            STATUS current
            DESCRIPTION
                "laser_groupPer15mCur."
            ::= { laser_group 10 }

        -- 1.3.6.1.4.1.2011.2.25.3.40.50.119.10.1
        laser_groupPer15mCurEntry OBJECT-TYPE
            SYNTAX Laser_groupPer15mCurEntry
            MAX-ACCESS not-accessible
            STATUS current
            DESCRIPTION
                "laser_groupPer15mCur."
            INDEX {laser_groupPer15mCurEid, laser_groupPer15mCurPara}
            ::= { laser_groupPer15mCurTable 1 }

        Laser_groupPer15mCurEntry ::=
            SEQUENCE {
                laser_groupPer15mCurEid
                    PerformanceEventType,
                laser_groupPer15mCurMonValue
                    OCTET STRING,
                laser_groupPer15mCurVldty
                    INTEGER,
                laser_groupPer15mCurDateTime
                    DateAndTime,
                laser_groupPer15mCurParaLen
                    INTEGER,
                laser_groupPer15mCurPara
                    OCTET STRING
             }

        -- 1.3.6.1.4.1.2011.2.25.3.40.50.119.10.1.1
        laser_groupPer15mCurEid OBJECT-TYPE
            SYNTAX PerformanceEventType
            MAX-ACCESS read-only
            STATUS current
            DESCRIPTION
                "perEid."
            ::= { laser_groupPer15mCurEntry 1 }

        -- 1.3.6.1.4.1.2011.2.25.3.40.50.119.10.1.2
        laser_groupPer15mCurMonValue OBJECT-TYPE
            SYNTAX OCTET STRING (SIZE (0..100))
            MAX-ACCESS read-only
            STATUS current
            DESCRIPTION
                "perMonValue."
            ::= { laser_groupPer15mCurEntry 2 }

        -- 1.3.6.1.4.1.2011.2.25.3.40.50.119.10.3
        laser_groupPer15mCurVldty OBJECT-TYPE
            SYNTAX INTEGER
            MAX-ACCESS read-only
            STATUS current
            DESCRIPTION
                "perVldty. "
            ::= { laser_groupPer15mCurEntry 3 }

        -- 1.3.6.1.4.1.2011.2.25.3.40.50.119.10.1.4
        laser_groupPer15mCurDateTime OBJECT-TYPE
            SYNTAX DateAndTime
            MAX-ACCESS read-only
            STATUS current
            DESCRIPTION
                "perDateTime. "
            ::= { laser_groupPer15mCurEntry 4 }

        -- 1.3.6.1.4.1.2011.2.25.3.40.50.119.10.1.5
        laser_groupPer15mCurParaLen OBJECT-TYPE
            SYNTAX INTEGER
            MAX-ACCESS read-only
            STATUS current
            DESCRIPTION
                "perParaLen."
            ::= { laser_groupPer15mCurEntry 5 }

        -- 1.3.6.1.4.1.2011.2.25.3.40.50.119.10.1.6
        laser_groupPer15mCurPara OBJECT-TYPE
            SYNTAX OCTET STRING (SIZE (0..100))
            MAX-ACCESS read-only
            STATUS current
            DESCRIPTION
                "perPara."
            ::= { laser_groupPer15mCurEntry 6 }


-- -------------------------------------------------------------------------
-- Perfomance 15-MIN History Data Table (RTRV-PER-<MOD2>)
-- -------------------------------------------------------------------------
        laser_groupPer15MHisTable OBJECT-TYPE
            SYNTAX SEQUENCE OF Laser_groupPer15MHisEntry
            MAX-ACCESS not-accessible
            STATUS current
            DESCRIPTION
                "laser_groupPer15MHis."
            ::= { laser_group 20 }


        laser_groupPer15MHisEntry OBJECT-TYPE
            SYNTAX Laser_groupPer15MHisEntry
            MAX-ACCESS not-accessible
            STATUS current
            DESCRIPTION
                "laser_groupPer15MHis."
            INDEX {laser_groupPer15MHisEid, laser_groupPer15MHisParaLen, laser_groupPer15MHisPara, laser_groupPer15MHisDateTimeStart, laser_groupPer15MHisDateTimeEnd}
            ::= { laser_groupPer15MHisTable 1 }

        Laser_groupPer15MHisEntry ::=
            SEQUENCE {
                laser_groupPer15MHisEid
                    PerformanceEventType,
                laser_groupPer15MHisParaLen
                    INTEGER,
                laser_groupPer15MHisPara
                    OCTET STRING,
                laser_groupPer15MHisMonValue
                    OCTET STRING,
                laser_groupPer15MHisDateTimeStart
                    DateAndTime,
                laser_groupPer15MHisDateTimeEnd
                    DateAndTime,
                laser_groupPer15MHisVldty
                    INTEGER,
             }

        laser_groupPer15MHisEid OBJECT-TYPE
            SYNTAX PerformanceEventType
            MAX-ACCESS read-only
            STATUS current
            DESCRIPTION
                "perEid."
            ::= { laser_groupPer15MHisEntry 1 }

        laser_groupPer15MHisParaLen OBJECT-TYPE
            SYNTAX INTEGER
            MAX-ACCESS read-only
            STATUS current
            DESCRIPTION
                "perParaLen."
            ::= { laser_groupPer15MHisEntry 2 }


        laser_groupPer15MHisPara OBJECT-TYPE
            SYNTAX OCTET STRING (SIZE (0..100))
            MAX-ACCESS read-only
            STATUS current
            DESCRIPTION
                "perPara."
            ::= { laser_groupPer15MHisEntry 3 }



        laser_groupPer15MHisMonValue OBJECT-TYPE
            SYNTAX OCTET STRING (SIZE (0..100))
            MAX-ACCESS read-only
            STATUS current
            DESCRIPTION
                "perMonValue."
            ::= { laser_groupPer15MHisEntry 4 }



        laser_groupPer15MHisDateTimeStart OBJECT-TYPE
            SYNTAX DateAndTime
            MAX-ACCESS read-only
            STATUS current
            DESCRIPTION
                "perDateTimeStart. "
            ::= { laser_groupPer15MHisEntry 5 }

        laser_groupPer15MHisDateTimeEnd OBJECT-TYPE
            SYNTAX DateAndTime
            MAX-ACCESS read-only
            STATUS current
            DESCRIPTION
                "perDateTimeEnd. "
            ::= { laser_groupPer15MHisEntry 6 }


        laser_groupPer15MHisVldty OBJECT-TYPE
            SYNTAX INTEGER
            MAX-ACCESS read-only
            STATUS current
            DESCRIPTION
                "perVldty. "
            ::= { laser_groupPer15MHisEntry 7 }


-- -------------------------------------------------------------------------
-- Perfomance 24-HOUR Current Data Table (RTRV-PER-<MOD2>)
-- -------------------------------------------------------------------------
        laser_groupPer24HCurTable OBJECT-TYPE
            SYNTAX SEQUENCE OF Laser_groupPer24HCurEntry
            MAX-ACCESS not-accessible
            STATUS current
            DESCRIPTION
                "laser_groupPer24HCur."
            ::= { laser_group 30 }


        laser_groupPer24HCurEntry OBJECT-TYPE
            SYNTAX Laser_groupPer24HCurEntry
            MAX-ACCESS not-accessible
            STATUS current
            DESCRIPTION
                "laser_groupPer24HCur."
            INDEX {laser_groupPer24HCurEid, laser_groupPer24HCurPara}
            ::= { laser_groupPer24HCurTable 1 }

        Laser_groupPer24HCurEntry ::=
            SEQUENCE {
                laser_groupPer24HCurEid
                    PerformanceEventType,
                laser_groupPer24HCurMonValue
                    OCTET STRING,
                laser_groupPer24HCurVldty
                    INTEGER,
                laser_groupPer24HCurDateTime
                    DateAndTime,
                laser_groupPer24HCurParaLen
                    INTEGER,
                laser_groupPer24HCurPara
                    OCTET STRING
             }


        laser_groupPer24HCurEid OBJECT-TYPE
            SYNTAX PerformanceEventType
            MAX-ACCESS read-only
            STATUS current
            DESCRIPTION
                "perEid."
            ::= { laser_groupPer24HCurEntry 1 }


        laser_groupPer24HCurMonValue OBJECT-TYPE
            SYNTAX OCTET STRING (SIZE (0..100))
            MAX-ACCESS read-only
            STATUS current
            DESCRIPTION
                "perMonValue."
            ::= { laser_groupPer24HCurEntry 2 }


        laser_groupPer24HCurVldty OBJECT-TYPE
            SYNTAX INTEGER
            MAX-ACCESS read-only
            STATUS current
            DESCRIPTION
                "perVldty. "
            ::= { laser_groupPer24HCurEntry 3 }


        laser_groupPer24HCurDateTime OBJECT-TYPE
            SYNTAX DateAndTime
            MAX-ACCESS read-only
            STATUS current
            DESCRIPTION
                "perDateTime. "
            ::= { laser_groupPer24HCurEntry 4 }


        laser_groupPer24HCurParaLen OBJECT-TYPE
            SYNTAX INTEGER
            MAX-ACCESS read-only
            STATUS current
            DESCRIPTION
                "perParaLen."
            ::= { laser_groupPer24HCurEntry 5 }


        laser_groupPer24HCurPara OBJECT-TYPE
            SYNTAX OCTET STRING (SIZE (0..100))
            MAX-ACCESS read-only
            STATUS current
            DESCRIPTION
                "perPara."
            ::= { laser_groupPer24HCurEntry 6 }


-- -------------------------------------------------------------------------
-- Perfomance 24-HOUR History Data Table (RTRV-PER-<MOD2>)
-- -------------------------------------------------------------------------
        laser_groupPer24HHisTable OBJECT-TYPE
            SYNTAX SEQUENCE OF Laser_groupPer24HHisEntry
            MAX-ACCESS not-accessible
            STATUS current
            DESCRIPTION
                "laser_groupPer24HHis."
            ::= { laser_group 40 }


        laser_groupPer24HHisEntry OBJECT-TYPE
            SYNTAX Laser_groupPer24HHisEntry
            MAX-ACCESS not-accessible
            STATUS current
            DESCRIPTION
                "laser_groupPer24HHis."
            INDEX {laser_groupPer24HHisEid, laser_groupPer24HHisParaLen, laser_groupPer24HHisPara, laser_groupPer24HHisDateTimeStart, laser_groupPer24HHisDateTimeEnd}
            ::= { laser_groupPer24HHisTable 1 }

        Laser_groupPer24HHisEntry ::=
            SEQUENCE {
                laser_groupPer24HHisEid
                    PerformanceEventType,
                laser_groupPer24HHisParaLen
                    INTEGER,
                laser_groupPer24HHisPara
                    OCTET STRING,
                laser_groupPer24HHisMonValue
                    OCTET STRING,
                laser_groupPer24HHisDateTimeStart
                    DateAndTime,
                laser_groupPer24HHisDateTimeEnd
                    DateAndTime,
                laser_groupPer24HHisVldty
                    INTEGER,
             }

        laser_groupPer24HHisEid OBJECT-TYPE
            SYNTAX PerformanceEventType
            MAX-ACCESS read-only
            STATUS current
            DESCRIPTION
                "perEid."
            ::= { laser_groupPer24HHisEntry 1 }

        laser_groupPer24HHisParaLen OBJECT-TYPE
            SYNTAX INTEGER
            MAX-ACCESS read-only
            STATUS current
            DESCRIPTION
                "perParaLen."
            ::= { laser_groupPer24HHisEntry 2 }


        laser_groupPer24HHisPara OBJECT-TYPE
            SYNTAX OCTET STRING (SIZE (0..100))
            MAX-ACCESS read-only
            STATUS current
            DESCRIPTION
                "perPara."
            ::= { laser_groupPer24HHisEntry 3 }



        laser_groupPer24HHisMonValue OBJECT-TYPE
            SYNTAX OCTET STRING (SIZE (0..100))
            MAX-ACCESS read-only
            STATUS current
            DESCRIPTION
                "perMonValue."
            ::= { laser_groupPer24HHisEntry 4 }



        laser_groupPer24HHisDateTimeStart OBJECT-TYPE
            SYNTAX DateAndTime
            MAX-ACCESS read-only
            STATUS current
            DESCRIPTION
                "perDateTimeStart. "
            ::= { laser_groupPer24HHisEntry 5 }

        laser_groupPer24HHisDateTimeEnd OBJECT-TYPE
            SYNTAX DateAndTime
            MAX-ACCESS read-only
            STATUS current
            DESCRIPTION
                "perDateTimeEnd. "
            ::= { laser_groupPer24HHisEntry 6 }


        laser_groupPer24HHisVldty OBJECT-TYPE
            SYNTAX INTEGER
            MAX-ACCESS read-only
            STATUS current
            DESCRIPTION
                "perVldty. "
            ::= { laser_groupPer24HHisEntry 7 }

--  Alarm data
        -- 1.3.6.1.4.1.2011.2.25.3.40.50.93
        odu2_path OBJECT IDENTIFIER ::= { optixGlobalNGWDM 93 }

-- -------------------------------------------------------------------------
-- Perfomance 15-MIN Current Data Table (RTRV-PER-<MOD2>)
-- -------------------------------------------------------------------------
        -- 1.3.6.1.4.1.2011.2.25.3.40.50.93.10
        odu2_pathPer15mCurTable OBJECT-TYPE
            SYNTAX SEQUENCE OF Odu2_pathPer15mCurEntry
            MAX-ACCESS not-accessible
            STATUS current
            DESCRIPTION
                "odu2_pathPer15mCur."
            ::= { odu2_path 10 }

        -- 1.3.6.1.4.1.2011.2.25.3.40.50.93.10.1
        odu2_pathPer15mCurEntry OBJECT-TYPE
            SYNTAX Odu2_pathPer15mCurEntry
            MAX-ACCESS not-accessible
            STATUS current
            DESCRIPTION
                "odu2_pathPer15mCur."
            INDEX {odu2_pathPer15mCurEid, odu2_pathPer15mCurPara}
            ::= { odu2_pathPer15mCurTable 1 }

        Odu2_pathPer15mCurEntry ::=
            SEQUENCE {
                odu2_pathPer15mCurEid
                    PerformanceEventType,
                odu2_pathPer15mCurMonValue
                    OCTET STRING,
                odu2_pathPer15mCurVldty
                    INTEGER,
                odu2_pathPer15mCurDateTime
                    DateAndTime,
                odu2_pathPer15mCurParaLen
                    INTEGER,
                odu2_pathPer15mCurPara
                    OCTET STRING
             }

        -- 1.3.6.1.4.1.2011.2.25.3.40.50.93.10.1.1
        odu2_pathPer15mCurEid OBJECT-TYPE
            SYNTAX PerformanceEventType
            MAX-ACCESS read-only
            STATUS current
            DESCRIPTION
                "perEid."
            ::= { odu2_pathPer15mCurEntry 1 }

        -- 1.3.6.1.4.1.2011.2.25.3.40.50.93.10.1.2
        odu2_pathPer15mCurMonValue OBJECT-TYPE
            SYNTAX OCTET STRING (SIZE (0..100))
            MAX-ACCESS read-only
            STATUS current
            DESCRIPTION
                "perMonValue."
            ::= { odu2_pathPer15mCurEntry 2 }

        -- 1.3.6.1.4.1.2011.2.25.3.40.50.93.10.3
        odu2_pathPer15mCurVldty OBJECT-TYPE
            SYNTAX INTEGER
            MAX-ACCESS read-only
            STATUS current
            DESCRIPTION
                "perVldty. "
            ::= { odu2_pathPer15mCurEntry 3 }

        -- 1.3.6.1.4.1.2011.2.25.3.40.50.93.10.1.4
        odu2_pathPer15mCurDateTime OBJECT-TYPE
            SYNTAX DateAndTime
            MAX-ACCESS read-only
            STATUS current
            DESCRIPTION
                "perDateTime. "
            ::= { odu2_pathPer15mCurEntry 4 }

        -- 1.3.6.1.4.1.2011.2.25.3.40.50.93.10.1.5
        odu2_pathPer15mCurParaLen OBJECT-TYPE
            SYNTAX INTEGER
            MAX-ACCESS read-only
            STATUS current
            DESCRIPTION
                "perParaLen."
            ::= { odu2_pathPer15mCurEntry 5 }

        -- 1.3.6.1.4.1.2011.2.25.3.40.50.93.10.1.6
        odu2_pathPer15mCurPara OBJECT-TYPE
            SYNTAX OCTET STRING (SIZE (0..100))
            MAX-ACCESS read-only
            STATUS current
            DESCRIPTION
                "perPara."
            ::= { odu2_pathPer15mCurEntry 6 }


-- -------------------------------------------------------------------------
-- Perfomance 15-MIN History Data Table (RTRV-PER-<MOD2>)
-- -------------------------------------------------------------------------
        odu2_pathPer15MHisTable OBJECT-TYPE
            SYNTAX SEQUENCE OF Odu2_pathPer15MHisEntry
            MAX-ACCESS not-accessible
            STATUS current
            DESCRIPTION
                "odu2_pathPer15MHis."
            ::= { odu2_path 20 }


        odu2_pathPer15MHisEntry OBJECT-TYPE
            SYNTAX Odu2_pathPer15MHisEntry
            MAX-ACCESS not-accessible
            STATUS current
            DESCRIPTION
                "odu2_pathPer15MHis."
            INDEX {odu2_pathPer15MHisEid, odu2_pathPer15MHisParaLen, odu2_pathPer15MHisPara, odu2_pathPer15MHisDateTimeStart, odu2_pathPer15MHisDateTimeEnd}
            ::= { odu2_pathPer15MHisTable 1 }

        Odu2_pathPer15MHisEntry ::=
            SEQUENCE {
                odu2_pathPer15MHisEid
                    PerformanceEventType,
                odu2_pathPer15MHisParaLen
                    INTEGER,
                odu2_pathPer15MHisPara
                    OCTET STRING,
                odu2_pathPer15MHisMonValue
                    OCTET STRING,
                odu2_pathPer15MHisDateTimeStart
                    DateAndTime,
                odu2_pathPer15MHisDateTimeEnd
                    DateAndTime,
                odu2_pathPer15MHisVldty
                    INTEGER,
             }

        odu2_pathPer15MHisEid OBJECT-TYPE
            SYNTAX PerformanceEventType
            MAX-ACCESS read-only
            STATUS current
            DESCRIPTION
                "perEid."
            ::= { odu2_pathPer15MHisEntry 1 }

        odu2_pathPer15MHisParaLen OBJECT-TYPE
            SYNTAX INTEGER
            MAX-ACCESS read-only
            STATUS current
            DESCRIPTION
                "perParaLen."
            ::= { odu2_pathPer15MHisEntry 2 }


        odu2_pathPer15MHisPara OBJECT-TYPE
            SYNTAX OCTET STRING (SIZE (0..100))
            MAX-ACCESS read-only
            STATUS current
            DESCRIPTION
                "perPara."
            ::= { odu2_pathPer15MHisEntry 3 }



        odu2_pathPer15MHisMonValue OBJECT-TYPE
            SYNTAX OCTET STRING (SIZE (0..100))
            MAX-ACCESS read-only
            STATUS current
            DESCRIPTION
                "perMonValue."
            ::= { odu2_pathPer15MHisEntry 4 }



        odu2_pathPer15MHisDateTimeStart OBJECT-TYPE
            SYNTAX DateAndTime
            MAX-ACCESS read-only
            STATUS current
            DESCRIPTION
                "perDateTimeStart. "
            ::= { odu2_pathPer15MHisEntry 5 }

        odu2_pathPer15MHisDateTimeEnd OBJECT-TYPE
            SYNTAX DateAndTime
            MAX-ACCESS read-only
            STATUS current
            DESCRIPTION
                "perDateTimeEnd. "
            ::= { odu2_pathPer15MHisEntry 6 }


        odu2_pathPer15MHisVldty OBJECT-TYPE
            SYNTAX INTEGER
            MAX-ACCESS read-only
            STATUS current
            DESCRIPTION
                "perVldty. "
            ::= { odu2_pathPer15MHisEntry 7 }


-- -------------------------------------------------------------------------
-- Perfomance 24-HOUR Current Data Table (RTRV-PER-<MOD2>)
-- -------------------------------------------------------------------------
        odu2_pathPer24HCurTable OBJECT-TYPE
            SYNTAX SEQUENCE OF Odu2_pathPer24HCurEntry
            MAX-ACCESS not-accessible
            STATUS current
            DESCRIPTION
                "odu2_pathPer24HCur."
            ::= { odu2_path 30 }


        odu2_pathPer24HCurEntry OBJECT-TYPE
            SYNTAX Odu2_pathPer24HCurEntry
            MAX-ACCESS not-accessible
            STATUS current
            DESCRIPTION
                "odu2_pathPer24HCur."
            INDEX {odu2_pathPer24HCurEid, odu2_pathPer24HCurPara}
            ::= { odu2_pathPer24HCurTable 1 }

        Odu2_pathPer24HCurEntry ::=
            SEQUENCE {
                odu2_pathPer24HCurEid
                    PerformanceEventType,
                odu2_pathPer24HCurMonValue
                    OCTET STRING,
                odu2_pathPer24HCurVldty
                    INTEGER,
                odu2_pathPer24HCurDateTime
                    DateAndTime,
                odu2_pathPer24HCurParaLen
                    INTEGER,
                odu2_pathPer24HCurPara
                    OCTET STRING
             }


        odu2_pathPer24HCurEid OBJECT-TYPE
            SYNTAX PerformanceEventType
            MAX-ACCESS read-only
            STATUS current
            DESCRIPTION
                "perEid."
            ::= { odu2_pathPer24HCurEntry 1 }


        odu2_pathPer24HCurMonValue OBJECT-TYPE
            SYNTAX OCTET STRING (SIZE (0..100))
            MAX-ACCESS read-only
            STATUS current
            DESCRIPTION
                "perMonValue."
            ::= { odu2_pathPer24HCurEntry 2 }


        odu2_pathPer24HCurVldty OBJECT-TYPE
            SYNTAX INTEGER
            MAX-ACCESS read-only
            STATUS current
            DESCRIPTION
                "perVldty. "
            ::= { odu2_pathPer24HCurEntry 3 }


        odu2_pathPer24HCurDateTime OBJECT-TYPE
            SYNTAX DateAndTime
            MAX-ACCESS read-only
            STATUS current
            DESCRIPTION
                "perDateTime. "
            ::= { odu2_pathPer24HCurEntry 4 }


        odu2_pathPer24HCurParaLen OBJECT-TYPE
            SYNTAX INTEGER
            MAX-ACCESS read-only
            STATUS current
            DESCRIPTION
                "perParaLen."
            ::= { odu2_pathPer24HCurEntry 5 }


        odu2_pathPer24HCurPara OBJECT-TYPE
            SYNTAX OCTET STRING (SIZE (0..100))
            MAX-ACCESS read-only
            STATUS current
            DESCRIPTION
                "perPara."
            ::= { odu2_pathPer24HCurEntry 6 }


-- -------------------------------------------------------------------------
-- Perfomance 24-HOUR History Data Table (RTRV-PER-<MOD2>)
-- -------------------------------------------------------------------------
        odu2_pathPer24HHisTable OBJECT-TYPE
            SYNTAX SEQUENCE OF Odu2_pathPer24HHisEntry
            MAX-ACCESS not-accessible
            STATUS current
            DESCRIPTION
                "odu2_pathPer24HHis."
            ::= { odu2_path 40 }


        odu2_pathPer24HHisEntry OBJECT-TYPE
            SYNTAX Odu2_pathPer24HHisEntry
            MAX-ACCESS not-accessible
            STATUS current
            DESCRIPTION
                "odu2_pathPer24HHis."
            INDEX {odu2_pathPer24HHisEid, odu2_pathPer24HHisParaLen, odu2_pathPer24HHisPara, odu2_pathPer24HHisDateTimeStart, odu2_pathPer24HHisDateTimeEnd}
            ::= { odu2_pathPer24HHisTable 1 }

        Odu2_pathPer24HHisEntry ::=
            SEQUENCE {
                odu2_pathPer24HHisEid
                    PerformanceEventType,
              odu2_pathPer24HHisParaLen
                    INTEGER,
                odu2_pathPer24HHisPara
                    OCTET STRING,
                odu2_pathPer24HHisMonValue
                    OCTET STRING,
                odu2_pathPer24HHisDateTimeStart
                    DateAndTime,
                odu2_pathPer24HHisDateTimeEnd
                    DateAndTime,
                odu2_pathPer24HHisVldty
                    INTEGER,
             }

        odu2_pathPer24HHisEid OBJECT-TYPE
            SYNTAX PerformanceEventType
            MAX-ACCESS read-only
            STATUS current
            DESCRIPTION
                "perEid."
            ::= { odu2_pathPer24HHisEntry 1 }

        odu2_pathPer24HHisParaLen OBJECT-TYPE
            SYNTAX INTEGER
            MAX-ACCESS read-only
            STATUS current
            DESCRIPTION
                "perParaLen."
            ::= { odu2_pathPer24HHisEntry 2 }


        odu2_pathPer24HHisPara OBJECT-TYPE
            SYNTAX OCTET STRING (SIZE (0..100))
            MAX-ACCESS read-only
            STATUS current
            DESCRIPTION
                "perPara."
            ::= { odu2_pathPer24HHisEntry 3 }



        odu2_pathPer24HHisMonValue OBJECT-TYPE
            SYNTAX OCTET STRING (SIZE (0..100))
            MAX-ACCESS read-only
            STATUS current
            DESCRIPTION
                "perMonValue."
            ::= { odu2_pathPer24HHisEntry 4 }



        odu2_pathPer24HHisDateTimeStart OBJECT-TYPE
            SYNTAX DateAndTime
            MAX-ACCESS read-only
            STATUS current
            DESCRIPTION
                "perDateTimeStart. "
            ::= { odu2_pathPer24HHisEntry 5 }

        odu2_pathPer24HHisDateTimeEnd OBJECT-TYPE
            SYNTAX DateAndTime
            MAX-ACCESS read-only
            STATUS current
            DESCRIPTION
                "perDateTimeEnd. "
            ::= { odu2_pathPer24HHisEntry 6 }


        odu2_pathPer24HHisVldty OBJECT-TYPE
            SYNTAX INTEGER
            MAX-ACCESS read-only
            STATUS current
            DESCRIPTION
                "perVldty. "
            ::= { odu2_pathPer24HHisEntry 7 }

--  Alarm data
        -- 1.3.6.1.4.1.2011.2.25.3.40.50.95
        odu3_path OBJECT IDENTIFIER ::= { optixGlobalNGWDM 95 }

-- -------------------------------------------------------------------------
-- Perfomance 15-MIN Current Data Table (RTRV-PER-<MOD2>)
-- -------------------------------------------------------------------------
        -- 1.3.6.1.4.1.2011.2.25.3.40.50.95.10
        odu3_pathPer15mCurTable OBJECT-TYPE
            SYNTAX SEQUENCE OF Odu3_pathPer15mCurEntry
            MAX-ACCESS not-accessible
            STATUS current
            DESCRIPTION
                "odu3_pathPer15mCur."
            ::= { odu3_path 10 }

        -- 1.3.6.1.4.1.2011.2.25.3.40.50.95.10.1
        odu3_pathPer15mCurEntry OBJECT-TYPE
            SYNTAX Odu3_pathPer15mCurEntry
            MAX-ACCESS not-accessible
            STATUS current
            DESCRIPTION
                "odu3_pathPer15mCur."
            INDEX {odu3_pathPer15mCurEid, odu3_pathPer15mCurPara}
            ::= { odu3_pathPer15mCurTable 1 }

        Odu3_pathPer15mCurEntry ::=
            SEQUENCE {
                odu3_pathPer15mCurEid
                    PerformanceEventType,
                odu3_pathPer15mCurMonValue
                    OCTET STRING,
                odu3_pathPer15mCurVldty
                    INTEGER,
                odu3_pathPer15mCurDateTime
                    DateAndTime,
                odu3_pathPer15mCurParaLen
                    INTEGER,
                odu3_pathPer15mCurPara
                    OCTET STRING
             }

        -- 1.3.6.1.4.1.2011.2.25.3.40.50.95.10.1.1
        odu3_pathPer15mCurEid OBJECT-TYPE
            SYNTAX PerformanceEventType
            MAX-ACCESS read-only
            STATUS current
            DESCRIPTION
                "perEid."
            ::= { odu3_pathPer15mCurEntry 1 }

        -- 1.3.6.1.4.1.2011.2.25.3.40.50.95.10.1.2
        odu3_pathPer15mCurMonValue OBJECT-TYPE
            SYNTAX OCTET STRING (SIZE (0..100))
            MAX-ACCESS read-only
            STATUS current
            DESCRIPTION
                "perMonValue."
            ::= { odu3_pathPer15mCurEntry 2 }

        -- 1.3.6.1.4.1.2011.2.25.3.40.50.95.10.3
        odu3_pathPer15mCurVldty OBJECT-TYPE
            SYNTAX INTEGER
            MAX-ACCESS read-only
            STATUS current
            DESCRIPTION
                "perVldty. "
            ::= { odu3_pathPer15mCurEntry 3 }

        -- 1.3.6.1.4.1.2011.2.25.3.40.50.95.10.1.4
        odu3_pathPer15mCurDateTime OBJECT-TYPE
            SYNTAX DateAndTime
            MAX-ACCESS read-only
            STATUS current
            DESCRIPTION
                "perDateTime. "
            ::= { odu3_pathPer15mCurEntry 4 }

        -- 1.3.6.1.4.1.2011.2.25.3.40.50.95.10.1.5
        odu3_pathPer15mCurParaLen OBJECT-TYPE
            SYNTAX INTEGER
            MAX-ACCESS read-only
            STATUS current
            DESCRIPTION
                "perParaLen."
            ::= { odu3_pathPer15mCurEntry 5 }

        -- 1.3.6.1.4.1.2011.2.25.3.40.50.95.10.1.6
        odu3_pathPer15mCurPara OBJECT-TYPE
            SYNTAX OCTET STRING (SIZE (0..100))
            MAX-ACCESS read-only
            STATUS current
            DESCRIPTION
                "perPara."
            ::= { odu3_pathPer15mCurEntry 6 }


-- -------------------------------------------------------------------------
-- Perfomance 15-MIN History Data Table (RTRV-PER-<MOD2>)
-- -------------------------------------------------------------------------
        odu3_pathPer15MHisTable OBJECT-TYPE
            SYNTAX SEQUENCE OF Odu3_pathPer15MHisEntry
            MAX-ACCESS not-accessible
            STATUS current
            DESCRIPTION
                "odu3_pathPer15MHis."
            ::= { odu3_path 20 }


        odu3_pathPer15MHisEntry OBJECT-TYPE
            SYNTAX Odu3_pathPer15MHisEntry
            MAX-ACCESS not-accessible
            STATUS current
            DESCRIPTION
                "odu3_pathPer15MHis."
            INDEX {odu3_pathPer15MHisEid, odu3_pathPer15MHisParaLen, odu3_pathPer15MHisPara, odu3_pathPer15MHisDateTimeStart, odu3_pathPer15MHisDateTimeEnd}
            ::= { odu3_pathPer15MHisTable 1 }

        Odu3_pathPer15MHisEntry ::=
            SEQUENCE {
                odu3_pathPer15MHisEid
                    PerformanceEventType,
                odu3_pathPer15MHisParaLen
                    INTEGER,
                odu3_pathPer15MHisPara
                    OCTET STRING,
                odu3_pathPer15MHisMonValue
                    OCTET STRING,
                odu3_pathPer15MHisDateTimeStart
                    DateAndTime,
                odu3_pathPer15MHisDateTimeEnd
                    DateAndTime,
                odu3_pathPer15MHisVldty
                    INTEGER,
             }

        odu3_pathPer15MHisEid OBJECT-TYPE
            SYNTAX PerformanceEventType
            MAX-ACCESS read-only
            STATUS current
            DESCRIPTION
                "perEid."
            ::= { odu3_pathPer15MHisEntry 1 }

        odu3_pathPer15MHisParaLen OBJECT-TYPE
            SYNTAX INTEGER
            MAX-ACCESS read-only
            STATUS current
            DESCRIPTION
                "perParaLen."
            ::= { odu3_pathPer15MHisEntry 2 }


        odu3_pathPer15MHisPara OBJECT-TYPE
            SYNTAX OCTET STRING (SIZE (0..100))
            MAX-ACCESS read-only
            STATUS current
            DESCRIPTION
                "perPara."
            ::= { odu3_pathPer15MHisEntry 3 }



        odu3_pathPer15MHisMonValue OBJECT-TYPE
            SYNTAX OCTET STRING (SIZE (0..100))
            MAX-ACCESS read-only
            STATUS current
            DESCRIPTION
                "perMonValue."
            ::= { odu3_pathPer15MHisEntry 4 }



        odu3_pathPer15MHisDateTimeStart OBJECT-TYPE
            SYNTAX DateAndTime
            MAX-ACCESS read-only
            STATUS current
            DESCRIPTION
                "perDateTimeStart. "
            ::= { odu3_pathPer15MHisEntry 5 }

        odu3_pathPer15MHisDateTimeEnd OBJECT-TYPE
            SYNTAX DateAndTime
            MAX-ACCESS read-only
            STATUS current
            DESCRIPTION
                "perDateTimeEnd. "
            ::= { odu3_pathPer15MHisEntry 6 }


        odu3_pathPer15MHisVldty OBJECT-TYPE
            SYNTAX INTEGER
            MAX-ACCESS read-only
            STATUS current
            DESCRIPTION
                "perVldty. "
            ::= { odu3_pathPer15MHisEntry 7 }


-- -------------------------------------------------------------------------
-- Perfomance 24-HOUR Current Data Table (RTRV-PER-<MOD2>)
-- -------------------------------------------------------------------------
        odu3_pathPer24HCurTable OBJECT-TYPE
            SYNTAX SEQUENCE OF Odu3_pathPer24HCurEntry
            MAX-ACCESS not-accessible
            STATUS current
            DESCRIPTION
                "odu3_pathPer24HCur."
            ::= { odu3_path 30 }


        odu3_pathPer24HCurEntry OBJECT-TYPE
            SYNTAX Odu3_pathPer24HCurEntry
            MAX-ACCESS not-accessible
            STATUS current
            DESCRIPTION
                "odu3_pathPer24HCur."
            INDEX {odu3_pathPer24HCurEid, odu3_pathPer24HCurPara}
            ::= { odu3_pathPer24HCurTable 1 }

        Odu3_pathPer24HCurEntry ::=
            SEQUENCE {
                odu3_pathPer24HCurEid
                    PerformanceEventType,
                odu3_pathPer24HCurMonValue
                    OCTET STRING,
                odu3_pathPer24HCurVldty
                    INTEGER,
                odu3_pathPer24HCurDateTime
                    DateAndTime,
                odu3_pathPer24HCurParaLen
                    INTEGER,
                odu3_pathPer24HCurPara
                    OCTET STRING
             }


        odu3_pathPer24HCurEid OBJECT-TYPE
            SYNTAX PerformanceEventType
            MAX-ACCESS read-only
            STATUS current
            DESCRIPTION
                "perEid."
            ::= { odu3_pathPer24HCurEntry 1 }


        odu3_pathPer24HCurMonValue OBJECT-TYPE
            SYNTAX OCTET STRING (SIZE (0..100))
            MAX-ACCESS read-only
            STATUS current
            DESCRIPTION
                "perMonValue."
            ::= { odu3_pathPer24HCurEntry 2 }


        odu3_pathPer24HCurVldty OBJECT-TYPE
            SYNTAX INTEGER
            MAX-ACCESS read-only
            STATUS current
            DESCRIPTION
                "perVldty. "
            ::= { odu3_pathPer24HCurEntry 3 }


        odu3_pathPer24HCurDateTime OBJECT-TYPE
            SYNTAX DateAndTime
            MAX-ACCESS read-only
            STATUS current
            DESCRIPTION
                "perDateTime. "
            ::= { odu3_pathPer24HCurEntry 4 }


        odu3_pathPer24HCurParaLen OBJECT-TYPE
            SYNTAX INTEGER
            MAX-ACCESS read-only
            STATUS current
            DESCRIPTION
                "perParaLen."
            ::= { odu3_pathPer24HCurEntry 5 }


        odu3_pathPer24HCurPara OBJECT-TYPE
            SYNTAX OCTET STRING (SIZE (0..100))
            MAX-ACCESS read-only
            STATUS current
            DESCRIPTION
                "perPara."
            ::= { odu3_pathPer24HCurEntry 6 }


-- -------------------------------------------------------------------------
-- Perfomance 24-HOUR History Data Table (RTRV-PER-<MOD2>)
-- -------------------------------------------------------------------------
        odu3_pathPer24HHisTable OBJECT-TYPE
            SYNTAX SEQUENCE OF Odu3_pathPer24HHisEntry
            MAX-ACCESS not-accessible
            STATUS current
            DESCRIPTION
                "odu3_pathPer24HHis."
            ::= { odu3_path 40 }


        odu3_pathPer24HHisEntry OBJECT-TYPE
            SYNTAX Odu3_pathPer24HHisEntry
            MAX-ACCESS not-accessible
            STATUS current
            DESCRIPTION
                "odu3_pathPer24HHis."
            INDEX {odu3_pathPer24HHisEid, odu3_pathPer24HHisParaLen, odu3_pathPer24HHisPara, odu3_pathPer24HHisDateTimeStart, odu3_pathPer24HHisDateTimeEnd}
            ::= { odu3_pathPer24HHisTable 1 }

        Odu3_pathPer24HHisEntry ::=
            SEQUENCE {
                odu3_pathPer24HHisEid
                    PerformanceEventType,
              odu3_pathPer24HHisParaLen
                    INTEGER,
                odu3_pathPer24HHisPara
                    OCTET STRING,
                odu3_pathPer24HHisMonValue
                    OCTET STRING,
                odu3_pathPer24HHisDateTimeStart
                    DateAndTime,
                odu3_pathPer24HHisDateTimeEnd
                    DateAndTime,
                odu3_pathPer24HHisVldty
                    INTEGER,
             }

        odu3_pathPer24HHisEid OBJECT-TYPE
            SYNTAX PerformanceEventType
            MAX-ACCESS read-only
            STATUS current
            DESCRIPTION
                "perEid."
            ::= { odu3_pathPer24HHisEntry 1 }

        odu3_pathPer24HHisParaLen OBJECT-TYPE
            SYNTAX INTEGER
            MAX-ACCESS read-only
            STATUS current
            DESCRIPTION
                "perParaLen."
            ::= { odu3_pathPer24HHisEntry 2 }


        odu3_pathPer24HHisPara OBJECT-TYPE
            SYNTAX OCTET STRING (SIZE (0..100))
            MAX-ACCESS read-only
            STATUS current
            DESCRIPTION
                "perPara."
            ::= { odu3_pathPer24HHisEntry 3 }



        odu3_pathPer24HHisMonValue OBJECT-TYPE
            SYNTAX OCTET STRING (SIZE (0..100))
            MAX-ACCESS read-only
            STATUS current
            DESCRIPTION
                "perMonValue."
            ::= { odu3_pathPer24HHisEntry 4 }



        odu3_pathPer24HHisDateTimeStart OBJECT-TYPE
            SYNTAX DateAndTime
            MAX-ACCESS read-only
            STATUS current
            DESCRIPTION
                "perDateTimeStart. "
            ::= { odu3_pathPer24HHisEntry 5 }

        odu3_pathPer24HHisDateTimeEnd OBJECT-TYPE
            SYNTAX DateAndTime
            MAX-ACCESS read-only
            STATUS current
            DESCRIPTION
                "perDateTimeEnd. "
            ::= { odu3_pathPer24HHisEntry 6 }


        odu3_pathPer24HHisVldty OBJECT-TYPE
            SYNTAX INTEGER
            MAX-ACCESS read-only
            STATUS current
            DESCRIPTION
                "perVldty. "
            ::= { odu3_pathPer24HHisEntry 7 }

--  Alarm data
        -- 1.3.6.1.4.1.2011.2.25.3.40.50.96
        sdh_path OBJECT IDENTIFIER ::= { optixGlobalNGWDM 96 }

-- -------------------------------------------------------------------------
-- Perfomance 15-MIN Current Data Table (RTRV-PER-<MOD2>)
-- -------------------------------------------------------------------------
        -- 1.3.6.1.4.1.2011.2.25.3.40.50.96.10
        sdh_pathPer15mCurTable OBJECT-TYPE
            SYNTAX SEQUENCE OF Sdh_pathPer15mCurEntry
            MAX-ACCESS not-accessible
            STATUS current
            DESCRIPTION
                "sdh_pathPer15mCur."
            ::= { sdh_path 10 }

        -- 1.3.6.1.4.1.2011.2.25.3.40.50.96.10.1
        sdh_pathPer15mCurEntry OBJECT-TYPE
            SYNTAX Sdh_pathPer15mCurEntry
            MAX-ACCESS not-accessible
            STATUS current
            DESCRIPTION
                "sdh_pathPer15mCur."
            INDEX {sdh_pathPer15mCurEid, sdh_pathPer15mCurPara}
            ::= { sdh_pathPer15mCurTable 1 }

        Sdh_pathPer15mCurEntry ::=
            SEQUENCE {
                sdh_pathPer15mCurEid
                    PerformanceEventType,
                sdh_pathPer15mCurMonValue
                    OCTET STRING,
                sdh_pathPer15mCurVldty
                    INTEGER,
                sdh_pathPer15mCurDateTime
                    DateAndTime,
                sdh_pathPer15mCurParaLen
                    INTEGER,
                sdh_pathPer15mCurPara
                    OCTET STRING
             }

        -- 1.3.6.1.4.1.2011.2.25.3.40.50.96.10.1.1
        sdh_pathPer15mCurEid OBJECT-TYPE
            SYNTAX PerformanceEventType
            MAX-ACCESS read-only
            STATUS current
            DESCRIPTION
                "perEid."
            ::= { sdh_pathPer15mCurEntry 1 }

        -- 1.3.6.1.4.1.2011.2.25.3.40.50.96.10.1.2
        sdh_pathPer15mCurMonValue OBJECT-TYPE
            SYNTAX OCTET STRING (SIZE (0..100))
            MAX-ACCESS read-only
            STATUS current
            DESCRIPTION
                "perMonValue."
            ::= { sdh_pathPer15mCurEntry 2 }

        -- 1.3.6.1.4.1.2011.2.25.3.40.50.96.10.3
        sdh_pathPer15mCurVldty OBJECT-TYPE
            SYNTAX INTEGER
            MAX-ACCESS read-only
            STATUS current
            DESCRIPTION
                "perVldty. "
            ::= { sdh_pathPer15mCurEntry 3 }

        -- 1.3.6.1.4.1.2011.2.25.3.40.50.96.10.1.4
        sdh_pathPer15mCurDateTime OBJECT-TYPE
            SYNTAX DateAndTime
            MAX-ACCESS read-only
            STATUS current
            DESCRIPTION
                "perDateTime. "
            ::= { sdh_pathPer15mCurEntry 4 }

        -- 1.3.6.1.4.1.2011.2.25.3.40.50.96.10.1.5
        sdh_pathPer15mCurParaLen OBJECT-TYPE
            SYNTAX INTEGER
            MAX-ACCESS read-only
            STATUS current
            DESCRIPTION
                "perParaLen."
            ::= { sdh_pathPer15mCurEntry 5 }

        -- 1.3.6.1.4.1.2011.2.25.3.40.50.96.10.1.6
        sdh_pathPer15mCurPara OBJECT-TYPE
            SYNTAX OCTET STRING (SIZE (0..100))
            MAX-ACCESS read-only
            STATUS current
            DESCRIPTION
                "perPara."
            ::= { sdh_pathPer15mCurEntry 6 }


-- -------------------------------------------------------------------------
-- Perfomance 15-MIN History Data Table (RTRV-PER-<MOD2>)
-- -------------------------------------------------------------------------
        sdh_pathPer15MHisTable OBJECT-TYPE
            SYNTAX SEQUENCE OF Sdh_pathPer15MHisEntry
            MAX-ACCESS not-accessible
            STATUS current
            DESCRIPTION
                "sdh_pathPer15MHis."
            ::= { sdh_path 20 }


        sdh_pathPer15MHisEntry OBJECT-TYPE
            SYNTAX Sdh_pathPer15MHisEntry
            MAX-ACCESS not-accessible
            STATUS current
            DESCRIPTION
                "sdh_pathPer15MHis."
            INDEX {sdh_pathPer15MHisEid, sdh_pathPer15MHisParaLen, sdh_pathPer15MHisPara, sdh_pathPer15MHisDateTimeStart, sdh_pathPer15MHisDateTimeEnd}
            ::= { sdh_pathPer15MHisTable 1 }

        Sdh_pathPer15MHisEntry ::=
            SEQUENCE {
                sdh_pathPer15MHisEid
                    PerformanceEventType,
                sdh_pathPer15MHisParaLen
                    INTEGER,
                sdh_pathPer15MHisPara
                    OCTET STRING,
                sdh_pathPer15MHisMonValue
                    OCTET STRING,
                sdh_pathPer15MHisDateTimeStart
                    DateAndTime,
                sdh_pathPer15MHisDateTimeEnd
                    DateAndTime,
                sdh_pathPer15MHisVldty
                    INTEGER,
             }

        sdh_pathPer15MHisEid OBJECT-TYPE
            SYNTAX PerformanceEventType
            MAX-ACCESS read-only
            STATUS current
            DESCRIPTION
                "perEid."
            ::= { sdh_pathPer15MHisEntry 1 }

        sdh_pathPer15MHisParaLen OBJECT-TYPE
            SYNTAX INTEGER
            MAX-ACCESS read-only
            STATUS current
            DESCRIPTION
                "perParaLen."
            ::= { sdh_pathPer15MHisEntry 2 }


        sdh_pathPer15MHisPara OBJECT-TYPE
            SYNTAX OCTET STRING (SIZE (0..100))
            MAX-ACCESS read-only
            STATUS current
            DESCRIPTION
                "perPara."
            ::= { sdh_pathPer15MHisEntry 3 }



        sdh_pathPer15MHisMonValue OBJECT-TYPE
            SYNTAX OCTET STRING (SIZE (0..100))
            MAX-ACCESS read-only
            STATUS current
            DESCRIPTION
                "perMonValue."
            ::= { sdh_pathPer15MHisEntry 4 }



        sdh_pathPer15MHisDateTimeStart OBJECT-TYPE
            SYNTAX DateAndTime
            MAX-ACCESS read-only
            STATUS current
            DESCRIPTION
                "perDateTimeStart. "
            ::= { sdh_pathPer15MHisEntry 5 }

        sdh_pathPer15MHisDateTimeEnd OBJECT-TYPE
            SYNTAX DateAndTime
            MAX-ACCESS read-only
            STATUS current
            DESCRIPTION
                "perDateTimeEnd. "
            ::= { sdh_pathPer15MHisEntry 6 }


        sdh_pathPer15MHisVldty OBJECT-TYPE
            SYNTAX INTEGER
            MAX-ACCESS read-only
            STATUS current
            DESCRIPTION
                "perVldty. "
            ::= { sdh_pathPer15MHisEntry 7 }


-- -------------------------------------------------------------------------
-- Perfomance 24-HOUR Current Data Table (RTRV-PER-<MOD2>)
-- -------------------------------------------------------------------------
        sdh_pathPer24HCurTable OBJECT-TYPE
            SYNTAX SEQUENCE OF Sdh_pathPer24HCurEntry
            MAX-ACCESS not-accessible
            STATUS current
            DESCRIPTION
                "sdh_pathPer24HCur."
            ::= { sdh_path 30 }


        sdh_pathPer24HCurEntry OBJECT-TYPE
            SYNTAX Sdh_pathPer24HCurEntry
            MAX-ACCESS not-accessible
            STATUS current
            DESCRIPTION
                "sdh_pathPer24HCur."
            INDEX {sdh_pathPer24HCurEid, sdh_pathPer24HCurPara}
            ::= { sdh_pathPer24HCurTable 1 }

        Sdh_pathPer24HCurEntry ::=
            SEQUENCE {
                sdh_pathPer24HCurEid
                    PerformanceEventType,
                sdh_pathPer24HCurMonValue
                    OCTET STRING,
                sdh_pathPer24HCurVldty
                    INTEGER,
                sdh_pathPer24HCurDateTime
                    DateAndTime,
                sdh_pathPer24HCurParaLen
                    INTEGER,
                sdh_pathPer24HCurPara
                    OCTET STRING
             }


        sdh_pathPer24HCurEid OBJECT-TYPE
            SYNTAX PerformanceEventType
            MAX-ACCESS read-only
            STATUS current
            DESCRIPTION
                "perEid."
            ::= { sdh_pathPer24HCurEntry 1 }


        sdh_pathPer24HCurMonValue OBJECT-TYPE
            SYNTAX OCTET STRING (SIZE (0..100))
            MAX-ACCESS read-only
            STATUS current
            DESCRIPTION
                "perMonValue."
            ::= { sdh_pathPer24HCurEntry 2 }


        sdh_pathPer24HCurVldty OBJECT-TYPE
            SYNTAX INTEGER
            MAX-ACCESS read-only
            STATUS current
            DESCRIPTION
                "perVldty. "
            ::= { sdh_pathPer24HCurEntry 3 }


        sdh_pathPer24HCurDateTime OBJECT-TYPE
            SYNTAX DateAndTime
            MAX-ACCESS read-only
            STATUS current
            DESCRIPTION
                "perDateTime. "
            ::= { sdh_pathPer24HCurEntry 4 }


        sdh_pathPer24HCurParaLen OBJECT-TYPE
            SYNTAX INTEGER
            MAX-ACCESS read-only
            STATUS current
            DESCRIPTION
                "perParaLen."
            ::= { sdh_pathPer24HCurEntry 5 }


        sdh_pathPer24HCurPara OBJECT-TYPE
            SYNTAX OCTET STRING (SIZE (0..100))
            MAX-ACCESS read-only
            STATUS current
            DESCRIPTION
                "perPara."
            ::= { sdh_pathPer24HCurEntry 6 }


-- -------------------------------------------------------------------------
-- Perfomance 24-HOUR History Data Table (RTRV-PER-<MOD2>)
-- -------------------------------------------------------------------------
        sdh_pathPer24HHisTable OBJECT-TYPE
            SYNTAX SEQUENCE OF Sdh_pathPer24HHisEntry
            MAX-ACCESS not-accessible
            STATUS current
            DESCRIPTION
                "sdh_pathPer24HHis."
            ::= { sdh_path 40 }


        sdh_pathPer24HHisEntry OBJECT-TYPE
            SYNTAX Sdh_pathPer24HHisEntry
            MAX-ACCESS not-accessible
            STATUS current
            DESCRIPTION
                "sdh_pathPer24HHis."
            INDEX {sdh_pathPer24HHisEid, sdh_pathPer24HHisParaLen, sdh_pathPer24HHisPara, sdh_pathPer24HHisDateTimeStart, sdh_pathPer24HHisDateTimeEnd}
            ::= { sdh_pathPer24HHisTable 1 }

        Sdh_pathPer24HHisEntry ::=
            SEQUENCE {
                sdh_pathPer24HHisEid
                    PerformanceEventType,
              sdh_pathPer24HHisParaLen
                    INTEGER,
                sdh_pathPer24HHisPara
                    OCTET STRING,
                sdh_pathPer24HHisMonValue
                    OCTET STRING,
                sdh_pathPer24HHisDateTimeStart
                    DateAndTime,
                sdh_pathPer24HHisDateTimeEnd
                    DateAndTime,
                sdh_pathPer24HHisVldty
                    INTEGER,
             }

        sdh_pathPer24HHisEid OBJECT-TYPE
            SYNTAX PerformanceEventType
            MAX-ACCESS read-only
            STATUS current
            DESCRIPTION
                "perEid."
            ::= { sdh_pathPer24HHisEntry 1 }

        sdh_pathPer24HHisParaLen OBJECT-TYPE
            SYNTAX INTEGER
            MAX-ACCESS read-only
            STATUS current
            DESCRIPTION
                "perParaLen."
            ::= { sdh_pathPer24HHisEntry 2 }


        sdh_pathPer24HHisPara OBJECT-TYPE
            SYNTAX OCTET STRING (SIZE (0..100))
            MAX-ACCESS read-only
            STATUS current
            DESCRIPTION
                "perPara."
            ::= { sdh_pathPer24HHisEntry 3 }



        sdh_pathPer24HHisMonValue OBJECT-TYPE
            SYNTAX OCTET STRING (SIZE (0..100))
            MAX-ACCESS read-only
            STATUS current
            DESCRIPTION
                "perMonValue."
            ::= { sdh_pathPer24HHisEntry 4 }



        sdh_pathPer24HHisDateTimeStart OBJECT-TYPE
            SYNTAX DateAndTime
            MAX-ACCESS read-only
            STATUS current
            DESCRIPTION
                "perDateTimeStart. "
            ::= { sdh_pathPer24HHisEntry 5 }

        sdh_pathPer24HHisDateTimeEnd OBJECT-TYPE
            SYNTAX DateAndTime
            MAX-ACCESS read-only
            STATUS current
            DESCRIPTION
                "perDateTimeEnd. "
            ::= { sdh_pathPer24HHisEntry 6 }


        sdh_pathPer24HHisVldty OBJECT-TYPE
            SYNTAX INTEGER
            MAX-ACCESS read-only
            STATUS current
            DESCRIPTION
                "perVldty. "
            ::= { sdh_pathPer24HHisEntry 7 }

--  *************************************************************************
-- -------------------------------------------------------------------------
-- DataPmfomance 30-MIN Current Data Table (RTRV-DataPm-<MOD2>)
-- -------------------------------------------------------------------------

        sdh_pathDataPm30mTable OBJECT-TYPE
            SYNTAX SEQUENCE OF Sdh_pathDataPm30mEntry
            MAX-ACCESS not-accessible
            STATUS current
            DESCRIPTION
                "sdh_pathDataPm30minite."
            ::= { sdh_path 60 }


        sdh_pathDataPm30mEntry OBJECT-TYPE
            SYNTAX Sdh_pathDataPm30mEntry
            MAX-ACCESS not-accessible
            STATUS current
            DESCRIPTION
                "sdh_pathDataPm30m."
            INDEX {sdh_pathData30mPmEid, sdh_pathData30mPmParaLen, sdh_pathData30mPmPara, sdh_pathData30mPmStartTime, sdh_pathData30mPmEndTime}
            ::= { sdh_pathDataPm30mTable 1 }

        Sdh_pathDataPm30mEntry ::=
            SEQUENCE {
                sdh_pathData30mPmEid
                    DataPmEventType,
                sdh_pathData30mPmParaLen
                    INTEGER,
                sdh_pathData30mPmPara
                    DisplayString,
                sdh_pathData30mPmMonValue
                    Counter64,
                sdh_pathData30mPmStartTime
                    DateAndTime,
                sdh_pathData30mPmEndTime
										DateAndTime,
								sdh_pathData30mPmValidity
										INTEGER,
             }

        sdh_pathData30mPmEid OBJECT-TYPE
            SYNTAX DataPmEventType
            MAX-ACCESS read-only
            STATUS current
            DESCRIPTION
                "DataPmName."
            ::= { sdh_pathDataPm30mEntry 1 }

        sdh_pathData30mPmParaLen OBJECT-TYPE
            SYNTAX INTEGER
            MAX-ACCESS read-only
            STATUS current
            DESCRIPTION
                "ParaLen."
            ::= { sdh_pathDataPm30mEntry 2 }


        sdh_pathData30mPmPara OBJECT-TYPE
            SYNTAX DisplayString
            MAX-ACCESS read-only
            STATUS current
            DESCRIPTION
                "para"
            ::= { sdh_pathDataPm30mEntry 3 }



        sdh_pathData30mPmMonValue OBJECT-TYPE
            SYNTAX Counter64
            MAX-ACCESS read-only
            STATUS current
            DESCRIPTION
                "DataPmMonValue. "
            ::= { sdh_pathDataPm30mEntry 4 }

        sdh_pathData30mPmStartTime OBJECT-TYPE
            SYNTAX DateAndTime
            MAX-ACCESS read-only
            STATUS current
            DESCRIPTION
                "Start Time. "
            ::= { sdh_pathDataPm30mEntry 5 }

        sdh_pathData30mPmEndTime OBJECT-TYPE
            SYNTAX DateAndTime
            MAX-ACCESS read-only
            STATUS current
            DESCRIPTION
                "End Time. "
            ::= { sdh_pathDataPm30mEntry 6 }

        sdh_pathData30mPmValidity OBJECT-TYPE
            SYNTAX INTEGER
            MAX-ACCESS read-only
            STATUS current
            DESCRIPTION
                "Validity. "
            ::= { sdh_pathDataPm30mEntry 7 }


-- -------------------------------------------------------------------------
-- DataPmfomance 30-MIN Current Data Table (RTRV-DataPm-<MOD2>)
-- -------------------------------------------------------------------------
		-- 1.3.6.1.4.1.2011.2.25.3.20.20.10.10
		sdh_pathDataPmStatTable OBJECT-TYPE
			SYNTAX SEQUENCE OF Sdh_pathDataPmStatEntry
			MAX-ACCESS not-accessible
			STATUS current
			DESCRIPTION
				"sdh_pathDataPm30SCur."
			::= { sdh_path 50 }

		-- 1.3.6.1.4.1.2011.2.25.3.20.20.10.10.1
		sdh_pathDataPmStatEntry OBJECT-TYPE
			SYNTAX Sdh_pathDataPmStatEntry
			MAX-ACCESS not-accessible
			STATUS current
			DESCRIPTION
				"sdh_pathDataPmStat."
			INDEX {sdh_pathDataPmName, sdh_pathDataPmParaLen, sdh_pathDataPmPara}
			::= { sdh_pathDataPmStatTable 1 }

		Sdh_pathDataPmStatEntry ::=
			SEQUENCE {
				sdh_pathDataPmName
					DataPmEventType,
				sdh_pathDataPmParaLen
					INTEGER,
				sdh_pathDataPmPara
					DisplayString,
				sdh_pathDataPmMonValue
					Counter64,
				sdh_pathDataPmStartTime
					DateAndTime,
			 }

		sdh_pathDataPmName OBJECT-TYPE
			SYNTAX DataPmEventType
			MAX-ACCESS read-only
			STATUS current
			DESCRIPTION
				"DataPmName."
			::= { sdh_pathDataPmStatEntry 1 }

		sdh_pathDataPmParaLen OBJECT-TYPE
			SYNTAX INTEGER
			MAX-ACCESS read-only
			STATUS current
			DESCRIPTION
				"ParaLen."
			::= { sdh_pathDataPmStatEntry 2 }

		-- 1.3.6.1.4.1.2011.2.25.3.20.20.10.10.1.1
		sdh_pathDataPmPara OBJECT-TYPE
			SYNTAX DisplayString
			MAX-ACCESS read-only
			STATUS current
			DESCRIPTION
				"para"
			::= { sdh_pathDataPmStatEntry 3 }

		-- 1.3.6.1.4.1.2011.2.25.3.20.20.10.10.1.3
		sdh_pathDataPmMonValue OBJECT-TYPE
			SYNTAX Counter64
			MAX-ACCESS read-only
			STATUS current
			DESCRIPTION
				"DataPmMonValue. "
			::= { sdh_pathDataPmStatEntry 4 }

		sdh_pathDataPmStartTime OBJECT-TYPE
			SYNTAX DateAndTime
			MAX-ACCESS read-only
			STATUS current
			DESCRIPTION
				"Start Time. "
			::= { sdh_pathDataPmStatEntry 5 }
--  *************************************************************************
-- -------------------------------------------------------------------------
-- DataPmfomance 30-MIN Current Data Table (RTRV-DataPm-<MOD2>)
-- -------------------------------------------------------------------------

			-- 1.3.6.1.4.1.2011.2.25.3.40.50.98.50
			eth_pathDataPmStatTable OBJECT-TYPE
				SYNTAX SEQUENCE OF Eth_pathDataPmStatEntry
				MAX-ACCESS not-accessible
				STATUS current
				DESCRIPTION
					"eth_pathDataPm30SCur."
				::= { eth_path 50 }

			-- 1.3.6.1.4.1.2011.2.25.3.40.50.98.50.1
			eth_pathDataPmStatEntry OBJECT-TYPE
				SYNTAX Eth_pathDataPmStatEntry
				MAX-ACCESS not-accessible
				STATUS current
				DESCRIPTION
					"eth_pathDataPmStat."
				INDEX {eth_pathDataPmName, eth_pathDataPmParaLen, eth_pathDataPmPara}
				::= { eth_pathDataPmStatTable 1 }

			Eth_pathDataPmStatEntry ::=
				SEQUENCE {
					eth_pathDataPmName
						DataPmEventType,
					eth_pathDataPmParaLen
						INTEGER,
					eth_pathDataPmPara
						DisplayString,
					eth_pathDataPmMonValue
						Counter64,
					eth_pathDataPmStartTime
						DateAndTime,
				 }
			-- 1.3.6.1.4.1.2011.2.25.3.40.50.98.50.1.1
			eth_pathDataPmName OBJECT-TYPE
				SYNTAX DataPmEventType
				MAX-ACCESS read-only
				STATUS current
				DESCRIPTION
					"DataPmName."
				::= { eth_pathDataPmStatEntry 1 }
	        -- 1.3.6.1.4.1.2011.2.25.3.40.50.98.50.1.2
			eth_pathDataPmParaLen OBJECT-TYPE
				SYNTAX INTEGER
				MAX-ACCESS read-only
				STATUS current
				DESCRIPTION
					"ParaLen."
				::= { eth_pathDataPmStatEntry 2 }

			-- 1.3.6.1.4.1.2011.2.25.3.40.50.98.50.1.3
			eth_pathDataPmPara OBJECT-TYPE
				SYNTAX DisplayString
				MAX-ACCESS read-only
				STATUS current
				DESCRIPTION
					"para"
				::= { eth_pathDataPmStatEntry 3 }

			-- 1.3.6.1.4.1.2011.2.25.3.40.50.98.50.1.4
			eth_pathDataPmMonValue OBJECT-TYPE
				SYNTAX Counter64
				MAX-ACCESS read-only
				STATUS current
				DESCRIPTION
					"DataPmMonValue. "
				::= { eth_pathDataPmStatEntry 4 }
	        -- 1.3.6.1.4.1.2011.2.25.3.40.50.98.50.1.5
			eth_pathDataPmStartTime OBJECT-TYPE
				SYNTAX DateAndTime
				MAX-ACCESS read-only
				STATUS current
				DESCRIPTION
					"Start Time. "
				::= { eth_pathDataPmStatEntry 5 }

-- -------------------------------------------------------------------------
        -- 1.3.6.1.4.1.2011.2.25.3.40.50.98.60
        eth_pathDataPm30mTable OBJECT-TYPE
            SYNTAX SEQUENCE OF Eth_pathDataPm30mEntry
            MAX-ACCESS not-accessible
            STATUS current
            DESCRIPTION
                "eth_pathDataPm30minite."
            ::= { eth_path 60 }

        -- 1.3.6.1.4.1.2011.2.25.3.40.50.98.60.1
        eth_pathDataPm30mEntry OBJECT-TYPE
            SYNTAX Eth_pathDataPm30mEntry
            MAX-ACCESS not-accessible
            STATUS current
            DESCRIPTION
                "eth_pathDataPm30m."
            INDEX {eth_pathData30mPmEid, eth_pathData30mPmParaLen, eth_pathData30mPmPara, eth_pathData30mPmStartTime, eth_pathData30mPmEndTime}
            ::= { eth_pathDataPm30mTable 1 }

        Eth_pathDataPm30mEntry ::=
            SEQUENCE {
                eth_pathData30mPmEid
                    DataPmEventType,
                eth_pathData30mPmParaLen
                    INTEGER,
                eth_pathData30mPmPara
                    DisplayString,
                eth_pathData30mPmMonValue
                    Counter64,
                eth_pathData30mPmStartTime
                    DateAndTime,
                eth_pathData30mPmEndTime
                    DateAndTime,
                eth_pathData30mPmValidity
                    INTEGER,
             }
        -- 1.3.6.1.4.1.2011.2.25.3.40.50.98.60.1.1
        eth_pathData30mPmEid OBJECT-TYPE
            SYNTAX DataPmEventType
            MAX-ACCESS read-only
            STATUS current
            DESCRIPTION
                "DataPmName."
            ::= { eth_pathDataPm30mEntry 1 }
        -- 1.3.6.1.4.1.2011.2.25.3.40.50.98.60.1.2
        eth_pathData30mPmParaLen OBJECT-TYPE
            SYNTAX INTEGER
            MAX-ACCESS read-only
            STATUS current
            DESCRIPTION
                "ParaLen."
            ::= { eth_pathDataPm30mEntry 2 }

        -- 1.3.6.1.4.1.2011.2.25.3.40.50.98.60.1.3
        eth_pathData30mPmPara OBJECT-TYPE
            SYNTAX DisplayString
            MAX-ACCESS read-only
            STATUS current
            DESCRIPTION
                "para"
            ::= { eth_pathDataPm30mEntry 3 }


        -- 1.3.6.1.4.1.2011.2.25.3.40.50.98.60.1.4
        eth_pathData30mPmMonValue OBJECT-TYPE
            SYNTAX Counter64
            MAX-ACCESS read-only
            STATUS current
            DESCRIPTION
                "DataPmMonValue. "
            ::= { eth_pathDataPm30mEntry 4 }
        -- 1.3.6.1.4.1.2011.2.25.3.40.50.98.60.1.5
        eth_pathData30mPmStartTime OBJECT-TYPE
            SYNTAX DateAndTime
            MAX-ACCESS read-only
            STATUS current
            DESCRIPTION
                "Start Time. "
            ::= { eth_pathDataPm30mEntry 5 }
        -- 1.3.6.1.4.1.2011.2.25.3.40.50.98.60.1.6
        eth_pathData30mPmEndTime OBJECT-TYPE
            SYNTAX DateAndTime
            MAX-ACCESS read-only
            STATUS current
            DESCRIPTION
                "End Time. "
            ::= { eth_pathDataPm30mEntry 6 }
        -- 1.3.6.1.4.1.2011.2.25.3.40.50.98.60.1.7
        eth_pathData30mPmValidity OBJECT-TYPE
            SYNTAX INTEGER
            MAX-ACCESS read-only
            STATUS current
            DESCRIPTION
                "Validity. "
            ::= { eth_pathDataPm30mEntry 7 }


--  Alarm data
        -- 1.3.6.1.4.1.2011.2.25.3.40.50.167
        efi OBJECT IDENTIFIER ::= { optixGlobalNGWDM 167 }

-- -------------------------------------------------------------------------
-- Perfomance 15-MIN Current Data Table (RTRV-PER-<MOD2>)
-- -------------------------------------------------------------------------
        -- 1.3.6.1.4.1.2011.2.25.3.40.50.167.10
        efiPer15mCurTable OBJECT-TYPE
            SYNTAX SEQUENCE OF EfiPer15mCurEntry
            MAX-ACCESS not-accessible
            STATUS current
            DESCRIPTION
                "efiPer15mCur."
            ::= { efi 10 }

        -- 1.3.6.1.4.1.2011.2.25.3.40.50.167.10.1
        efiPer15mCurEntry OBJECT-TYPE
            SYNTAX EfiPer15mCurEntry
            MAX-ACCESS not-accessible
            STATUS current
            DESCRIPTION
                "efiPer15mCur."
            INDEX {efiPer15mCurEid, efiPer15mCurPara}
            ::= { efiPer15mCurTable 1 }

        EfiPer15mCurEntry ::=
            SEQUENCE {
                efiPer15mCurEid
                    PerformanceEventType,
                efiPer15mCurMonValue
                    OCTET STRING,
                efiPer15mCurVldty
                    INTEGER,
                efiPer15mCurDateTime
                    DateAndTime,
                efiPer15mCurParaLen
                    INTEGER,
                efiPer15mCurPara
                    OCTET STRING
             }

        -- 1.3.6.1.4.1.2011.2.25.3.40.50.167.10.1.1
        efiPer15mCurEid OBJECT-TYPE
            SYNTAX PerformanceEventType
            MAX-ACCESS read-only
            STATUS current
            DESCRIPTION
                "perEid."
            ::= { efiPer15mCurEntry 1 }

        -- 1.3.6.1.4.1.2011.2.25.3.40.50.167.10.1.2
        efiPer15mCurMonValue OBJECT-TYPE
            SYNTAX OCTET STRING (SIZE (0..100))
            MAX-ACCESS read-only
            STATUS current
            DESCRIPTION
                "perMonValue."
            ::= { efiPer15mCurEntry 2 }

        -- 1.3.6.1.4.1.2011.2.25.3.40.50.167.10.3
        efiPer15mCurVldty OBJECT-TYPE
            SYNTAX INTEGER
            MAX-ACCESS read-only
            STATUS current
            DESCRIPTION
                "perVldty. "
            ::= { efiPer15mCurEntry 3 }

        -- 1.3.6.1.4.1.2011.2.25.3.40.50.167.10.1.4
        efiPer15mCurDateTime OBJECT-TYPE
            SYNTAX DateAndTime
            MAX-ACCESS read-only
            STATUS current
            DESCRIPTION
                "perDateTime. "
            ::= { efiPer15mCurEntry 4 }

        -- 1.3.6.1.4.1.2011.2.25.3.40.50.167.10.1.5
        efiPer15mCurParaLen OBJECT-TYPE
            SYNTAX INTEGER
            MAX-ACCESS read-only
            STATUS current
            DESCRIPTION
                "perParaLen."
            ::= { efiPer15mCurEntry 5 }

        -- 1.3.6.1.4.1.2011.2.25.3.40.50.167.10.1.6
        efiPer15mCurPara OBJECT-TYPE
            SYNTAX OCTET STRING (SIZE (0..100))
            MAX-ACCESS read-only
            STATUS current
            DESCRIPTION
                "perPara."
            ::= { efiPer15mCurEntry 6 }


-- -------------------------------------------------------------------------
-- Perfomance 15-MIN History Data Table (RTRV-PER-<MOD2>)
-- -------------------------------------------------------------------------
        efiPer15MHisTable OBJECT-TYPE
            SYNTAX SEQUENCE OF EfiPer15MHisEntry
            MAX-ACCESS not-accessible
            STATUS current
            DESCRIPTION
                "efiPer15MHis."
            ::= { efi 20 }


        efiPer15MHisEntry OBJECT-TYPE
            SYNTAX EfiPer15MHisEntry
            MAX-ACCESS not-accessible
            STATUS current
            DESCRIPTION
                "efiPer15MHis."
            INDEX {efiPer15MHisEid, efiPer15MHisParaLen, efiPer15MHisPara, efiPer15MHisDateTimeStart, efiPer15MHisDateTimeEnd}
            ::= { efiPer15MHisTable 1 }

        EfiPer15MHisEntry ::=
            SEQUENCE {
                efiPer15MHisEid
                    PerformanceEventType,
                efiPer15MHisParaLen
                    INTEGER,
                efiPer15MHisPara
                    OCTET STRING,
                efiPer15MHisMonValue
                    OCTET STRING,
                efiPer15MHisDateTimeStart
                    DateAndTime,
                efiPer15MHisDateTimeEnd
                    DateAndTime,
                efiPer15MHisVldty
                    INTEGER,
             }

        efiPer15MHisEid OBJECT-TYPE
            SYNTAX PerformanceEventType
            MAX-ACCESS read-only
            STATUS current
            DESCRIPTION
                "perEid."
            ::= { efiPer15MHisEntry 1 }

        efiPer15MHisParaLen OBJECT-TYPE
            SYNTAX INTEGER
            MAX-ACCESS read-only
            STATUS current
            DESCRIPTION
                "perParaLen."
            ::= { efiPer15MHisEntry 2 }


        efiPer15MHisPara OBJECT-TYPE
            SYNTAX OCTET STRING (SIZE (0..100))
            MAX-ACCESS read-only
            STATUS current
            DESCRIPTION
                "perPara."
            ::= { efiPer15MHisEntry 3 }



        efiPer15MHisMonValue OBJECT-TYPE
            SYNTAX OCTET STRING (SIZE (0..100))
            MAX-ACCESS read-only
            STATUS current
            DESCRIPTION
                "perMonValue."
            ::= { efiPer15MHisEntry 4 }



        efiPer15MHisDateTimeStart OBJECT-TYPE
            SYNTAX DateAndTime
            MAX-ACCESS read-only
            STATUS current
            DESCRIPTION
                "perDateTimeStart. "
            ::= { efiPer15MHisEntry 5 }

        efiPer15MHisDateTimeEnd OBJECT-TYPE
            SYNTAX DateAndTime
            MAX-ACCESS read-only
            STATUS current
            DESCRIPTION
                "perDateTimeEnd. "
            ::= { efiPer15MHisEntry 6 }


        efiPer15MHisVldty OBJECT-TYPE
            SYNTAX INTEGER
            MAX-ACCESS read-only
            STATUS current
            DESCRIPTION
                "perVldty. "
            ::= { efiPer15MHisEntry 7 }


-- -------------------------------------------------------------------------
-- Perfomance 24-HOUR Current Data Table (RTRV-PER-<MOD2>)
-- -------------------------------------------------------------------------
        efiPer24HCurTable OBJECT-TYPE
            SYNTAX SEQUENCE OF EfiPer24HCurEntry
            MAX-ACCESS not-accessible
            STATUS current
            DESCRIPTION
                "efiPer24HCur."
            ::= { efi 30 }


        efiPer24HCurEntry OBJECT-TYPE
            SYNTAX EfiPer24HCurEntry
            MAX-ACCESS not-accessible
            STATUS current
            DESCRIPTION
                "efiPer24HCur."
            INDEX {efiPer24HCurEid, efiPer24HCurPara}
            ::= { efiPer24HCurTable 1 }

        EfiPer24HCurEntry ::=
            SEQUENCE {
                efiPer24HCurEid
                    PerformanceEventType,
                efiPer24HCurMonValue
                    OCTET STRING,
                efiPer24HCurVldty
                    INTEGER,
                efiPer24HCurDateTime
                    DateAndTime,
                efiPer24HCurParaLen
                    INTEGER,
                efiPer24HCurPara
                    OCTET STRING
             }


        efiPer24HCurEid OBJECT-TYPE
            SYNTAX PerformanceEventType
            MAX-ACCESS read-only
            STATUS current
            DESCRIPTION
                "perEid."
            ::= { efiPer24HCurEntry 1 }


        efiPer24HCurMonValue OBJECT-TYPE
            SYNTAX OCTET STRING (SIZE (0..100))
            MAX-ACCESS read-only
            STATUS current
            DESCRIPTION
                "perMonValue."
            ::= { efiPer24HCurEntry 2 }


        efiPer24HCurVldty OBJECT-TYPE
            SYNTAX INTEGER
            MAX-ACCESS read-only
            STATUS current
            DESCRIPTION
                "perVldty. "
            ::= { efiPer24HCurEntry 3 }


        efiPer24HCurDateTime OBJECT-TYPE
            SYNTAX DateAndTime
            MAX-ACCESS read-only
            STATUS current
            DESCRIPTION
                "perDateTime. "
            ::= { efiPer24HCurEntry 4 }


        efiPer24HCurParaLen OBJECT-TYPE
            SYNTAX INTEGER
            MAX-ACCESS read-only
            STATUS current
            DESCRIPTION
                "perParaLen."
            ::= { efiPer24HCurEntry 5 }


        efiPer24HCurPara OBJECT-TYPE
            SYNTAX OCTET STRING (SIZE (0..100))
            MAX-ACCESS read-only
            STATUS current
            DESCRIPTION
                "perPara."
            ::= { efiPer24HCurEntry 6 }


-- -------------------------------------------------------------------------
-- Perfomance 24-HOUR History Data Table (RTRV-PER-<MOD2>)
-- -------------------------------------------------------------------------
        efiPer24HHisTable OBJECT-TYPE
            SYNTAX SEQUENCE OF EfiPer24HHisEntry
            MAX-ACCESS not-accessible
            STATUS current
            DESCRIPTION
                "efiPer24HHis."
            ::= { efi 40 }


        efiPer24HHisEntry OBJECT-TYPE
            SYNTAX EfiPer24HHisEntry
            MAX-ACCESS not-accessible
            STATUS current
            DESCRIPTION
                "efiPer24HHis."
            INDEX {efiPer24HHisEid, efiPer24HHisParaLen, efiPer24HHisPara, efiPer24HHisDateTimeStart, efiPer24HHisDateTimeEnd}
            ::= { efiPer24HHisTable 1 }

        EfiPer24HHisEntry ::=
            SEQUENCE {
                efiPer24HHisEid
                    PerformanceEventType,
              efiPer24HHisParaLen
                    INTEGER,
                efiPer24HHisPara
                    OCTET STRING,
                efiPer24HHisMonValue
                    OCTET STRING,
                efiPer24HHisDateTimeStart
                    DateAndTime,
                efiPer24HHisDateTimeEnd
                    DateAndTime,
                efiPer24HHisVldty
                    INTEGER,
             }

        efiPer24HHisEid OBJECT-TYPE
            SYNTAX PerformanceEventType
            MAX-ACCESS read-only
            STATUS current
            DESCRIPTION
                "perEid."
            ::= { efiPer24HHisEntry 1 }

        efiPer24HHisParaLen OBJECT-TYPE
            SYNTAX INTEGER
            MAX-ACCESS read-only
            STATUS current
            DESCRIPTION
                "perParaLen."
            ::= { efiPer24HHisEntry 2 }


        efiPer24HHisPara OBJECT-TYPE
            SYNTAX OCTET STRING (SIZE (0..100))
            MAX-ACCESS read-only
            STATUS current
            DESCRIPTION
                "perPara."
            ::= { efiPer24HHisEntry 3 }



        efiPer24HHisMonValue OBJECT-TYPE
            SYNTAX OCTET STRING (SIZE (0..100))
            MAX-ACCESS read-only
            STATUS current
            DESCRIPTION
                "perMonValue."
            ::= { efiPer24HHisEntry 4 }



        efiPer24HHisDateTimeStart OBJECT-TYPE
            SYNTAX DateAndTime
            MAX-ACCESS read-only
            STATUS current
            DESCRIPTION
                "perDateTimeStart. "
            ::= { efiPer24HHisEntry 5 }

        efiPer24HHisDateTimeEnd OBJECT-TYPE
            SYNTAX DateAndTime
            MAX-ACCESS read-only
            STATUS current
            DESCRIPTION
                "perDateTimeEnd. "
            ::= { efiPer24HHisEntry 6 }


        efiPer24HHisVldty OBJECT-TYPE
            SYNTAX INTEGER
            MAX-ACCESS read-only
            STATUS current
            DESCRIPTION
                "perVldty. "
            ::= { efiPer24HHisEntry 7 }


--  Alarm data
        -- 1.3.6.1.4.1.2011.2.25.3.40.50.57
        sysclock OBJECT IDENTIFIER ::= { optixGlobalNGWDM 57 }

-- -------------------------------------------------------------------------
-- Perfomance 15-MIN Current Data Table (RTRV-PER-<MOD2>)
-- -------------------------------------------------------------------------
        -- 1.3.6.1.4.1.2011.2.25.3.40.50.57.10
        sysclockPer15mCurTable OBJECT-TYPE
            SYNTAX SEQUENCE OF SysclockPer15mCurEntry
            MAX-ACCESS not-accessible
            STATUS current
            DESCRIPTION
                "sysclockPer15mCur."
            ::= { sysclock 10 }

        -- 1.3.6.1.4.1.2011.2.25.3.40.50.57.10.1
        sysclockPer15mCurEntry OBJECT-TYPE
            SYNTAX SysclockPer15mCurEntry
            MAX-ACCESS not-accessible
            STATUS current
            DESCRIPTION
                "sysclockPer15mCur."
            INDEX {sysclockPer15mCurEid, sysclockPer15mCurPara}
            ::= { sysclockPer15mCurTable 1 }

        SysclockPer15mCurEntry ::=
            SEQUENCE {
                sysclockPer15mCurEid
                    PerformanceEventType,
                sysclockPer15mCurMonValue
                    OCTET STRING,
                sysclockPer15mCurVldty
                    INTEGER,
                sysclockPer15mCurDateTime
                    DateAndTime,
                sysclockPer15mCurParaLen
                    INTEGER,
                sysclockPer15mCurPara
                    OCTET STRING
             }

        -- 1.3.6.1.4.1.2011.2.25.3.40.50.57.10.1.1
        sysclockPer15mCurEid OBJECT-TYPE
            SYNTAX PerformanceEventType
            MAX-ACCESS read-only
            STATUS current
            DESCRIPTION
                "perEid."
            ::= { sysclockPer15mCurEntry 1 }

        -- 1.3.6.1.4.1.2011.2.25.3.40.50.57.10.1.2
        sysclockPer15mCurMonValue OBJECT-TYPE
            SYNTAX OCTET STRING (SIZE (0..100))
            MAX-ACCESS read-only
            STATUS current
            DESCRIPTION
                "perMonValue."
            ::= { sysclockPer15mCurEntry 2 }

        -- 1.3.6.1.4.1.2011.2.25.3.40.50.57.10.3
        sysclockPer15mCurVldty OBJECT-TYPE
            SYNTAX INTEGER
            MAX-ACCESS read-only
            STATUS current
            DESCRIPTION
                "perVldty. "
            ::= { sysclockPer15mCurEntry 3 }

        -- 1.3.6.1.4.1.2011.2.25.3.40.50.57.10.1.4
        sysclockPer15mCurDateTime OBJECT-TYPE
            SYNTAX DateAndTime
            MAX-ACCESS read-only
            STATUS current
            DESCRIPTION
                "perDateTime. "
            ::= { sysclockPer15mCurEntry 4 }

        -- 1.3.6.1.4.1.2011.2.25.3.40.50.57.10.1.5
        sysclockPer15mCurParaLen OBJECT-TYPE
            SYNTAX INTEGER
            MAX-ACCESS read-only
            STATUS current
            DESCRIPTION
                "perParaLen."
            ::= { sysclockPer15mCurEntry 5 }

        -- 1.3.6.1.4.1.2011.2.25.3.40.50.57.10.1.6
        sysclockPer15mCurPara OBJECT-TYPE
            SYNTAX OCTET STRING (SIZE (0..100))
            MAX-ACCESS read-only
            STATUS current
            DESCRIPTION
                "perPara."
            ::= { sysclockPer15mCurEntry 6 }


-- -------------------------------------------------------------------------
-- Perfomance 15-MIN History Data Table (RTRV-PER-<MOD2>)
-- -------------------------------------------------------------------------
        sysclockPer15MHisTable OBJECT-TYPE
            SYNTAX SEQUENCE OF SysclockPer15MHisEntry
            MAX-ACCESS not-accessible
            STATUS current
            DESCRIPTION
                "sysclockPer15MHis."
            ::= { sysclock 20 }


        sysclockPer15MHisEntry OBJECT-TYPE
            SYNTAX SysclockPer15MHisEntry
            MAX-ACCESS not-accessible
            STATUS current
            DESCRIPTION
                "sysclockPer15MHis."
            INDEX {sysclockPer15MHisEid, sysclockPer15MHisParaLen, sysclockPer15MHisPara, sysclockPer15MHisDateTimeStart, sysclockPer15MHisDateTimeEnd}
            ::= { sysclockPer15MHisTable 1 }

        SysclockPer15MHisEntry ::=
            SEQUENCE {
                sysclockPer15MHisEid
                    PerformanceEventType,
                sysclockPer15MHisParaLen
                    INTEGER,
                sysclockPer15MHisPara
                    OCTET STRING,
                sysclockPer15MHisMonValue
                    OCTET STRING,
                sysclockPer15MHisDateTimeStart
                    DateAndTime,
                sysclockPer15MHisDateTimeEnd
                    DateAndTime,
                sysclockPer15MHisVldty
                    INTEGER,
             }

        sysclockPer15MHisEid OBJECT-TYPE
            SYNTAX PerformanceEventType
            MAX-ACCESS read-only
            STATUS current
            DESCRIPTION
                "perEid."
            ::= { sysclockPer15MHisEntry 1 }

        sysclockPer15MHisParaLen OBJECT-TYPE
            SYNTAX INTEGER
            MAX-ACCESS read-only
            STATUS current
            DESCRIPTION
                "perParaLen."
            ::= { sysclockPer15MHisEntry 2 }


        sysclockPer15MHisPara OBJECT-TYPE
            SYNTAX OCTET STRING (SIZE (0..100))
            MAX-ACCESS read-only
            STATUS current
            DESCRIPTION
                "perPara."
            ::= { sysclockPer15MHisEntry 3 }



        sysclockPer15MHisMonValue OBJECT-TYPE
            SYNTAX OCTET STRING (SIZE (0..100))
            MAX-ACCESS read-only
            STATUS current
            DESCRIPTION
                "perMonValue."
            ::= { sysclockPer15MHisEntry 4 }



        sysclockPer15MHisDateTimeStart OBJECT-TYPE
            SYNTAX DateAndTime
            MAX-ACCESS read-only
            STATUS current
            DESCRIPTION
                "perDateTimeStart. "
            ::= { sysclockPer15MHisEntry 5 }

        sysclockPer15MHisDateTimeEnd OBJECT-TYPE
            SYNTAX DateAndTime
            MAX-ACCESS read-only
            STATUS current
            DESCRIPTION
                "perDateTimeEnd. "
            ::= { sysclockPer15MHisEntry 6 }


        sysclockPer15MHisVldty OBJECT-TYPE
            SYNTAX INTEGER
            MAX-ACCESS read-only
            STATUS current
            DESCRIPTION
                "perVldty. "
            ::= { sysclockPer15MHisEntry 7 }


-- -------------------------------------------------------------------------
-- Perfomance 24-HOUR Current Data Table (RTRV-PER-<MOD2>)
-- -------------------------------------------------------------------------
        sysclockPer24HCurTable OBJECT-TYPE
            SYNTAX SEQUENCE OF SysclockPer24HCurEntry
            MAX-ACCESS not-accessible
            STATUS current
            DESCRIPTION
                "sysclockPer24HCur."
            ::= { sysclock 30 }


        sysclockPer24HCurEntry OBJECT-TYPE
            SYNTAX SysclockPer24HCurEntry
            MAX-ACCESS not-accessible
            STATUS current
            DESCRIPTION
                "sysclockPer24HCur."
            INDEX {sysclockPer24HCurEid, sysclockPer24HCurPara}
            ::= { sysclockPer24HCurTable 1 }

        SysclockPer24HCurEntry ::=
            SEQUENCE {
                sysclockPer24HCurEid
                    PerformanceEventType,
                sysclockPer24HCurMonValue
                    OCTET STRING,
                sysclockPer24HCurVldty
                    INTEGER,
                sysclockPer24HCurDateTime
                    DateAndTime,
                sysclockPer24HCurParaLen
                    INTEGER,
                sysclockPer24HCurPara
                    OCTET STRING
             }


        sysclockPer24HCurEid OBJECT-TYPE
            SYNTAX PerformanceEventType
            MAX-ACCESS read-only
            STATUS current
            DESCRIPTION
                "perEid."
            ::= { sysclockPer24HCurEntry 1 }


        sysclockPer24HCurMonValue OBJECT-TYPE
            SYNTAX OCTET STRING (SIZE (0..100))
            MAX-ACCESS read-only
            STATUS current
            DESCRIPTION
                "perMonValue."
            ::= { sysclockPer24HCurEntry 2 }


        sysclockPer24HCurVldty OBJECT-TYPE
            SYNTAX INTEGER
            MAX-ACCESS read-only
            STATUS current
            DESCRIPTION
                "perVldty. "
            ::= { sysclockPer24HCurEntry 3 }


        sysclockPer24HCurDateTime OBJECT-TYPE
            SYNTAX DateAndTime
            MAX-ACCESS read-only
            STATUS current
            DESCRIPTION
                "perDateTime. "
            ::= { sysclockPer24HCurEntry 4 }


        sysclockPer24HCurParaLen OBJECT-TYPE
            SYNTAX INTEGER
            MAX-ACCESS read-only
            STATUS current
            DESCRIPTION
                "perParaLen."
            ::= { sysclockPer24HCurEntry 5 }


        sysclockPer24HCurPara OBJECT-TYPE
            SYNTAX OCTET STRING (SIZE (0..100))
            MAX-ACCESS read-only
            STATUS current
            DESCRIPTION
                "perPara."
            ::= { sysclockPer24HCurEntry 6 }


-- -------------------------------------------------------------------------
-- Perfomance 24-HOUR History Data Table (RTRV-PER-<MOD2>)
-- -------------------------------------------------------------------------
        sysclockPer24HHisTable OBJECT-TYPE
            SYNTAX SEQUENCE OF SysclockPer24HHisEntry
            MAX-ACCESS not-accessible
            STATUS current
            DESCRIPTION
                "sysclockPer24HHis."
            ::= { sysclock 40 }


        sysclockPer24HHisEntry OBJECT-TYPE
            SYNTAX SysclockPer24HHisEntry
            MAX-ACCESS not-accessible
            STATUS current
            DESCRIPTION
                "sysclockPer24HHis."
            INDEX {sysclockPer24HHisEid, sysclockPer24HHisParaLen, sysclockPer24HHisPara, sysclockPer24HHisDateTimeStart, sysclockPer24HHisDateTimeEnd}
            ::= { sysclockPer24HHisTable 1 }

        SysclockPer24HHisEntry ::=
            SEQUENCE {
                sysclockPer24HHisEid
                    PerformanceEventType,
                sysclockPer24HHisParaLen
                    INTEGER,
                sysclockPer24HHisPara
                    OCTET STRING,
                sysclockPer24HHisMonValue
                    OCTET STRING,
                sysclockPer24HHisDateTimeStart
                    DateAndTime,
                sysclockPer24HHisDateTimeEnd
                    DateAndTime,
                sysclockPer24HHisVldty
                    INTEGER,
             }

        sysclockPer24HHisEid OBJECT-TYPE
            SYNTAX PerformanceEventType
            MAX-ACCESS read-only
            STATUS current
            DESCRIPTION
                "perEid."
            ::= { sysclockPer24HHisEntry 1 }

        sysclockPer24HHisParaLen OBJECT-TYPE
            SYNTAX INTEGER
            MAX-ACCESS read-only
            STATUS current
            DESCRIPTION
                "perParaLen."
            ::= { sysclockPer24HHisEntry 2 }


        sysclockPer24HHisPara OBJECT-TYPE
            SYNTAX OCTET STRING (SIZE (0..100))
            MAX-ACCESS read-only
            STATUS current
            DESCRIPTION
                "perPara."
            ::= { sysclockPer24HHisEntry 3 }



        sysclockPer24HHisMonValue OBJECT-TYPE
            SYNTAX OCTET STRING (SIZE (0..100))
            MAX-ACCESS read-only
            STATUS current
            DESCRIPTION
                "perMonValue."
            ::= { sysclockPer24HHisEntry 4 }



        sysclockPer24HHisDateTimeStart OBJECT-TYPE
            SYNTAX DateAndTime
            MAX-ACCESS read-only
            STATUS current
            DESCRIPTION
                "perDateTimeStart. "
            ::= { sysclockPer24HHisEntry 5 }

        sysclockPer24HHisDateTimeEnd OBJECT-TYPE
            SYNTAX DateAndTime
            MAX-ACCESS read-only
            STATUS current
            DESCRIPTION
                "perDateTimeEnd. "
            ::= { sysclockPer24HHisEntry 6 }


        sysclockPer24HHisVldty OBJECT-TYPE
            SYNTAX INTEGER
            MAX-ACCESS read-only
            STATUS current
            DESCRIPTION
                "perVldty. "
            ::= { sysclockPer24HHisEntry 7 }

--  Alarm data
        -- 1.3.6.1.4.1.2011.2.25.3.40.50.84
        new_laser OBJECT IDENTIFIER ::= { optixGlobalNGWDM 84 }

-- -------------------------------------------------------------------------
-- Perfomance 15-MIN Current Data Table (RTRV-PER-<MOD2>)
-- -------------------------------------------------------------------------
        -- 1.3.6.1.4.1.2011.2.25.3.40.50.84.10
        new_laserPer15mCurTable OBJECT-TYPE
            SYNTAX SEQUENCE OF New_laserPer15mCurEntry
            MAX-ACCESS not-accessible
            STATUS current
            DESCRIPTION
                "new_laserPer15mCur."
            ::= { new_laser 10 }

        -- 1.3.6.1.4.1.2011.2.25.3.40.50.84.10.1
        new_laserPer15mCurEntry OBJECT-TYPE
            SYNTAX New_laserPer15mCurEntry
            MAX-ACCESS not-accessible
            STATUS current
            DESCRIPTION
                "new_laserPer15mCur."
            INDEX {new_laserPer15mCurEid, new_laserPer15mCurPara}
            ::= { new_laserPer15mCurTable 1 }

        New_laserPer15mCurEntry ::=
            SEQUENCE {
                new_laserPer15mCurEid
                    PerformanceEventType,
                new_laserPer15mCurMonValue
                    OCTET STRING,
                new_laserPer15mCurVldty
                    INTEGER,
                new_laserPer15mCurDateTime
                    DateAndTime,
                new_laserPer15mCurParaLen
                    INTEGER,
                new_laserPer15mCurPara
                    OCTET STRING
             }

        -- 1.3.6.1.4.1.2011.2.25.3.40.50.84.10.1.1
        new_laserPer15mCurEid OBJECT-TYPE
            SYNTAX PerformanceEventType
            MAX-ACCESS read-only
            STATUS current
            DESCRIPTION
                "perEid."
            ::= { new_laserPer15mCurEntry 1 }

        -- 1.3.6.1.4.1.2011.2.25.3.40.50.84.10.1.2
        new_laserPer15mCurMonValue OBJECT-TYPE
            SYNTAX OCTET STRING (SIZE (0..100))
            MAX-ACCESS read-only
            STATUS current
            DESCRIPTION
                "perMonValue."
            ::= { new_laserPer15mCurEntry 2 }

        -- 1.3.6.1.4.1.2011.2.25.3.40.50.84.10.3
        new_laserPer15mCurVldty OBJECT-TYPE
            SYNTAX INTEGER
            MAX-ACCESS read-only
            STATUS current
            DESCRIPTION
                "perVldty. "
            ::= { new_laserPer15mCurEntry 3 }

        -- 1.3.6.1.4.1.2011.2.25.3.40.50.84.10.1.4
        new_laserPer15mCurDateTime OBJECT-TYPE
            SYNTAX DateAndTime
            MAX-ACCESS read-only
            STATUS current
            DESCRIPTION
                "perDateTime. "
            ::= { new_laserPer15mCurEntry 4 }

        -- 1.3.6.1.4.1.2011.2.25.3.40.50.84.10.1.5
        new_laserPer15mCurParaLen OBJECT-TYPE
            SYNTAX INTEGER
            MAX-ACCESS read-only
            STATUS current
            DESCRIPTION
                "perParaLen."
            ::= { new_laserPer15mCurEntry 5 }

        -- 1.3.6.1.4.1.2011.2.25.3.40.50.84.10.1.6
        new_laserPer15mCurPara OBJECT-TYPE
            SYNTAX OCTET STRING (SIZE (0..100))
            MAX-ACCESS read-only
            STATUS current
            DESCRIPTION
                "perPara."
            ::= { new_laserPer15mCurEntry 6 }


-- -------------------------------------------------------------------------
-- Perfomance 15-MIN History Data Table (RTRV-PER-<MOD2>)
-- -------------------------------------------------------------------------
        new_laserPer15MHisTable OBJECT-TYPE
            SYNTAX SEQUENCE OF New_laserPer15MHisEntry
            MAX-ACCESS not-accessible
            STATUS current
            DESCRIPTION
                "new_laserPer15MHis."
            ::= { new_laser 20 }


        new_laserPer15MHisEntry OBJECT-TYPE
            SYNTAX New_laserPer15MHisEntry
            MAX-ACCESS not-accessible
            STATUS current
            DESCRIPTION
                "new_laserPer15MHis."
            INDEX {new_laserPer15MHisEid, new_laserPer15MHisParaLen, new_laserPer15MHisPara, new_laserPer15MHisDateTimeStart, new_laserPer15MHisDateTimeEnd}
            ::= { new_laserPer15MHisTable 1 }

        New_laserPer15MHisEntry ::=
            SEQUENCE {
                new_laserPer15MHisEid
                    PerformanceEventType,
                new_laserPer15MHisParaLen
                    INTEGER,
                new_laserPer15MHisPara
                    OCTET STRING,
                new_laserPer15MHisMonValue
                    OCTET STRING,
                new_laserPer15MHisDateTimeStart
                    DateAndTime,
                new_laserPer15MHisDateTimeEnd
                    DateAndTime,
                new_laserPer15MHisVldty
                    INTEGER,
             }

        new_laserPer15MHisEid OBJECT-TYPE
            SYNTAX PerformanceEventType
            MAX-ACCESS read-only
            STATUS current
            DESCRIPTION
                "perEid."
            ::= { new_laserPer15MHisEntry 1 }

        new_laserPer15MHisParaLen OBJECT-TYPE
            SYNTAX INTEGER
            MAX-ACCESS read-only
            STATUS current
            DESCRIPTION
                "perParaLen."
            ::= { new_laserPer15MHisEntry 2 }


        new_laserPer15MHisPara OBJECT-TYPE
            SYNTAX OCTET STRING (SIZE (0..100))
            MAX-ACCESS read-only
            STATUS current
            DESCRIPTION
                "perPara."
            ::= { new_laserPer15MHisEntry 3 }



        new_laserPer15MHisMonValue OBJECT-TYPE
            SYNTAX OCTET STRING (SIZE (0..100))
            MAX-ACCESS read-only
            STATUS current
            DESCRIPTION
                "perMonValue."
            ::= { new_laserPer15MHisEntry 4 }



        new_laserPer15MHisDateTimeStart OBJECT-TYPE
            SYNTAX DateAndTime
            MAX-ACCESS read-only
            STATUS current
            DESCRIPTION
                "perDateTimeStart. "
            ::= { new_laserPer15MHisEntry 5 }

        new_laserPer15MHisDateTimeEnd OBJECT-TYPE
            SYNTAX DateAndTime
            MAX-ACCESS read-only
            STATUS current
            DESCRIPTION
                "perDateTimeEnd. "
            ::= { new_laserPer15MHisEntry 6 }


        new_laserPer15MHisVldty OBJECT-TYPE
            SYNTAX INTEGER
            MAX-ACCESS read-only
            STATUS current
            DESCRIPTION
                "perVldty. "
            ::= { new_laserPer15MHisEntry 7 }


-- -------------------------------------------------------------------------
-- Perfomance 24-HOUR Current Data Table (RTRV-PER-<MOD2>)
-- -------------------------------------------------------------------------
        new_laserPer24HCurTable OBJECT-TYPE
            SYNTAX SEQUENCE OF New_laserPer24HCurEntry
            MAX-ACCESS not-accessible
            STATUS current
            DESCRIPTION
                "new_laserPer24HCur."
            ::= { new_laser 30 }


        new_laserPer24HCurEntry OBJECT-TYPE
            SYNTAX New_laserPer24HCurEntry
            MAX-ACCESS not-accessible
            STATUS current
            DESCRIPTION
                "new_laserPer24HCur."
            INDEX {new_laserPer24HCurEid, new_laserPer24HCurPara}
            ::= { new_laserPer24HCurTable 1 }

        New_laserPer24HCurEntry ::=
            SEQUENCE {
                new_laserPer24HCurEid
                    PerformanceEventType,
                new_laserPer24HCurMonValue
                    OCTET STRING,
                new_laserPer24HCurVldty
                    INTEGER,
                new_laserPer24HCurDateTime
                    DateAndTime,
                new_laserPer24HCurParaLen
                    INTEGER,
                new_laserPer24HCurPara
                    OCTET STRING
             }


        new_laserPer24HCurEid OBJECT-TYPE
            SYNTAX PerformanceEventType
            MAX-ACCESS read-only
            STATUS current
            DESCRIPTION
                "perEid."
            ::= { new_laserPer24HCurEntry 1 }


        new_laserPer24HCurMonValue OBJECT-TYPE
            SYNTAX OCTET STRING (SIZE (0..100))
            MAX-ACCESS read-only
            STATUS current
            DESCRIPTION
                "perMonValue."
            ::= { new_laserPer24HCurEntry 2 }


        new_laserPer24HCurVldty OBJECT-TYPE
            SYNTAX INTEGER
            MAX-ACCESS read-only
            STATUS current
            DESCRIPTION
                "perVldty. "
            ::= { new_laserPer24HCurEntry 3 }


        new_laserPer24HCurDateTime OBJECT-TYPE
            SYNTAX DateAndTime
            MAX-ACCESS read-only
            STATUS current
            DESCRIPTION
                "perDateTime. "
            ::= { new_laserPer24HCurEntry 4 }


        new_laserPer24HCurParaLen OBJECT-TYPE
            SYNTAX INTEGER
            MAX-ACCESS read-only
            STATUS current
            DESCRIPTION
                "perParaLen."
            ::= { new_laserPer24HCurEntry 5 }


        new_laserPer24HCurPara OBJECT-TYPE
            SYNTAX OCTET STRING (SIZE (0..100))
            MAX-ACCESS read-only
            STATUS current
            DESCRIPTION
                "perPara."
            ::= { new_laserPer24HCurEntry 6 }


-- -------------------------------------------------------------------------
-- Perfomance 24-HOUR History Data Table (RTRV-PER-<MOD2>)
-- -------------------------------------------------------------------------
        new_laserPer24HHisTable OBJECT-TYPE
            SYNTAX SEQUENCE OF New_laserPer24HHisEntry
            MAX-ACCESS not-accessible
            STATUS current
            DESCRIPTION
                "new_laserPer24HHis."
            ::= { new_laser 40 }


        new_laserPer24HHisEntry OBJECT-TYPE
            SYNTAX New_laserPer24HHisEntry
            MAX-ACCESS not-accessible
            STATUS current
            DESCRIPTION
                "new_laserPer24HHis."
            INDEX {new_laserPer24HHisEid, new_laserPer24HHisParaLen, new_laserPer24HHisPara, new_laserPer24HHisDateTimeStart, new_laserPer24HHisDateTimeEnd}
            ::= { new_laserPer24HHisTable 1 }

        New_laserPer24HHisEntry ::=
            SEQUENCE {
                new_laserPer24HHisEid
                    PerformanceEventType,
                new_laserPer24HHisParaLen
                    INTEGER,
                new_laserPer24HHisPara
                    OCTET STRING,
                new_laserPer24HHisMonValue
                    OCTET STRING,
                new_laserPer24HHisDateTimeStart
                    DateAndTime,
                new_laserPer24HHisDateTimeEnd
                    DateAndTime,
                new_laserPer24HHisVldty
                    INTEGER,
             }

        new_laserPer24HHisEid OBJECT-TYPE
            SYNTAX PerformanceEventType
            MAX-ACCESS read-only
            STATUS current
            DESCRIPTION
                "perEid."
            ::= { new_laserPer24HHisEntry 1 }

        new_laserPer24HHisParaLen OBJECT-TYPE
            SYNTAX INTEGER
            MAX-ACCESS read-only
            STATUS current
            DESCRIPTION
                "perParaLen."
            ::= { new_laserPer24HHisEntry 2 }


        new_laserPer24HHisPara OBJECT-TYPE
            SYNTAX OCTET STRING (SIZE (0..100))
            MAX-ACCESS read-only
            STATUS current
            DESCRIPTION
                "perPara."
            ::= { new_laserPer24HHisEntry 3 }



        new_laserPer24HHisMonValue OBJECT-TYPE
            SYNTAX OCTET STRING (SIZE (0..100))
            MAX-ACCESS read-only
            STATUS current
            DESCRIPTION
                "perMonValue."
            ::= { new_laserPer24HHisEntry 4 }



        new_laserPer24HHisDateTimeStart OBJECT-TYPE
            SYNTAX DateAndTime
            MAX-ACCESS read-only
            STATUS current
            DESCRIPTION
                "perDateTimeStart. "
            ::= { new_laserPer24HHisEntry 5 }

        new_laserPer24HHisDateTimeEnd OBJECT-TYPE
            SYNTAX DateAndTime
            MAX-ACCESS read-only
            STATUS current
            DESCRIPTION
                "perDateTimeEnd. "
            ::= { new_laserPer24HHisEntry 6 }


        new_laserPer24HHisVldty OBJECT-TYPE
            SYNTAX INTEGER
            MAX-ACCESS read-only
            STATUS current
            DESCRIPTION
                "perVldty. "
            ::= { new_laserPer24HHisEntry 7 }

--  Alarm data
        -- 1.3.6.1.4.1.2011.2.25.3.40.50.189
        otu4_path OBJECT IDENTIFIER ::= { optixGlobalNGWDM 189 }

-- -------------------------------------------------------------------------
-- Perfomance 15-MIN Current Data Table (RTRV-PER-<MOD2>)
-- -------------------------------------------------------------------------
        -- 1.3.6.1.4.1.2011.2.25.3.40.50.189.10
        otu4_pathPer15mCurTable OBJECT-TYPE
            SYNTAX SEQUENCE OF Otu4_pathPer15mCurEntry
            MAX-ACCESS not-accessible
            STATUS current
            DESCRIPTION
                "otu4_pathPer15mCur."
            ::= { otu4_path 10 }

        -- 1.3.6.1.4.1.2011.2.25.3.40.50.189.10.1
        otu4_pathPer15mCurEntry OBJECT-TYPE
            SYNTAX Otu4_pathPer15mCurEntry
            MAX-ACCESS not-accessible
            STATUS current
            DESCRIPTION
                "otu4_pathPer15mCur."
            INDEX {otu4_pathPer15mCurEid, otu4_pathPer15mCurPara}
            ::= { otu4_pathPer15mCurTable 1 }

        Otu4_pathPer15mCurEntry ::=
            SEQUENCE {
                otu4_pathPer15mCurEid
                    PerformanceEventType,
                otu4_pathPer15mCurMonValue
                    OCTET STRING,
                otu4_pathPer15mCurVldty
                    INTEGER,
                otu4_pathPer15mCurDateTime
                    DateAndTime,
                otu4_pathPer15mCurParaLen
                    INTEGER,
                otu4_pathPer15mCurPara
                    OCTET STRING
             }

        -- 1.3.6.1.4.1.2011.2.25.3.40.50.189.10.1.1
        otu4_pathPer15mCurEid OBJECT-TYPE
            SYNTAX PerformanceEventType
            MAX-ACCESS read-only
            STATUS current
            DESCRIPTION
                "perEid."
            ::= { otu4_pathPer15mCurEntry 1 }

        -- 1.3.6.1.4.1.2011.2.25.3.40.50.189.10.1.2
        otu4_pathPer15mCurMonValue OBJECT-TYPE
            SYNTAX OCTET STRING (SIZE (0..100))
            MAX-ACCESS read-only
            STATUS current
            DESCRIPTION
                "perMonValue."
            ::= { otu4_pathPer15mCurEntry 2 }

        -- 1.3.6.1.4.1.2011.2.25.3.40.50.189.10.3
        otu4_pathPer15mCurVldty OBJECT-TYPE
            SYNTAX INTEGER
            MAX-ACCESS read-only
            STATUS current
            DESCRIPTION
                "perVldty. "
            ::= { otu4_pathPer15mCurEntry 3 }

        -- 1.3.6.1.4.1.2011.2.25.3.40.50.189.10.1.4
        otu4_pathPer15mCurDateTime OBJECT-TYPE
            SYNTAX DateAndTime
            MAX-ACCESS read-only
            STATUS current
            DESCRIPTION
                "perDateTime. "
            ::= { otu4_pathPer15mCurEntry 4 }

        -- 1.3.6.1.4.1.2011.2.25.3.40.50.189.10.1.5
        otu4_pathPer15mCurParaLen OBJECT-TYPE
            SYNTAX INTEGER
            MAX-ACCESS read-only
            STATUS current
            DESCRIPTION
                "perParaLen."
            ::= { otu4_pathPer15mCurEntry 5 }

        -- 1.3.6.1.4.1.2011.2.25.3.40.50.189.10.1.6
        otu4_pathPer15mCurPara OBJECT-TYPE
            SYNTAX OCTET STRING (SIZE (0..100))
            MAX-ACCESS read-only
            STATUS current
            DESCRIPTION
                "perPara."
            ::= { otu4_pathPer15mCurEntry 6 }


-- -------------------------------------------------------------------------
-- Perfomance 15-MIN History Data Table (RTRV-PER-<MOD2>)
-- -------------------------------------------------------------------------
        otu4_pathPer15MHisTable OBJECT-TYPE
            SYNTAX SEQUENCE OF Otu4_pathPer15MHisEntry
            MAX-ACCESS not-accessible
            STATUS current
            DESCRIPTION
                "otu4_pathPer15MHis."
            ::= { otu4_path 20 }


        otu4_pathPer15MHisEntry OBJECT-TYPE
            SYNTAX Otu4_pathPer15MHisEntry
            MAX-ACCESS not-accessible
            STATUS current
            DESCRIPTION
                "otu4_pathPer15MHis."
            INDEX {otu4_pathPer15MHisEid, otu4_pathPer15MHisParaLen, otu4_pathPer15MHisPara, otu4_pathPer15MHisDateTimeStart, otu4_pathPer15MHisDateTimeEnd}
            ::= { otu4_pathPer15MHisTable 1 }

        Otu4_pathPer15MHisEntry ::=
            SEQUENCE {
                otu4_pathPer15MHisEid
                    PerformanceEventType,
                otu4_pathPer15MHisParaLen
                    INTEGER,
                otu4_pathPer15MHisPara
                    OCTET STRING,
                otu4_pathPer15MHisMonValue
                    OCTET STRING,
                otu4_pathPer15MHisDateTimeStart
                    DateAndTime,
                otu4_pathPer15MHisDateTimeEnd
                    DateAndTime,
                otu4_pathPer15MHisVldty
                    INTEGER,
             }

        otu4_pathPer15MHisEid OBJECT-TYPE
            SYNTAX PerformanceEventType
            MAX-ACCESS read-only
            STATUS current
            DESCRIPTION
                "perEid."
            ::= { otu4_pathPer15MHisEntry 1 }

        otu4_pathPer15MHisParaLen OBJECT-TYPE
            SYNTAX INTEGER
            MAX-ACCESS read-only
            STATUS current
            DESCRIPTION
                "perParaLen."
            ::= { otu4_pathPer15MHisEntry 2 }


        otu4_pathPer15MHisPara OBJECT-TYPE
            SYNTAX OCTET STRING (SIZE (0..100))
            MAX-ACCESS read-only
            STATUS current
            DESCRIPTION
                "perPara."
            ::= { otu4_pathPer15MHisEntry 3 }



        otu4_pathPer15MHisMonValue OBJECT-TYPE
            SYNTAX OCTET STRING (SIZE (0..100))
            MAX-ACCESS read-only
            STATUS current
            DESCRIPTION
                "perMonValue."
            ::= { otu4_pathPer15MHisEntry 4 }



        otu4_pathPer15MHisDateTimeStart OBJECT-TYPE
            SYNTAX DateAndTime
            MAX-ACCESS read-only
            STATUS current
            DESCRIPTION
                "perDateTimeStart. "
            ::= { otu4_pathPer15MHisEntry 5 }

        otu4_pathPer15MHisDateTimeEnd OBJECT-TYPE
            SYNTAX DateAndTime
            MAX-ACCESS read-only
            STATUS current
            DESCRIPTION
                "perDateTimeEnd. "
            ::= { otu4_pathPer15MHisEntry 6 }


        otu4_pathPer15MHisVldty OBJECT-TYPE
            SYNTAX INTEGER
            MAX-ACCESS read-only
            STATUS current
            DESCRIPTION
                "perVldty. "
            ::= { otu4_pathPer15MHisEntry 7 }


-- -------------------------------------------------------------------------
-- Perfomance 24-HOUR Current Data Table (RTRV-PER-<MOD2>)
-- -------------------------------------------------------------------------
        otu4_pathPer24HCurTable OBJECT-TYPE
            SYNTAX SEQUENCE OF Otu4_pathPer24HCurEntry
            MAX-ACCESS not-accessible
            STATUS current
            DESCRIPTION
                "otu4_pathPer24HCur."
            ::= { otu4_path 30 }


        otu4_pathPer24HCurEntry OBJECT-TYPE
            SYNTAX Otu4_pathPer24HCurEntry
            MAX-ACCESS not-accessible
            STATUS current
            DESCRIPTION
                "otu4_pathPer24HCur."
            INDEX {otu4_pathPer24HCurEid, otu4_pathPer24HCurPara}
            ::= { otu4_pathPer24HCurTable 1 }

        Otu4_pathPer24HCurEntry ::=
            SEQUENCE {
                otu4_pathPer24HCurEid
                    PerformanceEventType,
                otu4_pathPer24HCurMonValue
                    OCTET STRING,
                otu4_pathPer24HCurVldty
                    INTEGER,
                otu4_pathPer24HCurDateTime
                    DateAndTime,
                otu4_pathPer24HCurParaLen
                    INTEGER,
                otu4_pathPer24HCurPara
                    OCTET STRING
             }


        otu4_pathPer24HCurEid OBJECT-TYPE
            SYNTAX PerformanceEventType
            MAX-ACCESS read-only
            STATUS current
            DESCRIPTION
                "perEid."
            ::= { otu4_pathPer24HCurEntry 1 }


        otu4_pathPer24HCurMonValue OBJECT-TYPE
            SYNTAX OCTET STRING (SIZE (0..100))
            MAX-ACCESS read-only
            STATUS current
            DESCRIPTION
                "perMonValue."
            ::= { otu4_pathPer24HCurEntry 2 }


        otu4_pathPer24HCurVldty OBJECT-TYPE
            SYNTAX INTEGER
            MAX-ACCESS read-only
            STATUS current
            DESCRIPTION
                "perVldty. "
            ::= { otu4_pathPer24HCurEntry 3 }


        otu4_pathPer24HCurDateTime OBJECT-TYPE
            SYNTAX DateAndTime
            MAX-ACCESS read-only
            STATUS current
            DESCRIPTION
                "perDateTime. "
            ::= { otu4_pathPer24HCurEntry 4 }


        otu4_pathPer24HCurParaLen OBJECT-TYPE
            SYNTAX INTEGER
            MAX-ACCESS read-only
            STATUS current
            DESCRIPTION
                "perParaLen."
            ::= { otu4_pathPer24HCurEntry 5 }


        otu4_pathPer24HCurPara OBJECT-TYPE
            SYNTAX OCTET STRING (SIZE (0..100))
            MAX-ACCESS read-only
            STATUS current
            DESCRIPTION
                "perPara."
            ::= { otu4_pathPer24HCurEntry 6 }


-- -------------------------------------------------------------------------
-- Perfomance 24-HOUR History Data Table (RTRV-PER-<MOD2>)
-- -------------------------------------------------------------------------
        otu4_pathPer24HHisTable OBJECT-TYPE
            SYNTAX SEQUENCE OF Otu4_pathPer24HHisEntry
            MAX-ACCESS not-accessible
            STATUS current
            DESCRIPTION
                "otu4_pathPer24HHis."
            ::= { otu4_path 40 }


        otu4_pathPer24HHisEntry OBJECT-TYPE
            SYNTAX Otu4_pathPer24HHisEntry
            MAX-ACCESS not-accessible
            STATUS current
            DESCRIPTION
                "otu4_pathPer24HHis."
            INDEX {otu4_pathPer24HHisEid, otu4_pathPer24HHisParaLen, otu4_pathPer24HHisPara, otu4_pathPer24HHisDateTimeStart, otu4_pathPer24HHisDateTimeEnd}
            ::= { otu4_pathPer24HHisTable 1 }

        Otu4_pathPer24HHisEntry ::=
            SEQUENCE {
                otu4_pathPer24HHisEid
                    PerformanceEventType,
                otu4_pathPer24HHisParaLen
                    INTEGER,
                otu4_pathPer24HHisPara
                    OCTET STRING,
                otu4_pathPer24HHisMonValue
                    OCTET STRING,
                otu4_pathPer24HHisDateTimeStart
                    DateAndTime,
                otu4_pathPer24HHisDateTimeEnd
                    DateAndTime,
                otu4_pathPer24HHisVldty
                    INTEGER,
             }

        otu4_pathPer24HHisEid OBJECT-TYPE
            SYNTAX PerformanceEventType
            MAX-ACCESS read-only
            STATUS current
            DESCRIPTION
                "perEid."
            ::= { otu4_pathPer24HHisEntry 1 }

        otu4_pathPer24HHisParaLen OBJECT-TYPE
            SYNTAX INTEGER
            MAX-ACCESS read-only
            STATUS current
            DESCRIPTION
                "perParaLen."
            ::= { otu4_pathPer24HHisEntry 2 }


        otu4_pathPer24HHisPara OBJECT-TYPE
            SYNTAX OCTET STRING (SIZE (0..100))
            MAX-ACCESS read-only
            STATUS current
            DESCRIPTION
                "perPara."
            ::= { otu4_pathPer24HHisEntry 3 }



        otu4_pathPer24HHisMonValue OBJECT-TYPE
            SYNTAX OCTET STRING (SIZE (0..100))
            MAX-ACCESS read-only
            STATUS current
            DESCRIPTION
                "perMonValue."
            ::= { otu4_pathPer24HHisEntry 4 }



        otu4_pathPer24HHisDateTimeStart OBJECT-TYPE
            SYNTAX DateAndTime
            MAX-ACCESS read-only
            STATUS current
            DESCRIPTION
                "perDateTimeStart. "
            ::= { otu4_pathPer24HHisEntry 5 }

        otu4_pathPer24HHisDateTimeEnd OBJECT-TYPE
            SYNTAX DateAndTime
            MAX-ACCESS read-only
            STATUS current
            DESCRIPTION
                "perDateTimeEnd. "
            ::= { otu4_pathPer24HHisEntry 6 }


        otu4_pathPer24HHisVldty OBJECT-TYPE
            SYNTAX INTEGER
            MAX-ACCESS read-only
            STATUS current
            DESCRIPTION
                "perVldty. "
            ::= { otu4_pathPer24HHisEntry 7 }

--  Alarm data
        -- 1.3.6.1.4.1.2011.2.25.3.40.50.190
        odu4_path OBJECT IDENTIFIER ::= { optixGlobalNGWDM 190 }

-- -------------------------------------------------------------------------
-- Perfomance 15-MIN Current Data Table (RTRV-PER-<MOD2>)
-- -------------------------------------------------------------------------
        -- 1.3.6.1.4.1.2011.2.25.3.40.50.190.10
        odu4_pathPer15mCurTable OBJECT-TYPE
            SYNTAX SEQUENCE OF Odu4_pathPer15mCurEntry
            MAX-ACCESS not-accessible
            STATUS current
            DESCRIPTION
                "odu4_pathPer15mCur."
            ::= { odu4_path 10 }

        -- 1.3.6.1.4.1.2011.2.25.3.40.50.190.10.1
        odu4_pathPer15mCurEntry OBJECT-TYPE
            SYNTAX Odu4_pathPer15mCurEntry
            MAX-ACCESS not-accessible
            STATUS current
            DESCRIPTION
                "odu4_pathPer15mCur."
            INDEX {odu4_pathPer15mCurEid, odu4_pathPer15mCurPara}
            ::= { odu4_pathPer15mCurTable 1 }

        Odu4_pathPer15mCurEntry ::=
            SEQUENCE {
                odu4_pathPer15mCurEid
                    PerformanceEventType,
                odu4_pathPer15mCurMonValue
                    OCTET STRING,
                odu4_pathPer15mCurVldty
                    INTEGER,
                odu4_pathPer15mCurDateTime
                    DateAndTime,
                odu4_pathPer15mCurParaLen
                    INTEGER,
                odu4_pathPer15mCurPara
                    OCTET STRING
             }

        -- 1.3.6.1.4.1.2011.2.25.3.40.50.190.10.1.1
        odu4_pathPer15mCurEid OBJECT-TYPE
            SYNTAX PerformanceEventType
            MAX-ACCESS read-only
            STATUS current
            DESCRIPTION
                "perEid."
            ::= { odu4_pathPer15mCurEntry 1 }

        -- 1.3.6.1.4.1.2011.2.25.3.40.50.190.10.1.2
        odu4_pathPer15mCurMonValue OBJECT-TYPE
            SYNTAX OCTET STRING (SIZE (0..100))
            MAX-ACCESS read-only
            STATUS current
            DESCRIPTION
                "perMonValue."
            ::= { odu4_pathPer15mCurEntry 2 }

        -- 1.3.6.1.4.1.2011.2.25.3.40.50.190.10.3
        odu4_pathPer15mCurVldty OBJECT-TYPE
            SYNTAX INTEGER
            MAX-ACCESS read-only
            STATUS current
            DESCRIPTION
                "perVldty. "
            ::= { odu4_pathPer15mCurEntry 3 }

        -- 1.3.6.1.4.1.2011.2.25.3.40.50.190.10.1.4
        odu4_pathPer15mCurDateTime OBJECT-TYPE
            SYNTAX DateAndTime
            MAX-ACCESS read-only
            STATUS current
            DESCRIPTION
                "perDateTime. "
            ::= { odu4_pathPer15mCurEntry 4 }

        -- 1.3.6.1.4.1.2011.2.25.3.40.50.190.10.1.5
        odu4_pathPer15mCurParaLen OBJECT-TYPE
            SYNTAX INTEGER
            MAX-ACCESS read-only
            STATUS current
            DESCRIPTION
                "perParaLen."
            ::= { odu4_pathPer15mCurEntry 5 }

        -- 1.3.6.1.4.1.2011.2.25.3.40.50.190.10.1.6
        odu4_pathPer15mCurPara OBJECT-TYPE
            SYNTAX OCTET STRING (SIZE (0..100))
            MAX-ACCESS read-only
            STATUS current
            DESCRIPTION
                "perPara."
            ::= { odu4_pathPer15mCurEntry 6 }


-- -------------------------------------------------------------------------
-- Perfomance 15-MIN History Data Table (RTRV-PER-<MOD2>)
-- -------------------------------------------------------------------------
        odu4_pathPer15MHisTable OBJECT-TYPE
            SYNTAX SEQUENCE OF Odu4_pathPer15MHisEntry
            MAX-ACCESS not-accessible
            STATUS current
            DESCRIPTION
                "odu4_pathPer15MHis."
            ::= { odu4_path 20 }


        odu4_pathPer15MHisEntry OBJECT-TYPE
            SYNTAX Odu4_pathPer15MHisEntry
            MAX-ACCESS not-accessible
            STATUS current
            DESCRIPTION
                "odu4_pathPer15MHis."
            INDEX {odu4_pathPer15MHisEid, odu4_pathPer15MHisParaLen, odu4_pathPer15MHisPara, odu4_pathPer15MHisDateTimeStart, odu4_pathPer15MHisDateTimeEnd}
            ::= { odu4_pathPer15MHisTable 1 }

        Odu4_pathPer15MHisEntry ::=
            SEQUENCE {
                odu4_pathPer15MHisEid
                    PerformanceEventType,
                odu4_pathPer15MHisParaLen
                    INTEGER,
                odu4_pathPer15MHisPara
                    OCTET STRING,
                odu4_pathPer15MHisMonValue
                    OCTET STRING,
                odu4_pathPer15MHisDateTimeStart
                    DateAndTime,
                odu4_pathPer15MHisDateTimeEnd
                    DateAndTime,
                odu4_pathPer15MHisVldty
                    INTEGER,
             }

        odu4_pathPer15MHisEid OBJECT-TYPE
            SYNTAX PerformanceEventType
            MAX-ACCESS read-only
            STATUS current
            DESCRIPTION
                "perEid."
            ::= { odu4_pathPer15MHisEntry 1 }

        odu4_pathPer15MHisParaLen OBJECT-TYPE
            SYNTAX INTEGER
            MAX-ACCESS read-only
            STATUS current
            DESCRIPTION
                "perParaLen."
            ::= { odu4_pathPer15MHisEntry 2 }


        odu4_pathPer15MHisPara OBJECT-TYPE
            SYNTAX OCTET STRING (SIZE (0..100))
            MAX-ACCESS read-only
            STATUS current
            DESCRIPTION
                "perPara."
            ::= { odu4_pathPer15MHisEntry 3 }



        odu4_pathPer15MHisMonValue OBJECT-TYPE
            SYNTAX OCTET STRING (SIZE (0..100))
            MAX-ACCESS read-only
            STATUS current
            DESCRIPTION
                "perMonValue."
            ::= { odu4_pathPer15MHisEntry 4 }



        odu4_pathPer15MHisDateTimeStart OBJECT-TYPE
            SYNTAX DateAndTime
            MAX-ACCESS read-only
            STATUS current
            DESCRIPTION
                "perDateTimeStart. "
            ::= { odu4_pathPer15MHisEntry 5 }

        odu4_pathPer15MHisDateTimeEnd OBJECT-TYPE
            SYNTAX DateAndTime
            MAX-ACCESS read-only
            STATUS current
            DESCRIPTION
                "perDateTimeEnd. "
            ::= { odu4_pathPer15MHisEntry 6 }


        odu4_pathPer15MHisVldty OBJECT-TYPE
            SYNTAX INTEGER
            MAX-ACCESS read-only
            STATUS current
            DESCRIPTION
                "perVldty. "
            ::= { odu4_pathPer15MHisEntry 7 }


-- -------------------------------------------------------------------------
-- Perfomance 24-HOUR Current Data Table (RTRV-PER-<MOD2>)
-- -------------------------------------------------------------------------
        odu4_pathPer24HCurTable OBJECT-TYPE
            SYNTAX SEQUENCE OF Odu4_pathPer24HCurEntry
            MAX-ACCESS not-accessible
            STATUS current
            DESCRIPTION
                "odu4_pathPer24HCur."
            ::= { odu4_path 30 }


        odu4_pathPer24HCurEntry OBJECT-TYPE
            SYNTAX Odu4_pathPer24HCurEntry
            MAX-ACCESS not-accessible
            STATUS current
            DESCRIPTION
                "odu4_pathPer24HCur."
            INDEX {odu4_pathPer24HCurEid, odu4_pathPer24HCurPara}
            ::= { odu4_pathPer24HCurTable 1 }

        Odu4_pathPer24HCurEntry ::=
            SEQUENCE {
                odu4_pathPer24HCurEid
                    PerformanceEventType,
                odu4_pathPer24HCurMonValue
                    OCTET STRING,
                odu4_pathPer24HCurVldty
                    INTEGER,
                odu4_pathPer24HCurDateTime
                    DateAndTime,
                odu4_pathPer24HCurParaLen
                    INTEGER,
                odu4_pathPer24HCurPara
                    OCTET STRING
             }


        odu4_pathPer24HCurEid OBJECT-TYPE
            SYNTAX PerformanceEventType
            MAX-ACCESS read-only
            STATUS current
            DESCRIPTION
                "perEid."
            ::= { odu4_pathPer24HCurEntry 1 }


        odu4_pathPer24HCurMonValue OBJECT-TYPE
            SYNTAX OCTET STRING (SIZE (0..100))
            MAX-ACCESS read-only
            STATUS current
            DESCRIPTION
                "perMonValue."
            ::= { odu4_pathPer24HCurEntry 2 }


        odu4_pathPer24HCurVldty OBJECT-TYPE
            SYNTAX INTEGER
            MAX-ACCESS read-only
            STATUS current
            DESCRIPTION
                "perVldty. "
            ::= { odu4_pathPer24HCurEntry 3 }


        odu4_pathPer24HCurDateTime OBJECT-TYPE
            SYNTAX DateAndTime
            MAX-ACCESS read-only
            STATUS current
            DESCRIPTION
                "perDateTime. "
            ::= { odu4_pathPer24HCurEntry 4 }


        odu4_pathPer24HCurParaLen OBJECT-TYPE
            SYNTAX INTEGER
            MAX-ACCESS read-only
            STATUS current
            DESCRIPTION
                "perParaLen."
            ::= { odu4_pathPer24HCurEntry 5 }


        odu4_pathPer24HCurPara OBJECT-TYPE
            SYNTAX OCTET STRING (SIZE (0..100))
            MAX-ACCESS read-only
            STATUS current
            DESCRIPTION
                "perPara."
            ::= { odu4_pathPer24HCurEntry 6 }


-- -------------------------------------------------------------------------
-- Perfomance 24-HOUR History Data Table (RTRV-PER-<MOD2>)
-- -------------------------------------------------------------------------
        odu4_pathPer24HHisTable OBJECT-TYPE
            SYNTAX SEQUENCE OF Odu4_pathPer24HHisEntry
            MAX-ACCESS not-accessible
            STATUS current
            DESCRIPTION
                "odu4_pathPer24HHis."
            ::= { odu4_path 40 }


        odu4_pathPer24HHisEntry OBJECT-TYPE
            SYNTAX Odu4_pathPer24HHisEntry
            MAX-ACCESS not-accessible
            STATUS current
            DESCRIPTION
                "odu4_pathPer24HHis."
            INDEX {odu4_pathPer24HHisEid, odu4_pathPer24HHisParaLen, odu4_pathPer24HHisPara, odu4_pathPer24HHisDateTimeStart, odu4_pathPer24HHisDateTimeEnd}
            ::= { odu4_pathPer24HHisTable 1 }

        Odu4_pathPer24HHisEntry ::=
            SEQUENCE {
                odu4_pathPer24HHisEid
                    PerformanceEventType,
                odu4_pathPer24HHisParaLen
                    INTEGER,
                odu4_pathPer24HHisPara
                    OCTET STRING,
                odu4_pathPer24HHisMonValue
                    OCTET STRING,
                odu4_pathPer24HHisDateTimeStart
                    DateAndTime,
                odu4_pathPer24HHisDateTimeEnd
                    DateAndTime,
                odu4_pathPer24HHisVldty
                    INTEGER,
             }

        odu4_pathPer24HHisEid OBJECT-TYPE
            SYNTAX PerformanceEventType
            MAX-ACCESS read-only
            STATUS current
            DESCRIPTION
                "perEid."
            ::= { odu4_pathPer24HHisEntry 1 }

        odu4_pathPer24HHisParaLen OBJECT-TYPE
            SYNTAX INTEGER
            MAX-ACCESS read-only
            STATUS current
            DESCRIPTION
                "perParaLen."
            ::= { odu4_pathPer24HHisEntry 2 }


        odu4_pathPer24HHisPara OBJECT-TYPE
            SYNTAX OCTET STRING (SIZE (0..100))
            MAX-ACCESS read-only
            STATUS current
            DESCRIPTION
                "perPara."
            ::= { odu4_pathPer24HHisEntry 3 }



        odu4_pathPer24HHisMonValue OBJECT-TYPE
            SYNTAX OCTET STRING (SIZE (0..100))
            MAX-ACCESS read-only
            STATUS current
            DESCRIPTION
                "perMonValue."
            ::= { odu4_pathPer24HHisEntry 4 }



        odu4_pathPer24HHisDateTimeStart OBJECT-TYPE
            SYNTAX DateAndTime
            MAX-ACCESS read-only
            STATUS current
            DESCRIPTION
                "perDateTimeStart. "
            ::= { odu4_pathPer24HHisEntry 5 }

        odu4_pathPer24HHisDateTimeEnd OBJECT-TYPE
            SYNTAX DateAndTime
            MAX-ACCESS read-only
            STATUS current
            DESCRIPTION
                "perDateTimeEnd. "
            ::= { odu4_pathPer24HHisEntry 6 }


        odu4_pathPer24HHisVldty OBJECT-TYPE
            SYNTAX INTEGER
            MAX-ACCESS read-only
            STATUS current
            DESCRIPTION
                "perVldty. "
            ::= { odu4_pathPer24HHisEntry 7 }

--  Alarm data
        -- 1.3.6.1.4.1.2011.2.25.3.40.50.248
        otucn_path OBJECT IDENTIFIER ::= { optixGlobalNGWDM 248 }

-- -------------------------------------------------------------------------
-- Perfomance 15-MIN Current Data Table (RTRV-PER-<MOD2>)
-- -------------------------------------------------------------------------
        -- 1.3.6.1.4.1.2011.2.25.3.40.50.248.10
        otucn_pathPer15mCurTable OBJECT-TYPE
            SYNTAX SEQUENCE OF Otucn_pathPer15mCurEntry
            MAX-ACCESS not-accessible
            STATUS current
            DESCRIPTION
                "otucn_pathPer15mCur."
            ::= { otucn_path 10 }

        -- 1.3.6.1.4.1.2011.2.25.3.40.50.248.10.1
        otucn_pathPer15mCurEntry OBJECT-TYPE
            SYNTAX Otucn_pathPer15mCurEntry
            MAX-ACCESS not-accessible
            STATUS current
            DESCRIPTION
                "otucn_pathPer15mCur."
            INDEX {otucn_pathPer15mCurEid, otucn_pathPer15mCurPara}
            ::= { otucn_pathPer15mCurTable 1 }

        Otucn_pathPer15mCurEntry ::=
            SEQUENCE {
                otucn_pathPer15mCurEid
                    PerformanceEventType,
                otucn_pathPer15mCurMonValue
                    OCTET STRING,
                otucn_pathPer15mCurVldty
                    INTEGER,
                otucn_pathPer15mCurDateTime
                    DateAndTime,
                otucn_pathPer15mCurParaLen
                    INTEGER,
                otucn_pathPer15mCurPara
                    OCTET STRING
             }

        -- 1.3.6.1.4.1.2011.2.25.3.40.50.248.10.1.1
        otucn_pathPer15mCurEid OBJECT-TYPE
            SYNTAX PerformanceEventType
            MAX-ACCESS read-only
            STATUS current
            DESCRIPTION
                "perEid."
            ::= { otucn_pathPer15mCurEntry 1 }

        -- 1.3.6.1.4.1.2011.2.25.3.40.50.248.10.1.2
        otucn_pathPer15mCurMonValue OBJECT-TYPE
            SYNTAX OCTET STRING (SIZE (0..100))
            MAX-ACCESS read-only
            STATUS current
            DESCRIPTION
                "perMonValue."
            ::= { otucn_pathPer15mCurEntry 2 }

        -- 1.3.6.1.4.1.2011.2.25.3.40.50.248.10.1.3
        otucn_pathPer15mCurVldty OBJECT-TYPE
            SYNTAX INTEGER
            MAX-ACCESS read-only
            STATUS current
            DESCRIPTION
                "perVldty. "
            ::= { otucn_pathPer15mCurEntry 3 }

        -- 1.3.6.1.4.1.2011.2.25.3.40.50.248.10.1.4
        otucn_pathPer15mCurDateTime OBJECT-TYPE
            SYNTAX DateAndTime
            MAX-ACCESS read-only
            STATUS current
            DESCRIPTION
                "perDateTime. "
            ::= { otucn_pathPer15mCurEntry 4 }

        -- 1.3.6.1.4.1.2011.2.25.3.40.50.248.10.1.5
        otucn_pathPer15mCurParaLen OBJECT-TYPE
            SYNTAX INTEGER
            MAX-ACCESS read-only
            STATUS current
            DESCRIPTION
                "perParaLen."
            ::= { otucn_pathPer15mCurEntry 5 }

        -- 1.3.6.1.4.1.2011.2.25.3.40.50.248.10.1.6
        otucn_pathPer15mCurPara OBJECT-TYPE
            SYNTAX OCTET STRING (SIZE (0..100))
            MAX-ACCESS read-only
            STATUS current
            DESCRIPTION
                "perPara."
            ::= { otucn_pathPer15mCurEntry 6 }


-- -------------------------------------------------------------------------
-- Perfomance 15-MIN History Data Table (RTRV-PER-<MOD2>)
-- -------------------------------------------------------------------------
        -- 1.3.6.1.4.1.2011.2.25.3.40.50.248.20
        otucn_pathPer15MHisTable OBJECT-TYPE
            SYNTAX SEQUENCE OF Otucn_pathPer15MHisEntry
            MAX-ACCESS not-accessible
            STATUS current
            DESCRIPTION
                "otucn_pathPer15MHis."
            ::= { otucn_path 20 }

        -- 1.3.6.1.4.1.2011.2.25.3.40.50.248.20.1
        otucn_pathPer15MHisEntry OBJECT-TYPE
            SYNTAX Otucn_pathPer15MHisEntry
            MAX-ACCESS not-accessible
            STATUS current
            DESCRIPTION
                "otucn_pathPer15MHis."
            INDEX {otucn_pathPer15MHisEid, otucn_pathPer15MHisParaLen, otucn_pathPer15MHisPara, otucn_pathPer15MHisDateTimeStart, otucn_pathPer15MHisDateTimeEnd}
            ::= { otucn_pathPer15MHisTable 1 }

        Otucn_pathPer15MHisEntry ::=
            SEQUENCE {
                otucn_pathPer15MHisEid
                    PerformanceEventType,
                otucn_pathPer15MHisParaLen
                    INTEGER,
                otucn_pathPer15MHisPara
                    OCTET STRING,
                otucn_pathPer15MHisMonValue
                    OCTET STRING,
                otucn_pathPer15MHisDateTimeStart
                    DateAndTime,
                otucn_pathPer15MHisDateTimeEnd
                    DateAndTime,
                otucn_pathPer15MHisVldty
                    INTEGER,
             }

        -- 1.3.6.1.4.1.2011.2.25.3.40.50.248.20.1.1
        otucn_pathPer15MHisEid OBJECT-TYPE
            SYNTAX PerformanceEventType
            MAX-ACCESS read-only
            STATUS current
            DESCRIPTION
                "perEid."
            ::= { otucn_pathPer15MHisEntry 1 }

        -- 1.3.6.1.4.1.2011.2.25.3.40.50.248.20.1.2
        otucn_pathPer15MHisParaLen OBJECT-TYPE
            SYNTAX INTEGER
            MAX-ACCESS read-only
            STATUS current
            DESCRIPTION
                "perParaLen."
            ::= { otucn_pathPer15MHisEntry 2 }

        -- 1.3.6.1.4.1.2011.2.25.3.40.50.248.20.1.3
        otucn_pathPer15MHisPara OBJECT-TYPE
            SYNTAX OCTET STRING (SIZE (0..100))
            MAX-ACCESS read-only
            STATUS current
            DESCRIPTION
                "perPara."
            ::= { otucn_pathPer15MHisEntry 3 }


        -- 1.3.6.1.4.1.2011.2.25.3.40.50.248.20.1.4
        otucn_pathPer15MHisMonValue OBJECT-TYPE
            SYNTAX OCTET STRING (SIZE (0..100))
            MAX-ACCESS read-only
            STATUS current
            DESCRIPTION
                "perMonValue."
            ::= { otucn_pathPer15MHisEntry 4 }


        -- 1.3.6.1.4.1.2011.2.25.3.40.50.248.20.1.5
        otucn_pathPer15MHisDateTimeStart OBJECT-TYPE
            SYNTAX DateAndTime
            MAX-ACCESS read-only
            STATUS current
            DESCRIPTION
                "perDateTimeStart. "
            ::= { otucn_pathPer15MHisEntry 5 }

        -- 1.3.6.1.4.1.2011.2.25.3.40.50.248.20.1.6
        otucn_pathPer15MHisDateTimeEnd OBJECT-TYPE
            SYNTAX DateAndTime
            MAX-ACCESS read-only
            STATUS current
            DESCRIPTION
                "perDateTimeEnd. "
            ::= { otucn_pathPer15MHisEntry 6 }

        -- 1.3.6.1.4.1.2011.2.25.3.40.50.248.20.1.7
        otucn_pathPer15MHisVldty OBJECT-TYPE
            SYNTAX INTEGER
            MAX-ACCESS read-only
            STATUS current
            DESCRIPTION
                "perVldty. "
            ::= { otucn_pathPer15MHisEntry 7 }


-- -------------------------------------------------------------------------
-- Perfomance 24-HOUR Current Data Table (RTRV-PER-<MOD2>)
-- -------------------------------------------------------------------------
        -- 1.3.6.1.4.1.2011.2.25.3.40.50.248.30
        otucn_pathPer24HCurTable OBJECT-TYPE
            SYNTAX SEQUENCE OF Otucn_pathPer24HCurEntry
            MAX-ACCESS not-accessible
            STATUS current
            DESCRIPTION
                "otucn_pathPer24HCur."
            ::= { otucn_path 30 }

        -- 1.3.6.1.4.1.2011.2.25.3.40.50.248.30.1
        otucn_pathPer24HCurEntry OBJECT-TYPE
            SYNTAX Otucn_pathPer24HCurEntry
            MAX-ACCESS not-accessible
            STATUS current
            DESCRIPTION
                "otucn_pathPer24HCur."
            INDEX {otucn_pathPer24HCurEid, otucn_pathPer24HCurPara}
            ::= { otucn_pathPer24HCurTable 1 }

        Otucn_pathPer24HCurEntry ::=
            SEQUENCE {
                otucn_pathPer24HCurEid
                    PerformanceEventType,
                otucn_pathPer24HCurMonValue
                    OCTET STRING,
                otucn_pathPer24HCurVldty
                    INTEGER,
                otucn_pathPer24HCurDateTime
                    DateAndTime,
                otucn_pathPer24HCurParaLen
                    INTEGER,
                otucn_pathPer24HCurPara
                    OCTET STRING
             }

        -- 1.3.6.1.4.1.2011.2.25.3.40.50.248.30.1.1
        otucn_pathPer24HCurEid OBJECT-TYPE
            SYNTAX PerformanceEventType
            MAX-ACCESS read-only
            STATUS current
            DESCRIPTION
                "perEid."
            ::= { otucn_pathPer24HCurEntry 1 }

        -- 1.3.6.1.4.1.2011.2.25.3.40.50.248.30.1.2
        otucn_pathPer24HCurMonValue OBJECT-TYPE
            SYNTAX OCTET STRING (SIZE (0..100))
            MAX-ACCESS read-only
            STATUS current
            DESCRIPTION
                "perMonValue."
            ::= { otucn_pathPer24HCurEntry 2 }

        -- 1.3.6.1.4.1.2011.2.25.3.40.50.248.30.1.3
        otucn_pathPer24HCurVldty OBJECT-TYPE
            SYNTAX INTEGER
            MAX-ACCESS read-only
            STATUS current
            DESCRIPTION
                "perVldty. "
            ::= { otucn_pathPer24HCurEntry 3 }

        -- 1.3.6.1.4.1.2011.2.25.3.40.50.248.30.1.4
        otucn_pathPer24HCurDateTime OBJECT-TYPE
            SYNTAX DateAndTime
            MAX-ACCESS read-only
            STATUS current
            DESCRIPTION
                "perDateTime. "
            ::= { otucn_pathPer24HCurEntry 4 }

        -- 1.3.6.1.4.1.2011.2.25.3.40.50.248.30.1.5
        otucn_pathPer24HCurParaLen OBJECT-TYPE
            SYNTAX INTEGER
            MAX-ACCESS read-only
            STATUS current
            DESCRIPTION
                "perParaLen."
            ::= { otucn_pathPer24HCurEntry 5 }

        -- 1.3.6.1.4.1.2011.2.25.3.40.50.248.30.1.6
        otucn_pathPer24HCurPara OBJECT-TYPE
            SYNTAX OCTET STRING (SIZE (0..100))
            MAX-ACCESS read-only
            STATUS current
            DESCRIPTION
                "perPara."
            ::= { otucn_pathPer24HCurEntry 6 }


-- -------------------------------------------------------------------------
-- Perfomance 24-HOUR History Data Table (RTRV-PER-<MOD2>)
-- -------------------------------------------------------------------------
        -- 1.3.6.1.4.1.2011.2.25.3.40.50.248.40
        otucn_pathPer24HHisTable OBJECT-TYPE
            SYNTAX SEQUENCE OF Otucn_pathPer24HHisEntry
            MAX-ACCESS not-accessible
            STATUS current
            DESCRIPTION
                "otucn_pathPer24HHis."
            ::= { otucn_path 40 }

        -- 1.3.6.1.4.1.2011.2.25.3.40.50.248.40.1
        otucn_pathPer24HHisEntry OBJECT-TYPE
            SYNTAX Otucn_pathPer24HHisEntry
            MAX-ACCESS not-accessible
            STATUS current
            DESCRIPTION
                "otucn_pathPer24HHis."
            INDEX {otucn_pathPer24HHisEid, otucn_pathPer24HHisParaLen, otucn_pathPer24HHisPara, otucn_pathPer24HHisDateTimeStart, otucn_pathPer24HHisDateTimeEnd}
            ::= { otucn_pathPer24HHisTable 1 }

        Otucn_pathPer24HHisEntry ::=
            SEQUENCE {
                otucn_pathPer24HHisEid
                    PerformanceEventType,
                otucn_pathPer24HHisParaLen
                    INTEGER,
                otucn_pathPer24HHisPara
                    OCTET STRING,
                otucn_pathPer24HHisMonValue
                    OCTET STRING,
                otucn_pathPer24HHisDateTimeStart
                    DateAndTime,
                otucn_pathPer24HHisDateTimeEnd
                    DateAndTime,
                otucn_pathPer24HHisVldty
                    INTEGER,
             }

        -- 1.3.6.1.4.1.2011.2.25.3.40.50.248.40.1.1
        otucn_pathPer24HHisEid OBJECT-TYPE
            SYNTAX PerformanceEventType
            MAX-ACCESS read-only
            STATUS current
            DESCRIPTION
                "perEid."
            ::= { otucn_pathPer24HHisEntry 1 }

        -- 1.3.6.1.4.1.2011.2.25.3.40.50.248.40.1.2
        otucn_pathPer24HHisParaLen OBJECT-TYPE
            SYNTAX INTEGER
            MAX-ACCESS read-only
            STATUS current
            DESCRIPTION
                "perParaLen."
            ::= { otucn_pathPer24HHisEntry 2 }

        -- 1.3.6.1.4.1.2011.2.25.3.40.50.248.40.1.3
        otucn_pathPer24HHisPara OBJECT-TYPE
            SYNTAX OCTET STRING (SIZE (0..100))
            MAX-ACCESS read-only
            STATUS current
            DESCRIPTION
                "perPara."
            ::= { otucn_pathPer24HHisEntry 3 }


        -- 1.3.6.1.4.1.2011.2.25.3.40.50.248.40.1.4
        otucn_pathPer24HHisMonValue OBJECT-TYPE
            SYNTAX OCTET STRING (SIZE (0..100))
            MAX-ACCESS read-only
            STATUS current
            DESCRIPTION
                "perMonValue."
            ::= { otucn_pathPer24HHisEntry 4 }


        -- 1.3.6.1.4.1.2011.2.25.3.40.50.248.40.1.5
        otucn_pathPer24HHisDateTimeStart OBJECT-TYPE
            SYNTAX DateAndTime
            MAX-ACCESS read-only
            STATUS current
            DESCRIPTION
                "perDateTimeStart. "
            ::= { otucn_pathPer24HHisEntry 5 }

        -- 1.3.6.1.4.1.2011.2.25.3.40.50.248.40.1.6
        otucn_pathPer24HHisDateTimeEnd OBJECT-TYPE
            SYNTAX DateAndTime
            MAX-ACCESS read-only
            STATUS current
            DESCRIPTION
                "perDateTimeEnd. "
            ::= { otucn_pathPer24HHisEntry 6 }

        -- 1.3.6.1.4.1.2011.2.25.3.40.50.248.40.1.7
        otucn_pathPer24HHisVldty OBJECT-TYPE
            SYNTAX INTEGER
            MAX-ACCESS read-only
            STATUS current
            DESCRIPTION
                "perVldty. "
            ::= { otucn_pathPer24HHisEntry 7 }

--  Alarm data
        -- 1.3.6.1.4.1.2011.2.25.3.40.50.249
        oducn_path OBJECT IDENTIFIER ::= { optixGlobalNGWDM 249 }

-- -------------------------------------------------------------------------
-- Perfomance 15-MIN Current Data Table (RTRV-PER-<MOD2>)
-- -------------------------------------------------------------------------
        -- 1.3.6.1.4.1.2011.2.25.3.40.50.249.10
        oducn_pathPer15mCurTable OBJECT-TYPE
            SYNTAX SEQUENCE OF Oducn_pathPer15mCurEntry
            MAX-ACCESS not-accessible
            STATUS current
            DESCRIPTION
                "oducn_pathPer15mCur."
            ::= { oducn_path 10 }

        -- 1.3.6.1.4.1.2011.2.25.3.40.50.249.10.1
        oducn_pathPer15mCurEntry OBJECT-TYPE
            SYNTAX Oducn_pathPer15mCurEntry
            MAX-ACCESS not-accessible
            STATUS current
            DESCRIPTION
                "oducn_pathPer15mCur."
            INDEX {oducn_pathPer15mCurEid, oducn_pathPer15mCurPara}
            ::= { oducn_pathPer15mCurTable 1 }

        Oducn_pathPer15mCurEntry ::=
            SEQUENCE {
                oducn_pathPer15mCurEid
                    PerformanceEventType,
                oducn_pathPer15mCurMonValue
                    OCTET STRING,
                oducn_pathPer15mCurVldty
                    INTEGER,
                oducn_pathPer15mCurDateTime
                    DateAndTime,
                oducn_pathPer15mCurParaLen
                    INTEGER,
                oducn_pathPer15mCurPara
                    OCTET STRING
             }

        -- 1.3.6.1.4.1.2011.2.25.3.40.50.249.10.1.1
        oducn_pathPer15mCurEid OBJECT-TYPE
            SYNTAX PerformanceEventType
            MAX-ACCESS read-only
            STATUS current
            DESCRIPTION
                "perEid."
            ::= { oducn_pathPer15mCurEntry 1 }

        -- 1.3.6.1.4.1.2011.2.25.3.40.50.249.10.1.2
        oducn_pathPer15mCurMonValue OBJECT-TYPE
            SYNTAX OCTET STRING (SIZE (0..100))
            MAX-ACCESS read-only
            STATUS current
            DESCRIPTION
                "perMonValue."
            ::= { oducn_pathPer15mCurEntry 2 }

        -- 1.3.6.1.4.1.2011.2.25.3.40.50.249.10.1.3
        oducn_pathPer15mCurVldty OBJECT-TYPE
            SYNTAX INTEGER
            MAX-ACCESS read-only
            STATUS current
            DESCRIPTION
                "perVldty. "
            ::= { oducn_pathPer15mCurEntry 3 }

        -- 1.3.6.1.4.1.2011.2.25.3.40.50.249.10.1.4
        oducn_pathPer15mCurDateTime OBJECT-TYPE
            SYNTAX DateAndTime
            MAX-ACCESS read-only
            STATUS current
            DESCRIPTION
                "perDateTime. "
            ::= { oducn_pathPer15mCurEntry 4 }

        -- 1.3.6.1.4.1.2011.2.25.3.40.50.249.10.1.5
        oducn_pathPer15mCurParaLen OBJECT-TYPE
            SYNTAX INTEGER
            MAX-ACCESS read-only
            STATUS current
            DESCRIPTION
                "perParaLen."
            ::= { oducn_pathPer15mCurEntry 5 }

        -- 1.3.6.1.4.1.2011.2.25.3.40.50.249.10.1.6
        oducn_pathPer15mCurPara OBJECT-TYPE
            SYNTAX OCTET STRING (SIZE (0..100))
            MAX-ACCESS read-only
            STATUS current
            DESCRIPTION
                "perPara."
            ::= { oducn_pathPer15mCurEntry 6 }


-- -------------------------------------------------------------------------
-- Perfomance 15-MIN History Data Table (RTRV-PER-<MOD2>)
-- -------------------------------------------------------------------------
        -- 1.3.6.1.4.1.2011.2.25.3.40.50.249.20
        oducn_pathPer15MHisTable OBJECT-TYPE
            SYNTAX SEQUENCE OF Oducn_pathPer15MHisEntry
            MAX-ACCESS not-accessible
            STATUS current
            DESCRIPTION
                "oducn_pathPer15MHis."
            ::= { oducn_path 20 }

        -- 1.3.6.1.4.1.2011.2.25.3.40.50.249.20.1
        oducn_pathPer15MHisEntry OBJECT-TYPE
            SYNTAX Oducn_pathPer15MHisEntry
            MAX-ACCESS not-accessible
            STATUS current
            DESCRIPTION
                "oducn_pathPer15MHis."
            INDEX {oducn_pathPer15MHisEid, oducn_pathPer15MHisParaLen, oducn_pathPer15MHisPara, oducn_pathPer15MHisDateTimeStart, oducn_pathPer15MHisDateTimeEnd}
            ::= { oducn_pathPer15MHisTable 1 }

        Oducn_pathPer15MHisEntry ::=
            SEQUENCE {
                oducn_pathPer15MHisEid
                    PerformanceEventType,
                oducn_pathPer15MHisParaLen
                    INTEGER,
                oducn_pathPer15MHisPara
                    OCTET STRING,
                oducn_pathPer15MHisMonValue
                    OCTET STRING,
                oducn_pathPer15MHisDateTimeStart
                    DateAndTime,
                oducn_pathPer15MHisDateTimeEnd
                    DateAndTime,
                oducn_pathPer15MHisVldty
                    INTEGER,
             }

        -- 1.3.6.1.4.1.2011.2.25.3.40.50.249.20.1.1
        oducn_pathPer15MHisEid OBJECT-TYPE
            SYNTAX PerformanceEventType
            MAX-ACCESS read-only
            STATUS current
            DESCRIPTION
                "perEid."
            ::= { oducn_pathPer15MHisEntry 1 }

        -- 1.3.6.1.4.1.2011.2.25.3.40.50.249.20.1.2
        oducn_pathPer15MHisParaLen OBJECT-TYPE
            SYNTAX INTEGER
            MAX-ACCESS read-only
            STATUS current
            DESCRIPTION
                "perParaLen."
            ::= { oducn_pathPer15MHisEntry 2 }

        -- 1.3.6.1.4.1.2011.2.25.3.40.50.249.20.1.3
        oducn_pathPer15MHisPara OBJECT-TYPE
            SYNTAX OCTET STRING (SIZE (0..100))
            MAX-ACCESS read-only
            STATUS current
            DESCRIPTION
                "perPara."
            ::= { oducn_pathPer15MHisEntry 3 }


        -- 1.3.6.1.4.1.2011.2.25.3.40.50.249.20.1.4
        oducn_pathPer15MHisMonValue OBJECT-TYPE
            SYNTAX OCTET STRING (SIZE (0..100))
            MAX-ACCESS read-only
            STATUS current
            DESCRIPTION
                "perMonValue."
            ::= { oducn_pathPer15MHisEntry 4 }


        -- 1.3.6.1.4.1.2011.2.25.3.40.50.249.20.1.5
        oducn_pathPer15MHisDateTimeStart OBJECT-TYPE
            SYNTAX DateAndTime
            MAX-ACCESS read-only
            STATUS current
            DESCRIPTION
                "perDateTimeStart. "
            ::= { oducn_pathPer15MHisEntry 5 }

        -- 1.3.6.1.4.1.2011.2.25.3.40.50.249.20.1.6
        oducn_pathPer15MHisDateTimeEnd OBJECT-TYPE
            SYNTAX DateAndTime
            MAX-ACCESS read-only
            STATUS current
            DESCRIPTION
                "perDateTimeEnd. "
            ::= { oducn_pathPer15MHisEntry 6 }

        -- 1.3.6.1.4.1.2011.2.25.3.40.50.249.20.1.7
        oducn_pathPer15MHisVldty OBJECT-TYPE
            SYNTAX INTEGER
            MAX-ACCESS read-only
            STATUS current
            DESCRIPTION
                "perVldty. "
            ::= { oducn_pathPer15MHisEntry 7 }


-- -------------------------------------------------------------------------
-- Perfomance 24-HOUR Current Data Table (RTRV-PER-<MOD2>)
-- -------------------------------------------------------------------------
        -- 1.3.6.1.4.1.2011.2.25.3.40.50.249.30
        oducn_pathPer24HCurTable OBJECT-TYPE
            SYNTAX SEQUENCE OF Oducn_pathPer24HCurEntry
            MAX-ACCESS not-accessible
            STATUS current
            DESCRIPTION
                "oducn_pathPer24HCur."
            ::= { oducn_path 30 }

        -- 1.3.6.1.4.1.2011.2.25.3.40.50.249.30.1
        oducn_pathPer24HCurEntry OBJECT-TYPE
            SYNTAX Oducn_pathPer24HCurEntry
            MAX-ACCESS not-accessible
            STATUS current
            DESCRIPTION
                "oducn_pathPer24HCur."
            INDEX {oducn_pathPer24HCurEid, oducn_pathPer24HCurPara}
            ::= { oducn_pathPer24HCurTable 1 }

        Oducn_pathPer24HCurEntry ::=
            SEQUENCE {
                oducn_pathPer24HCurEid
                    PerformanceEventType,
                oducn_pathPer24HCurMonValue
                    OCTET STRING,
                oducn_pathPer24HCurVldty
                    INTEGER,
                oducn_pathPer24HCurDateTime
                    DateAndTime,
                oducn_pathPer24HCurParaLen
                    INTEGER,
                oducn_pathPer24HCurPara
                    OCTET STRING
             }

        -- 1.3.6.1.4.1.2011.2.25.3.40.50.249.30.1.1
        oducn_pathPer24HCurEid OBJECT-TYPE
            SYNTAX PerformanceEventType
            MAX-ACCESS read-only
            STATUS current
            DESCRIPTION
                "perEid."
            ::= { oducn_pathPer24HCurEntry 1 }

        -- 1.3.6.1.4.1.2011.2.25.3.40.50.249.30.1.2
        oducn_pathPer24HCurMonValue OBJECT-TYPE
            SYNTAX OCTET STRING (SIZE (0..100))
            MAX-ACCESS read-only
            STATUS current
            DESCRIPTION
                "perMonValue."
            ::= { oducn_pathPer24HCurEntry 2 }

        -- 1.3.6.1.4.1.2011.2.25.3.40.50.249.30.1.3
        oducn_pathPer24HCurVldty OBJECT-TYPE
            SYNTAX INTEGER
            MAX-ACCESS read-only
            STATUS current
            DESCRIPTION
                "perVldty. "
            ::= { oducn_pathPer24HCurEntry 3 }

        -- 1.3.6.1.4.1.2011.2.25.3.40.50.249.30.1.4
        oducn_pathPer24HCurDateTime OBJECT-TYPE
            SYNTAX DateAndTime
            MAX-ACCESS read-only
            STATUS current
            DESCRIPTION
                "perDateTime. "
            ::= { oducn_pathPer24HCurEntry 4 }

        -- 1.3.6.1.4.1.2011.2.25.3.40.50.249.30.1.5
        oducn_pathPer24HCurParaLen OBJECT-TYPE
            SYNTAX INTEGER
            MAX-ACCESS read-only
            STATUS current
            DESCRIPTION
                "perParaLen."
            ::= { oducn_pathPer24HCurEntry 5 }

        -- 1.3.6.1.4.1.2011.2.25.3.40.50.249.30.1.6
        oducn_pathPer24HCurPara OBJECT-TYPE
            SYNTAX OCTET STRING (SIZE (0..100))
            MAX-ACCESS read-only
            STATUS current
            DESCRIPTION
                "perPara."
            ::= { oducn_pathPer24HCurEntry 6 }


-- -------------------------------------------------------------------------
-- Perfomance 24-HOUR History Data Table (RTRV-PER-<MOD2>)
-- -------------------------------------------------------------------------
        -- 1.3.6.1.4.1.2011.2.25.3.40.50.249.40
        oducn_pathPer24HHisTable OBJECT-TYPE
            SYNTAX SEQUENCE OF Oducn_pathPer24HHisEntry
            MAX-ACCESS not-accessible
            STATUS current
            DESCRIPTION
                "oducn_pathPer24HHis."
            ::= { oducn_path 40 }

        -- 1.3.6.1.4.1.2011.2.25.3.40.50.249.40.1
        oducn_pathPer24HHisEntry OBJECT-TYPE
            SYNTAX Oducn_pathPer24HHisEntry
            MAX-ACCESS not-accessible
            STATUS current
            DESCRIPTION
                "oducn_pathPer24HHis."
            INDEX {oducn_pathPer24HHisEid, oducn_pathPer24HHisParaLen, oducn_pathPer24HHisPara, oducn_pathPer24HHisDateTimeStart, oducn_pathPer24HHisDateTimeEnd}
            ::= { oducn_pathPer24HHisTable 1 }

        Oducn_pathPer24HHisEntry ::=
            SEQUENCE {
                oducn_pathPer24HHisEid
                    PerformanceEventType,
                oducn_pathPer24HHisParaLen
                    INTEGER,
                oducn_pathPer24HHisPara
                    OCTET STRING,
                oducn_pathPer24HHisMonValue
                    OCTET STRING,
                oducn_pathPer24HHisDateTimeStart
                    DateAndTime,
                oducn_pathPer24HHisDateTimeEnd
                    DateAndTime,
                oducn_pathPer24HHisVldty
                    INTEGER,
             }

        -- 1.3.6.1.4.1.2011.2.25.3.40.50.249.40.1.1
        oducn_pathPer24HHisEid OBJECT-TYPE
            SYNTAX PerformanceEventType
            MAX-ACCESS read-only
            STATUS current
            DESCRIPTION
                "perEid."
            ::= { oducn_pathPer24HHisEntry 1 }

        -- 1.3.6.1.4.1.2011.2.25.3.40.50.249.40.1.2
        oducn_pathPer24HHisParaLen OBJECT-TYPE
            SYNTAX INTEGER
            MAX-ACCESS read-only
            STATUS current
            DESCRIPTION
                "perParaLen."
            ::= { oducn_pathPer24HHisEntry 2 }

        -- 1.3.6.1.4.1.2011.2.25.3.40.50.249.40.1.3
        oducn_pathPer24HHisPara OBJECT-TYPE
            SYNTAX OCTET STRING (SIZE (0..100))
            MAX-ACCESS read-only
            STATUS current
            DESCRIPTION
                "perPara."
            ::= { oducn_pathPer24HHisEntry 3 }


        -- 1.3.6.1.4.1.2011.2.25.3.40.50.249.40.1.4
        oducn_pathPer24HHisMonValue OBJECT-TYPE
            SYNTAX OCTET STRING (SIZE (0..100))
            MAX-ACCESS read-only
            STATUS current
            DESCRIPTION
                "perMonValue."
            ::= { oducn_pathPer24HHisEntry 4 }


        -- 1.3.6.1.4.1.2011.2.25.3.40.50.249.40.1.5
        oducn_pathPer24HHisDateTimeStart OBJECT-TYPE
            SYNTAX DateAndTime
            MAX-ACCESS read-only
            STATUS current
            DESCRIPTION
                "perDateTimeStart. "
            ::= { oducn_pathPer24HHisEntry 5 }

        -- 1.3.6.1.4.1.2011.2.25.3.40.50.249.40.1.6
        oducn_pathPer24HHisDateTimeEnd OBJECT-TYPE
            SYNTAX DateAndTime
            MAX-ACCESS read-only
            STATUS current
            DESCRIPTION
                "perDateTimeEnd. "
            ::= { oducn_pathPer24HHisEntry 6 }

        -- 1.3.6.1.4.1.2011.2.25.3.40.50.249.40.1.7
        oducn_pathPer24HHisVldty OBJECT-TYPE
            SYNTAX INTEGER
            MAX-ACCESS read-only
            STATUS current
            DESCRIPTION
                "perVldty. "
            ::= { oducn_pathPer24HHisEntry 7 }

--  Alarm data
        -- 1.3.6.1.4.1.2011.2.25.3.40.50.283
        laser_lane OBJECT IDENTIFIER ::= { optixGlobalNGWDM 283 }

-- -------------------------------------------------------------------------
-- Perfomance 15-MIN Current Data Table (RTRV-PER-<MOD2>)
-- -------------------------------------------------------------------------
        -- 1.3.6.1.4.1.2011.2.25.3.40.50.283.10
        laser_lanePer15mCurTable OBJECT-TYPE
            SYNTAX SEQUENCE OF Laser_lanePer15mCurEntry
            MAX-ACCESS not-accessible
            STATUS current
            DESCRIPTION
                "laser_lanePer15mCur."
            ::= { laser_lane 10 }

        -- 1.3.6.1.4.1.2011.2.25.3.40.50.283.10.1
        laser_lanePer15mCurEntry OBJECT-TYPE
            SYNTAX Laser_lanePer15mCurEntry
            MAX-ACCESS not-accessible
            STATUS current
            DESCRIPTION
                "laser_lanePer15mCur."
            INDEX {laser_lanePer15mCurEid, laser_lanePer15mCurPara}
            ::= { laser_lanePer15mCurTable 1 }

        Laser_lanePer15mCurEntry ::=
            SEQUENCE {
                laser_lanePer15mCurEid
                    PerformanceEventType,
                laser_lanePer15mCurMonValue
                    OCTET STRING,
                laser_lanePer15mCurVldty
                    INTEGER,
                laser_lanePer15mCurDateTime
                    DateAndTime,
                laser_lanePer15mCurParaLen
                    INTEGER,
                laser_lanePer15mCurPara
                    OCTET STRING
             }

        -- 1.3.6.1.4.1.2011.2.25.3.40.50.283.10.1.1
        laser_lanePer15mCurEid OBJECT-TYPE
            SYNTAX PerformanceEventType
            MAX-ACCESS read-only
            STATUS current
            DESCRIPTION
                "perEid."
            ::= { laser_lanePer15mCurEntry 1 }

        -- 1.3.6.1.4.1.2011.2.25.3.40.50.283.10.1.2
        laser_lanePer15mCurMonValue OBJECT-TYPE
            SYNTAX OCTET STRING (SIZE (0..100))
            MAX-ACCESS read-only
            STATUS current
            DESCRIPTION
                "perMonValue."
            ::= { laser_lanePer15mCurEntry 2 }

        -- 1.3.6.1.4.1.2011.2.25.3.40.50.283.10.1.3
        laser_lanePer15mCurVldty OBJECT-TYPE
            SYNTAX INTEGER
            MAX-ACCESS read-only
            STATUS current
            DESCRIPTION
                "perVldty. "
            ::= { laser_lanePer15mCurEntry 3 }

        -- 1.3.6.1.4.1.2011.2.25.3.40.50.283.10.1.4
        laser_lanePer15mCurDateTime OBJECT-TYPE
            SYNTAX DateAndTime
            MAX-ACCESS read-only
            STATUS current
            DESCRIPTION
                "perDateTime. "
            ::= { laser_lanePer15mCurEntry 4 }

        -- 1.3.6.1.4.1.2011.2.25.3.40.50.283.10.1.5
        laser_lanePer15mCurParaLen OBJECT-TYPE
            SYNTAX INTEGER
            MAX-ACCESS read-only
            STATUS current
            DESCRIPTION
                "perParaLen."
            ::= { laser_lanePer15mCurEntry 5 }

        -- 1.3.6.1.4.1.2011.2.25.3.40.50.283.10.1.6
        laser_lanePer15mCurPara OBJECT-TYPE
            SYNTAX OCTET STRING (SIZE (0..100))
            MAX-ACCESS read-only
            STATUS current
            DESCRIPTION
                "perPara."
            ::= { laser_lanePer15mCurEntry 6 }


-- -------------------------------------------------------------------------
-- Perfomance 15-MIN History Data Table (RTRV-PER-<MOD2>)
-- -------------------------------------------------------------------------
        -- 1.3.6.1.4.1.2011.2.25.3.40.50.283.20
        laser_lanePer15MHisTable OBJECT-TYPE
            SYNTAX SEQUENCE OF Laser_lanePer15MHisEntry
            MAX-ACCESS not-accessible
            STATUS current
            DESCRIPTION
                "laser_lanePer15MHis."
            ::= { laser_lane 20 }

        -- 1.3.6.1.4.1.2011.2.25.3.40.50.283.20.1
        laser_lanePer15MHisEntry OBJECT-TYPE
            SYNTAX Laser_lanePer15MHisEntry
            MAX-ACCESS not-accessible
            STATUS current
            DESCRIPTION
                "laser_lanePer15MHis."
            INDEX {laser_lanePer15MHisEid, laser_lanePer15MHisParaLen, laser_lanePer15MHisPara, laser_lanePer15MHisDateTimeStart, laser_lanePer15MHisDateTimeEnd}
            ::= { laser_lanePer15MHisTable 1 }

        Laser_lanePer15MHisEntry ::=
            SEQUENCE {
                laser_lanePer15MHisEid
                    PerformanceEventType,
                laser_lanePer15MHisParaLen
                    INTEGER,
                laser_lanePer15MHisPara
                    OCTET STRING,
                laser_lanePer15MHisMonValue
                    OCTET STRING,
                laser_lanePer15MHisDateTimeStart
                    DateAndTime,
                laser_lanePer15MHisDateTimeEnd
                    DateAndTime,
                laser_lanePer15MHisVldty
                    INTEGER,
             }

        -- 1.3.6.1.4.1.2011.2.25.3.40.50.283.20.1.1
        laser_lanePer15MHisEid OBJECT-TYPE
            SYNTAX PerformanceEventType
            MAX-ACCESS read-only
            STATUS current
            DESCRIPTION
                "perEid."
            ::= { laser_lanePer15MHisEntry 1 }

        -- 1.3.6.1.4.1.2011.2.25.3.40.50.283.20.1.2
        laser_lanePer15MHisParaLen OBJECT-TYPE
            SYNTAX INTEGER
            MAX-ACCESS read-only
            STATUS current
            DESCRIPTION
                "perParaLen."
            ::= { laser_lanePer15MHisEntry 2 }

        -- 1.3.6.1.4.1.2011.2.25.3.40.50.283.20.1.3
        laser_lanePer15MHisPara OBJECT-TYPE
            SYNTAX OCTET STRING (SIZE (0..100))
            MAX-ACCESS read-only
            STATUS current
            DESCRIPTION
                "perPara."
            ::= { laser_lanePer15MHisEntry 3 }


        -- 1.3.6.1.4.1.2011.2.25.3.40.50.283.20.1.4
        laser_lanePer15MHisMonValue OBJECT-TYPE
            SYNTAX OCTET STRING (SIZE (0..100))
            MAX-ACCESS read-only
            STATUS current
            DESCRIPTION
                "perMonValue."
            ::= { laser_lanePer15MHisEntry 4 }


        -- 1.3.6.1.4.1.2011.2.25.3.40.50.283.20.1.5
        laser_lanePer15MHisDateTimeStart OBJECT-TYPE
            SYNTAX DateAndTime
            MAX-ACCESS read-only
            STATUS current
            DESCRIPTION
                "perDateTimeStart. "
            ::= { laser_lanePer15MHisEntry 5 }

        -- 1.3.6.1.4.1.2011.2.25.3.40.50.283.20.1.6
        laser_lanePer15MHisDateTimeEnd OBJECT-TYPE
            SYNTAX DateAndTime
            MAX-ACCESS read-only
            STATUS current
            DESCRIPTION
                "perDateTimeEnd. "
            ::= { laser_lanePer15MHisEntry 6 }

        -- 1.3.6.1.4.1.2011.2.25.3.40.50.283.20.1.7
        laser_lanePer15MHisVldty OBJECT-TYPE
            SYNTAX INTEGER
            MAX-ACCESS read-only
            STATUS current
            DESCRIPTION
                "perVldty. "
            ::= { laser_lanePer15MHisEntry 7 }


-- -------------------------------------------------------------------------
-- Perfomance 24-HOUR Current Data Table (RTRV-PER-<MOD2>)
-- -------------------------------------------------------------------------
        -- 1.3.6.1.4.1.2011.2.25.3.40.50.283.30
        laser_lanePer24HCurTable OBJECT-TYPE
            SYNTAX SEQUENCE OF Laser_lanePer24HCurEntry
            MAX-ACCESS not-accessible
            STATUS current
            DESCRIPTION
                "laser_lanePer24HCur."
            ::= { laser_lane 30 }

        -- 1.3.6.1.4.1.2011.2.25.3.40.50.283.30.1
        laser_lanePer24HCurEntry OBJECT-TYPE
            SYNTAX Laser_lanePer24HCurEntry
            MAX-ACCESS not-accessible
            STATUS current
            DESCRIPTION
                "laser_lanePer24HCur."
            INDEX {laser_lanePer24HCurEid, laser_lanePer24HCurPara}
            ::= { laser_lanePer24HCurTable 1 }

        Laser_lanePer24HCurEntry ::=
            SEQUENCE {
                laser_lanePer24HCurEid
                    PerformanceEventType,
                laser_lanePer24HCurMonValue
                    OCTET STRING,
                laser_lanePer24HCurVldty
                    INTEGER,
                laser_lanePer24HCurDateTime
                    DateAndTime,
                laser_lanePer24HCurParaLen
                    INTEGER,
                laser_lanePer24HCurPara
                    OCTET STRING
             }

        -- 1.3.6.1.4.1.2011.2.25.3.40.50.283.30.1.1
        laser_lanePer24HCurEid OBJECT-TYPE
            SYNTAX PerformanceEventType
            MAX-ACCESS read-only
            STATUS current
            DESCRIPTION
                "perEid."
            ::= { laser_lanePer24HCurEntry 1 }

        -- 1.3.6.1.4.1.2011.2.25.3.40.50.283.30.1.2
        laser_lanePer24HCurMonValue OBJECT-TYPE
            SYNTAX OCTET STRING (SIZE (0..100))
            MAX-ACCESS read-only
            STATUS current
            DESCRIPTION
                "perMonValue."
            ::= { laser_lanePer24HCurEntry 2 }

        -- 1.3.6.1.4.1.2011.2.25.3.40.50.283.30.1.3
        laser_lanePer24HCurVldty OBJECT-TYPE
            SYNTAX INTEGER
            MAX-ACCESS read-only
            STATUS current
            DESCRIPTION
                "perVldty. "
            ::= { laser_lanePer24HCurEntry 3 }

        -- 1.3.6.1.4.1.2011.2.25.3.40.50.283.30.1.4
        laser_lanePer24HCurDateTime OBJECT-TYPE
            SYNTAX DateAndTime
            MAX-ACCESS read-only
            STATUS current
            DESCRIPTION
                "perDateTime. "
            ::= { laser_lanePer24HCurEntry 4 }

        -- 1.3.6.1.4.1.2011.2.25.3.40.50.283.30.1.5
        laser_lanePer24HCurParaLen OBJECT-TYPE
            SYNTAX INTEGER
            MAX-ACCESS read-only
            STATUS current
            DESCRIPTION
                "perParaLen."
            ::= { laser_lanePer24HCurEntry 5 }

        -- 1.3.6.1.4.1.2011.2.25.3.40.50.283.30.1.6
        laser_lanePer24HCurPara OBJECT-TYPE
            SYNTAX OCTET STRING (SIZE (0..100))
            MAX-ACCESS read-only
            STATUS current
            DESCRIPTION
                "perPara."
            ::= { laser_lanePer24HCurEntry 6 }


-- -------------------------------------------------------------------------
-- Perfomance 24-HOUR History Data Table (RTRV-PER-<MOD2>)
-- -------------------------------------------------------------------------
        -- 1.3.6.1.4.1.2011.2.25.3.40.50.283.40
        laser_lanePer24HHisTable OBJECT-TYPE
            SYNTAX SEQUENCE OF Laser_lanePer24HHisEntry
            MAX-ACCESS not-accessible
            STATUS current
            DESCRIPTION
                "laser_lanePer24HHis."
            ::= { laser_lane 40 }

        -- 1.3.6.1.4.1.2011.2.25.3.40.50.283.40.1
        laser_lanePer24HHisEntry OBJECT-TYPE
            SYNTAX Laser_lanePer24HHisEntry
            MAX-ACCESS not-accessible
            STATUS current
            DESCRIPTION
                "laser_lanePer24HHis."
            INDEX {laser_lanePer24HHisEid, laser_lanePer24HHisParaLen, laser_lanePer24HHisPara, laser_lanePer24HHisDateTimeStart, laser_lanePer24HHisDateTimeEnd}
            ::= { laser_lanePer24HHisTable 1 }

        Laser_lanePer24HHisEntry ::=
            SEQUENCE {
                laser_lanePer24HHisEid
                    PerformanceEventType,
                laser_lanePer24HHisParaLen
                    INTEGER,
                laser_lanePer24HHisPara
                    OCTET STRING,
                laser_lanePer24HHisMonValue
                    OCTET STRING,
                laser_lanePer24HHisDateTimeStart
                    DateAndTime,
                laser_lanePer24HHisDateTimeEnd
                    DateAndTime,
                laser_lanePer24HHisVldty
                    INTEGER,
             }

        -- 1.3.6.1.4.1.2011.2.25.3.40.50.283.40.1.1
        laser_lanePer24HHisEid OBJECT-TYPE
            SYNTAX PerformanceEventType
            MAX-ACCESS read-only
            STATUS current
            DESCRIPTION
                "perEid."
            ::= { laser_lanePer24HHisEntry 1 }

        -- 1.3.6.1.4.1.2011.2.25.3.40.50.283.40.1.2
        laser_lanePer24HHisParaLen OBJECT-TYPE
            SYNTAX INTEGER
            MAX-ACCESS read-only
            STATUS current
            DESCRIPTION
                "perParaLen."
            ::= { laser_lanePer24HHisEntry 2 }

        -- 1.3.6.1.4.1.2011.2.25.3.40.50.283.40.1.3
        laser_lanePer24HHisPara OBJECT-TYPE
            SYNTAX OCTET STRING (SIZE (0..100))
            MAX-ACCESS read-only
            STATUS current
            DESCRIPTION
                "perPara."
            ::= { laser_lanePer24HHisEntry 3 }


        -- 1.3.6.1.4.1.2011.2.25.3.40.50.283.40.1.4
        laser_lanePer24HHisMonValue OBJECT-TYPE
            SYNTAX OCTET STRING (SIZE (0..100))
            MAX-ACCESS read-only
            STATUS current
            DESCRIPTION
                "perMonValue."
            ::= { laser_lanePer24HHisEntry 4 }


        -- 1.3.6.1.4.1.2011.2.25.3.40.50.283.40.1.5
        laser_lanePer24HHisDateTimeStart OBJECT-TYPE
            SYNTAX DateAndTime
            MAX-ACCESS read-only
            STATUS current
            DESCRIPTION
                "perDateTimeStart. "
            ::= { laser_lanePer24HHisEntry 5 }

        -- 1.3.6.1.4.1.2011.2.25.3.40.50.283.40.1.6
        laser_lanePer24HHisDateTimeEnd OBJECT-TYPE
            SYNTAX DateAndTime
            MAX-ACCESS read-only
            STATUS current
            DESCRIPTION
                "perDateTimeEnd. "
            ::= { laser_lanePer24HHisEntry 6 }

        -- 1.3.6.1.4.1.2011.2.25.3.40.50.283.40.1.7
        laser_lanePer24HHisVldty OBJECT-TYPE
            SYNTAX INTEGER
            MAX-ACCESS read-only
            STATUS current
            DESCRIPTION
                "perVldty. "
            ::= { laser_lanePer24HHisEntry 7 }








-- -------------------------------------------------------------------------
-- Perfomance 15-MIN Current Data Table (RTRV-PER-<MOD2>)
-- -------------------------------------------------------------------------



-- Alarm data



-- Alarm data
      -- 1.3.6.1.4.1.2011.2.25.3.40.50.289
      oducn_tcm6 OBJECT IDENTIFIER ::={ optixGlobalNGWDM 289 }


-- -------------------------------------------------------------------------
-- Perfomance 15-MIN Current Data Table (RTRV-PER-<MOD2>)
-- -------------------------------------------------------------------------
        -- 1.3.6.1.4.1.2011.2.25.3.40.50.289.10
        oducn_tcm6Per15MCurTable OBJECT-TYPE
            SYNTAX SEQUENCE OF Oducn_tcm6Per15MCurEntry
            MAX-ACCESS not-accessible
            STATUS current
            DESCRIPTION
                "oducn_tcm6Per15MCur."
            ::= { oducn_tcm6 10 }

        -- 1.3.6.1.4.1.2011.2.25.3.40.50.289.10.1
        oducn_tcm6Per15MCurEntry OBJECT-TYPE
            SYNTAX Oducn_tcm6Per15MCurEntry
            MAX-ACCESS not-accessible
            STATUS current
            DESCRIPTION
              "oducn_tcm6Per15MCur."
            INDEX { oducn_tcm6Per15MCurEid, oducn_tcm6Per15MCurPara }
            ::= { oducn_tcm6Per15MCurTable 1 }

        Oducn_tcm6Per15MCurEntry ::=
            SEQUENCE {
                oducn_tcm6Per15MCurEid
                    PerformanceEventType,
                oducn_tcm6Per15MCurMonValue
                    OCTET STRING,
                oducn_tcm6Per15MCurVldty
                    INTEGER,
                oducn_tcm6Per15MCurDateTime
                    DateAndTime,
                oducn_tcm6Per15MCurParaLen
                    INTEGER,
                oducn_tcm6Per15MCurPara
                    OCTET STRING
            }

        -- 1.3.6.1.4.1.2011.2.25.3.40.50.289.10.1.1
        oducn_tcm6Per15MCurEid OBJECT-TYPE
            SYNTAX PerformanceEventType
            MAX-ACCESS read-only
            STATUS current
            DESCRIPTION
                "perEid."
            ::= { oducn_tcm6Per15MCurEntry 1 }

        -- 1.3.6.1.4.1.2011.2.25.3.40.50.289.10.1.2
        oducn_tcm6Per15MCurMonValue OBJECT-TYPE
            SYNTAX OCTET STRING (SIZE (0..100))
            MAX-ACCESS read-only
            STATUS current
            DESCRIPTION
                "perMonValue."
            ::= { oducn_tcm6Per15MCurEntry 2 }

        -- 1.3.6.1.4.1.2011.2.25.3.40.50.289.10.1.3
        oducn_tcm6Per15MCurVldty OBJECT-TYPE
            SYNTAX INTEGER
            MAX-ACCESS read-only
            STATUS current
            DESCRIPTION
                "perVldty. "
            ::= { oducn_tcm6Per15MCurEntry 3 }

        -- 1.3.6.1.4.1.2011.2.25.3.40.50.289.10.1.4
        oducn_tcm6Per15MCurDateTime OBJECT-TYPE
            SYNTAX DateAndTime
            MAX-ACCESS read-only
            STATUS current
            DESCRIPTION
                "perDateTime. "
            ::= { oducn_tcm6Per15MCurEntry 4 }

        -- 1.3.6.1.4.1.2011.2.25.3.40.50.289.10.1.5
        oducn_tcm6Per15MCurParaLen OBJECT-TYPE
            SYNTAX INTEGER
            MAX-ACCESS read-only
            STATUS current
            DESCRIPTION
                "perParaLen."
            ::= { oducn_tcm6Per15MCurEntry 5 }

        -- 1.3.6.1.4.1.2011.2.25.3.40.50.289.10.1.6
        oducn_tcm6Per15MCurPara OBJECT-TYPE
            SYNTAX OCTET STRING (SIZE (0..100))
            MAX-ACCESS read-only
            STATUS current
            DESCRIPTION
                "perPara."
            ::= { oducn_tcm6Per15MCurEntry 6 }



-- -------------------------------------------------------------------------
-- Perfomance 15-MIN History Data Table (RTRV-PER-<MOD2>)
-- -------------------------------------------------------------------------
        -- 1.3.6.1.4.1.2011.2.25.3.40.50.289.20
        oducn_tcm6Per15MHisTable OBJECT-TYPE
            SYNTAX SEQUENCE OF Oducn_tcm6Per15MHisEntry
            MAX-ACCESS not-accessible
            STATUS current
            DESCRIPTION
                "oducn_tcm6Per15MHis."
            ::= { oducn_tcm6 20 }

        -- 1.3.6.1.4.1.2011.2.25.3.40.50.289.20.1
        oducn_tcm6Per15MHisEntry OBJECT-TYPE
            SYNTAX Oducn_tcm6Per15MHisEntry
            MAX-ACCESS not-accessible
            STATUS current
            DESCRIPTION
                "oducn_tcm6Per15MHis."
            INDEX {oducn_tcm6Per15MHisEid, oducn_tcm6Per15MHisParaLen, oducn_tcm6Per15MHisPara, oducn_tcm6Per15MHisDateTimeStart, oducn_tcm6Per15MHisDateTimeEnd}
            ::= { oducn_tcm6Per15MHisTable 1 }

        Oducn_tcm6Per15MHisEntry ::=
            SEQUENCE {
                oducn_tcm6Per15MHisEid
                    PerformanceEventType,
                oducn_tcm6Per15MHisParaLen
                    INTEGER,
                oducn_tcm6Per15MHisPara
                    OCTET STRING,
                oducn_tcm6Per15MHisMonValue
                    OCTET STRING,
                oducn_tcm6Per15MHisDateTimeStart
                    DateAndTime,
                oducn_tcm6Per15MHisDateTimeEnd
                    DateAndTime,
                oducn_tcm6Per15MHisVldty
                    INTEGER,
             }

        -- 1.3.6.1.4.1.2011.2.25.3.40.50.289.20.1.1
        oducn_tcm6Per15MHisEid OBJECT-TYPE
            SYNTAX PerformanceEventType
            MAX-ACCESS read-only
            STATUS current
            DESCRIPTION
                "perEid."
            ::= { oducn_tcm6Per15MHisEntry 1 }

        -- 1.3.6.1.4.1.2011.2.25.3.40.50.289.20.1.2
        oducn_tcm6Per15MHisParaLen OBJECT-TYPE
            SYNTAX INTEGER
            MAX-ACCESS read-only
            STATUS current
            DESCRIPTION
                "perParaLen."
            ::= { oducn_tcm6Per15MHisEntry 2 }

        -- 1.3.6.1.4.1.2011.2.25.3.40.50.289.20.1.3
        oducn_tcm6Per15MHisPara OBJECT-TYPE
            SYNTAX OCTET STRING (SIZE (0..100))
            MAX-ACCESS read-only
            STATUS current
            DESCRIPTION
                "perPara."
            ::= { oducn_tcm6Per15MHisEntry 3 }

        -- 1.3.6.1.4.1.2011.2.25.3.40.50.289.20.1.4
        oducn_tcm6Per15MHisMonValue OBJECT-TYPE
            SYNTAX OCTET STRING (SIZE (0..100))
            MAX-ACCESS read-only
            STATUS current
            DESCRIPTION
                "perMonValue."
            ::= { oducn_tcm6Per15MHisEntry 4 }

        -- 1.3.6.1.4.1.2011.2.25.3.40.50.289.20.1.5
        oducn_tcm6Per15MHisDateTimeStart OBJECT-TYPE
            SYNTAX DateAndTime
            MAX-ACCESS read-only
            STATUS current
            DESCRIPTION
                "perDateTimeStart. "
            ::= { oducn_tcm6Per15MHisEntry 5 }

        -- 1.3.6.1.4.1.2011.2.25.3.40.50.289.20.1.6
        oducn_tcm6Per15MHisDateTimeEnd OBJECT-TYPE
            SYNTAX DateAndTime
            MAX-ACCESS read-only
            STATUS current
            DESCRIPTION
                "perDateTimeEnd. "
            ::= { oducn_tcm6Per15MHisEntry 6 }

        -- 1.3.6.1.4.1.2011.2.25.3.40.50.289.20.1.7
        oducn_tcm6Per15MHisVldty OBJECT-TYPE
            SYNTAX INTEGER
            MAX-ACCESS read-only
            STATUS current
            DESCRIPTION
                "perVldty. "
            ::= { oducn_tcm6Per15MHisEntry 7 }




-- -------------------------------------------------------------------------
-- Perfomance 24-HOUR Current Data Table (RTRV-PER-<MOD2>)
-- -------------------------------------------------------------------------
        -- 1.3.6.1.4.1.2011.2.25.3.40.50.289.30
        oducn_tcm6Per24HCurTable OBJECT-TYPE
          SYNTAX SEQUENCE OF Oducn_tcm6Per24HCurEntry
          MAX-ACCESS not-accessible
          STATUS current
          DESCRIPTION
              "oducn_tcm6Per24HCur."
          ::= { oducn_tcm6 30 }

        -- 1.3.6.1.4.1.2011.2.25.3.40.50.289.30.1
        oducn_tcm6Per24HCurEntry OBJECT-TYPE
            SYNTAX Oducn_tcm6Per24HCurEntry
            MAX-ACCESS not-accessible
            STATUS current
            DESCRIPTION
              "oducn_tcm6Per24HCur."
            INDEX { oducn_tcm6Per24HCurEid, oducn_tcm6Per24HCurPara }
            ::= { oducn_tcm6Per24HCurTable 1 }

        Oducn_tcm6Per24HCurEntry ::=
            SEQUENCE {
                oducn_tcm6Per24HCurEid
                    PerformanceEventType,
                oducn_tcm6Per24HCurMonValue
                    OCTET STRING,
                oducn_tcm6Per24HCurVldty
                    INTEGER,
                oducn_tcm6Per24HCurDateTime
                    DateAndTime,
                oducn_tcm6Per24HCurParaLen
                    INTEGER,
                oducn_tcm6Per24HCurPara
                    OCTET STRING
            }

        -- 1.3.6.1.4.1.2011.2.25.3.40.50.289.30.1.1
        oducn_tcm6Per24HCurEid OBJECT-TYPE
            SYNTAX PerformanceEventType
            MAX-ACCESS read-only
            STATUS current
            DESCRIPTION
                "perEid."
            ::= { oducn_tcm6Per24HCurEntry 1 }

        -- 1.3.6.1.4.1.2011.2.25.3.40.50.289.30.1.2
        oducn_tcm6Per24HCurMonValue OBJECT-TYPE
            SYNTAX OCTET STRING (SIZE (0..100))
            MAX-ACCESS read-only
            STATUS current
            DESCRIPTION
                "perMonValue."
            ::= { oducn_tcm6Per24HCurEntry 2 }

        -- 1.3.6.1.4.1.2011.2.25.3.40.50.289.30.1.3
        oducn_tcm6Per24HCurVldty OBJECT-TYPE
            SYNTAX INTEGER
            MAX-ACCESS read-only
            STATUS current
            DESCRIPTION
                "perVldty. "
            ::= { oducn_tcm6Per24HCurEntry 3 }

        -- 1.3.6.1.4.1.2011.2.25.3.40.50.289.30.1.4
        oducn_tcm6Per24HCurDateTime OBJECT-TYPE
            SYNTAX DateAndTime
            MAX-ACCESS read-only
            STATUS current
            DESCRIPTION
                "perDateTime. "
            ::= { oducn_tcm6Per24HCurEntry 4 }

        -- 1.3.6.1.4.1.2011.2.25.3.40.50.289.30.1.5
        oducn_tcm6Per24HCurParaLen OBJECT-TYPE
            SYNTAX INTEGER
            MAX-ACCESS read-only
            STATUS current
            DESCRIPTION
                "perParaLen."
            ::= { oducn_tcm6Per24HCurEntry 5 }

        -- 1.3.6.1.4.1.2011.2.25.3.40.50.289.30.1.6
        oducn_tcm6Per24HCurPara OBJECT-TYPE
            SYNTAX OCTET STRING (SIZE (0..100))
            MAX-ACCESS read-only
            STATUS current
            DESCRIPTION
                "perPara."
            ::= { oducn_tcm6Per24HCurEntry 6 }




-- -------------------------------------------------------------------------
-- Perfomance 24-HOUR History Data Table (RTRV-PER-<MOD2>)
-- -------------------------------------------------------------------------
        -- 1.3.6.1.4.1.2011.2.25.3.40.50.289.40
        oducn_tcm6Per24HHisTable OBJECT-TYPE
          SYNTAX SEQUENCE OF Oducn_tcm6Per24HHisEntry
          MAX-ACCESS not-accessible
          STATUS current
          DESCRIPTION
              "oducn_tcm6Per24HHis."
          ::= { oducn_tcm6 40 }

        -- 1.3.6.1.4.1.2011.2.25.3.40.50.289.40.1
        oducn_tcm6Per24HHisEntry OBJECT-TYPE
            SYNTAX Oducn_tcm6Per24HHisEntry
            MAX-ACCESS not-accessible
            STATUS current
            DESCRIPTION
                "oducn_tcm6Per24HHis."
            INDEX {oducn_tcm6Per24HHisEid, oducn_tcm6Per24HHisParaLen, oducn_tcm6Per24HHisPara, oducn_tcm6Per24HHisDateTimeStart, oducn_tcm6Per24HHisDateTimeEnd}
            ::= { oducn_tcm6Per24HHisTable 1 }

        Oducn_tcm6Per24HHisEntry ::=
            SEQUENCE {
                oducn_tcm6Per24HHisEid
                    PerformanceEventType,
                oducn_tcm6Per24HHisParaLen
                    INTEGER,
                oducn_tcm6Per24HHisPara
                    OCTET STRING,
                oducn_tcm6Per24HHisMonValue
                    OCTET STRING,
                oducn_tcm6Per24HHisDateTimeStart
                    DateAndTime,
                oducn_tcm6Per24HHisDateTimeEnd
                    DateAndTime,
                oducn_tcm6Per24HHisVldty
                    INTEGER,
             }

        -- 1.3.6.1.4.1.2011.2.25.3.40.50.289.40.1.1
        oducn_tcm6Per24HHisEid OBJECT-TYPE
            SYNTAX PerformanceEventType
            MAX-ACCESS read-only
            STATUS current
            DESCRIPTION
                "perEid."
            ::= { oducn_tcm6Per24HHisEntry 1 }

        -- 1.3.6.1.4.1.2011.2.25.3.40.50.289.40.1.2
        oducn_tcm6Per24HHisParaLen OBJECT-TYPE
            SYNTAX INTEGER
            MAX-ACCESS read-only
            STATUS current
            DESCRIPTION
                "perParaLen."
            ::= { oducn_tcm6Per24HHisEntry 2 }

        -- 1.3.6.1.4.1.2011.2.25.3.40.50.289.40.1.3
        oducn_tcm6Per24HHisPara OBJECT-TYPE
            SYNTAX OCTET STRING (SIZE (0..100))
            MAX-ACCESS read-only
            STATUS current
            DESCRIPTION
                "perPara."
            ::= { oducn_tcm6Per24HHisEntry 3 }

        -- 1.3.6.1.4.1.2011.2.25.3.40.50.289.40.1.4
        oducn_tcm6Per24HHisMonValue OBJECT-TYPE
            SYNTAX OCTET STRING (SIZE (0..100))
            MAX-ACCESS read-only
            STATUS current
            DESCRIPTION
                "perMonValue."
            ::= { oducn_tcm6Per24HHisEntry 4 }

        -- 1.3.6.1.4.1.2011.2.25.3.40.50.289.40.1.5
        oducn_tcm6Per24HHisDateTimeStart OBJECT-TYPE
            SYNTAX DateAndTime
            MAX-ACCESS read-only
            STATUS current
            DESCRIPTION
                "perDateTimeStart. "
            ::= { oducn_tcm6Per24HHisEntry 5 }

        -- 1.3.6.1.4.1.2011.2.25.3.40.50.289.40.1.6
        oducn_tcm6Per24HHisDateTimeEnd OBJECT-TYPE
            SYNTAX DateAndTime
            MAX-ACCESS read-only
            STATUS current
            DESCRIPTION
                "perDateTimeEnd. "
            ::= { oducn_tcm6Per24HHisEntry 6 }

        -- 1.3.6.1.4.1.2011.2.25.3.40.50.289.40.1.7
        oducn_tcm6Per24HHisVldty OBJECT-TYPE
            SYNTAX INTEGER
            MAX-ACCESS read-only
            STATUS current
            DESCRIPTION
                "perVldty. "
            ::= { oducn_tcm6Per24HHisEntry 7 }


-- Alarm data
      -- 1.3.6.1.4.1.2011.2.25.3.40.50.290
      oducn_tcm1 OBJECT IDENTIFIER ::={ optixGlobalNGWDM 290 }


-- -------------------------------------------------------------------------
-- Perfomance 15-MIN Current Data Table (RTRV-PER-<MOD2>)
-- -------------------------------------------------------------------------
        -- 1.3.6.1.4.1.2011.2.25.3.40.50.290.10
        oducn_tcm1Per15MCurTable OBJECT-TYPE
            SYNTAX SEQUENCE OF Oducn_tcm1Per15MCurEntry
            MAX-ACCESS not-accessible
            STATUS current
            DESCRIPTION
                "oducn_tcm1Per15MCur."
            ::= { oducn_tcm1 10 }

        -- 1.3.6.1.4.1.2011.2.25.3.40.50.290.10.1
        oducn_tcm1Per15MCurEntry OBJECT-TYPE
            SYNTAX Oducn_tcm1Per15MCurEntry
            MAX-ACCESS not-accessible
            STATUS current
            DESCRIPTION
              "oducn_tcm1Per15MCur."
            INDEX { oducn_tcm1Per15MCurEid, oducn_tcm1Per15MCurPara }
            ::= { oducn_tcm1Per15MCurTable 1 }

        Oducn_tcm1Per15MCurEntry ::=
            SEQUENCE {
                oducn_tcm1Per15MCurEid
                    PerformanceEventType,
                oducn_tcm1Per15MCurMonValue
                    OCTET STRING,
                oducn_tcm1Per15MCurVldty
                    INTEGER,
                oducn_tcm1Per15MCurDateTime
                    DateAndTime,
                oducn_tcm1Per15MCurParaLen
                    INTEGER,
                oducn_tcm1Per15MCurPara
                    OCTET STRING
            }

        -- 1.3.6.1.4.1.2011.2.25.3.40.50.290.10.1.1
        oducn_tcm1Per15MCurEid OBJECT-TYPE
            SYNTAX PerformanceEventType
            MAX-ACCESS read-only
            STATUS current
            DESCRIPTION
                "perEid."
            ::= { oducn_tcm1Per15MCurEntry 1 }

        -- 1.3.6.1.4.1.2011.2.25.3.40.50.290.10.1.2
        oducn_tcm1Per15MCurMonValue OBJECT-TYPE
            SYNTAX OCTET STRING (SIZE (0..100))
            MAX-ACCESS read-only
            STATUS current
            DESCRIPTION
                "perMonValue."
            ::= { oducn_tcm1Per15MCurEntry 2 }

        -- 1.3.6.1.4.1.2011.2.25.3.40.50.290.10.1.3
        oducn_tcm1Per15MCurVldty OBJECT-TYPE
            SYNTAX INTEGER
            MAX-ACCESS read-only
            STATUS current
            DESCRIPTION
                "perVldty. "
            ::= { oducn_tcm1Per15MCurEntry 3 }

        -- 1.3.6.1.4.1.2011.2.25.3.40.50.290.10.1.4
        oducn_tcm1Per15MCurDateTime OBJECT-TYPE
            SYNTAX DateAndTime
            MAX-ACCESS read-only
            STATUS current
            DESCRIPTION
                "perDateTime. "
            ::= { oducn_tcm1Per15MCurEntry 4 }

        -- 1.3.6.1.4.1.2011.2.25.3.40.50.290.10.1.5
        oducn_tcm1Per15MCurParaLen OBJECT-TYPE
            SYNTAX INTEGER
            MAX-ACCESS read-only
            STATUS current
            DESCRIPTION
                "perParaLen."
            ::= { oducn_tcm1Per15MCurEntry 5 }

        -- 1.3.6.1.4.1.2011.2.25.3.40.50.290.10.1.6
        oducn_tcm1Per15MCurPara OBJECT-TYPE
            SYNTAX OCTET STRING (SIZE (0..100))
            MAX-ACCESS read-only
            STATUS current
            DESCRIPTION
                "perPara."
            ::= { oducn_tcm1Per15MCurEntry 6 }



-- -------------------------------------------------------------------------
-- Perfomance 15-MIN History Data Table (RTRV-PER-<MOD2>)
-- -------------------------------------------------------------------------
        -- 1.3.6.1.4.1.2011.2.25.3.40.50.290.20
        oducn_tcm1Per15MHisTable OBJECT-TYPE
            SYNTAX SEQUENCE OF Oducn_tcm1Per15MHisEntry
            MAX-ACCESS not-accessible
            STATUS current
            DESCRIPTION
                "oducn_tcm1Per15MHis."
            ::= { oducn_tcm1 20 }

        -- 1.3.6.1.4.1.2011.2.25.3.40.50.290.20.1
        oducn_tcm1Per15MHisEntry OBJECT-TYPE
            SYNTAX Oducn_tcm1Per15MHisEntry
            MAX-ACCESS not-accessible
            STATUS current
            DESCRIPTION
                "oducn_tcm1Per15MHis."
            INDEX {oducn_tcm1Per15MHisEid, oducn_tcm1Per15MHisParaLen, oducn_tcm1Per15MHisPara, oducn_tcm1Per15MHisDateTimeStart, oducn_tcm1Per15MHisDateTimeEnd}
            ::= { oducn_tcm1Per15MHisTable 1 }

        Oducn_tcm1Per15MHisEntry ::=
            SEQUENCE {
                oducn_tcm1Per15MHisEid
                    PerformanceEventType,
                oducn_tcm1Per15MHisParaLen
                    INTEGER,
                oducn_tcm1Per15MHisPara
                    OCTET STRING,
                oducn_tcm1Per15MHisMonValue
                    OCTET STRING,
                oducn_tcm1Per15MHisDateTimeStart
                    DateAndTime,
                oducn_tcm1Per15MHisDateTimeEnd
                    DateAndTime,
                oducn_tcm1Per15MHisVldty
                    INTEGER,
             }

        -- 1.3.6.1.4.1.2011.2.25.3.40.50.290.20.1.1
        oducn_tcm1Per15MHisEid OBJECT-TYPE
            SYNTAX PerformanceEventType
            MAX-ACCESS read-only
            STATUS current
            DESCRIPTION
                "perEid."
            ::= { oducn_tcm1Per15MHisEntry 1 }

        -- 1.3.6.1.4.1.2011.2.25.3.40.50.290.20.1.2
        oducn_tcm1Per15MHisParaLen OBJECT-TYPE
            SYNTAX INTEGER
            MAX-ACCESS read-only
            STATUS current
            DESCRIPTION
                "perParaLen."
            ::= { oducn_tcm1Per15MHisEntry 2 }

        -- 1.3.6.1.4.1.2011.2.25.3.40.50.290.20.1.3
        oducn_tcm1Per15MHisPara OBJECT-TYPE
            SYNTAX OCTET STRING (SIZE (0..100))
            MAX-ACCESS read-only
            STATUS current
            DESCRIPTION
                "perPara."
            ::= { oducn_tcm1Per15MHisEntry 3 }

        -- 1.3.6.1.4.1.2011.2.25.3.40.50.290.20.1.4
        oducn_tcm1Per15MHisMonValue OBJECT-TYPE
            SYNTAX OCTET STRING (SIZE (0..100))
            MAX-ACCESS read-only
            STATUS current
            DESCRIPTION
                "perMonValue."
            ::= { oducn_tcm1Per15MHisEntry 4 }

        -- 1.3.6.1.4.1.2011.2.25.3.40.50.290.20.1.5
        oducn_tcm1Per15MHisDateTimeStart OBJECT-TYPE
            SYNTAX DateAndTime
            MAX-ACCESS read-only
            STATUS current
            DESCRIPTION
                "perDateTimeStart. "
            ::= { oducn_tcm1Per15MHisEntry 5 }

        -- 1.3.6.1.4.1.2011.2.25.3.40.50.290.20.1.6
        oducn_tcm1Per15MHisDateTimeEnd OBJECT-TYPE
            SYNTAX DateAndTime
            MAX-ACCESS read-only
            STATUS current
            DESCRIPTION
                "perDateTimeEnd. "
            ::= { oducn_tcm1Per15MHisEntry 6 }

        -- 1.3.6.1.4.1.2011.2.25.3.40.50.290.20.1.7
        oducn_tcm1Per15MHisVldty OBJECT-TYPE
            SYNTAX INTEGER
            MAX-ACCESS read-only
            STATUS current
            DESCRIPTION
                "perVldty. "
            ::= { oducn_tcm1Per15MHisEntry 7 }




-- -------------------------------------------------------------------------
-- Perfomance 24-HOUR Current Data Table (RTRV-PER-<MOD2>)
-- -------------------------------------------------------------------------
        -- 1.3.6.1.4.1.2011.2.25.3.40.50.290.30
        oducn_tcm1Per24HCurTable OBJECT-TYPE
          SYNTAX SEQUENCE OF Oducn_tcm1Per24HCurEntry
          MAX-ACCESS not-accessible
          STATUS current
          DESCRIPTION
              "oducn_tcm1Per24HCur."
          ::= { oducn_tcm1 30 }

        -- 1.3.6.1.4.1.2011.2.25.3.40.50.290.30.1
        oducn_tcm1Per24HCurEntry OBJECT-TYPE
            SYNTAX Oducn_tcm1Per24HCurEntry
            MAX-ACCESS not-accessible
            STATUS current
            DESCRIPTION
              "oducn_tcm1Per24HCur."
            INDEX { oducn_tcm1Per24HCurEid, oducn_tcm1Per24HCurPara }
            ::= { oducn_tcm1Per24HCurTable 1 }

        Oducn_tcm1Per24HCurEntry ::=
            SEQUENCE {
                oducn_tcm1Per24HCurEid
                    PerformanceEventType,
                oducn_tcm1Per24HCurMonValue
                    OCTET STRING,
                oducn_tcm1Per24HCurVldty
                    INTEGER,
                oducn_tcm1Per24HCurDateTime
                    DateAndTime,
                oducn_tcm1Per24HCurParaLen
                    INTEGER,
                oducn_tcm1Per24HCurPara
                    OCTET STRING
            }

        -- 1.3.6.1.4.1.2011.2.25.3.40.50.290.30.1.1
        oducn_tcm1Per24HCurEid OBJECT-TYPE
            SYNTAX PerformanceEventType
            MAX-ACCESS read-only
            STATUS current
            DESCRIPTION
                "perEid."
            ::= { oducn_tcm1Per24HCurEntry 1 }

        -- 1.3.6.1.4.1.2011.2.25.3.40.50.290.30.1.2
        oducn_tcm1Per24HCurMonValue OBJECT-TYPE
            SYNTAX OCTET STRING (SIZE (0..100))
            MAX-ACCESS read-only
            STATUS current
            DESCRIPTION
                "perMonValue."
            ::= { oducn_tcm1Per24HCurEntry 2 }

        -- 1.3.6.1.4.1.2011.2.25.3.40.50.290.30.1.3
        oducn_tcm1Per24HCurVldty OBJECT-TYPE
            SYNTAX INTEGER
            MAX-ACCESS read-only
            STATUS current
            DESCRIPTION
                "perVldty. "
            ::= { oducn_tcm1Per24HCurEntry 3 }

        -- 1.3.6.1.4.1.2011.2.25.3.40.50.290.30.1.4
        oducn_tcm1Per24HCurDateTime OBJECT-TYPE
            SYNTAX DateAndTime
            MAX-ACCESS read-only
            STATUS current
            DESCRIPTION
                "perDateTime. "
            ::= { oducn_tcm1Per24HCurEntry 4 }

        -- 1.3.6.1.4.1.2011.2.25.3.40.50.290.30.1.5
        oducn_tcm1Per24HCurParaLen OBJECT-TYPE
            SYNTAX INTEGER
            MAX-ACCESS read-only
            STATUS current
            DESCRIPTION
                "perParaLen."
            ::= { oducn_tcm1Per24HCurEntry 5 }

        -- 1.3.6.1.4.1.2011.2.25.3.40.50.290.30.1.6
        oducn_tcm1Per24HCurPara OBJECT-TYPE
            SYNTAX OCTET STRING (SIZE (0..100))
            MAX-ACCESS read-only
            STATUS current
            DESCRIPTION
                "perPara."
            ::= { oducn_tcm1Per24HCurEntry 6 }




-- -------------------------------------------------------------------------
-- Perfomance 24-HOUR History Data Table (RTRV-PER-<MOD2>)
-- -------------------------------------------------------------------------
        -- 1.3.6.1.4.1.2011.2.25.3.40.50.290.40
        oducn_tcm1Per24HHisTable OBJECT-TYPE
          SYNTAX SEQUENCE OF Oducn_tcm1Per24HHisEntry
          MAX-ACCESS not-accessible
          STATUS current
          DESCRIPTION
              "oducn_tcm1Per24HHis."
          ::= { oducn_tcm1 40 }

        -- 1.3.6.1.4.1.2011.2.25.3.40.50.290.40.1
        oducn_tcm1Per24HHisEntry OBJECT-TYPE
            SYNTAX Oducn_tcm1Per24HHisEntry
            MAX-ACCESS not-accessible
            STATUS current
            DESCRIPTION
                "oducn_tcm1Per24HHis."
            INDEX {oducn_tcm1Per24HHisEid, oducn_tcm1Per24HHisParaLen, oducn_tcm1Per24HHisPara, oducn_tcm1Per24HHisDateTimeStart, oducn_tcm1Per24HHisDateTimeEnd}
            ::= { oducn_tcm1Per24HHisTable 1 }

        Oducn_tcm1Per24HHisEntry ::=
            SEQUENCE {
                oducn_tcm1Per24HHisEid
                    PerformanceEventType,
                oducn_tcm1Per24HHisParaLen
                    INTEGER,
                oducn_tcm1Per24HHisPara
                    OCTET STRING,
                oducn_tcm1Per24HHisMonValue
                    OCTET STRING,
                oducn_tcm1Per24HHisDateTimeStart
                    DateAndTime,
                oducn_tcm1Per24HHisDateTimeEnd
                    DateAndTime,
                oducn_tcm1Per24HHisVldty
                    INTEGER,
             }

        -- 1.3.6.1.4.1.2011.2.25.3.40.50.290.40.1.1
        oducn_tcm1Per24HHisEid OBJECT-TYPE
            SYNTAX PerformanceEventType
            MAX-ACCESS read-only
            STATUS current
            DESCRIPTION
                "perEid."
            ::= { oducn_tcm1Per24HHisEntry 1 }

        -- 1.3.6.1.4.1.2011.2.25.3.40.50.290.40.1.2
        oducn_tcm1Per24HHisParaLen OBJECT-TYPE
            SYNTAX INTEGER
            MAX-ACCESS read-only
            STATUS current
            DESCRIPTION
                "perParaLen."
            ::= { oducn_tcm1Per24HHisEntry 2 }

        -- 1.3.6.1.4.1.2011.2.25.3.40.50.290.40.1.3
        oducn_tcm1Per24HHisPara OBJECT-TYPE
            SYNTAX OCTET STRING (SIZE (0..100))
            MAX-ACCESS read-only
            STATUS current
            DESCRIPTION
                "perPara."
            ::= { oducn_tcm1Per24HHisEntry 3 }

        -- 1.3.6.1.4.1.2011.2.25.3.40.50.290.40.1.4
        oducn_tcm1Per24HHisMonValue OBJECT-TYPE
            SYNTAX OCTET STRING (SIZE (0..100))
            MAX-ACCESS read-only
            STATUS current
            DESCRIPTION
                "perMonValue."
            ::= { oducn_tcm1Per24HHisEntry 4 }

        -- 1.3.6.1.4.1.2011.2.25.3.40.50.290.40.1.5
        oducn_tcm1Per24HHisDateTimeStart OBJECT-TYPE
            SYNTAX DateAndTime
            MAX-ACCESS read-only
            STATUS current
            DESCRIPTION
                "perDateTimeStart. "
            ::= { oducn_tcm1Per24HHisEntry 5 }

        -- 1.3.6.1.4.1.2011.2.25.3.40.50.290.40.1.6
        oducn_tcm1Per24HHisDateTimeEnd OBJECT-TYPE
            SYNTAX DateAndTime
            MAX-ACCESS read-only
            STATUS current
            DESCRIPTION
                "perDateTimeEnd. "
            ::= { oducn_tcm1Per24HHisEntry 6 }

        -- 1.3.6.1.4.1.2011.2.25.3.40.50.290.40.1.7
        oducn_tcm1Per24HHisVldty OBJECT-TYPE
            SYNTAX INTEGER
            MAX-ACCESS read-only
            STATUS current
            DESCRIPTION
                "perVldty. "
            ::= { oducn_tcm1Per24HHisEntry 7 }


-- Alarm data
      -- 1.3.6.1.4.1.2011.2.25.3.40.50.291
      oducn_tcm2 OBJECT IDENTIFIER ::={ optixGlobalNGWDM 291 }


-- -------------------------------------------------------------------------
-- Perfomance 15-MIN Current Data Table (RTRV-PER-<MOD2>)
-- -------------------------------------------------------------------------
        -- 1.3.6.1.4.1.2011.2.25.3.40.50.291.10
        oducn_tcm2Per15MCurTable OBJECT-TYPE
            SYNTAX SEQUENCE OF Oducn_tcm2Per15MCurEntry
            MAX-ACCESS not-accessible
            STATUS current
            DESCRIPTION
                "oducn_tcm2Per15MCur."
            ::= { oducn_tcm2 10 }

        -- 1.3.6.1.4.1.2011.2.25.3.40.50.291.10.1
        oducn_tcm2Per15MCurEntry OBJECT-TYPE
            SYNTAX Oducn_tcm2Per15MCurEntry
            MAX-ACCESS not-accessible
            STATUS current
            DESCRIPTION
              "oducn_tcm2Per15MCur."
            INDEX { oducn_tcm2Per15MCurEid, oducn_tcm2Per15MCurPara }
            ::= { oducn_tcm2Per15MCurTable 1 }

        Oducn_tcm2Per15MCurEntry ::=
            SEQUENCE {
                oducn_tcm2Per15MCurEid
                    PerformanceEventType,
                oducn_tcm2Per15MCurMonValue
                    OCTET STRING,
                oducn_tcm2Per15MCurVldty
                    INTEGER,
                oducn_tcm2Per15MCurDateTime
                    DateAndTime,
                oducn_tcm2Per15MCurParaLen
                    INTEGER,
                oducn_tcm2Per15MCurPara
                    OCTET STRING
            }

        -- 1.3.6.1.4.1.2011.2.25.3.40.50.291.10.1.1
        oducn_tcm2Per15MCurEid OBJECT-TYPE
            SYNTAX PerformanceEventType
            MAX-ACCESS read-only
            STATUS current
            DESCRIPTION
                "perEid."
            ::= { oducn_tcm2Per15MCurEntry 1 }

        -- 1.3.6.1.4.1.2011.2.25.3.40.50.291.10.1.2
        oducn_tcm2Per15MCurMonValue OBJECT-TYPE
            SYNTAX OCTET STRING (SIZE (0..100))
            MAX-ACCESS read-only
            STATUS current
            DESCRIPTION
                "perMonValue."
            ::= { oducn_tcm2Per15MCurEntry 2 }

        -- 1.3.6.1.4.1.2011.2.25.3.40.50.291.10.1.3
        oducn_tcm2Per15MCurVldty OBJECT-TYPE
            SYNTAX INTEGER
            MAX-ACCESS read-only
            STATUS current
            DESCRIPTION
                "perVldty. "
            ::= { oducn_tcm2Per15MCurEntry 3 }

        -- 1.3.6.1.4.1.2011.2.25.3.40.50.291.10.1.4
        oducn_tcm2Per15MCurDateTime OBJECT-TYPE
            SYNTAX DateAndTime
            MAX-ACCESS read-only
            STATUS current
            DESCRIPTION
                "perDateTime. "
            ::= { oducn_tcm2Per15MCurEntry 4 }

        -- 1.3.6.1.4.1.2011.2.25.3.40.50.291.10.1.5
        oducn_tcm2Per15MCurParaLen OBJECT-TYPE
            SYNTAX INTEGER
            MAX-ACCESS read-only
            STATUS current
            DESCRIPTION
                "perParaLen."
            ::= { oducn_tcm2Per15MCurEntry 5 }

        -- 1.3.6.1.4.1.2011.2.25.3.40.50.291.10.1.6
        oducn_tcm2Per15MCurPara OBJECT-TYPE
            SYNTAX OCTET STRING (SIZE (0..100))
            MAX-ACCESS read-only
            STATUS current
            DESCRIPTION
                "perPara."
            ::= { oducn_tcm2Per15MCurEntry 6 }



-- -------------------------------------------------------------------------
-- Perfomance 15-MIN History Data Table (RTRV-PER-<MOD2>)
-- -------------------------------------------------------------------------
        -- 1.3.6.1.4.1.2011.2.25.3.40.50.291.20
        oducn_tcm2Per15MHisTable OBJECT-TYPE
            SYNTAX SEQUENCE OF Oducn_tcm2Per15MHisEntry
            MAX-ACCESS not-accessible
            STATUS current
            DESCRIPTION
                "oducn_tcm2Per15MHis."
            ::= { oducn_tcm2 20 }

        -- 1.3.6.1.4.1.2011.2.25.3.40.50.291.20.1
        oducn_tcm2Per15MHisEntry OBJECT-TYPE
            SYNTAX Oducn_tcm2Per15MHisEntry
            MAX-ACCESS not-accessible
            STATUS current
            DESCRIPTION
                "oducn_tcm2Per15MHis."
            INDEX {oducn_tcm2Per15MHisEid, oducn_tcm2Per15MHisParaLen, oducn_tcm2Per15MHisPara, oducn_tcm2Per15MHisDateTimeStart, oducn_tcm2Per15MHisDateTimeEnd}
            ::= { oducn_tcm2Per15MHisTable 1 }

        Oducn_tcm2Per15MHisEntry ::=
            SEQUENCE {
                oducn_tcm2Per15MHisEid
                    PerformanceEventType,
                oducn_tcm2Per15MHisParaLen
                    INTEGER,
                oducn_tcm2Per15MHisPara
                    OCTET STRING,
                oducn_tcm2Per15MHisMonValue
                    OCTET STRING,
                oducn_tcm2Per15MHisDateTimeStart
                    DateAndTime,
                oducn_tcm2Per15MHisDateTimeEnd
                    DateAndTime,
                oducn_tcm2Per15MHisVldty
                    INTEGER,
             }

        -- 1.3.6.1.4.1.2011.2.25.3.40.50.291.20.1.1
        oducn_tcm2Per15MHisEid OBJECT-TYPE
            SYNTAX PerformanceEventType
            MAX-ACCESS read-only
            STATUS current
            DESCRIPTION
                "perEid."
            ::= { oducn_tcm2Per15MHisEntry 1 }

        -- 1.3.6.1.4.1.2011.2.25.3.40.50.291.20.1.2
        oducn_tcm2Per15MHisParaLen OBJECT-TYPE
            SYNTAX INTEGER
            MAX-ACCESS read-only
            STATUS current
            DESCRIPTION
                "perParaLen."
            ::= { oducn_tcm2Per15MHisEntry 2 }

        -- 1.3.6.1.4.1.2011.2.25.3.40.50.291.20.1.3
        oducn_tcm2Per15MHisPara OBJECT-TYPE
            SYNTAX OCTET STRING (SIZE (0..100))
            MAX-ACCESS read-only
            STATUS current
            DESCRIPTION
                "perPara."
            ::= { oducn_tcm2Per15MHisEntry 3 }

        -- 1.3.6.1.4.1.2011.2.25.3.40.50.291.20.1.4
        oducn_tcm2Per15MHisMonValue OBJECT-TYPE
            SYNTAX OCTET STRING (SIZE (0..100))
            MAX-ACCESS read-only
            STATUS current
            DESCRIPTION
                "perMonValue."
            ::= { oducn_tcm2Per15MHisEntry 4 }

        -- 1.3.6.1.4.1.2011.2.25.3.40.50.291.20.1.5
        oducn_tcm2Per15MHisDateTimeStart OBJECT-TYPE
            SYNTAX DateAndTime
            MAX-ACCESS read-only
            STATUS current
            DESCRIPTION
                "perDateTimeStart. "
            ::= { oducn_tcm2Per15MHisEntry 5 }

        -- 1.3.6.1.4.1.2011.2.25.3.40.50.291.20.1.6
        oducn_tcm2Per15MHisDateTimeEnd OBJECT-TYPE
            SYNTAX DateAndTime
            MAX-ACCESS read-only
            STATUS current
            DESCRIPTION
                "perDateTimeEnd. "
            ::= { oducn_tcm2Per15MHisEntry 6 }

        -- 1.3.6.1.4.1.2011.2.25.3.40.50.291.20.1.7
        oducn_tcm2Per15MHisVldty OBJECT-TYPE
            SYNTAX INTEGER
            MAX-ACCESS read-only
            STATUS current
            DESCRIPTION
                "perVldty. "
            ::= { oducn_tcm2Per15MHisEntry 7 }




-- -------------------------------------------------------------------------
-- Perfomance 24-HOUR Current Data Table (RTRV-PER-<MOD2>)
-- -------------------------------------------------------------------------
        -- 1.3.6.1.4.1.2011.2.25.3.40.50.291.30
        oducn_tcm2Per24HCurTable OBJECT-TYPE
          SYNTAX SEQUENCE OF Oducn_tcm2Per24HCurEntry
          MAX-ACCESS not-accessible
          STATUS current
          DESCRIPTION
              "oducn_tcm2Per24HCur."
          ::= { oducn_tcm2 30 }

        -- 1.3.6.1.4.1.2011.2.25.3.40.50.291.30.1
        oducn_tcm2Per24HCurEntry OBJECT-TYPE
            SYNTAX Oducn_tcm2Per24HCurEntry
            MAX-ACCESS not-accessible
            STATUS current
            DESCRIPTION
              "oducn_tcm2Per24HCur."
            INDEX { oducn_tcm2Per24HCurEid, oducn_tcm2Per24HCurPara }
            ::= { oducn_tcm2Per24HCurTable 1 }

        Oducn_tcm2Per24HCurEntry ::=
            SEQUENCE {
                oducn_tcm2Per24HCurEid
                    PerformanceEventType,
                oducn_tcm2Per24HCurMonValue
                    OCTET STRING,
                oducn_tcm2Per24HCurVldty
                    INTEGER,
                oducn_tcm2Per24HCurDateTime
                    DateAndTime,
                oducn_tcm2Per24HCurParaLen
                    INTEGER,
                oducn_tcm2Per24HCurPara
                    OCTET STRING
            }

        -- 1.3.6.1.4.1.2011.2.25.3.40.50.291.30.1.1
        oducn_tcm2Per24HCurEid OBJECT-TYPE
            SYNTAX PerformanceEventType
            MAX-ACCESS read-only
            STATUS current
            DESCRIPTION
                "perEid."
            ::= { oducn_tcm2Per24HCurEntry 1 }

        -- 1.3.6.1.4.1.2011.2.25.3.40.50.291.30.1.2
        oducn_tcm2Per24HCurMonValue OBJECT-TYPE
            SYNTAX OCTET STRING (SIZE (0..100))
            MAX-ACCESS read-only
            STATUS current
            DESCRIPTION
                "perMonValue."
            ::= { oducn_tcm2Per24HCurEntry 2 }

        -- 1.3.6.1.4.1.2011.2.25.3.40.50.291.30.1.3
        oducn_tcm2Per24HCurVldty OBJECT-TYPE
            SYNTAX INTEGER
            MAX-ACCESS read-only
            STATUS current
            DESCRIPTION
                "perVldty. "
            ::= { oducn_tcm2Per24HCurEntry 3 }

        -- 1.3.6.1.4.1.2011.2.25.3.40.50.291.30.1.4
        oducn_tcm2Per24HCurDateTime OBJECT-TYPE
            SYNTAX DateAndTime
            MAX-ACCESS read-only
            STATUS current
            DESCRIPTION
                "perDateTime. "
            ::= { oducn_tcm2Per24HCurEntry 4 }

        -- 1.3.6.1.4.1.2011.2.25.3.40.50.291.30.1.5
        oducn_tcm2Per24HCurParaLen OBJECT-TYPE
            SYNTAX INTEGER
            MAX-ACCESS read-only
            STATUS current
            DESCRIPTION
                "perParaLen."
            ::= { oducn_tcm2Per24HCurEntry 5 }

        -- 1.3.6.1.4.1.2011.2.25.3.40.50.291.30.1.6
        oducn_tcm2Per24HCurPara OBJECT-TYPE
            SYNTAX OCTET STRING (SIZE (0..100))
            MAX-ACCESS read-only
            STATUS current
            DESCRIPTION
                "perPara."
            ::= { oducn_tcm2Per24HCurEntry 6 }




-- -------------------------------------------------------------------------
-- Perfomance 24-HOUR History Data Table (RTRV-PER-<MOD2>)
-- -------------------------------------------------------------------------
        -- 1.3.6.1.4.1.2011.2.25.3.40.50.291.40
        oducn_tcm2Per24HHisTable OBJECT-TYPE
          SYNTAX SEQUENCE OF Oducn_tcm2Per24HHisEntry
          MAX-ACCESS not-accessible
          STATUS current
          DESCRIPTION
              "oducn_tcm2Per24HHis."
          ::= { oducn_tcm2 40 }

        -- 1.3.6.1.4.1.2011.2.25.3.40.50.291.40.1
        oducn_tcm2Per24HHisEntry OBJECT-TYPE
            SYNTAX Oducn_tcm2Per24HHisEntry
            MAX-ACCESS not-accessible
            STATUS current
            DESCRIPTION
                "oducn_tcm2Per24HHis."
            INDEX {oducn_tcm2Per24HHisEid, oducn_tcm2Per24HHisParaLen, oducn_tcm2Per24HHisPara, oducn_tcm2Per24HHisDateTimeStart, oducn_tcm2Per24HHisDateTimeEnd}
            ::= { oducn_tcm2Per24HHisTable 1 }

        Oducn_tcm2Per24HHisEntry ::=
            SEQUENCE {
                oducn_tcm2Per24HHisEid
                    PerformanceEventType,
                oducn_tcm2Per24HHisParaLen
                    INTEGER,
                oducn_tcm2Per24HHisPara
                    OCTET STRING,
                oducn_tcm2Per24HHisMonValue
                    OCTET STRING,
                oducn_tcm2Per24HHisDateTimeStart
                    DateAndTime,
                oducn_tcm2Per24HHisDateTimeEnd
                    DateAndTime,
                oducn_tcm2Per24HHisVldty
                    INTEGER,
             }

        -- 1.3.6.1.4.1.2011.2.25.3.40.50.291.40.1.1
        oducn_tcm2Per24HHisEid OBJECT-TYPE
            SYNTAX PerformanceEventType
            MAX-ACCESS read-only
            STATUS current
            DESCRIPTION
                "perEid."
            ::= { oducn_tcm2Per24HHisEntry 1 }

        -- 1.3.6.1.4.1.2011.2.25.3.40.50.291.40.1.2
        oducn_tcm2Per24HHisParaLen OBJECT-TYPE
            SYNTAX INTEGER
            MAX-ACCESS read-only
            STATUS current
            DESCRIPTION
                "perParaLen."
            ::= { oducn_tcm2Per24HHisEntry 2 }

        -- 1.3.6.1.4.1.2011.2.25.3.40.50.291.40.1.3
        oducn_tcm2Per24HHisPara OBJECT-TYPE
            SYNTAX OCTET STRING (SIZE (0..100))
            MAX-ACCESS read-only
            STATUS current
            DESCRIPTION
                "perPara."
            ::= { oducn_tcm2Per24HHisEntry 3 }

        -- 1.3.6.1.4.1.2011.2.25.3.40.50.291.40.1.4
        oducn_tcm2Per24HHisMonValue OBJECT-TYPE
            SYNTAX OCTET STRING (SIZE (0..100))
            MAX-ACCESS read-only
            STATUS current
            DESCRIPTION
                "perMonValue."
            ::= { oducn_tcm2Per24HHisEntry 4 }

        -- 1.3.6.1.4.1.2011.2.25.3.40.50.291.40.1.5
        oducn_tcm2Per24HHisDateTimeStart OBJECT-TYPE
            SYNTAX DateAndTime
            MAX-ACCESS read-only
            STATUS current
            DESCRIPTION
                "perDateTimeStart. "
            ::= { oducn_tcm2Per24HHisEntry 5 }

        -- 1.3.6.1.4.1.2011.2.25.3.40.50.291.40.1.6
        oducn_tcm2Per24HHisDateTimeEnd OBJECT-TYPE
            SYNTAX DateAndTime
            MAX-ACCESS read-only
            STATUS current
            DESCRIPTION
                "perDateTimeEnd. "
            ::= { oducn_tcm2Per24HHisEntry 6 }

        -- 1.3.6.1.4.1.2011.2.25.3.40.50.291.40.1.7
        oducn_tcm2Per24HHisVldty OBJECT-TYPE
            SYNTAX INTEGER
            MAX-ACCESS read-only
            STATUS current
            DESCRIPTION
                "perVldty. "
            ::= { oducn_tcm2Per24HHisEntry 7 }


-- Alarm data
      -- 1.3.6.1.4.1.2011.2.25.3.40.50.292
      oducn_tcm3 OBJECT IDENTIFIER ::={ optixGlobalNGWDM 292 }


-- -------------------------------------------------------------------------
-- Perfomance 15-MIN Current Data Table (RTRV-PER-<MOD2>)
-- -------------------------------------------------------------------------
        -- 1.3.6.1.4.1.2011.2.25.3.40.50.292.10
        oducn_tcm3Per15MCurTable OBJECT-TYPE
            SYNTAX SEQUENCE OF Oducn_tcm3Per15MCurEntry
            MAX-ACCESS not-accessible
            STATUS current
            DESCRIPTION
                "oducn_tcm3Per15MCur."
            ::= { oducn_tcm3 10 }

        -- 1.3.6.1.4.1.2011.2.25.3.40.50.292.10.1
        oducn_tcm3Per15MCurEntry OBJECT-TYPE
            SYNTAX Oducn_tcm3Per15MCurEntry
            MAX-ACCESS not-accessible
            STATUS current
            DESCRIPTION
              "oducn_tcm3Per15MCur."
            INDEX { oducn_tcm3Per15MCurEid, oducn_tcm3Per15MCurPara }
            ::= { oducn_tcm3Per15MCurTable 1 }

        Oducn_tcm3Per15MCurEntry ::=
            SEQUENCE {
                oducn_tcm3Per15MCurEid
                    PerformanceEventType,
                oducn_tcm3Per15MCurMonValue
                    OCTET STRING,
                oducn_tcm3Per15MCurVldty
                    INTEGER,
                oducn_tcm3Per15MCurDateTime
                    DateAndTime,
                oducn_tcm3Per15MCurParaLen
                    INTEGER,
                oducn_tcm3Per15MCurPara
                    OCTET STRING
            }

        -- 1.3.6.1.4.1.2011.2.25.3.40.50.292.10.1.1
        oducn_tcm3Per15MCurEid OBJECT-TYPE
            SYNTAX PerformanceEventType
            MAX-ACCESS read-only
            STATUS current
            DESCRIPTION
                "perEid."
            ::= { oducn_tcm3Per15MCurEntry 1 }

        -- 1.3.6.1.4.1.2011.2.25.3.40.50.292.10.1.2
        oducn_tcm3Per15MCurMonValue OBJECT-TYPE
            SYNTAX OCTET STRING (SIZE (0..100))
            MAX-ACCESS read-only
            STATUS current
            DESCRIPTION
                "perMonValue."
            ::= { oducn_tcm3Per15MCurEntry 2 }

        -- 1.3.6.1.4.1.2011.2.25.3.40.50.292.10.1.3
        oducn_tcm3Per15MCurVldty OBJECT-TYPE
            SYNTAX INTEGER
            MAX-ACCESS read-only
            STATUS current
            DESCRIPTION
                "perVldty. "
            ::= { oducn_tcm3Per15MCurEntry 3 }

        -- 1.3.6.1.4.1.2011.2.25.3.40.50.292.10.1.4
        oducn_tcm3Per15MCurDateTime OBJECT-TYPE
            SYNTAX DateAndTime
            MAX-ACCESS read-only
            STATUS current
            DESCRIPTION
                "perDateTime. "
            ::= { oducn_tcm3Per15MCurEntry 4 }

        -- 1.3.6.1.4.1.2011.2.25.3.40.50.292.10.1.5
        oducn_tcm3Per15MCurParaLen OBJECT-TYPE
            SYNTAX INTEGER
            MAX-ACCESS read-only
            STATUS current
            DESCRIPTION
                "perParaLen."
            ::= { oducn_tcm3Per15MCurEntry 5 }

        -- 1.3.6.1.4.1.2011.2.25.3.40.50.292.10.1.6
        oducn_tcm3Per15MCurPara OBJECT-TYPE
            SYNTAX OCTET STRING (SIZE (0..100))
            MAX-ACCESS read-only
            STATUS current
            DESCRIPTION
                "perPara."
            ::= { oducn_tcm3Per15MCurEntry 6 }



-- -------------------------------------------------------------------------
-- Perfomance 15-MIN History Data Table (RTRV-PER-<MOD2>)
-- -------------------------------------------------------------------------
        -- 1.3.6.1.4.1.2011.2.25.3.40.50.292.20
        oducn_tcm3Per15MHisTable OBJECT-TYPE
            SYNTAX SEQUENCE OF Oducn_tcm3Per15MHisEntry
            MAX-ACCESS not-accessible
            STATUS current
            DESCRIPTION
                "oducn_tcm3Per15MHis."
            ::= { oducn_tcm3 20 }

        -- 1.3.6.1.4.1.2011.2.25.3.40.50.292.20.1
        oducn_tcm3Per15MHisEntry OBJECT-TYPE
            SYNTAX Oducn_tcm3Per15MHisEntry
            MAX-ACCESS not-accessible
            STATUS current
            DESCRIPTION
                "oducn_tcm3Per15MHis."
            INDEX {oducn_tcm3Per15MHisEid, oducn_tcm3Per15MHisParaLen, oducn_tcm3Per15MHisPara, oducn_tcm3Per15MHisDateTimeStart, oducn_tcm3Per15MHisDateTimeEnd}
            ::= { oducn_tcm3Per15MHisTable 1 }

        Oducn_tcm3Per15MHisEntry ::=
            SEQUENCE {
                oducn_tcm3Per15MHisEid
                    PerformanceEventType,
                oducn_tcm3Per15MHisParaLen
                    INTEGER,
                oducn_tcm3Per15MHisPara
                    OCTET STRING,
                oducn_tcm3Per15MHisMonValue
                    OCTET STRING,
                oducn_tcm3Per15MHisDateTimeStart
                    DateAndTime,
                oducn_tcm3Per15MHisDateTimeEnd
                    DateAndTime,
                oducn_tcm3Per15MHisVldty
                    INTEGER,
             }

        -- 1.3.6.1.4.1.2011.2.25.3.40.50.292.20.1.1
        oducn_tcm3Per15MHisEid OBJECT-TYPE
            SYNTAX PerformanceEventType
            MAX-ACCESS read-only
            STATUS current
            DESCRIPTION
                "perEid."
            ::= { oducn_tcm3Per15MHisEntry 1 }

        -- 1.3.6.1.4.1.2011.2.25.3.40.50.292.20.1.2
        oducn_tcm3Per15MHisParaLen OBJECT-TYPE
            SYNTAX INTEGER
            MAX-ACCESS read-only
            STATUS current
            DESCRIPTION
                "perParaLen."
            ::= { oducn_tcm3Per15MHisEntry 2 }

        -- 1.3.6.1.4.1.2011.2.25.3.40.50.292.20.1.3
        oducn_tcm3Per15MHisPara OBJECT-TYPE
            SYNTAX OCTET STRING (SIZE (0..100))
            MAX-ACCESS read-only
            STATUS current
            DESCRIPTION
                "perPara."
            ::= { oducn_tcm3Per15MHisEntry 3 }

        -- 1.3.6.1.4.1.2011.2.25.3.40.50.292.20.1.4
        oducn_tcm3Per15MHisMonValue OBJECT-TYPE
            SYNTAX OCTET STRING (SIZE (0..100))
            MAX-ACCESS read-only
            STATUS current
            DESCRIPTION
                "perMonValue."
            ::= { oducn_tcm3Per15MHisEntry 4 }

        -- 1.3.6.1.4.1.2011.2.25.3.40.50.292.20.1.5
        oducn_tcm3Per15MHisDateTimeStart OBJECT-TYPE
            SYNTAX DateAndTime
            MAX-ACCESS read-only
            STATUS current
            DESCRIPTION
                "perDateTimeStart. "
            ::= { oducn_tcm3Per15MHisEntry 5 }

        -- 1.3.6.1.4.1.2011.2.25.3.40.50.292.20.1.6
        oducn_tcm3Per15MHisDateTimeEnd OBJECT-TYPE
            SYNTAX DateAndTime
            MAX-ACCESS read-only
            STATUS current
            DESCRIPTION
                "perDateTimeEnd. "
            ::= { oducn_tcm3Per15MHisEntry 6 }

        -- 1.3.6.1.4.1.2011.2.25.3.40.50.292.20.1.7
        oducn_tcm3Per15MHisVldty OBJECT-TYPE
            SYNTAX INTEGER
            MAX-ACCESS read-only
            STATUS current
            DESCRIPTION
                "perVldty. "
            ::= { oducn_tcm3Per15MHisEntry 7 }




-- -------------------------------------------------------------------------
-- Perfomance 24-HOUR Current Data Table (RTRV-PER-<MOD2>)
-- -------------------------------------------------------------------------
        -- 1.3.6.1.4.1.2011.2.25.3.40.50.292.30
        oducn_tcm3Per24HCurTable OBJECT-TYPE
          SYNTAX SEQUENCE OF Oducn_tcm3Per24HCurEntry
          MAX-ACCESS not-accessible
          STATUS current
          DESCRIPTION
              "oducn_tcm3Per24HCur."
          ::= { oducn_tcm3 30 }

        -- 1.3.6.1.4.1.2011.2.25.3.40.50.292.30.1
        oducn_tcm3Per24HCurEntry OBJECT-TYPE
            SYNTAX Oducn_tcm3Per24HCurEntry
            MAX-ACCESS not-accessible
            STATUS current
            DESCRIPTION
              "oducn_tcm3Per24HCur."
            INDEX { oducn_tcm3Per24HCurEid, oducn_tcm3Per24HCurPara }
            ::= { oducn_tcm3Per24HCurTable 1 }

        Oducn_tcm3Per24HCurEntry ::=
            SEQUENCE {
                oducn_tcm3Per24HCurEid
                    PerformanceEventType,
                oducn_tcm3Per24HCurMonValue
                    OCTET STRING,
                oducn_tcm3Per24HCurVldty
                    INTEGER,
                oducn_tcm3Per24HCurDateTime
                    DateAndTime,
                oducn_tcm3Per24HCurParaLen
                    INTEGER,
                oducn_tcm3Per24HCurPara
                    OCTET STRING
            }

        -- 1.3.6.1.4.1.2011.2.25.3.40.50.292.30.1.1
        oducn_tcm3Per24HCurEid OBJECT-TYPE
            SYNTAX PerformanceEventType
            MAX-ACCESS read-only
            STATUS current
            DESCRIPTION
                "perEid."
            ::= { oducn_tcm3Per24HCurEntry 1 }

        -- 1.3.6.1.4.1.2011.2.25.3.40.50.292.30.1.2
        oducn_tcm3Per24HCurMonValue OBJECT-TYPE
            SYNTAX OCTET STRING (SIZE (0..100))
            MAX-ACCESS read-only
            STATUS current
            DESCRIPTION
                "perMonValue."
            ::= { oducn_tcm3Per24HCurEntry 2 }

        -- 1.3.6.1.4.1.2011.2.25.3.40.50.292.30.1.3
        oducn_tcm3Per24HCurVldty OBJECT-TYPE
            SYNTAX INTEGER
            MAX-ACCESS read-only
            STATUS current
            DESCRIPTION
                "perVldty. "
            ::= { oducn_tcm3Per24HCurEntry 3 }

        -- 1.3.6.1.4.1.2011.2.25.3.40.50.292.30.1.4
        oducn_tcm3Per24HCurDateTime OBJECT-TYPE
            SYNTAX DateAndTime
            MAX-ACCESS read-only
            STATUS current
            DESCRIPTION
                "perDateTime. "
            ::= { oducn_tcm3Per24HCurEntry 4 }

        -- 1.3.6.1.4.1.2011.2.25.3.40.50.292.30.1.5
        oducn_tcm3Per24HCurParaLen OBJECT-TYPE
            SYNTAX INTEGER
            MAX-ACCESS read-only
            STATUS current
            DESCRIPTION
                "perParaLen."
            ::= { oducn_tcm3Per24HCurEntry 5 }

        -- 1.3.6.1.4.1.2011.2.25.3.40.50.292.30.1.6
        oducn_tcm3Per24HCurPara OBJECT-TYPE
            SYNTAX OCTET STRING (SIZE (0..100))
            MAX-ACCESS read-only
            STATUS current
            DESCRIPTION
                "perPara."
            ::= { oducn_tcm3Per24HCurEntry 6 }




-- -------------------------------------------------------------------------
-- Perfomance 24-HOUR History Data Table (RTRV-PER-<MOD2>)
-- -------------------------------------------------------------------------
        -- 1.3.6.1.4.1.2011.2.25.3.40.50.292.40
        oducn_tcm3Per24HHisTable OBJECT-TYPE
          SYNTAX SEQUENCE OF Oducn_tcm3Per24HHisEntry
          MAX-ACCESS not-accessible
          STATUS current
          DESCRIPTION
              "oducn_tcm3Per24HHis."
          ::= { oducn_tcm3 40 }

        -- 1.3.6.1.4.1.2011.2.25.3.40.50.292.40.1
        oducn_tcm3Per24HHisEntry OBJECT-TYPE
            SYNTAX Oducn_tcm3Per24HHisEntry
            MAX-ACCESS not-accessible
            STATUS current
            DESCRIPTION
                "oducn_tcm3Per24HHis."
            INDEX {oducn_tcm3Per24HHisEid, oducn_tcm3Per24HHisParaLen, oducn_tcm3Per24HHisPara, oducn_tcm3Per24HHisDateTimeStart, oducn_tcm3Per24HHisDateTimeEnd}
            ::= { oducn_tcm3Per24HHisTable 1 }

        Oducn_tcm3Per24HHisEntry ::=
            SEQUENCE {
                oducn_tcm3Per24HHisEid
                    PerformanceEventType,
                oducn_tcm3Per24HHisParaLen
                    INTEGER,
                oducn_tcm3Per24HHisPara
                    OCTET STRING,
                oducn_tcm3Per24HHisMonValue
                    OCTET STRING,
                oducn_tcm3Per24HHisDateTimeStart
                    DateAndTime,
                oducn_tcm3Per24HHisDateTimeEnd
                    DateAndTime,
                oducn_tcm3Per24HHisVldty
                    INTEGER,
             }

        -- 1.3.6.1.4.1.2011.2.25.3.40.50.292.40.1.1
        oducn_tcm3Per24HHisEid OBJECT-TYPE
            SYNTAX PerformanceEventType
            MAX-ACCESS read-only
            STATUS current
            DESCRIPTION
                "perEid."
            ::= { oducn_tcm3Per24HHisEntry 1 }

        -- 1.3.6.1.4.1.2011.2.25.3.40.50.292.40.1.2
        oducn_tcm3Per24HHisParaLen OBJECT-TYPE
            SYNTAX INTEGER
            MAX-ACCESS read-only
            STATUS current
            DESCRIPTION
                "perParaLen."
            ::= { oducn_tcm3Per24HHisEntry 2 }

        -- 1.3.6.1.4.1.2011.2.25.3.40.50.292.40.1.3
        oducn_tcm3Per24HHisPara OBJECT-TYPE
            SYNTAX OCTET STRING (SIZE (0..100))
            MAX-ACCESS read-only
            STATUS current
            DESCRIPTION
                "perPara."
            ::= { oducn_tcm3Per24HHisEntry 3 }

        -- 1.3.6.1.4.1.2011.2.25.3.40.50.292.40.1.4
        oducn_tcm3Per24HHisMonValue OBJECT-TYPE
            SYNTAX OCTET STRING (SIZE (0..100))
            MAX-ACCESS read-only
            STATUS current
            DESCRIPTION
                "perMonValue."
            ::= { oducn_tcm3Per24HHisEntry 4 }

        -- 1.3.6.1.4.1.2011.2.25.3.40.50.292.40.1.5
        oducn_tcm3Per24HHisDateTimeStart OBJECT-TYPE
            SYNTAX DateAndTime
            MAX-ACCESS read-only
            STATUS current
            DESCRIPTION
                "perDateTimeStart. "
            ::= { oducn_tcm3Per24HHisEntry 5 }

        -- 1.3.6.1.4.1.2011.2.25.3.40.50.292.40.1.6
        oducn_tcm3Per24HHisDateTimeEnd OBJECT-TYPE
            SYNTAX DateAndTime
            MAX-ACCESS read-only
            STATUS current
            DESCRIPTION
                "perDateTimeEnd. "
            ::= { oducn_tcm3Per24HHisEntry 6 }

        -- 1.3.6.1.4.1.2011.2.25.3.40.50.292.40.1.7
        oducn_tcm3Per24HHisVldty OBJECT-TYPE
            SYNTAX INTEGER
            MAX-ACCESS read-only
            STATUS current
            DESCRIPTION
                "perVldty. "
            ::= { oducn_tcm3Per24HHisEntry 7 }


-- Alarm data
      -- 1.3.6.1.4.1.2011.2.25.3.40.50.293
      oducn_tcm4 OBJECT IDENTIFIER ::={ optixGlobalNGWDM 293 }


-- -------------------------------------------------------------------------
-- Perfomance 15-MIN Current Data Table (RTRV-PER-<MOD2>)
-- -------------------------------------------------------------------------
        -- 1.3.6.1.4.1.2011.2.25.3.40.50.293.10
        oducn_tcm4Per15MCurTable OBJECT-TYPE
            SYNTAX SEQUENCE OF Oducn_tcm4Per15MCurEntry
            MAX-ACCESS not-accessible
            STATUS current
            DESCRIPTION
                "oducn_tcm4Per15MCur."
            ::= { oducn_tcm4 10 }

        -- 1.3.6.1.4.1.2011.2.25.3.40.50.293.10.1
        oducn_tcm4Per15MCurEntry OBJECT-TYPE
            SYNTAX Oducn_tcm4Per15MCurEntry
            MAX-ACCESS not-accessible
            STATUS current
            DESCRIPTION
              "oducn_tcm4Per15MCur."
            INDEX { oducn_tcm4Per15MCurEid, oducn_tcm4Per15MCurPara }
            ::= { oducn_tcm4Per15MCurTable 1 }

        Oducn_tcm4Per15MCurEntry ::=
            SEQUENCE {
                oducn_tcm4Per15MCurEid
                    PerformanceEventType,
                oducn_tcm4Per15MCurMonValue
                    OCTET STRING,
                oducn_tcm4Per15MCurVldty
                    INTEGER,
                oducn_tcm4Per15MCurDateTime
                    DateAndTime,
                oducn_tcm4Per15MCurParaLen
                    INTEGER,
                oducn_tcm4Per15MCurPara
                    OCTET STRING
            }

        -- 1.3.6.1.4.1.2011.2.25.3.40.50.293.10.1.1
        oducn_tcm4Per15MCurEid OBJECT-TYPE
            SYNTAX PerformanceEventType
            MAX-ACCESS read-only
            STATUS current
            DESCRIPTION
                "perEid."
            ::= { oducn_tcm4Per15MCurEntry 1 }

        -- 1.3.6.1.4.1.2011.2.25.3.40.50.293.10.1.2
        oducn_tcm4Per15MCurMonValue OBJECT-TYPE
            SYNTAX OCTET STRING (SIZE (0..100))
            MAX-ACCESS read-only
            STATUS current
            DESCRIPTION
                "perMonValue."
            ::= { oducn_tcm4Per15MCurEntry 2 }

        -- 1.3.6.1.4.1.2011.2.25.3.40.50.293.10.1.3
        oducn_tcm4Per15MCurVldty OBJECT-TYPE
            SYNTAX INTEGER
            MAX-ACCESS read-only
            STATUS current
            DESCRIPTION
                "perVldty. "
            ::= { oducn_tcm4Per15MCurEntry 3 }

        -- 1.3.6.1.4.1.2011.2.25.3.40.50.293.10.1.4
        oducn_tcm4Per15MCurDateTime OBJECT-TYPE
            SYNTAX DateAndTime
            MAX-ACCESS read-only
            STATUS current
            DESCRIPTION
                "perDateTime. "
            ::= { oducn_tcm4Per15MCurEntry 4 }

        -- 1.3.6.1.4.1.2011.2.25.3.40.50.293.10.1.5
        oducn_tcm4Per15MCurParaLen OBJECT-TYPE
            SYNTAX INTEGER
            MAX-ACCESS read-only
            STATUS current
            DESCRIPTION
                "perParaLen."
            ::= { oducn_tcm4Per15MCurEntry 5 }

        -- 1.3.6.1.4.1.2011.2.25.3.40.50.293.10.1.6
        oducn_tcm4Per15MCurPara OBJECT-TYPE
            SYNTAX OCTET STRING (SIZE (0..100))
            MAX-ACCESS read-only
            STATUS current
            DESCRIPTION
                "perPara."
            ::= { oducn_tcm4Per15MCurEntry 6 }



-- -------------------------------------------------------------------------
-- Perfomance 15-MIN History Data Table (RTRV-PER-<MOD2>)
-- -------------------------------------------------------------------------
        -- 1.3.6.1.4.1.2011.2.25.3.40.50.293.20
        oducn_tcm4Per15MHisTable OBJECT-TYPE
            SYNTAX SEQUENCE OF Oducn_tcm4Per15MHisEntry
            MAX-ACCESS not-accessible
            STATUS current
            DESCRIPTION
                "oducn_tcm4Per15MHis."
            ::= { oducn_tcm4 20 }

        -- 1.3.6.1.4.1.2011.2.25.3.40.50.293.20.1
        oducn_tcm4Per15MHisEntry OBJECT-TYPE
            SYNTAX Oducn_tcm4Per15MHisEntry
            MAX-ACCESS not-accessible
            STATUS current
            DESCRIPTION
                "oducn_tcm4Per15MHis."
            INDEX {oducn_tcm4Per15MHisEid, oducn_tcm4Per15MHisParaLen, oducn_tcm4Per15MHisPara, oducn_tcm4Per15MHisDateTimeStart, oducn_tcm4Per15MHisDateTimeEnd}
            ::= { oducn_tcm4Per15MHisTable 1 }

        Oducn_tcm4Per15MHisEntry ::=
            SEQUENCE {
                oducn_tcm4Per15MHisEid
                    PerformanceEventType,
                oducn_tcm4Per15MHisParaLen
                    INTEGER,
                oducn_tcm4Per15MHisPara
                    OCTET STRING,
                oducn_tcm4Per15MHisMonValue
                    OCTET STRING,
                oducn_tcm4Per15MHisDateTimeStart
                    DateAndTime,
                oducn_tcm4Per15MHisDateTimeEnd
                    DateAndTime,
                oducn_tcm4Per15MHisVldty
                    INTEGER,
             }

        -- 1.3.6.1.4.1.2011.2.25.3.40.50.293.20.1.1
        oducn_tcm4Per15MHisEid OBJECT-TYPE
            SYNTAX PerformanceEventType
            MAX-ACCESS read-only
            STATUS current
            DESCRIPTION
                "perEid."
            ::= { oducn_tcm4Per15MHisEntry 1 }

        -- 1.3.6.1.4.1.2011.2.25.3.40.50.293.20.1.2
        oducn_tcm4Per15MHisParaLen OBJECT-TYPE
            SYNTAX INTEGER
            MAX-ACCESS read-only
            STATUS current
            DESCRIPTION
                "perParaLen."
            ::= { oducn_tcm4Per15MHisEntry 2 }

        -- 1.3.6.1.4.1.2011.2.25.3.40.50.293.20.1.3
        oducn_tcm4Per15MHisPara OBJECT-TYPE
            SYNTAX OCTET STRING (SIZE (0..100))
            MAX-ACCESS read-only
            STATUS current
            DESCRIPTION
                "perPara."
            ::= { oducn_tcm4Per15MHisEntry 3 }

        -- 1.3.6.1.4.1.2011.2.25.3.40.50.293.20.1.4
        oducn_tcm4Per15MHisMonValue OBJECT-TYPE
            SYNTAX OCTET STRING (SIZE (0..100))
            MAX-ACCESS read-only
            STATUS current
            DESCRIPTION
                "perMonValue."
            ::= { oducn_tcm4Per15MHisEntry 4 }

        -- 1.3.6.1.4.1.2011.2.25.3.40.50.293.20.1.5
        oducn_tcm4Per15MHisDateTimeStart OBJECT-TYPE
            SYNTAX DateAndTime
            MAX-ACCESS read-only
            STATUS current
            DESCRIPTION
                "perDateTimeStart. "
            ::= { oducn_tcm4Per15MHisEntry 5 }

        -- 1.3.6.1.4.1.2011.2.25.3.40.50.293.20.1.6
        oducn_tcm4Per15MHisDateTimeEnd OBJECT-TYPE
            SYNTAX DateAndTime
            MAX-ACCESS read-only
            STATUS current
            DESCRIPTION
                "perDateTimeEnd. "
            ::= { oducn_tcm4Per15MHisEntry 6 }

        -- 1.3.6.1.4.1.2011.2.25.3.40.50.293.20.1.7
        oducn_tcm4Per15MHisVldty OBJECT-TYPE
            SYNTAX INTEGER
            MAX-ACCESS read-only
            STATUS current
            DESCRIPTION
                "perVldty. "
            ::= { oducn_tcm4Per15MHisEntry 7 }




-- -------------------------------------------------------------------------
-- Perfomance 24-HOUR Current Data Table (RTRV-PER-<MOD2>)
-- -------------------------------------------------------------------------
        -- 1.3.6.1.4.1.2011.2.25.3.40.50.293.30
        oducn_tcm4Per24HCurTable OBJECT-TYPE
          SYNTAX SEQUENCE OF Oducn_tcm4Per24HCurEntry
          MAX-ACCESS not-accessible
          STATUS current
          DESCRIPTION
              "oducn_tcm4Per24HCur."
          ::= { oducn_tcm4 30 }

        -- 1.3.6.1.4.1.2011.2.25.3.40.50.293.30.1
        oducn_tcm4Per24HCurEntry OBJECT-TYPE
            SYNTAX Oducn_tcm4Per24HCurEntry
            MAX-ACCESS not-accessible
            STATUS current
            DESCRIPTION
              "oducn_tcm4Per24HCur."
            INDEX { oducn_tcm4Per24HCurEid, oducn_tcm4Per24HCurPara }
            ::= { oducn_tcm4Per24HCurTable 1 }

        Oducn_tcm4Per24HCurEntry ::=
            SEQUENCE {
                oducn_tcm4Per24HCurEid
                    PerformanceEventType,
                oducn_tcm4Per24HCurMonValue
                    OCTET STRING,
                oducn_tcm4Per24HCurVldty
                    INTEGER,
                oducn_tcm4Per24HCurDateTime
                    DateAndTime,
                oducn_tcm4Per24HCurParaLen
                    INTEGER,
                oducn_tcm4Per24HCurPara
                    OCTET STRING
            }

        -- 1.3.6.1.4.1.2011.2.25.3.40.50.293.30.1.1
        oducn_tcm4Per24HCurEid OBJECT-TYPE
            SYNTAX PerformanceEventType
            MAX-ACCESS read-only
            STATUS current
            DESCRIPTION
                "perEid."
            ::= { oducn_tcm4Per24HCurEntry 1 }

        -- 1.3.6.1.4.1.2011.2.25.3.40.50.293.30.1.2
        oducn_tcm4Per24HCurMonValue OBJECT-TYPE
            SYNTAX OCTET STRING (SIZE (0..100))
            MAX-ACCESS read-only
            STATUS current
            DESCRIPTION
                "perMonValue."
            ::= { oducn_tcm4Per24HCurEntry 2 }

        -- 1.3.6.1.4.1.2011.2.25.3.40.50.293.30.1.3
        oducn_tcm4Per24HCurVldty OBJECT-TYPE
            SYNTAX INTEGER
            MAX-ACCESS read-only
            STATUS current
            DESCRIPTION
                "perVldty. "
            ::= { oducn_tcm4Per24HCurEntry 3 }

        -- 1.3.6.1.4.1.2011.2.25.3.40.50.293.30.1.4
        oducn_tcm4Per24HCurDateTime OBJECT-TYPE
            SYNTAX DateAndTime
            MAX-ACCESS read-only
            STATUS current
            DESCRIPTION
                "perDateTime. "
            ::= { oducn_tcm4Per24HCurEntry 4 }

        -- 1.3.6.1.4.1.2011.2.25.3.40.50.293.30.1.5
        oducn_tcm4Per24HCurParaLen OBJECT-TYPE
            SYNTAX INTEGER
            MAX-ACCESS read-only
            STATUS current
            DESCRIPTION
                "perParaLen."
            ::= { oducn_tcm4Per24HCurEntry 5 }

        -- 1.3.6.1.4.1.2011.2.25.3.40.50.293.30.1.6
        oducn_tcm4Per24HCurPara OBJECT-TYPE
            SYNTAX OCTET STRING (SIZE (0..100))
            MAX-ACCESS read-only
            STATUS current
            DESCRIPTION
                "perPara."
            ::= { oducn_tcm4Per24HCurEntry 6 }




-- -------------------------------------------------------------------------
-- Perfomance 24-HOUR History Data Table (RTRV-PER-<MOD2>)
-- -------------------------------------------------------------------------
        -- 1.3.6.1.4.1.2011.2.25.3.40.50.293.40
        oducn_tcm4Per24HHisTable OBJECT-TYPE
          SYNTAX SEQUENCE OF Oducn_tcm4Per24HHisEntry
          MAX-ACCESS not-accessible
          STATUS current
          DESCRIPTION
              "oducn_tcm4Per24HHis."
          ::= { oducn_tcm4 40 }

        -- 1.3.6.1.4.1.2011.2.25.3.40.50.293.40.1
        oducn_tcm4Per24HHisEntry OBJECT-TYPE
            SYNTAX Oducn_tcm4Per24HHisEntry
            MAX-ACCESS not-accessible
            STATUS current
            DESCRIPTION
                "oducn_tcm4Per24HHis."
            INDEX {oducn_tcm4Per24HHisEid, oducn_tcm4Per24HHisParaLen, oducn_tcm4Per24HHisPara, oducn_tcm4Per24HHisDateTimeStart, oducn_tcm4Per24HHisDateTimeEnd}
            ::= { oducn_tcm4Per24HHisTable 1 }

        Oducn_tcm4Per24HHisEntry ::=
            SEQUENCE {
                oducn_tcm4Per24HHisEid
                    PerformanceEventType,
                oducn_tcm4Per24HHisParaLen
                    INTEGER,
                oducn_tcm4Per24HHisPara
                    OCTET STRING,
                oducn_tcm4Per24HHisMonValue
                    OCTET STRING,
                oducn_tcm4Per24HHisDateTimeStart
                    DateAndTime,
                oducn_tcm4Per24HHisDateTimeEnd
                    DateAndTime,
                oducn_tcm4Per24HHisVldty
                    INTEGER,
             }

        -- 1.3.6.1.4.1.2011.2.25.3.40.50.293.40.1.1
        oducn_tcm4Per24HHisEid OBJECT-TYPE
            SYNTAX PerformanceEventType
            MAX-ACCESS read-only
            STATUS current
            DESCRIPTION
                "perEid."
            ::= { oducn_tcm4Per24HHisEntry 1 }

        -- 1.3.6.1.4.1.2011.2.25.3.40.50.293.40.1.2
        oducn_tcm4Per24HHisParaLen OBJECT-TYPE
            SYNTAX INTEGER
            MAX-ACCESS read-only
            STATUS current
            DESCRIPTION
                "perParaLen."
            ::= { oducn_tcm4Per24HHisEntry 2 }

        -- 1.3.6.1.4.1.2011.2.25.3.40.50.293.40.1.3
        oducn_tcm4Per24HHisPara OBJECT-TYPE
            SYNTAX OCTET STRING (SIZE (0..100))
            MAX-ACCESS read-only
            STATUS current
            DESCRIPTION
                "perPara."
            ::= { oducn_tcm4Per24HHisEntry 3 }

        -- 1.3.6.1.4.1.2011.2.25.3.40.50.293.40.1.4
        oducn_tcm4Per24HHisMonValue OBJECT-TYPE
            SYNTAX OCTET STRING (SIZE (0..100))
            MAX-ACCESS read-only
            STATUS current
            DESCRIPTION
                "perMonValue."
            ::= { oducn_tcm4Per24HHisEntry 4 }

        -- 1.3.6.1.4.1.2011.2.25.3.40.50.293.40.1.5
        oducn_tcm4Per24HHisDateTimeStart OBJECT-TYPE
            SYNTAX DateAndTime
            MAX-ACCESS read-only
            STATUS current
            DESCRIPTION
                "perDateTimeStart. "
            ::= { oducn_tcm4Per24HHisEntry 5 }

        -- 1.3.6.1.4.1.2011.2.25.3.40.50.293.40.1.6
        oducn_tcm4Per24HHisDateTimeEnd OBJECT-TYPE
            SYNTAX DateAndTime
            MAX-ACCESS read-only
            STATUS current
            DESCRIPTION
                "perDateTimeEnd. "
            ::= { oducn_tcm4Per24HHisEntry 6 }

        -- 1.3.6.1.4.1.2011.2.25.3.40.50.293.40.1.7
        oducn_tcm4Per24HHisVldty OBJECT-TYPE
            SYNTAX INTEGER
            MAX-ACCESS read-only
            STATUS current
            DESCRIPTION
                "perVldty. "
            ::= { oducn_tcm4Per24HHisEntry 7 }


-- Alarm data
      -- 1.3.6.1.4.1.2011.2.25.3.40.50.294
      oducn_tcm5 OBJECT IDENTIFIER ::={ optixGlobalNGWDM 294 }


-- -------------------------------------------------------------------------
-- Perfomance 15-MIN Current Data Table (RTRV-PER-<MOD2>)
-- -------------------------------------------------------------------------
        -- 1.3.6.1.4.1.2011.2.25.3.40.50.294.10
        oducn_tcm5Per15MCurTable OBJECT-TYPE
            SYNTAX SEQUENCE OF Oducn_tcm5Per15MCurEntry
            MAX-ACCESS not-accessible
            STATUS current
            DESCRIPTION
                "oducn_tcm5Per15MCur."
            ::= { oducn_tcm5 10 }

        -- 1.3.6.1.4.1.2011.2.25.3.40.50.294.10.1
        oducn_tcm5Per15MCurEntry OBJECT-TYPE
            SYNTAX Oducn_tcm5Per15MCurEntry
            MAX-ACCESS not-accessible
            STATUS current
            DESCRIPTION
              "oducn_tcm5Per15MCur."
            INDEX { oducn_tcm5Per15MCurEid, oducn_tcm5Per15MCurPara }
            ::= { oducn_tcm5Per15MCurTable 1 }

        Oducn_tcm5Per15MCurEntry ::=
            SEQUENCE {
                oducn_tcm5Per15MCurEid
                    PerformanceEventType,
                oducn_tcm5Per15MCurMonValue
                    OCTET STRING,
                oducn_tcm5Per15MCurVldty
                    INTEGER,
                oducn_tcm5Per15MCurDateTime
                    DateAndTime,
                oducn_tcm5Per15MCurParaLen
                    INTEGER,
                oducn_tcm5Per15MCurPara
                    OCTET STRING
            }

        -- 1.3.6.1.4.1.2011.2.25.3.40.50.294.10.1.1
        oducn_tcm5Per15MCurEid OBJECT-TYPE
            SYNTAX PerformanceEventType
            MAX-ACCESS read-only
            STATUS current
            DESCRIPTION
                "perEid."
            ::= { oducn_tcm5Per15MCurEntry 1 }

        -- 1.3.6.1.4.1.2011.2.25.3.40.50.294.10.1.2
        oducn_tcm5Per15MCurMonValue OBJECT-TYPE
            SYNTAX OCTET STRING (SIZE (0..100))
            MAX-ACCESS read-only
            STATUS current
            DESCRIPTION
                "perMonValue."
            ::= { oducn_tcm5Per15MCurEntry 2 }

        -- 1.3.6.1.4.1.2011.2.25.3.40.50.294.10.1.3
        oducn_tcm5Per15MCurVldty OBJECT-TYPE
            SYNTAX INTEGER
            MAX-ACCESS read-only
            STATUS current
            DESCRIPTION
                "perVldty. "
            ::= { oducn_tcm5Per15MCurEntry 3 }

        -- 1.3.6.1.4.1.2011.2.25.3.40.50.294.10.1.4
        oducn_tcm5Per15MCurDateTime OBJECT-TYPE
            SYNTAX DateAndTime
            MAX-ACCESS read-only
            STATUS current
            DESCRIPTION
                "perDateTime. "
            ::= { oducn_tcm5Per15MCurEntry 4 }

        -- 1.3.6.1.4.1.2011.2.25.3.40.50.294.10.1.5
        oducn_tcm5Per15MCurParaLen OBJECT-TYPE
            SYNTAX INTEGER
            MAX-ACCESS read-only
            STATUS current
            DESCRIPTION
                "perParaLen."
            ::= { oducn_tcm5Per15MCurEntry 5 }

        -- 1.3.6.1.4.1.2011.2.25.3.40.50.294.10.1.6
        oducn_tcm5Per15MCurPara OBJECT-TYPE
            SYNTAX OCTET STRING (SIZE (0..100))
            MAX-ACCESS read-only
            STATUS current
            DESCRIPTION
                "perPara."
            ::= { oducn_tcm5Per15MCurEntry 6 }



-- -------------------------------------------------------------------------
-- Perfomance 15-MIN History Data Table (RTRV-PER-<MOD2>)
-- -------------------------------------------------------------------------
        -- 1.3.6.1.4.1.2011.2.25.3.40.50.294.20
        oducn_tcm5Per15MHisTable OBJECT-TYPE
            SYNTAX SEQUENCE OF Oducn_tcm5Per15MHisEntry
            MAX-ACCESS not-accessible
            STATUS current
            DESCRIPTION
                "oducn_tcm5Per15MHis."
            ::= { oducn_tcm5 20 }

        -- 1.3.6.1.4.1.2011.2.25.3.40.50.294.20.1
        oducn_tcm5Per15MHisEntry OBJECT-TYPE
            SYNTAX Oducn_tcm5Per15MHisEntry
            MAX-ACCESS not-accessible
            STATUS current
            DESCRIPTION
                "oducn_tcm5Per15MHis."
            INDEX {oducn_tcm5Per15MHisEid, oducn_tcm5Per15MHisParaLen, oducn_tcm5Per15MHisPara, oducn_tcm5Per15MHisDateTimeStart, oducn_tcm5Per15MHisDateTimeEnd}
            ::= { oducn_tcm5Per15MHisTable 1 }

        Oducn_tcm5Per15MHisEntry ::=
            SEQUENCE {
                oducn_tcm5Per15MHisEid
                    PerformanceEventType,
                oducn_tcm5Per15MHisParaLen
                    INTEGER,
                oducn_tcm5Per15MHisPara
                    OCTET STRING,
                oducn_tcm5Per15MHisMonValue
                    OCTET STRING,
                oducn_tcm5Per15MHisDateTimeStart
                    DateAndTime,
                oducn_tcm5Per15MHisDateTimeEnd
                    DateAndTime,
                oducn_tcm5Per15MHisVldty
                    INTEGER,
             }

        -- 1.3.6.1.4.1.2011.2.25.3.40.50.294.20.1.1
        oducn_tcm5Per15MHisEid OBJECT-TYPE
            SYNTAX PerformanceEventType
            MAX-ACCESS read-only
            STATUS current
            DESCRIPTION
                "perEid."
            ::= { oducn_tcm5Per15MHisEntry 1 }

        -- 1.3.6.1.4.1.2011.2.25.3.40.50.294.20.1.2
        oducn_tcm5Per15MHisParaLen OBJECT-TYPE
            SYNTAX INTEGER
            MAX-ACCESS read-only
            STATUS current
            DESCRIPTION
                "perParaLen."
            ::= { oducn_tcm5Per15MHisEntry 2 }

        -- 1.3.6.1.4.1.2011.2.25.3.40.50.294.20.1.3
        oducn_tcm5Per15MHisPara OBJECT-TYPE
            SYNTAX OCTET STRING (SIZE (0..100))
            MAX-ACCESS read-only
            STATUS current
            DESCRIPTION
                "perPara."
            ::= { oducn_tcm5Per15MHisEntry 3 }

        -- 1.3.6.1.4.1.2011.2.25.3.40.50.294.20.1.4
        oducn_tcm5Per15MHisMonValue OBJECT-TYPE
            SYNTAX OCTET STRING (SIZE (0..100))
            MAX-ACCESS read-only
            STATUS current
            DESCRIPTION
                "perMonValue."
            ::= { oducn_tcm5Per15MHisEntry 4 }

        -- 1.3.6.1.4.1.2011.2.25.3.40.50.294.20.1.5
        oducn_tcm5Per15MHisDateTimeStart OBJECT-TYPE
            SYNTAX DateAndTime
            MAX-ACCESS read-only
            STATUS current
            DESCRIPTION
                "perDateTimeStart. "
            ::= { oducn_tcm5Per15MHisEntry 5 }

        -- 1.3.6.1.4.1.2011.2.25.3.40.50.294.20.1.6
        oducn_tcm5Per15MHisDateTimeEnd OBJECT-TYPE
            SYNTAX DateAndTime
            MAX-ACCESS read-only
            STATUS current
            DESCRIPTION
                "perDateTimeEnd. "
            ::= { oducn_tcm5Per15MHisEntry 6 }

        -- 1.3.6.1.4.1.2011.2.25.3.40.50.294.20.1.7
        oducn_tcm5Per15MHisVldty OBJECT-TYPE
            SYNTAX INTEGER
            MAX-ACCESS read-only
            STATUS current
            DESCRIPTION
                "perVldty. "
            ::= { oducn_tcm5Per15MHisEntry 7 }




-- -------------------------------------------------------------------------
-- Perfomance 24-HOUR Current Data Table (RTRV-PER-<MOD2>)
-- -------------------------------------------------------------------------
        -- 1.3.6.1.4.1.2011.2.25.3.40.50.294.30
        oducn_tcm5Per24HCurTable OBJECT-TYPE
          SYNTAX SEQUENCE OF Oducn_tcm5Per24HCurEntry
          MAX-ACCESS not-accessible
          STATUS current
          DESCRIPTION
              "oducn_tcm5Per24HCur."
          ::= { oducn_tcm5 30 }

        -- 1.3.6.1.4.1.2011.2.25.3.40.50.294.30.1
        oducn_tcm5Per24HCurEntry OBJECT-TYPE
            SYNTAX Oducn_tcm5Per24HCurEntry
            MAX-ACCESS not-accessible
            STATUS current
            DESCRIPTION
              "oducn_tcm5Per24HCur."
            INDEX { oducn_tcm5Per24HCurEid, oducn_tcm5Per24HCurPara }
            ::= { oducn_tcm5Per24HCurTable 1 }

        Oducn_tcm5Per24HCurEntry ::=
            SEQUENCE {
                oducn_tcm5Per24HCurEid
                    PerformanceEventType,
                oducn_tcm5Per24HCurMonValue
                    OCTET STRING,
                oducn_tcm5Per24HCurVldty
                    INTEGER,
                oducn_tcm5Per24HCurDateTime
                    DateAndTime,
                oducn_tcm5Per24HCurParaLen
                    INTEGER,
                oducn_tcm5Per24HCurPara
                    OCTET STRING
            }

        -- 1.3.6.1.4.1.2011.2.25.3.40.50.294.30.1.1
        oducn_tcm5Per24HCurEid OBJECT-TYPE
            SYNTAX PerformanceEventType
            MAX-ACCESS read-only
            STATUS current
            DESCRIPTION
                "perEid."
            ::= { oducn_tcm5Per24HCurEntry 1 }

        -- 1.3.6.1.4.1.2011.2.25.3.40.50.294.30.1.2
        oducn_tcm5Per24HCurMonValue OBJECT-TYPE
            SYNTAX OCTET STRING (SIZE (0..100))
            MAX-ACCESS read-only
            STATUS current
            DESCRIPTION
                "perMonValue."
            ::= { oducn_tcm5Per24HCurEntry 2 }

        -- 1.3.6.1.4.1.2011.2.25.3.40.50.294.30.1.3
        oducn_tcm5Per24HCurVldty OBJECT-TYPE
            SYNTAX INTEGER
            MAX-ACCESS read-only
            STATUS current
            DESCRIPTION
                "perVldty. "
            ::= { oducn_tcm5Per24HCurEntry 3 }

        -- 1.3.6.1.4.1.2011.2.25.3.40.50.294.30.1.4
        oducn_tcm5Per24HCurDateTime OBJECT-TYPE
            SYNTAX DateAndTime
            MAX-ACCESS read-only
            STATUS current
            DESCRIPTION
                "perDateTime. "
            ::= { oducn_tcm5Per24HCurEntry 4 }

        -- 1.3.6.1.4.1.2011.2.25.3.40.50.294.30.1.5
        oducn_tcm5Per24HCurParaLen OBJECT-TYPE
            SYNTAX INTEGER
            MAX-ACCESS read-only
            STATUS current
            DESCRIPTION
                "perParaLen."
            ::= { oducn_tcm5Per24HCurEntry 5 }

        -- 1.3.6.1.4.1.2011.2.25.3.40.50.294.30.1.6
        oducn_tcm5Per24HCurPara OBJECT-TYPE
            SYNTAX OCTET STRING (SIZE (0..100))
            MAX-ACCESS read-only
            STATUS current
            DESCRIPTION
                "perPara."
            ::= { oducn_tcm5Per24HCurEntry 6 }




-- -------------------------------------------------------------------------
-- Perfomance 24-HOUR History Data Table (RTRV-PER-<MOD2>)
-- -------------------------------------------------------------------------
        -- 1.3.6.1.4.1.2011.2.25.3.40.50.294.40
        oducn_tcm5Per24HHisTable OBJECT-TYPE
          SYNTAX SEQUENCE OF Oducn_tcm5Per24HHisEntry
          MAX-ACCESS not-accessible
          STATUS current
          DESCRIPTION
              "oducn_tcm5Per24HHis."
          ::= { oducn_tcm5 40 }

        -- 1.3.6.1.4.1.2011.2.25.3.40.50.294.40.1
        oducn_tcm5Per24HHisEntry OBJECT-TYPE
            SYNTAX Oducn_tcm5Per24HHisEntry
            MAX-ACCESS not-accessible
            STATUS current
            DESCRIPTION
                "oducn_tcm5Per24HHis."
            INDEX {oducn_tcm5Per24HHisEid, oducn_tcm5Per24HHisParaLen, oducn_tcm5Per24HHisPara, oducn_tcm5Per24HHisDateTimeStart, oducn_tcm5Per24HHisDateTimeEnd}
            ::= { oducn_tcm5Per24HHisTable 1 }

        Oducn_tcm5Per24HHisEntry ::=
            SEQUENCE {
                oducn_tcm5Per24HHisEid
                    PerformanceEventType,
                oducn_tcm5Per24HHisParaLen
                    INTEGER,
                oducn_tcm5Per24HHisPara
                    OCTET STRING,
                oducn_tcm5Per24HHisMonValue
                    OCTET STRING,
                oducn_tcm5Per24HHisDateTimeStart
                    DateAndTime,
                oducn_tcm5Per24HHisDateTimeEnd
                    DateAndTime,
                oducn_tcm5Per24HHisVldty
                    INTEGER,
             }

        -- 1.3.6.1.4.1.2011.2.25.3.40.50.294.40.1.1
        oducn_tcm5Per24HHisEid OBJECT-TYPE
            SYNTAX PerformanceEventType
            MAX-ACCESS read-only
            STATUS current
            DESCRIPTION
                "perEid."
            ::= { oducn_tcm5Per24HHisEntry 1 }

        -- 1.3.6.1.4.1.2011.2.25.3.40.50.294.40.1.2
        oducn_tcm5Per24HHisParaLen OBJECT-TYPE
            SYNTAX INTEGER
            MAX-ACCESS read-only
            STATUS current
            DESCRIPTION
                "perParaLen."
            ::= { oducn_tcm5Per24HHisEntry 2 }

        -- 1.3.6.1.4.1.2011.2.25.3.40.50.294.40.1.3
        oducn_tcm5Per24HHisPara OBJECT-TYPE
            SYNTAX OCTET STRING (SIZE (0..100))
            MAX-ACCESS read-only
            STATUS current
            DESCRIPTION
                "perPara."
            ::= { oducn_tcm5Per24HHisEntry 3 }

        -- 1.3.6.1.4.1.2011.2.25.3.40.50.294.40.1.4
        oducn_tcm5Per24HHisMonValue OBJECT-TYPE
            SYNTAX OCTET STRING (SIZE (0..100))
            MAX-ACCESS read-only
            STATUS current
            DESCRIPTION
                "perMonValue."
            ::= { oducn_tcm5Per24HHisEntry 4 }

        -- 1.3.6.1.4.1.2011.2.25.3.40.50.294.40.1.5
        oducn_tcm5Per24HHisDateTimeStart OBJECT-TYPE
            SYNTAX DateAndTime
            MAX-ACCESS read-only
            STATUS current
            DESCRIPTION
                "perDateTimeStart. "
            ::= { oducn_tcm5Per24HHisEntry 5 }

        -- 1.3.6.1.4.1.2011.2.25.3.40.50.294.40.1.6
        oducn_tcm5Per24HHisDateTimeEnd OBJECT-TYPE
            SYNTAX DateAndTime
            MAX-ACCESS read-only
            STATUS current
            DESCRIPTION
                "perDateTimeEnd. "
            ::= { oducn_tcm5Per24HHisEntry 6 }

        -- 1.3.6.1.4.1.2011.2.25.3.40.50.294.40.1.7
        oducn_tcm5Per24HHisVldty OBJECT-TYPE
            SYNTAX INTEGER
            MAX-ACCESS read-only
            STATUS current
            DESCRIPTION
                "perVldty. "
            ::= { oducn_tcm5Per24HHisEntry 7 }


     -- 1.3.6.1.4.1.2011.2.25.3.40.50.102
      Ethport OBJECT IDENTIFIER ::={ optixGlobalNGWDM 102 }

		-- 1.3.6.1.4.1.2011.2.25.3.40.50.102.50
		EthportDataPmStatTable OBJECT-TYPE
			SYNTAX SEQUENCE OF EthportDataPmStatEntry
			MAX-ACCESS not-accessible
			STATUS current
			DESCRIPTION
				"EthportDataPm30SCur."
			::= { Ethport 50 }

		-- 1.3.6.1.4.1.2011.2.25.3.40.50.102.50.1
		EthportDataPmStatEntry OBJECT-TYPE
			SYNTAX EthportDataPmStatEntry
			MAX-ACCESS not-accessible
			STATUS current
			DESCRIPTION
				"EthportDataPmStat."
			INDEX {EthportDataPmName, EthportDataPmParaLen, EthportDataPmPara}
			::= { EthportDataPmStatTable 1 }

		EthportDataPmStatEntry ::=
			SEQUENCE {
				EthportDataPmName
					DataPmEventType,
				EthportDataPmParaLen
					INTEGER,
				EthportDataPmPara
					DisplayString,
				EthportDataPmMonValue
					Counter64,
				EthportDataPmStartTime
					DateAndTime,
			 }
       --1.3.6.1.4.1.2011.2.25.3.40.50.102.50.1.1
		EthportDataPmName OBJECT-TYPE
			SYNTAX DataPmEventType
			MAX-ACCESS read-write
			STATUS current
			DESCRIPTION
				"DataPmName."
			::= { EthportDataPmStatEntry 1 }
       -- 1.3.6.1.4.1.2011.2.25.3.40.50.102.50.1.2
		EthportDataPmParaLen OBJECT-TYPE
			SYNTAX INTEGER
			MAX-ACCESS read-write
			STATUS current
			DESCRIPTION
				"ParaLen."
			::= { EthportDataPmStatEntry 2 }

		-- 1.3.6.1.4.1.2011.2.25.3.40.50.102.50.1.3
		EthportDataPmPara OBJECT-TYPE
			SYNTAX DisplayString
			MAX-ACCESS read-only
			STATUS current
			DESCRIPTION
				"para"
			::= { EthportDataPmStatEntry 3 }

		-- 1.3.6.1.4.1.2011.2.25.3.40.50.102.50.1.4
		EthportDataPmMonValue OBJECT-TYPE
			SYNTAX Counter64
			MAX-ACCESS read-write
			STATUS current
			DESCRIPTION
				"DataPmMonValue. "
			::= { EthportDataPmStatEntry 4 }

       -- 1.3.6.1.4.1.2011.2.25.3.40.50.102.50.1.5
		EthportDataPmStartTime OBJECT-TYPE
			SYNTAX DateAndTime
			MAX-ACCESS read-write
			STATUS current
			DESCRIPTION
				"Start Time. "
			::= { EthportDataPmStatEntry 5 }

-- 1.3.6.1.4.1.2011.2.25.3.40.50.102.60
		EthportDataPm30SHisTable OBJECT-TYPE
			SYNTAX SEQUENCE OF EthportDataPm30SHisEntry
			MAX-ACCESS not-accessible
			STATUS current
			DESCRIPTION
				"EthportDataPm30SHis."
			::= { Ethport 60 }

		-- 1.3.6.1.4.1.2011.2.25.3.40.50.102.60.1
		EthportDataPm30SHisEntry OBJECT-TYPE
			SYNTAX EthportDataPm30SHisEntry
			MAX-ACCESS not-accessible
			STATUS current
			DESCRIPTION
				"EthportDataPm30SHis."
			INDEX {EthportDataPmName, EthportDataPmParaLen, EthportDataPmPara, EthportDataPmStartTime, EthportDataPmEndTime}
			::= { EthportDataPm30SHisTable 1 }

		EthportDataPm30SHisEntry ::=
			SEQUENCE {
				EthportDataPm30SHisName
					DataPmEventType,
				EthportDataPm30SHisParaLen
					INTEGER,
				EthportDataPm30SHisPara
					DisplayString,
				EthportDataPm30SHisMonValue
					Counter64,
				EthportDataPm30SHisStartTime
					DateAndTime,
				EthportDataPm30SHisEndTime
					DateAndTime,
				EthportDataPm30SValidity
					ValidflagType,
			 }
-- 1.3.6.1.4.1.2011.2.25.3.40.50.102.60.1.1
		EthportDataPm30SHisName OBJECT-TYPE
			SYNTAX DataPmEventType
			MAX-ACCESS read-write
			STATUS current
			DESCRIPTION
				"DataPmName."
			::= { EthportDataPm30SHisEntry 1 }
-- 1.3.6.1.4.1.2011.2.25.3.40.50.102.60.1.2
		EthportDataPm30SHisParaLen OBJECT-TYPE
			SYNTAX INTEGER
			MAX-ACCESS read-write
			STATUS current
			DESCRIPTION
				"ParaLen."
			::= { EthportDataPm30SHisEntry 2 }

	-- 1.3.6.1.4.1.2011.2.25.3.40.50.102.60.1.3
		EthportDataPm30SHisPara OBJECT-TYPE
			SYNTAX DisplayString
			MAX-ACCESS read-only
			STATUS current
			DESCRIPTION
				"para"
			::= { EthportDataPm30SHisEntry 3 }


-- 1.3.6.1.4.1.2011.2.25.3.40.50.102.60.1.4
		EthportDataPm30SHisMonValue OBJECT-TYPE
			SYNTAX Counter64
			MAX-ACCESS read-write
			STATUS current
			DESCRIPTION
				"DataPmMonValue. "
			::= { EthportDataPm30SHisEntry 4 }
-- 1.3.6.1.4.1.2011.2.25.3.40.50.102.60.1.5
		EthportDataPm30SHisStartTime OBJECT-TYPE
			SYNTAX DateAndTime
			MAX-ACCESS read-write
			STATUS current
			DESCRIPTION
				"Start Time. "
			::= { EthportDataPm30SHisEntry 5 }
-- 1.3.6.1.4.1.2011.2.25.3.40.50.102.60.1.6
		EthportDataPm30SHisEndTime OBJECT-TYPE
			SYNTAX DateAndTime
			MAX-ACCESS read-write
			STATUS current
			DESCRIPTION
				"End Time. "
			::= { EthportDataPm30SHisEntry 6 }
-- 1.3.6.1.4.1.2011.2.25.3.40.50.102.60.1.7
		EthportDataPm30SValidity OBJECT-TYPE
			SYNTAX ValidflagType
			MAX-ACCESS read-write
			STATUS current
			DESCRIPTION
				"Validity. "
			::= { EthportDataPm30SHisEntry 7 }


 -- -------------------------------------------------------------------------
-- Perfomance 24-HOUR History Data Table (RTRV-PER-<MOD2>)
-- -------------------------------------------------------------------------

      -- 1.3.6.1.4.1.2011.2.25.3.40.50.149
      Eth_vcgport OBJECT IDENTIFIER ::={ optixGlobalNGWDM 149 }

-- ------------------------------------------	-------------------------------
-- DataPmfomance 30-MIN Current Data Table (RTRV-DataPm-<MOD2>)
-- -------------------------------------------------------------------------
		-- 1.3.6.1.4.1.2011.2.25.3.40.50.149.50
		Eth_vcgportDataPmStatTable OBJECT-TYPE
			SYNTAX SEQUENCE OF Eth_vcgportDataPmStatEntry
			MAX-ACCESS not-accessible
			STATUS current
			DESCRIPTION
				"Eth_vcgportDataPm30SCur."
			::= { Eth_vcgport 50 }

		-- 1.3.6.1.4.1.2011.2.25.3.40.50.149.50.1
		Eth_vcgportDataPmStatEntry OBJECT-TYPE
			SYNTAX Eth_vcgportDataPmStatEntry
			MAX-ACCESS not-accessible
			STATUS current
			DESCRIPTION
				"Eth_vcgportDataPmStat."
			INDEX {Eth_vcgportDataPmName, Eth_vcgportDataPmParaLen, Eth_vcgportDataPmPara}
			::= { Eth_vcgportDataPmStatTable 1 }

		Eth_vcgportDataPmStatEntry ::=
			SEQUENCE {
				Eth_vcgportDataPmName
					DataPmEventType,
				Eth_vcgportDataPmParaLen
					INTEGER,
				Eth_vcgportDataPmPara
					DisplayString,
				Eth_vcgportDataPmMonValue
					Counter64,
				Eth_vcgportDataPmStartTime
					DateAndTime,
			 }
       --1.3.6.1.4.1.2011.2.25.3.40.50.149.50.1.1
		Eth_vcgportDataPmName OBJECT-TYPE
			SYNTAX DataPmEventType
			MAX-ACCESS read-write
			STATUS current
			DESCRIPTION
				"DataPmName."
			::= { Eth_vcgportDataPmStatEntry 1 }
       -- 1.3.6.1.4.1.2011.2.25.3.40.50.149.50.1.2
		Eth_vcgportDataPmParaLen OBJECT-TYPE
			SYNTAX INTEGER
			MAX-ACCESS read-write
			STATUS current
			DESCRIPTION
				"ParaLen."
			::= { Eth_vcgportDataPmStatEntry 2 }

		-- 1.3.6.1.4.1.2011.2.25.3.40.50.149.50.1.3
		Eth_vcgportDataPmPara OBJECT-TYPE
			SYNTAX DisplayString
			MAX-ACCESS read-only
			STATUS current
			DESCRIPTION
				"para"
			::= { Eth_vcgportDataPmStatEntry 3 }

		-- 1.3.6.1.4.1.2011.2.25.3.40.50.149.50.1.4
		Eth_vcgportDataPmMonValue OBJECT-TYPE
			SYNTAX Counter64
			MAX-ACCESS read-write
			STATUS current
			DESCRIPTION
				"DataPmMonValue. "
			::= { Eth_vcgportDataPmStatEntry 4 }

       -- 1.3.6.1.4.1.2011.2.25.3.40.50.149.50.1.5
		Eth_vcgportDataPmStartTime OBJECT-TYPE
			SYNTAX DateAndTime
			MAX-ACCESS read-write
			STATUS current
			DESCRIPTION
				"Start Time. "
			::= { Eth_vcgportDataPmStatEntry 5 }

-- 1.3.6.1.4.1.2011.2.25.3.40.50.149.60
		Eth_vcgportDataPm30SHisTable OBJECT-TYPE
			SYNTAX SEQUENCE OF Eth_vcgportDataPm30SHisEntry
			MAX-ACCESS not-accessible
			STATUS current
			DESCRIPTION
				"Eth_vcgportDataPm30SHis."
			::= { Eth_vcgport 60 }

		-- 1.3.6.1.4.1.2011.2.25.3.40.50.149.60.1
		Eth_vcgportDataPm30SHisEntry OBJECT-TYPE
			SYNTAX Eth_vcgportDataPm30SHisEntry
			MAX-ACCESS not-accessible
			STATUS current
			DESCRIPTION
				"Eth_vcgportDataPm30SHis."
			INDEX {Eth_vcgportDataPmName, Eth_vcgportDataPmParaLen, Eth_vcgportDataPmPara, Eth_vcgportDataPmStartTime, Eth_vcgportDataPmEndTime}
			::= { Eth_vcgportDataPm30SHisTable 1 }

		Eth_vcgportDataPm30SHisEntry ::=
			SEQUENCE {
				Eth_vcgportDataPm30SHisName
					DataPmEventType,
				Eth_vcgportDataPm30SHisParaLen
					INTEGER,
				Eth_vcgportDataPm30SHisPara
					DisplayString,
				Eth_vcgportDataPm30SHisMonValue
					Counter64,
				Eth_vcgportDataPm30SHisStartTime
					DateAndTime,
				Eth_vcgportDataPm30SHisEndTime
					DateAndTime,
				Eth_vcgportDataPm30SValidity
					ValidflagType,
			 }
-- 1.3.6.1.4.1.2011.2.25.3.40.50.149.60.1.1
		Eth_vcgportDataPm30SHisName OBJECT-TYPE
			SYNTAX DataPmEventType
			MAX-ACCESS read-write
			STATUS current
			DESCRIPTION
				"DataPmName."
			::= { Eth_vcgportDataPm30SHisEntry 1 }
-- 1.3.6.1.4.1.2011.2.25.3.40.50.149.60.1.2
		Eth_vcgportDataPm30SHisParaLen OBJECT-TYPE
			SYNTAX INTEGER
			MAX-ACCESS read-write
			STATUS current
			DESCRIPTION
				"ParaLen."
			::= { Eth_vcgportDataPm30SHisEntry 2 }

	-- 1.3.6.1.4.1.2011.2.25.3.40.50.149.60.1.3
		Eth_vcgportDataPm30SHisPara OBJECT-TYPE
			SYNTAX DisplayString
			MAX-ACCESS read-only
			STATUS current
			DESCRIPTION
				"para"
			::= { Eth_vcgportDataPm30SHisEntry 3 }


-- 1.3.6.1.4.1.2011.2.25.3.40.50.149.60.1.4
		Eth_vcgportDataPm30SHisMonValue OBJECT-TYPE
			SYNTAX Counter64
			MAX-ACCESS read-write
			STATUS current
			DESCRIPTION
				"DataPmMonValue. "
			::= { Eth_vcgportDataPm30SHisEntry 4 }
-- 1.3.6.1.4.1.2011.2.25.3.40.50.149.60.1.5
		Eth_vcgportDataPm30SHisStartTime OBJECT-TYPE
			SYNTAX DateAndTime
			MAX-ACCESS read-write
			STATUS current
			DESCRIPTION
				"Start Time. "
			::= { Eth_vcgportDataPm30SHisEntry 5 }
-- 1.3.6.1.4.1.2011.2.25.3.40.50.149.60.1.6
		Eth_vcgportDataPm30SHisEndTime OBJECT-TYPE
			SYNTAX DateAndTime
			MAX-ACCESS read-write
			STATUS current
			DESCRIPTION
				"End Time. "
			::= { Eth_vcgportDataPm30SHisEntry 6 }
-- 1.3.6.1.4.1.2011.2.25.3.40.50.149.60.1.7
		Eth_vcgportDataPm30SValidity OBJECT-TYPE
			SYNTAX ValidflagType
			MAX-ACCESS read-write
			STATUS current
			DESCRIPTION
				"Validity. "
			::= { Eth_vcgportDataPm30SHisEntry 7 }



	END
--
-- OPTIX-SONET-DataPm-MIB.mib
--
