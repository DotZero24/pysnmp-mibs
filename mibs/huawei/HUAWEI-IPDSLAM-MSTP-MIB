-- =======================================================================================================
-- Copyright (C) 2014 by  HUAWEI TECHNOLOGIES. All rights reserved.
-- Description: The mib is used for defining MIB objects of the multiple spanning tree protocol (MSTP).
--              MSTP is an improvement of STP and RSTP.
--              MSTP prevents the proliferation and infinite cycling of the packets in the loop network.
--              In addition, MSTP provides multiple redundant paths for VLAN data transmission to
--              achieve the load-sharing purpose.
--              It supports MSTP loop network that helps meet various networking requirements.
-- Reference:
-- Version: V1.16
-- ========================================================================================================
    HUAWEI-IPDSLAM-MSTP-MIB  DEFINITIONS ::= BEGIN

        IMPORTS

            MODULE-IDENTITY,OBJECT-TYPE,Counter32, OBJECT-IDENTITY, NOTIFICATION-TYPE, Integer32
                FROM SNMPv2-SMI
            TEXTUAL-CONVENTION,RowStatus
                FROM SNMPv2-TC
            OBJECT-GROUP, MODULE-COMPLIANCE
                FROM SNMPv2-CONF
            hwDatacomm
                FROM HUAWEI-MIB;

            hwL2Mgmt  OBJECT IDENTIFIER ::= { hwDatacomm 42 }
            hwMstp MODULE-IDENTITY
            LAST-UPDATED "201406100000Z"
            ORGANIZATION "Huawei Technologies Co.,Ltd."
            CONTACT-INFO
                "Huawei Industrial Base
                 Bantian, Longgang
                 Shenzhen 518129
                 People's Republic of China
                 Website: http://www.huawei.com
                 Email: support@huawei.com
                "
            DESCRIPTION
                "The mib is used for defining MIB objects of the multiple spanning tree protocol (MSTP).
                 MSTP is an improvement of STP and RSTP.
                 MSTP prevents the proliferation and infinite cycling of the packets in the loop network.
                 In addition, MSTP provides multiple redundant paths for VLAN data transmission to
                 achieve the load-sharing purpose.
                 It supports MSTP loop network that helps meet various networking requirements."

            --  Revision history
            REVISION     "201408120000Z"
            DESCRIPTION  "V1.16, modified the description of hwMstpiBridgeID hwMstpiOperMappedVlanListLow and hwMstpiOperMappedVlanListHigh"

            REVISION     "201406100000Z"
            DESCRIPTION  "V1.15, modified the MAX-ACCESS of hwMstpInstanceID and hwMstpiPortIndex"

            REVISION     "201211280000Z"
            DESCRIPTION  "V1.14, modified the attribute of node hwMstpiRowStatus in table hwMstpInstanceTable"

            REVISION     "201208130000Z"
            DESCRIPTION  "V1.13, modified the node hwMstpiPortState in table hwMstpPortTable"

            REVISION     "201205040000Z"
            DESCRIPTION  "V1.12, added the node hwMstpiPortCompliance in table hwMstpPortTable."

            REVISION     "201204270000Z"
            DESCRIPTION  "V1.11, modified the description of node hwMstpRegionConfActive."

            REVISION     "201204120000Z"
            DESCRIPTION  "V1.10, added the node hwMstpiBridgeCurrentPriority in table hwMstpInstanceTable."

            REVISION     "201111140000Z"
            DESCRIPTION  "V1.09, added two nodes hwMstpiBridgeSecondaryPriority and hwMstpiBridgeSecondaryPriorityBindPort."

            REVISION     "201011200000Z"
            DESCRIPTION  "V1.08, modified the descriptions of this MIB file and leaves."

            REVISION     "201007191936Z"
            DESCRIPTION  "V1.07, modified the description of leaves."

            REVISION     "201007120000Z"
            DESCRIPTION  "V1.06, modified the description of node hwMstpMasterBridgeID, hwMstpiBridgeID, hwMstpiAdminMappedVlanListLow, hwMstpiAdminMappedVlanListHigh, hwMstpiOperMappedVlanListLow, hwMstpiOperMappedVlanListHigh, hwMstpiDesignatedRoot"

            REVISION     "201004260000Z"
            DESCRIPTION  "V1.05, modified enumeration format.Add trap hwMstpiPortDisable, hwMstpiPortBpduGuardedResume, hwMstpiPortRootGuardedResume to hwMstpTraps"

            REVISION     "201002271500Z"
            DESCRIPTION  "V1.04, modified the description of node hwMstpPathCostStandard."

            REVISION     "200912301500Z"
            DESCRIPTION  "V1.03, modified datatype definition,description of objects,Add hwMstpTraps in hwMstp. Add hwMstpAlarmTraps in hwMstpTraps."

            REVISION     "200711250000Z"
            DESCRIPTION  "V1.01, modified node(hwMstpiPortState) value,from(3:learning,4:forwarding)to(4:learning,5:forwarding)"

            REVISION     "200504191936Z"
            DESCRIPTION  "V1.00, initial version."

            ::= { hwL2Mgmt 4 }

        HwMSTPEnabledStatus ::= TEXTUAL-CONVENTION
            STATUS      current
            DESCRIPTION
                "A simple status value for the object.
                "
            SYNTAX  INTEGER
                {
                enabled(1),
                disabled(2)
                }

        hwMstpObjects OBJECT IDENTIFIER ::= {  hwMstp 1  }

        hwMstpStatus OBJECT-TYPE
            SYNTAX      HwMSTPEnabledStatus
            MAX-ACCESS  read-write
            STATUS      current
            DESCRIPTION
                "Indicates the status of the MSTP function of a bridge.
                 Options:
                 1. enabled(1)  -indicates the MSTP function of a bridge is enabled
                 2. disabled(2) -indicates the MSTP function of a bridge is disabled
                 Default: disabled(2)
                "

            ::= { hwMstpObjects 1 }

        hwMstpForceVersion OBJECT-TYPE
            SYNTAX INTEGER
                {
                stp(0),
                rstp(2),
                mstp(3)
                }
            MAX-ACCESS  read-write
            STATUS      current
            DESCRIPTION
                "Indicates the MSTP version of the current bridge.
                 Options:
                 1. stp(0)  -indicates the MSTP version of the current bridge is stp
                 2. rstp(2) -indicates the MSTP version of the current bridge is rstp
                 3. mstp(3) -indicates the MSTP version of the current bridge is mstp
                 Default: mstp(3)
                 rstp(2) is not supported.
                "
            ::= { hwMstpObjects 2 }

        hwMstpDiameter OBJECT-TYPE
            SYNTAX      Integer32(2..7)
            MAX-ACCESS  read-write
            STATUS      current
            DESCRIPTION
                "Indicates the diameter of the current bridged network.
                 Range: 2-7
                 Default: 7
                "
            ::= { hwMstpObjects 3 }

        hwMstpBridgeMaxHops OBJECT-TYPE
            SYNTAX      Integer32(1..40)
            MAX-ACCESS  read-write
            STATUS      current
            DESCRIPTION
                "Indicates the maximum hop count of a region.
                 Range: 1-40
                 Default: 20
                "
            ::= { hwMstpObjects 4 }

        hwMstpMasterBridgeID OBJECT-TYPE
            SYNTAX      OCTET STRING (SIZE (8))
            MAX-ACCESS  read-only
            STATUS      current
            DESCRIPTION
                "Indicates the master bridge ID of an IST in an MSTP region.
                 It is the root Bridge Identifier of the instance 0 in the region.
                 The format of the bridge ID is bridge priority (2B) + bridge MAC address (6B).
                 For example, if the bridge priority is 32768, and the bridge MAC address is 00.EE.DC.F9.13.20,
                 then the bridge ID is 80.00.00.EE.DC.F9.13.20.
                "
            ::= { hwMstpObjects 5 }

        hwMstpMasterPathCost OBJECT-TYPE
            SYNTAX      Integer32
            MAX-ACCESS  read-only
            STATUS      current
            DESCRIPTION
                "Indicates the external path cost.
                 The value range of this leaf is relevant to hwMstpPathCostStandard.
                 Range: 1-65535     (The 802.1d-1998 protocol is used as the computing standard)
                        1-200000000 (The 802.1t protocol is used as the computing standard)
                        1-200000    (Huawei's proprietary legacy is used as the computing standard)
                "
            ::= { hwMstpObjects 6 }

        hwMstpBpduGuard OBJECT-TYPE
            SYNTAX      HwMSTPEnabledStatus
            MAX-ACCESS  read-write
            STATUS      current
            DESCRIPTION
                "Indicates whether a bridge is enabled with BPDU protection.
                 Options:
                 1. enabled(1)  -indicates BPDU protection of the bridge is enabled
                 2. disabled(2) -indicates BPDU protection of the bridge is disabled
                 Default: disabled(2)
                "
            ::= { hwMstpObjects 7 }

        hwMstpAdminFormatSelector OBJECT-TYPE
            SYNTAX      Integer32
            MAX-ACCESS  read-only
            STATUS      current
            DESCRIPTION
                "Indicates the configuration ID format of a bridge.
                "
            ::= { hwMstpObjects 8 }

        hwMstpAdminRegionName OBJECT-TYPE
            SYNTAX      OCTET STRING(SIZE(1..32))
            MAX-ACCESS  read-write
            STATUS      current
            DESCRIPTION
                "Indicates the MSTP region name. The region name consists of up to 32 characters,
                 and only letters (case sensitive), numerals, the hyphen (-), and the underline (_)
                 are allowed.
                "
            ::= { hwMstpObjects 9 }

        hwMstpAdminRevisionLevel OBJECT-TYPE
            SYNTAX      Integer32(0..65535)
            MAX-ACCESS  read-write
            STATUS      current
            DESCRIPTION
                "Indicates the revision level of an MSTP region name.
                 Range: 0-65535
                 Default: 0
                "
            ::= { hwMstpObjects 10 }

        hwMstpOperFormatSelector OBJECT-TYPE
            SYNTAX      Integer32
            MAX-ACCESS  read-only
            STATUS      current
            DESCRIPTION
                "Indicates the configuration format of the region of a bridge in actual running.
                "
            ::= { hwMstpObjects 11 }

        hwMstpOperRegionName OBJECT-TYPE
            SYNTAX      OCTET STRING( SIZE(0..32) )
            MAX-ACCESS  read-only
            STATUS      current
            DESCRIPTION
                "Indicates the actually-used MSTP region name.
                "
            ::= { hwMstpObjects 12 }

        hwMstpOperRevisionLevel OBJECT-TYPE
            SYNTAX      Integer32(0..65535)
            MAX-ACCESS  read-only
            STATUS      current
            DESCRIPTION
                "Indicates the revision level of the actually-used MSTP region name.
                 Default: 0
                "
            ::= { hwMstpObjects 13 }

        hwMstpRegionConfActive OBJECT-TYPE
            SYNTAX      INTEGER{enable(1),disable(2)}
            MAX-ACCESS  read-write
            STATUS      current
            DESCRIPTION
                "Indicates whether to activate the modified MSTP region configuration.
                 Options:
                 1. enable (1) -when you need to activate the modified MSTP region configuration, use this value to perform the set operation.
                 2. disable(2) -the modified MSTP region configuration cannot be set to disable. When you perform the get operation to query the configuration, this value will be returned.
                 This leaf supports only the set operation and it is recommended that you do not perform the get operation. If you perform the get operation, the value disable (2) will be returned.
                "
            ::= { hwMstpObjects 14 }

        hwMstpDefaultVlanAllo OBJECT-TYPE
            SYNTAX      INTEGER{enable(1),unused(65535)}
            MAX-ACCESS  read-write
            STATUS      current
            DESCRIPTION
                "Sets the default mapping between VLANs and spanning trees.
                 Options:
                 1. enable(1)     -indicates the default mapping between VLANs and spanning trees is enabled
                 2. unused(65535) -indicates the default mapping between VLANs and spanning trees is unused
                "
            ::= { hwMstpObjects 15 }

        hwMstpDefaultRegionName OBJECT-TYPE
            SYNTAX      INTEGER{reset(1),unused(65535)}
            MAX-ACCESS  read-write
            STATUS      current
            DESCRIPTION
                "Sets the default region name.
                 Options:
                 1. reset(1)      -indicates the default region name is used
                 2. unused(65535) -indicates the default region name is unused
                "
            ::= { hwMstpObjects 16 }

        hwMstpPathCostStandard  OBJECT-TYPE
            SYNTAX      INTEGER{dot1d1998(1),dot1t(2),legacy(3)}
            MAX-ACCESS  read-write
            STATUS      current
            DESCRIPTION
                "Indicates the reference standard for path cost computation of a bridge.
                 Options:
                 1. dot1d1998(1) -indicates dot1d1998 is the reference standard for path cost computation of a bridge
                 2. dot1t(2)     -indicates dot1t is the reference standard for path cost computation of a bridge
                 3. legacy(3)    -indicates legacy is the reference standard for path cost computation of a bridge
                 Default: legacy(3)
                "
            ::= { hwMstpObjects 17 }

        hwMstpTimeFactor  OBJECT-TYPE
            SYNTAX      Integer32 (1..10)
            MAX-ACCESS  read-write
            STATUS      current
            DESCRIPTION
                "Indicates the timeout factor of a bridge.
                 Range: 1-10
                 Default: 3
                "
            ::= { hwMstpObjects 21 }

        hwMstpMD5KEY  OBJECT-TYPE
            SYNTAX      OCTET STRING (SIZE(0..16))
            MAX-ACCESS  read-write
            STATUS      current
            DESCRIPTION
                "Indicates the MD5 key used for generating the region configuration digest of the MSTP protocol.
                 Default: 0x13AC06A62E47FD51F95D2BA243CD0346
                "
            ::= { hwMstpObjects 22 }

        hwMstpVIDAllocationTable OBJECT-TYPE
            SYNTAX      SEQUENCE OF HwMstpVIDAllocationEntry
            MAX-ACCESS  not-accessible
            STATUS      current
            DESCRIPTION
                "Indicates the mapping between VLANs and instances extended by MSTP.
                 The index of this table is hwMstpVID.
                "
            ::= { hwMstpObjects 18 }

        hwMstpVIDAllocationEntry OBJECT-TYPE
            SYNTAX      HwMstpVIDAllocationEntry
            MAX-ACCESS  not-accessible
            STATUS      current
            DESCRIPTION
                "Indicates the mapping between VLANs and instances extended by MSTP.
                 The index of this entry is hwMstpVID.
                "
            INDEX { hwMstpVID }
            ::= { hwMstpVIDAllocationTable 1 }

        HwMstpVIDAllocationEntry ::=
            SEQUENCE
                {
                hwMstpVID    Integer32,
                hwMstpAdminMstID    Integer32,
                hwMstpOperMstID    Integer32
                }

        hwMstpVID OBJECT-TYPE
            SYNTAX      Integer32(1..4094)
            MAX-ACCESS  not-accessible
            STATUS      current
            DESCRIPTION
                "It is an index and indicates the VLAN ID.
                 Range: 1-4094
                "
            ::={ hwMstpVIDAllocationEntry 1 }

        hwMstpAdminMstID OBJECT-TYPE
            SYNTAX      Integer32(0..48)
            MAX-ACCESS  read-only
            STATUS      current
            DESCRIPTION
                "Indicates the configured MSTP region ID. Currently, the system supports
                 only 17 instances, that is, instances 0-16.
                 Range: 0-48
                "
            ::={ hwMstpVIDAllocationEntry 2 }

        hwMstpOperMstID OBJECT-TYPE
            SYNTAX      Integer32(0..48)
            MAX-ACCESS  read-only
            STATUS      current
            DESCRIPTION
                "Indicates the MSTP region ID in actual running. Currently, the system
                 supports only 17 instances, that is, instances 0-16.
                 Range: 0-48
                "
            ::={ hwMstpVIDAllocationEntry 3 }

        hwMstpInstanceTable OBJECT-TYPE
            SYNTAX      SEQUENCE OF HwMstpInstanceEntry
            MAX-ACCESS  not-accessible
            STATUS      current
            DESCRIPTION
                "Indicates the instances extended by MSTP.
                 The index of this table is hwMstpInstanceID.
                "
            ::= { hwMstpObjects 19 }

        hwMstpInstanceEntry OBJECT-TYPE
            SYNTAX      HwMstpInstanceEntry
            MAX-ACCESS  not-accessible
            STATUS      current
            DESCRIPTION
                "Indicates the instances extended by MSTP.
                 The index of this entry is hwMstpInstanceID.
                "
            INDEX { hwMstpInstanceID }
            ::= { hwMstpInstanceTable 1 }

        HwMstpInstanceEntry ::=
            SEQUENCE
                {
                hwMstpInstanceID
                    Integer32,
                hwMstpiBridgeID
                    OCTET STRING,
                hwMstpiBridgePriority
                    Integer32,
                hwMstpiDesignedRoot
                    OCTET STRING,
                hwMstpiRootPathCost
                    Integer32,
                hwMstpiRootPort
                    Integer32,
                hwMstpiRootType
                    INTEGER,
                hwMstpiRemainingHops
                    Integer32,
                hwMstpiAdminMappedVlanListLow
                    OCTET STRING,
                hwMstpiAdminMappedVlanListHigh
                    OCTET STRING,
                hwMstpiOperMappedVlanListLow
                    OCTET STRING,
                hwMstpiOperMappedVlanListHigh
                    OCTET STRING,
                hwMstpiRowStatus
                    RowStatus,
                hwMstpiBridgeSecondaryPriority
                    Integer32,
                hwMstpiBridgeSecondaryPriorityBindPort
                    Integer32,
                hwMstpiBridgeCurrentPriority
                    Integer32
                }

        hwMstpInstanceID OBJECT-TYPE
            SYNTAX      Integer32(0..48)
            MAX-ACCESS  accessible-for-notify
            STATUS      current
            DESCRIPTION
                "It is an index and indicates the MSTI ID.
                "
            ::={ hwMstpInstanceEntry 1 }

        hwMstpiBridgeID OBJECT-TYPE
            SYNTAX      OCTET STRING (SIZE (8))
            MAX-ACCESS  read-only
            STATUS      current
            DESCRIPTION
                "The Bridge Identifier for the spanning tree instance identified by MSTID.
                 The bridge ID consists of the sum (2 bytes) of bridge priority and instance ID + the bridge MAC address (6 bytes).
                 For example, if the bridge priority is 32768 (its hexadecimal value is 80.00),
                 the instance ID is 1, and the bridge MAC address is 00.E0.FC.F9.13.20,
                 the bridge ID is 80.01.00.E0.FC.F9.13.20.
                "
            ::={ hwMstpInstanceEntry 2 }

        hwMstpiBridgePriority OBJECT-TYPE
            SYNTAX      Integer32(0..61440)
            MAX-ACCESS  read-create
            STATUS      current
            DESCRIPTION
                "Indicates the primary priority of the CIST bridge, or priority of the bridge in others.
                 Range: 0-61440
                 Default: 32768
                 Step: 4096
                "
            DEFVAL { 32768 }
            ::={ hwMstpInstanceEntry 3 }

        hwMstpiDesignedRoot OBJECT-TYPE
            SYNTAX      OCTET STRING (SIZE (8))
            MAX-ACCESS  read-only
            STATUS      current
            DESCRIPTION
                "Indicates the master bridge ID of an MSTI in the region.
                "
            ::={ hwMstpInstanceEntry 4 }

        hwMstpiRootPathCost OBJECT-TYPE
            SYNTAX      Integer32
            MAX-ACCESS  read-only
            STATUS      current
            DESCRIPTION
                "Indicates the cost of the path from the BPDU-transmitting bridge to the root bridge.
                "
            ::={ hwMstpInstanceEntry 5 }

        hwMstpiRootPort OBJECT-TYPE
            SYNTAX      Integer32
            MAX-ACCESS  read-only
            STATUS      current
            DESCRIPTION
                "Indicates the root port of an MSTI in the region.
                "
            ::={ hwMstpInstanceEntry 6 }

        hwMstpiRootType OBJECT-TYPE
            SYNTAX  INTEGER
                {
                normal(0),
                secondary(1),
                primary(2)
                }
            MAX-ACCESS  read-create
            STATUS      current
            DESCRIPTION
                "Indicates the type of the bridge.
                 Options:
                 1. normal(0)    -indicates the bridge is normal
                 2. secondary(1) -indicates the bridge is secondary
                 3. primary(2)   -indicates the bridge is primary
                 Default: normal(0)
                "
            DEFVAL { normal }
            ::={ hwMstpInstanceEntry 7 }

        hwMstpiRemainingHops OBJECT-TYPE
            SYNTAX      Integer32
            MAX-ACCESS  read-only
            STATUS      current
            DESCRIPTION
                "Indicates the remaining hops of an MSTI in the region.
                "
            ::={ hwMstpInstanceEntry 8 }

        hwMstpiAdminMappedVlanListLow  OBJECT-TYPE
            SYNTAX  OCTET STRING (SIZE(0..256))
            MAX-ACCESS read-create
            STATUS current
            DESCRIPTION
                "Used for setting the mapping between the first 2047 VLANs (VLAN 1 to VLAN 2047) in a VLAN list and MSTIs.
                 For example, if the vlan 1 and vlan 2047 belongs to this instance,
                 the hwMstpiAdminMappedVlanListLow is # 40.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.01.
                "
            ::= { hwMstpInstanceEntry 9 }

        hwMstpiAdminMappedVlanListHigh  OBJECT-TYPE
            SYNTAX  OCTET STRING (SIZE(0..256))
            MAX-ACCESS read-create
            STATUS current
            DESCRIPTION
                "Used for setting the mapping between the last 2047 VLANs (VLAN 2048 to VLAN 4094) in a VLAN list and MSTIs.
                 For example, if the vlan 2048 and vlan 4094 belongs to this instance,
                 the hwMstpiAdminMappedVlanListHigh is # 80.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.02.
                "
            ::= { hwMstpInstanceEntry 10 }

        hwMstpiOperMappedVlanListLow  OBJECT-TYPE
            SYNTAX  OCTET STRING (SIZE(0..256))
            MAX-ACCESS read-only
            STATUS current
            DESCRIPTION
                "Used for getting the mapping between the first 2047 VLANs (VLAN 1 to VLAN 2047) in a VLAN list and MSTIs in
                 actual running.
                 For example, if the vlan 1 and vlan 2047 belongs to this instance,
                 the hwMstpiOperMappedVlanListLow is # 40.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.01.
                "
            ::= { hwMstpInstanceEntry 11 }

        hwMstpiOperMappedVlanListHigh  OBJECT-TYPE
            SYNTAX  OCTET STRING (SIZE(0..256))
            MAX-ACCESS read-only
            STATUS current
            DESCRIPTION
                "Used for getting the mapping between the last 2047 VLANs (VLAN 2048 to VLAN 4094) in a VLAN list and MSTIs in actual running.
                 For example, if the vlan 2048 and vlan 4094 belongs to this instance,
                 the hwMstpiOperMappedVlanListHigh is # 80.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.00.02.
                "
            ::= { hwMstpInstanceEntry 12 }

        hwMstpiRowStatus  OBJECT-TYPE
            SYNTAX  RowStatus
            MAX-ACCESS  read-create
            STATUS      deprecated
            DESCRIPTION
                "Indicates the row status, which is the operation type of the table.
                 Only option createAndGo(4) supports the set operation.
                 In the query operation, the value of this leaf is always active(1).
                 To create an MSTI, optionally input leaves hwMstpiBridgePriority, hwMstpiRootType,
                 hwMstpiAdminMappedVlanListLow, and hwMstpiAdminMappedVlanListHigh, specify the value
                 of hwMstpiRowStatus to createAndGo(4), and perform the set operation.
                 To modify the values of other leaves, you can directly perform the set operation without
                 setting and issuing the row status.
                 Options:
                 1. active(1)         -indicates the query operation
                 2. createAndGo(4)    -indicates creating an MSTI
                 3. destroy(6)        -indicates deleting an MSTI
                "
            ::= { hwMstpInstanceEntry 13 }

        hwMstpiBridgeSecondaryPriority OBJECT-TYPE
            SYNTAX      Integer32(0..61440)
            MAX-ACCESS  read-create
            STATUS      current
            DESCRIPTION
                "Indicates the secondary priority of the CIST bridge. Only used by CIST.
                 Range: 0-61440
                 Default: 61440
                 Step: 4096
                "
            DEFVAL { 61440 }
            ::= { hwMstpInstanceEntry 14 }

        hwMstpiBridgeSecondaryPriorityBindPort OBJECT-TYPE
            SYNTAX      Integer32
            MAX-ACCESS  read-create
            STATUS      current
            DESCRIPTION
                "Indicates the port which bound secondary priority of the CIST bridge in the region. Only used by CIST.
                 Default: 0
                "
            DEFVAL { 0 }
            ::= { hwMstpInstanceEntry 15 }

        hwMstpiBridgeCurrentPriority OBJECT-TYPE
            SYNTAX      Integer32(0..61440)
            MAX-ACCESS  read-only
            STATUS      current
            DESCRIPTION
                "Indicates the current priority of the bridge, including CIST and others.
                Range: 0-61440
                "
            ::= { hwMstpInstanceEntry 16 }

        hwMstpPortTable OBJECT-TYPE
            SYNTAX      SEQUENCE OF HwMstpPortEntry
            MAX-ACCESS  not-accessible
            STATUS      current
            DESCRIPTION
                "Indicates the ports extended by MSTP.
                 The indexes of this table are hwMstpInstanceID and hwMstpiPortIndex.
                "
            ::= { hwMstpObjects 20 }

        hwMstpPortEntry OBJECT-TYPE
            SYNTAX      HwMstpPortEntry
            MAX-ACCESS  not-accessible
            STATUS      current
            DESCRIPTION
                "Indicates the ports extended by MSTP.
                 The indexes of this entry are hwMstpInstanceID and hwMstpiPortIndex.
                "
            INDEX { hwMstpInstanceID, hwMstpiPortIndex }
            ::= { hwMstpPortTable 1 }

        HwMstpPortEntry ::=
            SEQUENCE
                {
                hwMstpiPortIndex
                    Integer32,
                hwMstpiPortState
                    INTEGER,
                hwMstpiPortPriority
                    Integer32,
                hwMstpiPortPathCost
                    Integer32,
                hwMstpiDesignatedRoot
                    OCTET STRING,
                hwMstpiDesignatedCost
                    Integer32,
                hwMstpiDesignatedBridge
                    OCTET STRING,
                hwMstpiDesignatedPort
                    OCTET STRING,
                hwMstpiStpPortEdgeport
                    HwMSTPEnabledStatus,
                hwMstpiStpPortPointToPoint
                    INTEGER,
                hwMstpiStpMcheck
                    INTEGER,
                hwMstpiStpTransLimit
                    Integer32,
                hwMstpiStpRXStpBPDU
                    Counter32,
                hwMstpiStpTXStpBPDU
                    Counter32,
                hwMstpiStpRXTCNBPDU
                    Counter32,
                hwMstpiStpTXTCNBPDU
                    Counter32,
                hwMstpiStpRXRSTPBPDU
                    Counter32,
                hwMstpiStpTXRSTPBPDU
                    Counter32,
                hwMstpiStpRXMSTPBPDU
                    Counter32,
                hwMstpiStpTXMSTPBPDU
                    Counter32,
                hwMstpiStpClearStatistics
                    INTEGER,
                hwMstpiStpDefaultPortCost
                    INTEGER,
                hwMstpiStpStatus
                    HwMSTPEnabledStatus,
                hwMstpiPortRootGuard
                    HwMSTPEnabledStatus,
                hwMstpiPortLoopGuard
                    HwMSTPEnabledStatus,
                hwMstpiPortCompliance
                    INTEGER
                }

        hwMstpiPortIndex OBJECT-TYPE
            SYNTAX      Integer32
            MAX-ACCESS  accessible-for-notify
            STATUS      current
            DESCRIPTION
                "It is an index and indicates a bridge port.
                "
            ::={ hwMstpPortEntry 1 }

        hwMstpiPortState OBJECT-TYPE
            SYNTAX      INTEGER{disabled(1),discarding(2),learning(4),forwarding(5)}
            MAX-ACCESS  read-only
            STATUS      current
            DESCRIPTION
                "Indicates the port status.
                 Options:
                 1. disabled(1)   -indicates the port is disabled
                 2. discarding(2) -indicates the port is discarding. During this phase,
                                   port can only receive and process BPDU data packet,
                                   not forward traffic, root bridge, root port, and specified
                                   port will be voted
                 3. learning(4)   -indicates the port is learning. During this phase,
                                   bridge will create MAC address table according the
                                   received traffic, but not forward traffic
                 4. forwarding(5) -indicates traffic forward
                "
            ::={ hwMstpPortEntry 2 }

        hwMstpiPortPriority OBJECT-TYPE
            SYNTAX      Integer32(0..240)
            MAX-ACCESS  read-write
            STATUS      current
            DESCRIPTION
                "Indicates the port priority.
                 Range: 0-240
                 Default: 128
                 Step: 16
                "
            DEFVAL { 128 }
            ::={ hwMstpPortEntry 3 }

        hwMstpiPortPathCost OBJECT-TYPE
            SYNTAX      Integer32(1..200000000)
            MAX-ACCESS  read-write
            STATUS      current
            DESCRIPTION
                "Indicates the path cost of the port.
                 The value range of this leaf is relevant to hwMstpPathCostStandard.
                 Range: 1-65535 (The 802.1d-1998 protocol is used as the computing standard)
                        1-200000000 (The 802.1t protocol is used as the computing standard)
                        1-200000 (Huawei's proprietary legacy is used as the computing standard)
                "
            ::={ hwMstpPortEntry 4 }

        hwMstpiDesignatedRoot OBJECT-TYPE
            SYNTAX      OCTET STRING (SIZE (8))
            MAX-ACCESS  read-only
            STATUS      current
            DESCRIPTION
                "The Bridge Identifier of the Root Bridge for the port of the Spanning Tree instance identified by the MSTID.
                 The format of the bridge ID is bridge priority (2B) + bridge MAC address (6B).
                 For example, if the bridge priority is 32768, and the bridge MAC address is 00.EE.DC.F9.13.20,
                 then the bridge ID is 80.00.00.EE.DC.F9.13.20.
                "
            ::={ hwMstpPortEntry 5 }

        hwMstpiDesignatedCost OBJECT-TYPE
            SYNTAX      Integer32
            MAX-ACCESS  read-only
            STATUS      current
            DESCRIPTION
                "Indicates the cost of the path from the port to the root bridge.
                "
            ::={ hwMstpPortEntry 6}

        hwMstpiDesignatedBridge OBJECT-TYPE
            SYNTAX      OCTET STRING (SIZE (8))
            MAX-ACCESS  read-only
            STATUS      current
            DESCRIPTION
                "Indicates the designated bridge.
                 The format of the bridge ID is bridge priority (2B) + bridge MAC address (6B).
                 For example, if the bridge priority is 32768, and the bridge MAC address is 00.EE.DC.F9.13.20,
                 then the bridge ID is 80.00.00.EE.DC.F9.13.20.
                "
            ::={ hwMstpPortEntry 7 }

        hwMstpiDesignatedPort OBJECT-TYPE
            SYNTAX      OCTET STRING(SIZE (2))
            MAX-ACCESS  read-only
            STATUS      current
            DESCRIPTION
                "Indicates the designated port.
                 The format of the port ID is port priority (1B) + port number (1B).
                 For example, if the port priority is 128, and the port number is 1, then the port ID is 80.01.
                "
            ::={ hwMstpPortEntry 8 }

        hwMstpiStpPortEdgeport OBJECT-TYPE
            SYNTAX      HwMSTPEnabledStatus
            MAX-ACCESS  read-write
            STATUS      current
            DESCRIPTION
                "Indicates whether the current port is an edge port.
                 Options:
                 1. enabled(1)  -indicates the current port is an edge port
                 2. disabled(2) -indicates the current port is not an edge port
                 Default: disabled(2)
                "
            DEFVAL { disabled }
            ::={ hwMstpPortEntry 9 }

        hwMstpiStpPortPointToPoint OBJECT-TYPE
            SYNTAX      INTEGER{forceTrue (1),forceFalse (2),auto  (3)}
            MAX-ACCESS  read-write
            STATUS      current
            DESCRIPTION
                "Indicates whether the current port is a point-to-point port.
                 Options:
                 1. forceTrue(1)  -indicates the current port is a point-to-point port
                 2. forceFalse(2) -indicates the current port is not a point-to-point port
                 3. auto(3)       -indicates the current port is a self-negotiation port
                 Default: auto(3)
                "
            DEFVAL { auto }
            ::={ hwMstpPortEntry 10 }

        hwMstpiStpMcheck OBJECT-TYPE
            SYNTAX  INTEGER
                {
                enable(1),
                unused(65535)
                }
            MAX-ACCESS  read-write
            STATUS      current
            DESCRIPTION
                "Indicates the mcheck parameter of the bridge port.
                 Options:
                 1. enable(1)     -indicates the mcheck parameter of the bridge port is enabled
                 2. unused(65535) -indicates the mcheck parameter of the bridge port is unused
                "
            ::={ hwMstpPortEntry 11 }

        hwMstpiStpTransLimit OBJECT-TYPE
            SYNTAX      Integer32(1..255)
            MAX-ACCESS  read-write
            STATUS      current
            DESCRIPTION
                "Indicates the maximum number of BPDUs that can be transmitted within the hello time.
                 Range: 1-255
                 Default: 3
                "
            DEFVAL { 3 }
            ::={ hwMstpPortEntry 12 }

        hwMstpiStpRXStpBPDU OBJECT-TYPE
            SYNTAX      Counter32
            MAX-ACCESS  read-only
            STATUS      current
            DESCRIPTION
                "Indicates the number of BPDUs received by the port.
                "
            ::={ hwMstpPortEntry 13 }

        hwMstpiStpTXStpBPDU OBJECT-TYPE
            SYNTAX      Counter32
            MAX-ACCESS  read-only
            STATUS      current
            DESCRIPTION
                "Indicates the number of BPDUs transmitted by the port.
                "
            ::={ hwMstpPortEntry 14 }

        hwMstpiStpRXTCNBPDU OBJECT-TYPE
            SYNTAX      Counter32
            MAX-ACCESS  read-only
            STATUS      current
            DESCRIPTION
                "Indicates the number of TCN BPDUs received by the port.
                "
            ::={ hwMstpPortEntry 15 }

        hwMstpiStpTXTCNBPDU OBJECT-TYPE
            SYNTAX      Counter32
            MAX-ACCESS  read-only
            STATUS      current
            DESCRIPTION
                "Indicates the number of TCN BPDUs transmitted by the port.
                "
            ::={ hwMstpPortEntry 16 }

        hwMstpiStpRXRSTPBPDU OBJECT-TYPE
            SYNTAX      Counter32
            MAX-ACCESS  read-only
            STATUS      current
            DESCRIPTION
                "Indicates the number of RST BPDUs received by the port.
                "
            ::={ hwMstpPortEntry 17 }

        hwMstpiStpTXRSTPBPDU OBJECT-TYPE
            SYNTAX      Counter32
            MAX-ACCESS  read-only
            STATUS      current
            DESCRIPTION
                "Indicates the number of RST BPDUs transmitted by the port.
                "
            ::={ hwMstpPortEntry 18 }

        hwMstpiStpRXMSTPBPDU OBJECT-TYPE
            SYNTAX      Counter32
            MAX-ACCESS  read-only
            STATUS      current
            DESCRIPTION
                "Indicates the number of MST BPDUs received by the port.
                "
            ::={ hwMstpPortEntry 19 }

        hwMstpiStpTXMSTPBPDU OBJECT-TYPE
            SYNTAX      Counter32
            MAX-ACCESS  read-only
            STATUS      current
            DESCRIPTION
                "Indicates the number of MST BPDUs transmitted by the port.
                "
            ::={ hwMstpPortEntry 20 }

        hwMstpiStpClearStatistics OBJECT-TYPE
            SYNTAX   INTEGER
                {
                clear(1),
                unused(65535)
                }
            MAX-ACCESS  read-write
            STATUS      current
            DESCRIPTION
                "Indicates whether to clear the statistics.
                 Options:
                 1. clear(1)      -indicates the statistics is cleared
                 2. unused(65535) -indicates the statistics is not cleared
                "
            ::={ hwMstpPortEntry 21 }

        hwMstpiStpDefaultPortCost OBJECT-TYPE
            SYNTAX      INTEGER
                {
                reset(1),
                unused(65535)
                }
            MAX-ACCESS  read-write
            STATUS      current
            DESCRIPTION
                "Indicates whether to restore the default port cost.
                 Options:
                 1. reset(1)      -indicates the default port cost is restored
                 2. unused(65535) -indicates the default port cost is not restored
                "
            ::={ hwMstpPortEntry 22}

        hwMstpiStpStatus OBJECT-TYPE
            SYNTAX      HwMSTPEnabledStatus
            MAX-ACCESS  read-write
            STATUS      current
            DESCRIPTION
                "Indicates whether STP is enabled on the port.
                 Options:
                 1. enabled(1)  -indicates STP is enabled on the port
                 2. disabled(2) -indicates STP is not enabled on the port
                 Default: enabled(1)
                "
            DEFVAL { enabled}
            ::={ hwMstpPortEntry 23 }

        hwMstpiPortRootGuard OBJECT-TYPE
            SYNTAX      HwMSTPEnabledStatus
            MAX-ACCESS  read-write
            STATUS      current
            DESCRIPTION
                "Indicates whether root protection is enabled on the port.
                 Options:
                 1. enabled(1)  -indicates root protection is enabled on the port
                 2. disabled(2) -indicates root protection is disabled on the port
                 Default: disabled(2)
                "
            DEFVAL { disabled }
            ::={ hwMstpPortEntry 24 }

        hwMstpiPortLoopGuard OBJECT-TYPE
            SYNTAX      HwMSTPEnabledStatus
            MAX-ACCESS  read-write
            STATUS      current
            DESCRIPTION
                "Indicates whether loop protection is enabled on the port.
                 Options:
                 1. enabled(1)  -indicates loop protection is enabled on the port
                 2. disabled(2) -indicates loop protection is disabled on the port
                 Default: disabled(2)
                "
            DEFVAL { disabled }
            ::={ hwMstpPortEntry 25 }

        hwMstpiPortCompliance OBJECT-TYPE
            SYNTAX      INTEGER{auto(1),dot1w(2)}
            MAX-ACCESS  read-write
            STATUS      current
            DESCRIPTION
                "Indicates the MSTP compliance type of the current port.
                 Options:
                 1. auto(1)  -indicates the MSTP compliance type of the current port is auto
                 2. dot1w(2) -indicates the MSTP compliance type of the current port is dot1w
                 Default: auto(1).
                "
            DEFVAL { auto }
            ::={ hwMstpPortEntry 26 }

        hwMstpTraps OBJECT-IDENTITY
            STATUS      current
            DESCRIPTION
                "Definition point for Mstp notifications.
                "
            ::= { hwMstp 2 }

        hwMstpCommonTraps OBJECT IDENTIFIER ::= { hwMstpTraps 1 }

        hwMstpCommonTrapsPrefix OBJECT IDENTIFIER ::= { hwMstpCommonTraps 0 }

        hwMstpAlarmTraps OBJECT IDENTIFIER ::= { hwMstpTraps 2 }

        hwMstpAlarmTrapsPrefix OBJECT IDENTIFIER ::= { hwMstpAlarmTraps 0 }

        hwMstpiPortStateForwarding NOTIFICATION-TYPE
            OBJECTS
                {
                hwMstpInstanceID ,
                hwMstpiPortIndex
                }
            STATUS   current
            DESCRIPTION
                "The SNMP trap that is generated when a port turns into
                 forwarding state form other state.
                "
            ::= { hwMstpCommonTraps 0 1 }

        hwMstpiPortStateDiscarding NOTIFICATION-TYPE
            OBJECTS
                {
                hwMstpInstanceID ,
                hwMstpiPortIndex
                }
            STATUS   current
            DESCRIPTION
                "The SNMP trap that is generated when a port turns into
                 discarding state form forwarding state.
                "
            ::= { hwMstpCommonTraps 0 2 }

        hwMstpiPortRootGuarded NOTIFICATION-TYPE
            OBJECTS
                {
                hwMstpInstanceID ,
                hwMstpiPortIndex
                }
            STATUS   current
            DESCRIPTION
                "The SNMP trap that is generated when a root-guard port
                 receives a superior message on the relevant instance.
                "
            ::= { hwMstpCommonTraps 0 3 }

        hwMstpiPortRootGuardedResume NOTIFICATION-TYPE
            OBJECTS
                {
                hwMstpInstanceID ,
                hwMstpiPortIndex
                }
            STATUS   current
            DESCRIPTION
                "The SNMP trap that is generated when a root-guard port
                 not receives a superior message on the relevant instance.
                "
            ::= { hwMstpCommonTraps 0 4 }

        hwMstpiPortBpduGuarded NOTIFICATION-TYPE
            OBJECTS  { hwMstpiPortIndex }
            STATUS   current
            DESCRIPTION
                "The SNMP trap that is generated when an edged port of
                 the BPDU-guard switch receives BPDU packets.
                "
            ::= { hwMstpCommonTraps 0 5 }

        hwMstpiPortBpduGuardedResume NOTIFICATION-TYPE
            OBJECTS  { hwMstpiPortIndex }
            STATUS   current
            DESCRIPTION
                "The SNMP trap that is generated when an edged port of
                 the BPDU-guard switch not receives BPDU packets.
                "
            ::= { hwMstpCommonTraps 0 6 }

        hwMstpiPortDisable NOTIFICATION-TYPE
            OBJECTS  { hwMstpiPortIndex }
            STATUS   current
            DESCRIPTION
                "The SNMP trap that is generated when a port disable
                 stp.
                "
            ::= { hwMstpCommonTraps 0 7 }

        hwMstpConformance OBJECT IDENTIFIER ::= { hwMstp 3 }

        hwMstpGroups OBJECT IDENTIFIER ::= { hwMstpConformance 1 }

        hwMstpBridgeInfoGroup OBJECT-GROUP
            OBJECTS
                {
                hwMstpStatus,
                hwMstpForceVersion,
                hwMstpDiameter,
                hwMstpBridgeMaxHops,
                hwMstpMasterBridgeID,
                hwMstpMasterPathCost,
                hwMstpBpduGuard,
                hwMstpAdminFormatSelector,
                hwMstpAdminRegionName,
                hwMstpAdminRevisionLevel,
                hwMstpOperFormatSelector,
                hwMstpOperRegionName,
                hwMstpOperRevisionLevel,
                hwMstpRegionConfActive,
                hwMstpDefaultVlanAllo,
                hwMstpDefaultRegionName,
                hwMstpPathCostStandard,
                hwMstpTimeFactor,
                hwMstpMD5KEY
                }
            STATUS      current
            DESCRIPTION
                "A collection of objects indicating the necessary
                 capabilites of the bridge device which is running the multi spanning tree protocol.
                "
            ::= { hwMstpGroups 1 }

        hwMstpVlanInfoGroup  OBJECT-GROUP
            OBJECTS
                {
                hwMstpVID,
                hwMstpAdminMstID,
                hwMstpOperMstID
                }
            STATUS      current
            DESCRIPTION
                "A collection of objects describes
                 the attribute of the vlan in the multi spanning tree protocol.
                 They are necessary to find the relation
                 between vlan and instance by the vlan identifier.
                "
            ::= { hwMstpGroups 2 }

        hwMstpInstanceInfoGroup  OBJECT-GROUP
            OBJECTS
                {
                hwMstpInstanceID,
                hwMstpiBridgeID,
                hwMstpiBridgePriority,
                hwMstpiDesignedRoot,
                hwMstpiRootPathCost,
                hwMstpiRootPort,
                hwMstpiRootType,
                hwMstpiRemainingHops,
                hwMstpiAdminMappedVlanListLow,
                hwMstpiAdminMappedVlanListHigh,
                hwMstpiOperMappedVlanListLow,
                hwMstpiOperMappedVlanListHigh
                }
            STATUS      current
            DESCRIPTION
                "A collection of objects describes
                 the attribute of the instance in the multi spanning tree protocol.
                "
            ::= { hwMstpGroups 3 }

        hwMstpPortInfoGroup  OBJECT-GROUP
            OBJECTS
                {
                hwMstpiPortIndex,
                hwMstpiPortState,
                hwMstpiPortPriority,
                hwMstpiPortPathCost,
                hwMstpiDesignatedRoot,
                hwMstpiDesignatedCost,
                hwMstpiDesignatedBridge,
                hwMstpiDesignatedPort,
                hwMstpiStpPortEdgeport,
                hwMstpiStpPortPointToPoint,
                hwMstpiStpMcheck,
                hwMstpiStpTransLimit,
                hwMstpiStpRXStpBPDU,
                hwMstpiStpTXStpBPDU,
                hwMstpiStpRXTCNBPDU,
                hwMstpiStpTXTCNBPDU,
                hwMstpiStpRXRSTPBPDU,
                hwMstpiStpTXRSTPBPDU,
                hwMstpiStpRXMSTPBPDU,
                hwMstpiStpTXMSTPBPDU,
                hwMstpiStpClearStatistics,
                hwMstpiStpDefaultPortCost,
                hwMstpiStpStatus,
                hwMstpiPortRootGuard,
                hwMstpiPortLoopGuard,
                hwMstpiPortCompliance
                }
            STATUS      current
            DESCRIPTION
                "A collection of objects is necessary to show the
                 information of the port in the bridge in the multi
                 spanning tree protocol.
                "
            ::= { hwMstpGroups 4 }

        hwMstpCompliances OBJECT IDENTIFIER
            ::= { hwMstpConformance 2 }

        hwMstpCompliance MODULE-COMPLIANCE
            STATUS  current
            DESCRIPTION
                "The compliance statement for device support of Priority
                 and Multicast Filtering extended bridging services.
                "

            MODULE
                MANDATORY-GROUPS
                    {
                    hwMstpBridgeInfoGroup,
                    hwMstpVlanInfoGroup,
                    hwMstpInstanceInfoGroup,
                    hwMstpPortInfoGroup
                    }
            ::= { hwMstpCompliances 1 }

END
