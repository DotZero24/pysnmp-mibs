-- ==================================================================
-- Copyright (C) 2010 by HUAWEI TECHNOLOGIES. All rights reserved.
-- Description:   This mib is used for defining the FR Interface MIB objects.
-- Reference:
-- Version: V1.0 initial
-- ==================================================================

    HUAWEI-FR-MIB DEFINITIONS ::= BEGIN

        IMPORTS
            hwDatacomm
                FROM HUAWEI-MIB
            InterfaceIndex
                FROM IF-MIB
            OBJECT-GROUP, MODULE-COMPLIANCE
                FROM SNMPv2-CONF
            IpAddress, Integer32, OBJECT-TYPE, MODULE-IDENTITY
                FROM SNMPv2-SMI
            RowStatus, TruthValue
                FROM SNMPv2-TC;


-- Sept 10, 2010 at 20:30 GMT
-- Sept 10, 2010 at 20:30 GMT
        hwFrMIB MODULE-IDENTITY
            LAST-UPDATED "201009102030Z"
            ORGANIZATION
                "Huawei Technologies Co.,Ltd."
            CONTACT-INFO
                "Huawei Industrial Base
                  Bantian, Longgang
                   Shenzhen 518129
                   People's Republic of China
                   Website: http://www.huawei.com
                   Email: support@huawei.com
                 "
            DESCRIPTION
                "This MIB is mainly used to indicate the information of Fr interface"
            ::= { hwDatacomm 168 }

--
-- Node definitions
--
        hwFrObjects OBJECT IDENTIFIER ::= { hwFrMIB 1 }

--     hwFrTable Table
--
        hwFrTable OBJECT-TYPE
            SYNTAX SEQUENCE OF HwFrEntry
            MAX-ACCESS not-accessible
            STATUS current
            DESCRIPTION
               "This table is used to indicate the parameters of the Fr interface.
                The index of this table is hwFrIfIndex."
            ::= { hwFrObjects 1 }

        hwFrEntry OBJECT-TYPE
            SYNTAX HwFrEntry
            MAX-ACCESS not-accessible
            STATUS current
            DESCRIPTION
               "This table is used to indicate the parameters of the Fr interface.
                The index of this entry is hwFrIfIndex."
            INDEX { hwFrIfIndex }
            ::= { hwFrTable 1 }

        HwFrEntry ::=
            SEQUENCE {
                hwFrIfIndex
                    InterfaceIndex,
                hwFrEncapType
                    INTEGER,
                hwFrIfType
                    INTEGER,
                hwFrLmiType
                    INTEGER,
                hwFrLmiN391DteValue
                    Integer32,
                hwFrLmiN392DteValue
                    Integer32,
                hwFrLmiN392DceValue
                    Integer32,
                hwFrLmiN393DteValue
                    Integer32,
                hwFrLmiN393DceValue
                    Integer32,
                hwFrLmiT391DteValue
                    Integer32,
                hwFrLmiT392DceValue
                    Integer32,
                hwFrIphcEnable
                    TruthValue,
                hwFrIphcNonstandardFormat
                    TruthValue,
                hwFrIphcTcpInclude
                    TruthValue,
                hwFrInarpEnable
                    TruthValue,
                hwFrIphcTcpConnection
                    Integer32,
                hwFrIphcRtpConnection
                    Integer32
             }

        hwFrIfIndex OBJECT-TYPE
            SYNTAX InterfaceIndex
            MAX-ACCESS not-accessible
            STATUS current
            DESCRIPTION
               "Indicates the interface index."
            ::= { hwFrEntry 1 }

        hwFrEncapType OBJECT-TYPE
            SYNTAX INTEGER
                {
                nonstandard(1),
                ietf(2)
                }
            MAX-ACCESS read-only
            STATUS current
            DESCRIPTION
               "Indicates the interface fr encapsulation type.
                Options:
                1.nonstandard(1) - nonstandard encapsulation
                2.ietf(2)        - RFC1490 encapsulation"
            ::= { hwFrEntry 2 }

        hwFrIfType OBJECT-TYPE
            SYNTAX INTEGER
                {
                dte(1),
                dce(2),
                nni(3)
                }
            MAX-ACCESS read-only
            STATUS current
            DESCRIPTION
               "Indicates fr interface type.
                Options:
                1.dte(1) - DTE type
                2.dce(2) - DCE type
                3.nni(3) - NNI type"
            ::= { hwFrEntry 3 }

        hwFrLmiType OBJECT-TYPE
            SYNTAX INTEGER
                {
                notset(1),
                nonstandard(2),
                ansi(3),
                q933a(4)
                }
            MAX-ACCESS read-only
            STATUS current
            DESCRIPTION
                "Indicates the Lmi protocol type.
                 Options:
                 1.notset(1)      - NotSet
                 2.nonstandard(2) - nonstandard type
                 3.ansi(3)        - ANSI type
                 4.q933a(4)       - Q.933a type"
            ::= { hwFrEntry 4 }

        hwFrLmiN391DteValue OBJECT-TYPE
            SYNTAX Integer32 (1..255 | 65535)
            MAX-ACCESS read-only
            STATUS current
            DESCRIPTION
                "Indicates the parameter of DTE N391.
                 Get 65535 when the fr interface type is DCE.
                 Range: 1-255
                 Default: 6
                 Unit: count"
            ::= { hwFrEntry 5 }

        hwFrLmiN392DteValue OBJECT-TYPE
            SYNTAX Integer32 (1..10 | 65535)
            MAX-ACCESS read-only
            STATUS current
            DESCRIPTION
                "Indicates the parameter of DTE N392.
                 Get 65535 when the fr interface type is DCE.
                 Range: 1-10
                 Default: 3
                 Unit: count"
            ::= { hwFrEntry 6 }

        hwFrLmiN392DceValue OBJECT-TYPE
            SYNTAX Integer32 (1..10 | 65535)
            MAX-ACCESS read-only
            STATUS current
            DESCRIPTION
                "Indicates the parameter of DCE N392.
                 Get 65535 when the fr interface type is DTE.
                 Range: 1-10
                 Default: 3
                 Unit: count"
            ::= { hwFrEntry 7 }

        hwFrLmiN393DteValue OBJECT-TYPE
            SYNTAX Integer32 (1..10 | 65535)
            MAX-ACCESS read-only
            STATUS current
            DESCRIPTION
                "Indicates the parameter of DTE N393.
                 Get 65535 when the fr interface type is DCE.
                 Range: 1-10
                 Default: 4
                 Unit: count
                "
            ::= { hwFrEntry 8 }

        hwFrLmiN393DceValue OBJECT-TYPE
            SYNTAX Integer32 (1..10 | 65535)
            MAX-ACCESS read-only
            STATUS current
            DESCRIPTION
                "Indicates the parameter of DCE N393.
                 Get 65535 when the fr interface type is DTE.
                 Range: 1-10
                 Default: 4
                 Unit: count
                "
            ::= { hwFrEntry 9 }

         hwFrLmiT391DteValue OBJECT-TYPE
            SYNTAX Integer32 (0..32767 | 65535)
            MAX-ACCESS read-only
            STATUS current
            DESCRIPTION
                "Indicates the parameter of DTE T391.
                 Get 65535 when the fr interface type is DCE.
                 Range: 1-32767
                 Default: 10
                 Unit: second"
            ::= { hwFrEntry 10 }

         hwFrLmiT392DceValue OBJECT-TYPE
            SYNTAX Integer32 (5..30 | 65535)
            MAX-ACCESS read-only
            STATUS current
            DESCRIPTION
                "Indicates the parameter of DCE T392.
                 Get 65535 when the fr interface type is DTE.
                 Range: 5-30
                 Default: 15
                 Unit: second"
            ::= { hwFrEntry 11 }

         hwFrIphcEnable OBJECT-TYPE
            SYNTAX TruthValue
            MAX-ACCESS read-only
            STATUS current
            DESCRIPTION
                "Indicates IPHC is enabled or disabled.
                 By default, RTP header compression with IPHC format is disabled.
                 true: enable RTP header compression with IPHC format.
                 false: disable RTP header compression with IPHC format."
            ::= { hwFrEntry 12 }

         hwFrIphcNonstandardFormat OBJECT-TYPE
            SYNTAX TruthValue
            MAX-ACCESS read-only
            STATUS current
            DESCRIPTION
                "Indicates nonstandard-format compressing is enabled or disabled.
                 By default, don't support nonstandard-format while compressing.
                 true: support nonstandard-format while compressing.
                 false: don't support nonstandard-format while compressing."
            ::= { hwFrEntry 13 }

         hwFrIphcTcpInclude OBJECT-TYPE
            SYNTAX TruthValue
            MAX-ACCESS read-only
            STATUS current
            DESCRIPTION
                "Indicates TCP header compression is enabled or disabled.
                 By default, exclude TCP header compression while compressing RTP.
                 true: include TCP header compression while compressing RTP.
                 false: exclude TCP header compression while compressing RTP."
            ::= { hwFrEntry 14 }

         hwFrInarpEnable OBJECT-TYPE
            SYNTAX TruthValue
            MAX-ACCESS read-only
            STATUS current
            DESCRIPTION
                "Indicates inverse address resolution protocol is enabled or disabled.
                 By default, inverse address resolution protocol is enabled.
                 true: inverse address resolution protocol is enabled.
                 false: inverse address resolution protocol is disabled."
            ::= { hwFrEntry 15 }

         hwFrIphcTcpConnection OBJECT-TYPE
            SYNTAX Integer32 (3..255 | 256 | 65535)
            MAX-ACCESS read-only
            STATUS current
            DESCRIPTION
                "Indicates the number of tcp compression connections.
                 256 is a valid connection number, get 256 when IPHC is enabled.
                 Get 65535 when IPHC is disabled.
                 Range: 3-255
                 Default: 256
                 Unit: count"
            ::= { hwFrEntry 16 }

         hwFrIphcRtpConnection OBJECT-TYPE
            SYNTAX Integer32 (3..255 | 256 | 65535)
            MAX-ACCESS read-only
            STATUS current
            DESCRIPTION
                "Indicates the number of rtp compression connections.
                 256 is a valid connection number, get 256 when IPHC is enabled.
                 Get 65535 when IPHC is disabled.
                 Range: 3-255
                 Default: 256
                 Unit: count"
            ::= { hwFrEntry 17 }

--      hwFrPvcTable table
--
        hwFrPvcTable OBJECT-TYPE
            SYNTAX SEQUENCE OF HwFrPvcEntry
            MAX-ACCESS not-accessible
            STATUS current
            DESCRIPTION
               "This table is used to indicate the PVC for the Fr interface.
                The index of this table are hwFrPvcIfIndex and hwFrPvcDlciNumber."
            ::= { hwFrObjects 2 }

        hwFrPvcEntry OBJECT-TYPE
            SYNTAX HwFrPvcEntry
            MAX-ACCESS not-accessible
            STATUS current
            DESCRIPTION
                "This table is used to indicate the PVC for the Fr interface.
                 The index of this entry are hwFrPvcIfIndex and hwFrPvcDlciNumber."
            INDEX { hwFrPvcIfIndex, hwFrPvcDlciNumber }
            ::= { hwFrPvcTable 1 }

        HwFrPvcEntry ::=
            SEQUENCE {
                hwFrPvcIfIndex
                    InterfaceIndex,
                hwFrPvcDlciNumber
                    Integer32,
                hwFrPvcState
                    INTEGER,
                hwFrPvcInarpEnable
                    TruthValue
             }

        hwFrPvcIfIndex OBJECT-TYPE
            SYNTAX InterfaceIndex
            MAX-ACCESS not-accessible
            STATUS current
            DESCRIPTION
               "Indicates the interface index."
            ::= { hwFrPvcEntry 1 }

        hwFrPvcDlciNumber OBJECT-TYPE
            SYNTAX Integer32 (16..1022)
            MAX-ACCESS read-only
            STATUS current
            DESCRIPTION
               "Indicates the Dlci number."
            ::= { hwFrPvcEntry 2 }

        hwFrPvcState OBJECT-TYPE
            SYNTAX INTEGER
                {
                inactive(1),
                active(2)
                }
            MAX-ACCESS read-only
            STATUS current
            DESCRIPTION
               "Indicates the state of the PVC.
                Options:
                1.inactive(1) - inactive
                2.active(2)   - active"
            ::= { hwFrPvcEntry 3 }

        hwFrPvcInarpEnable OBJECT-TYPE
            SYNTAX TruthValue
            MAX-ACCESS read-only
            STATUS current
            DESCRIPTION
                "Indicates the inarp is enabled or disabled.
                 By default, the inarp of the PVC is enabled.
                 true: enable inarp.
                 false: disable inarp."
            ::= { hwFrPvcEntry 4 }

--
-- hwFrPvcGroupTable
--
        hwFrPvcGroupTable OBJECT-TYPE
            SYNTAX SEQUENCE OF HwFrPvcGroupEntry
            MAX-ACCESS not-accessible
            STATUS current
            DESCRIPTION
                "This table is used to indicate the pvc-group on the interface.
                 The index of this table are hwFrPvcGroupIfIndex and hwFrPvcGroupName."
            ::= { hwFrObjects 3 }

        hwFrPvcGroupEntry OBJECT-TYPE
            SYNTAX HwFrPvcGroupEntry
            MAX-ACCESS not-accessible
            STATUS current
            DESCRIPTION
                "This table is used to indicate the pvc-group on the interface.
                The index of this entry are hwFrPvcGroupIfIndex and hwFrPvcGroupName."
            INDEX { hwFrPvcGroupIfIndex, hwFrPvcGroupName }
            ::= { hwFrPvcGroupTable 1 }

        HwFrPvcGroupEntry ::=
            SEQUENCE {
                hwFrPvcGroupIfIndex
                    InterfaceIndex,
                hwFrPvcGroupName
                    OCTET STRING,
                hwFrPvcGroupState
                    INTEGER,
                hwFrPvcGroupTosType
                    INTEGER,
                hwFrPvcGroupInArpEnable
                    TruthValue
             }

        hwFrPvcGroupIfIndex OBJECT-TYPE
            SYNTAX InterfaceIndex
            MAX-ACCESS not-accessible
            STATUS current
            DESCRIPTION
                "Indicates the interface index."
            ::= { hwFrPvcGroupEntry 1 }

        hwFrPvcGroupName OBJECT-TYPE
            SYNTAX OCTET STRING (SIZE (1..16))
            MAX-ACCESS read-only
            STATUS current
            DESCRIPTION
                "Indicates the name of the pvc-group. The name is a string of 1 to 16 characters.
                 Only support visible characters."
            ::= { hwFrPvcGroupEntry 2 }

        hwFrPvcGroupState OBJECT-TYPE
            SYNTAX INTEGER
                {
                inactive(1),
                active(2)
                }
            MAX-ACCESS read-only
            STATUS current
            DESCRIPTION
               "Indicates the state of a pvc-group.
                Options:
                1.inactive(1) - inactive
                2.active(2)   - active"
            ::= { hwFrPvcGroupEntry 3 }

        hwFrPvcGroupTosType OBJECT-TYPE
            SYNTAX INTEGER
                {
                none(1),
                precedence(2),
                dscp(3)
                }
            MAX-ACCESS read-only
            STATUS current
            DESCRIPTION
               "Indicates the TOS type of a pvc-group.
                Options:
                1.none(1)       - none
                2.precedence(2) - precedence
                3.dscp(3)       - DSCP"
            ::= { hwFrPvcGroupEntry 4 }

        hwFrPvcGroupInArpEnable OBJECT-TYPE
            SYNTAX TruthValue
            MAX-ACCESS read-only
            STATUS current
            DESCRIPTION
                "Indicates inarp is enabled or disabled.
                 By default, the inarp of the pvc-group is enabled.
                 true: enable inarp.
                 false: disable inarp."
            ::= { hwFrPvcGroupEntry 5 }

-- hwFrPvcGroupMemTable
--
         hwFrPvcGroupMemTable OBJECT-TYPE
            SYNTAX SEQUENCE OF HwFrPvcGroupMemEntry
            MAX-ACCESS not-accessible
            STATUS current
            DESCRIPTION
               "This table is used to indicate the member of the pvc-group.
                The index of this table are hwFrPvcGroupMemIfIndex, hwFrPvcGroupMemPvcGroupName
                and hwFrPvcGroupMemDlciNumber."
            ::= { hwFrObjects 4 }

         hwFrPvcGroupMemEntry OBJECT-TYPE
            SYNTAX HwFrPvcGroupMemEntry
            MAX-ACCESS not-accessible
            STATUS current
            DESCRIPTION
                "This table is used to indicate the member of the pvc-group.
                 The index of this entry are hwFrPvcGroupMemIfIndex, hwFrPvcGroupMemPvcGroupName
                 and hwFrPvcGroupMemDlciNumber."
            INDEX { hwFrPvcGroupMemIfIndex, hwFrPvcGroupMemPvcGroupName, hwFrPvcGroupMemDlciNumber }
            ::= { hwFrPvcGroupMemTable 1 }

         HwFrPvcGroupMemEntry ::=
            SEQUENCE {
                hwFrPvcGroupMemIfIndex
                    InterfaceIndex,
                hwFrPvcGroupMemPvcGroupName
                    OCTET STRING,
                hwFrPvcGroupMemDlciNumber
                    Integer32,
                hwFrPvcGroupMemTosType
                    INTEGER,
                hwFrPvcGroupMemDefault
                    TruthValue,
                hwFrPvcGroupMemMinGrade
                    Integer32,
                hwFrPvcGroupMemMaxGrade
                    Integer32
               }

         hwFrPvcGroupMemIfIndex OBJECT-TYPE
            SYNTAX InterfaceIndex
            MAX-ACCESS not-accessible
            STATUS current
            DESCRIPTION
                "Indicates the interface index."
            ::= { hwFrPvcGroupMemEntry 1 }

         hwFrPvcGroupMemPvcGroupName OBJECT-TYPE
            SYNTAX OCTET STRING (SIZE (1..16))
            MAX-ACCESS read-only
            STATUS current
            DESCRIPTION
                "Indicates the name of the pvc-group. The name is a string of 1 to 16 characters.
                 Only support visible characters."
            ::= { hwFrPvcGroupMemEntry 2 }

         hwFrPvcGroupMemDlciNumber OBJECT-TYPE
            SYNTAX Integer32 (16..1022)
            MAX-ACCESS read-only
            STATUS current
            DESCRIPTION
                "Indicates the DLCI of the PVC."
            ::= { hwFrPvcGroupMemEntry 3 }

         hwFrPvcGroupMemTosType OBJECT-TYPE
            SYNTAX INTEGER
                {
                none(1),
                precedence(2),
                dscp(3)
                }
            MAX-ACCESS read-only
            STATUS current
            DESCRIPTION
               "Indicates the TOS type of a PVC belong to the pvc-group.
                Options:
                1.none(1)       - none
                2.precedence(2) - precedence
                3.dscp(3)       - DSCP"
            ::= { hwFrPvcGroupMemEntry 4 }

         hwFrPvcGroupMemDefault OBJECT-TYPE
             SYNTAX TruthValue
            MAX-ACCESS read-only
            STATUS current
            DESCRIPTION
                "Indicates the TOS value of the PVC whether is default or not.
                 true: default TOS value.
                 false: none default TOS value."
            DEFVAL { false }
            ::= { hwFrPvcGroupMemEntry 5 }

         hwFrPvcGroupMemMinGrade OBJECT-TYPE
            SYNTAX Integer32 (0..63 | 255)
            MAX-ACCESS read-only
            STATUS current
            DESCRIPTION
                "Indicates the minimum value of the TOS with one member PVC.
                 If the TOS type is precedence, the maximum value cannot be larger than 7.
                 Get 255 when this value is not configed."
            ::= { hwFrPvcGroupMemEntry 6 }

         hwFrPvcGroupMemMaxGrade OBJECT-TYPE
            SYNTAX Integer32 (0..63 | 255)
            MAX-ACCESS read-only
            STATUS current
            DESCRIPTION
                "Indicates the maximum value of the TOS with one member PVC.
                 If the TOS type is precedence, the maximum value cannot be larger than 7.
                 Get 255 when this value is not configed."
            ::= { hwFrPvcGroupMemEntry 7 }

--
-- hwFrPvcGroupMapIpTable
--
        hwFrPvcGroupMapIpTable OBJECT-TYPE
            SYNTAX SEQUENCE OF HwFrPvcGroupMapIpEntry
            MAX-ACCESS not-accessible
            STATUS current
            DESCRIPTION
               "This table is used to indicate the bridge mapping on the pvc-group.
                The index of this table are hwFrPvcGroupMapIpIfIndex, hwFrPvcGroupMapIpName and hwFrPvcGroupMapIpIpAddr."
            ::= { hwFrObjects 5 }

        hwFrPvcGroupMapIpEntry OBJECT-TYPE
            SYNTAX HwFrPvcGroupMapIpEntry
            MAX-ACCESS not-accessible
            STATUS current
            DESCRIPTION
                "This table is used to indicate the bridge mapping on the pvc-group.
                 The index of this entry are hwFrPvcGroupMapIpIfIndex, hwFrPvcGroupMapIpName and hwFrPvcGroupMapIpIpAddr."
            INDEX { hwFrPvcGroupMapIpIfIndex, hwFrPvcGroupMapIpName, hwFrPvcGroupMapIpIpAddr }
            ::= { hwFrPvcGroupMapIpTable 1 }

        HwFrPvcGroupMapIpEntry ::=
            SEQUENCE {
                hwFrPvcGroupMapIpIfIndex
                    InterfaceIndex,
                hwFrPvcGroupMapIpName
                    OCTET STRING,
                hwFrPvcGroupMapIpIpAddr
                    IpAddress,
                hwFrPvcGroupMapIpMask
                    IpAddress,
                hwFrPvcGroupMapIpEncapType
                    INTEGER,
                hwFrPvcGroupMapIpBroadcast
                    TruthValue,
                hwFrPvcGroupMapIpDefault
                    TruthValue
             }

        hwFrPvcGroupMapIpIfIndex OBJECT-TYPE
            SYNTAX InterfaceIndex
            MAX-ACCESS not-accessible
            STATUS current
            DESCRIPTION
                "Indicates the interface index."
            ::= { hwFrPvcGroupMapIpEntry 1 }

        hwFrPvcGroupMapIpName OBJECT-TYPE
            SYNTAX OCTET STRING (SIZE (1..16))
            MAX-ACCESS read-only
            STATUS current
            DESCRIPTION
                "Indicates the name of the pvc-group. The name is a string of 1 to 16 characters."
            ::= { hwFrPvcGroupMapIpEntry 2 }

        hwFrPvcGroupMapIpIpAddr OBJECT-TYPE
            SYNTAX IpAddress
            MAX-ACCESS read-only
            STATUS current
            DESCRIPTION
                "Indicates the peer IP address mapped to the pvc-group.
                 Get 0.0.0.0 when the map is default map."
            ::= { hwFrPvcGroupMapIpEntry 3 }

        hwFrPvcGroupMapIpMask OBJECT-TYPE
            SYNTAX IpAddress
            MAX-ACCESS read-only
            STATUS current
            DESCRIPTION
               "Indicates the IP address mask mapped to the pvc-group.
                Get 255.255.255.255 when the map is default map."
            ::= { hwFrPvcGroupMapIpEntry 4 }

        hwFrPvcGroupMapIpEncapType OBJECT-TYPE
            SYNTAX INTEGER
                {
                nonstandard(1),
                ietf(2)
                }
            MAX-ACCESS read-only
            STATUS current
            DESCRIPTION
               "Indicates the encapsulation type of the PVC mapped by pvc-group.
                1.nonstandard(1) - nonstandard encapsulation
                2.ietf(2)        - RFC1490 encapsulation"
            ::= { hwFrPvcGroupMapIpEntry 5 }

         hwFrPvcGroupMapIpBroadcast OBJECT-TYPE
             SYNTAX TruthValue
            MAX-ACCESS read-only
            STATUS current
            DESCRIPTION
                "Indicates sending broadcast packets is enabled or disabled.
                 By default, sending broadcast packets is disabled.
                 true: enable sending broadcast packets.
                 false: disable sending broadcast packets."
            ::= { hwFrPvcGroupMapIpEntry 6 }

         hwFrPvcGroupMapIpDefault OBJECT-TYPE
            SYNTAX TruthValue
            MAX-ACCESS read-only
            STATUS current
            DESCRIPTION
                "Indicates the map is default map or not.
                 By default, the map is not default map.
                 true: the map is default map.
                 false: the map is not default map."
            ::= { hwFrPvcGroupMapIpEntry 7 }

--     hwFrMapIpTable table
--
        hwFrMapIpTable OBJECT-TYPE
            SYNTAX SEQUENCE OF HwFrMapIpEntry
            MAX-ACCESS not-accessible
            STATUS current
            DESCRIPTION
                "This table is used to indicate the static address mapping for a PVC.
                 The index of this table are hwFrMapIpIfIndex, hwFrMapIpDlciNumber and hwFrMapIpAddress."
            ::= { hwFrObjects 6 }

        hwFrMapIpEntry OBJECT-TYPE
            SYNTAX HwFrMapIpEntry
            MAX-ACCESS not-accessible
            STATUS current
            DESCRIPTION
                "This table is used to indicate the static address mapping for a PVC.
                 The index of this entry are hwFrMapIpIfIndex, hwFrMapIpDlciNumber and hwFrMapIpAddress."
            INDEX { hwFrMapIpIfIndex, hwFrMapIpDlciNumber, hwFrMapIpAddress }
            ::= { hwFrMapIpTable 1 }

        HwFrMapIpEntry ::=
            SEQUENCE {
                hwFrMapIpIfIndex
                    InterfaceIndex,
                hwFrMapIpDlciNumber
                    Integer32,
                hwFrMapIpAddress
                    IpAddress,
                hwFrMapIpMask
                    IpAddress,
                hwFrMapIpBroadcast
                    TruthValue,
                hwFrMapIpEncapType
                    INTEGER,
                hwFrMapIpDefault
                    TruthValue,
                hwFrMapIpFrf9Enable
                    TruthValue,
                hwFrMapIpIphcEnable
                    TruthValue,
                hwFrMapIpRtpConnNumber
                    Integer32
             }

        hwFrMapIpIfIndex OBJECT-TYPE
            SYNTAX InterfaceIndex
            MAX-ACCESS not-accessible
            STATUS current
            DESCRIPTION
               "Indicates the interface index."
            ::= { hwFrMapIpEntry 1 }

        hwFrMapIpDlciNumber OBJECT-TYPE
            SYNTAX Integer32 (16..1022)
            MAX-ACCESS read-only
            STATUS current
            DESCRIPTION
               "Indicates the Dlci number."
            ::= { hwFrMapIpEntry 2 }

        hwFrMapIpAddress OBJECT-TYPE
            SYNTAX IpAddress
            MAX-ACCESS read-only
            STATUS current
            DESCRIPTION
                "Indicates the peer IP address mapped to the PVC.
                 Get 0.0.0.0 when the map is default map."
            ::= { hwFrMapIpEntry 3 }

        hwFrMapIpMask OBJECT-TYPE
            SYNTAX IpAddress
            MAX-ACCESS read-only
            STATUS current
            DESCRIPTION
               "Indicates the IP address mask.
                Get 255.255.255.255 when the map is default map."
            ::= { hwFrMapIpEntry 4 }

         hwFrMapIpBroadcast OBJECT-TYPE
            SYNTAX TruthValue
            MAX-ACCESS read-only
            STATUS current
            DESCRIPTION
                "Indicates sending broadcast packets is enabled or disabled.
                 By default, sending broadcast packets is disabled.
                 true: enable sending broadcast packets.
                 false: disable sending broadcast packets."
            ::= { hwFrMapIpEntry 5 }

         hwFrMapIpEncapType OBJECT-TYPE
            SYNTAX INTEGER
                {
                nonstandard(1),
                ietf(2)
                }
            MAX-ACCESS read-only
            STATUS current
            DESCRIPTION
               "Indicates the encapsulation type of map.
                Option:
                1.nonstandard(1) - nonstandard encapsulation
                2.ietf(2)        - RFC1490 encapsulation"
            ::= { hwFrMapIpEntry 6 }

         hwFrMapIpDefault OBJECT-TYPE
            SYNTAX TruthValue
            MAX-ACCESS read-only
            STATUS current
            DESCRIPTION
                "Indicates the map is default map or not.
                 By default, the map is not default map.
                 true: the map is default map.
                 false: the map is not default map."
            ::= { hwFrMapIpEntry 7 }

         hwFrMapIpFrf9Enable OBJECT-TYPE
            SYNTAX TruthValue
            MAX-ACCESS read-only
            STATUS current
            DESCRIPTION
                "Indicates frf9 on the map is enabled or disabled.
                 By default, payload data compression is disabled.
                 true: enable payload data compression.
                 false: disable payload data compression."
            ::= { hwFrMapIpEntry 8 }

         hwFrMapIpIphcEnable OBJECT-TYPE
            SYNTAX TruthValue
            MAX-ACCESS read-only
            STATUS current
            DESCRIPTION
                "Indicates iphc on the map is enabled or disabled.
                 By default, compress IP/UDP/RTP head with iphc-compression is disabled.
                 true: enable compress IP/UDP/RTP head with iphc-compression.
                 false: disable compress IP/UDP/RTP head with iphc-compression."
            ::= { hwFrMapIpEntry 9 }

         hwFrMapIpRtpConnNumber OBJECT-TYPE
            SYNTAX Integer32 (3..256| 65535)
            MAX-ACCESS read-only
            STATUS current
            DESCRIPTION
                "Indicates the number of rtp compression connections.
                 Get 65535 when IPHC is disabled.
                 Range: 3-256
                 Default: 65535
                 Unit: count"
            ::= { hwFrMapIpEntry 10 }

--
-- hwFrMapPppTable
--
        hwFrMapPppTable OBJECT-TYPE
            SYNTAX SEQUENCE OF HwFrMapPppEntry
            MAX-ACCESS not-accessible
            STATUS current
            DESCRIPTION
                "This table is used to indicate the PPPoFR mapping on the PVC.
                 The index of this table are hwFrMapPppIfIndex and hwFrMapPppDlciNumber."
            ::= { hwFrObjects 7 }

        hwFrMapPppEntry OBJECT-TYPE
            SYNTAX HwFrMapPppEntry
            MAX-ACCESS not-accessible
            STATUS current
            DESCRIPTION
                "This table is used to indicate the PPPoFR mapping on the PVC.
                 The index of this entry are hwFrMapPppIfIndex and hwFrMapPppDlciNumber."
            INDEX { hwFrMapPppIfIndex, hwFrMapPppDlciNumber }
            ::= { hwFrMapPppTable 1 }

        HwFrMapPppEntry ::=
            SEQUENCE {
                hwFrMapPppIfIndex
                    InterfaceIndex,
                hwFrMapPppDlciNumber
                    Integer32,
                hwFrMapPppVTIfIndex
                    Integer32,
                hwFrMapPppState
                    INTEGER
             }

        hwFrMapPppIfIndex OBJECT-TYPE
            SYNTAX InterfaceIndex
            MAX-ACCESS not-accessible
            STATUS current
            DESCRIPTION
                "Indicates the interface index."
            ::= { hwFrMapPppEntry 1 }

        hwFrMapPppDlciNumber OBJECT-TYPE
            SYNTAX Integer32 (16..1022)
            MAX-ACCESS read-only
            STATUS current
            DESCRIPTION
                "Indicates the DLCI of the PVC mapped by PPP."
            ::= { hwFrMapPppEntry 2 }

        hwFrMapPppVTIfIndex OBJECT-TYPE
            SYNTAX Integer32
            MAX-ACCESS read-only
            STATUS current
            DESCRIPTION
                "Indicates the index of the VT interface."
            ::= { hwFrMapPppEntry 3 }

        hwFrMapPppState OBJECT-TYPE
            SYNTAX INTEGER
                {
                inactive(1),
                active(2)
                }
            MAX-ACCESS read-only
            STATUS current
            DESCRIPTION
               "Indicates the state of the PPP map.
                Options:
                1.inactive(1) - inactive
                2.active(2)   - active"
            ::= { hwFrMapPppEntry 4 }

--
-- hwFrMapBridgeTable
--
        hwFrMapBridgeTable OBJECT-TYPE
            SYNTAX SEQUENCE OF HwFrMapBridgeEntry
            MAX-ACCESS not-accessible
            STATUS current
            DESCRIPTION
                "This table is used to indicate the bridge mapping on the PVC.
                 The index of this table are hwFrMapBridgeIfIndex and hwFrMapBridgeDlciNumber."
            ::= { hwFrObjects 8 }

        hwFrMapBridgeEntry OBJECT-TYPE
            SYNTAX HwFrMapBridgeEntry
            MAX-ACCESS not-accessible
            STATUS current
            DESCRIPTION
                "This table is used to indicate the bridge mapping on the PVC.
                 The index of this entry are hwFrMapBridgeIfIndex and hwFrMapBridgeDlciNumber."
            INDEX { hwFrMapBridgeIfIndex, hwFrMapBridgeDlciNumber }
            ::= { hwFrMapBridgeTable 1 }

        HwFrMapBridgeEntry ::=
            SEQUENCE {
                hwFrMapBridgeIfIndex
                    InterfaceIndex,
                hwFrMapBridgeDlciNumber
                    Integer32,
                hwFrMapBridgeState
                    INTEGER
             }

        hwFrMapBridgeIfIndex OBJECT-TYPE
            SYNTAX InterfaceIndex
            MAX-ACCESS not-accessible
            STATUS current
            DESCRIPTION
                "Indicates the interface index."
            ::= { hwFrMapBridgeEntry 1 }

        hwFrMapBridgeDlciNumber OBJECT-TYPE
            SYNTAX Integer32 (16..1022)
            MAX-ACCESS read-only
            STATUS current
            DESCRIPTION
                "Indicates the DLCI of the PVC mapped by bridge."
            ::= { hwFrMapBridgeEntry 2 }

        hwFrMapBridgeState OBJECT-TYPE
            SYNTAX INTEGER
                {
                   inactive(1),
                   active(2)
                }
            MAX-ACCESS read-only
            STATUS current
            DESCRIPTION
               "Indicates the state of the PVC mapped by bridge.
                Options:
                1.inactive(1) - inactive
                2.active(2)   - active"
            ::= { hwFrMapBridgeEntry 3 }

-- Conformance definitions
        hwFrConformance OBJECT IDENTIFIER ::= { hwFrMIB 2 }

        hwFrCompliances OBJECT IDENTIFIER ::= { hwFrConformance 1 }

        hwFrCompliance MODULE-COMPLIANCE
            STATUS current
            DESCRIPTION
                "The compliance statement for systems supporting
                the HUAWEI-Fr-MIB."
            MODULE
                MANDATORY-GROUPS { hwFrObjectGroup, hwFrPvcObjectGroup, hwFrPvcGroupObjectGroup, hwFrPvcGroupMemObjectGroup, hwFrPvcGroupMapIpObjectGroup, hwFrMapIpObjectGroup, hwFrMapPppObjectGroup, hwFrMapBridgeObjectGroup }
            ::= { hwFrCompliances 1 }

        hwFrGroups OBJECT IDENTIFIER ::= { hwFrConformance 2 }

        hwFrObjectGroup OBJECT-GROUP
            OBJECTS { hwFrIfIndex }
            STATUS current
            DESCRIPTION
                "The fr attribute group."
            ::= { hwFrGroups 1 }

        hwFrPvcObjectGroup OBJECT-GROUP
            OBJECTS { hwFrPvcIfIndex, hwFrPvcDlciNumber }
            STATUS current
            DESCRIPTION
                "The fr PVC attribute group."
            ::= { hwFrGroups 2 }

        hwFrPvcGroupObjectGroup OBJECT-GROUP
            OBJECTS { hwFrPvcGroupIfIndex, hwFrPvcGroupName }
            STATUS current
            DESCRIPTION
                "The fr pvc-group attribute group."
            ::= { hwFrGroups 3 }

        hwFrPvcGroupMemObjectGroup OBJECT-GROUP
            OBJECTS { hwFrPvcGroupMemIfIndex, hwFrPvcGroupMemPvcGroupName, hwFrPvcGroupMemDlciNumber }
            STATUS current
            DESCRIPTION
                "The fr pvc-group member attribute group."
            ::= { hwFrGroups 4 }

        hwFrPvcGroupMapIpObjectGroup OBJECT-GROUP
            OBJECTS { hwFrPvcGroupMapIpIfIndex, hwFrPvcGroupMapIpName, hwFrPvcGroupMapIpIpAddr }
            STATUS current
            DESCRIPTION
                "The fr pvc-group mapping attribute group."
            ::= { hwFrGroups 5 }

        hwFrMapIpObjectGroup OBJECT-GROUP
            OBJECTS { hwFrMapIpIfIndex, hwFrMapIpAddress, hwFrMapIpDlciNumber }
            STATUS current
            DESCRIPTION
                "The fr ip mapping attribute group."
            ::= { hwFrGroups 6 }

        hwFrMapPppObjectGroup OBJECT-GROUP
            OBJECTS { hwFrMapPppIfIndex, hwFrMapPppDlciNumber }
            STATUS current
            DESCRIPTION
                "The fr ppp mapping attribute group."
            ::= { hwFrGroups 7 }

        hwFrMapBridgeObjectGroup OBJECT-GROUP
            OBJECTS { hwFrMapBridgeIfIndex, hwFrMapBridgeDlciNumber }
            STATUS current
            DESCRIPTION
                "The fr bridge mapping attribute group."
            ::= { hwFrGroups 8 }

    END
--
-- HUAWEI-Fr-MIB.mib
--
