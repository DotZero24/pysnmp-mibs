-- ============================================================================
-- Copyright (C) 2017 by  HUAWEI TECHNOLOGIES. All rights reserved.
--
-- Description: HUAWEI-FLOW-SPEC-MIB , this Mib module for management
--              of flow specifications.
-- Reference: This Mib was extracted from RFC 5575
-- Version: V1.03
-- History:
-- ============================================================================

 HUAWEI-FLOW-SPEC-MIB DEFINITIONS ::= BEGIN

        IMPORTS
            entPhysicalIndex
                FROM ENTITY-MIB
            hwDatacomm
                FROM HUAWEI-MIB
            OBJECT-GROUP, MODULE-COMPLIANCE, NOTIFICATION-GROUP
                FROM SNMPv2-CONF
            IpAddress, Integer32, Unsigned32, Gauge32, Counter32, Counter64,
            OBJECT-TYPE, MODULE-IDENTITY, NOTIFICATION-TYPE
                FROM SNMPv2-SMI
            TEXTUAL-CONVENTION
                FROM SNMPv2-TC
            DisplayString, TimeStamp, RowStatus, DateAndTime
                FROM SNMPv2-TC;

-- Jan 19, 2015 at 15:02 GMT
        hwFlowSpecMIB MODULE-IDENTITY
            LAST-UPDATED "201708291211Z"        -- Jan 19, 2015 at 11:40 GMT
            ORGANIZATION
                "Huawei Technologies Co.,Ltd."
            CONTACT-INFO
                "Huawei Industrial Base
                  Bantian, Longgang
                   Shenzhen 518129
                   People's Republic of China
                   Website: http://www.huawei.com
                   Email: support@huawei.com
                 "

            DESCRIPTION
                "The Mib module for management of flow specifications. Huawei Technologies co.,Ltd.
                Supplementary information may be available at:
                http://www.huawei.com"

           REVISION "201708291211Z"
           DESCRIPTION
           "Update"

           REVISION "201703191211Z"
           DESCRIPTION
           "Update"

           REVISION "201611071511Z"
           DESCRIPTION
           "Update"

           REVISION "201501070955Z"
           DESCRIPTION
           "Update"
            ::= { hwDatacomm 339 }

--
-- Textual conventions
--
        HWFlowAddrFmType ::= TEXTUAL-CONVENTION
            STATUS current
            DESCRIPTION
                "Address Family Type for Flow Route."
            SYNTAX INTEGER
                {
                ipv4flow(7),
                ipv6flow(15)
                }

--
-- Node definitions
--
        -- 1.3.6.1.4.1.2011.5.25.339.1
        hwFlowSpecificationsObjects OBJECT IDENTIFIER ::= { hwFlowSpecMIB 1 }

        -- 1.3.6.1.4.1.2011.5.25.339.1.1
        hwFlowSpecRtStatisticsTable OBJECT-TYPE
            SYNTAX SEQUENCE OF HwFlowSpecRtStatisticsEntry
            MAX-ACCESS not-accessible
            STATUS current
            DESCRIPTION
                "FlowSpec Statistics Table.
                This table describes the Flow Specification table and contains all Flow Specification data."
            ::= { hwFlowSpecificationsObjects 1 }

        -- 1.3.6.1.4.1.2011.5.25.339.1.1.1
        hwFlowSpecRtStatisticsEntry OBJECT-TYPE
            SYNTAX HwFlowSpecRtStatisticsEntry
            MAX-ACCESS not-accessible
            STATUS current
            DESCRIPTION
                "The entry information about the flow specifications statistics."
            INDEX { hwFlowRtIndex }
            ::= { hwFlowSpecRtStatisticsTable 1 }

        HwFlowSpecRtStatisticsEntry ::=
            SEQUENCE {
                hwFlowRtIndex
                    Unsigned32,
                hwFlowRuleNumber
                    Counter64,
                hwFlowRtMatchPackets
                    Counter64,
                hwFlowRtMatchBytes
                    Counter64,
                hwFlowRtMatchPacketPerSec
                    Counter64,
                hwFlowRtMatchBitPerSec
                    Counter64
             }

        -- 1.3.6.1.4.1.2011.5.25.339.1.1.1.1
        hwFlowRtIndex OBJECT-TYPE
            SYNTAX Unsigned32
            MAX-ACCESS not-accessible
            STATUS current
            DESCRIPTION
                "The index of the flow route."
            ::= { hwFlowSpecRtStatisticsEntry 1 }

        -- 1.3.6.1.4.1.2011.5.25.339.1.1.1.2
        hwFlowRuleNumber OBJECT-TYPE
            SYNTAX Counter64
            MAX-ACCESS read-only
            STATUS current
            DESCRIPTION
                "The rule number."
            ::= { hwFlowSpecRtStatisticsEntry 2 }

        -- 1.3.6.1.4.1.2011.5.25.339.1.1.1.3
        hwFlowRtMatchPackets OBJECT-TYPE
            SYNTAX Counter64
            MAX-ACCESS read-only
            STATUS current
            DESCRIPTION
                "The match packets."
            ::= { hwFlowSpecRtStatisticsEntry 3 }

        -- 1.3.6.1.4.1.2011.5.25.339.1.1.1.4
        hwFlowRtMatchBytes OBJECT-TYPE
            SYNTAX Counter64
            MAX-ACCESS read-only
            STATUS current
            DESCRIPTION
                "The match bytes."
            ::= { hwFlowSpecRtStatisticsEntry 4 }

        -- 1.3.6.1.4.1.2011.5.25.339.1.1.1.5
        hwFlowRtMatchPacketPerSec OBJECT-TYPE
            SYNTAX Counter64
            MAX-ACCESS read-only
            STATUS current
            DESCRIPTION
                "The match packets per sec."
            ::= { hwFlowSpecRtStatisticsEntry 5 }

        -- 1.3.6.1.4.1.2011.5.25.339.1.1.1.6
        hwFlowRtMatchBitPerSec OBJECT-TYPE
            SYNTAX Counter64
            MAX-ACCESS read-only
            STATUS current
            DESCRIPTION
                "The match bits per sec."
            ::= { hwFlowSpecRtStatisticsEntry 6 }

        -- 1.3.6.1.4.1.2011.5.25.339.1.2
        hwFlowSpecRtTable OBJECT-TYPE
            SYNTAX SEQUENCE OF HwFlowSpecRtEntry
            MAX-ACCESS not-accessible
            STATUS current
            DESCRIPTION
                "FlowSpec Statistics Table.
                This table describes the Flow Specification routing table and contains all Flow Specification route data."
            ::= { hwFlowSpecificationsObjects 2 }

        -- 1.3.6.1.4.1.2011.5.25.339.1.2.1
        hwFlowSpecRtEntry OBJECT-TYPE
            SYNTAX HwFlowSpecRtEntry
            MAX-ACCESS not-accessible
            STATUS current
            DESCRIPTION
                "The entry information about the flow specifications statistics."
            INDEX { hwFlowSpecComponents }
            ::= { hwFlowSpecRtTable 1 }

        HwFlowSpecRtEntry ::=
            SEQUENCE {
                hwFlowSpecComponents
                    OCTET STRING,
                hwFlowSpecRuleNumber
                    Counter64,
                hwFlowSpecRtMatchPackets
                    Counter64,
                hwFlowSpecRtMatchBytes
                    Counter64,
                hwFlowSpecRtMatchPacketPerSec
                    Counter64,
                hwFlowSpecRtMatchBitPerSec
                    Counter64,
                hwFlowSpecRtPassPackets
                    Counter64,
                hwFlowSpecRtPassPckPerSec
                    Counter64,
                hwFlowSpecRtPassBytes
                    Counter64,
                hwFlowSpecRtPassBitPerSec
                    Counter64,
                hwFlowSpecRtDropPackets
                    Counter64,
                hwFlowSpecRtDropPckPerSec
                    Counter64,
                hwFlowSpecRtDropBytes
                    Counter64,
                hwFlowSpecRtDropBitPerSec
                    Counter64
             }

        -- 1.3.6.1.4.1.2011.5.25.339.1.1.2.1
        hwFlowSpecComponents OBJECT-TYPE
            SYNTAX OCTET STRING
            MAX-ACCESS not-accessible
            STATUS current
            DESCRIPTION
                "The components supported."
            ::= { hwFlowSpecRtEntry 1 }

        -- 1.3.6.1.4.1.2011.5.25.339.1.1.2.2
        hwFlowSpecRuleNumber OBJECT-TYPE
            SYNTAX Counter64
            MAX-ACCESS read-only
            STATUS current
            DESCRIPTION
                "The rule number."
            ::= { hwFlowSpecRtEntry 2 }

        -- 1.3.6.1.4.1.2011.5.25.339.1.1.2.3
        hwFlowSpecRtMatchPackets OBJECT-TYPE
            SYNTAX Counter64
            MAX-ACCESS read-only
            STATUS current
            DESCRIPTION
                "The match packets."
            ::= { hwFlowSpecRtEntry 3 }

        -- 1.3.6.1.4.1.2011.5.25.339.1.1.2.4
        hwFlowSpecRtMatchBytes OBJECT-TYPE
            SYNTAX Counter64
            MAX-ACCESS read-only
            STATUS current
            DESCRIPTION
                "The match bytes."
            ::= { hwFlowSpecRtEntry 4 }

        -- 1.3.6.1.4.1.2011.5.25.339.1.1.2.5
        hwFlowSpecRtMatchPacketPerSec OBJECT-TYPE
            SYNTAX Counter64
            MAX-ACCESS read-only
            STATUS current
            DESCRIPTION
                "The match packets per sec."
            ::= { hwFlowSpecRtEntry 5 }

        -- 1.3.6.1.4.1.2011.5.25.339.1.1.2.6
        hwFlowSpecRtMatchBitPerSec OBJECT-TYPE
            SYNTAX Counter64
            MAX-ACCESS read-only
            STATUS current
            DESCRIPTION
                "The match bits per sec."
            ::= { hwFlowSpecRtEntry 6 }

        -- 1.3.6.1.4.1.2011.5.25.339.1.1.2.7
        hwFlowSpecRtPassPackets OBJECT-TYPE
            SYNTAX Counter64
            MAX-ACCESS read-only
            STATUS current
            DESCRIPTION
                "The pass packets."
            ::= { hwFlowSpecRtEntry 7 }

        -- 1.3.6.1.4.1.2011.5.25.339.1.1.2.8
        hwFlowSpecRtPassPckPerSec OBJECT-TYPE
            SYNTAX Counter64
            MAX-ACCESS read-only
            STATUS current
            DESCRIPTION
                "The pass packets per sec."
            ::= { hwFlowSpecRtEntry 8 }

        -- 1.3.6.1.4.1.2011.5.25.339.1.1.2.9
        hwFlowSpecRtPassBytes OBJECT-TYPE
            SYNTAX Counter64
            MAX-ACCESS read-only
            STATUS current
            DESCRIPTION
                "The pass bytes."
            ::= { hwFlowSpecRtEntry 9 }

        -- 1.3.6.1.4.1.2011.5.25.339.1.1.2.10
        hwFlowSpecRtPassBitPerSec OBJECT-TYPE
            SYNTAX Counter64
            MAX-ACCESS read-only
            STATUS current
            DESCRIPTION
                "The pass bits per sec."
            ::= { hwFlowSpecRtEntry 10 }

        -- 1.3.6.1.4.1.2011.5.25.339.1.1.2.11
        hwFlowSpecRtDropPackets OBJECT-TYPE
            SYNTAX Counter64
            MAX-ACCESS read-only
            STATUS current
            DESCRIPTION
                "The drop packets."
            ::= { hwFlowSpecRtEntry 11 }

        -- 1.3.6.1.4.1.2011.5.25.339.1.1.2.12
        hwFlowSpecRtDropPckPerSec OBJECT-TYPE
            SYNTAX Counter64
            MAX-ACCESS read-only
            STATUS current
            DESCRIPTION
                "The drop packets per sec."
            ::= { hwFlowSpecRtEntry 12 }

        -- 1.3.6.1.4.1.2011.5.25.339.1.1.2.13
        hwFlowSpecRtDropBytes OBJECT-TYPE
            SYNTAX Counter64
            MAX-ACCESS read-only
            STATUS current
            DESCRIPTION
                "The drop bytes."
            ::= { hwFlowSpecRtEntry 13 }

        -- 1.3.6.1.4.1.2011.5.25.339.1.1.2.14
        hwFlowSpecRtDropBitPerSec OBJECT-TYPE
            SYNTAX Counter64
            MAX-ACCESS read-only
            STATUS current
            DESCRIPTION
                "The drop bits per sec."
            ::= { hwFlowSpecRtEntry 14 }

	-- 1.3.6.1.4.1.2011.5.25.339.1.3
        hwFlowRouteStatisticsTable OBJECT-TYPE
            SYNTAX SEQUENCE OF HwFlowRouteStatisticsEntry
            MAX-ACCESS not-accessible
            STATUS current
            DESCRIPTION
                "FlowSpec Statistics Table.
                This table describes the Flow Specification statistics table and contains all Flow Specification statistics."
            ::= { hwFlowSpecificationsObjects 3 }

        -- 1.3.6.1.4.1.2011.5.25.339.1.3.1
        hwFlowRouteStatisticsEntry OBJECT-TYPE
            SYNTAX HwFlowRouteStatisticsEntry
            MAX-ACCESS not-accessible
            STATUS current
            DESCRIPTION
                "The entry information about the flow specifications statistics."
            INDEX { hwFlowRouteIndex, hwFlowRouteVrfIndex, hwFlowRouteAddrFamily }
            ::= { hwFlowRouteStatisticsTable 1 }

        HwFlowRouteStatisticsEntry ::=
            SEQUENCE {
                hwFlowRouteIndex
                    Unsigned32,
                hwFlowRouteVrfIndex
                    Unsigned32,
                hwFlowRouteAddrFamily
                    HWFlowAddrFmType,
                hwFlowRouteRuleNumber
                    Counter64,
                hwFlowRouteMatchPackets
                    Counter64,
                hwFlowRouteRtMatchBytes
                    Counter64,
                hwFlowRouteMatchPacketPerSec
                    Counter64,
                hwFlowRouteMatchBitPerSec
                    Counter64
             }

        -- 1.3.6.1.4.1.2011.5.25.339.1.3.1.1
        hwFlowRouteIndex OBJECT-TYPE
            SYNTAX Unsigned32
            MAX-ACCESS not-accessible
            STATUS current
            DESCRIPTION
                "The index of the flow route."
            ::= { hwFlowRouteStatisticsEntry 1 }

        -- 1.3.6.1.4.1.2011.5.25.339.1.3.1.2
       hwFlowRouteVrfIndex OBJECT-TYPE
            SYNTAX Unsigned32
            MAX-ACCESS not-accessible
            STATUS current
            DESCRIPTION
                "The VRF's index of the flow route.."
            ::= { hwFlowRouteStatisticsEntry 2 }

        -- 1.3.6.1.4.1.2011.5.25.339.1.3.1.3
        hwFlowRouteAddrFamily OBJECT-TYPE
            SYNTAX HWFlowAddrFmType
            MAX-ACCESS not-accessible
            STATUS current
            DESCRIPTION
                "Address Family Type for Flow Route."
            ::= { hwFlowRouteStatisticsEntry 3 }

	-- 1.3.6.1.4.1.2011.5.25.339.1.3.1.4
        hwFlowRouteRuleNumber OBJECT-TYPE
            SYNTAX Counter64
            MAX-ACCESS read-only
            STATUS current
            DESCRIPTION
                "The rule number."
            ::= { hwFlowRouteStatisticsEntry 4 }

        -- 1.3.6.1.4.1.2011.5.25.339.1.3.1.5
        hwFlowRouteMatchPackets OBJECT-TYPE
            SYNTAX Counter64
            MAX-ACCESS read-only
            STATUS current
            DESCRIPTION
                "The match packets."
            ::= { hwFlowRouteStatisticsEntry 5 }

        -- 1.3.6.1.4.1.2011.5.25.339.1.3.1.6
        hwFlowRouteRtMatchBytes OBJECT-TYPE
            SYNTAX Counter64
            MAX-ACCESS read-only
            STATUS current
            DESCRIPTION
                "The match bytes."
            ::= { hwFlowRouteStatisticsEntry 6 }

        -- 1.3.6.1.4.1.2011.5.25.339.1.3.1.7
        hwFlowRouteMatchPacketPerSec OBJECT-TYPE
            SYNTAX Counter64
            MAX-ACCESS read-only
            STATUS current
            DESCRIPTION
                "The match packets per sec."
            ::= { hwFlowRouteStatisticsEntry 7 }

        -- 1.3.6.1.4.1.2011.5.25.339.1.3.1.8
        hwFlowRouteMatchBitPerSec OBJECT-TYPE
            SYNTAX Counter64
            MAX-ACCESS read-only
            STATUS current
            DESCRIPTION
                "The match bits per sec."
            ::= { hwFlowRouteStatisticsEntry 8 }

    END

--
-- HUAWEI-FLOW-SPEC-MIB.mib
--
