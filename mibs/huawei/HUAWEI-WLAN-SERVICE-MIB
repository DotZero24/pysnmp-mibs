--
-- HUAWEI-WLAN-SERVICE-MIB.mib
-- MIB generated by MG-SOFT Visual MIB Builder Version 4.0 Build 341
-- Sunday, May 27, 2012 at 18:29:22
--

--  HUAWEI-WLAN-SERVICE-MIB.mib
-- MIB generated by MG-SOFT Visual MIB Builder Version 4.0 Build 341
-- Sunday, May 27, 2012 at 15:17:45
--
--  HUAWEI-WLAN-SERVICE-MIB.mib
-- MIB generated by MG-SOFT Visual MIB Builder Version 4.0 Build 341
-- Saturday, May 26, 2012 at 19:37:01
--
--  HUAWEI-WLAN-SERVICE-MIB.mib
-- MIB generated by MG-SOFT Visual MIB Builder Version 4.0 Build 253
-- Friday, August 8, 2014 at 13:25:09

--  HUAWEI-WLAN-SERVICE-MIB.mib
-- MIB generated by MG-SOFT Visual MIB Builder Version 4.0 Build 253
-- Friday, August 22, 2014 at 13:25:09

--  HUAWEI-WLAN-SERVICE-MIB.mib
-- MIB generated by MG-SOFT Visual MIB Builder Version 4.0 Build 253
-- Saturday, November 29, 2014 at 13:25:09
--
--  ============================================================================
-- Copyright (C) 2015 by  HUAWEI TECHNOLOGIES. All rights reserved.
-- Description:  The mib is used for configuring the information of the SERVICE, including
--               ESS management,STA management and so on.
-- Reference:
-- Version:      V1.14
--
-- ============================================================================

	HUAWEI-WLAN-SERVICE-MIB DEFINITIONS ::= BEGIN

		IMPORTS
			hwWlan
				FROM HUAWEI-WLAN-MIB
			OBJECT-GROUP, MODULE-COMPLIANCE
				FROM SNMPv2-CONF
			IpAddress, Integer32, Unsigned32, Counter64, OBJECT-TYPE,
			MODULE-IDENTITY
				FROM SNMPv2-SMI
			RowStatus, MacAddress, DateAndTime
				FROM SNMPv2-TC;


--     revision history
-- September 02, 2010 at 10:00 GMT
-- June 01, 2010 at 10:00 GMT
-- August 13, 2010 at 10:00 GMT
-- September 02, 2010 at 10:00 GMT
-- 1.3.6.1.4.1.2011.6.139.4
-- September 02, 2010 at 10:00 GMT
-- September 02, 2010 at 10:00 GMT
-- August 13, 2010 at 10:00 GMT
-- June 01, 2010 at 10:00 GMT
-- 1.3.6.1.4.1.2011.6.139.4
-- September 02, 2010 at 10:00 GMT
-- June 01, 2010 at 10:00 GMT
-- August 13, 2010 at 10:00 GMT
-- September 02, 2010 at 10:00 GMT
		-- 1.3.6.1.4.1.2011.6.139.4
		hwWlanServiceManagement MODULE-IDENTITY
			LAST-UPDATED "201509250938Z"         --Sep 25, 2015 at 09:38 GMT
			ORGANIZATION
				"Huawei Technologies Co.,Ltd."
			CONTACT-INFO
            "Huawei Industrial Base
				   Bantian, Longgang
				   Shenzhen 518129
				   People's Republic of China
				   Website: http://www.huawei.com
				   Email: support@huawei.com
				  "
			DESCRIPTION
				"V1.14 add hwWlanServiceVapFrequency."
			REVISION "201509250938Z"         --Sep 25, 2015 at 09:38 GMT
			DESCRIPTION
				"V1.13 modifiy the range of hwMeshProfileUrgentHandoverLowRateThreshold node."
			REVISION "201506182025Z"         --June 18, 2015 at 20:25 GMT
			DESCRIPTION
				"V1.12 modifiy hwNeighborApLocationIDList,hwMacBridgeChannelID,hwBridgeLinkChannelID."
			REVISION "201501202025Z"         --January 20, 2015 at 20:25 GMT

			DESCRIPTION
				"V1.11 modifiy hwBridgeProfileBridgeName and hwMeshProfileMeshID nodes in mesh profile and bridge profile."
			REVISION "201412161525Z"         --Dec 16, 2014 at 15:25 GMT

			DESCRIPTION
				"V1.10 add fwa node in mesh profile."
			REVISION "201411291525Z"         --November 29, 2014 at 15:25 GMT

			DESCRIPTION
				"V1.09 modify the range of hwMeshProfileUrgentHandoverLowRateThreshold node."
			REVISION "201408301525Z"         --August 30, 2014 at 15:25 GMT

			DESCRIPTION
				"V1.08 add location ID nodes."
			REVISION "201408221525Z"         --August 22, 2014 at 15:25 GMT

			DESCRIPTION
				"V1.07 add mesh profile nodes and statistic nodes."
			REVISION "201408081525Z"         --August 8, 2014 at 15:25 GMT

			DESCRIPTION
				"V1.06 add hwL3RoamInStationCount and hwL3RoamOutStationCount nodes."
			REVISION "201407171525Z"         --Jun 08, 2014 at 15:25 GMT

			DESCRIPTION
				"V1.05 Mesh Link number change."
			REVISION "201406081525Z"         --Jun 08, 2014 at 15:25 GMT

			DESCRIPTION
				"Wlan service management."
			REVISION "201404211405Z"         -- Apirl 21, 2014 at 14:05 GMT
			DESCRIPTION
				" V1.04 add new nodes for hwStationTable."
                                                    	REVISION "201403221405Z"         -- Mar 22, 2014 at 14:05 GMT
			DESCRIPTION
				" V1.03 add new nodes for hwEssManagementTable,hwStationTable and hwAcStatistics."

			REVISION "201312111409Z"         -- Dec 11, 2013 at 14:09 GMT
			DESCRIPTION
				" V1.02, modify both hwStaStatOperMode and hwMeshProfileMaxLinkNum"
			REVISION "201310231409Z"         -- October 23, 2013 at 14:09 GMT
			DESCRIPTION
				" V1.01, Add for v2r5"
			REVISION "201006011000Z"
			DESCRIPTION
				" V1.00, The first Draft."
			REVISION "201008131000Z"
			DESCRIPTION
				" V1.02, Add enum value unknown(-1) in hwWlanServiceEssForwardMode of hwEssManagementTable."
			REVISION "201009021000Z"
			DESCRIPTION
				" V1.03, Add leaf nodes named hwWlanServiceVapBssid in hwVapManagementTable."

			::= { hwWlan 4 }




--
-- Node definitions
--


		-- 1.3.6.1.4.1.2011.6.139.4.1
		hwEssManagementTable OBJECT-TYPE
			SYNTAX SEQUENCE OF HwEssManagementEntry
			MAX-ACCESS not-accessible
			STATUS current
			DESCRIPTION
				"Ess management table."
			::= { hwWlanServiceManagement 1 }


		-- 1.3.6.1.4.1.2011.6.139.4.1.1
		hwEssManagementEntry OBJECT-TYPE
			SYNTAX HwEssManagementEntry
			MAX-ACCESS not-accessible
			STATUS current
			DESCRIPTION
				"Ess management entry."
			INDEX { hwWlanServiceEssName }
			::= { hwEssManagementTable 1 }

		HwEssManagementEntry ::=
			SEQUENCE {
				hwWlanServiceEssName
					OCTET STRING,
				hwWlanServiceEssSsid
					OCTET STRING,
				hwWlanServiceEssHideSsid
					INTEGER,
				hwWlanServiceEssUserIsolate
					INTEGER,
				hwWlanServiceEssType
					INTEGER,
				hwWlanServiceEssTrafficProfileName
					OCTET STRING,
				hwWlanServiceEssSecurityProfileName
					OCTET STRING,
				hwWlanServiceEssMaxUserNumber
					Integer32,
				hwWlanServiceEssAssociationTimeOut
					Integer32,
				hwWlanServiceEssIgmpMode
					INTEGER,
				hwWlanServiceEssRowStatus
					RowStatus,
				hwWlanServiceEssForwardMode
					INTEGER,
				hwWlanServiceEssNum
					Integer32,
				hwWlanServiceVlan
					Integer32,
				hwWlanServiceEssDhcpSnooping
					INTEGER,
				hwWlanServiceEssServiceVlanEnable
					INTEGER,
				hwWlanServiceEssIPSGEnable
					INTEGER,
				hwWlanServiceEssDhcpTrustPort
					INTEGER,
				hwWlanServiceEssDaiSwitch
					INTEGER,
				hwWlanServiceEssArpThreshold
					Integer32,
				hwWlanServiceEssTunnelProtocol
					Integer32,
				hwWlanServiceEssStatus
					Integer32,
				hwWlanServiceEssOfflineManagement
					INTEGER,
				hwWlanServiceEssBlacklistProfileName
					OCTET STRING,
				hwWlanServiceEssWhitelistProfileName
					OCTET STRING,
				hwWlanServiceEssStaAccessMode
					INTEGER,
				hwWlanServiceEssDhcpOption82InsertSwitch
					INTEGER,
				hwWlanServiceEssDhcpOption82RemoteIdFormat
					INTEGER,
				hwWlanServiceEssDhcpSnoopingOption
					OCTET STRING,
				hwWlanServiceEssBroadCastPps
					Integer32,
				hwWlanServiceEssMultiCastPps
					Integer32,
				hwWlanServiceEssUniCastPps
					Integer32,
				hwWlanServiceEssBroadCastSwitch
					INTEGER,
				hwWlanServiceEssMultiCastSwitch
					INTEGER,
				hwWlanServiceEssUniCastSwitch
					INTEGER,
				hwWlanServiceEssSaclNameInbound
					OCTET STRING,
				hwWlanServiceEssSaclNameOutbound
					OCTET STRING,
				hwWlanServiceEssSaclNumInbound
					Integer32,
				hwWlanServiceEssSaclNumOutbound
					Integer32,
				hwWlanServiceEssSaclSwtichInbound
					INTEGER,
				hwWlanServiceEssSaclSwtichOutbound
					INTEGER,
				hwWlanServiceEssServiceModeSwitch
					INTEGER,
				hwWlanServiceEssAutoOffEssAdminSwitch
					INTEGER,
				hwWlanServiceEssAutoOffEssStartTime
					OCTET STRING,
				hwWlanServiceEssAutoOffEssEndTime
					OCTET STRING,
				hwWlanServiceEssNdSnooping
					INTEGER,
				hwWlanServiceEssSaclNameInboundIPv6
					OCTET STRING,
				hwWlanServiceEssSaclNameOutboundIPv6
					OCTET STRING,
				hwWlanServiceEssSaclNumInboundIPv6
					Integer32,
				hwWlanServiceEssSaclNumOutboundIPv6
					Integer32,
				hwWlanServiceEssSaclSwtichInboundIPv6
					INTEGER,
				hwWlanServiceEssSaclSwtichOutboundIPv6
					INTEGER,
				hwWlanServiceEssNdTrustPort
					INTEGER,
				hwWlanServiceEssMldSnoopingEable
					INTEGER,
				hwWlanServiceEssIPSGEnableRejectAssoc
					INTEGER,
				hwWlanServiceEssLearnClientIpEnable
					INTEGER,
				hwWlanServiceEssHomeAgent
					INTEGER,
				hwWlanServiceEssVlanMobilityGroup
					Integer32
			 }

		-- 1.3.6.1.4.1.2011.6.139.4.1.1.1
		hwWlanServiceEssName OBJECT-TYPE
			SYNTAX OCTET STRING (SIZE (1..31))
			MAX-ACCESS not-accessible
			STATUS current
			DESCRIPTION
				"Ess name, the key of the ess management table."
			::= { hwEssManagementEntry 1 }

		-- 1.3.6.1.4.1.2011.6.139.4.1.1.2
		hwWlanServiceEssSsid OBJECT-TYPE
			SYNTAX OCTET STRING (SIZE (1..32))
			MAX-ACCESS read-create
			STATUS current
			DESCRIPTION
				"Ess's ssid, a string name of ess."
			::= { hwEssManagementEntry 2 }

		-- 1.3.6.1.4.1.2011.6.139.4.1.1.3
		hwWlanServiceEssHideSsid OBJECT-TYPE
			SYNTAX INTEGER
				{
				enable(1),
				disable(2)
				}
			MAX-ACCESS read-create
			STATUS current
			DESCRIPTION
				"The switch whether the ess hide its ssid or not,
				when sent a beacon frame.
				Enable means hidden, and disable means not hidden."
			::= { hwEssManagementEntry 3 }

		-- 1.3.6.1.4.1.2011.6.139.4.1.1.4
		hwWlanServiceEssUserIsolate OBJECT-TYPE
			SYNTAX INTEGER
				{
				enable(1),
				disable(2)
				}
			MAX-ACCESS read-create
			STATUS current
			DESCRIPTION
				"The switch whether the users of the ess
				are isolated or not.
				Enable means isolated, disable means not isolated."
			::= { hwEssManagementEntry 4 }

		-- 1.3.6.1.4.1.2011.6.139.4.1.1.5
		hwWlanServiceEssType OBJECT-TYPE
			SYNTAX INTEGER
				{
				service(1),
				apManagement(2),
				acManagement(3)
				}
			MAX-ACCESS read-create
			STATUS current
			DESCRIPTION
				"The ess type.
				service means the ess is used for service,
				ap-management means the ess is used for managing ap,
				ac-management means the ess is used for managing ac."
			::= { hwEssManagementEntry 5 }

		-- 1.3.6.1.4.1.2011.6.139.4.1.1.6
		hwWlanServiceEssTrafficProfileName OBJECT-TYPE
			SYNTAX OCTET STRING (SIZE (1..31))
			MAX-ACCESS read-create
			STATUS current
			DESCRIPTION
				"The traffic profile name that the ess bind."
			::= { hwEssManagementEntry 6 }

		-- 1.3.6.1.4.1.2011.6.139.4.1.1.7
		hwWlanServiceEssSecurityProfileName OBJECT-TYPE
			SYNTAX OCTET STRING (SIZE (1..31))
			MAX-ACCESS read-create
			STATUS current
			DESCRIPTION
				"The security profile name that the ess bind."
			::= { hwEssManagementEntry 7 }


		-- 1.3.6.1.4.1.2011.6.139.4.1.1.8
		hwWlanServiceEssMaxUserNumber OBJECT-TYPE
			SYNTAX Integer32
			MAX-ACCESS read-create
			STATUS current
			DESCRIPTION
				"The maximum number of users the ess can burden."
			::= { hwEssManagementEntry 8 }

		-- 1.3.6.1.4.1.2011.6.139.4.1.1.9
		hwWlanServiceEssAssociationTimeOut OBJECT-TYPE
			SYNTAX Integer32
			MAX-ACCESS read-create
			STATUS current
			DESCRIPTION
				"The user's association aging time."
			::= { hwEssManagementEntry 9 }

		-- 1.3.6.1.4.1.2011.6.139.4.1.1.10
		hwWlanServiceEssIgmpMode OBJECT-TYPE
			SYNTAX INTEGER
				{
				proxy(1),
				snooping(2),
				off(3)
				}
			MAX-ACCESS read-create
			STATUS current
			DESCRIPTION
				"The igmp mode of the ess,
				proxy means the ess will act igmp proxy function,
				snooping means the ess will act igmp snooping function,
				off means the ess will do nothing."
			::= { hwEssManagementEntry 10 }

		-- 1.3.6.1.4.1.2011.6.139.4.1.1.11
		hwWlanServiceEssRowStatus OBJECT-TYPE
			SYNTAX RowStatus
			MAX-ACCESS read-write
			STATUS current
			DESCRIPTION
				"The row status of ess management table."
			::= { hwEssManagementEntry 11 }


		-- 1.3.6.1.4.1.2011.6.139.4.1.1.12
		hwWlanServiceEssForwardMode OBJECT-TYPE
			SYNTAX INTEGER
				{
				directForward(1),
				tunnel(2),
				unknown(-1)
				}
			MAX-ACCESS read-write
			STATUS current
			DESCRIPTION
				"Set ess based forward mode."
			::= { hwEssManagementEntry 12 }

		-- 1.3.6.1.4.1.2011.6.139.4.1.1.13
		hwWlanServiceEssNum OBJECT-TYPE
			SYNTAX Integer32
			MAX-ACCESS read-write
			STATUS current
			DESCRIPTION
				"The wlan-ess interface that the ess bind.The value of default wlan-ess interface num is 0xffffffff"
			::= { hwEssManagementEntry 13 }

		-- 1.3.6.1.4.1.2011.6.139.4.1.1.14
		hwWlanServiceVlan OBJECT-TYPE
			SYNTAX Integer32 (1..4094)
			MAX-ACCESS read-write
			STATUS current
			DESCRIPTION
				"The service-vlan  that the AP used.The value of default service-vlan is 1"
			::= { hwEssManagementEntry 14 }


		-- 1.3.6.1.4.1.2011.6.139.4.1.1.15
		hwWlanServiceEssDhcpSnooping OBJECT-TYPE
			SYNTAX INTEGER
				{
				enable(1),
				disable(2)
				}
			MAX-ACCESS read-write
			STATUS current
			DESCRIPTION
				"Description."
			::= { hwEssManagementEntry 15 }

		-- 1.3.6.1.4.1.2011.6.139.4.1.1.16
		hwWlanServiceEssServiceVlanEnable OBJECT-TYPE
			SYNTAX INTEGER
				{
				disable(1),
				enable(2)
				}
			MAX-ACCESS read-write
			STATUS current
			DESCRIPTION
				"Description: This node is not supported now."
			::= { hwEssManagementEntry 16 }

		-- 1.3.6.1.4.1.2011.6.139.4.1.1.17
		hwWlanServiceEssIPSGEnable OBJECT-TYPE
			SYNTAX INTEGER
				{
				disable(1),
				enable(2)
				}
			MAX-ACCESS read-write
			STATUS current
			DESCRIPTION
				"Description."
			::= { hwEssManagementEntry 17 }

		-- 1.3.6.1.4.1.2011.6.139.4.1.1.18
		hwWlanServiceEssDhcpTrustPort OBJECT-TYPE
			SYNTAX INTEGER
				{
				disable(1),
				enable(2)
				}
			MAX-ACCESS read-write
			STATUS current
			DESCRIPTION
				"Description."
			DEFVAL { disable }
			::= { hwEssManagementEntry 18 }

		-- 1.3.6.1.4.1.2011.6.139.4.1.1.19
		hwWlanServiceEssDaiSwitch OBJECT-TYPE
			SYNTAX INTEGER
				{
				disable(1),
				enable(2)
				}
			MAX-ACCESS read-write
			STATUS current
			DESCRIPTION
				"Description."
			DEFVAL { disable }
			::= { hwEssManagementEntry 19 }

		-- 1.3.6.1.4.1.2011.6.139.4.1.1.20
		hwWlanServiceEssArpThreshold OBJECT-TYPE
			SYNTAX Integer32 (0..2048)
			MAX-ACCESS read-write
			STATUS current
			DESCRIPTION
				"Description."
			::= { hwEssManagementEntry 20 }

		-- 1.3.6.1.4.1.2011.6.139.4.1.1.21
		hwWlanServiceEssTunnelProtocol OBJECT-TYPE
			SYNTAX Integer32
			MAX-ACCESS read-write
			STATUS current
			DESCRIPTION
				"Set tunnel protocol. Use bit for protocol configuration, each bit for a protocol: 1 -- configed,
				 0 -- be not configed. For example, EAP(0000 0001),DHCP(0000 0010),HTTP(0000 0100),WAPI(0000 1000),
				 MDNS(0001 0000).Now it just can be set with HTTP, EAP, MDNS or their combination."
			::= { hwEssManagementEntry 21 }


		-- 1.3.6.1.4.1.2011.6.139.4.1.1.22
		hwWlanServiceEssStatus OBJECT-TYPE
			SYNTAX Integer32
			MAX-ACCESS read-only
			STATUS current
			DESCRIPTION
				"Description."
			::= { hwEssManagementEntry 22 }

		-- 1.3.6.1.4.1.2011.6.139.4.1.1.23
		hwWlanServiceEssOfflineManagement OBJECT-TYPE
			SYNTAX INTEGER
				{
				disable(1),
				enable(2)
				}
			MAX-ACCESS read-write
			STATUS current
			DESCRIPTION
				"Description."
			::= { hwEssManagementEntry 23 }


		-- 1.3.6.1.4.1.2011.6.139.4.1.1.24
		hwWlanServiceEssBlacklistProfileName OBJECT-TYPE
			SYNTAX OCTET STRING (SIZE (1..31))
			MAX-ACCESS read-write
			STATUS current
			DESCRIPTION
				"Description."
			::= { hwEssManagementEntry 24 }


		-- 1.3.6.1.4.1.2011.6.139.4.1.1.25
		hwWlanServiceEssWhitelistProfileName OBJECT-TYPE
			SYNTAX OCTET STRING (SIZE (1..31))
			MAX-ACCESS read-write
			STATUS current
			DESCRIPTION
				"Description."
			::= { hwEssManagementEntry 25 }


		-- 1.3.6.1.4.1.2011.6.139.4.1.1.26
		hwWlanServiceEssStaAccessMode OBJECT-TYPE
			SYNTAX INTEGER
				{
				unknown(-1),
				disable(1),
				blacklistProfile(2),
				whitelistProfile(3)
				}
			MAX-ACCESS read-write
			STATUS current
			DESCRIPTION
				"Description."
			::= { hwEssManagementEntry 26 }


		-- 1.3.6.1.4.1.2011.6.139.4.1.1.27
		hwWlanServiceEssDhcpOption82InsertSwitch OBJECT-TYPE
			SYNTAX INTEGER
				{
				disable(1),
				enable(2)
				}
			MAX-ACCESS read-write
			STATUS current
			DESCRIPTION
				"Description."
			DEFVAL { disable }
			::= { hwEssManagementEntry 27 }
		-- 1.3.6.1.4.1.2011.6.139.4.1.1.28
		hwWlanServiceEssDhcpOption82RemoteIdFormat OBJECT-TYPE
			SYNTAX INTEGER
				{
				apMac(1),
				apMacSsid(2)
				}
			MAX-ACCESS read-write
			STATUS current
			DESCRIPTION
				"Description."
			DEFVAL { ap-mac }
			::= { hwEssManagementEntry 28 }


		-- 1.3.6.1.4.1.2011.6.139.4.1.1.29
		hwWlanServiceEssDhcpSnoopingOption OBJECT-TYPE
			SYNTAX OCTET STRING (SIZE (0..256))
			MAX-ACCESS read-write
			STATUS current
			DESCRIPTION
				"related cmd:
				dhcp snooping option <option-id>
				undo dhcp snooping option <option-id>
				undo dhcp snooping all

				Valid option id range is [1, 254].
				bit0 and bit 255 are reserved."
			::= { hwEssManagementEntry 29 }


		-- 1.3.6.1.4.1.2011.6.139.4.1.1.30
		hwWlanServiceEssBroadCastPps OBJECT-TYPE
			SYNTAX Integer32
			MAX-ACCESS read-write
			STATUS current
			DESCRIPTION
				"Description."
			::= { hwEssManagementEntry 30 }


		-- 1.3.6.1.4.1.2011.6.139.4.1.1.31
		hwWlanServiceEssMultiCastPps OBJECT-TYPE
			SYNTAX Integer32
			MAX-ACCESS read-write
			STATUS current
			DESCRIPTION
				"Description."
			::= { hwEssManagementEntry 31 }


		-- 1.3.6.1.4.1.2011.6.139.4.1.1.32
		hwWlanServiceEssUniCastPps OBJECT-TYPE
			SYNTAX Integer32
			MAX-ACCESS read-write
			STATUS current
			DESCRIPTION
				"Description."
			::= { hwEssManagementEntry 32 }


		-- 1.3.6.1.4.1.2011.6.139.4.1.1.33
		hwWlanServiceEssBroadCastSwitch OBJECT-TYPE
			SYNTAX INTEGER
				{
				disable(1),
				enable(2)
				}
			MAX-ACCESS read-write
			STATUS current
			DESCRIPTION
				"Description."
			DEFVAL { disable }
			::= { hwEssManagementEntry 33 }


		-- 1.3.6.1.4.1.2011.6.139.4.1.1.34
		hwWlanServiceEssMultiCastSwitch OBJECT-TYPE
			SYNTAX INTEGER
				{
				disable(1),
				enable(2)
				}
			MAX-ACCESS read-write
			STATUS current
			DESCRIPTION
				"Description."
			DEFVAL { disable }
			::= { hwEssManagementEntry 34 }


		-- 1.3.6.1.4.1.2011.6.139.4.1.1.35
		hwWlanServiceEssUniCastSwitch OBJECT-TYPE
			SYNTAX INTEGER
				{
				disable(1),
				enable(2)
				}
			MAX-ACCESS read-write
			STATUS current
			DESCRIPTION
				"Description."
			DEFVAL { disable }
			::= { hwEssManagementEntry 35 }


		-- 1.3.6.1.4.1.2011.6.139.4.1.1.36
		hwWlanServiceEssSaclNameInbound OBJECT-TYPE
			SYNTAX OCTET STRING (SIZE (1..65))
			MAX-ACCESS read-write
			STATUS current
			DESCRIPTION
				"Description."
			::= { hwEssManagementEntry 36 }


		-- 1.3.6.1.4.1.2011.6.139.4.1.1.37
		hwWlanServiceEssSaclNameOutbound OBJECT-TYPE
			SYNTAX OCTET STRING (SIZE (1..65))
			MAX-ACCESS read-write
			STATUS current
			DESCRIPTION
				"Description."
			::= { hwEssManagementEntry 37 }


		-- 1.3.6.1.4.1.2011.6.139.4.1.1.38
		hwWlanServiceEssSaclNumInbound OBJECT-TYPE
			SYNTAX Integer32
			MAX-ACCESS read-write
			STATUS current
			DESCRIPTION
				"The Sacl number range is 3000 to 3031, or 6000 to 6031."
			::= { hwEssManagementEntry 38 }


		-- 1.3.6.1.4.1.2011.6.139.4.1.1.39
		hwWlanServiceEssSaclNumOutbound OBJECT-TYPE
			SYNTAX Integer32
			MAX-ACCESS read-write
			STATUS current
			DESCRIPTION
				"The Sacl number range is 3000 to 3031, or 6000 to 6031."
			::= { hwEssManagementEntry 39 }


		-- 1.3.6.1.4.1.2011.6.139.4.1.1.40
		hwWlanServiceEssSaclSwtichInbound OBJECT-TYPE
			SYNTAX INTEGER
				{
				disable(1),
				enable(2)
				}
			MAX-ACCESS read-write
			STATUS current
			DESCRIPTION
				"Description."
			::= { hwEssManagementEntry 40 }


		-- 1.3.6.1.4.1.2011.6.139.4.1.1.41
		hwWlanServiceEssSaclSwtichOutbound OBJECT-TYPE
			SYNTAX INTEGER
				{
				disable(1),
				enable(2)
				}
			MAX-ACCESS read-write
			STATUS current
			DESCRIPTION
				"Description."
			::= { hwEssManagementEntry 41 }


		-- 1.3.6.1.4.1.2011.6.139.4.1.1.42
		hwWlanServiceEssServiceModeSwitch OBJECT-TYPE
			SYNTAX INTEGER
				{
				disable(1),
				enable(2)
				}
			MAX-ACCESS read-write
			STATUS current
			DESCRIPTION
				"Description."
			::= { hwEssManagementEntry 42 }


		-- 1.3.6.1.4.1.2011.6.139.4.1.1.43
		hwWlanServiceEssAutoOffEssAdminSwitch OBJECT-TYPE
			SYNTAX INTEGER
				{
				disable(1),
				enable(2)
				}
			MAX-ACCESS read-write
			STATUS current
			DESCRIPTION
				"Description."
			::= { hwEssManagementEntry 43 }


		-- 1.3.6.1.4.1.2011.6.139.4.1.1.44
		hwWlanServiceEssAutoOffEssStartTime OBJECT-TYPE
			SYNTAX OCTET STRING (SIZE (1..11))
			MAX-ACCESS read-write
			STATUS current
			DESCRIPTION
				"Description."
			::= { hwEssManagementEntry 44 }


		-- 1.3.6.1.4.1.2011.6.139.4.1.1.45
		hwWlanServiceEssAutoOffEssEndTime OBJECT-TYPE
			SYNTAX OCTET STRING (SIZE (1..11))
			MAX-ACCESS read-write
			STATUS current
			DESCRIPTION
				"Description."
			::= { hwEssManagementEntry 45 }


		-- 1.3.6.1.4.1.2011.6.139.4.1.1.46
		hwWlanServiceEssNdSnooping OBJECT-TYPE
			SYNTAX INTEGER
				{
				enable(1),
				disable(2)
				}
			MAX-ACCESS read-write
			STATUS current
			DESCRIPTION
				"Description."
			DEFVAL { disable }
			::= { hwEssManagementEntry 46 }

		-- 1.3.6.1.4.1.2011.6.139.4.1.1.47
		hwWlanServiceEssSaclNameInboundIPv6 OBJECT-TYPE
			SYNTAX OCTET STRING (SIZE (1..65))
			MAX-ACCESS read-write
			STATUS current
			DESCRIPTION
				"Description."
			::= { hwEssManagementEntry 47 }


		-- 1.3.6.1.4.1.2011.6.139.4.1.1.48
		hwWlanServiceEssSaclNameOutboundIPv6 OBJECT-TYPE
			SYNTAX OCTET STRING (SIZE (1..65))
			MAX-ACCESS read-write
			STATUS current
			DESCRIPTION
				"Description."
			::= { hwEssManagementEntry 48 }


		-- 1.3.6.1.4.1.2011.6.139.4.1.1.49
		hwWlanServiceEssSaclNumInboundIPv6 OBJECT-TYPE
			SYNTAX Integer32
			MAX-ACCESS read-write
			STATUS current
			DESCRIPTION
				"Description."
			::= { hwEssManagementEntry 49 }


		-- 1.3.6.1.4.1.2011.6.139.4.1.1.50
		hwWlanServiceEssSaclNumOutboundIPv6 OBJECT-TYPE
			SYNTAX Integer32
			MAX-ACCESS read-write
			STATUS current
			DESCRIPTION
				"Description."
			::= { hwEssManagementEntry 50 }


		-- 1.3.6.1.4.1.2011.6.139.4.1.1.51
		hwWlanServiceEssSaclSwtichInboundIPv6 OBJECT-TYPE
			SYNTAX INTEGER
				{
				disable(1),
				enable(2)
				}
			MAX-ACCESS read-write
			STATUS current
			DESCRIPTION
				"Description."
			::= { hwEssManagementEntry 51 }


		-- 1.3.6.1.4.1.2011.6.139.4.1.1.52
		hwWlanServiceEssSaclSwtichOutboundIPv6 OBJECT-TYPE
			SYNTAX INTEGER
				{
				disable(1),
				enable(2)
				}
			MAX-ACCESS read-write
			STATUS current
			DESCRIPTION
				"Description."
			::= { hwEssManagementEntry 52 }


		-- 1.3.6.1.4.1.2011.6.139.4.1.1.53
		hwWlanServiceEssNdTrustPort OBJECT-TYPE
			SYNTAX INTEGER
				{
				disable(1),
				enable(2)
				}
			MAX-ACCESS read-write
			STATUS current
			DESCRIPTION
				"Description."
			DEFVAL { disable }
			::= { hwEssManagementEntry 53 }


		-- 1.3.6.1.4.1.2011.6.139.4.1.1.54
		hwWlanServiceEssMldSnoopingEable OBJECT-TYPE
			SYNTAX INTEGER
				{
				disable(1),
				enable(2)
				}
			MAX-ACCESS read-write
			STATUS current
			DESCRIPTION
				"Description."
			::= { hwEssManagementEntry 54 }

		-- 1.3.6.1.4.1.2011.6.139.4.1.1.55
		hwWlanServiceEssIPSGEnableRejectAssoc OBJECT-TYPE
			SYNTAX INTEGER
				{
				disable(1),
				enable(2)
				}
			MAX-ACCESS read-write
			STATUS current
			DESCRIPTION
				"Description."
			::= { hwEssManagementEntry 55 }
		-- 1.3.6.1.4.1.2011.6.139.4.1.1.56
		hwWlanServiceEssLearnClientIpEnable OBJECT-TYPE
			SYNTAX INTEGER
				{
				disable(1),
				enable(2)
				}
			MAX-ACCESS read-write
			STATUS current
			DESCRIPTION
				"Description."
			::= { hwEssManagementEntry 56 }
		-- 1.3.6.1.4.1.2011.6.139.4.1.1.57
		hwWlanServiceEssHomeAgent OBJECT-TYPE
			SYNTAX INTEGER
				{
				ap(1),
				ac(2)
				}
			MAX-ACCESS read-write
			STATUS current
			DESCRIPTION
				"Description."
			::= { hwEssManagementEntry 57 }

		-- 1.3.6.1.4.1.2011.6.139.4.1.1.58
		hwWlanServiceEssVlanMobilityGroup OBJECT-TYPE
			SYNTAX Integer32 (1..4094)
			MAX-ACCESS read-write
			STATUS current
			DESCRIPTION
				"Description."
			::= { hwEssManagementEntry 58 }
--       1.3.6.1.4.1.2011.6.139.4.2
-- 1.3.6.1.4.1.2011.6.139.4.2
-- 1.3.6.1.4.1.2011.6.139.4.2
-- 1.3.6.1.4.1.2011.6.139.4.2
-- 1.3.6.1.4.1.2011.6.139.4.2
-- 1.3.6.1.4.1.2011.6.139.4.2
		-- 1.3.6.1.4.1.2011.6.139.4.2
		hwVapManagementTable OBJECT-TYPE
			SYNTAX SEQUENCE OF HwVapManagementEntry
			MAX-ACCESS not-accessible
			STATUS current
			DESCRIPTION
				"Visual ap management table."
			::= { hwWlanServiceManagement 2 }

		-- 1.3.6.1.4.1.2011.6.139.4.2.1
		hwVapManagementEntry OBJECT-TYPE
			SYNTAX HwVapManagementEntry
			MAX-ACCESS not-accessible
			STATUS current
			DESCRIPTION
				"Visual ap management entry."
			INDEX { hwWlanServiceVapApIndex, hwWlanServiceVapRadioIndex, hwWlanServiceVapEssName }
			::= { hwVapManagementTable 1 }


		HwVapManagementEntry ::=
			SEQUENCE {
				hwWlanServiceVapApIndex
					Integer32,
				hwWlanServiceVapRadioIndex
					Integer32,
				hwWlanServiceVapEssName
					OCTET STRING,
				hwWlanServiceVapWlanIndex
					Integer32,
				hwWlanServiceVapRowStatus
					RowStatus,
				hwWlanServiceVapBssid
					MacAddress,
				hwWlanServiceVapSSID
					OCTET STRING,
				hwWlanServiceVapVlan
					Integer32,
				hwWlanServiceVapFrequency
					OCTET STRING
			 }

		-- 1.3.6.1.4.1.2011.6.139.4.2.1.1
		hwWlanServiceVapApIndex OBJECT-TYPE
			SYNTAX Integer32
			MAX-ACCESS not-accessible
			STATUS current
			DESCRIPTION
				"The ap index."
			::= { hwVapManagementEntry 1 }


		-- 1.3.6.1.4.1.2011.6.139.4.2.1.2
		hwWlanServiceVapRadioIndex OBJECT-TYPE
			SYNTAX Integer32
			MAX-ACCESS not-accessible
			STATUS current
			DESCRIPTION
				"The radio index."
			::= { hwVapManagementEntry 2 }

		-- 1.3.6.1.4.1.2011.6.139.4.2.1.3
		hwWlanServiceVapEssName OBJECT-TYPE
			SYNTAX OCTET STRING (SIZE (1..31))
			MAX-ACCESS not-accessible
			STATUS current
			DESCRIPTION
				"The ess name."
			::= { hwVapManagementEntry 3 }

		-- 1.3.6.1.4.1.2011.6.139.4.2.1.4
		hwWlanServiceVapWlanIndex OBJECT-TYPE
			SYNTAX Integer32
			MAX-ACCESS read-only
			STATUS current
			DESCRIPTION
				"The wlan index."
			::= { hwVapManagementEntry 4 }

		-- 1.3.6.1.4.1.2011.6.139.4.2.1.5
		hwWlanServiceVapRowStatus OBJECT-TYPE
			SYNTAX RowStatus
			MAX-ACCESS read-write
			STATUS current
			DESCRIPTION
				"The row status of visual ap management table."
			::= { hwVapManagementEntry 5 }

		-- 1.3.6.1.4.1.2011.6.139.4.2.1.6
		hwWlanServiceVapBssid OBJECT-TYPE
			SYNTAX MacAddress
			MAX-ACCESS read-only
			STATUS current
			DESCRIPTION
				"BSSID is the MAC address of VAP in the 802.11 net. "
			::= { hwVapManagementEntry 6 }

		-- 1.3.6.1.4.1.2011.6.139.4.2.1.7
		hwWlanServiceVapSSID OBJECT-TYPE
			SYNTAX OCTET STRING
			MAX-ACCESS read-only
			STATUS current
			DESCRIPTION
				"Description."
			::= { hwVapManagementEntry 7 }

		-- 1.3.6.1.4.1.2011.6.139.4.2.1.8
		hwWlanServiceVapVlan OBJECT-TYPE
			SYNTAX Integer32
			MAX-ACCESS read-only
			STATUS current
			DESCRIPTION
				"Description."
			::= { hwVapManagementEntry 8 }

                                       -- 1.3.6.1.4.1.2011.6.139.4.2.1.9
		hwWlanServiceVapFrequency OBJECT-TYPE
			SYNTAX OCTET STRING
			MAX-ACCESS read-only
			STATUS current
			DESCRIPTION
				"WLAN Vap Frquency"
			::= { hwVapManagementEntry 9 }

		-- 1.3.6.1.4.1.2011.6.139.4.3
		hwServiceBatchTable OBJECT-TYPE
			SYNTAX SEQUENCE OF HwServiceBatchEntry
			MAX-ACCESS not-accessible
			STATUS current
			DESCRIPTION
				"The service batch table."
			::= { hwWlanServiceManagement 3 }

		-- 1.3.6.1.4.1.2011.6.139.4.3.1
		hwServiceBatchEntry OBJECT-TYPE
			SYNTAX HwServiceBatchEntry
			MAX-ACCESS not-accessible
			STATUS current
			DESCRIPTION
				"The service batch entry."
			INDEX { hwWlanServiceBatchApType, hwWlanServiceBatchRadioIndex }
			::= { hwServiceBatchTable 1 }


		HwServiceBatchEntry ::=
			SEQUENCE {
				hwWlanServiceBatchApType
					OCTET STRING,
				hwWlanServiceBatchRadioIndex
					Integer32,
				hwWlanServiceBatchRadioProfileName
					OCTET STRING,
				hwWlanServiceBatchEssNameNumber
					Integer32,
				hwWlanServiceBatchEssNameList
					OCTET STRING,
				hwWlanServiceBatchRowStatus
					RowStatus
			 }

		-- 1.3.6.1.4.1.2011.6.139.4.3.1.1
		hwWlanServiceBatchApType OBJECT-TYPE
			SYNTAX OCTET STRING (SIZE (1..31))
			MAX-ACCESS not-accessible
			STATUS current
			DESCRIPTION
				"The ap type."
			::= { hwServiceBatchEntry 1 }

		-- 1.3.6.1.4.1.2011.6.139.4.3.1.2
		hwWlanServiceBatchRadioIndex OBJECT-TYPE
			SYNTAX Integer32
			MAX-ACCESS not-accessible
			STATUS current
			DESCRIPTION
				"The radio index."
			::= { hwServiceBatchEntry 2 }

		-- 1.3.6.1.4.1.2011.6.139.4.3.1.3
		hwWlanServiceBatchRadioProfileName OBJECT-TYPE
			SYNTAX OCTET STRING (SIZE (1..31))
			MAX-ACCESS read-create
			STATUS current
			DESCRIPTION
				"The radio profile name."
			::= { hwServiceBatchEntry 3 }

		-- 1.3.6.1.4.1.2011.6.139.4.3.1.4
		hwWlanServiceBatchEssNameNumber OBJECT-TYPE
			SYNTAX Integer32
			MAX-ACCESS read-create
			STATUS current
			DESCRIPTION
				"The ess name number."
			::= { hwServiceBatchEntry 4 }

		-- 1.3.6.1.4.1.2011.6.139.4.3.1.5
		hwWlanServiceBatchEssNameList OBJECT-TYPE
			SYNTAX OCTET STRING
			MAX-ACCESS read-create
			STATUS current
			DESCRIPTION
				"The ess name list, each ess name is divided by '?'."
			::= { hwServiceBatchEntry 5 }

		-- 1.3.6.1.4.1.2011.6.139.4.3.1.6
		hwWlanServiceBatchRowStatus OBJECT-TYPE
			SYNTAX RowStatus
			MAX-ACCESS read-write
			STATUS current
			DESCRIPTION
				"The row status."
			::= { hwServiceBatchEntry 6 }

		-- 1.3.6.1.4.1.2011.6.139.4.4
		hwCapwapConfigManagementTable OBJECT-TYPE
			SYNTAX SEQUENCE OF HwCapwapConfigManagementEntry
			MAX-ACCESS not-accessible
			STATUS current
			DESCRIPTION
				"The capwap configuration management table."
			::= { hwWlanServiceManagement 4 }

		-- 1.3.6.1.4.1.2011.6.139.4.4.1
		hwCapwapConfigManagementEntry OBJECT-TYPE
			SYNTAX HwCapwapConfigManagementEntry
			MAX-ACCESS not-accessible
			STATUS current
			DESCRIPTION
				"The capwap configuration management entry."
			INDEX { hwWlanServiceCapwapConfigApIndex }
			::= { hwCapwapConfigManagementTable 1 }


		HwCapwapConfigManagementEntry ::=
			SEQUENCE {
				hwWlanServiceCapwapConfigApIndex
					Integer32,
				hwWlanServiceCapwapConfigCommit
					Integer32
			 }

		-- 1.3.6.1.4.1.2011.6.139.4.4.1.1
		hwWlanServiceCapwapConfigApIndex OBJECT-TYPE
			SYNTAX Integer32
			MAX-ACCESS not-accessible
			STATUS current
			DESCRIPTION
				"The capwap configuration ap index."
			::= { hwCapwapConfigManagementEntry 1 }


		-- 1.3.6.1.4.1.2011.6.139.4.4.1.2
		hwWlanServiceCapwapConfigCommit OBJECT-TYPE
			SYNTAX Integer32
			MAX-ACCESS read-write
			STATUS current
			DESCRIPTION
				"The switch whether send the ap's configuration to ap device."
			::= { hwCapwapConfigManagementEntry 2 }

		-- 1.3.6.1.4.1.2011.6.139.4.5
		hwStationTable OBJECT-TYPE
			SYNTAX SEQUENCE OF HwStationEntry
			MAX-ACCESS not-accessible
			STATUS current
			DESCRIPTION
				"Station info table"
			::= { hwWlanServiceManagement 5 }

		-- 1.3.6.1.4.1.2011.6.139.4.5.1
		hwStationEntry OBJECT-TYPE
			SYNTAX HwStationEntry
			MAX-ACCESS not-accessible
			STATUS current
			DESCRIPTION
				"Specifies each station info entry."
			INDEX { hwWlanServiceStaMac }
			::= { hwStationTable 1 }


		HwStationEntry ::=
			SEQUENCE {
				hwWlanServiceStaMac
					MacAddress,
				hwWlanServiceStaApId
					Integer32,
				hwWlanServiceStaRadioId
					Integer32,
				hwWlanServiceStaEssName
					OCTET STRING,
				hwWlanServiceStaSsid
					OCTET STRING,
				hwWlanServiceStaOnlineTime
					Integer32,
				hwWlanServiceStaSnrUs
					Integer32,
				hwWlanServiceStaRxPowerUs
					Integer32,
				hwStaWirelessStatTxPkts
					Integer32,
				hwStaWirelessStatRxPkts
					Integer32,
				hwStaWirelessStatTxBytes
					Integer32,
				hwStaWirelessStatRxBytes
					Integer32,
				hwStaWirelessStatTxRate
					Integer32,
				hwStaWirelessStatRxRate
					Integer32,
				hwStaAccessChannel
					Integer32,
				hwStaIp
					IpAddress,
				hwStaRssi
					Integer32,
				hwStaNoise
					Integer32,
				hwStaVlan
					Unsigned32,
				hwStaRecvDropFrames
					Counter64,
				hwStaSendDropFrames
					Counter64,
				hwStaRecvErrorFrames
					Counter64,
				hwStaSendErrorFrames
					Counter64,
				hwStaReSendFrames
					Counter64,
				hwStaReSendBytes
					Counter64,
				hwStaUsername
					OCTET STRING,
				hwStaStatus
					Integer32,
				hwStaWirelessStatRxBytes64Bits
					Counter64,
				hwStaWirelessStatTxBytes64Bits
					Counter64,
				hwStaGateway
					IpAddress,
				hwStaAuthenMethod
					Integer32,
				hwStaEncryptMethod
					Integer32,
				hwStaBSSID
					MacAddress,
				hwStaQosMode
					INTEGER,
				hwStaHtMode
					INTEGER,
				hwStaMcsVal
					Integer32,
				hwStaShortGIStatus
					INTEGER,
				hwStaRoamStatus
					INTEGER,
				hwStaStatOperMode
					INTEGER,
				hwStaWirelessStatTxPkts64Bits
					Counter64,
				hwStaWirelessStatRxPkts64Bits
					Counter64,
				hwStaRfMode
					Integer32,
				hwStaIpV6
					OCTET STRING,
				hwStaAssociateTime
					Integer32,
				hwStaAccessTime
					Integer32,
				hwStaAccessOnlineTime
					Integer32,
				hwStaLinkRxRate
					Integer32,
				hwStaLinkTxRate
					Integer32,
				hwStaActualBandwidth
					Unsigned32,
				hwStaPackets
					Counter64,
				hwStaChannelUtilRate
					Unsigned32,
				hwStaChannelBusyRate
					Unsigned32,
				hwStaChannelFreeRate
					Unsigned32,
				hwStaChannelInterfRate
					Unsigned32
			 }

		-- 1.3.6.1.4.1.2011.6.139.4.5.1.1
		hwWlanServiceStaMac OBJECT-TYPE
			SYNTAX MacAddress
			MAX-ACCESS accessible-for-notify
			STATUS current
			DESCRIPTION
				"Station mac address."
			::= { hwStationEntry 1 }

		-- 1.3.6.1.4.1.2011.6.139.4.5.1.2
		hwWlanServiceStaApId OBJECT-TYPE
			SYNTAX Integer32
			MAX-ACCESS read-only
			STATUS current
			DESCRIPTION
				"Station association AP id."
			::= { hwStationEntry 2 }

		-- 1.3.6.1.4.1.2011.6.139.4.5.1.3
		hwWlanServiceStaRadioId OBJECT-TYPE
			SYNTAX Integer32
			MAX-ACCESS read-only
			STATUS current
			DESCRIPTION
				"Station association radio id."
			::= { hwStationEntry 3 }

		-- 1.3.6.1.4.1.2011.6.139.4.5.1.4
		hwWlanServiceStaEssName OBJECT-TYPE
			SYNTAX OCTET STRING
			MAX-ACCESS read-only
			STATUS current
			DESCRIPTION
				"Station association ESS name."
			::= { hwStationEntry 4 }

		-- 1.3.6.1.4.1.2011.6.139.4.5.1.5
		hwWlanServiceStaSsid OBJECT-TYPE
			SYNTAX OCTET STRING
			MAX-ACCESS read-only
			STATUS current
			DESCRIPTION
				"Station association SSID."
			::= { hwStationEntry 5 }

		-- 1.3.6.1.4.1.2011.6.139.4.5.1.6
		hwWlanServiceStaOnlineTime OBJECT-TYPE
			SYNTAX Integer32
			UNITS "seconds"
			MAX-ACCESS read-only
			STATUS current
			DESCRIPTION
				"Station online time."
			::= { hwStationEntry 6 }

		-- 1.3.6.1.4.1.2011.6.139.4.5.1.7
		hwWlanServiceStaSnrUs OBJECT-TYPE
			SYNTAX Integer32
			UNITS "0.01 dB"
			MAX-ACCESS read-only
			STATUS current
			DESCRIPTION
				"AP can't support it.
				The upstream SNR(ratio between the received signal power and received noise power).
				A special value of 0x7FFFFFFF (2147483647) indicates the SNR is out of range to be represented.
				A special value of 0x7FFFFFFE (2147483646) indicates the SNR measurement is currently unavailable."
			::= { hwStationEntry 7 }

		-- 1.3.6.1.4.1.2011.6.139.4.5.1.8
		hwWlanServiceStaRxPowerUs OBJECT-TYPE
			SYNTAX Integer32
			UNITS "0.01 dB"
			MAX-ACCESS read-only
			STATUS current
			DESCRIPTION
				"The upstream aggregate receive power.
				A special value of 0x7FFFFFFF (2147483647) indicates the receive power is out of range to be represented.
				A special value of 0x7FFFFFFE (2147483646) indicates the receive power measurement is currently unavailable."
			::= { hwStationEntry 8 }

		-- 1.3.6.1.4.1.2011.6.139.4.5.1.9
		hwStaWirelessStatTxPkts OBJECT-TYPE
			SYNTAX Integer32
			MAX-ACCESS read-only
			STATUS current
			DESCRIPTION
				"Count of sent wireless packets to the station since associated."
			::= { hwStationEntry 9 }

		-- 1.3.6.1.4.1.2011.6.139.4.5.1.10
		hwStaWirelessStatRxPkts OBJECT-TYPE
			SYNTAX Integer32
			MAX-ACCESS read-only
			STATUS current
			DESCRIPTION
				"Count of received wireless packets from the station since associated."
			::= { hwStationEntry 10 }

		-- 1.3.6.1.4.1.2011.6.139.4.5.1.11
		hwStaWirelessStatTxBytes OBJECT-TYPE
			SYNTAX Integer32
			MAX-ACCESS read-only
			STATUS current
			DESCRIPTION
				"Count of sent bytes to the station since associated."
			::= { hwStationEntry 11 }

		-- 1.3.6.1.4.1.2011.6.139.4.5.1.12
		hwStaWirelessStatRxBytes OBJECT-TYPE
			SYNTAX Integer32
			MAX-ACCESS read-only
			STATUS current
			DESCRIPTION
				"Count of received bytes from the station since associated."
			::= { hwStationEntry 12 }

		-- 1.3.6.1.4.1.2011.6.139.4.5.1.13
		hwStaWirelessStatTxRate OBJECT-TYPE
			SYNTAX Integer32
			UNITS "bits/second"
			MAX-ACCESS read-only
			STATUS current
			DESCRIPTION
				"Wireless data rate sent to the station."
			::= { hwStationEntry 13 }

		-- 1.3.6.1.4.1.2011.6.139.4.5.1.14
		hwStaWirelessStatRxRate OBJECT-TYPE
			SYNTAX Integer32
			UNITS "bits/second"
			MAX-ACCESS read-only
			STATUS current
			DESCRIPTION
				"Wireless data rate received from the station."
			::= { hwStationEntry 14 }

		-- 1.3.6.1.4.1.2011.6.139.4.5.1.15
		hwStaAccessChannel OBJECT-TYPE
			SYNTAX Integer32
			MAX-ACCESS read-only
			STATUS current
			DESCRIPTION
				"Description."
			::= { hwStationEntry 15 }

		-- 1.3.6.1.4.1.2011.6.139.4.5.1.16
		hwStaIp OBJECT-TYPE
			SYNTAX IpAddress
			MAX-ACCESS read-only
			STATUS current
			DESCRIPTION
				"Description."
			::= { hwStationEntry 16 }

		-- 1.3.6.1.4.1.2011.6.139.4.5.1.17
		hwStaRssi OBJECT-TYPE
			SYNTAX Integer32
			UNITS "dB"
			MAX-ACCESS read-only
			STATUS current
			DESCRIPTION
				"Description."
			::= { hwStationEntry 17 }

		-- 1.3.6.1.4.1.2011.6.139.4.5.1.18
		hwStaNoise OBJECT-TYPE
			SYNTAX Integer32
			MAX-ACCESS read-only
			STATUS current
			DESCRIPTION
				"Description."
			::= { hwStationEntry 18 }

		-- 1.3.6.1.4.1.2011.6.139.4.5.1.19
		hwStaVlan OBJECT-TYPE
			SYNTAX Unsigned32
			MAX-ACCESS read-only
			STATUS current
			DESCRIPTION
				"Description."
			::= { hwStationEntry 19 }

		-- 1.3.6.1.4.1.2011.6.139.4.5.1.20
		hwStaRecvDropFrames OBJECT-TYPE
			SYNTAX Counter64
			MAX-ACCESS read-only
			STATUS current
			DESCRIPTION
				"Description."
			::= { hwStationEntry 20 }

		-- 1.3.6.1.4.1.2011.6.139.4.5.1.21
		hwStaSendDropFrames OBJECT-TYPE
			SYNTAX Counter64
			MAX-ACCESS read-only
			STATUS current
			DESCRIPTION
				"Description."
			::= { hwStationEntry 21 }

		-- 1.3.6.1.4.1.2011.6.139.4.5.1.22
		hwStaRecvErrorFrames OBJECT-TYPE
			SYNTAX Counter64
			MAX-ACCESS read-only
			STATUS current
			DESCRIPTION
				"Description."
			::= { hwStationEntry 22 }

		-- 1.3.6.1.4.1.2011.6.139.4.5.1.23
		hwStaSendErrorFrames OBJECT-TYPE
			SYNTAX Counter64
			MAX-ACCESS read-only
			STATUS current
			DESCRIPTION
				"Description."
			::= { hwStationEntry 23 }

		-- 1.3.6.1.4.1.2011.6.139.4.5.1.24
		hwStaReSendFrames OBJECT-TYPE
			SYNTAX Counter64
			MAX-ACCESS read-only
			STATUS current
			DESCRIPTION
				"Description."
			::= { hwStationEntry 24 }

		-- 1.3.6.1.4.1.2011.6.139.4.5.1.25
		hwStaReSendBytes OBJECT-TYPE
			SYNTAX Counter64
			MAX-ACCESS read-only
			STATUS current
			DESCRIPTION
				"Description."
			::= { hwStationEntry 25 }

		-- 1.3.6.1.4.1.2011.6.139.4.5.1.26
		hwStaUsername OBJECT-TYPE
			SYNTAX OCTET STRING
			MAX-ACCESS read-only
			STATUS current
			DESCRIPTION
				"Description."
			::= { hwStationEntry 26 }

		-- 1.3.6.1.4.1.2011.6.139.4.5.1.27
		hwStaStatus OBJECT-TYPE
			SYNTAX Integer32
			MAX-ACCESS read-only
			STATUS current
			DESCRIPTION
				"Description."
			::= { hwStationEntry 27 }

		-- 1.3.6.1.4.1.2011.6.139.4.5.1.28
		hwStaWirelessStatRxBytes64Bits OBJECT-TYPE
			SYNTAX Counter64
			MAX-ACCESS read-only
			STATUS current
			DESCRIPTION
				"Description."
			::= { hwStationEntry 28 }

		-- 1.3.6.1.4.1.2011.6.139.4.5.1.29
		hwStaWirelessStatTxBytes64Bits OBJECT-TYPE
			SYNTAX Counter64
			MAX-ACCESS read-only
			STATUS current
			DESCRIPTION
				"Description."
			::= { hwStationEntry 29 }

		-- 1.3.6.1.4.1.2011.6.139.4.5.1.30
		hwStaGateway OBJECT-TYPE
			SYNTAX IpAddress
			MAX-ACCESS read-only
			STATUS current
			DESCRIPTION
				"Description."
			::= { hwStationEntry 30 }

		-- 1.3.6.1.4.1.2011.6.139.4.5.1.31
		hwStaAuthenMethod OBJECT-TYPE
			SYNTAX Integer32
			MAX-ACCESS read-only
			STATUS current
			DESCRIPTION
				"Description."
			::= { hwStationEntry 31 }

		-- 1.3.6.1.4.1.2011.6.139.4.5.1.32
		hwStaEncryptMethod OBJECT-TYPE
			SYNTAX Integer32
			MAX-ACCESS read-only
			STATUS current
			DESCRIPTION
				"Description."
			::= { hwStationEntry 32 }

		-- 1.3.6.1.4.1.2011.6.139.4.5.1.33
		hwStaBSSID OBJECT-TYPE
			SYNTAX MacAddress
			MAX-ACCESS read-only
			STATUS current
			DESCRIPTION
				"Description."
			::= { hwStationEntry 33 }

		-- 1.3.6.1.4.1.2011.6.139.4.5.1.34
		hwStaQosMode OBJECT-TYPE
			SYNTAX INTEGER
				{
				wmm(1),
				null(2)
				}
			MAX-ACCESS read-only
			STATUS current
			DESCRIPTION
				"Description."
			::= { hwStationEntry 34 }

		-- 1.3.6.1.4.1.2011.6.139.4.5.1.35
		hwStaHtMode OBJECT-TYPE
			SYNTAX INTEGER
				{
				invalid(0),
				ht40(1),
				ht20(2),
				vht80(3)
				}
			MAX-ACCESS read-only
			STATUS current
			DESCRIPTION
				"Description."
			::= { hwStationEntry 35 }

		-- 1.3.6.1.4.1.2011.6.139.4.5.1.36
		hwStaMcsVal OBJECT-TYPE
			SYNTAX Integer32
			MAX-ACCESS read-only
			STATUS current
			DESCRIPTION
				"Description."
			::= { hwStationEntry 36 }

		-- 1.3.6.1.4.1.2011.6.139.4.5.1.37
		hwStaShortGIStatus OBJECT-TYPE
			SYNTAX INTEGER
				{
				nonsupport(1),
				support(2)
				}
			MAX-ACCESS read-only
			STATUS current
			DESCRIPTION
				"Description."
			::= { hwStationEntry 37 }

		-- 1.3.6.1.4.1.2011.6.139.4.5.1.38
		hwStaRoamStatus OBJECT-TYPE
			SYNTAX INTEGER
				{
				no(1),
				yes(2)
				}
			MAX-ACCESS read-only
			STATUS current
			DESCRIPTION
				"Description."
			::= { hwStationEntry 38 }

		-- 1.3.6.1.4.1.2011.6.139.4.5.1.39
		hwStaStatOperMode OBJECT-TYPE
			SYNTAX INTEGER
				{
				invalid(1),
				clearstatistic(2)
				}
			MAX-ACCESS read-write
			STATUS current
			DESCRIPTION
				"Description."
			::= { hwStationEntry 39 }


		-- 1.3.6.1.4.1.2011.6.139.4.5.1.40
		hwStaWirelessStatTxPkts64Bits OBJECT-TYPE
			SYNTAX Counter64
			MAX-ACCESS read-only
			STATUS current
			DESCRIPTION
				"Description."
			::= { hwStationEntry 40 }


		-- 1.3.6.1.4.1.2011.6.139.4.5.1.41
		hwStaWirelessStatRxPkts64Bits OBJECT-TYPE
			SYNTAX Counter64
			MAX-ACCESS read-only
			STATUS current
			DESCRIPTION
				"Description."
			::= { hwStationEntry 41 }


		-- 1.3.6.1.4.1.2011.6.139.4.5.1.42
		hwStaRfMode OBJECT-TYPE
			SYNTAX Integer32
			MAX-ACCESS read-only
			STATUS current
			DESCRIPTION
				"1(11b)
				 2(11g)
				 3(11n)
				 4(11a)
				 5(11ac)
				 0(unknown)."
			::= { hwStationEntry 42 }

		-- 1.3.6.1.4.1.2011.6.139.4.5.1.43
		hwStaIpV6 OBJECT-TYPE
			SYNTAX OCTET STRING
			MAX-ACCESS read-only
			STATUS current
			DESCRIPTION
				"Description."
			::= { hwStationEntry 43 }


		-- 1.3.6.1.4.1.2011.6.139.4.5.1.44
		hwStaAssociateTime OBJECT-TYPE
			SYNTAX Integer32
			UNITS "seconds"
			MAX-ACCESS read-only
			STATUS current
			DESCRIPTION
				"Description."
			::= { hwStationEntry 44 }
		-- 1.3.6.1.4.1.2011.6.139.4.5.1.45
		hwStaAccessTime OBJECT-TYPE
			SYNTAX Integer32
			UNITS "seconds"
			MAX-ACCESS read-only
			STATUS current
			DESCRIPTION
				"Description."
			::= { hwStationEntry 45 }
		-- 1.3.6.1.4.1.2011.6.139.4.5.1.46
		hwStaAccessOnlineTime OBJECT-TYPE
			SYNTAX Integer32
			UNITS "seconds"
			MAX-ACCESS read-only
			STATUS current
			DESCRIPTION
				"Description."
			::= { hwStationEntry 46 }
		-- 1.3.6.1.4.1.2011.6.139.4.5.1.47
		hwStaLinkRxRate OBJECT-TYPE
			SYNTAX Integer32
			UNITS "Mbps"
			MAX-ACCESS read-only
			STATUS current
			DESCRIPTION
				"It means actual business rate when the equipment has packets from station to AP.
				 It means actual negotiated connection rate when the equioment has no packets."
			::= { hwStationEntry 47 }
		-- 1.3.6.1.4.1.2011.6.139.4.5.1.48
		hwStaLinkTxRate OBJECT-TYPE
			SYNTAX Integer32
			UNITS "Mbps"
			MAX-ACCESS read-only
			STATUS current
			DESCRIPTION
				"It means actual business rate when the equipment has packets from AP to station.
				 It means actual negotiated connection rate when the equioment has no packets."
			::= { hwStationEntry 48 }

		-- 1.3.6.1.4.1.2011.6.139.4.5.1.49
		hwStaActualBandwidth OBJECT-TYPE
			SYNTAX Unsigned32
			MAX-ACCESS read-only
			STATUS current
			DESCRIPTION
				"It means actual bandwidth, include all of both the sent rate and the received rate."
			::= { hwStationEntry 49 }


		-- 1.3.6.1.4.1.2011.6.139.4.5.1.50
		hwStaPackets OBJECT-TYPE
			SYNTAX Counter64
			MAX-ACCESS read-only
			STATUS current
			DESCRIPTION
				"It means all of both the sent frames and the received frames."
			::= { hwStationEntry 50 }


		-- 1.3.6.1.4.1.2011.6.139.4.5.1.51
		hwStaChannelUtilRate OBJECT-TYPE
			SYNTAX Unsigned32
			MAX-ACCESS read-only
			STATUS current
			DESCRIPTION
				"It means the rate of channel utilization."
			::= { hwStationEntry 51 }


		-- 1.3.6.1.4.1.2011.6.139.4.5.1.52
		hwStaChannelBusyRate OBJECT-TYPE
			SYNTAX Unsigned32
			MAX-ACCESS read-only
			STATUS current
			DESCRIPTION
				"It means the rate of busy channel."
			::= { hwStationEntry 52 }


		-- 1.3.6.1.4.1.2011.6.139.4.5.1.53
		hwStaChannelFreeRate OBJECT-TYPE
			SYNTAX Unsigned32
			MAX-ACCESS read-only
			STATUS current
			DESCRIPTION
				"It means the rate of free channel."
			::= { hwStationEntry 53 }


		-- 1.3.6.1.4.1.2011.6.139.4.5.1.54
		hwStaChannelInterfRate OBJECT-TYPE
			SYNTAX Unsigned32
			MAX-ACCESS read-only
			STATUS current
			DESCRIPTION
				"It means the rate of channel interference."
			::= { hwStationEntry 54 }
		-- 1.3.6.1.4.1.2011.6.139.4.6
		hwVapStationListTable OBJECT-TYPE
			SYNTAX SEQUENCE OF HwVapStationListEntry
			MAX-ACCESS not-accessible
			STATUS current
			DESCRIPTION
				"Station list in VAP."
			::= { hwWlanServiceManagement 6 }

		-- 1.3.6.1.4.1.2011.6.139.4.6.1
		hwVapStationListEntry OBJECT-TYPE
			SYNTAX HwVapStationListEntry
			MAX-ACCESS not-accessible
			STATUS current
			DESCRIPTION
				"VAP station list entry."
			INDEX { hwWlanServiceVapStaApId, hwWlanServiceVapStaRadioId, hwWlanServiceVapStaEssName }
			::= { hwVapStationListTable 1 }


		HwVapStationListEntry ::=
			SEQUENCE {
				hwWlanServiceVapStaApId
					Integer32,
				hwWlanServiceVapStaRadioId
					Integer32,
				hwWlanServiceVapStaEssName
					OCTET STRING,
				hwWlanServiceVapStaNum
					Integer32,
				hwWlanServiceVapStaMacList
					OCTET STRING,
				hwWlanServiceVapAssociatedStationCount
					Integer32,
				hwWlanServiceVapCurOnlineStaCount
					Integer32,
				hwWlanServiceVapStaAssocAndReAssocReqCount
					Integer32,
				hwWlanServiceVapStaOnlineTime
					Integer32
			 }

		-- 1.3.6.1.4.1.2011.6.139.4.6.1.1
		hwWlanServiceVapStaApId OBJECT-TYPE
			SYNTAX Integer32
			MAX-ACCESS not-accessible
			STATUS current
			DESCRIPTION
				"Ap ID."
			::= { hwVapStationListEntry 1 }


		-- 1.3.6.1.4.1.2011.6.139.4.6.1.2
		hwWlanServiceVapStaRadioId OBJECT-TYPE
			SYNTAX Integer32
			MAX-ACCESS not-accessible
			STATUS current
			DESCRIPTION
				"Radio ID."
			::= { hwVapStationListEntry 2 }

		-- 1.3.6.1.4.1.2011.6.139.4.6.1.3
		hwWlanServiceVapStaEssName OBJECT-TYPE
			SYNTAX OCTET STRING
			MAX-ACCESS not-accessible
			STATUS current
			DESCRIPTION
				"ESS name."
			::= { hwVapStationListEntry 3 }

		-- 1.3.6.1.4.1.2011.6.139.4.6.1.4
		hwWlanServiceVapStaNum OBJECT-TYPE
			SYNTAX Integer32
			MAX-ACCESS read-only
			STATUS current
			DESCRIPTION
				"Station number in this VAP."
			::= { hwVapStationListEntry 4 }

		-- 1.3.6.1.4.1.2011.6.139.4.6.1.5
		hwWlanServiceVapStaMacList OBJECT-TYPE
			SYNTAX OCTET STRING
			MAX-ACCESS read-only
			STATUS current
			DESCRIPTION
				"Station MAC list in this VAP. String length is (hwWlanServiceVapStaNum * 6)."
			::= { hwVapStationListEntry 5 }

		-- 1.3.6.1.4.1.2011.6.139.4.6.1.6
		hwWlanServiceVapAssociatedStationCount OBJECT-TYPE
			SYNTAX Integer32
			MAX-ACCESS read-only
			STATUS current
			DESCRIPTION
				"Counts of STA associated or reassociated successful in vap."
			::= { hwVapStationListEntry 6 }

		-- 1.3.6.1.4.1.2011.6.139.4.6.1.7
		hwWlanServiceVapCurOnlineStaCount OBJECT-TYPE
			SYNTAX Integer32
			MAX-ACCESS read-only
			STATUS current
			DESCRIPTION
				"Current online STA count based on portal Authentication success."
			::= { hwVapStationListEntry 7 }

		-- 1.3.6.1.4.1.2011.6.139.4.6.1.8
		hwWlanServiceVapStaAssocAndReAssocReqCount OBJECT-TYPE
			SYNTAX Integer32
			MAX-ACCESS read-only
			STATUS current
			DESCRIPTION
				"Count of station association and reassociation request base on VAP with index of AP id."
			::= { hwVapStationListEntry 8 }

		-- 1.3.6.1.4.1.2011.6.139.4.6.1.9
		hwWlanServiceVapStaOnlineTime OBJECT-TYPE
			SYNTAX Integer32
			MAX-ACCESS read-only
			STATUS current
			DESCRIPTION
				"Sum of station online time based on vap."
			::= { hwVapStationListEntry 9 }

		-- 1.3.6.1.4.1.2011.6.139.4.7
		hwWlanServiceBatchEssInfo OBJECT IDENTIFIER ::= { hwWlanServiceManagement 7 }

		-- 1.3.6.1.4.1.2011.6.139.4.7.1
		hwWlanServiceBatchEssStartNumber OBJECT-TYPE
			SYNTAX Integer32
			MAX-ACCESS read-write
			STATUS current
			DESCRIPTION
				"The ess start number in batch operation. This node is used with node
				hwWlanServiceBatchEssNumber, for example, hwWlanServiceBatchEssStartNumber
				is set to one, and hwWlanServiceBatchEssNumber is set to three, then get
				the node hwWlanServiceBatchReturnEssNumber,hwWlanServiceBatchEssName,
				hwWlanServiceBatchEssSsid, that means start from the first ess, get three
				ess's name and ssid list. if it dose not exist three esses, the
				hwWlanServiceBatchReturnEssNumber will be the real ess number, otherwise,
				it is equal to hwWlanServiceBatchEssNumber."
			::= { hwWlanServiceBatchEssInfo 1 }

		-- 1.3.6.1.4.1.2011.6.139.4.7.2
		hwWlanServiceBatchEssNumber OBJECT-TYPE
			SYNTAX Integer32
			MAX-ACCESS read-write
			STATUS current
			DESCRIPTION
				"The ess number that want to get in batch operation.This node is used with node
				hwWlanServiceBatchEssStartNumber, for example, hwWlanServiceBatchEssStartNumber
				is set to one, and hwWlanServiceBatchEssNumber is set to three, then get
				the node hwWlanServiceBatchReturnEssNumber,hwWlanServiceBatchEssName, and
				hwWlanServiceBatchEssSsid, that means start from the first ess, get three
				ess's name and ssid list. if it dose not exist three esses, the
				hwWlanServiceBatchReturnEssNumber will be the real ess number, otherwise,
				it is equal to hwWlanServiceBatchEssNumber."
			::= { hwWlanServiceBatchEssInfo 2 }

		-- 1.3.6.1.4.1.2011.6.139.4.7.3
		hwWlanServiceBatchReturnEssNumber OBJECT-TYPE
			SYNTAX Integer32
			MAX-ACCESS read-only
			STATUS current
			DESCRIPTION
				"The ess number get in batch operation."
			::= { hwWlanServiceBatchEssInfo 3 }

		-- 1.3.6.1.4.1.2011.6.139.4.7.4
		hwWlanServiceBatchEssName OBJECT-TYPE
			SYNTAX OCTET STRING
			MAX-ACCESS read-only
			STATUS current
			DESCRIPTION
				"The names of esses which are determined by node hwWlanServiceBatchEssStartNumber
				and node hwWlanServiceBatchEssNumber.
				each ess name is divided by '?'."
			::= { hwWlanServiceBatchEssInfo 4 }

		-- 1.3.6.1.4.1.2011.6.139.4.7.5
		hwWlanServiceBatchEssSsid OBJECT-TYPE
			SYNTAX OCTET STRING
			MAX-ACCESS read-only
			STATUS current
			DESCRIPTION
				"Get the ssids of esses which are determined in node hwWlanServiceEssBatchIndex.
				each ssid is divided by '?'."
			::= { hwWlanServiceBatchEssInfo 5 }

		-- 1.3.6.1.4.1.2011.6.139.4.8
		hwCapwapConfigCommitAll OBJECT-TYPE
			SYNTAX Integer32
			MAX-ACCESS read-write
			STATUS current
			DESCRIPTION
				"The switch whether send the all ap's configuration to ap device."
			::= { hwWlanServiceManagement 8 }

		-- 1.3.6.1.4.1.2011.6.139.4.9
		hwApAssocStatTable OBJECT-TYPE
			SYNTAX SEQUENCE OF HwApAssocStatEntry
			MAX-ACCESS not-accessible
			STATUS current
			DESCRIPTION
				"The table hwApAssocStatTable contains station association, reassociation and disassociation statistics."
			::= { hwWlanServiceManagement 9 }

		-- 1.3.6.1.4.1.2011.6.139.4.9.1
		hwApAssocStatEntry OBJECT-TYPE
			SYNTAX HwApAssocStatEntry
			MAX-ACCESS not-accessible
			STATUS current
			DESCRIPTION
				"The table hwApAssocStatTable contains station association, reassociation and disassociation statistics."
			INDEX { hwApAssocStatApId }
			::= { hwApAssocStatTable 1 }


		HwApAssocStatEntry ::=
			SEQUENCE {
				hwApAssocStatApId
					Integer32,
				hwTotalOnlineTime
					Integer32,
				hwTotalAssociatedStationCount
					Integer32,
				hwCurrAssociatedStationCount
					Integer32,
				hwAssociationRequestCount
					Integer32,
				hwAssociationRejectCount
					Integer32,
				hwAssociationFailedCount
					Integer32,
				hwReAssociationRequestCount
					Integer32,
				hwReAssociationRejectCount
					Integer32,
				hwReAssociationFailedCount
					Integer32,
				hwDisAssocOfUserNotifiedCount
					Integer32,
				hwDisAssocOfStaRoamCount
					Integer32,
				hwDisAssocOfStaAgeCount
					Integer32,
				hwDisAssocOfApUnableHandleCount
					Integer32,
				hwDisAssocOfOtherReasonsCount
					Integer32,
				hwAssocRequestCntByResource
					Integer32,
				hwStaExceptionalOfflineCnt
					Integer32,
				hwReAssociationSuccessCount
					Integer32,
				hwBSSNotSupportAssocFailCount
					Unsigned32,
				hwStaAccessRequestCount
					Unsigned32,
				hwStaAccessRequestFailedCount
					Unsigned32,
				hwStaAuthenRequestCount
					Unsigned32,
				hwStaAuthenRequestFailedCount
					Unsigned32,
				hwRefusedStaNumByResource
					Unsigned32,
				hwStaAssocAndReAssocRequestCount
					Integer32,
				hwStaAuthenRequestSuccessCount
					Integer32,
				hwL3RoamInStationCount
					Unsigned32,
				hwL3RoamOutStationCount
					Unsigned32
			 }

		-- 1.3.6.1.4.1.2011.6.139.4.9.1.1
		hwApAssocStatApId OBJECT-TYPE
			SYNTAX Integer32
			MAX-ACCESS not-accessible
			STATUS current
			DESCRIPTION
				"Ap ID."
			::= { hwApAssocStatEntry 1 }

		-- 1.3.6.1.4.1.2011.6.139.4.9.1.2
		hwTotalOnlineTime OBJECT-TYPE
			SYNTAX Integer32
			UNITS "seconds"
			MAX-ACCESS read-only
			STATUS current
			DESCRIPTION
				"Stations total online time, the stations are that which have associated to this AP."
			::= { hwApAssocStatEntry 2 }

		-- 1.3.6.1.4.1.2011.6.139.4.9.1.3
		hwTotalAssociatedStationCount OBJECT-TYPE
			SYNTAX Integer32
			MAX-ACCESS read-only
			STATUS current
			DESCRIPTION
				"Count of success association and reassociation request base on AP id."
			::= { hwApAssocStatEntry 3 }

		-- 1.3.6.1.4.1.2011.6.139.4.9.1.4
		hwCurrAssociatedStationCount OBJECT-TYPE
			SYNTAX Integer32
			MAX-ACCESS read-only
			STATUS current
			DESCRIPTION
				"Count of stations that are associating to this AP."
			::= { hwApAssocStatEntry 4 }

		-- 1.3.6.1.4.1.2011.6.139.4.9.1.5
		hwAssociationRequestCount OBJECT-TYPE
			SYNTAX Integer32
			MAX-ACCESS read-only
			STATUS current
			DESCRIPTION
				"Count of association request."
			::= { hwApAssocStatEntry 5 }

		-- 1.3.6.1.4.1.2011.6.139.4.9.1.6
		hwAssociationRejectCount OBJECT-TYPE
			SYNTAX Integer32
			MAX-ACCESS read-only
			STATUS current
			DESCRIPTION
				"Count of reject association request."
			::= { hwApAssocStatEntry 6 }

		-- 1.3.6.1.4.1.2011.6.139.4.9.1.7
		hwAssociationFailedCount OBJECT-TYPE
			SYNTAX Integer32
			MAX-ACCESS read-only
			STATUS current
			DESCRIPTION
				"Count of failed association request."
			::= { hwApAssocStatEntry 7 }

		-- 1.3.6.1.4.1.2011.6.139.4.9.1.8
		hwReAssociationRequestCount OBJECT-TYPE
			SYNTAX Integer32
			MAX-ACCESS read-only
			STATUS current
			DESCRIPTION
				"Count of reassociation request."
			::= { hwApAssocStatEntry 8 }

		-- 1.3.6.1.4.1.2011.6.139.4.9.1.9
		hwReAssociationRejectCount OBJECT-TYPE
			SYNTAX Integer32
			MAX-ACCESS read-only
			STATUS current
			DESCRIPTION
				"Count of reject reassociation request."
			::= { hwApAssocStatEntry 9 }

		-- 1.3.6.1.4.1.2011.6.139.4.9.1.10
		hwReAssociationFailedCount OBJECT-TYPE
			SYNTAX Integer32
			MAX-ACCESS read-only
			STATUS current
			DESCRIPTION
				"Count of failed reassociation request."
			::= { hwApAssocStatEntry 10 }

		-- 1.3.6.1.4.1.2011.6.139.4.9.1.11
		hwDisAssocOfUserNotifiedCount OBJECT-TYPE
			SYNTAX Integer32
			MAX-ACCESS read-only
			STATUS current
			DESCRIPTION
				"Count of disassociations because of users notified."
			::= { hwApAssocStatEntry 11 }

		-- 1.3.6.1.4.1.2011.6.139.4.9.1.12
		hwDisAssocOfStaRoamCount OBJECT-TYPE
			SYNTAX Integer32
			MAX-ACCESS read-only
			STATUS current
			DESCRIPTION
				"Count of disassociations because of users roam."
			::= { hwApAssocStatEntry 12 }

		-- 1.3.6.1.4.1.2011.6.139.4.9.1.13
		hwDisAssocOfStaAgeCount OBJECT-TYPE
			SYNTAX Integer32
			MAX-ACCESS read-only
			STATUS current
			DESCRIPTION
				"Count of disassociations because of users left without notification."
			::= { hwApAssocStatEntry 13 }

		-- 1.3.6.1.4.1.2011.6.139.4.9.1.14
		hwDisAssocOfApUnableHandleCount OBJECT-TYPE
			SYNTAX Integer32
			MAX-ACCESS read-only
			STATUS current
			DESCRIPTION
				"Count of disassociations because of AP is unable to handle all currently associated stations."
			::= { hwApAssocStatEntry 14 }

		-- 1.3.6.1.4.1.2011.6.139.4.9.1.15
		hwDisAssocOfOtherReasonsCount OBJECT-TYPE
			SYNTAX Integer32
			MAX-ACCESS read-only
			STATUS current
			DESCRIPTION
				"Count of disassociations because of other reasons."
			::= { hwApAssocStatEntry 15 }

		-- 1.3.6.1.4.1.2011.6.139.4.9.1.16
		hwAssocRequestCntByResource OBJECT-TYPE
			SYNTAX Integer32
			MAX-ACCESS read-only
			STATUS current
			DESCRIPTION
				"Description."
			::= { hwApAssocStatEntry 16 }

		-- 1.3.6.1.4.1.2011.6.139.4.9.1.17
		hwStaExceptionalOfflineCnt OBJECT-TYPE
			SYNTAX Integer32
			MAX-ACCESS read-only
			STATUS current
			DESCRIPTION
				"Description."
			::= { hwApAssocStatEntry 17 }

		-- 1.3.6.1.4.1.2011.6.139.4.9.1.18
		hwReAssociationSuccessCount OBJECT-TYPE
			SYNTAX Integer32
			MAX-ACCESS read-only
			STATUS current
			DESCRIPTION
				"Description."
			::= { hwApAssocStatEntry 18 }

		-- 1.3.6.1.4.1.2011.6.139.4.9.1.19
		hwBSSNotSupportAssocFailCount OBJECT-TYPE
			SYNTAX Unsigned32
			MAX-ACCESS read-only
			STATUS current
			DESCRIPTION
				"Description."
			::= { hwApAssocStatEntry 19 }

		-- 1.3.6.1.4.1.2011.6.139.4.9.1.20
		hwStaAccessRequestCount OBJECT-TYPE
			SYNTAX Unsigned32
			MAX-ACCESS read-only
			STATUS current
			DESCRIPTION
				"Description."
			::= { hwApAssocStatEntry 20 }

		-- 1.3.6.1.4.1.2011.6.139.4.9.1.21
		hwStaAccessRequestFailedCount OBJECT-TYPE
			SYNTAX Unsigned32
			MAX-ACCESS read-only
			STATUS current
			DESCRIPTION
				"Description."
			::= { hwApAssocStatEntry 21 }

		-- 1.3.6.1.4.1.2011.6.139.4.9.1.22
		hwStaAuthenRequestCount OBJECT-TYPE
			SYNTAX Unsigned32
			MAX-ACCESS read-only
			STATUS current
			DESCRIPTION
				"Description."
			::= { hwApAssocStatEntry 22 }

		-- 1.3.6.1.4.1.2011.6.139.4.9.1.23
		hwStaAuthenRequestFailedCount OBJECT-TYPE
			SYNTAX Unsigned32
			MAX-ACCESS read-only
			STATUS current
			DESCRIPTION
				"Description."
			::= { hwApAssocStatEntry 23 }

		-- 1.3.6.1.4.1.2011.6.139.4.9.1.24
		hwRefusedStaNumByResource OBJECT-TYPE
			SYNTAX Unsigned32
			MAX-ACCESS read-only
			STATUS current
			DESCRIPTION
				"Description."
			::= { hwApAssocStatEntry 24 }

		-- 1.3.6.1.4.1.2011.6.139.4.9.1.25
		hwStaAssocAndReAssocRequestCount OBJECT-TYPE
			SYNTAX Integer32
			MAX-ACCESS read-only
			STATUS current
			DESCRIPTION
				"Count of station association and reassociation request base on AP id."
			::= { hwApAssocStatEntry 25 }

		-- 1.3.6.1.4.1.2011.6.139.4.9.1.26
		hwStaAuthenRequestSuccessCount OBJECT-TYPE
			SYNTAX Integer32
			MAX-ACCESS read-only
			STATUS current
			DESCRIPTION
				"Count of hwStaAuthenRequestSuccessCount base on Portal authentification successful."
			::= { hwApAssocStatEntry 26 }

		-- 1.3.6.1.4.1.2011.6.139.4.9.1.27
		hwL3RoamInStationCount OBJECT-TYPE
			SYNTAX Unsigned32
			MAX-ACCESS read-only
			STATUS current
			DESCRIPTION
				"It means count of station roamed to the AP for L3, not include roaming between different service sets for one AP."
			::= { hwApAssocStatEntry 27 }


		-- 1.3.6.1.4.1.2011.6.139.4.9.1.28
		hwL3RoamOutStationCount OBJECT-TYPE
			SYNTAX Unsigned32
			MAX-ACCESS read-only
			STATUS current
			DESCRIPTION
				"It means count of station roamed from the AP for L3, not include roaming between different service sets for one AP."
			::= { hwApAssocStatEntry 28 }
		-- 1.3.6.1.4.1.2011.6.139.4.10
		hwVlanMappingTable OBJECT-TYPE
			SYNTAX SEQUENCE OF HwVlanMappingEntry
			MAX-ACCESS not-accessible
			STATUS current
			DESCRIPTION
				"The table hwVlanMappingTable contains the VLAN mapping relations based ESS."
			::= { hwWlanServiceManagement 10 }

		-- 1.3.6.1.4.1.2011.6.139.4.10.1
		hwVlanMappingEntry OBJECT-TYPE
			SYNTAX HwVlanMappingEntry
			MAX-ACCESS not-accessible
			STATUS current
			DESCRIPTION
				"The table hwVlanMappingTable contains the VLAN mapping relations based ESS."
			INDEX { hwVlanMappingEssName }
			::= { hwVlanMappingTable 1 }

		HwVlanMappingEntry ::=
			SEQUENCE {
				hwVlanMappingEssName
					OCTET STRING,
				hwVlanMappingEssVlanMode
					INTEGER,
				hwVlanMappingEssVlanId
					Integer32,
				hwVlanMappingVlanList0
					OCTET STRING,
				hwVlanMappingVlanList1
					OCTET STRING,
				hwVlanMappingVlanList2
					OCTET STRING,
				hwVlanMappingVlanList3
					OCTET STRING,
				hwVlanMappingVlanList4
					OCTET STRING,
				hwVlanMappingVlanList5
					OCTET STRING,
				hwVlanMappingVlanList6
					OCTET STRING,
				hwVlanMappingVlanList7
					OCTET STRING
			 }

		-- 1.3.6.1.4.1.2011.6.139.4.10.1.1
		hwVlanMappingEssName OBJECT-TYPE
			SYNTAX OCTET STRING (SIZE (1..31))
			MAX-ACCESS not-accessible
			STATUS current
			DESCRIPTION
				"ESS name."
			::= { hwVlanMappingEntry 1 }

		-- 1.3.6.1.4.1.2011.6.139.4.10.1.2
		hwVlanMappingEssVlanMode OBJECT-TYPE
			SYNTAX INTEGER
				{
				essMode(1),
				regionMode(2),
				apMode(3)
				}
			MAX-ACCESS read-write
			STATUS current
			DESCRIPTION
				"VLAN mode."
			::= { hwVlanMappingEntry 2 }

		-- 1.3.6.1.4.1.2011.6.139.4.10.1.3
		hwVlanMappingEssVlanId OBJECT-TYPE
			SYNTAX Integer32 (0..4094 | 65535)
			MAX-ACCESS read-write
			STATUS current
			DESCRIPTION
				"VLAN ID of the ESS when VLAN mode is ess-mode."
			::= { hwVlanMappingEntry 3 }

		-- 1.3.6.1.4.1.2011.6.139.4.10.1.4
		hwVlanMappingVlanList0 OBJECT-TYPE
			SYNTAX OCTET STRING (SIZE (2..1024))
			MAX-ACCESS read-write
			STATUS current
			DESCRIPTION
				"VLAN ID list of the ap or region when VLAN mode is region-mode or ap-mode,
				its' max length is 512*2bytes,per two bytes represent the corresponding
				VLAN ID."
			::= { hwVlanMappingEntry 4 }

		-- 1.3.6.1.4.1.2011.6.139.4.10.1.5
		hwVlanMappingVlanList1 OBJECT-TYPE
			SYNTAX OCTET STRING (SIZE (2..1024))
			MAX-ACCESS read-write
			STATUS current
			DESCRIPTION
				"VLAN ID list of the ap or region when VLAN mode is ap-mode or region-mode,
				its' max length is 512*2bytes,per two bytes represent the corresponding
				VLAN ID."
			::= { hwVlanMappingEntry 5 }

		-- 1.3.6.1.4.1.2011.6.139.4.10.1.6
		hwVlanMappingVlanList2 OBJECT-TYPE
			SYNTAX OCTET STRING (SIZE (2..1024))
			MAX-ACCESS read-write
			STATUS current
			DESCRIPTION
				"VLAN ID list of the ap or region when VLAN mode is ap-mode or region-mode,
				its' max length is 512*2bytes,per two bytes represent the corresponding
				VLAN ID."
			::= { hwVlanMappingEntry 6 }

		-- 1.3.6.1.4.1.2011.6.139.4.10.1.7
		hwVlanMappingVlanList3 OBJECT-TYPE
			SYNTAX OCTET STRING (SIZE (2..1024))
			MAX-ACCESS read-write
			STATUS current
			DESCRIPTION
				"VLAN ID list of the ap or region when VLAN mode is ap-mode or region-mode,
				its' max length is 512*2bytes,per two bytes represent the corresponding
				VLAN ID."
			::= { hwVlanMappingEntry 7 }

		-- 1.3.6.1.4.1.2011.6.139.4.10.1.8
		hwVlanMappingVlanList4 OBJECT-TYPE
			SYNTAX OCTET STRING (SIZE (2..1024))
			MAX-ACCESS read-write
			STATUS current
			DESCRIPTION
				"VLAN ID list of the ap or region when VLAN mode is ap-mode or region-mode,
				its' max length is 512*2bytes,per two bytes represent the corresponding
				VLAN ID."
			::= { hwVlanMappingEntry 8 }

		-- 1.3.6.1.4.1.2011.6.139.4.10.1.9
		hwVlanMappingVlanList5 OBJECT-TYPE
			SYNTAX OCTET STRING (SIZE (2..1024))
			MAX-ACCESS read-write
			STATUS current
			DESCRIPTION
				"VLAN ID list of the ap or region when VLAN mode is ap-mode or region-mode,
				its' max length is 512*2bytes,per two bytes represent the corresponding
				VLAN ID."
			::= { hwVlanMappingEntry 9 }

		-- 1.3.6.1.4.1.2011.6.139.4.10.1.10
		hwVlanMappingVlanList6 OBJECT-TYPE
			SYNTAX OCTET STRING (SIZE (2..1024))
			MAX-ACCESS read-write
			STATUS current
			DESCRIPTION
				"VLAN ID list of the ap or region when VLAN mode is ap-mode or region-mode,
				its' max length is 512*2bytes,per two bytes represent the corresponding
				VLAN ID."
			::= { hwVlanMappingEntry 10 }

		-- 1.3.6.1.4.1.2011.6.139.4.10.1.11
		hwVlanMappingVlanList7 OBJECT-TYPE
			SYNTAX OCTET STRING (SIZE (2..1024))
			MAX-ACCESS read-write
			STATUS current
			DESCRIPTION
				"VLAN ID list of the ap or region when VLAN mode is ap-mode or region-mode,
				its' max length is 512*2bytes,per two bytes represent the corresponding
				VLAN ID."
			::= { hwVlanMappingEntry 11 }

		-- 1.3.6.1.4.1.2011.6.139.4.11
		hwGlobalStaMacWhiteListTable OBJECT-TYPE
			SYNTAX SEQUENCE OF HwGlobalStaMacWhiteListEntry
			MAX-ACCESS not-accessible
			STATUS current
			DESCRIPTION
				"Description."
			::= { hwWlanServiceManagement 11 }

		-- 1.3.6.1.4.1.2011.6.139.4.11.1
		hwGlobalStaMacWhiteListEntry OBJECT-TYPE
			SYNTAX HwGlobalStaMacWhiteListEntry
			MAX-ACCESS not-accessible
			STATUS current
			DESCRIPTION
				"Description."
			INDEX { hwStaMacWhiteListMacAddr }
			::= { hwGlobalStaMacWhiteListTable 1 }

		HwGlobalStaMacWhiteListEntry ::=
			SEQUENCE {
				hwStaMacWhiteListMacAddr
					MacAddress,
				hwGlobalStaMacWhiteListRowStatus
					RowStatus
			 }

		-- 1.3.6.1.4.1.2011.6.139.4.11.1.1
		hwStaMacWhiteListMacAddr OBJECT-TYPE
			SYNTAX MacAddress
			MAX-ACCESS not-accessible
			STATUS current
			DESCRIPTION
				"Description."
			::= { hwGlobalStaMacWhiteListEntry 1 }

		-- 1.3.6.1.4.1.2011.6.139.4.11.1.2
		hwGlobalStaMacWhiteListRowStatus OBJECT-TYPE
			SYNTAX RowStatus
			MAX-ACCESS read-create
			STATUS current
			DESCRIPTION
				"Description."
			::= { hwGlobalStaMacWhiteListEntry 2 }

		-- 1.3.6.1.4.1.2011.6.139.4.12
		hwStaMacBlackListTable OBJECT-TYPE
			SYNTAX SEQUENCE OF HwStaMacBlackListEntry
			MAX-ACCESS not-accessible
			STATUS current
			DESCRIPTION
				"The table hwStaMacBlackListTable contains the black list of station Mac addresses."
			::= { hwWlanServiceManagement 12 }

		-- 1.3.6.1.4.1.2011.6.139.4.12.1
		hwStaMacBlackListEntry OBJECT-TYPE
			SYNTAX HwStaMacBlackListEntry
			MAX-ACCESS not-accessible
			STATUS current
			DESCRIPTION
				"Station black list entry."
			INDEX { hwStaMacBlackListMacAddr }
			::= { hwStaMacBlackListTable 1 }

		HwStaMacBlackListEntry ::=
			SEQUENCE {
				hwStaMacBlackListMacAddr
					MacAddress,
				hwStaMacBlackListRowStatus
					RowStatus
			 }

		-- 1.3.6.1.4.1.2011.6.139.4.12.1.1
		hwStaMacBlackListMacAddr OBJECT-TYPE
			SYNTAX MacAddress
			MAX-ACCESS not-accessible
			STATUS current
			DESCRIPTION
				"Station MAC address that will be added to or deleted from the black list."
			::= { hwStaMacBlackListEntry 1 }

		-- 1.3.6.1.4.1.2011.6.139.4.12.1.2
		hwStaMacBlackListRowStatus OBJECT-TYPE
			SYNTAX RowStatus
			MAX-ACCESS read-write
			STATUS current
			DESCRIPTION
				"The row status of hwStaMacBlackListTable."
			::= { hwStaMacBlackListEntry 2 }

		-- 1.3.6.1.4.1.2011.6.139.4.13
		hwApStaAccessControlTable OBJECT-TYPE
			SYNTAX SEQUENCE OF HwApStaAccessControlEntry
			MAX-ACCESS not-accessible
			STATUS current
			DESCRIPTION
				"Description."
			::= { hwWlanServiceManagement 13 }

		-- 1.3.6.1.4.1.2011.6.139.4.13.1
		hwApStaAccessControlEntry OBJECT-TYPE
			SYNTAX HwApStaAccessControlEntry
			MAX-ACCESS not-accessible
			STATUS current
			DESCRIPTION
				"Description."
			INDEX { hwApStaAccessControlApId }
			::= { hwApStaAccessControlTable 1 }


		HwApStaAccessControlEntry ::=
			SEQUENCE {
				hwApStaAccessControlApId
					Integer32,
				hwApStaAccessControlMode
					Integer32,
				hwApStaAccessControlRowStatus
					Integer32
			 }

		-- 1.3.6.1.4.1.2011.6.139.4.13.1.1
		hwApStaAccessControlApId OBJECT-TYPE
			SYNTAX Integer32
			MAX-ACCESS not-accessible
			STATUS current
			DESCRIPTION
				"Description."
			::= { hwApStaAccessControlEntry 1 }

		-- 1.3.6.1.4.1.2011.6.139.4.13.1.2
		hwApStaAccessControlMode OBJECT-TYPE
			SYNTAX Integer32
			MAX-ACCESS read-write
			STATUS current
			DESCRIPTION
				"Description."
			::= { hwApStaAccessControlEntry 2 }

		-- 1.3.6.1.4.1.2011.6.139.4.13.1.3
		hwApStaAccessControlRowStatus OBJECT-TYPE
			SYNTAX Integer32
			MAX-ACCESS read-only
			STATUS current
			DESCRIPTION
				"Description."
			::= { hwApStaAccessControlEntry 3 }

		-- 1.3.6.1.4.1.2011.6.139.4.14
		hwAcStatistics OBJECT IDENTIFIER ::= { hwWlanServiceManagement 14 }


		-- 1.3.6.1.4.1.2011.6.139.4.14.1
		hwAcReassocSuccessTimes OBJECT-TYPE
			SYNTAX Integer32
			MAX-ACCESS read-only
			STATUS current
			DESCRIPTION
				"At present,the function doesn't support."
			::= { hwAcStatistics 1 }

		-- 1.3.6.1.4.1.2011.6.139.4.14.2
		hwApPerformanceStatTimerLen OBJECT-TYPE
			SYNTAX Integer32
			MAX-ACCESS read-write
			STATUS current
			DESCRIPTION
				"Description."
			::= { hwAcStatistics 2 }

		-- 1.3.6.1.4.1.2011.6.139.4.14.3
		hwRtCollectOnoff OBJECT-TYPE
			SYNTAX Integer32
			MAX-ACCESS read-write
			STATUS current
			DESCRIPTION
				"Description."
			::= { hwAcStatistics 3 }

		-- 1.3.6.1.4.1.2011.6.139.4.14.4
		hwApNormalCollectCycle OBJECT-TYPE
			SYNTAX Integer32
			MAX-ACCESS read-write
			STATUS current
			DESCRIPTION
				"Description."
			::= { hwAcStatistics 4 }

		-- 1.3.6.1.4.1.2011.6.139.4.14.5
		hwApRtCollectCycle OBJECT-TYPE
			SYNTAX Integer32
			MAX-ACCESS read-write
			STATUS current
			DESCRIPTION
				"Description."
			::= { hwAcStatistics 5 }

		-- 1.3.6.1.4.1.2011.6.139.4.14.6
		hwAcCurAssocStaNum OBJECT-TYPE
			SYNTAX Integer32
			MAX-ACCESS read-only
			STATUS current
			DESCRIPTION
				"hwAcCurAssocStaNum of STA associated or reassociated successful in AC."
			::= { hwAcStatistics 6 }

		-- 1.3.6.1.4.1.2011.6.139.4.14.7
		hwAcCurAuthSuccessStaNum OBJECT-TYPE
			SYNTAX Integer32
			MAX-ACCESS read-only
			STATUS current
			DESCRIPTION
				"Description."
			::= { hwAcStatistics 7 }

		-- 1.3.6.1.4.1.2011.6.139.4.14.8
		hwAcCurJointApNum OBJECT-TYPE
			SYNTAX Integer32
			MAX-ACCESS read-only
			STATUS current
			DESCRIPTION
				"Description."
			::= { hwAcStatistics 8 }


		-- 1.3.6.1.4.1.2011.6.139.4.14.9
		hwAcCurAssoc24gStaNum OBJECT-TYPE
			SYNTAX Integer32
			MAX-ACCESS read-write
			STATUS current
			DESCRIPTION
				"Description."
			::= { hwAcStatistics 9 }


		-- 1.3.6.1.4.1.2011.6.139.4.14.10
		hwAcCurAssoc5gStaNum OBJECT-TYPE
			SYNTAX Integer32
			MAX-ACCESS read-write
			STATUS current
			DESCRIPTION
				"Description."
			::= { hwAcStatistics 10 }


--  1.3.6.1.4.1.2011.6.139.4.15
		-- 1.3.6.1.4.1.2011.6.139.4.16
		hwMacVapManagementTable OBJECT-TYPE
			SYNTAX SEQUENCE OF HwMacVapManagementEntry
			MAX-ACCESS not-accessible
			STATUS current
			DESCRIPTION
				"Description."
			::= { hwWlanServiceManagement 15 }

		-- 1.3.6.1.4.1.2011.6.139.4.15.1
		hwMacVapManagementEntry OBJECT-TYPE
			SYNTAX HwMacVapManagementEntry
			MAX-ACCESS not-accessible
			STATUS current
			DESCRIPTION
				"Description."
			INDEX { hwMacWlanServiceVapApMac, hwMacWlanServiceVapRadioIndex, hwMacWlanServiceVapEssName }
			::= { hwMacVapManagementTable 1 }


		HwMacVapManagementEntry ::=
			SEQUENCE {
				hwMacWlanServiceVapApMac
					MacAddress,
				hwMacWlanServiceVapRadioIndex
					Integer32,
				hwMacWlanServiceVapEssName
					OCTET STRING,
				hwMacWlanServiceVapWlanIndex
					Integer32,
				hwMacWlanServiceVapBssid
					MacAddress,
				hwMacWlanServiceVapRowStatus
					RowStatus,
				hwMacWlanServiceVapSSID
					OCTET STRING,
				hwMacWlanServiceVapVlan
					Integer32
			 }

		-- 1.3.6.1.4.1.2011.6.139.4.15.1.1
		hwMacWlanServiceVapApMac OBJECT-TYPE
			SYNTAX MacAddress
			MAX-ACCESS not-accessible
			STATUS current
			DESCRIPTION
				"Description."
			::= { hwMacVapManagementEntry 1 }

		-- 1.3.6.1.4.1.2011.6.139.4.15.1.2
		hwMacWlanServiceVapRadioIndex OBJECT-TYPE
			SYNTAX Integer32
			MAX-ACCESS not-accessible
			STATUS current
			DESCRIPTION
				"Description."
			::= { hwMacVapManagementEntry 2 }

		-- 1.3.6.1.4.1.2011.6.139.4.15.1.3
		hwMacWlanServiceVapEssName OBJECT-TYPE
			SYNTAX OCTET STRING (SIZE (1..31))
			MAX-ACCESS not-accessible
			STATUS current
			DESCRIPTION
				"Description."
			::= { hwMacVapManagementEntry 3 }

		-- 1.3.6.1.4.1.2011.6.139.4.15.1.4
		hwMacWlanServiceVapWlanIndex OBJECT-TYPE
			SYNTAX Integer32
			MAX-ACCESS read-only
			STATUS current
			DESCRIPTION
				"Description."
			::= { hwMacVapManagementEntry 4 }

		-- 1.3.6.1.4.1.2011.6.139.4.15.1.5
		hwMacWlanServiceVapBssid OBJECT-TYPE
			SYNTAX MacAddress
			MAX-ACCESS read-only
			STATUS current
			DESCRIPTION
				"Description."
			::= { hwMacVapManagementEntry 5 }

		-- 1.3.6.1.4.1.2011.6.139.4.15.1.6
		hwMacWlanServiceVapRowStatus OBJECT-TYPE
			SYNTAX RowStatus
			MAX-ACCESS read-write
			STATUS current
			DESCRIPTION
				"Description."
			::= { hwMacVapManagementEntry 6 }

		-- 1.3.6.1.4.1.2011.6.139.4.15.1.7
		hwMacWlanServiceVapSSID OBJECT-TYPE
			SYNTAX OCTET STRING
			MAX-ACCESS read-only
			STATUS current
			DESCRIPTION
				"Description."
			::= { hwMacVapManagementEntry 7 }

		-- 1.3.6.1.4.1.2011.6.139.4.15.1.8
		hwMacWlanServiceVapVlan OBJECT-TYPE
			SYNTAX Integer32
			MAX-ACCESS read-only
			STATUS current
			DESCRIPTION
				"Description."
			::= { hwMacVapManagementEntry 8 }

		-- 1.3.6.1.4.1.2011.6.139.4.16
		hwMacCapwapConfigManagementTable OBJECT-TYPE
			SYNTAX SEQUENCE OF HwMacCapwapConfigManagementEntry
			MAX-ACCESS not-accessible
			STATUS current
			DESCRIPTION
				"Description."
			::= { hwWlanServiceManagement 16 }

		-- 1.3.6.1.4.1.2011.6.139.4.16.1
		hwMacCapwapConfigManagementEntry OBJECT-TYPE
			SYNTAX HwMacCapwapConfigManagementEntry
			MAX-ACCESS not-accessible
			STATUS current
			DESCRIPTION
				"Description."
			INDEX { hwMacWlanServiceCapwapConfigApMac }
			::= { hwMacCapwapConfigManagementTable 1 }

		HwMacCapwapConfigManagementEntry ::=
			SEQUENCE {
				hwMacWlanServiceCapwapConfigApMac
					MacAddress,
				hwMacWlanServiceCapwapConfigCommit
					Integer32
			 }

		-- 1.3.6.1.4.1.2011.6.139.4.16.1.1
		hwMacWlanServiceCapwapConfigApMac OBJECT-TYPE
			SYNTAX MacAddress
			MAX-ACCESS not-accessible
			STATUS current
			DESCRIPTION
				"Description."
			::= { hwMacCapwapConfigManagementEntry 1 }

		-- 1.3.6.1.4.1.2011.6.139.4.16.1.2
		hwMacWlanServiceCapwapConfigCommit OBJECT-TYPE
			SYNTAX Integer32
			MAX-ACCESS read-write
			STATUS current
			DESCRIPTION
				"Description."
			::= { hwMacCapwapConfigManagementEntry 2 }

		-- 1.3.6.1.4.1.2011.6.139.4.17
		hwMacVapStationListTable OBJECT-TYPE
			SYNTAX SEQUENCE OF HwMacVapStationListEntry
			MAX-ACCESS not-accessible
			STATUS current
			DESCRIPTION
				"Description."
			::= { hwWlanServiceManagement 17 }

		-- 1.3.6.1.4.1.2011.6.139.4.17.1
		hwMacVapStationListEntry OBJECT-TYPE
			SYNTAX HwMacVapStationListEntry
			MAX-ACCESS not-accessible
			STATUS current
			DESCRIPTION
				"Description."
			INDEX { hwMacWlanServiceVapStaApMac, hwMacWlanServiceVapStaRadioId, hwMacWlanServiceVapStaEssName }
			::= { hwMacVapStationListTable 1 }

		HwMacVapStationListEntry ::=
			SEQUENCE {
				hwMacWlanServiceVapStaApMac
					MacAddress,
				hwMacWlanServiceVapStaRadioId
					Integer32,
				hwMacWlanServiceVapStaEssName
					OCTET STRING,
				hwMacWlanServiceVapStaNum
					Integer32,
				hwMacWlanServiceVapStaMacList
					OCTET STRING,
				hwMacWlanServiceVapAssociatedStationCount
					Integer32,
				hwMacWlanServiceVapCurOnlineStaCount
					Integer32,
				hwMacWlanServiceVapStaAssocAndReAssocReqCount
					Integer32,
				hwMacWlanServiceVapStaOnlineTime
					Integer32
			 }


		-- 1.3.6.1.4.1.2011.6.139.4.17.1.1
		hwMacWlanServiceVapStaApMac OBJECT-TYPE
			SYNTAX MacAddress
			MAX-ACCESS not-accessible
			STATUS current
			DESCRIPTION
				"Description."
			::= { hwMacVapStationListEntry 1 }

		-- 1.3.6.1.4.1.2011.6.139.4.17.1.2
		hwMacWlanServiceVapStaRadioId OBJECT-TYPE
			SYNTAX Integer32
			MAX-ACCESS not-accessible
			STATUS current
			DESCRIPTION
				"Description."
			::= { hwMacVapStationListEntry 2 }

		-- 1.3.6.1.4.1.2011.6.139.4.17.1.3
		hwMacWlanServiceVapStaEssName OBJECT-TYPE
			SYNTAX OCTET STRING
			MAX-ACCESS not-accessible
			STATUS current
			DESCRIPTION
				"Description."
			::= { hwMacVapStationListEntry 3 }

		-- 1.3.6.1.4.1.2011.6.139.4.17.1.4
		hwMacWlanServiceVapStaNum OBJECT-TYPE
			SYNTAX Integer32
			MAX-ACCESS read-only
			STATUS current
			DESCRIPTION
				"Description."
			::= { hwMacVapStationListEntry 4 }

		-- 1.3.6.1.4.1.2011.6.139.4.17.1.5
		hwMacWlanServiceVapStaMacList OBJECT-TYPE
			SYNTAX OCTET STRING
			MAX-ACCESS read-only
			STATUS current
			DESCRIPTION
				"Description."
			::= { hwMacVapStationListEntry 5 }

		-- 1.3.6.1.4.1.2011.6.139.4.17.1.6
		hwMacWlanServiceVapAssociatedStationCount OBJECT-TYPE
			SYNTAX Integer32
			MAX-ACCESS read-only
			STATUS current
			DESCRIPTION
				"Counts of STA associated or reassociated successful in vap."
			::= { hwMacVapStationListEntry 6 }

		-- 1.3.6.1.4.1.2011.6.139.4.17.1.7
		hwMacWlanServiceVapCurOnlineStaCount OBJECT-TYPE
			SYNTAX Integer32
			MAX-ACCESS read-only
			STATUS current
			DESCRIPTION
				"Current online STA count based on portal Authentication success."
			::= { hwMacVapStationListEntry 7 }

		-- 1.3.6.1.4.1.2011.6.139.4.17.1.8
		hwMacWlanServiceVapStaAssocAndReAssocReqCount OBJECT-TYPE
			SYNTAX Integer32
			MAX-ACCESS read-only
			STATUS current
			DESCRIPTION
				"Count of station association and reassociation request base on VAP with index of AP MAC."
			::= { hwMacVapStationListEntry 8 }

		-- 1.3.6.1.4.1.2011.6.139.4.17.1.9
		hwMacWlanServiceVapStaOnlineTime OBJECT-TYPE
			SYNTAX Integer32
			MAX-ACCESS read-only
			STATUS current
			DESCRIPTION
				"Sum of station online time based on vap."
			::= { hwMacVapStationListEntry 9 }

		-- 1.3.6.1.4.1.2011.6.139.4.18
		hwMacApAssocStatTable OBJECT-TYPE
			SYNTAX SEQUENCE OF HwMacApAssocStatEntry
			MAX-ACCESS not-accessible
			STATUS current
			DESCRIPTION
				"Description."
			::= { hwWlanServiceManagement 18 }

		-- 1.3.6.1.4.1.2011.6.139.4.18.1
		hwMacApAssocStatEntry OBJECT-TYPE
			SYNTAX HwMacApAssocStatEntry
			MAX-ACCESS not-accessible
			STATUS current
			DESCRIPTION
				"Description."
			INDEX { hwMacApAssocStatApMac }
			::= { hwMacApAssocStatTable 1 }

		HwMacApAssocStatEntry ::=
			SEQUENCE {
				hwMacApAssocStatApMac
					MacAddress,
				hwMacTotalOnlineTime
					Unsigned32,
				hwMacTotalAssociatedStationCount
					Unsigned32,
				hwMacCurrAssociatedStationCount
					Unsigned32,
				hwMacAssociationRequestCount
					Unsigned32,
				hwMacAssociationRejectCount
					Unsigned32,
				hwMacAssociationFailedCount
					Unsigned32,
				hwMacReAssociationRequestCount
					Unsigned32,
				hwMacReAssociationRejectCount
					Unsigned32,
				hwMacReAssociationFailedCount
					Unsigned32,
				hwMacDisAssocOfUserNotifiedCount
					Unsigned32,
				hwMacDisAssocOfStaRoamCount
					Unsigned32,
				hwMacDisAssocOfStaAgeCount
					Unsigned32,
				hwMacDisAssocOfApUnableHandleCount
					Unsigned32,
				hwMacDisAssocOfOtherReasonsCount
					Unsigned32,
				hwMacAssocRequestCntByResource
					Unsigned32,
				hwMacStaExceptionalOfflineCnt
					Unsigned32,
				hwMacReAssociationSuccessCount
					Unsigned32,
				hwMacBSSNotSupportAssocFailCount
					Unsigned32,
				hwMacStaAccessRequestCount
					Unsigned32,
				hwMacStaAccessRequestFailedCount
					Unsigned32,
				hwMacStaAuthenRequestCount
					Unsigned32,
				hwMacStaAuthenRequestFailedCount
					Unsigned32,
				hwMacRefusedStaNumByResource
					Unsigned32,
				hwMacStaAssocAndReAssocRequestCount
					Integer32,
				hwMacStaAuthenRequestSuccessCount
					Integer32,
				hwMacL3RoamInStationCount
					Unsigned32,
				hwMacL3RoamOutStationCount
					Unsigned32
			 }

		-- 1.3.6.1.4.1.2011.6.139.4.18.1.1
		hwMacApAssocStatApMac OBJECT-TYPE
			SYNTAX MacAddress
			MAX-ACCESS not-accessible
			STATUS current
			DESCRIPTION
				"Description."
			::= { hwMacApAssocStatEntry 1 }

		-- 1.3.6.1.4.1.2011.6.139.4.18.1.2
		hwMacTotalOnlineTime OBJECT-TYPE
			SYNTAX Unsigned32
			MAX-ACCESS read-only
			STATUS current
			DESCRIPTION
				"Description."
			::= { hwMacApAssocStatEntry 2 }

		-- 1.3.6.1.4.1.2011.6.139.4.18.1.3
		hwMacTotalAssociatedStationCount OBJECT-TYPE
			SYNTAX Unsigned32
			MAX-ACCESS read-only
			STATUS current
			DESCRIPTION
				"Description."
			::= { hwMacApAssocStatEntry 3 }

		-- 1.3.6.1.4.1.2011.6.139.4.18.1.4
		hwMacCurrAssociatedStationCount OBJECT-TYPE
			SYNTAX Unsigned32
			MAX-ACCESS read-only
			STATUS current
			DESCRIPTION
				"Description."
			::= { hwMacApAssocStatEntry 4 }

		-- 1.3.6.1.4.1.2011.6.139.4.18.1.5
		hwMacAssociationRequestCount OBJECT-TYPE
			SYNTAX Unsigned32
			MAX-ACCESS read-only
			STATUS current
			DESCRIPTION
				"Description."
			::= { hwMacApAssocStatEntry 5 }

		-- 1.3.6.1.4.1.2011.6.139.4.18.1.6
		hwMacAssociationRejectCount OBJECT-TYPE
			SYNTAX Unsigned32
			MAX-ACCESS read-only
			STATUS current
			DESCRIPTION
				"Description."
			::= { hwMacApAssocStatEntry 6 }

		-- 1.3.6.1.4.1.2011.6.139.4.18.1.7
		hwMacAssociationFailedCount OBJECT-TYPE
			SYNTAX Unsigned32
			MAX-ACCESS read-only
			STATUS current
			DESCRIPTION
				"Description."
			::= { hwMacApAssocStatEntry 7 }

		-- 1.3.6.1.4.1.2011.6.139.4.18.1.8
		hwMacReAssociationRequestCount OBJECT-TYPE
			SYNTAX Unsigned32
			MAX-ACCESS read-only
			STATUS current
			DESCRIPTION
				"Description."
			::= { hwMacApAssocStatEntry 8 }

		-- 1.3.6.1.4.1.2011.6.139.4.18.1.9
		hwMacReAssociationRejectCount OBJECT-TYPE
			SYNTAX Unsigned32
			MAX-ACCESS read-only
			STATUS current
			DESCRIPTION
				"Description."
			::= { hwMacApAssocStatEntry 9 }

		-- 1.3.6.1.4.1.2011.6.139.4.18.1.10
		hwMacReAssociationFailedCount OBJECT-TYPE
			SYNTAX Unsigned32
			MAX-ACCESS read-only
			STATUS current
			DESCRIPTION
				"Description."
			::= { hwMacApAssocStatEntry 10 }

		-- 1.3.6.1.4.1.2011.6.139.4.18.1.11
		hwMacDisAssocOfUserNotifiedCount OBJECT-TYPE
			SYNTAX Unsigned32
			MAX-ACCESS read-only
			STATUS current
			DESCRIPTION
				"Description."
			::= { hwMacApAssocStatEntry 11 }

		-- 1.3.6.1.4.1.2011.6.139.4.18.1.12
		hwMacDisAssocOfStaRoamCount OBJECT-TYPE
			SYNTAX Unsigned32
			MAX-ACCESS read-only
			STATUS current
			DESCRIPTION
				"Description."
			::= { hwMacApAssocStatEntry 12 }

		-- 1.3.6.1.4.1.2011.6.139.4.18.1.13
		hwMacDisAssocOfStaAgeCount OBJECT-TYPE
			SYNTAX Unsigned32
			MAX-ACCESS read-only
			STATUS current
			DESCRIPTION
				"Description."
			::= { hwMacApAssocStatEntry 13 }

		-- 1.3.6.1.4.1.2011.6.139.4.18.1.14
		hwMacDisAssocOfApUnableHandleCount OBJECT-TYPE
			SYNTAX Unsigned32
			MAX-ACCESS read-only
			STATUS current
			DESCRIPTION
				"Description."
			::= { hwMacApAssocStatEntry 14 }

		-- 1.3.6.1.4.1.2011.6.139.4.18.1.15
		hwMacDisAssocOfOtherReasonsCount OBJECT-TYPE
			SYNTAX Unsigned32
			MAX-ACCESS read-only
			STATUS current
			DESCRIPTION
				"Description."
			::= { hwMacApAssocStatEntry 15 }

		-- 1.3.6.1.4.1.2011.6.139.4.18.1.16
		hwMacAssocRequestCntByResource OBJECT-TYPE
			SYNTAX Unsigned32
			MAX-ACCESS read-only
			STATUS current
			DESCRIPTION
				"Description."
			::= { hwMacApAssocStatEntry 16 }

		-- 1.3.6.1.4.1.2011.6.139.4.18.1.17
		hwMacStaExceptionalOfflineCnt OBJECT-TYPE
			SYNTAX Unsigned32
			MAX-ACCESS read-only
			STATUS current
			DESCRIPTION
				"Description."
			::= { hwMacApAssocStatEntry 17 }

		-- 1.3.6.1.4.1.2011.6.139.4.18.1.18
		hwMacReAssociationSuccessCount OBJECT-TYPE
			SYNTAX Unsigned32
			MAX-ACCESS read-only
			STATUS current
			DESCRIPTION
				"Description."
			::= { hwMacApAssocStatEntry 18 }

		-- 1.3.6.1.4.1.2011.6.139.4.18.1.19
		hwMacBSSNotSupportAssocFailCount OBJECT-TYPE
			SYNTAX Unsigned32
			MAX-ACCESS read-only
			STATUS current
			DESCRIPTION
				"Description."
			::= { hwMacApAssocStatEntry 19 }

		-- 1.3.6.1.4.1.2011.6.139.4.18.1.20
		hwMacStaAccessRequestCount OBJECT-TYPE
			SYNTAX Unsigned32
			MAX-ACCESS read-only
			STATUS current
			DESCRIPTION
				"Description."
			::= { hwMacApAssocStatEntry 20 }

		-- 1.3.6.1.4.1.2011.6.139.4.18.1.21
		hwMacStaAccessRequestFailedCount OBJECT-TYPE
			SYNTAX Unsigned32
			MAX-ACCESS read-only
			STATUS current
			DESCRIPTION
				"Description."
			::= { hwMacApAssocStatEntry 21 }

		-- 1.3.6.1.4.1.2011.6.139.4.18.1.22
		hwMacStaAuthenRequestCount OBJECT-TYPE
			SYNTAX Unsigned32
			MAX-ACCESS read-only
			STATUS current
			DESCRIPTION
				"Description."
			::= { hwMacApAssocStatEntry 22 }

		-- 1.3.6.1.4.1.2011.6.139.4.18.1.23
		hwMacStaAuthenRequestFailedCount OBJECT-TYPE
			SYNTAX Unsigned32
			MAX-ACCESS read-only
			STATUS current
			DESCRIPTION
				"Description."
			::= { hwMacApAssocStatEntry 23 }

		-- 1.3.6.1.4.1.2011.6.139.4.18.1.24
		hwMacRefusedStaNumByResource OBJECT-TYPE
			SYNTAX Unsigned32
			MAX-ACCESS read-only
			STATUS current
			DESCRIPTION
				"Description."
			::= { hwMacApAssocStatEntry 24 }

		-- 1.3.6.1.4.1.2011.6.139.4.18.1.25
		hwMacStaAssocAndReAssocRequestCount OBJECT-TYPE
			SYNTAX Integer32
			MAX-ACCESS read-only
			STATUS current
			DESCRIPTION
				"Count of station association and reassociation request base on AP MAC."
			::= { hwMacApAssocStatEntry 25 }

		-- 1.3.6.1.4.1.2011.6.139.4.18.1.26
		hwMacStaAuthenRequestSuccessCount OBJECT-TYPE
			SYNTAX Integer32
			MAX-ACCESS read-only
			STATUS current
			DESCRIPTION
				"Count of hwMacStaAuthenRequestSuccessCount base on Portal authentification successful."
			::= { hwMacApAssocStatEntry 26 }

		-- 1.3.6.1.4.1.2011.6.139.4.18.1.27
		hwMacL3RoamInStationCount OBJECT-TYPE
			SYNTAX Unsigned32
			MAX-ACCESS read-only
			STATUS current
			DESCRIPTION
				"It means count of station roamed to the AP for L3, not include roaming between different service sets for one AP."
			::= { hwMacApAssocStatEntry 27 }


		-- 1.3.6.1.4.1.2011.6.139.4.18.1.28
		hwMacL3RoamOutStationCount OBJECT-TYPE
			SYNTAX Unsigned32
			MAX-ACCESS read-only
			STATUS current
			DESCRIPTION
				"It means count of station roamed from the AP for L3, not include roaming between different service sets for one AP."
			::= { hwMacApAssocStatEntry 28 }
		-- 1.3.6.1.4.1.2011.6.139.4.19
		hwVapConfigTable OBJECT-TYPE
			SYNTAX SEQUENCE OF HwVapConfigEntry
			MAX-ACCESS not-accessible
			STATUS current
			DESCRIPTION
				"This Table is invalid!"
			::= { hwWlanServiceManagement 19 }

		-- 1.3.6.1.4.1.2011.6.139.4.19.1
		hwVapConfigEntry OBJECT-TYPE
			SYNTAX HwVapConfigEntry
			MAX-ACCESS not-accessible
			STATUS current
			DESCRIPTION
				"Description."
			INDEX { hwMacWlanServiceVapStaApMac, hwMacWlanServiceVapStaRadioId, hwMacWlanServiceVapStaEssName }
			::= { hwVapConfigTable 1 }

		HwVapConfigEntry ::=
			SEQUENCE {
				hwVapOptValue
					Integer32
			 }

		-- 1.3.6.1.4.1.2011.6.139.4.19.1.1
		hwVapOptValue OBJECT-TYPE
			SYNTAX Integer32 (0..1)
			MAX-ACCESS read-write
			STATUS current
			DESCRIPTION
				"The value only can be seted as 0 or 1,0 means switch disable and 1 means switch enable."
			::= { hwVapConfigEntry 1 }

		-- 1.3.6.1.4.1.2011.6.139.4.20
		hwSsidStatisticTable OBJECT-TYPE
			SYNTAX SEQUENCE OF HwSsidStatisticEntry
			MAX-ACCESS not-accessible
			STATUS current
			DESCRIPTION
				"Description."
			::= { hwWlanServiceManagement 20 }

		-- 1.3.6.1.4.1.2011.6.139.4.20.1
		hwSsidStatisticEntry OBJECT-TYPE
			SYNTAX HwSsidStatisticEntry
			MAX-ACCESS not-accessible
			STATUS current
			DESCRIPTION
				"Description."
			INDEX { hwSsidStatisticApIndex, hwSsidStatisticRadioIndex, hwSsidStatisticEssSsid }
			::= { hwSsidStatisticTable 1 }

		HwSsidStatisticEntry ::=
			SEQUENCE {
				hwSsidStatisticApIndex
					Integer32,
				hwSsidStatisticRadioIndex
					Integer32,
				hwSsidStatisticEssSsid
					OCTET STRING,
				hwSsidAirportRecvBytes
					Counter64,
				hwSsidAirportRecvErrorFrames
					Counter64,
				hwSsidAirportRecvFrames
					Counter64,
				hwSsidAirportRecvUnicastFrames
					Counter64,
				hwSsidAirportRecvDropFrames
					Counter64,
				hwSsidAirportTransmitBytes
					Counter64,
				hwSsidAirportTransmitErrorFrames
					Counter64,
				hwSsidAirportTransmitFrames
					Counter64,
				hwSsidAirportTransmitUnicastFrames
					Counter64,
				hwSsidAirportTransmitDropFrames
					Counter64,
				hwSsidAirportDownReTransmitFrames
					Counter64,
				hwSsidCurrentStaNum
					Unsigned32,
				hwSsidAirportNoise
					Integer32,
				hwSsidAirportSNR
					Integer32
			 }

		-- 1.3.6.1.4.1.2011.6.139.4.20.1.1
		hwSsidStatisticApIndex OBJECT-TYPE
			SYNTAX Integer32
			MAX-ACCESS not-accessible
			STATUS current
			DESCRIPTION
				"Description."
			::= { hwSsidStatisticEntry 1 }

		-- 1.3.6.1.4.1.2011.6.139.4.20.1.2
		hwSsidStatisticRadioIndex OBJECT-TYPE
			SYNTAX Integer32
			MAX-ACCESS not-accessible
			STATUS current
			DESCRIPTION
				"Description."
			::= { hwSsidStatisticEntry 2 }

		-- 1.3.6.1.4.1.2011.6.139.4.20.1.3
		hwSsidStatisticEssSsid OBJECT-TYPE
			SYNTAX OCTET STRING
			MAX-ACCESS not-accessible
			STATUS current
			DESCRIPTION
				"Description."
			::= { hwSsidStatisticEntry 3 }

		-- 1.3.6.1.4.1.2011.6.139.4.20.1.4
		hwSsidAirportRecvBytes OBJECT-TYPE
			SYNTAX Counter64
			MAX-ACCESS read-only
			STATUS current
			DESCRIPTION
				"Description."
			::= { hwSsidStatisticEntry 4 }

		-- 1.3.6.1.4.1.2011.6.139.4.20.1.5
		hwSsidAirportRecvErrorFrames OBJECT-TYPE
			SYNTAX Counter64
			MAX-ACCESS read-only
			STATUS current
			DESCRIPTION
				"Description."
			::= { hwSsidStatisticEntry 5 }

		-- 1.3.6.1.4.1.2011.6.139.4.20.1.6
		hwSsidAirportRecvFrames OBJECT-TYPE
			SYNTAX Counter64
			MAX-ACCESS read-only
			STATUS current
			DESCRIPTION
				"Description."
			::= { hwSsidStatisticEntry 6 }

		-- 1.3.6.1.4.1.2011.6.139.4.20.1.7
		hwSsidAirportRecvUnicastFrames OBJECT-TYPE
			SYNTAX Counter64
			MAX-ACCESS read-only
			STATUS current
			DESCRIPTION
				"Description."
			::= { hwSsidStatisticEntry 7 }

		-- 1.3.6.1.4.1.2011.6.139.4.20.1.8
		hwSsidAirportRecvDropFrames OBJECT-TYPE
			SYNTAX Counter64
			MAX-ACCESS read-only
			STATUS current
			DESCRIPTION
				"Description."
			::= { hwSsidStatisticEntry 8 }

		-- 1.3.6.1.4.1.2011.6.139.4.20.1.9
		hwSsidAirportTransmitBytes OBJECT-TYPE
			SYNTAX Counter64
			MAX-ACCESS read-only
			STATUS current
			DESCRIPTION
				"Description."
			::= { hwSsidStatisticEntry 9 }

		-- 1.3.6.1.4.1.2011.6.139.4.20.1.10
		hwSsidAirportTransmitErrorFrames OBJECT-TYPE
			SYNTAX Counter64
			MAX-ACCESS read-only
			STATUS current
			DESCRIPTION
				"Description."
			::= { hwSsidStatisticEntry 10 }

		-- 1.3.6.1.4.1.2011.6.139.4.20.1.11
		hwSsidAirportTransmitFrames OBJECT-TYPE
			SYNTAX Counter64
			MAX-ACCESS read-only
			STATUS current
			DESCRIPTION
				"Description."
			::= { hwSsidStatisticEntry 11 }

		-- 1.3.6.1.4.1.2011.6.139.4.20.1.12
		hwSsidAirportTransmitUnicastFrames OBJECT-TYPE
			SYNTAX Counter64
			MAX-ACCESS read-only
			STATUS current
			DESCRIPTION
				"Description."
			::= { hwSsidStatisticEntry 12 }

		-- 1.3.6.1.4.1.2011.6.139.4.20.1.13
		hwSsidAirportTransmitDropFrames OBJECT-TYPE
			SYNTAX Counter64
			MAX-ACCESS read-only
			STATUS current
			DESCRIPTION
				"Description."
			::= { hwSsidStatisticEntry 13 }

		-- 1.3.6.1.4.1.2011.6.139.4.20.1.14
		hwSsidAirportDownReTransmitFrames OBJECT-TYPE
			SYNTAX Counter64
			MAX-ACCESS read-only
			STATUS current
			DESCRIPTION
				"Description."
			::= { hwSsidStatisticEntry 14 }

		-- 1.3.6.1.4.1.2011.6.139.4.20.1.15
		hwSsidCurrentStaNum OBJECT-TYPE
			SYNTAX Unsigned32
			MAX-ACCESS read-only
			STATUS current
			DESCRIPTION
				"Description."
			::= { hwSsidStatisticEntry 15 }

		-- 1.3.6.1.4.1.2011.6.139.4.20.1.16
		hwSsidAirportNoise OBJECT-TYPE
			SYNTAX Integer32
			MAX-ACCESS read-only
			STATUS current
			DESCRIPTION
				"Description."
			::= { hwSsidStatisticEntry 16 }
		-- 1.3.6.1.4.1.2011.6.139.4.20.1.17
		hwSsidAirportSNR OBJECT-TYPE
			SYNTAX Integer32
			MAX-ACCESS read-only
			STATUS current
			DESCRIPTION
				"Description."
			::= { hwSsidStatisticEntry 17 }

		-- 1.3.6.1.4.1.2011.6.139.4.21
		hwMacSsidStatisticTable OBJECT-TYPE
			SYNTAX SEQUENCE OF HwMacSsidStatisticEntry
			MAX-ACCESS not-accessible
			STATUS current
			DESCRIPTION
				"Description."
			::= { hwWlanServiceManagement 21 }

		-- 1.3.6.1.4.1.2011.6.139.4.21.1
		hwMacSsidStatisticEntry OBJECT-TYPE
			SYNTAX HwMacSsidStatisticEntry
			MAX-ACCESS not-accessible
			STATUS current
			DESCRIPTION
				"Description."
			INDEX { hwMacSsidStatisticApMac, hwMacSsidStatisticRadioIndex, hwMacSsidStatisticEssSsid }
			::= { hwMacSsidStatisticTable 1 }

		HwMacSsidStatisticEntry ::=
			SEQUENCE {
				hwMacSsidStatisticApMac
					MacAddress,
				hwMacSsidStatisticRadioIndex
					Integer32,
				hwMacSsidStatisticEssSsid
					OCTET STRING,
				hwMacSsidAirportRecvBytes
					Counter64,
				hwMacSsidAirportRecvErrorFrames
					Counter64,
				hwMacSsidAirportRecvFrames
					Counter64,
				hwMacSsidAirportRecvUnicastFrames
					Counter64,
				hwMacSsidAirportRecvDropFrames
					Counter64,
				hwMacSsidAirportTransmitBytes
					Counter64,
				hwMacSsidAirportTransmitErrorFrames
					Counter64,
				hwMacSsidAirportTransmitFrames
					Counter64,
				hwMacSsidAirportTransmitUnicastFrames
					Counter64,
				hwMacSsidAirportTransmitDropFrames
					Counter64,
				hwMacSsidAirportDownReTransmitFrames
					Counter64,
				hwMacSsidCurrentStaNum
					Unsigned32,
				hwMacSsidAirportNoise
					Integer32,
				hwMacSsidAirportSNR
					Integer32
			 }

		-- 1.3.6.1.4.1.2011.6.139.4.21.1.1
		hwMacSsidStatisticApMac OBJECT-TYPE
			SYNTAX MacAddress
			MAX-ACCESS not-accessible
			STATUS current
			DESCRIPTION
				"Description."
			::= { hwMacSsidStatisticEntry 1 }

		-- 1.3.6.1.4.1.2011.6.139.4.21.1.2
		hwMacSsidStatisticRadioIndex OBJECT-TYPE
			SYNTAX Integer32
			MAX-ACCESS not-accessible
			STATUS current
			DESCRIPTION
				"Description."
			::= { hwMacSsidStatisticEntry 2 }

		-- 1.3.6.1.4.1.2011.6.139.4.21.1.3
		hwMacSsidStatisticEssSsid OBJECT-TYPE
			SYNTAX OCTET STRING
			MAX-ACCESS not-accessible
			STATUS current
			DESCRIPTION
				"Description."
			::= { hwMacSsidStatisticEntry 3 }

		-- 1.3.6.1.4.1.2011.6.139.4.21.1.4
		hwMacSsidAirportRecvBytes OBJECT-TYPE
			SYNTAX Counter64
			MAX-ACCESS read-only
			STATUS current
			DESCRIPTION
				"Description."
			::= { hwMacSsidStatisticEntry 4 }

		-- 1.3.6.1.4.1.2011.6.139.4.21.1.5
		hwMacSsidAirportRecvErrorFrames OBJECT-TYPE
			SYNTAX Counter64
			MAX-ACCESS read-only
			STATUS current
			DESCRIPTION
				"Description."
			::= { hwMacSsidStatisticEntry 5 }

		-- 1.3.6.1.4.1.2011.6.139.4.21.1.6
		hwMacSsidAirportRecvFrames OBJECT-TYPE
			SYNTAX Counter64
			MAX-ACCESS read-only
			STATUS current
			DESCRIPTION
				"Description."
			::= { hwMacSsidStatisticEntry 6 }

		-- 1.3.6.1.4.1.2011.6.139.4.21.1.7
		hwMacSsidAirportRecvUnicastFrames OBJECT-TYPE
			SYNTAX Counter64
			MAX-ACCESS read-only
			STATUS current
			DESCRIPTION
				"Description."
			::= { hwMacSsidStatisticEntry 7 }

		-- 1.3.6.1.4.1.2011.6.139.4.21.1.8
		hwMacSsidAirportRecvDropFrames OBJECT-TYPE
			SYNTAX Counter64
			MAX-ACCESS read-only
			STATUS current
			DESCRIPTION
				"Description."
			::= { hwMacSsidStatisticEntry 8 }

		-- 1.3.6.1.4.1.2011.6.139.4.21.1.9
		hwMacSsidAirportTransmitBytes OBJECT-TYPE
			SYNTAX Counter64
			MAX-ACCESS read-only
			STATUS current
			DESCRIPTION
				"Description."
			::= { hwMacSsidStatisticEntry 9 }

		-- 1.3.6.1.4.1.2011.6.139.4.21.1.10
		hwMacSsidAirportTransmitErrorFrames OBJECT-TYPE
			SYNTAX Counter64
			MAX-ACCESS read-only
			STATUS current
			DESCRIPTION
				"Description."
			::= { hwMacSsidStatisticEntry 10 }

		-- 1.3.6.1.4.1.2011.6.139.4.21.1.11
		hwMacSsidAirportTransmitFrames OBJECT-TYPE
			SYNTAX Counter64
			MAX-ACCESS read-only
			STATUS current
			DESCRIPTION
				"Description."
			::= { hwMacSsidStatisticEntry 11 }

		-- 1.3.6.1.4.1.2011.6.139.4.21.1.12
		hwMacSsidAirportTransmitUnicastFrames OBJECT-TYPE
			SYNTAX Counter64
			MAX-ACCESS read-only
			STATUS current
			DESCRIPTION
				"Description."
			::= { hwMacSsidStatisticEntry 12 }

		-- 1.3.6.1.4.1.2011.6.139.4.21.1.13
		hwMacSsidAirportTransmitDropFrames OBJECT-TYPE
			SYNTAX Counter64
			MAX-ACCESS read-only
			STATUS current
			DESCRIPTION
				"Description."
			::= { hwMacSsidStatisticEntry 13 }

		-- 1.3.6.1.4.1.2011.6.139.4.21.1.14
		hwMacSsidAirportDownReTransmitFrames OBJECT-TYPE
			SYNTAX Counter64
			MAX-ACCESS read-only
			STATUS current
			DESCRIPTION
				"Description."
			::= { hwMacSsidStatisticEntry 14 }

		-- 1.3.6.1.4.1.2011.6.139.4.21.1.15
		hwMacSsidCurrentStaNum OBJECT-TYPE
			SYNTAX Unsigned32
			MAX-ACCESS read-only
			STATUS current
			DESCRIPTION
				"Description."
			::= { hwMacSsidStatisticEntry 15 }
		-- 1.3.6.1.4.1.2011.6.139.4.21.1.16
		hwMacSsidAirportNoise OBJECT-TYPE
			SYNTAX Integer32
			MAX-ACCESS read-only
			STATUS current
			DESCRIPTION
				"Description."
			::= { hwMacSsidStatisticEntry 16 }
		-- 1.3.6.1.4.1.2011.6.139.4.21.1.17
		hwMacSsidAirportSNR OBJECT-TYPE
			SYNTAX Integer32
			MAX-ACCESS read-only
			STATUS current
			DESCRIPTION
				"Description."
			::= { hwMacSsidStatisticEntry 17 }

		-- 1.3.6.1.4.1.2011.6.139.4.22
		hwMacApStaAccessControlTable OBJECT-TYPE
			SYNTAX SEQUENCE OF HwMacApStaAccessControlEntry
			MAX-ACCESS not-accessible
			STATUS current
			DESCRIPTION
				"Description."
			::= { hwWlanServiceManagement 22 }

		-- 1.3.6.1.4.1.2011.6.139.4.22.1
		hwMacApStaAccessControlEntry OBJECT-TYPE
			SYNTAX HwMacApStaAccessControlEntry
			MAX-ACCESS not-accessible
			STATUS current
			DESCRIPTION
				"Description."
			INDEX { hwMacApStaAccessControlApMac }
			::= { hwMacApStaAccessControlTable 1 }

		HwMacApStaAccessControlEntry ::=
			SEQUENCE {
				hwMacApStaAccessControlApMac
					MacAddress,
				hwMacApStaAccessControlMode
					Integer32,
				hwMacApStaAccessControlRowStatus
					Integer32
			 }

		-- 1.3.6.1.4.1.2011.6.139.4.22.1.1
		hwMacApStaAccessControlApMac OBJECT-TYPE
			SYNTAX MacAddress
			MAX-ACCESS not-accessible
			STATUS current
			DESCRIPTION
				"Description."
			::= { hwMacApStaAccessControlEntry 1 }

		-- 1.3.6.1.4.1.2011.6.139.4.22.1.2
		hwMacApStaAccessControlMode OBJECT-TYPE
			SYNTAX Integer32
			MAX-ACCESS read-write
			STATUS current
			DESCRIPTION
				"Description."
			::= { hwMacApStaAccessControlEntry 2 }

		-- 1.3.6.1.4.1.2011.6.139.4.22.1.3
		hwMacApStaAccessControlRowStatus OBJECT-TYPE
			SYNTAX Integer32
			MAX-ACCESS read-create
			STATUS current
			DESCRIPTION
				"Description."
			::= { hwMacApStaAccessControlEntry 3 }

		-- 1.3.6.1.4.1.2011.6.139.4.23
		hwApStaInfoTable OBJECT-TYPE
			SYNTAX SEQUENCE OF HwApStaInfoEntry
			MAX-ACCESS not-accessible
			STATUS current
			DESCRIPTION
				"Description."
			::= { hwWlanServiceManagement 23 }

		-- 1.3.6.1.4.1.2011.6.139.4.23.1
		hwApStaInfoEntry OBJECT-TYPE
			SYNTAX HwApStaInfoEntry
			MAX-ACCESS not-accessible
			STATUS current
			DESCRIPTION
				"Description."
			INDEX { hwWlanServiceStaApId }
			::= { hwApStaInfoTable 1 }

		HwApStaInfoEntry ::=
			SEQUENCE {
				hwStaMAC
					OCTET STRING,
				hwStaIPAddress
					OCTET STRING,
				hwStaWMMAttr
					OCTET STRING,
				hwStaRadioMode
					OCTET STRING,
				hwStaRadioChannel
					OCTET STRING,
				hwAPTxRates
					OCTET STRING,
				hwStaPowerSaveMode
					OCTET STRING,
				hwStaVlanId
					OCTET STRING,
				hwStaSSIDName
					OCTET STRING,
				hwApStaTxPacket
					OCTET STRING,
				hwApStaRxPacket
					OCTET STRING,
				hwApStaStatus
					OCTET STRING,
				hwApStaBssid
					OCTET STRING,
				hwApStaRssi
					OCTET STRING,
				hwApStaSnr
					OCTET STRING
			 }

		-- 1.3.6.1.4.1.2011.6.139.4.23.1.1
		hwStaMAC OBJECT-TYPE
			SYNTAX OCTET STRING
			MAX-ACCESS read-only
			STATUS current
			DESCRIPTION
				"Description."
			::= { hwApStaInfoEntry 1 }

		-- 1.3.6.1.4.1.2011.6.139.4.23.1.2
		hwStaIPAddress OBJECT-TYPE
			SYNTAX OCTET STRING
			MAX-ACCESS read-only
			STATUS current
			DESCRIPTION
				"Description."
			::= { hwApStaInfoEntry 2 }

		-- 1.3.6.1.4.1.2011.6.139.4.23.1.3
		hwStaWMMAttr OBJECT-TYPE
			SYNTAX OCTET STRING
			MAX-ACCESS read-only
			STATUS current
			DESCRIPTION
				"Description."
			::= { hwApStaInfoEntry 3 }

		-- 1.3.6.1.4.1.2011.6.139.4.23.1.4
		hwStaRadioMode OBJECT-TYPE
			SYNTAX OCTET STRING
			MAX-ACCESS read-only
			STATUS current
			DESCRIPTION
				"Description."
			::= { hwApStaInfoEntry 4 }

		-- 1.3.6.1.4.1.2011.6.139.4.23.1.5
		hwStaRadioChannel OBJECT-TYPE
			SYNTAX OCTET STRING
			MAX-ACCESS read-only
			STATUS current
			DESCRIPTION
				"Description."
			::= { hwApStaInfoEntry 5 }

		-- 1.3.6.1.4.1.2011.6.139.4.23.1.6
		hwAPTxRates OBJECT-TYPE
			SYNTAX OCTET STRING
			MAX-ACCESS read-only
			STATUS current
			DESCRIPTION
				"Description."
			::= { hwApStaInfoEntry 6 }

		-- 1.3.6.1.4.1.2011.6.139.4.23.1.7
		hwStaPowerSaveMode OBJECT-TYPE
			SYNTAX OCTET STRING
			MAX-ACCESS read-only
			STATUS current
			DESCRIPTION
				"Description."
			::= { hwApStaInfoEntry 7 }

		-- 1.3.6.1.4.1.2011.6.139.4.23.1.8
		hwStaVlanId OBJECT-TYPE
			SYNTAX OCTET STRING
			MAX-ACCESS read-only
			STATUS current
			DESCRIPTION
				"Description."
			::= { hwApStaInfoEntry 8 }

		-- 1.3.6.1.4.1.2011.6.139.4.23.1.9
		hwStaSSIDName OBJECT-TYPE
			SYNTAX OCTET STRING
			MAX-ACCESS read-only
			STATUS current
			DESCRIPTION
				"Description."
			::= { hwApStaInfoEntry 9 }

		-- 1.3.6.1.4.1.2011.6.139.4.23.1.10
		hwApStaTxPacket OBJECT-TYPE
			SYNTAX OCTET STRING
			MAX-ACCESS read-only
			STATUS current
			DESCRIPTION
				"Description."
			::= { hwApStaInfoEntry 10 }
		-- 1.3.6.1.4.1.2011.6.139.4.23.1.11
		hwApStaRxPacket OBJECT-TYPE
			SYNTAX OCTET STRING
			MAX-ACCESS read-only
			STATUS current
			DESCRIPTION
				"Description."
			::= { hwApStaInfoEntry 11 }
		-- 1.3.6.1.4.1.2011.6.139.4.23.1.12
		hwApStaStatus OBJECT-TYPE
			SYNTAX OCTET STRING
			MAX-ACCESS read-only
			STATUS current
			DESCRIPTION
				"Description."
			::= { hwApStaInfoEntry 12 }

		-- 1.3.6.1.4.1.2011.6.139.4.23.1.13
		hwApStaBssid OBJECT-TYPE
			SYNTAX OCTET STRING
			MAX-ACCESS read-only
			STATUS current
			DESCRIPTION
				"Description."
			::= { hwApStaInfoEntry 13 }
		-- 1.3.6.1.4.1.2011.6.139.4.23.1.14
		hwApStaRssi OBJECT-TYPE
			SYNTAX OCTET STRING
			MAX-ACCESS read-only
			STATUS current
			DESCRIPTION
				"Description."
			::= { hwApStaInfoEntry 14 }
		-- 1.3.6.1.4.1.2011.6.139.4.23.1.15
		hwApStaSnr OBJECT-TYPE
			SYNTAX OCTET STRING
			MAX-ACCESS read-only
			STATUS current
			DESCRIPTION
				"Description."
			::= { hwApStaInfoEntry 15 }

--     1.3.6.1.4.1.2011.6.139.4.24
-- 1.3.6.1.4.1.2011.6.139.4.24
-- 1.3.6.1.4.1.2011.6.139.4.24
-- 1.3.6.1.4.1.2011.6.139.4.24
		-- 1.3.6.1.4.1.2011.6.139.4.24
		hwMacApStaInfoTable OBJECT-TYPE
			SYNTAX SEQUENCE OF HwMacApStaInfoEntry
			MAX-ACCESS not-accessible
			STATUS current
			DESCRIPTION
				"Description."
			::= { hwWlanServiceManagement 24 }

		-- 1.3.6.1.4.1.2011.6.139.4.24.1
		hwMacApStaInfoEntry OBJECT-TYPE
			SYNTAX HwMacApStaInfoEntry
			MAX-ACCESS not-accessible
			STATUS current
			DESCRIPTION
				"Description."
			INDEX { hwMacWlanServiceVapStaApMac }
			::= { hwMacApStaInfoTable 1 }

		HwMacApStaInfoEntry ::=
			SEQUENCE {
				hwMacStaMAC
					OCTET STRING,
				hwMacStaIPAddress
					OCTET STRING,
				hwMacStaWMMAttr
					OCTET STRING,
				hwMacStaRadioMode
					OCTET STRING,
				hwMacStaRadioChannel
					OCTET STRING,
				hwMacAPTxRates
					OCTET STRING,
				hwMacStaPowerSaveMode
					OCTET STRING,
				hwMacStaVlanId
					OCTET STRING,
				hwMacStaSSIDName
					OCTET STRING,
				hwMacApStaTxPacket
					OCTET STRING,
				hwMacApStaRxPacket
					OCTET STRING,
				hwMacApStaStatus
					OCTET STRING,
				hwMacApStaBssid
					OCTET STRING,
				hwMacApStaRssi
					OCTET STRING,
				hwMacApStaSnr
					OCTET STRING
			 }

		-- 1.3.6.1.4.1.2011.6.139.4.24.1.1
		hwMacStaMAC OBJECT-TYPE
			SYNTAX OCTET STRING
			MAX-ACCESS read-only
			STATUS current
			DESCRIPTION
				"Description."
			::= { hwMacApStaInfoEntry 1 }

		-- 1.3.6.1.4.1.2011.6.139.4.24.1.2
		hwMacStaIPAddress OBJECT-TYPE
			SYNTAX OCTET STRING
			MAX-ACCESS read-only
			STATUS current
			DESCRIPTION
				"Description."
			::= { hwMacApStaInfoEntry 2 }

		-- 1.3.6.1.4.1.2011.6.139.4.24.1.3
		hwMacStaWMMAttr OBJECT-TYPE
			SYNTAX OCTET STRING
			MAX-ACCESS read-only
			STATUS current
			DESCRIPTION
				"Description."
			::= { hwMacApStaInfoEntry 3 }

		-- 1.3.6.1.4.1.2011.6.139.4.24.1.4
		hwMacStaRadioMode OBJECT-TYPE
			SYNTAX OCTET STRING
			MAX-ACCESS read-only
			STATUS current
			DESCRIPTION
				"Description."
			::= { hwMacApStaInfoEntry 4 }

		-- 1.3.6.1.4.1.2011.6.139.4.24.1.5
		hwMacStaRadioChannel OBJECT-TYPE
			SYNTAX OCTET STRING
			MAX-ACCESS read-only
			STATUS current
			DESCRIPTION
				"Description."
			::= { hwMacApStaInfoEntry 5 }

		-- 1.3.6.1.4.1.2011.6.139.4.24.1.6
		hwMacAPTxRates OBJECT-TYPE
			SYNTAX OCTET STRING
			MAX-ACCESS read-only
			STATUS current
			DESCRIPTION
				"Description."
			::= { hwMacApStaInfoEntry 6 }

		-- 1.3.6.1.4.1.2011.6.139.4.24.1.7
		hwMacStaPowerSaveMode OBJECT-TYPE
			SYNTAX OCTET STRING
			MAX-ACCESS read-only
			STATUS current
			DESCRIPTION
				"Description."
			::= { hwMacApStaInfoEntry 7 }

		-- 1.3.6.1.4.1.2011.6.139.4.24.1.8
		hwMacStaVlanId OBJECT-TYPE
			SYNTAX OCTET STRING
			MAX-ACCESS read-only
			STATUS current
			DESCRIPTION
				"Description."
			::= { hwMacApStaInfoEntry 8 }

		-- 1.3.6.1.4.1.2011.6.139.4.24.1.9
		hwMacStaSSIDName OBJECT-TYPE
			SYNTAX OCTET STRING
			MAX-ACCESS read-only
			STATUS current
			DESCRIPTION
				"Description."
			::= { hwMacApStaInfoEntry 9 }

		-- 1.3.6.1.4.1.2011.6.139.4.24.1.10
		hwMacApStaTxPacket OBJECT-TYPE
			SYNTAX OCTET STRING
			MAX-ACCESS read-only
			STATUS current
			DESCRIPTION
				"Description."
			::= { hwMacApStaInfoEntry 10 }
		-- 1.3.6.1.4.1.2011.6.139.4.24.1.11
		hwMacApStaRxPacket OBJECT-TYPE
			SYNTAX OCTET STRING
			MAX-ACCESS read-only
			STATUS current
			DESCRIPTION
				"Description."
			::= { hwMacApStaInfoEntry 11 }
		-- 1.3.6.1.4.1.2011.6.139.4.24.1.12
		hwMacApStaStatus OBJECT-TYPE
			SYNTAX OCTET STRING
			MAX-ACCESS read-only
			STATUS current
			DESCRIPTION
				"Description."
			::= { hwMacApStaInfoEntry 12 }
		-- 1.3.6.1.4.1.2011.6.139.4.24.1.13
		hwMacApStaBssid OBJECT-TYPE
			SYNTAX OCTET STRING
			MAX-ACCESS read-only
			STATUS current
			DESCRIPTION
				"Description."
			::= { hwMacApStaInfoEntry 13 }
		-- 1.3.6.1.4.1.2011.6.139.4.24.1.14
		hwMacApStaRssi OBJECT-TYPE
			SYNTAX OCTET STRING
			MAX-ACCESS read-only
			STATUS current
			DESCRIPTION
				"Description."
			::= { hwMacApStaInfoEntry 14 }
		-- 1.3.6.1.4.1.2011.6.139.4.24.1.15
		hwMacApStaSnr OBJECT-TYPE
			SYNTAX OCTET STRING
			MAX-ACCESS read-only
			STATUS current
			DESCRIPTION
				"Description."
			::= { hwMacApStaInfoEntry 15 }

		-- 1.3.6.1.4.1.2011.6.139.4.25
		hwInterACRoamingInfo OBJECT IDENTIFIER ::= { hwWlanServiceManagement 25 }

		-- 1.3.6.1.4.1.2011.6.139.4.25.1
		hwInterACRoamingInSuccCnt OBJECT-TYPE
			SYNTAX Integer32
			MAX-ACCESS read-write
			STATUS current
			DESCRIPTION
				"Description."
			::= { hwInterACRoamingInfo 1 }

		-- 1.3.6.1.4.1.2011.6.139.4.25.2
		hwInterACRoamingOutSuccCnt OBJECT-TYPE
			SYNTAX Integer32
			MAX-ACCESS read-write
			STATUS current
			DESCRIPTION
				"Description."
			::= { hwInterACRoamingInfo 2 }

		-- 1.3.6.1.4.1.2011.6.139.4.26
		hwRadioStaListTable OBJECT-TYPE
			SYNTAX SEQUENCE OF HwRadioStaListEntry
			MAX-ACCESS not-accessible
			STATUS current
			DESCRIPTION
				"Description."
			::= { hwWlanServiceManagement 26 }

		-- 1.3.6.1.4.1.2011.6.139.4.26.1
		hwRadioStaListEntry OBJECT-TYPE
			SYNTAX HwRadioStaListEntry
			MAX-ACCESS not-accessible
			STATUS current
			DESCRIPTION
				"Description."
			INDEX { hwRadioStaApId, hwRadioStaRadioId }
			::= { hwRadioStaListTable 1 }

		HwRadioStaListEntry ::=
			SEQUENCE {
				hwRadioStaApId
					Unsigned32,
				hwRadioStaRadioId
					Unsigned32,
				hwRadioStaNumber
					Unsigned32,
				hwRadioStaMacList
					OCTET STRING,
				hwRadioStaTotalAssociatedCount
					Integer32,
				hwRadioStaAccessReqCount
					Integer32
			 }

		-- 1.3.6.1.4.1.2011.6.139.4.26.1.1
		hwRadioStaApId OBJECT-TYPE
			SYNTAX Unsigned32
			MAX-ACCESS not-accessible
			STATUS current
			DESCRIPTION
				"Description."
			::= { hwRadioStaListEntry 1 }

		-- 1.3.6.1.4.1.2011.6.139.4.26.1.2
		hwRadioStaRadioId OBJECT-TYPE
			SYNTAX Unsigned32
			MAX-ACCESS not-accessible
			STATUS current
			DESCRIPTION
				"Description."
			::= { hwRadioStaListEntry 2 }

		-- 1.3.6.1.4.1.2011.6.139.4.26.1.3
		hwRadioStaNumber OBJECT-TYPE
			SYNTAX Unsigned32
			MAX-ACCESS read-only
			STATUS current
			DESCRIPTION
				"Description."
			::= { hwRadioStaListEntry 3 }

		-- 1.3.6.1.4.1.2011.6.139.4.26.1.4
		hwRadioStaMacList OBJECT-TYPE
			SYNTAX OCTET STRING
			MAX-ACCESS read-only
			STATUS current
			DESCRIPTION
				"Description."
			::= { hwRadioStaListEntry 4 }

		-- 1.3.6.1.4.1.2011.6.139.4.26.1.5
		hwRadioStaTotalAssociatedCount OBJECT-TYPE
			SYNTAX Integer32
			MAX-ACCESS read-only
			STATUS current
			DESCRIPTION
				"Description."
			::= { hwRadioStaListEntry 5 }

		-- 1.3.6.1.4.1.2011.6.139.4.26.1.6
		hwRadioStaAccessReqCount OBJECT-TYPE
			SYNTAX Integer32
			MAX-ACCESS read-only
			STATUS current
			DESCRIPTION
				"Description."
			::= { hwRadioStaListEntry 6 }

		-- 1.3.6.1.4.1.2011.6.139.4.27
		hwMacRadioStaListTable OBJECT-TYPE
			SYNTAX SEQUENCE OF HwMacRadioStaListEntry
			MAX-ACCESS not-accessible
			STATUS current
			DESCRIPTION
				"Description."
			::= { hwWlanServiceManagement 27 }

		-- 1.3.6.1.4.1.2011.6.139.4.27.1
		hwMacRadioStaListEntry OBJECT-TYPE
			SYNTAX HwMacRadioStaListEntry
			MAX-ACCESS not-accessible
			STATUS current
			DESCRIPTION
				"Description."
			INDEX { hwMacRadioStaApMac, hwMacRadioStaRadioId }
			::= { hwMacRadioStaListTable 1 }

		HwMacRadioStaListEntry ::=
			SEQUENCE {
				hwMacRadioStaApMac
					MacAddress,
				hwMacRadioStaRadioId
					Unsigned32,
				hwMacRadioStaNumber
					Unsigned32,
				hwMacRadioStaMacList
					OCTET STRING,
				hwMacRadioStaTotalAssociatedCount
					Integer32,
				hwMacRadioStaAccessReqCount
					Integer32
			 }

		-- 1.3.6.1.4.1.2011.6.139.4.27.1.1
		hwMacRadioStaApMac OBJECT-TYPE
			SYNTAX MacAddress
			MAX-ACCESS not-accessible
			STATUS current
			DESCRIPTION
				"Description."
			::= { hwMacRadioStaListEntry 1 }

		-- 1.3.6.1.4.1.2011.6.139.4.27.1.2
		hwMacRadioStaRadioId OBJECT-TYPE
			SYNTAX Unsigned32
			MAX-ACCESS not-accessible
			STATUS current
			DESCRIPTION
				"Description."
			::= { hwMacRadioStaListEntry 2 }

		-- 1.3.6.1.4.1.2011.6.139.4.27.1.3
		hwMacRadioStaNumber OBJECT-TYPE
			SYNTAX Unsigned32
			MAX-ACCESS read-only
			STATUS current
			DESCRIPTION
				"Description."
			::= { hwMacRadioStaListEntry 3 }

		-- 1.3.6.1.4.1.2011.6.139.4.27.1.4
		hwMacRadioStaMacList OBJECT-TYPE
			SYNTAX OCTET STRING
			MAX-ACCESS read-only
			STATUS current
			DESCRIPTION
				"Description."
			::= { hwMacRadioStaListEntry 4 }

		-- 1.3.6.1.4.1.2011.6.139.4.27.1.5
		hwMacRadioStaTotalAssociatedCount OBJECT-TYPE
			SYNTAX Integer32
			MAX-ACCESS read-only
			STATUS current
			DESCRIPTION
				"Description."
			::= { hwMacRadioStaListEntry 5 }

		-- 1.3.6.1.4.1.2011.6.139.4.27.1.6
		hwMacRadioStaAccessReqCount OBJECT-TYPE
			SYNTAX Integer32
			MAX-ACCESS read-only
			STATUS current
			DESCRIPTION
				"Description."
			::= { hwMacRadioStaListEntry 6 }

		-- 1.3.6.1.4.1.2011.6.139.4.28
		hwBridgeProfileTable OBJECT-TYPE
			SYNTAX SEQUENCE OF HwBridgeProfileEntry
			MAX-ACCESS not-accessible
			STATUS current
			DESCRIPTION
				"Description."
			::= { hwWlanServiceManagement 28 }

		-- 1.3.6.1.4.1.2011.6.139.4.28.1
		hwBridgeProfileEntry OBJECT-TYPE
			SYNTAX HwBridgeProfileEntry
			MAX-ACCESS not-accessible
			STATUS current
			DESCRIPTION
				"Description."
			INDEX { hwBridgeProfileName }
			::= { hwBridgeProfileTable 1 }

		HwBridgeProfileEntry ::=
			SEQUENCE {
				hwBridgeProfileName
					OCTET STRING,
				hwBridgeProfileBridgeName
					OCTET STRING,
				hwBridgeProfileSecurityProfileName
					OCTET STRING,
				hwBridgeProfileVlanTagged
					OCTET STRING,
				hwBridgeProfileRowStatus
					RowStatus,
				hwBridgeProfileDhcpTrustPort
					INTEGER,
				hwBridgeProfileNdTrustPort
					INTEGER
			 }

		-- 1.3.6.1.4.1.2011.6.139.4.28.1.1
		hwBridgeProfileName OBJECT-TYPE
			SYNTAX OCTET STRING (SIZE (1..31))
			MAX-ACCESS not-accessible
			STATUS current
			DESCRIPTION
				"Description."
			::= { hwBridgeProfileEntry 1 }

		-- 1.3.6.1.4.1.2011.6.139.4.28.1.2
		hwBridgeProfileBridgeName OBJECT-TYPE
			SYNTAX OCTET STRING (SIZE (1..32))
			MAX-ACCESS read-create
			STATUS current
			DESCRIPTION
				"Description."
			::= { hwBridgeProfileEntry 2 }

		-- 1.3.6.1.4.1.2011.6.139.4.28.1.3
		hwBridgeProfileSecurityProfileName OBJECT-TYPE
			SYNTAX OCTET STRING (SIZE (1..31))
			MAX-ACCESS read-create
			STATUS current
			DESCRIPTION
				"Description."
			::= { hwBridgeProfileEntry 3 }

		-- 1.3.6.1.4.1.2011.6.139.4.28.1.4
		hwBridgeProfileVlanTagged OBJECT-TYPE
			SYNTAX OCTET STRING (SIZE (1..4094))
			MAX-ACCESS read-write
			STATUS current
			DESCRIPTION
				"Description."
			::= { hwBridgeProfileEntry 4 }

		-- 1.3.6.1.4.1.2011.6.139.4.28.1.5
		hwBridgeProfileRowStatus OBJECT-TYPE
			SYNTAX RowStatus
			MAX-ACCESS read-write
			STATUS current
			DESCRIPTION
				"Description."
			::= { hwBridgeProfileEntry 5 }

		hwBridgeProfileDhcpTrustPort OBJECT-TYPE
			SYNTAX INTEGER
				{
				disable(1),
				enable(2)
				}
			MAX-ACCESS read-write
			STATUS current
			DESCRIPTION
				"Description."
			::= { hwBridgeProfileEntry 6 }

		-- 1.3.6.1.4.1.2011.6.139.4.28.1.7
		hwBridgeProfileNdTrustPort OBJECT-TYPE
			SYNTAX INTEGER
				{
				disable(1),
				enable(2)
				}
			MAX-ACCESS read-write
			STATUS current
			DESCRIPTION
				"Description."
			DEFVAL { enable }
			::= { hwBridgeProfileEntry 7 }

--    1.3.6.1.4.1.2011.6.139.4.29
-- 1.3.6.1.4.1.2011.6.139.4.29
-- 1.3.6.1.4.1.2011.6.139.4.29
		-- 1.3.6.1.4.1.2011.6.139.4.29
		hwBridgeVapManagementTable OBJECT-TYPE
			SYNTAX SEQUENCE OF HwBridgeVapManagementEntry
			MAX-ACCESS not-accessible
			STATUS current
			DESCRIPTION
				"Description."
			::= { hwWlanServiceManagement 29 }

		-- 1.3.6.1.4.1.2011.6.139.4.29.1
		hwBridgeVapManagementEntry OBJECT-TYPE
			SYNTAX HwBridgeVapManagementEntry
			MAX-ACCESS not-accessible
			STATUS current
			DESCRIPTION
				"Description."
			INDEX { hwBridgeVapApIndex, hwBridgeVapRadioIndex, hwBridgeVapBridgeProfileName }
			::= { hwBridgeVapManagementTable 1 }

		HwBridgeVapManagementEntry ::=
			SEQUENCE {
				hwBridgeVapApIndex
					Integer32,
				hwBridgeVapRadioIndex
					Integer32,
				hwBridgeVapBridgeProfileName
					OCTET STRING,
				hwBridgeVapRowStatus
					RowStatus,
				hwBridgeVapBssid
					OCTET STRING
			 }

		-- 1.3.6.1.4.1.2011.6.139.4.29.1.1
		hwBridgeVapApIndex OBJECT-TYPE
			SYNTAX Integer32
			MAX-ACCESS not-accessible
			STATUS current
			DESCRIPTION
				"Description."
			::= { hwBridgeVapManagementEntry 1 }

		-- 1.3.6.1.4.1.2011.6.139.4.29.1.2
		hwBridgeVapRadioIndex OBJECT-TYPE
			SYNTAX Integer32
			MAX-ACCESS not-accessible
			STATUS current
			DESCRIPTION
				"Description."
			::= { hwBridgeVapManagementEntry 2 }

		-- 1.3.6.1.4.1.2011.6.139.4.29.1.3
		hwBridgeVapBridgeProfileName OBJECT-TYPE
			SYNTAX OCTET STRING (SIZE (1..31))
			MAX-ACCESS not-accessible
			STATUS current
			DESCRIPTION
				"Description."
			::= { hwBridgeVapManagementEntry 3 }

		-- 1.3.6.1.4.1.2011.6.139.4.29.1.4
		hwBridgeVapRowStatus OBJECT-TYPE
			SYNTAX RowStatus
			MAX-ACCESS read-write
			STATUS current
			DESCRIPTION
				"Description."
			::= { hwBridgeVapManagementEntry 4 }

		hwBridgeVapBssid OBJECT-TYPE
			SYNTAX OCTET STRING
			MAX-ACCESS read-only
			STATUS current
			DESCRIPTION
				"Description."
			::= { hwBridgeVapManagementEntry 5 }

--    1.3.6.1.4.1.2011.6.139.4.30
-- 1.3.6.1.4.1.2011.6.139.4.30
-- 1.3.6.1.4.1.2011.6.139.4.30
		-- 1.3.6.1.4.1.2011.6.139.4.30
		hwMacBridgeVapManagementTable OBJECT-TYPE
			SYNTAX SEQUENCE OF HwMacBridgeVapManagementEntry
			MAX-ACCESS not-accessible
			STATUS current
			DESCRIPTION
				"Description."
			::= { hwWlanServiceManagement 30 }

		-- 1.3.6.1.4.1.2011.6.139.4.30.1
		hwMacBridgeVapManagementEntry OBJECT-TYPE
			SYNTAX HwMacBridgeVapManagementEntry
			MAX-ACCESS not-accessible
			STATUS current
			DESCRIPTION
				"Description."
			INDEX { hwMacBridgeVapApMac, hwMacBridgeVapRadioIndex, hwMacBridgeVapBridgeProfileName }
			::= { hwMacBridgeVapManagementTable 1 }


		HwMacBridgeVapManagementEntry ::=
			SEQUENCE {
				hwMacBridgeVapApMac
					MacAddress,
				hwMacBridgeVapRadioIndex
					Integer32,
				hwMacBridgeVapBridgeProfileName
					OCTET STRING,
				hwMacBridgeVapRowStatus
					RowStatus,
				hwMacBridgeVapBssid
					OCTET STRING
			 }

		-- 1.3.6.1.4.1.2011.6.139.4.30.1.1
		hwMacBridgeVapApMac OBJECT-TYPE
			SYNTAX MacAddress
			MAX-ACCESS not-accessible
			STATUS current
			DESCRIPTION
				"Description."
			::= { hwMacBridgeVapManagementEntry 1 }

		-- 1.3.6.1.4.1.2011.6.139.4.30.1.2
		hwMacBridgeVapRadioIndex OBJECT-TYPE
			SYNTAX Integer32
			MAX-ACCESS not-accessible
			STATUS current
			DESCRIPTION
				"Description."
			::= { hwMacBridgeVapManagementEntry 2 }

		-- 1.3.6.1.4.1.2011.6.139.4.30.1.3
		hwMacBridgeVapBridgeProfileName OBJECT-TYPE
			SYNTAX OCTET STRING (SIZE (1..31))
			MAX-ACCESS not-accessible
			STATUS current
			DESCRIPTION
				"Description."
			::= { hwMacBridgeVapManagementEntry 3 }

		-- 1.3.6.1.4.1.2011.6.139.4.30.1.4
		hwMacBridgeVapRowStatus OBJECT-TYPE
			SYNTAX RowStatus
			MAX-ACCESS read-write
			STATUS current
			DESCRIPTION
				"Description."
			::= { hwMacBridgeVapManagementEntry 4 }

		hwMacBridgeVapBssid OBJECT-TYPE
			SYNTAX OCTET STRING
			MAX-ACCESS read-only
			STATUS current
			DESCRIPTION
				"Description."
			::= { hwMacBridgeVapManagementEntry 5 }

--    1.3.6.1.4.1.2011.6.139.4.31
-- 1.3.6.1.4.1.2011.6.139.4.31
-- 1.3.6.1.4.1.2011.6.139.4.31
		-- 1.3.6.1.4.1.2011.6.139.4.31
		hwBridgeLinkTable OBJECT-TYPE
			SYNTAX SEQUENCE OF HwBridgeLinkEntry
			MAX-ACCESS not-accessible
			STATUS current
			DESCRIPTION
				"Description."
			::= { hwWlanServiceManagement 31 }

		-- 1.3.6.1.4.1.2011.6.139.4.31.1
		hwBridgeLinkEntry OBJECT-TYPE
			SYNTAX HwBridgeLinkEntry
			MAX-ACCESS not-accessible
			STATUS current
			DESCRIPTION
				"Description."
			INDEX { hwBridgeVapApIndex, hwBridgeVapRadioIndex, hwBridgeLinkIndex }
			::= { hwBridgeLinkTable 1 }


		HwBridgeLinkEntry ::=
			SEQUENCE {
				hwBridgeLinkIndex
					Integer32,
				hwBridgeLinkWlanID
					Integer32,
				hwBridgeLinkBridgeType
					Integer32,
				hwBridgeLinkBridgeSubType
					Integer32,
				hwBridgeLinkPeerMac
					MacAddress,
				hwBridgeLinkBridgeProfileName
					OCTET STRING,
				hwBridgeLinkStpMode
					Integer32,
				hwBridgeLinkInstanceIdList
					OCTET STRING,
				hwBridgeLinkInstanceStateList
					OCTET STRING,
				hwBridgeLinkApMac
					MacAddress,
				hwBridgeLinkBridgeMode
					INTEGER,
				hwBridgeLinkCoverageDistance
					Integer32,
				hwBridgeLinkPeerAPID
					Integer32,
				hwBridgeLinkPeerAPStatus
					INTEGER,
				hwBridgeLinkMaxRssi
					Integer32,
				hwBridgeLinkRssi
					Integer32,
				hwBridgeLinkPeerApMac
					MacAddress,
				hwBridgeLinkChannelID
					Integer32
			 }

		-- 1.3.6.1.4.1.2011.6.139.4.31.1.1
		hwBridgeLinkIndex OBJECT-TYPE
			SYNTAX Integer32
			MAX-ACCESS not-accessible
			STATUS current
			DESCRIPTION
				"Description."
			::= { hwBridgeLinkEntry 1 }

		-- 1.3.6.1.4.1.2011.6.139.4.31.1.2
		hwBridgeLinkWlanID OBJECT-TYPE
			SYNTAX Integer32
			MAX-ACCESS read-only
			STATUS current
			DESCRIPTION
				"Description."
			::= { hwBridgeLinkEntry 2 }

		-- 1.3.6.1.4.1.2011.6.139.4.31.1.3
		hwBridgeLinkBridgeType OBJECT-TYPE
			SYNTAX Integer32
			MAX-ACCESS read-only
			STATUS current
			DESCRIPTION
				"Description."
			::= { hwBridgeLinkEntry 3 }

		-- 1.3.6.1.4.1.2011.6.139.4.31.1.4
		hwBridgeLinkBridgeSubType OBJECT-TYPE
			SYNTAX Integer32
			MAX-ACCESS read-only
			STATUS current
			DESCRIPTION
				"Description."
			::= { hwBridgeLinkEntry 4 }

		-- 1.3.6.1.4.1.2011.6.139.4.31.1.5
		hwBridgeLinkPeerMac OBJECT-TYPE
			SYNTAX MacAddress
			MAX-ACCESS read-only
			STATUS current
			DESCRIPTION
				"Description."
			::= { hwBridgeLinkEntry 5 }

		-- 1.3.6.1.4.1.2011.6.139.4.31.1.6
		hwBridgeLinkBridgeProfileName OBJECT-TYPE
			SYNTAX OCTET STRING (SIZE (0..31))
			MAX-ACCESS read-only
			STATUS current
			DESCRIPTION
				"Description."
			::= { hwBridgeLinkEntry 6 }

		-- 1.3.6.1.4.1.2011.6.139.4.31.1.7
		hwBridgeLinkStpMode OBJECT-TYPE
			SYNTAX Integer32
			MAX-ACCESS read-only
			STATUS current
			DESCRIPTION
				"Description."
			::= { hwBridgeLinkEntry 7 }

		-- 1.3.6.1.4.1.2011.6.139.4.31.1.8
		hwBridgeLinkInstanceIdList OBJECT-TYPE
			SYNTAX OCTET STRING
			MAX-ACCESS read-only
			STATUS current
			DESCRIPTION
				"Description."
			::= { hwBridgeLinkEntry 8 }

		-- 1.3.6.1.4.1.2011.6.139.4.31.1.9
		hwBridgeLinkInstanceStateList OBJECT-TYPE
			SYNTAX OCTET STRING
			MAX-ACCESS read-only
			STATUS current
			DESCRIPTION
				"Description."
			::= { hwBridgeLinkEntry 9 }


--  1.3.6.1.4.1.2011.6.139.4.31.1.10
		-- 1.3.6.1.4.1.2011.6.139.4.31.1.10
		hwBridgeLinkApMac OBJECT-TYPE
			SYNTAX MacAddress
			MAX-ACCESS read-only
			STATUS current
			DESCRIPTION
				"It means local ap mac."
			::= { hwBridgeLinkEntry 10 }


--  1.3.6.1.4.1.2011.6.139.4.31.1.11
		-- 1.3.6.1.4.1.2011.6.139.4.31.1.11
		hwBridgeLinkBridgeMode OBJECT-TYPE
			SYNTAX INTEGER
				{
				middle(1),
				root(2),
				leaf(3)
				}
			MAX-ACCESS read-only
			STATUS current
			DESCRIPTION
				"It means bridge mode for local AP."
			::= { hwBridgeLinkEntry 11 }


--  1.3.6.1.4.1.2011.6.139.4.31.1.12
		-- 1.3.6.1.4.1.2011.6.139.4.31.1.12
		hwBridgeLinkCoverageDistance OBJECT-TYPE
			SYNTAX Integer32
			MAX-ACCESS read-only
			STATUS current
			DESCRIPTION
				"It means coverage distance for loacal ap."
			::= { hwBridgeLinkEntry 12 }


--  1.3.6.1.4.1.2011.6.139.4.31.1.13
		-- 1.3.6.1.4.1.2011.6.139.4.31.1.13
		hwBridgeLinkPeerAPID OBJECT-TYPE
			SYNTAX Integer32
			MAX-ACCESS read-only
			STATUS current
			DESCRIPTION
				"It means peer AP ID."
			::= { hwBridgeLinkEntry 13 }


--  1.3.6.1.4.1.2011.6.139.4.31.1.14
		-- 1.3.6.1.4.1.2011.6.139.4.31.1.14
		hwBridgeLinkPeerAPStatus OBJECT-TYPE
			SYNTAX INTEGER
				{
				idle(1),
				autoFind(2),
				typeNotMatch(3),
				verMismatch(4),
				fault(5),
				config(6),
				commitFailed(7),
				download(8),
				standby(9),
				normal(10),
				committing(11),
				configFailed(12),
				invalid(13)
				}
			MAX-ACCESS read-only
			STATUS current
			DESCRIPTION
				"It means peer AP status."
			::= { hwBridgeLinkEntry 14 }


--  1.3.6.1.4.1.2011.6.139.4.31.1.15
		-- 1.3.6.1.4.1.2011.6.139.4.31.1.15
		hwBridgeLinkMaxRssi OBJECT-TYPE
			SYNTAX Integer32
			MAX-ACCESS read-only
			STATUS current
			DESCRIPTION
				"It means max rssi."
			::= { hwBridgeLinkEntry 15 }


--  1.3.6.1.4.1.2011.6.139.4.31.1.16
		-- 1.3.6.1.4.1.2011.6.139.4.31.1.16
		hwBridgeLinkRssi OBJECT-TYPE
			SYNTAX Integer32
			MAX-ACCESS read-only
			STATUS current
			DESCRIPTION
				"It means current rssi."
			::= { hwBridgeLinkEntry 16 }


--  1.3.6.1.4.1.2011.6.139.4.31.1.17
		-- 1.3.6.1.4.1.2011.6.139.4.31.1.17
		hwBridgeLinkPeerApMac OBJECT-TYPE
			SYNTAX MacAddress
			MAX-ACCESS read-only
			STATUS current
			DESCRIPTION
				"It means peer AP mac."
			::= { hwBridgeLinkEntry 17 }

		-- 1.3.6.1.4.1.2011.6.139.4.31.1.18
		hwBridgeLinkChannelID OBJECT-TYPE
			SYNTAX Integer32
			MAX-ACCESS read-only
			STATUS current
			DESCRIPTION
				"It means the current channel id."
			::= { hwBridgeLinkEntry 18 }

--  1.3.6.1.4.1.2011.6.139.4.32
		-- 1.3.6.1.4.1.2011.6.139.4.32
		hwMacBridgeLinkTable OBJECT-TYPE
			SYNTAX SEQUENCE OF HwMacBridgeLinkEntry
			MAX-ACCESS not-accessible
			STATUS current
			DESCRIPTION
				"It means bridge link table."
			::= { hwWlanServiceManagement 32 }

		-- 1.3.6.1.4.1.2011.6.139.4.32.1
		hwMacBridgeLinkEntry OBJECT-TYPE
			SYNTAX HwMacBridgeLinkEntry
			MAX-ACCESS not-accessible
			STATUS current
			DESCRIPTION
				"Description."
			INDEX { hwMacBridgeVapApMac, hwMacBridgeVapRadioIndex, hwMacBridgeLinkIndex }
			::= { hwMacBridgeLinkTable 1 }

		HwMacBridgeLinkEntry ::=
			SEQUENCE {
				hwMacBridgeLinkIndex
					Integer32,
				hwMacBridgeLinkWlanID
					Integer32,
				hwMacBridgeLinkBridgeType
					Integer32,
				hwMacBridgeLinkBridgeSubType
					Integer32,
				hwMacBridgeLinkPeerMac
					MacAddress,
				hwMacBridgeLinkBridgeProfileName
					OCTET STRING,
				hwMacBridgeLinkStpMode
					Integer32,
				hwMacBridgeLinkInstanceIdList
					OCTET STRING,
				hwMacBridgeLinkInstanceStateList
					OCTET STRING,
				hwMacBridgeLinkApID
					Integer32,
				hwMacBridgeLinkBridgeMode
					INTEGER,
				hwMacBridgeLinkCoverageDistance
					Integer32,
				hwMacBridgeLinkPeerAPID
					Integer32,
				hwMacBridgeLinkPeerAPStatus
					INTEGER,
				hwMacBridgeLinkMaxRssi
					Integer32,
				hwMacBridgeLinkRssi
					Integer32,
				hwMacBridgeLinkPeerApMac
					MacAddress,
				hwMacBridgeChannelID
					Integer32
			 }

		-- 1.3.6.1.4.1.2011.6.139.4.32.1.1
		hwMacBridgeLinkIndex OBJECT-TYPE
			SYNTAX Integer32
			MAX-ACCESS not-accessible
			STATUS current
			DESCRIPTION
				"It means bridge link index."
			::= { hwMacBridgeLinkEntry 1 }

		-- 1.3.6.1.4.1.2011.6.139.4.32.1.2
		hwMacBridgeLinkWlanID OBJECT-TYPE
			SYNTAX Integer32
			MAX-ACCESS read-only
			STATUS current
			DESCRIPTION
				"It means bridge link wlan id."
			::= { hwMacBridgeLinkEntry 2 }

		-- 1.3.6.1.4.1.2011.6.139.4.32.1.3
		hwMacBridgeLinkBridgeType OBJECT-TYPE
			SYNTAX Integer32
			MAX-ACCESS read-only
			STATUS current
			DESCRIPTION
				"It means bridge link type."
			::= { hwMacBridgeLinkEntry 3 }

		-- 1.3.6.1.4.1.2011.6.139.4.32.1.4
		hwMacBridgeLinkBridgeSubType OBJECT-TYPE
			SYNTAX Integer32
			MAX-ACCESS read-only
			STATUS current
			DESCRIPTION
				"It means bridge link subtype."
			::= { hwMacBridgeLinkEntry 4 }

		-- 1.3.6.1.4.1.2011.6.139.4.32.1.5
		hwMacBridgeLinkPeerMac OBJECT-TYPE
			SYNTAX MacAddress
			MAX-ACCESS read-only
			STATUS current
			DESCRIPTION
				"It means peer bssid."
			::= { hwMacBridgeLinkEntry 5 }

		-- 1.3.6.1.4.1.2011.6.139.4.32.1.6
		hwMacBridgeLinkBridgeProfileName OBJECT-TYPE
			SYNTAX OCTET STRING (SIZE (0..31))
			MAX-ACCESS read-only
			STATUS current
			DESCRIPTION
				"It means bridge profile name."
			::= { hwMacBridgeLinkEntry 6 }

		-- 1.3.6.1.4.1.2011.6.139.4.32.1.7
		hwMacBridgeLinkStpMode OBJECT-TYPE
			SYNTAX Integer32
			MAX-ACCESS read-only
			STATUS current
			DESCRIPTION
				"It means stp mode."
			::= { hwMacBridgeLinkEntry 7 }

		-- 1.3.6.1.4.1.2011.6.139.4.32.1.8
		hwMacBridgeLinkInstanceIdList OBJECT-TYPE
			SYNTAX OCTET STRING
			MAX-ACCESS read-only
			STATUS current
			DESCRIPTION
				"Description."
			::= { hwMacBridgeLinkEntry 8 }

		-- 1.3.6.1.4.1.2011.6.139.4.32.1.9
		hwMacBridgeLinkInstanceStateList OBJECT-TYPE
			SYNTAX OCTET STRING
			MAX-ACCESS read-only
			STATUS current
			DESCRIPTION
				"Description."
			::= { hwMacBridgeLinkEntry 9 }


--  1.3.6.1.4.1.2011.6.139.4.32.1.10
		-- 1.3.6.1.4.1.2011.6.139.4.32.1.10
		hwMacBridgeLinkApID OBJECT-TYPE
			SYNTAX Integer32
			MAX-ACCESS read-only
			STATUS current
			DESCRIPTION
				"It means AP ID."
			::= { hwMacBridgeLinkEntry 10 }


--  1.3.6.1.4.1.2011.6.139.4.32.1.11
		-- 1.3.6.1.4.1.2011.6.139.4.32.1.11
		hwMacBridgeLinkBridgeMode OBJECT-TYPE
			SYNTAX INTEGER
				{
				middle(1),
				root(2),
				leaf(3)
				}
			MAX-ACCESS read-only
			STATUS current
			DESCRIPTION
				"It means bridge mode for local AP."
			::= { hwMacBridgeLinkEntry 11 }


--  1.3.6.1.4.1.2011.6.139.4.32.1.12
		-- 1.3.6.1.4.1.2011.6.139.4.32.1.12
		hwMacBridgeLinkCoverageDistance OBJECT-TYPE
			SYNTAX Integer32
			MAX-ACCESS read-only
			STATUS current
			DESCRIPTION
				"It means coverage distance for local AP."
			::= { hwMacBridgeLinkEntry 12 }


--  1.3.6.1.4.1.2011.6.139.4.32.1.13
		-- 1.3.6.1.4.1.2011.6.139.4.32.1.13
		hwMacBridgeLinkPeerAPID OBJECT-TYPE
			SYNTAX Integer32
			MAX-ACCESS read-only
			STATUS current
			DESCRIPTION
				"It means peer AP ID."
			::= { hwMacBridgeLinkEntry 13 }


--  1.3.6.1.4.1.2011.6.139.4.32.1.14
		-- 1.3.6.1.4.1.2011.6.139.4.32.1.14
		hwMacBridgeLinkPeerAPStatus OBJECT-TYPE
			SYNTAX INTEGER
				{
				idle(1),
				autoFind(2),
				typeNotMatch(3),
				verMismatch(4),
				fault(5),
				config(6),
				commitFailed(7),
				download(8),
				standby(9),
				normal(10),
				committing(11),
				configFailed(12),
				invalid(13)
				}
			MAX-ACCESS read-only
			STATUS current
			DESCRIPTION
				"It means peer AP status."
			::= { hwMacBridgeLinkEntry 14 }


--  1.3.6.1.4.1.2011.6.139.4.32.1.15
		-- 1.3.6.1.4.1.2011.6.139.4.32.1.15
		hwMacBridgeLinkMaxRssi OBJECT-TYPE
			SYNTAX Integer32
			MAX-ACCESS read-only
			STATUS current
			DESCRIPTION
				"It means max rssi."
			::= { hwMacBridgeLinkEntry 15 }


--  1.3.6.1.4.1.2011.6.139.4.32.1.16
		-- 1.3.6.1.4.1.2011.6.139.4.32.1.16
		hwMacBridgeLinkRssi OBJECT-TYPE
			SYNTAX Integer32
			MAX-ACCESS read-only
			STATUS current
			DESCRIPTION
				"It means rssi."
			::= { hwMacBridgeLinkEntry 16 }


--  1.3.6.1.4.1.2011.6.139.4.32.1.17
		-- 1.3.6.1.4.1.2011.6.139.4.32.1.17
		hwMacBridgeLinkPeerApMac OBJECT-TYPE
			SYNTAX MacAddress
			MAX-ACCESS read-only
			STATUS current
			DESCRIPTION
				"It means peer AP mac."
			::= { hwMacBridgeLinkEntry 17 }

		-- 1.3.6.1.4.1.2011.6.139.4.32.1.18
		hwMacBridgeChannelID OBJECT-TYPE
			SYNTAX Integer32
			MAX-ACCESS read-only
			STATUS current
			DESCRIPTION
				"It means the current channel id."
			::= { hwMacBridgeLinkEntry 18 }

--  1.3.6.1.4.1.2011.6.139.4.33
		-- 1.3.6.1.4.1.2011.6.139.4.33
		hwBridgeWhitelistTable OBJECT-TYPE
			SYNTAX SEQUENCE OF HwBridgeWhitelistEntry
			MAX-ACCESS not-accessible
			STATUS current
			DESCRIPTION
				"Description."
			::= { hwWlanServiceManagement 33 }

		-- 1.3.6.1.4.1.2011.6.139.4.33.1
		hwBridgeWhitelistEntry OBJECT-TYPE
			SYNTAX HwBridgeWhitelistEntry
			MAX-ACCESS not-accessible
			STATUS current
			DESCRIPTION
				"Description."
			INDEX { hwBridgeWhitelistName }
			::= { hwBridgeWhitelistTable 1 }

		HwBridgeWhitelistEntry ::=
			SEQUENCE {
				hwBridgeWhitelistName
					OCTET STRING,
				hwBridgeWhitelistPeerList
					OCTET STRING,
				hwBridgeWhitelistRowStatus
					RowStatus
			 }

		-- 1.3.6.1.4.1.2011.6.139.4.33.1.1
		hwBridgeWhitelistName OBJECT-TYPE
			SYNTAX OCTET STRING (SIZE (1..31))
			MAX-ACCESS not-accessible
			STATUS current
			DESCRIPTION
				"Description."
			::= { hwBridgeWhitelistEntry 1 }

		-- 1.3.6.1.4.1.2011.6.139.4.33.1.2
		hwBridgeWhitelistPeerList OBJECT-TYPE
			SYNTAX OCTET STRING (SIZE (0..89))
			MAX-ACCESS read-create
			STATUS current
			DESCRIPTION
				"Description."
			::= { hwBridgeWhitelistEntry 2 }

		-- 1.3.6.1.4.1.2011.6.139.4.33.1.3
		hwBridgeWhitelistRowStatus OBJECT-TYPE
			SYNTAX RowStatus
			MAX-ACCESS read-create
			STATUS current
			DESCRIPTION
				"Description."
			::= { hwBridgeWhitelistEntry 3 }

		-- 1.3.6.1.4.1.2011.6.139.4.34
		hwWirelessSsidStatisticTable OBJECT-TYPE
			SYNTAX SEQUENCE OF HwWirelessSsidStatisticEntry
			MAX-ACCESS not-accessible
			STATUS current
			DESCRIPTION
				"Description."
			::= { hwWlanServiceManagement 34 }

		-- 1.3.6.1.4.1.2011.6.139.4.34.1
		hwWirelessSsidStatisticEntry OBJECT-TYPE
			SYNTAX HwWirelessSsidStatisticEntry
			MAX-ACCESS not-accessible
			STATUS current
			DESCRIPTION
				"Description."
			INDEX { hwWirelessSsidStatisticEssSsid }
			::= { hwWirelessSsidStatisticTable 1 }

		HwWirelessSsidStatisticEntry ::=
			SEQUENCE {
				hwWirelessSsidStatisticEssSsid
					OCTET STRING,
				hwWirelessSsidAirportTransmitUnicastFrames
					Counter64,
				hwWirelessSsidAirportTransmitFrames
					Counter64,
				hwWirelessSsidAirportTransmitErrorFrames
					Counter64,
				hwWirelessSsidAirportDownReTransmitFrames
					Counter64,
				hwWirelessSsidAirportTransmitDropFrames
					Counter64,
				hwWirelessSsidAirportTransmitBytes
					Counter64,
				hwWirelessSsidAirportRecvUnicastFrames
					Counter64,
				hwWirelessSsidAirportRecvFrames
					Counter64,
				hwWirelessSsidAirportRecvErrorFrames
					Counter64,
				hwWirelessSsidAirportRecvDropFrames
					Counter64,
				hwWirelessSsidAirportRecvBytes
					Counter64,
				hwWirelessSsidTotalAssociatedSuccessStationCount
					Integer32,
				hwWirelessSsidCurAssocStationCount
					Integer32,
				hwWirelessSsidTotalAssociatedFailedStationCount
					Integer32
			 }

		-- 1.3.6.1.4.1.2011.6.139.4.34.1.1
		hwWirelessSsidStatisticEssSsid OBJECT-TYPE
			SYNTAX OCTET STRING
			MAX-ACCESS not-accessible
			STATUS current
			DESCRIPTION
				"Description."
			::= { hwWirelessSsidStatisticEntry 1 }

		-- 1.3.6.1.4.1.2011.6.139.4.34.1.2
		hwWirelessSsidAirportTransmitUnicastFrames OBJECT-TYPE
			SYNTAX Counter64
			MAX-ACCESS read-only
			STATUS current
			DESCRIPTION
				"Description."
			::= { hwWirelessSsidStatisticEntry 2 }

		-- 1.3.6.1.4.1.2011.6.139.4.34.1.3
		hwWirelessSsidAirportTransmitFrames OBJECT-TYPE
			SYNTAX Counter64
			MAX-ACCESS read-only
			STATUS current
			DESCRIPTION
				"Description."
			::= { hwWirelessSsidStatisticEntry 3 }

		-- 1.3.6.1.4.1.2011.6.139.4.34.1.4
		hwWirelessSsidAirportTransmitErrorFrames OBJECT-TYPE
			SYNTAX Counter64
			MAX-ACCESS read-only
			STATUS current
			DESCRIPTION
				"Description."
			::= { hwWirelessSsidStatisticEntry 4 }

		-- 1.3.6.1.4.1.2011.6.139.4.34.1.5
		hwWirelessSsidAirportDownReTransmitFrames OBJECT-TYPE
			SYNTAX Counter64
			MAX-ACCESS read-only
			STATUS current
			DESCRIPTION
				"Description."
			::= { hwWirelessSsidStatisticEntry 5 }

		-- 1.3.6.1.4.1.2011.6.139.4.34.1.6
		hwWirelessSsidAirportTransmitDropFrames OBJECT-TYPE
			SYNTAX Counter64
			MAX-ACCESS read-only
			STATUS current
			DESCRIPTION
				"Description."
			::= { hwWirelessSsidStatisticEntry 6 }

		-- 1.3.6.1.4.1.2011.6.139.4.34.1.7
		hwWirelessSsidAirportTransmitBytes OBJECT-TYPE
			SYNTAX Counter64
			MAX-ACCESS read-only
			STATUS current
			DESCRIPTION
				"Description."
			::= { hwWirelessSsidStatisticEntry 7 }

		-- 1.3.6.1.4.1.2011.6.139.4.34.1.8
		hwWirelessSsidAirportRecvUnicastFrames OBJECT-TYPE
			SYNTAX Counter64
			MAX-ACCESS read-only
			STATUS current
			DESCRIPTION
				"Description."
			::= { hwWirelessSsidStatisticEntry 8 }

		-- 1.3.6.1.4.1.2011.6.139.4.34.1.9
		hwWirelessSsidAirportRecvFrames OBJECT-TYPE
			SYNTAX Counter64
			MAX-ACCESS read-only
			STATUS current
			DESCRIPTION
				"Description."
			::= { hwWirelessSsidStatisticEntry 9 }

		-- 1.3.6.1.4.1.2011.6.139.4.34.1.10
		hwWirelessSsidAirportRecvErrorFrames OBJECT-TYPE
			SYNTAX Counter64
			MAX-ACCESS read-only
			STATUS current
			DESCRIPTION
				"Description."
			::= { hwWirelessSsidStatisticEntry 10 }

		-- 1.3.6.1.4.1.2011.6.139.4.34.1.11
		hwWirelessSsidAirportRecvDropFrames OBJECT-TYPE
			SYNTAX Counter64
			MAX-ACCESS read-only
			STATUS current
			DESCRIPTION
				"Description."
			::= { hwWirelessSsidStatisticEntry 11 }

		-- 1.3.6.1.4.1.2011.6.139.4.34.1.12
		hwWirelessSsidAirportRecvBytes OBJECT-TYPE
			SYNTAX Counter64
			MAX-ACCESS read-only
			STATUS current
			DESCRIPTION
				"Description."
			::= { hwWirelessSsidStatisticEntry 12 }

		-- 1.3.6.1.4.1.2011.6.139.4.34.1.13
		hwWirelessSsidTotalAssociatedSuccessStationCount OBJECT-TYPE
			SYNTAX Integer32
			MAX-ACCESS read-only
			STATUS current
			DESCRIPTION
				"Description."
			::= { hwWirelessSsidStatisticEntry 13 }

		-- 1.3.6.1.4.1.2011.6.139.4.34.1.14
		hwWirelessSsidCurAssocStationCount OBJECT-TYPE
			SYNTAX Integer32
			MAX-ACCESS read-only
			STATUS current
			DESCRIPTION
				"Description."
			::= { hwWirelessSsidStatisticEntry 14 }

		-- 1.3.6.1.4.1.2011.6.139.4.34.1.15
		hwWirelessSsidTotalAssociatedFailedStationCount OBJECT-TYPE
			SYNTAX Integer32
			MAX-ACCESS read-only
			STATUS current
			DESCRIPTION
				"Description."
			::= { hwWirelessSsidStatisticEntry 15 }

		-- 1.3.6.1.4.1.2011.6.139.4.35
		hwStaBlacklistProfileTable OBJECT-TYPE
			SYNTAX SEQUENCE OF HwStaBlacklistProfileEntry
			MAX-ACCESS not-accessible
			STATUS current
			DESCRIPTION
				"Description."
			::= { hwWlanServiceManagement 35 }

		-- 1.3.6.1.4.1.2011.6.139.4.35.1
		hwStaBlacklistProfileEntry OBJECT-TYPE
			SYNTAX HwStaBlacklistProfileEntry
			MAX-ACCESS not-accessible
			STATUS current
			DESCRIPTION
				"Description."
			INDEX { hwStaBlacklistProfileName }
			::= { hwStaBlacklistProfileTable 1 }

		HwStaBlacklistProfileEntry ::=
			SEQUENCE {
				hwStaBlacklistProfileName
					OCTET STRING,
				hwStaBlacklistProfileStaMac
					MacAddress,
				hwStaBlacklistProfileOper
					Integer32,
				hwStaBlacklistProfileStaNum
					Integer32,
				hwStaBlacklistProfileStaList
					OCTET STRING,
				hwStaBlacklistProfileRowStatus
					RowStatus
			 }

		-- 1.3.6.1.4.1.2011.6.139.4.35.1.1
		hwStaBlacklistProfileName OBJECT-TYPE
			SYNTAX OCTET STRING (SIZE (1..31))
			MAX-ACCESS not-accessible
			STATUS current
			DESCRIPTION
				"Description."
			::= { hwStaBlacklistProfileEntry 1 }

		-- 1.3.6.1.4.1.2011.6.139.4.35.1.2
		hwStaBlacklistProfileStaMac OBJECT-TYPE
			SYNTAX MacAddress
			MAX-ACCESS read-write
			STATUS current
			DESCRIPTION
				"Description."
			::= { hwStaBlacklistProfileEntry 2 }

		-- 1.3.6.1.4.1.2011.6.139.4.35.1.3
		hwStaBlacklistProfileOper OBJECT-TYPE
			SYNTAX Integer32
			MAX-ACCESS read-write
			STATUS current
			DESCRIPTION
				"Delete station mac: 1
				Add station mac:    2"
			::= { hwStaBlacklistProfileEntry 3 }

		-- 1.3.6.1.4.1.2011.6.139.4.35.1.4
		hwStaBlacklistProfileStaNum OBJECT-TYPE
			SYNTAX Integer32
			MAX-ACCESS read-only
			STATUS current
			DESCRIPTION
				"Description."
			::= { hwStaBlacklistProfileEntry 4 }

		-- 1.3.6.1.4.1.2011.6.139.4.35.1.5
		hwStaBlacklistProfileStaList OBJECT-TYPE
			SYNTAX OCTET STRING
			MAX-ACCESS read-only
			STATUS current
			DESCRIPTION
				"Description."
			::= { hwStaBlacklistProfileEntry 5 }

		-- 1.3.6.1.4.1.2011.6.139.4.35.1.6
		hwStaBlacklistProfileRowStatus OBJECT-TYPE
			SYNTAX RowStatus
			MAX-ACCESS read-create
			STATUS current
			DESCRIPTION
				"Description."
			::= { hwStaBlacklistProfileEntry 6 }

		-- 1.3.6.1.4.1.2011.6.139.4.36
		hwStaWhitelistProfileTable OBJECT-TYPE
			SYNTAX SEQUENCE OF HwStaWhitelistProfileEntry
			MAX-ACCESS not-accessible
			STATUS current
			DESCRIPTION
				"Description."
			::= { hwWlanServiceManagement 36 }

		-- 1.3.6.1.4.1.2011.6.139.4.36.1
		hwStaWhitelistProfileEntry OBJECT-TYPE
			SYNTAX HwStaWhitelistProfileEntry
			MAX-ACCESS not-accessible
			STATUS current
			DESCRIPTION
				"Description."
			INDEX { hwStaWhitelistProfileName }
			::= { hwStaWhitelistProfileTable 1 }

		HwStaWhitelistProfileEntry ::=
			SEQUENCE {
				hwStaWhitelistProfileName
					OCTET STRING,
				hwStaWhitelistProfileStaMac
					MacAddress,
				hwStaWhitelistProfileOper
					Integer32,
				hwStaWhitelistProfileStaNum
					Integer32,
				hwStaWhitelistProfileStaList
					OCTET STRING,
				hwStaWhitelistProfileRowStatus
					RowStatus
			 }

		-- 1.3.6.1.4.1.2011.6.139.4.36.1.1
		hwStaWhitelistProfileName OBJECT-TYPE
			SYNTAX OCTET STRING (SIZE (1..31))
			MAX-ACCESS not-accessible
			STATUS current
			DESCRIPTION
				"Description."
			::= { hwStaWhitelistProfileEntry 1 }

		-- 1.3.6.1.4.1.2011.6.139.4.36.1.2
		hwStaWhitelistProfileStaMac OBJECT-TYPE
			SYNTAX MacAddress
			MAX-ACCESS read-write
			STATUS current
			DESCRIPTION
				"Description."
			::= { hwStaWhitelistProfileEntry 2 }

		-- 1.3.6.1.4.1.2011.6.139.4.36.1.3
		hwStaWhitelistProfileOper OBJECT-TYPE
			SYNTAX Integer32
			MAX-ACCESS read-write
			STATUS current
			DESCRIPTION
				"Delete station mac: 1
				Add station mac:    2"
			::= { hwStaWhitelistProfileEntry 3 }

		-- 1.3.6.1.4.1.2011.6.139.4.36.1.4
		hwStaWhitelistProfileStaNum OBJECT-TYPE
			SYNTAX Integer32
			MAX-ACCESS read-only
			STATUS current
			DESCRIPTION
				"Description."
			::= { hwStaWhitelistProfileEntry 4 }

		-- 1.3.6.1.4.1.2011.6.139.4.36.1.5
		hwStaWhitelistProfileStaList OBJECT-TYPE
			SYNTAX OCTET STRING
			MAX-ACCESS read-only
			STATUS current
			DESCRIPTION
				"Description."
			::= { hwStaWhitelistProfileEntry 5 }

		-- 1.3.6.1.4.1.2011.6.139.4.36.1.6
		hwStaWhitelistProfileRowStatus OBJECT-TYPE
			SYNTAX RowStatus
			MAX-ACCESS read-create
			STATUS current
			DESCRIPTION
				"Description."
			::= { hwStaWhitelistProfileEntry 6 }

		-- 1.3.6.1.4.1.2011.6.139.4.37
		hwMeshProfileTable OBJECT-TYPE
			SYNTAX SEQUENCE OF HwMeshProfileEntry
			MAX-ACCESS not-accessible
			STATUS current
			DESCRIPTION
				"Description."
			::= { hwWlanServiceManagement 37 }

		-- 1.3.6.1.4.1.2011.6.139.4.37.1
		hwMeshProfileEntry OBJECT-TYPE
			SYNTAX HwMeshProfileEntry
			MAX-ACCESS not-accessible
			STATUS current
			DESCRIPTION
				"Description."
			INDEX { hwMeshProfileName }
			::= { hwMeshProfileTable 1 }

		HwMeshProfileEntry ::=
			SEQUENCE {
				hwMeshProfileName
					OCTET STRING,
				hwMeshProfileSecurityProfileName
					OCTET STRING,
				hwMeshProfileMeshID
					OCTET STRING,
				hwMeshProfileMaxLinkNum
					Integer32,
				hwMeshProfileRssiThreshold
					Integer32,
				hwMeshProfileReportInterval
					Integer32,
				hwMeshProfileRowStatus
					RowStatus,
				hwMeshProfileDhcpTrustPort
					INTEGER,
				hwMeshProfileNdTrustPort
					INTEGER,
				hwMeshProfileQuickHoSwitch
					INTEGER,
				hwMeshProfileLinkHoThreshold
					Integer32,
				hwMeshProfileLinkHoldPeriod
					Integer32,
				hwMeshProfileLinkLinkSaturationThreshold
					Integer32,
				hwMeshProfileLinkProbePeriod
					Integer32,
				hwMeshProfileFwaMode
					INTEGER,
				hwMeshProfileFwaEdcaMode
					INTEGER,
				hwMeshProfileQuickHandoverMinRssiThreshold
					Integer32,
				hwMeshProfileLocationBasedHandoverAlgorithmSwitch
					INTEGER,
				hwMeshProfileMovingDirection
					INTEGER,
				hwMeshProfileHandoverAlgorithmPNCriteriaObserveTime
					Integer32,
				hwMeshProfileHandoverAlgorithmPNCriteriaQualifyTime
					Integer32,
				hwMeshProfileUrgentHandoverLowRateThreshold
					Integer32,
				hwMeshProfileUrgentHandoverLowRatePeriod
					Integer32,
				hwMeshProfileUrgentHandoverPunishmentPeriod
					Integer32,
				hwMeshProfileUrgentHandoverPunishmentRssi
					Integer32
			 }

		-- 1.3.6.1.4.1.2011.6.139.4.37.1.1
		hwMeshProfileName OBJECT-TYPE
			SYNTAX OCTET STRING (SIZE (1..31))
			MAX-ACCESS not-accessible
			STATUS current
			DESCRIPTION
				"Description."
			::= { hwMeshProfileEntry 1 }

		-- 1.3.6.1.4.1.2011.6.139.4.37.1.2
		hwMeshProfileSecurityProfileName OBJECT-TYPE
			SYNTAX OCTET STRING (SIZE (1..31))
			MAX-ACCESS read-create
			STATUS current
			DESCRIPTION
				"Description."
			::= { hwMeshProfileEntry 2 }

		-- 1.3.6.1.4.1.2011.6.139.4.37.1.3
		hwMeshProfileMeshID OBJECT-TYPE
			SYNTAX OCTET STRING (SIZE (1..32))
			MAX-ACCESS read-create
			STATUS current
			DESCRIPTION
				"Description."
			::= { hwMeshProfileEntry 3 }

		-- 1.3.6.1.4.1.2011.6.139.4.37.1.4
		hwMeshProfileMaxLinkNum OBJECT-TYPE
			SYNTAX Integer32 (1..32)
			MAX-ACCESS read-write
			STATUS current
			DESCRIPTION
				"Description."
			DEFVAL { 8 }
			::= { hwMeshProfileEntry 4 }

		-- 1.3.6.1.4.1.2011.6.139.4.37.1.5
		hwMeshProfileRssiThreshold OBJECT-TYPE
			SYNTAX Integer32 (-90..-20)
			UNITS "dBm"
			MAX-ACCESS read-write
			STATUS current
			DESCRIPTION
				"It means the rssi threshold when the mesh links build or hold."
			DEFVAL { -75 }
			::= { hwMeshProfileEntry 5 }

		-- 1.3.6.1.4.1.2011.6.139.4.37.1.6
		hwMeshProfileReportInterval OBJECT-TYPE
			SYNTAX Integer32 (5..3600)
			UNITS "s"
			MAX-ACCESS read-write
			STATUS current
			DESCRIPTION
				"Description."
			DEFVAL { 30 }
			::= { hwMeshProfileEntry 6 }

		-- 1.3.6.1.4.1.2011.6.139.4.37.1.7
		hwMeshProfileRowStatus OBJECT-TYPE
			SYNTAX RowStatus
			MAX-ACCESS read-write
			STATUS current
			DESCRIPTION
				"Description."
			::= { hwMeshProfileEntry 7 }

		-- 1.3.6.1.4.1.2011.6.139.4.37.1.8
		hwMeshProfileDhcpTrustPort OBJECT-TYPE
			SYNTAX INTEGER
				{
				disable(1),
				enable(2)
				}
			MAX-ACCESS read-write
			STATUS current
			DESCRIPTION
				"Description."
			::= { hwMeshProfileEntry 8 }

		-- 1.3.6.1.4.1.2011.6.139.4.37.1.9
		hwMeshProfileNdTrustPort OBJECT-TYPE
			SYNTAX INTEGER
				{
				disable(1),
				enable(2)
				}
			MAX-ACCESS read-write
			STATUS current
			DESCRIPTION
				"Description."
			DEFVAL { enable }
			::= { hwMeshProfileEntry 9 }


--  1.3.6.1.4.1.2011.6.139.4.37.1.10
		-- 1.3.6.1.4.1.2011.6.139.4.37.1.10
		hwMeshProfileQuickHoSwitch OBJECT-TYPE
			SYNTAX INTEGER
				{
				disable(1),
				enable(2)
				}
			MAX-ACCESS read-write
			STATUS current
			DESCRIPTION
				"It means quick handover switch."
			::= { hwMeshProfileEntry 10 }


--  1.3.6.1.4.1.2011.6.139.4.37.1.11
		-- 1.3.6.1.4.1.2011.6.139.4.37.1.11
		hwMeshProfileLinkHoThreshold OBJECT-TYPE
			SYNTAX Integer32 (1..70)
			UNITS "dB"
			MAX-ACCESS read-write
			STATUS current
			DESCRIPTION
				"It means handover switch when the rssi reach threshold, it happens."
			DEFVAL { 10 }
			::= { hwMeshProfileEntry 11 }


--  1.3.6.1.4.1.2011.6.139.4.37.1.12
		-- 1.3.6.1.4.1.2011.6.139.4.37.1.12
		hwMeshProfileLinkHoldPeriod OBJECT-TYPE
			SYNTAX Integer32 (1000..60000)
			UNITS "ms"
			MAX-ACCESS read-write
			STATUS current
			DESCRIPTION
				"It means link hold period."
			DEFVAL { 4000 }
			::= { hwMeshProfileEntry 12 }


--  1.3.6.1.4.1.2011.6.139.4.37.1.13
		-- 1.3.6.1.4.1.2011.6.139.4.37.1.13
		hwMeshProfileLinkLinkSaturationThreshold OBJECT-TYPE
			SYNTAX Integer32 (-90..0)
			UNITS "dBm"
			MAX-ACCESS read-write
			STATUS current
			DESCRIPTION
				"It means the rssi link saturation threshold."
			DEFVAL { -20 }
			::= { hwMeshProfileEntry 13 }


--  1.3.6.1.4.1.2011.6.139.4.37.1.14
		-- 1.3.6.1.4.1.2011.6.139.4.37.1.14
		hwMeshProfileLinkProbePeriod OBJECT-TYPE
			SYNTAX Integer32 (50..6000)
			UNITS "ms"
			MAX-ACCESS read-write
			STATUS current
			DESCRIPTION
				"It means link probe period."
			DEFVAL { 100 }
			::= { hwMeshProfileEntry 14 }

		-- 1.3.6.1.4.1.2011.6.139.4.37.1.15
		hwMeshProfileFwaMode OBJECT-TYPE
			SYNTAX INTEGER
				{
				disable(1),
				enable(2)
				}
			MAX-ACCESS read-write
			STATUS current
			DESCRIPTION
				"Description."
			DEFVAL { disable }
			::= { hwMeshProfileEntry 15 }

		-- 1.3.6.1.4.1.2011.6.139.4.37.1.16
		hwMeshProfileFwaEdcaMode OBJECT-TYPE
			SYNTAX INTEGER
				{
				auto(1),
				manual(2)
				}
			MAX-ACCESS read-write
			STATUS current
			DESCRIPTION
				"The AP automatically adjusts EDCA parameters based on the number of NPEs or uses the EDCA parameters configured in the WMM profile."
			DEFVAL { auto }
			::= { hwMeshProfileEntry 16 }

		-- 1.3.6.1.4.1.2011.6.139.4.37.1.17
		hwMeshProfileQuickHandoverMinRssiThreshold OBJECT-TYPE
			SYNTAX Integer32 (-90..-20)
			UNITS "dBm"
			MAX-ACCESS read-write
			STATUS current
			DESCRIPTION
				"It means mini rssi threshold of active links."
		        DEFVAL { -60 }
			::= { hwMeshProfileEntry 17 }

		-- 1.3.6.1.4.1.2011.6.139.4.37.1.18
		hwMeshProfileLocationBasedHandoverAlgorithmSwitch OBJECT-TYPE
			SYNTAX INTEGER
				{
				disable(1),
				enable(2)
				}
			MAX-ACCESS read-write
			STATUS current
			DESCRIPTION
				"It means handover algorithm switch based on location."
			::= { hwMeshProfileEntry 18 }

		-- 1.3.6.1.4.1.2011.6.139.4.37.1.19
		hwMeshProfileMovingDirection OBJECT-TYPE
			SYNTAX INTEGER
				{
				forward(1),
				backward(2),
				undetermined(3)
				}
			MAX-ACCESS read-write
			STATUS current
			DESCRIPTION
				"It means moving direction."
			::= { hwMeshProfileEntry 19 }

		-- 1.3.6.1.4.1.2011.6.139.4.37.1.20
		hwMeshProfileHandoverAlgorithmPNCriteriaObserveTime OBJECT-TYPE
			SYNTAX Integer32 (1..10)
			MAX-ACCESS read-write
			STATUS current
			DESCRIPTION
				"It means handover algorithm p-n criteria observe time."
		        DEFVAL { 3 }
			::= { hwMeshProfileEntry 20 }


		-- 1.3.6.1.4.1.2011.6.139.4.37.1.21
		hwMeshProfileHandoverAlgorithmPNCriteriaQualifyTime OBJECT-TYPE
			SYNTAX Integer32 (1..10)
			MAX-ACCESS read-write
			STATUS current
			DESCRIPTION
				"It means handover algorithm p-n criteria qualify time."
		        DEFVAL { 2 }
			::= { hwMeshProfileEntry 21 }


		-- 1.3.6.1.4.1.2011.6.139.4.37.1.22
		hwMeshProfileUrgentHandoverLowRateThreshold OBJECT-TYPE
			SYNTAX Integer32 (1..1300)
			UNITS "Mbps"
			MAX-ACCESS read-write
			STATUS current
			DESCRIPTION
				"It means rate threshold of the low rate urgent handover."
			DEFVAL { 10 }
			::= { hwMeshProfileEntry 22 }


		-- 1.3.6.1.4.1.2011.6.139.4.37.1.23
		hwMeshProfileUrgentHandoverLowRatePeriod OBJECT-TYPE
			SYNTAX Integer32 (0..10000)
			UNITS "ms"
			MAX-ACCESS read-write
			STATUS current
			DESCRIPTION
				"It means urgent handover low rate period."
			DEFVAL { 2000 }
			::= { hwMeshProfileEntry 23 }


		-- 1.3.6.1.4.1.2011.6.139.4.37.1.24
		hwMeshProfileUrgentHandoverPunishmentPeriod OBJECT-TYPE
			SYNTAX Integer32 (0..10000)
			UNITS "ms"
			MAX-ACCESS read-write
			STATUS current
			DESCRIPTION
				"It means urgent handover punishment period."
			DEFVAL { 2000 }
			::= { hwMeshProfileEntry 24 }


		-- 1.3.6.1.4.1.2011.6.139.4.37.1.25
		hwMeshProfileUrgentHandoverPunishmentRssi OBJECT-TYPE
			SYNTAX Integer32 (0..50)
			UNITS "dB"
			MAX-ACCESS read-write
			STATUS current
			DESCRIPTION
				"It means urgent handover punishment severity."
			DEFVAL { 10 }
			::= { hwMeshProfileEntry 25 }

-- 1.3.6.1.4.1.2011.6.139.4.38
		-- 1.3.6.1.4.1.2011.6.139.4.38
		hwMeshVapManagementTable OBJECT-TYPE
			SYNTAX SEQUENCE OF HwMeshVapManagementEntry
			MAX-ACCESS not-accessible
			STATUS current
			DESCRIPTION
				"Description."
			::= { hwWlanServiceManagement 38 }

		-- 1.3.6.1.4.1.2011.6.139.4.38.1
		hwMeshVapManagementEntry OBJECT-TYPE
			SYNTAX HwMeshVapManagementEntry
			MAX-ACCESS not-accessible
			STATUS current
			DESCRIPTION
				"Description."
			INDEX { hwMeshVapApIndex, hwMeshVapRadioIndex, hwMeshVapMeshProfileName }
			::= { hwMeshVapManagementTable 1 }

		HwMeshVapManagementEntry ::=
			SEQUENCE {
				hwMeshVapApIndex
					Integer32,
				hwMeshVapRadioIndex
					Integer32,
				hwMeshVapMeshProfileName
					OCTET STRING,
				hwMeshVapRowStatus
					RowStatus,
				hwMeshVapBssid
					OCTET STRING
			 }

		-- 1.3.6.1.4.1.2011.6.139.4.38.1.1
		hwMeshVapApIndex OBJECT-TYPE
			SYNTAX Integer32
			MAX-ACCESS not-accessible
			STATUS current
			DESCRIPTION
				"Description."
			::= { hwMeshVapManagementEntry 1 }

		-- 1.3.6.1.4.1.2011.6.139.4.38.1.2
		hwMeshVapRadioIndex OBJECT-TYPE
			SYNTAX Integer32
			MAX-ACCESS not-accessible
			STATUS current
			DESCRIPTION
				"Description."
			::= { hwMeshVapManagementEntry 2 }

		-- 1.3.6.1.4.1.2011.6.139.4.38.1.3
		hwMeshVapMeshProfileName OBJECT-TYPE
			SYNTAX OCTET STRING (SIZE (1..31))
			MAX-ACCESS not-accessible
			STATUS current
			DESCRIPTION
				"Description."
			::= { hwMeshVapManagementEntry 3 }


		-- 1.3.6.1.4.1.2011.6.139.4.38.1.4
		hwMeshVapRowStatus OBJECT-TYPE
			SYNTAX RowStatus
			MAX-ACCESS read-write
			STATUS current
			DESCRIPTION
				"Description."
			::= { hwMeshVapManagementEntry 4 }

		hwMeshVapBssid OBJECT-TYPE
			SYNTAX OCTET STRING
			MAX-ACCESS read-only
			STATUS current
			DESCRIPTION
				"Description."
			::= { hwMeshVapManagementEntry 5 }

		-- 1.3.6.1.4.1.2011.6.139.4.39
		hwMacMeshVapManagementTable OBJECT-TYPE
			SYNTAX SEQUENCE OF HwMacMeshVapManagementEntry
			MAX-ACCESS not-accessible
			STATUS current
			DESCRIPTION
				"Description."
			::= { hwWlanServiceManagement 39 }

		-- 1.3.6.1.4.1.2011.6.139.4.39.1
		hwMacMeshVapManagementEntry OBJECT-TYPE
			SYNTAX HwMacMeshVapManagementEntry
			MAX-ACCESS not-accessible
			STATUS current
			DESCRIPTION
				"Description."
			INDEX { hwMacMeshVapApMac, hwMacMeshVapRadioIndex, hwMacMeshVapMeshProfileName }
			::= { hwMacMeshVapManagementTable 1 }

		HwMacMeshVapManagementEntry ::=
			SEQUENCE {
				hwMacMeshVapApMac
					MacAddress,
				hwMacMeshVapRadioIndex
					Integer32,
				hwMacMeshVapMeshProfileName
					OCTET STRING,
				hwMacMeshVapRowStatus
					RowStatus,
				hwMacMeshVapBssid
					OCTET STRING
			 }

		-- 1.3.6.1.4.1.2011.6.139.4.39.1.1
		hwMacMeshVapApMac OBJECT-TYPE
			SYNTAX MacAddress
			MAX-ACCESS not-accessible
			STATUS current
			DESCRIPTION
				"Description."
			::= { hwMacMeshVapManagementEntry 1 }

		-- 1.3.6.1.4.1.2011.6.139.4.39.1.2
		hwMacMeshVapRadioIndex OBJECT-TYPE
			SYNTAX Integer32
			MAX-ACCESS not-accessible
			STATUS current
			DESCRIPTION
				"Description."
			::= { hwMacMeshVapManagementEntry 2 }

		-- 1.3.6.1.4.1.2011.6.139.4.39.1.3
		hwMacMeshVapMeshProfileName OBJECT-TYPE
			SYNTAX OCTET STRING (SIZE (1..31))
			MAX-ACCESS not-accessible
			STATUS current
			DESCRIPTION
				"Description."
			::= { hwMacMeshVapManagementEntry 3 }


		-- 1.3.6.1.4.1.2011.6.139.4.39.1.4
		hwMacMeshVapRowStatus OBJECT-TYPE
			SYNTAX RowStatus
			MAX-ACCESS read-write
			STATUS current
			DESCRIPTION
				"Description."
			::= { hwMacMeshVapManagementEntry 4 }

		hwMacMeshVapBssid OBJECT-TYPE
			SYNTAX OCTET STRING
			MAX-ACCESS read-only
			STATUS current
			DESCRIPTION
				"Description."
			::= { hwMacMeshVapManagementEntry 5 }

		-- 1.3.6.1.4.1.2011.6.139.4.40
		hwMeshLinkTable OBJECT-TYPE
			SYNTAX SEQUENCE OF HwMeshLinkEntry
			MAX-ACCESS not-accessible
			STATUS current
			DESCRIPTION
				"Description."
			::= { hwWlanServiceManagement 40 }

		-- 1.3.6.1.4.1.2011.6.139.4.40.1
		hwMeshLinkEntry OBJECT-TYPE
			SYNTAX HwMeshLinkEntry
			MAX-ACCESS not-accessible
			STATUS current
			DESCRIPTION
				"Description."
			INDEX { hwMeshVapApIndex, hwMeshVapRadioIndex, hwMeshLinkIndex }
			::= { hwMeshLinkTable 1 }

		HwMeshLinkEntry ::=
			SEQUENCE {
				hwMeshLinkIndex
					Integer32,
				hwMeshLinkWlanID
					Integer32,
				hwMeshLinkPeerMac
					MacAddress,
				hwMeshLinkChannelID
					Integer32,
				hwMeshLinkRssiValue
					Integer32,
				hwMeshLinkApMac
					MacAddress,
				hwMeshLinkMeshRole
					INTEGER,
				hwMeshLinkCoverageDistance
					Integer32,
				hwMeshLinkPeerAPID
					Integer32,
				hwMeshLinkPeerAPStatus
					INTEGER,
				hwMeshLinkMaxRssi
					Integer32,
				hwMeshLinkPeerApMac
					MacAddress
			 }

		-- 1.3.6.1.4.1.2011.6.139.4.40.1.1
		hwMeshLinkIndex OBJECT-TYPE
			SYNTAX Integer32
			MAX-ACCESS not-accessible
			STATUS current
			DESCRIPTION
				"Description."
			::= { hwMeshLinkEntry 1 }

		-- 1.3.6.1.4.1.2011.6.139.4.40.1.2
		hwMeshLinkWlanID OBJECT-TYPE
			SYNTAX Integer32
			MAX-ACCESS read-only
			STATUS current
			DESCRIPTION
				"Description."
			::= { hwMeshLinkEntry 2 }

		-- 1.3.6.1.4.1.2011.6.139.4.40.1.3
		hwMeshLinkPeerMac OBJECT-TYPE
			SYNTAX MacAddress
			MAX-ACCESS read-only
			STATUS current
			DESCRIPTION
				"Description."
			::= { hwMeshLinkEntry 3 }

		-- 1.3.6.1.4.1.2011.6.139.4.40.1.4
		hwMeshLinkChannelID OBJECT-TYPE
			SYNTAX Integer32
			MAX-ACCESS read-only
			STATUS current
			DESCRIPTION
				"Description."
			::= { hwMeshLinkEntry 4 }

		-- 1.3.6.1.4.1.2011.6.139.4.40.1.5
		hwMeshLinkRssiValue OBJECT-TYPE
			SYNTAX Integer32
			MAX-ACCESS read-only
			STATUS current
			DESCRIPTION
				"Description."
			::= { hwMeshLinkEntry 5 }

--  1.3.6.1.4.1.2011.6.139.4.40.1.6
		-- 1.3.6.1.4.1.2011.6.139.4.40.1.6
		hwMeshLinkApMac OBJECT-TYPE
			SYNTAX MacAddress
			MAX-ACCESS read-only
			STATUS current
			DESCRIPTION
				"It means AP mac."
			::= { hwMeshLinkEntry 6 }


--  1.3.6.1.4.1.2011.6.139.4.40.1.7
		-- 1.3.6.1.4.1.2011.6.139.4.40.1.7
		hwMeshLinkMeshRole OBJECT-TYPE
			SYNTAX INTEGER
				{
				meshNode(1),
				meshPortal(2)
				}
			MAX-ACCESS read-only
			STATUS current
			DESCRIPTION
				"It means mesh role."
			DEFVAL { 1 }
			::= { hwMeshLinkEntry 7 }


--  1.3.6.1.4.1.2011.6.139.4.40.1.8
		-- 1.3.6.1.4.1.2011.6.139.4.40.1.8
		hwMeshLinkCoverageDistance OBJECT-TYPE
			SYNTAX Integer32
			MAX-ACCESS read-only
			STATUS current
			DESCRIPTION
				"It means coverage distance."
			::= { hwMeshLinkEntry 8 }


--  1.3.6.1.4.1.2011.6.139.4.40.1.9
		-- 1.3.6.1.4.1.2011.6.139.4.40.1.9
		hwMeshLinkPeerAPID OBJECT-TYPE
			SYNTAX Integer32
			MAX-ACCESS read-only
			STATUS current
			DESCRIPTION
				"It means peer AP ID."
			::= { hwMeshLinkEntry 9 }


--  1.3.6.1.4.1.2011.6.139.4.40.1.10
		-- 1.3.6.1.4.1.2011.6.139.4.40.1.10
		hwMeshLinkPeerAPStatus OBJECT-TYPE
			SYNTAX INTEGER
				{
				idle(1),
				autoFind(2),
				typeNotMatch(3),
				verMismatch(4),
				fault(5),
				config(6),
				commitFailed(7),
				download(8),
				standby(9),
				normal(10),
				committing(11),
				configFailed(12),
				invalid(13)
				}
			MAX-ACCESS read-only
			STATUS current
			DESCRIPTION
				"It means peer AP status."
			::= { hwMeshLinkEntry 10 }


--  1.3.6.1.4.1.2011.6.139.4.40.1.11
		-- 1.3.6.1.4.1.2011.6.139.4.40.1.11
		hwMeshLinkMaxRssi OBJECT-TYPE
			SYNTAX Integer32
			MAX-ACCESS read-only
			STATUS current
			DESCRIPTION
				"It means max rssi."
			::= { hwMeshLinkEntry 11 }


--  1.3.6.1.4.1.2011.6.139.4.40.1.12
		-- 1.3.6.1.4.1.2011.6.139.4.40.1.12
		hwMeshLinkPeerApMac OBJECT-TYPE
			SYNTAX MacAddress
			MAX-ACCESS read-only
			STATUS current
			DESCRIPTION
				"It means peer ap mac."
			::= { hwMeshLinkEntry 12 }


--  1.3.6.1.4.1.2011.6.139.4.41
		-- 1.3.6.1.4.1.2011.6.139.4.41
		hwMacMeshLinkTable OBJECT-TYPE
			SYNTAX SEQUENCE OF HwMacMeshLinkEntry
			MAX-ACCESS not-accessible
			STATUS current
			DESCRIPTION
				"Description."
			::= { hwWlanServiceManagement 41 }

		-- 1.3.6.1.4.1.2011.6.139.4.41.1
		hwMacMeshLinkEntry OBJECT-TYPE
			SYNTAX HwMacMeshLinkEntry
			MAX-ACCESS not-accessible
			STATUS current
			DESCRIPTION
				"Description."
			INDEX { hwMacMeshVapApMac, hwMacMeshVapRadioIndex, hwMacMeshLinkIndex }
			::= { hwMacMeshLinkTable 1 }

		HwMacMeshLinkEntry ::=
			SEQUENCE {
				hwMacMeshLinkIndex
					Integer32,
				hwMacMeshLinkWlanID
					Integer32,
				hwMacMeshLinkPeerMac
					MacAddress,
				hwMacMeshLinkChannelID
					Integer32,
				hwMacMeshLinkRssiValue
					Integer32,
				hwMacMeshLinkApID
					Integer32,
				hwMacMeshLinkMeshRole
					INTEGER,
				hwMacMeshLinkCoverageDistance
					Integer32,
				hwMacMeshLinkPeerAPID
					Integer32,
				hwMacMeshLinkPeerAPStatus
					INTEGER,
				hwMacMeshLinkMaxRssi
					Integer32,
				hwMacMeshLinkPeerApMac
					MacAddress
			 }

		-- 1.3.6.1.4.1.2011.6.139.4.41.1.1
		hwMacMeshLinkIndex OBJECT-TYPE
			SYNTAX Integer32
			MAX-ACCESS not-accessible
			STATUS current
			DESCRIPTION
				"Description."
			::= { hwMacMeshLinkEntry 1 }

		-- 1.3.6.1.4.1.2011.6.139.4.41.1.2
		hwMacMeshLinkWlanID OBJECT-TYPE
			SYNTAX Integer32
			MAX-ACCESS read-only
			STATUS current
			DESCRIPTION
				"Description."
			::= { hwMacMeshLinkEntry 2 }

		-- 1.3.6.1.4.1.2011.6.139.4.41.1.3
		hwMacMeshLinkPeerMac OBJECT-TYPE
			SYNTAX MacAddress
			MAX-ACCESS read-only
			STATUS current
			DESCRIPTION
				"Description."
			::= { hwMacMeshLinkEntry 3 }


		-- 1.3.6.1.4.1.2011.6.139.4.41.1.4
		hwMacMeshLinkChannelID OBJECT-TYPE
			SYNTAX Integer32
			MAX-ACCESS read-only
			STATUS current
			DESCRIPTION
				"Description."
			::= { hwMacMeshLinkEntry 4 }


		-- 1.3.6.1.4.1.2011.6.139.4.41.1.5
		hwMacMeshLinkRssiValue OBJECT-TYPE
			SYNTAX Integer32
			MAX-ACCESS read-only
			STATUS current
			DESCRIPTION
				"Description."
			::= { hwMacMeshLinkEntry 5 }


--  1.3.6.1.4.1.2011.6.139.4.41.1.6
		-- 1.3.6.1.4.1.2011.6.139.4.41.1.6
		hwMacMeshLinkApID OBJECT-TYPE
			SYNTAX Integer32
			MAX-ACCESS read-only
			STATUS current
			DESCRIPTION
				"It means AP ID."
			::= { hwMacMeshLinkEntry 6 }


--  1.3.6.1.4.1.2011.6.139.4.41.1.7
		-- 1.3.6.1.4.1.2011.6.139.4.41.1.7
		hwMacMeshLinkMeshRole OBJECT-TYPE
			SYNTAX INTEGER
				{
				meshNode(1),
				meshPortal(2)
				}
			MAX-ACCESS read-only
			STATUS current
			DESCRIPTION
				"It means mesh role."
			::= { hwMacMeshLinkEntry 7 }


--  1.3.6.1.4.1.2011.6.139.4.41.1.8
		-- 1.3.6.1.4.1.2011.6.139.4.41.1.8
		hwMacMeshLinkCoverageDistance OBJECT-TYPE
			SYNTAX Integer32
			MAX-ACCESS read-only
			STATUS current
			DESCRIPTION
				"It means coverage distance."
			::= { hwMacMeshLinkEntry 8 }


--  1.3.6.1.4.1.2011.6.139.4.41.1.9
		-- 1.3.6.1.4.1.2011.6.139.4.41.1.9
		hwMacMeshLinkPeerAPID OBJECT-TYPE
			SYNTAX Integer32
			MAX-ACCESS read-only
			STATUS current
			DESCRIPTION
				"It means peer AP ID."
			::= { hwMacMeshLinkEntry 9 }


--  1.3.6.1.4.1.2011.6.139.4.41.1.10
		-- 1.3.6.1.4.1.2011.6.139.4.41.1.10
		hwMacMeshLinkPeerAPStatus OBJECT-TYPE
			SYNTAX INTEGER
				{
				idle(1),
				autoFind(2),
				typeNotMatch(3),
				verMismatch(4),
				fault(5),
				config(6),
				commitFailed(7),
				download(8),
				standby(9),
				normal(10),
				committing(11),
				configFailed(12),
				invalid(13)
				}
			MAX-ACCESS read-only
			STATUS current
			DESCRIPTION
				"It means peer AP status."
			::= { hwMacMeshLinkEntry 10 }


--  1.3.6.1.4.1.2011.6.139.4.41.1.11
		-- 1.3.6.1.4.1.2011.6.139.4.41.1.11
		hwMacMeshLinkMaxRssi OBJECT-TYPE
			SYNTAX Integer32
			MAX-ACCESS read-only
			STATUS current
			DESCRIPTION
				"It means max rssi."
			::= { hwMacMeshLinkEntry 11 }


--  1.3.6.1.4.1.2011.6.139.4.41.1.12
		-- 1.3.6.1.4.1.2011.6.139.4.41.1.12
		hwMacMeshLinkPeerApMac OBJECT-TYPE
			SYNTAX MacAddress
			MAX-ACCESS read-only
			STATUS current
			DESCRIPTION
				"It means peer AP mac."
			::= { hwMacMeshLinkEntry 12 }


--  1.3.6.1.4.1.2011.6.139.4.42
		-- 1.3.6.1.4.1.2011.6.139.4.42
		hwMeshWhitelistTable OBJECT-TYPE
			SYNTAX SEQUENCE OF HwMeshWhitelistEntry
			MAX-ACCESS not-accessible
			STATUS current
			DESCRIPTION
				"Description."
			::= { hwWlanServiceManagement 42 }


		-- 1.3.6.1.4.1.2011.6.139.4.42.1
		hwMeshWhitelistEntry OBJECT-TYPE
			SYNTAX HwMeshWhitelistEntry
			MAX-ACCESS not-accessible
			STATUS current
			DESCRIPTION
				"Description."
			INDEX { hwMeshWhitelistName }
			::= { hwMeshWhitelistTable 1 }


		HwMeshWhitelistEntry ::=
			SEQUENCE {
				hwMeshWhitelistName
					OCTET STRING,
				hwMeshWhitelistPeerList
					OCTET STRING,
				hwMeshWhitelistRowStatus
					RowStatus
			 }

		-- 1.3.6.1.4.1.2011.6.139.4.42.1.1
		hwMeshWhitelistName OBJECT-TYPE
			SYNTAX OCTET STRING (SIZE (1..31))
			MAX-ACCESS not-accessible
			STATUS current
			DESCRIPTION
				"Description."
			::= { hwMeshWhitelistEntry 1 }


		-- 1.3.6.1.4.1.2011.6.139.4.42.1.2
		hwMeshWhitelistPeerList OBJECT-TYPE
			SYNTAX OCTET STRING (SIZE (0..8193))
			MAX-ACCESS read-create
			STATUS current
			DESCRIPTION
				"Description."
			::= { hwMeshWhitelistEntry 2 }


		-- 1.3.6.1.4.1.2011.6.139.4.42.1.3
		hwMeshWhitelistRowStatus OBJECT-TYPE
			SYNTAX RowStatus
			MAX-ACCESS read-create
			STATUS current
			DESCRIPTION
				"Description."
			::= { hwMeshWhitelistEntry 3 }

		hwWlanServiceManagementObject OBJECT IDENTIFIER ::= { hwWlanServiceManagement 43 }

		-- BEGIN: Added by lishijun 00209691 on 2013-09-17, for tag device management
		-- 1.3.6.1.4.1.2011.6.139.4.43.1
		hwLbsTagDevTable OBJECT-TYPE
			SYNTAX SEQUENCE OF HwLbsTagDevEntry
			MAX-ACCESS not-accessible
			STATUS current
			DESCRIPTION
				"Tag device management"
			::= { hwWlanServiceManagementObject 1 }


		-- 1.3.6.1.4.1.2011.6.139.4.43.1.1
		hwLbsTagDevEntry OBJECT-TYPE
			SYNTAX HwLbsTagDevEntry
			MAX-ACCESS not-accessible
			STATUS current
			DESCRIPTION
				"Description."
			INDEX { hwLbsTagDevApID, hwLbsTagDevMac }
			::= { hwLbsTagDevTable 1 }


		HwLbsTagDevEntry ::=
			SEQUENCE {
				hwLbsTagDevApID
					Integer32,
				hwLbsTagDevMac
					MacAddress,
				hwLbsTagDevType
					Integer32,
				hwLbsTagDevChannel
					Integer32,
				hwLbsTagDevRssi
					Integer32
			 }

		-- 1.3.6.1.4.1.2011.6.139.4.43.1.1.1
		hwLbsTagDevApID OBJECT-TYPE
			SYNTAX Integer32
			MAX-ACCESS not-accessible
			STATUS current
			DESCRIPTION
				"Description."
			::= { hwLbsTagDevEntry 1 }

		-- 1.3.6.1.4.1.2011.6.139.4.43.1.1.2
		hwLbsTagDevMac OBJECT-TYPE
			SYNTAX MacAddress
			MAX-ACCESS not-accessible
			STATUS current
			DESCRIPTION
				"Description."
			::= { hwLbsTagDevEntry 2 }

		-- 1.3.6.1.4.1.2011.6.139.4.43.1.1.3
		hwLbsTagDevType OBJECT-TYPE
			SYNTAX Integer32
			MAX-ACCESS read-only
			STATUS current
			DESCRIPTION
				"Tag Type: 1 - AeroScout, 2 - Ekahau"
			::= { hwLbsTagDevEntry 3 }

		-- 1.3.6.1.4.1.2011.6.139.4.43.1.1.4
		hwLbsTagDevChannel OBJECT-TYPE
			SYNTAX Integer32
			MAX-ACCESS read-only
			STATUS current
			DESCRIPTION
				"Description."
			::= { hwLbsTagDevEntry 4 }

		-- 1.3.6.1.4.1.2011.6.139.4.43.1.1.5
		hwLbsTagDevRssi OBJECT-TYPE
			SYNTAX Integer32
			MAX-ACCESS read-only
			STATUS current
			DESCRIPTION
				"Description."
			::= { hwLbsTagDevEntry 5 }


--  1.3.6.1.4.1.2011.6.139.4.43.2
		-- 1.3.6.1.4.1.2011.6.139.4.43.2
		hwProxyTrackSideEquipTable OBJECT-TYPE
			SYNTAX SEQUENCE OF HwProxyTrackSideEquipEntry
			MAX-ACCESS not-accessible
			STATUS current
			DESCRIPTION
				"the table means proxy track side equipment info."
			::= { hwWlanServiceManagementObject 2 }


--  1.3.6.1.4.1.2011.6.139.4.43.2.1
		-- 1.3.6.1.4.1.2011.6.139.4.43.2.1
		hwProxyTrackSideEquipEntry OBJECT-TYPE
			SYNTAX HwProxyTrackSideEquipEntry
			MAX-ACCESS not-accessible
			STATUS current
			DESCRIPTION
				"Description."
			INDEX { hwProxyTrackSideEquipIndex }
			::= { hwProxyTrackSideEquipTable 1 }


		HwProxyTrackSideEquipEntry ::=
			SEQUENCE {
				hwProxyTrackSideEquipIndex
					Integer32,
				hwProxyTrackSideEquipMac
					MacAddress,
				hwProxyTrackSideEquipVlanID
					Integer32,
				hwProxyTrackSideEquipRowStatus
					RowStatus
			 }

--  1.3.6.1.4.1.2011.6.139.4.43.2.1.1
		-- 1.3.6.1.4.1.2011.6.139.4.43.2.1.1
		hwProxyTrackSideEquipIndex OBJECT-TYPE
			SYNTAX Integer32
			MAX-ACCESS not-accessible
			STATUS current
			DESCRIPTION
				"It means proxy track side equipment index."
			::= { hwProxyTrackSideEquipEntry 1 }


--  1.3.6.1.4.1.2011.6.139.4.43.2.1.2
		-- 1.3.6.1.4.1.2011.6.139.4.43.2.1.2
		hwProxyTrackSideEquipMac OBJECT-TYPE
			SYNTAX MacAddress
			MAX-ACCESS read-write
			STATUS current
			DESCRIPTION
				"It means the mac address of proxy track side equipment."
			::= { hwProxyTrackSideEquipEntry 2 }


--  1.3.6.1.4.1.2011.6.139.4.43.2.1.3
		-- 1.3.6.1.4.1.2011.6.139.4.43.2.1.3
		hwProxyTrackSideEquipVlanID OBJECT-TYPE
			SYNTAX Integer32 (1..4094)
			MAX-ACCESS read-write
			STATUS current
			DESCRIPTION
				"It means the vlan id of proxy track side equipment."
			::= { hwProxyTrackSideEquipEntry 3 }

		-- 1.3.6.1.4.1.2011.6.139.4.43.2.1.4
		hwProxyTrackSideEquipRowStatus OBJECT-TYPE
			SYNTAX RowStatus
			MAX-ACCESS read-create
			STATUS current
			DESCRIPTION
				"It means row status of the table."
			::= { hwProxyTrackSideEquipEntry 4 }


--  1.3.6.1.4.1.2011.6.139.4.43.3
		-- 1.3.6.1.4.1.2011.6.139.4.43.3
		hwProxyOnBoardEquipTable OBJECT-TYPE
			SYNTAX SEQUENCE OF HwProxyOnBoardEquipEntry
			MAX-ACCESS not-accessible
			STATUS current
			DESCRIPTION
				"It means proxy on-board equipment table."
			::= { hwWlanServiceManagementObject 3 }


--  1.3.6.1.4.1.2011.6.139.4.43.3.1
		-- 1.3.6.1.4.1.2011.6.139.4.43.3.1
		hwProxyOnBoardEquipEntry OBJECT-TYPE
			SYNTAX HwProxyOnBoardEquipEntry
			MAX-ACCESS not-accessible
			STATUS current
			DESCRIPTION
				"It means proxy on-board equipment entry."
			INDEX { hwProxyOnBoardEquipIndex }
			::= { hwProxyOnBoardEquipTable 1 }


		HwProxyOnBoardEquipEntry ::=
			SEQUENCE {
				hwProxyOnBoardEquipIndex
					Integer32,
				hwProxyOnBoardEquipMac
					MacAddress,
				hwProxyOnBoardEquipVlanID
					Integer32,
				hwProxyOnBoardEquipRowStatus
					RowStatus
			 }

--  1.3.6.1.4.1.2011.6.139.4.43.3.1.1
		-- 1.3.6.1.4.1.2011.6.139.4.43.3.1.1
		hwProxyOnBoardEquipIndex OBJECT-TYPE
			SYNTAX Integer32
			MAX-ACCESS not-accessible
			STATUS current
			DESCRIPTION
				"It means proxy on-board equipment index."
			::= { hwProxyOnBoardEquipEntry 1 }


--  1.3.6.1.4.1.2011.6.139.4.43.3.1.2
		-- 1.3.6.1.4.1.2011.6.139.4.43.3.1.2
		hwProxyOnBoardEquipMac OBJECT-TYPE
			SYNTAX MacAddress
			MAX-ACCESS read-write
			STATUS current
			DESCRIPTION
				"It means mac address of proxy on-board equipment."
			::= { hwProxyOnBoardEquipEntry 2 }


--  1.3.6.1.4.1.2011.6.139.4.43.3.1.3
		-- 1.3.6.1.4.1.2011.6.139.4.43.3.1.3
		hwProxyOnBoardEquipVlanID OBJECT-TYPE
			SYNTAX Integer32 (1..4094)
			MAX-ACCESS read-write
			STATUS current
			DESCRIPTION
				"It means vlan id of the proxy on-board equipment."
			::= { hwProxyOnBoardEquipEntry 3 }

		-- 1.3.6.1.4.1.2011.6.139.4.43.3.1.4
		hwProxyOnBoardEquipRowStatus OBJECT-TYPE
			SYNTAX RowStatus
			MAX-ACCESS read-create
			STATUS current
			DESCRIPTION
				"It means row status of table."
			::= { hwProxyOnBoardEquipEntry 4 }


--  1.3.6.1.4.1.2011.6.139.4.43.4
		-- 1.3.6.1.4.1.2011.6.139.4.43.4
		hwHandoverTraceTable OBJECT-TYPE
			SYNTAX SEQUENCE OF HwHandoverTraceEntry
			MAX-ACCESS not-accessible
			STATUS current
			DESCRIPTION
				"It means handover trace table of mesh."
			::= { hwWlanServiceManagementObject 4 }


--  1.3.6.1.4.1.2011.6.139.4.43.4.1
		-- 1.3.6.1.4.1.2011.6.139.4.43.4.1
		hwHandoverTraceEntry OBJECT-TYPE
			SYNTAX HwHandoverTraceEntry
			MAX-ACCESS not-accessible
			STATUS current
			DESCRIPTION
				"Description."
			INDEX { hwHandoverTraceIndex }
			::= { hwHandoverTraceTable 1 }


		HwHandoverTraceEntry ::=
			SEQUENCE {
				hwHandoverTraceIndex
					Integer32,
				hwHandoverTimeStamp
					OCTET STRING,
				hwHandoverFromApMac
					MacAddress,
				hwHandoverFromApRssi
					Integer32,
				hwHandoverToApMac
					MacAddress,
				hwHandoverToApRssi
					Integer32,
				hwHandoverFromApLocationID
					Unsigned32,
				hwHandoverToApLocationID
					Unsigned32
			 }

--  1.3.6.1.4.1.2011.6.139.4.43.4.1.1
		-- 1.3.6.1.4.1.2011.6.139.4.43.4.1.1
		hwHandoverTraceIndex OBJECT-TYPE
			SYNTAX Integer32
			MAX-ACCESS not-accessible
			STATUS current
			DESCRIPTION
				"It means handover trace index."
			::= { hwHandoverTraceEntry 1 }


--  1.3.6.1.4.1.2011.6.139.4.43.4.1.2
		-- 1.3.6.1.4.1.2011.6.139.4.43.4.1.2
		hwHandoverTimeStamp OBJECT-TYPE
			SYNTAX OCTET STRING (SIZE (1..20))
			MAX-ACCESS read-only
			STATUS current
			DESCRIPTION
				"It means the time stamp of handover trace."
			::= { hwHandoverTraceEntry 2 }


--  1.3.6.1.4.1.2011.6.139.4.43.4.1.3
		-- 1.3.6.1.4.1.2011.6.139.4.43.4.1.3
		hwHandoverFromApMac OBJECT-TYPE
			SYNTAX MacAddress
			MAX-ACCESS read-only
			STATUS current
			DESCRIPTION
				"It means the mac address of source AP for handover trace."
			::= { hwHandoverTraceEntry 3 }


--  1.3.6.1.4.1.2011.6.139.4.43.4.1.4
		-- 1.3.6.1.4.1.2011.6.139.4.43.4.1.4
		hwHandoverFromApRssi OBJECT-TYPE
			SYNTAX Integer32
			MAX-ACCESS read-only
			STATUS current
			DESCRIPTION
				"It means the rssi of source AP for handover trace."
			::= { hwHandoverTraceEntry 4 }


--  1.3.6.1.4.1.2011.6.139.4.43.4.1.5
		-- 1.3.6.1.4.1.2011.6.139.4.43.4.1.5
		hwHandoverToApMac OBJECT-TYPE
			SYNTAX MacAddress
			MAX-ACCESS read-only
			STATUS current
			DESCRIPTION
				"It means the mac address of destination AP for handover trace."
			::= { hwHandoverTraceEntry 5 }


--  1.3.6.1.4.1.2011.6.139.4.43.4.1.6
		-- 1.3.6.1.4.1.2011.6.139.4.43.4.1.6
		hwHandoverToApRssi OBJECT-TYPE
			SYNTAX Integer32
			MAX-ACCESS read-only
			STATUS current
			DESCRIPTION
				"It means the rssi of destination AP for handover trace."
			::= { hwHandoverTraceEntry 6 }


		-- 1.3.6.1.4.1.2011.6.139.4.43.4.1.7
		hwHandoverFromApLocationID OBJECT-TYPE
			SYNTAX Unsigned32 (0..65536)
			MAX-ACCESS read-only
			STATUS current
			DESCRIPTION
				"It means the location ID of sourse ap."
			::= { hwHandoverTraceEntry 7 }


		-- 1.3.6.1.4.1.2011.6.139.4.43.4.1.8
		hwHandoverToApLocationID OBJECT-TYPE
			SYNTAX Unsigned32 (0..65536)
			MAX-ACCESS read-only
			STATUS current
			DESCRIPTION
				"It means the location ID of destination ap."
			::= { hwHandoverTraceEntry 8 }
--  1.3.6.1.4.1.2011.6.139.4.43.5
		-- 1.3.6.1.4.1.2011.6.139.4.43.5
		hwNeighborApTable OBJECT-TYPE
			SYNTAX SEQUENCE OF HwNeighborApEntry
			MAX-ACCESS not-accessible
			STATUS current
			DESCRIPTION
				"Description."
			::= { hwWlanServiceManagementObject 5 }


--  1.3.6.1.4.1.2011.6.139.4.43.5.1
		-- 1.3.6.1.4.1.2011.6.139.4.43.5.1
		hwNeighborApEntry OBJECT-TYPE
			SYNTAX HwNeighborApEntry
			MAX-ACCESS not-accessible
			STATUS current
			DESCRIPTION
				"Description."
			INDEX { hwNeighborApLocalApId, hwNeighborApLocalRadioId }
			::= { hwNeighborApTable 1 }


		HwNeighborApEntry ::=
			SEQUENCE {
				hwNeighborApLocalApId
					Integer32,
				hwNeighborApLocalRadioId
					Integer32,
				hwNeighborApLocalApMac
					MacAddress,
				hwNeighborApIdList
					OCTET STRING,
				hwNeighborApMacList
					OCTET STRING,
				hwNeighborApRssiList
					OCTET STRING,
				hwNeighborApUpdateTime
					OCTET STRING,
				hwNeighborApLocalLocationID
					Unsigned32,
				hwNeighborApLocationIDList
					OCTET STRING
			 }

--  1.3.6.1.4.1.2011.6.139.4.43.5.1.1
		-- 1.3.6.1.4.1.2011.6.139.4.43.5.1.1
		hwNeighborApLocalApId OBJECT-TYPE
			SYNTAX Integer32
			MAX-ACCESS not-accessible
			STATUS current
			DESCRIPTION
				"It means the local ap id."
			::= { hwNeighborApEntry 1 }


		-- 1.3.6.1.4.1.2011.6.139.4.43.5.1.2
		hwNeighborApLocalRadioId OBJECT-TYPE
			SYNTAX Integer32
			MAX-ACCESS not-accessible
			STATUS current
			DESCRIPTION
				"It means the local radio id."
			::= { hwNeighborApEntry 2 }


		-- 1.3.6.1.4.1.2011.6.139.4.43.5.1.3
		hwNeighborApLocalApMac OBJECT-TYPE
			SYNTAX MacAddress
			MAX-ACCESS read-only
			STATUS current
			DESCRIPTION
				"It means the local ap mac address."
			::= { hwNeighborApEntry 3 }


		-- 1.3.6.1.4.1.2011.6.139.4.43.5.1.4
		hwNeighborApIdList OBJECT-TYPE
			SYNTAX OCTET STRING (SIZE (0..1280))
			MAX-ACCESS read-only
			STATUS current
			DESCRIPTION
				"It means the list of all of neighbor ap id."
			::= { hwNeighborApEntry 4 }


		-- 1.3.6.1.4.1.2011.6.139.4.43.5.1.5
		hwNeighborApMacList OBJECT-TYPE
			SYNTAX OCTET STRING (SIZE (0..3840))
			MAX-ACCESS read-only
			STATUS current
			DESCRIPTION
				"It means the list of all of ap mac."
			::= { hwNeighborApEntry 5 }


		-- 1.3.6.1.4.1.2011.6.139.4.43.5.1.6
		hwNeighborApRssiList OBJECT-TYPE
			SYNTAX OCTET STRING (SIZE (0..1280))
			MAX-ACCESS read-only
			STATUS current
			DESCRIPTION
				"It means the list of all of ap rssi."
			::= { hwNeighborApEntry 6 }


		-- 1.3.6.1.4.1.2011.6.139.4.43.5.1.7
		hwNeighborApUpdateTime OBJECT-TYPE
			SYNTAX OCTET STRING (SIZE (0..5120))
			MAX-ACCESS read-only
			STATUS current
			DESCRIPTION
				"It means the list of all of ap update time."
			::= { hwNeighborApEntry 7 }


		-- 1.3.6.1.4.1.2011.6.139.4.43.5.1.8
		hwNeighborApLocalLocationID OBJECT-TYPE
			SYNTAX Unsigned32 (0..65536)
			MAX-ACCESS read-only
			STATUS current
			DESCRIPTION
				"It means the local ap location ID."
			::= { hwNeighborApEntry 8 }


		-- 1.3.6.1.4.1.2011.6.139.4.43.5.1.9
		hwNeighborApLocationIDList OBJECT-TYPE
			SYNTAX OCTET STRING (SIZE (0..1550))
			MAX-ACCESS read-only
			STATUS current
			DESCRIPTION
				"It means the list of neighbor ap location ID based on radio."
			::= { hwNeighborApEntry 9 }

		-- 1.3.6.1.4.1.2011.6.139.4.43.6
		hwStaOnlineFailTable OBJECT-TYPE
			SYNTAX SEQUENCE OF HwStaOnlineFailEntry
			MAX-ACCESS not-accessible
			STATUS current
			DESCRIPTION
				"Description."
			::= { hwWlanServiceManagementObject 6 }


		-- 1.3.6.1.4.1.2011.6.139.4.43.6.1
		hwStaOnlineFailEntry OBJECT-TYPE
			SYNTAX HwStaOnlineFailEntry
			MAX-ACCESS not-accessible
			STATUS current
			DESCRIPTION
				"Description."
			INDEX { hwStaOnlineFailMacAddress, hwStaOnlineFailReasonIndex }
			::= { hwStaOnlineFailTable 1 }


		HwStaOnlineFailEntry ::=
			SEQUENCE {
				hwStaOnlineFailMacAddress
					MacAddress,
				hwStaOnlineFailReasonIndex
					Integer32,
				hwStaOnlineFailApId
					Integer32,
				hwStaOnlineFailRadioId
					Integer32,
				hwStaOnlineFailWlanId
					Integer32,
				hwStaOnlineFailLastFailTime
					OCTET STRING,
				hwStaOnlineFailReason
					OCTET STRING,
				hwStaOnlineFailRowStatus
					RowStatus
			 }

		-- 1.3.6.1.4.1.2011.6.139.4.43.6.1.1
		hwStaOnlineFailMacAddress OBJECT-TYPE
			SYNTAX MacAddress
			MAX-ACCESS not-accessible
			STATUS current
			DESCRIPTION
				"Description."
			::= { hwStaOnlineFailEntry 1 }


		-- 1.3.6.1.4.1.2011.6.139.4.43.6.1.2
		hwStaOnlineFailReasonIndex OBJECT-TYPE
			SYNTAX Integer32 (0..2)
			MAX-ACCESS not-accessible
			STATUS current
			DESCRIPTION
				"Description."
			::= { hwStaOnlineFailEntry 2 }


		-- 1.3.6.1.4.1.2011.6.139.4.43.6.1.3
		hwStaOnlineFailApId OBJECT-TYPE
			SYNTAX Integer32
			MAX-ACCESS read-only
			STATUS current
			DESCRIPTION
				"Description."
			::= { hwStaOnlineFailEntry 3 }


		-- 1.3.6.1.4.1.2011.6.139.4.43.6.1.4
		hwStaOnlineFailRadioId OBJECT-TYPE
			SYNTAX Integer32
			MAX-ACCESS read-only
			STATUS current
			DESCRIPTION
				"Description."
			::= { hwStaOnlineFailEntry 4 }


		-- 1.3.6.1.4.1.2011.6.139.4.43.6.1.5
		hwStaOnlineFailWlanId OBJECT-TYPE
			SYNTAX Integer32
			MAX-ACCESS read-only
			STATUS current
			DESCRIPTION
				"Description."
			::= { hwStaOnlineFailEntry 5 }


		-- 1.3.6.1.4.1.2011.6.139.4.43.6.1.6
		hwStaOnlineFailLastFailTime OBJECT-TYPE
			SYNTAX OCTET STRING
			MAX-ACCESS read-only
			STATUS current
			DESCRIPTION
				"Description."
			::= { hwStaOnlineFailEntry 6 }


		-- 1.3.6.1.4.1.2011.6.139.4.43.6.1.7
		hwStaOnlineFailReason OBJECT-TYPE
			SYNTAX OCTET STRING
			MAX-ACCESS read-only
			STATUS current
			DESCRIPTION
				"Description."
			::= { hwStaOnlineFailEntry 7 }


		-- 1.3.6.1.4.1.2011.6.139.4.43.6.1.8
		hwStaOnlineFailRowStatus OBJECT-TYPE
			SYNTAX RowStatus
			MAX-ACCESS read-write
			STATUS current
			DESCRIPTION
				"Description."
			::= { hwStaOnlineFailEntry 8 }


		-- 1.3.6.1.4.1.2011.6.139.4.43.7
		hwStaOnlineFailTableInfo OBJECT IDENTIFIER ::= { hwWlanServiceManagementObject 7 }


		-- 1.3.6.1.4.1.2011.6.139.4.43.7.1
		hwStaResetAllOnlineFailTableReason OBJECT-TYPE
			SYNTAX INTEGER { reset(1) }
			MAX-ACCESS read-write
			STATUS current
			DESCRIPTION
				"Description."
			::= { hwStaOnlineFailTableInfo 1 }


--  END:   Added by lishijun 00209691 on 2013-09-17, for tag device management


		hwWlanServiceManagementConformance OBJECT IDENTIFIER ::= { hwWlanServiceManagement 44 }

		hwWlanServiceManagementCompliances OBJECT IDENTIFIER ::= { hwWlanServiceManagementConformance 1 }

		hwWlanServiceManagementCompliance MODULE-COMPLIANCE
			STATUS current
			DESCRIPTION
				"Description."
			MODULE -- this module
			    MANDATORY-GROUPS { hwEssManagementGroup, hwVapManagementGroup, hwServiceBatchGroup, hwCapwapConfigManagementGroup, hwStationGroup,
			        hwVapStationListGroup, hwWlanServiceBatchEssInfoGroup, hwApAssocStatGroup, hwVlanMappingGroup, hwGlobalStaMacWhiteListGroup,
			        hwStaMacBlackListGroup, hwApStaAccessControlGroup, hwAcStatisticsGroup, hwMacVapManagementGroup, hwMacCapwapConfigManagementGroup,
			        hwMacVapStationListGroup, hwMacApAssocStatGroup, hwVapConfigGroup, hwSsidStatisticGroup, hwMacSsidStatisticGroup,
			        hwMacApStaAccessControlGroup, hwApStaInfoGroup, hwMacApStaInfoGroup, hwInterACRoamingInfoGroup, hwRadioStaListGroup,
			        hwMacRadioStaListGroup, hwBridgeProfileGroup, hwBridgeVapManagementGroup, hwMacBridgeVapManagementGroup, hwBridgeLinkGroup,
			        hwMacBridgeLinkGroup, hwBridgeWhitelistGroup, hwWirelessSsidStatisticGroup, hwStaBlacklistProfileGroup, hwStaWhitelistProfileGroup,
			        hwMeshProfileGroup, hwMeshVapManagementGroup, hwMacMeshVapManagementGroup, hwMeshLinkGroup, hwMacMeshLinkGroup,
			        hwMeshWhitelistGroup, hwWlanServiceManagementGroup, hwLbsTagDevGroup}
			::= { hwWlanServiceManagementCompliances 1 }

		hwWlanServiceManagementObjectGroups OBJECT IDENTIFIER ::= { hwWlanServiceManagementConformance 2 }

		hwEssManagementGroup OBJECT-GROUP
			OBJECTS { hwWlanServiceEssSsid, hwWlanServiceEssHideSsid, hwWlanServiceEssUserIsolate, hwWlanServiceEssType, hwWlanServiceEssTrafficProfileName,
				hwWlanServiceEssSecurityProfileName, hwWlanServiceEssMaxUserNumber, hwWlanServiceEssAssociationTimeOut, hwWlanServiceEssIgmpMode, hwWlanServiceEssRowStatus,
				hwWlanServiceEssForwardMode, hwWlanServiceEssNum, hwWlanServiceVlan, hwWlanServiceEssDhcpSnooping, hwWlanServiceEssServiceVlanEnable,
				hwWlanServiceEssIPSGEnable, hwWlanServiceEssDhcpTrustPort, hwWlanServiceEssDaiSwitch, hwWlanServiceEssArpThreshold, hwWlanServiceEssTunnelProtocol,
				hwWlanServiceEssStatus, hwWlanServiceEssOfflineManagement, hwWlanServiceEssBlacklistProfileName, hwWlanServiceEssWhitelistProfileName, hwWlanServiceEssStaAccessMode,
				hwWlanServiceEssDhcpOption82InsertSwitch, hwWlanServiceEssDhcpOption82RemoteIdFormat, hwWlanServiceEssDhcpSnoopingOption, hwWlanServiceEssBroadCastPps, hwWlanServiceEssMultiCastPps,
				hwWlanServiceEssUniCastPps, hwWlanServiceEssBroadCastSwitch, hwWlanServiceEssMultiCastSwitch, hwWlanServiceEssUniCastSwitch, hwWlanServiceEssSaclNameInbound,
				hwWlanServiceEssSaclNameOutbound, hwWlanServiceEssSaclNumInbound, hwWlanServiceEssSaclNumOutbound, hwWlanServiceEssSaclSwtichInbound, hwWlanServiceEssSaclSwtichOutbound,
				hwWlanServiceEssServiceModeSwitch, hwWlanServiceEssAutoOffEssAdminSwitch, hwWlanServiceEssAutoOffEssStartTime, hwWlanServiceEssAutoOffEssEndTime, hwWlanServiceEssNdSnooping,
				hwWlanServiceEssSaclNameInboundIPv6, hwWlanServiceEssSaclNameOutboundIPv6, hwWlanServiceEssSaclNumInboundIPv6, hwWlanServiceEssSaclNumOutboundIPv6, hwWlanServiceEssSaclSwtichInboundIPv6,
				hwWlanServiceEssSaclSwtichOutboundIPv6, hwWlanServiceEssNdTrustPort,hwWlanServiceEssMldSnoopingEable,hwWlanServiceEssIPSGEnableRejectAssoc,hwWlanServiceEssLearnClientIpEnable,hwWlanServiceEssHomeAgent,
				hwWlanServiceEssVlanMobilityGroup}
			STATUS current
			DESCRIPTION
				"Description."
			::= { hwWlanServiceManagementObjectGroups 1 }

		hwVapManagementGroup OBJECT-GROUP
			OBJECTS { hwWlanServiceVapWlanIndex, hwWlanServiceVapRowStatus, hwWlanServiceVapBssid, hwWlanServiceVapSSID, hwWlanServiceVapVlan, hwWlanServiceVapFrequency
				 }
			STATUS current
			DESCRIPTION
				"Description."
			::= { hwWlanServiceManagementObjectGroups 2 }

		hwServiceBatchGroup OBJECT-GROUP
			OBJECTS { hwWlanServiceBatchRadioProfileName, hwWlanServiceBatchEssNameNumber, hwWlanServiceBatchEssNameList, hwWlanServiceBatchRowStatus }
			STATUS current
			DESCRIPTION
				"Description."
			::= { hwWlanServiceManagementObjectGroups 3 }

		hwCapwapConfigManagementGroup OBJECT-GROUP
			OBJECTS { hwWlanServiceCapwapConfigCommit }
			STATUS current
			DESCRIPTION
				"Description."
			::= { hwWlanServiceManagementObjectGroups 4 }

		hwStationGroup OBJECT-GROUP
			OBJECTS { hwWlanServiceStaApId, hwWlanServiceStaRadioId, hwWlanServiceStaEssName, hwWlanServiceStaSsid, hwWlanServiceStaOnlineTime,
				hwWlanServiceStaSnrUs, hwWlanServiceStaRxPowerUs, hwStaWirelessStatTxPkts, hwStaWirelessStatRxPkts, hwStaWirelessStatTxBytes,
				hwStaWirelessStatRxBytes, hwStaWirelessStatTxRate, hwStaWirelessStatRxRate, hwStaAccessChannel, hwStaIp,
				hwStaRssi, hwStaNoise, hwStaVlan, hwStaRecvDropFrames, hwStaSendDropFrames,
				hwStaRecvErrorFrames, hwStaSendErrorFrames, hwStaReSendFrames, hwStaReSendBytes, hwStaUsername,
				hwStaStatus, hwStaWirelessStatRxBytes64Bits, hwStaWirelessStatTxBytes64Bits, hwStaGateway, hwStaAuthenMethod,
				hwStaEncryptMethod, hwStaBSSID, hwStaQosMode, hwStaHtMode, hwStaMcsVal,
				hwStaShortGIStatus, hwStaRoamStatus, hwStaStatOperMode, hwStaWirelessStatTxPkts64Bits, hwStaWirelessStatRxPkts64Bits,
				hwStaRfMode, hwStaIpV6, hwStaAssociateTime, hwStaAccessTime, hwStaAccessOnlineTime, hwStaLinkRxRate, hwStaLinkTxRate,
				hwStaActualBandwidth, hwStaPackets, hwStaChannelUtilRate, hwStaChannelBusyRate, hwStaChannelFreeRate, hwStaChannelInterfRate }
			STATUS current
			DESCRIPTION
				"Description."
			::= { hwWlanServiceManagementObjectGroups 5 }

		hwVapStationListGroup OBJECT-GROUP
			OBJECTS { hwWlanServiceVapStaNum, hwWlanServiceVapStaMacList, hwWlanServiceVapAssociatedStationCount, hwWlanServiceVapCurOnlineStaCount, hwWlanServiceVapStaAssocAndReAssocReqCount,
				hwWlanServiceVapStaOnlineTime }
			STATUS current
			DESCRIPTION
				"Description."
			::= { hwWlanServiceManagementObjectGroups 6 }

		hwWlanServiceBatchEssInfoGroup OBJECT-GROUP
			OBJECTS { hwWlanServiceBatchEssStartNumber, hwWlanServiceBatchEssNumber, hwWlanServiceBatchReturnEssNumber, hwWlanServiceBatchEssName, hwWlanServiceBatchEssSsid
				 }
			STATUS current
			DESCRIPTION
				"Description."
			::= { hwWlanServiceManagementObjectGroups 7 }

		hwApAssocStatGroup OBJECT-GROUP
			OBJECTS { hwTotalOnlineTime, hwTotalAssociatedStationCount, hwCurrAssociatedStationCount, hwAssociationRequestCount, hwAssociationRejectCount,
				hwAssociationFailedCount, hwReAssociationRequestCount, hwReAssociationRejectCount, hwReAssociationFailedCount, hwDisAssocOfUserNotifiedCount,
				hwDisAssocOfStaRoamCount, hwDisAssocOfStaAgeCount, hwDisAssocOfApUnableHandleCount, hwDisAssocOfOtherReasonsCount, hwAssocRequestCntByResource,
				hwStaExceptionalOfflineCnt, hwReAssociationSuccessCount, hwBSSNotSupportAssocFailCount, hwStaAccessRequestCount, hwStaAccessRequestFailedCount,
				hwStaAuthenRequestCount, hwStaAuthenRequestFailedCount, hwRefusedStaNumByResource, hwStaAssocAndReAssocRequestCount, hwStaAuthenRequestSuccessCount,
				hwL3RoamInStationCount, hwL3RoamOutStationCount}
			STATUS current
			DESCRIPTION
				"Description."
			::= { hwWlanServiceManagementObjectGroups 8 }

		hwVlanMappingGroup OBJECT-GROUP
			OBJECTS { hwVlanMappingEssVlanMode, hwVlanMappingEssVlanId, hwVlanMappingVlanList0, hwVlanMappingVlanList1, hwVlanMappingVlanList2,
				hwVlanMappingVlanList3, hwVlanMappingVlanList4, hwVlanMappingVlanList5, hwVlanMappingVlanList6, hwVlanMappingVlanList7
				 }
			STATUS current
			DESCRIPTION
				"Description."
			::= { hwWlanServiceManagementObjectGroups 9 }

		hwGlobalStaMacWhiteListGroup OBJECT-GROUP
			OBJECTS { hwGlobalStaMacWhiteListRowStatus }
			STATUS current
			DESCRIPTION
				"Description."
			::= { hwWlanServiceManagementObjectGroups 10 }

		hwStaMacBlackListGroup OBJECT-GROUP
			OBJECTS { hwStaMacBlackListRowStatus }
			STATUS current
			DESCRIPTION
				"Description."
			::= { hwWlanServiceManagementObjectGroups 11 }

		hwApStaAccessControlGroup OBJECT-GROUP
			OBJECTS { hwApStaAccessControlMode, hwApStaAccessControlRowStatus }
			STATUS current
			DESCRIPTION
				"Description."
			::= { hwWlanServiceManagementObjectGroups 12 }

		hwAcStatisticsGroup OBJECT-GROUP
			OBJECTS { hwAcReassocSuccessTimes, hwApPerformanceStatTimerLen, hwRtCollectOnoff, hwApNormalCollectCycle, hwApRtCollectCycle,
				hwAcCurAssocStaNum, hwAcCurAuthSuccessStaNum, hwAcCurJointApNum, hwAcCurAssoc24gStaNum, hwAcCurAssoc5gStaNum }
			STATUS current
			DESCRIPTION
				"Description."
			::= { hwWlanServiceManagementObjectGroups 13 }

		hwMacVapManagementGroup OBJECT-GROUP
			OBJECTS { hwMacWlanServiceVapWlanIndex, hwMacWlanServiceVapBssid, hwMacWlanServiceVapRowStatus, hwMacWlanServiceVapSSID, hwMacWlanServiceVapVlan
				 }
			STATUS current
			DESCRIPTION
				"Description."
			::= { hwWlanServiceManagementObjectGroups 14 }

		hwMacCapwapConfigManagementGroup OBJECT-GROUP
			OBJECTS { hwMacWlanServiceCapwapConfigCommit }
			STATUS current
			DESCRIPTION
				"Description."
			::= { hwWlanServiceManagementObjectGroups 15 }

		hwMacVapStationListGroup OBJECT-GROUP
			OBJECTS { hwMacWlanServiceVapStaNum, hwMacWlanServiceVapStaMacList, hwMacWlanServiceVapAssociatedStationCount, hwMacWlanServiceVapCurOnlineStaCount, hwMacWlanServiceVapStaAssocAndReAssocReqCount,
				hwMacWlanServiceVapStaOnlineTime }
			STATUS current
			DESCRIPTION
				"Description."
			::= { hwWlanServiceManagementObjectGroups 16 }

		hwMacApAssocStatGroup OBJECT-GROUP
			OBJECTS { hwMacTotalOnlineTime, hwMacTotalAssociatedStationCount, hwMacCurrAssociatedStationCount, hwMacAssociationRequestCount, hwMacAssociationRejectCount,
				hwMacAssociationFailedCount, hwMacReAssociationRequestCount, hwMacReAssociationRejectCount, hwMacReAssociationFailedCount, hwMacDisAssocOfUserNotifiedCount,
				hwMacDisAssocOfStaRoamCount, hwMacDisAssocOfStaAgeCount, hwMacDisAssocOfApUnableHandleCount, hwMacDisAssocOfOtherReasonsCount, hwMacAssocRequestCntByResource,
				hwMacStaExceptionalOfflineCnt, hwMacReAssociationSuccessCount, hwMacBSSNotSupportAssocFailCount, hwMacStaAccessRequestCount, hwMacStaAccessRequestFailedCount,
				hwMacStaAuthenRequestCount, hwMacStaAuthenRequestFailedCount, hwMacRefusedStaNumByResource, hwMacStaAssocAndReAssocRequestCount, hwMacStaAuthenRequestSuccessCount,
				hwL3RoamInStationCount, hwL3RoamOutStationCount}
			STATUS current
			DESCRIPTION
				"Description."
			::= { hwWlanServiceManagementObjectGroups 17 }

		hwVapConfigGroup OBJECT-GROUP
			OBJECTS { hwVapOptValue }
			STATUS current
			DESCRIPTION
				"Description."
			::= { hwWlanServiceManagementObjectGroups 18 }

		hwSsidStatisticGroup OBJECT-GROUP
			OBJECTS { hwSsidAirportRecvBytes, hwSsidAirportRecvErrorFrames, hwSsidAirportRecvFrames, hwSsidAirportRecvUnicastFrames, hwSsidAirportRecvDropFrames,
				hwSsidAirportTransmitBytes, hwSsidAirportTransmitErrorFrames, hwSsidAirportTransmitFrames, hwSsidAirportTransmitUnicastFrames, hwSsidAirportTransmitDropFrames,
				hwSsidAirportDownReTransmitFrames, hwSsidCurrentStaNum, hwSsidAirportNoise, hwSsidAirportSNR }
			STATUS current
			DESCRIPTION
				"Description."
			::= { hwWlanServiceManagementObjectGroups 19 }

		hwMacSsidStatisticGroup OBJECT-GROUP
			OBJECTS { hwMacSsidAirportRecvBytes, hwMacSsidAirportRecvErrorFrames,
				hwMacSsidAirportRecvFrames, hwMacSsidAirportRecvUnicastFrames, hwMacSsidAirportRecvDropFrames, hwMacSsidAirportTransmitBytes, hwMacSsidAirportTransmitErrorFrames,
				hwMacSsidAirportTransmitFrames, hwMacSsidAirportTransmitUnicastFrames, hwMacSsidAirportTransmitDropFrames, hwMacSsidAirportDownReTransmitFrames, hwMacSsidCurrentStaNum,
				hwMacSsidAirportNoise, hwMacSsidAirportSNR}
			STATUS current
			DESCRIPTION
				"Description."
			::= { hwWlanServiceManagementObjectGroups 20 }

		hwMacApStaAccessControlGroup OBJECT-GROUP
			OBJECTS { hwMacApStaAccessControlMode, hwMacApStaAccessControlRowStatus }
			STATUS current
			DESCRIPTION
				"Description."
			::= { hwWlanServiceManagementObjectGroups 21 }

		hwApStaInfoGroup OBJECT-GROUP
			OBJECTS { hwStaMAC, hwStaIPAddress, hwStaWMMAttr, hwStaRadioMode, hwStaRadioChannel,
				hwAPTxRates, hwStaPowerSaveMode, hwStaVlanId, hwStaSSIDName, hwApStaTxPacket,
				hwApStaRxPacket, hwApStaStatus, hwApStaBssid, hwApStaRssi, hwApStaSnr }
			STATUS current
			DESCRIPTION
				"Description."
			::= { hwWlanServiceManagementObjectGroups 22 }

		hwMacApStaInfoGroup OBJECT-GROUP
			OBJECTS { hwMacStaMAC, hwMacStaIPAddress, hwMacStaWMMAttr, hwMacStaRadioMode, hwMacStaRadioChannel,
				hwMacAPTxRates, hwMacStaPowerSaveMode, hwMacStaVlanId, hwMacStaSSIDName, hwMacApStaTxPacket,
				hwMacApStaRxPacket, hwMacApStaStatus, hwMacApStaBssid, hwMacApStaRssi, hwMacApStaSnr }
			STATUS current
			DESCRIPTION
				"Description."
			::= { hwWlanServiceManagementObjectGroups 23 }

		hwInterACRoamingInfoGroup OBJECT-GROUP
			OBJECTS { hwInterACRoamingInSuccCnt, hwInterACRoamingOutSuccCnt }
			STATUS current
			DESCRIPTION
				"Description."
			::= { hwWlanServiceManagementObjectGroups 24 }

		hwRadioStaListGroup OBJECT-GROUP
			OBJECTS { hwRadioStaNumber, hwRadioStaMacList, hwRadioStaTotalAssociatedCount, hwRadioStaAccessReqCount }
			STATUS current
			DESCRIPTION
				"Description."
			::= { hwWlanServiceManagementObjectGroups 25 }

		hwMacRadioStaListGroup OBJECT-GROUP
			OBJECTS { hwMacRadioStaNumber, hwMacRadioStaMacList, hwMacRadioStaTotalAssociatedCount, hwMacRadioStaAccessReqCount }
			STATUS current
			DESCRIPTION
				"Description."
			::= { hwWlanServiceManagementObjectGroups 26 }

		hwBridgeProfileGroup OBJECT-GROUP
			OBJECTS { hwBridgeProfileBridgeName, hwBridgeProfileSecurityProfileName, hwBridgeProfileVlanTagged, hwBridgeProfileRowStatus, hwBridgeProfileDhcpTrustPort,
				 hwBridgeProfileNdTrustPort}
			STATUS current
			DESCRIPTION
				"Description."
			::= { hwWlanServiceManagementObjectGroups 27 }

		hwBridgeVapManagementGroup OBJECT-GROUP
			OBJECTS { hwBridgeVapRowStatus }
			STATUS current
			DESCRIPTION
				"Description."
			::= { hwWlanServiceManagementObjectGroups 28 }

		hwMacBridgeVapManagementGroup OBJECT-GROUP
			OBJECTS { hwMacBridgeVapRowStatus }
			STATUS current
			DESCRIPTION
				"Description."
			::= { hwWlanServiceManagementObjectGroups 29 }

		hwBridgeLinkGroup OBJECT-GROUP
			OBJECTS { hwBridgeLinkWlanID, hwBridgeLinkBridgeType, hwBridgeLinkBridgeSubType, hwBridgeLinkPeerMac, hwBridgeLinkBridgeProfileName,
				hwBridgeLinkStpMode, hwBridgeLinkInstanceIdList, hwBridgeLinkInstanceStateList, hwBridgeLinkApMac, hwBridgeLinkBridgeMode, hwBridgeLinkCoverageDistance,
				hwBridgeLinkPeerAPID, hwBridgeLinkPeerAPStatus, hwBridgeLinkMaxRssi, hwBridgeLinkRssi, hwBridgeLinkPeerApMac, hwBridgeLinkChannelID }
			STATUS current
			DESCRIPTION
				"Description."
			::= { hwWlanServiceManagementObjectGroups 30 }

		hwMacBridgeLinkGroup OBJECT-GROUP
			OBJECTS { hwMacBridgeLinkWlanID, hwMacBridgeLinkBridgeType, hwMacBridgeLinkBridgeSubType, hwMacBridgeLinkPeerMac, hwMacBridgeLinkBridgeProfileName,
				hwMacBridgeLinkStpMode, hwMacBridgeLinkInstanceIdList, hwMacBridgeLinkInstanceStateList, hwMacBridgeLinkApID, hwMacBridgeLinkBridgeMode,
				hwMacBridgeLinkCoverageDistance, hwMacBridgeLinkPeerAPID, hwMacBridgeLinkPeerAPStatus, hwMacBridgeLinkMaxRssi, hwMacBridgeLinkRssi,
				hwMacBridgeLinkPeerApMac, hwMacBridgeChannelID }
			STATUS current
			DESCRIPTION
				"Description."
			::= { hwWlanServiceManagementObjectGroups 31 }

		hwBridgeWhitelistGroup OBJECT-GROUP
			OBJECTS { hwBridgeWhitelistPeerList, hwBridgeWhitelistRowStatus }
			STATUS current
			DESCRIPTION
				"Description."
			::= { hwWlanServiceManagementObjectGroups 32 }

		hwWirelessSsidStatisticGroup OBJECT-GROUP
			OBJECTS { hwWirelessSsidAirportTransmitUnicastFrames, hwWirelessSsidAirportTransmitFrames, hwWirelessSsidAirportTransmitErrorFrames, hwWirelessSsidAirportDownReTransmitFrames, hwWirelessSsidAirportTransmitDropFrames,
				hwWirelessSsidAirportTransmitBytes, hwWirelessSsidAirportRecvUnicastFrames, hwWirelessSsidAirportRecvFrames, hwWirelessSsidAirportRecvErrorFrames, hwWirelessSsidAirportRecvDropFrames,
				hwWirelessSsidAirportRecvBytes, hwWirelessSsidTotalAssociatedSuccessStationCount, hwWirelessSsidCurAssocStationCount, hwWirelessSsidTotalAssociatedFailedStationCount }
			STATUS current
			DESCRIPTION
				"Description."
			::= { hwWlanServiceManagementObjectGroups 33 }

		hwStaBlacklistProfileGroup OBJECT-GROUP
			OBJECTS { hwStaBlacklistProfileStaMac, hwStaBlacklistProfileOper, hwStaBlacklistProfileStaNum, hwStaBlacklistProfileStaList, hwStaBlacklistProfileRowStatus
				 }
			STATUS current
			DESCRIPTION
				"Description."
			::= { hwWlanServiceManagementObjectGroups 34 }

		hwStaWhitelistProfileGroup OBJECT-GROUP
			OBJECTS { hwStaWhitelistProfileStaMac, hwStaWhitelistProfileOper, hwStaWhitelistProfileStaNum, hwStaWhitelistProfileStaList, hwStaWhitelistProfileRowStatus
				 }
			STATUS current
			DESCRIPTION
				"Description."
			::= { hwWlanServiceManagementObjectGroups 35 }

		hwMeshProfileGroup OBJECT-GROUP
			OBJECTS { hwMeshProfileSecurityProfileName, hwMeshProfileMeshID, hwMeshProfileMaxLinkNum, hwMeshProfileRssiThreshold, hwMeshProfileReportInterval,
				hwMeshProfileRowStatus, hwMeshProfileDhcpTrustPort, hwMeshProfileNdTrustPort, hwMeshProfileQuickHoSwitch, hwMeshProfileLinkHoThreshold,
				hwMeshProfileLinkHoldPeriod, hwMeshProfileLinkLinkSaturationThreshold, hwMeshProfileLinkProbePeriod, hwMeshProfileFwaMode, hwMeshProfileFwaEdcaMode,
				hwMeshProfileQuickHandoverMinRssiThreshold, hwMeshProfileLocationBasedHandoverAlgorithmSwitch,hwMeshProfileMovingDirection,
				hwMeshProfileHandoverAlgorithmPNCriteriaObserveTime, hwMeshProfileHandoverAlgorithmPNCriteriaQualifyTime,
				hwMeshProfileUrgentHandoverLowRateThreshold, hwMeshProfileUrgentHandoverLowRatePeriod,
				hwMeshProfileUrgentHandoverPunishmentPeriod, hwMeshProfileUrgentHandoverPunishmentRssi }
			STATUS current
			DESCRIPTION
				"Description."
			::= { hwWlanServiceManagementObjectGroups 36 }

		hwMeshVapManagementGroup OBJECT-GROUP
			OBJECTS { hwMeshVapRowStatus }
			STATUS current
			DESCRIPTION
				"Description."
			::= { hwWlanServiceManagementObjectGroups 37 }

		hwMacMeshVapManagementGroup OBJECT-GROUP
			OBJECTS { hwMacMeshVapRowStatus }
			STATUS current
			DESCRIPTION
				"Description."
			::= { hwWlanServiceManagementObjectGroups 38 }

		hwMeshLinkGroup OBJECT-GROUP
			OBJECTS { hwMeshLinkWlanID, hwMeshLinkPeerMac, hwMeshLinkChannelID, hwMeshLinkRssiValue, hwMeshLinkApMac, hwMeshLinkMeshRole, hwMeshLinkCoverageDistance,
					hwMeshLinkPeerAPStatus, hwMeshLinkMaxRssi, hwMeshLinkPeerApMac }
			STATUS current
			DESCRIPTION
				"Description."
			::= { hwWlanServiceManagementObjectGroups 39 }

		hwMacMeshLinkGroup OBJECT-GROUP
			OBJECTS { hwMacMeshLinkWlanID, hwMacMeshLinkPeerMac, hwMacMeshLinkChannelID, hwMacMeshLinkRssiValue, hwMacMeshLinkApID,
					hwMacMeshLinkMeshRole, hwMacMeshLinkCoverageDistance, hwMacMeshLinkPeerAPID, hwMacMeshLinkPeerAPStatus, hwMacMeshLinkMaxRssi, hwMacMeshLinkPeerApMac }
			STATUS current
			DESCRIPTION
				"Description."
			::= { hwWlanServiceManagementObjectGroups 40 }

		hwMeshWhitelistGroup OBJECT-GROUP
			OBJECTS { hwMeshWhitelistPeerList, hwMeshWhitelistRowStatus }
			STATUS current
			DESCRIPTION
				"Description."
			::= { hwWlanServiceManagementObjectGroups 41 }

		hwWlanServiceManagementGroup OBJECT-GROUP
			OBJECTS { hwCapwapConfigCommitAll }
			STATUS current
			DESCRIPTION
				"Description."
			::= { hwWlanServiceManagementObjectGroups 42 }

		hwLbsTagDevGroup OBJECT-GROUP
			OBJECTS { hwLbsTagDevType, hwLbsTagDevChannel, hwLbsTagDevRssi }
			STATUS current
			DESCRIPTION
				"Description."
			::= { hwWlanServiceManagementObjectGroups 43 }

		hwProxyTrackSideEquipGroup OBJECT-GROUP
			OBJECTS { hwProxyTrackSideEquipMac, hwProxyTrackSideEquipVlanID, hwProxyTrackSideEquipRowStatus }
			STATUS current
			DESCRIPTION
				"Description."
			::= { hwWlanServiceManagementObjectGroups 44 }

		hwProxyOnBoardEquipGroup OBJECT-GROUP
			OBJECTS { hwProxyOnBoardEquipMac, hwProxyOnBoardEquipVlanID, hwProxyOnBoardEquipRowStatus }
			STATUS current
			DESCRIPTION
				"Description."
			::= { hwWlanServiceManagementObjectGroups 45 }

		hwHandoverTraceGroup OBJECT-GROUP
			OBJECTS { hwHandoverTimeStamp, hwHandoverFromApMac, hwHandoverFromApRssi, hwHandoverToApMac, hwHandoverToApRssi,
			    	hwHandoverFromApLocationID, hwHandoverToApLocationID }
			STATUS current
			DESCRIPTION
				"Description."
			::= { hwWlanServiceManagementObjectGroups 46 }

		hwNeighborApGroup OBJECT-GROUP
			OBJECTS { hwNeighborApLocalApMac, hwNeighborApIdList, hwNeighborApMacList,
				hwNeighborApRssiList, hwNeighborApUpdateTime, hwNeighborApLocalLocationID, hwNeighborApLocationIDList }
			STATUS current
			DESCRIPTION
				"Description."
			::= { hwWlanServiceManagementObjectGroups 47 }

	END

--
-- HUAWEI-WLAN-SERVICE-MIB.mib
--
