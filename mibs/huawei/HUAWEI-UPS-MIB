HUAWEI-UPS-MIB DEFINITIONS ::= BEGIN
                                 IMPORTS
huaweiUtility
FROM HUAWEI-MIB
                                             OBJECT-GROUP, NOTIFICATION-GROUP
                                                 FROM SNMPv2-CONF
                                             Integer32, Unsigned32, OBJECT-TYPE, MODULE-IDENTITY, NOTIFICATION-TYPE
                                                 FROM SNMPv2-SMI
                                             TEXTUAL-CONVENTION
                                                 FROM SNMPv2-TC;
hwUpsMIB MODULE-IDENTITY
LAST-UPDATED "201210240000Z"
ORGANIZATION
                                             "Huawei Technologies Co., Ltd."
CONTACT-INFO
                                             "Floor 5, Block 4, R&D Building,
                                             Huawei Longgang Production Base,
                                             Shenzhen,   P.R.C.
                                             http: // www.huawei.com
                                             Zip: 518129."
DESCRIPTION
                                             "EMAP MIB defines MIB objects which provides load and backup management, patch management NMS interfaces.
                                             The current version is v1.01"
REVISION "201210240000Z"
                                             DESCRIPTION
                                             "Huawei emap mib v1.00"
::= { huaweiUtility 174 }

DisplayString ::= TEXTUAL-CONVENTION
                                             STATUS current
                                             DESCRIPTION
                                             "Description."
                                             SYNTAX OCTET STRING (SIZE (1..64))

                                             RowStatus ::= TEXTUAL-CONVENTION
                                             STATUS current
                                             DESCRIPTION
                                             "Description."
                                             SYNTAX INTEGER
                                             {
                                                     active(1),
                                                     notInService(2),
                                                     notReady(3),
                                                     createAndGo(4),
                                                     createAndWait(5),
                                                     destroy(6)
                                             }

                                             DateAndTime ::= TEXTUAL-CONVENTION
                                             STATUS current
                                             DESCRIPTION
                                             "Description."
                                             SYNTAX OCTET STRING (SIZE (8..11))

                                             RunStatus ::= TEXTUAL-CONVENTION
                                             STATUS current
                                             DESCRIPTION
                                                     "This integer value represents running status of the system.
                                                     Depending on situation there may be limits on allowed values.
                                                     Operational values:
                                                     (1) unknown - status has not yet been defined
                                                     (2) normal - there are no activated alarms
                                                     (3) alarm - alarm status
                                             "
                                             SYNTAX INTEGER
                                             {
                                                     unknow(1),
                                                     normal(2),
                                                     alarm(3)
                                             }

                                             MeasuresRange ::= TEXTUAL-CONVENTION
                                             STATUS current
                                             DESCRIPTION
                                             "Description."
                                             SYNTAX Integer32

                                             TruthValue ::= TEXTUAL-CONVENTION
                                             STATUS current
                                             DESCRIPTION
                                             "Description."
                                             SYNTAX INTEGER
                                             {
                                                     true(1),
                                                     false(2)
                                             }
        hwUpsMIBObjects OBJECT IDENTIFIER ::= { hwUpsMIB 1 }

        hwUpsSystem OBJECT IDENTIFIER ::= { hwUpsMIBObjects 1 }

        hwUpsSysIdent OBJECT IDENTIFIER ::= { hwUpsSystem 1 }

        hwUpsSystemMainDeviceESN OBJECT-TYPE
            SYNTAX OCTET STRING (SIZE (0..127))
            MAX-ACCESS read-only
            STATUS current
            DESCRIPTION
                "ESN of the master device used for setting up a NetEco model. A string of characters."
            ::= { hwUpsSysIdent 1 }

        hwUpsSystemType OBJECT-TYPE
            SYNTAX OCTET STRING (SIZE (0..127))
            MAX-ACCESS read-only
            STATUS current
            DESCRIPTION
                "Name of the UPS system. A string of characters. Configurable."
            ::= { hwUpsSysIdent 2 }

        hwUpsSysInerProtVersion  OBJECT-TYPE
            SYNTAX OCTET STRING (SIZE (0..127))
            MAX-ACCESS read-only
            STATUS current
            DESCRIPTION
                "Version number of the system interface protocol between the NetEco and NEs.
                    A string of characters."
            ::= { hwUpsSysIdent 3 }

        hwUpsSysDeviceNum  OBJECT-TYPE
            SYNTAX Unsigned32 (0..63)
            MAX-ACCESS read-only
            STATUS current
            DESCRIPTION
                "Number of devices in the system. An integer ranging from 0 to 63."
            ::= { hwUpsSysIdent 4 }

        hwUpsParallelSysNum  OBJECT-TYPE
            SYNTAX Unsigned32 (0..63)
            MAX-ACCESS read-only
            STATUS current
            DESCRIPTION
                "Number of parallel systems. An integer ranging from 0 to 63."
            ::= { hwUpsSysIdent 5 }

        hwUpsEnvTemper  OBJECT-TYPE
            SYNTAX Integer32 ( -500..1200)
	    UNITS "C"
            MAX-ACCESS read-only
            STATUS current
            DESCRIPTION
                "Ambient temperature. An integer ranging from -50 to 120.
                    The value is accurate to one decimal place on the NetEco. The unit is C"
            ::= { hwUpsSysIdent 6 }

        hwUpsEnvHumidity  OBJECT-TYPE
            SYNTAX Unsigned32 (0..1000)
	    UNITS "%"
            MAX-ACCESS read-only
            STATUS current
            DESCRIPTION
                "Ambient humidity. An integer ranging from 0 to 100.
                    The value is accurate to one decimal place on the NetEco. The unit is %."
            ::= { hwUpsSysIdent 7 }

        hwUpsDevice OBJECT IDENTIFIER ::= { hwUpsMIBObjects 2 }

        hwUpsDeviceIdentTable OBJECT-TYPE
            SYNTAX SEQUENCE OF HwUpsDeviceIdentEntry
            MAX-ACCESS not-accessible
             STATUS current
             DESCRIPTION
                "The device identification table. Use this table to get device ID, and to get device type,
                  the soft version, the iner prot version, the ESN, the rating power of device,
                  the parallel system index of device. This table's index is hwUpsDeviceId."
            ::= { hwUpsDevice 100 }

        hwUpsDeviceIdentEntry OBJECT-TYPE
                        SYNTAX HwUpsDeviceIdentEntry
            MAX-ACCESS not-accessible
             STATUS current
             DESCRIPTION
                "The device identification table. Use this table to get device ID, and to get device type,
                  the soft version, the iner prot version, the ESN, the rating power of device,
                  the parallel system index of device. This table's index is hwUpsDeviceId."
            INDEX { hwUpsDeviceId }
            ::= { hwUpsDeviceIdentTable 1 }

        HwUpsDeviceIdentEntry            ::= SEQUENCE {
                hwUpsDeviceId
                    Unsigned32,
                hwUpsDeviceType
                    OCTET STRING,
                hwUpsDeviceSoftVersion
                    OCTET STRING,
                hwUpsDeviceInerProtVersion
                    OCTET STRING,
                hwUpsDeviceESN
                    OCTET STRING,
                hwUpsDevicePowerRating
                    INTEGER,
                hwUpsDeviceParaSysIndex
                    Unsigned32,
                hwUpsDeviceSysGrant
                    Unsigned32,
                hwUpsDeviceMonitorSoftVersion
                    OCTET STRING,
                hwUpsDevicePowerSoftVersion
                    OCTET STRING,
                hwUpsDeviceIdentRowStatus
                    RowStatus
            }

        hwUpsDeviceId OBJECT-TYPE
            SYNTAX Unsigned32 (1..100)
            MAX-ACCESS read-only
            STATUS current
            DESCRIPTION
                "Rack ID, ranging from 1 to 100. This node is referenced as an index node
                  by hwUpsDeviceIdentTable, hwUpsDeviceOperInfoTable, hwUpsInputTable,
                  hwUpsOutputTable,hwUpsBypassTable, hwUpsBatteryTable, hwUpsControlTable,
                  and hwUpsBattScheduleTestTable."
            ::= { hwUpsDeviceIdentEntry 1 }

        hwUpsDeviceType OBJECT-TYPE
            SYNTAX OCTET STRING (SIZE (0..127))
            MAX-ACCESS read-only
            STATUS current
            DESCRIPTION
                "Device model. A string of characters."
            ::= { hwUpsDeviceIdentEntry 2 }

        hwUpsDeviceSoftVersion OBJECT-TYPE
            SYNTAX OCTET STRING (SIZE (0..127))
            MAX-ACCESS read-only
            STATUS current
            DESCRIPTION
                "Device software version number. A string of characters."
            ::= { hwUpsDeviceIdentEntry 3 }

        hwUpsDeviceInerProtVersion OBJECT-TYPE
            SYNTAX OCTET STRING (SIZE (0..127))
            MAX-ACCESS read-only
            STATUS current
            DESCRIPTION
                "Interface protocol version number for the current device. A string of characters."
            ::= { hwUpsDeviceIdentEntry 4 }

        hwUpsDeviceESN OBJECT-TYPE
            SYNTAX OCTET STRING (SIZE (0..127))
            MAX-ACCESS read-only
            STATUS current
            DESCRIPTION
                "ESN. A string of characters."
            ::= { hwUpsDeviceIdentEntry 5 }

        hwUpsDevicePowerRating OBJECT-TYPE
            SYNTAX INTEGER
                {
                level80(1),
                level100(2),
                level120(3),
                level160(4),
                level200(5),
                level30(6),
                level40(7),
                level60(8),
                level240(9),
                level250(10),
                level280(11),
                level300(12)
                }
            MAX-ACCESS read-only
            STATUS current
            DESCRIPTION
                "System capacity. Enumeration type. The default value is 5. The unit is kVA.
                  Value 1 indicates 80 kVA
                  Value 2 indicates 100 kVA.
                  Value 3 indicates 120 kVA.
                  Value 4 indicates 160 kVA.
                  Value 5 indicates 200 kVA."
            ::= { hwUpsDeviceIdentEntry 6 }

        hwUpsDeviceParaSysIndex OBJECT-TYPE
            SYNTAX Unsigned32 (0..63)
            MAX-ACCESS read-only
            STATUS current
            DESCRIPTION
                "ID of the parallel system that the current device belongs to. An integer ranging from 0 to 63."
            ::= { hwUpsDeviceIdentEntry 7 }

        hwUpsDeviceSysGrant OBJECT-TYPE
            SYNTAX Unsigned32 (0..10000)
            MAX-ACCESS read-only
            STATUS current
            DESCRIPTION
                "System grant.An integer ranging from 0 to 10000."
            ::= { hwUpsDeviceIdentEntry 8 }

        hwUpsDeviceMonitorSoftVersion OBJECT-TYPE
            SYNTAX OCTET STRING (SIZE (0..127))
            MAX-ACCESS read-only
            STATUS current
            DESCRIPTION
                "Monitor software version number. A string of characters."
            ::= { hwUpsDeviceIdentEntry 9 }

        hwUpsDevicePowerSoftVersion OBJECT-TYPE
            SYNTAX OCTET STRING (SIZE (0..127))
            MAX-ACCESS read-only
            STATUS current
            DESCRIPTION
                "Power software version number A string of characters."
            ::= { hwUpsDeviceIdentEntry 10 }

        hwUpsDeviceIdentRowStatus OBJECT-TYPE
            SYNTAX RowStatus
            MAX-ACCESS read-only
            STATUS current
            DESCRIPTION
                "RowStatus of UPS device Identification table."
            ::= { hwUpsDeviceIdentEntry 100 }

        hwUpsDeviceOperInfoTable OBJECT-TYPE
            SYNTAX SEQUENCE OF HwUpsDeviceOperInfoEntry
            MAX-ACCESS not-accessible
             STATUS current
             DESCRIPTION
                "Device running information table. It's index is hwUpsDeviceId"
            ::= { hwUpsDevice 101 }

        hwUpsDeviceOperInfoEntry OBJECT-TYPE
                        SYNTAX HwUpsDeviceOperInfoEntry
            MAX-ACCESS not-accessible
             STATUS current
             DESCRIPTION
                "Device running information table. It's index is hwUpsDeviceId"
	    INDEX { hwUpsDeviceId }
            ::= { hwUpsDeviceOperInfoTable 1 }

        HwUpsDeviceOperInfoEntry            ::= SEQUENCE {
                hwUpsDevicePowerSupplyMethod
                    INTEGER,
                hwUpsDeviceRunningStatus
                    INTEGER,
                hwUpsDeviceBatteryState
                    INTEGER,
                hwUpsDeviceTemperature
                    Unsigned32,
                hwUpsDeviceEnergyFloatState
                    Unsigned32,
                hwUpsDeviceRedundantNumber
                    Unsigned32,
                hwUpsDeviceDelayShutdownState
                    Unsigned32,
                hwUpsDeviceDelayShutdownOrder
                    INTEGER,
                hwUpsDeviceWorkMode
                    INTEGER,
                hwUpsDeviceSmartPowerMode
                    INTEGER,
                hwUpsDeviceBSCState
                    INTEGER,
                hwUpsDeviceOperInfoRowStatus
                    RowStatus
            }

        hwUpsDevicePowerSupplyMethod OBJECT-TYPE
            SYNTAX INTEGER
                {
                noOutput(1),
                bypass(2),
                normal(3),
                battery(4),
                sourceShare(5),
                normalECO(6),
                batteryECO(7)


                }
            MAX-ACCESS read-only
            STATUS current
            DESCRIPTION
                "Device power supply mode. Enumeration type.
                  Value 1 indicates no power supply.
                  Value 2 indicates bypass mode.
                  Value 3 indicates normal mode.
                  Value 4 indicates battery mode.
                  Value 5 indicates combined mode.
                  Value 6 indicates mains ECO mode.
                  Value 7 indicates battery ECO mode."
            ::= { hwUpsDeviceOperInfoEntry 1 }

        hwUpsDeviceRunningStatus OBJECT-TYPE
            SYNTAX INTEGER
                {
                single(1),
                parallel(2),
                singleECO(3),
                parallelECO(4),
                aging(5)
                }
            MAX-ACCESS read-only
            STATUS current
            DESCRIPTION
                "UPS operating status. Enumeration type.
                  Value 1 indicates that a single UPS is operating.
                  Value 2 indicates that the parallel system is operating.
                  Value 3 indicates that a single UPS is operating in ECO mode.
                  Value 4 indicates that the parallel system is operating in ECO mode.
                  Value 5 indicates aging."
            ::= { hwUpsDeviceOperInfoEntry 2 }

        hwUpsDeviceBatteryState OBJECT-TYPE
            SYNTAX INTEGER
                {
                notExist(1),
                temperaryMode(2),
                sleep(3),
                floatCharge(4),
                boostCharge(5),
                discharge(6)
                }
            MAX-ACCESS read-only
            STATUS current
            DESCRIPTION
                "Battery status. Enumeration type.
                  Value 1 indicates that no battery is connected.
                  Value 2 indicates that the battery is not charging or discharging.
                  Value 3 indicates hibernation.
                  Value 4 indicates float charging.
                  Value 5 indicates equalized charging.
                  Value 6 indicates discharging."
            ::= { hwUpsDeviceOperInfoEntry 3 }

        hwUpsDeviceTemperature OBJECT-TYPE
            SYNTAX Unsigned32 (0..3000)
            MAX-ACCESS read-only
            STATUS current
            DESCRIPTION
                "Maximum temperature of the modules in the current device. An integer ranging from 0 to 300."
            ::= { hwUpsDeviceOperInfoEntry 4 }

        hwUpsDeviceEnergyFloatState OBJECT-TYPE
            SYNTAX Unsigned32 (0..70000)
            MAX-ACCESS read-only
            STATUS current
            DESCRIPTION
                "Current flow status. An integer ranging from 0 to 70000. "
            ::= { hwUpsDeviceOperInfoEntry 5 }

        hwUpsDeviceRedundantNumber OBJECT-TYPE
            SYNTAX Unsigned32 (0..3)
            MAX-ACCESS read-only
            STATUS obsolete
            DESCRIPTION
                "Redundant number of the parallel system. An integer ranging from 0 to 3."
            ::= { hwUpsDeviceOperInfoEntry 6 }

        hwUpsDeviceDelayShutdownState OBJECT-TYPE
            SYNTAX Unsigned32 (0..4294967295)
            MAX-ACCESS read-only
            STATUS obsolete
            DESCRIPTION
                "Delay to shutdown state. An integer ranging from 0 to 4294967295"
            ::= { hwUpsDeviceOperInfoEntry 7 }

        hwUpsDeviceDelayShutdownOrder OBJECT-TYPE
            SYNTAX INTEGER
                {
                invalid(1),
                    valid(2)
                }
            MAX-ACCESS read-only
            STATUS obsolete
            DESCRIPTION
                "Delay to shutdown state.  Enumeration type.
                    Value 1 indicates invalid.
                    Value 2 indicates valid."
            ::= { hwUpsDeviceOperInfoEntry 8 }

        hwUpsDeviceWorkMode OBJECT-TYPE
            SYNTAX INTEGER
                {
                normalMode(1),
                ecoMode(2),
                selfloadMode(3),
		converterMode(4)
                }
            MAX-ACCESS read-only
            STATUS current
            DESCRIPTION
                "Work Mode. Enumeration type.
                  Value 1 indicates that normal mode.
                  Value 2 indicates that eco mode.
                  Value 3 indicates that self load mode.
                  Value 4 indicates that converter mode.
                "
            ::= { hwUpsDeviceOperInfoEntry 9 }

        hwUpsDeviceSmartPowerMode OBJECT-TYPE
            SYNTAX INTEGER
                {
                disable(1),
                enable(2)

                }
            MAX-ACCESS read-only
            STATUS current
            DESCRIPTION
                "Smart Power Mode.Enumeration type.
                  Value 1 indicates that disable.
                  Value 2 indicates that enable.

                "
            ::= { hwUpsDeviceOperInfoEntry 10 }

        hwUpsDeviceBSCState OBJECT-TYPE
            SYNTAX INTEGER
                {
                notExist(1),
                masterMode(2),
                    slaveMode(3)
                }
            MAX-ACCESS read-only
            STATUS current
            DESCRIPTION
                "BSC system status. Enumeration type.
                    Value 1: Not activated
                    Value 2: BSC master mode
                    Value 3: BSC slave mode"
            ::= { hwUpsDeviceOperInfoEntry 11 }

        hwUpsDeviceOperInfoRowStatus OBJECT-TYPE
            SYNTAX RowStatus
            MAX-ACCESS read-only
            STATUS current
            DESCRIPTION
                "RowStatus of UPS device running information table."
            ::= { hwUpsDeviceOperInfoEntry 101 }

        hwUpsInput OBJECT IDENTIFIER ::= { hwUpsMIBObjects 3 }

        hwUpsInputTable OBJECT-TYPE
            SYNTAX SEQUENCE OF HwUpsInputEntry
            MAX-ACCESS not-accessible
             STATUS current
             DESCRIPTION
                "UPS input information table. It's index is hwUpsDeviceId"
            ::= { hwUpsInput 100 }

        hwUpsInputEntry OBJECT-TYPE
                        SYNTAX HwUpsInputEntry
            MAX-ACCESS not-accessible
             STATUS current
             DESCRIPTION
                "UPS input information table. It's index is hwUpsDeviceId"
	    INDEX { hwUpsDeviceId }
            ::= { hwUpsInputTable 1 }

        HwUpsInputEntry            ::= SEQUENCE {
                hwUpsInputVoltageA
                    Unsigned32,
                hwUpsInputVoltageB
                    Unsigned32,
                hwUpsInputVoltageC
                    Unsigned32,
                hwUpsInputFrequency
                    Unsigned32,
                hwUpsInputCurrentA
                    Unsigned32,
                hwUpsInputCurrentB
                    Unsigned32,
                hwUpsInputCurrentC
                    Unsigned32,
                hwUpsInputPowerFactorA
                    Integer32,
                hwUpsInputPowerFactorB
                    Integer32,
                hwUpsInputPowerFactorC
                    Integer32,
                hwUpsInputLineVoltageAB
                    Unsigned32,
                hwUpsInputLineVoltageBC
                    Unsigned32,
                hwUpsInputLineVoltageCA
                    Unsigned32,
                hwUpsInputRowStatus
                    RowStatus
            }

        hwUpsInputVoltageA  OBJECT-TYPE
            SYNTAX Unsigned32 (0..10000)
            MAX-ACCESS read-only
            STATUS current
            DESCRIPTION
                "Input voltage phase A. The value ranges from 0 to 10000.
                  The value is accurate to one decimal place on the NetEco. The unit is V."
            ::= { hwUpsInputEntry 1 }

        hwUpsInputVoltageB  OBJECT-TYPE
            SYNTAX Unsigned32 (0..10000)
	    UNITS "V"
            MAX-ACCESS read-only
            STATUS current
            DESCRIPTION
                "Input voltage phase B. The value ranges from 0 to 10000.
                  The value is accurate to one decimal place on the NetEco. The unit is V."
            ::= { hwUpsInputEntry 2 }

        hwUpsInputVoltageC  OBJECT-TYPE
            SYNTAX Unsigned32 (0..10000)
	    UNITS "V"
            MAX-ACCESS read-only
            STATUS current
            DESCRIPTION
                "Input voltage phase C. The value ranges from 0 to 10000.
                  The value is accurate to one decimal place on the NetEco. The unit is V."
            ::= { hwUpsInputEntry 3 }

        hwUpsInputFrequency OBJECT-TYPE
            SYNTAX Unsigned32 (0..10000)
	    UNITS "Hz"
            MAX-ACCESS read-only
            STATUS current
            DESCRIPTION
                "Input frequency. The value ranges from 0 to 10000.
                  The value is accurate to two decimal place on the NetEco. The unit is Hz."
            ::= { hwUpsInputEntry 4 }

        hwUpsInputCurrentA  OBJECT-TYPE
            SYNTAX Unsigned32 (0..10000)
            MAX-ACCESS read-only
            STATUS current
            DESCRIPTION
                "Input current phase A. The value ranges from 0 to 10000.
                  The value is accurate to one decimal place on the NetEco. The unit is A."
            ::= { hwUpsInputEntry 5 }

        hwUpsInputCurrentB  OBJECT-TYPE
            SYNTAX Unsigned32 (0..10000)
	    UNITS "A"
            MAX-ACCESS read-only
            STATUS current
            DESCRIPTION
                "Input current phase B. The value ranges from 0 to 10000.
                  The value is accurate to one decimal place on the NetEco. The unit is A."
            ::= { hwUpsInputEntry 6 }

        hwUpsInputCurrentC  OBJECT-TYPE
            SYNTAX Unsigned32 (0..10000)
	    UNITS "A"
            MAX-ACCESS read-only
            STATUS current
            DESCRIPTION
                "Input current phase C. The value ranges from 0 to 10000.
                  The value is accurate to one decimal place on the NetEco. The unit is A."
            ::= { hwUpsInputEntry 7 }

        hwUpsInputPowerFactorA OBJECT-TYPE
            SYNTAX Integer32 ( -100..100)
            MAX-ACCESS read-only
            STATUS current
            DESCRIPTION
                "Phase A input power factor. The value ranges from -100 to 100.
                  The value is accurate to one decimal place on the NetEco."
            ::= { hwUpsInputEntry 8 }

        hwUpsInputPowerFactorB OBJECT-TYPE
            SYNTAX Integer32 ( -100..100)
            MAX-ACCESS read-only
            STATUS current
            DESCRIPTION
                "Phase B input power factor. The value ranges from -100 to 100.
                  The value is accurate to one decimal place on the NetEco."
            ::= { hwUpsInputEntry 9 }

        hwUpsInputPowerFactorC OBJECT-TYPE
            SYNTAX Integer32 ( -100..100)
            MAX-ACCESS read-only
            STATUS current
            DESCRIPTION
                "Phase C input power factor. The value ranges from -100 to 100.
                  The value is accurate to one decimal place on the NetEco."
            ::= { hwUpsInputEntry 10 }

        hwUpsInputLineVoltageAB OBJECT-TYPE
            SYNTAX Unsigned32 (0..20000)
            MAX-ACCESS read-only
            STATUS current
            DESCRIPTION
                "Input Line voltage AB. The value ranges from 0 to 20000.
                    The value is accurate to one decimal place on the NetEco. The unit is V."
            ::= { hwUpsInputEntry 11 }

        hwUpsInputLineVoltageBC OBJECT-TYPE
            SYNTAX Unsigned32 (0..20000)
            MAX-ACCESS read-only
            STATUS current
            DESCRIPTION
                "Input Line voltage BC. The value ranges from 0 to 20000.
                    The value is accurate to one decimal place on the NetEco. The unit is V."
            ::= { hwUpsInputEntry 12 }

        hwUpsInputLineVoltageCA OBJECT-TYPE
            SYNTAX Unsigned32 (0..20000)
            MAX-ACCESS read-only
            STATUS current
            DESCRIPTION
                "Input Line voltage CA. The value ranges from 0 to 20000.
                    The value is accurate to one decimal place on the NetEco. The unit is V."
            ::= { hwUpsInputEntry 13 }

        hwUpsInputRowStatus OBJECT-TYPE
            SYNTAX RowStatus
            MAX-ACCESS read-only
            STATUS current
            DESCRIPTION
                "RowStatus of UPS input information table."
            ::= { hwUpsInputEntry 100 }

        hwUpsOutput OBJECT IDENTIFIER ::= { hwUpsMIBObjects 4 }

        hwUpsOutputTable OBJECT-TYPE
            SYNTAX SEQUENCE OF HwUpsOutputEntry
            MAX-ACCESS not-accessible
             STATUS current
             DESCRIPTION
                "UPS output information table. It's index is hwUpsDeviceId."
            ::= { hwUpsOutput 100 }

        hwUpsOutputEntry OBJECT-TYPE
                        SYNTAX HwUpsOutputEntry
            MAX-ACCESS not-accessible
             STATUS current
             DESCRIPTION
                "UPS output information table. It's index is hwUpsDeviceId.
                "
	    INDEX { hwUpsDeviceId }
            ::= { hwUpsOutputTable 1 }

        HwUpsOutputEntry            ::= SEQUENCE {
                hwUpsOutputVoltageA
                    Unsigned32,
                hwUpsOutputVoltageB
                    Unsigned32,
                hwUpsOutputVoltageC
                    Unsigned32,
                hwUpsOutputCurrentA
                    Unsigned32,
                hwUpsOutputCurrentB
                    Unsigned32,
                hwUpsOutputCurrentC
                    Unsigned32,
                hwUpsOutputFrequency
                    Unsigned32,
                hwUpsOutputActivePowerA
                    Integer32,
                hwUpsOutputActivePowerB
                    Integer32,
                hwUpsOutputActivePowerC
                    Integer32,
                hwUpsOutputAppearancePowerA
                    Integer32,
                hwUpsOutputAppearancePowerB
                    Integer32,
                hwUpsOutputAppearancePowerC
                    Integer32,
                hwUpsOutputLoadA
                    Unsigned32,
                hwUpsOutputLoadB
                    Unsigned32,
                hwUpsOutputLoadC
                    Unsigned32,
                hwUpsOutputPowerRating
                    INTEGER,
                hwUpsOutputFrequencyRating
                    INTEGER,
                hwUpsOutputPowerFactorA
                    Integer32,
                hwUpsOutputPowerFactorB
                    Integer32,
                hwUpsOutputPowerFactorC
                    Integer32,
                hwUpsOutputLineVoltageAB
                    Unsigned32,
                hwUpsOutputLineVoltageBC
                    Unsigned32,
                hwUpsOutputLineVoltageCA
                    Unsigned32,
                hwUpsRackOutputPeakRatioA
                    Unsigned32,
                hwUpsRackOutputPeakRatioB
                    Unsigned32,
                hwUpsRackOutputPeakRatioC
                    Unsigned32,
                hwUpsOutputRowStatus
                    RowStatus
            }

        hwUpsOutputVoltageA OBJECT-TYPE
            SYNTAX Unsigned32 ( 0..10000)
	    UNITS "V"
            MAX-ACCESS read-only
            STATUS current
            DESCRIPTION
                "Rack phase A output voltage. The value ranges from 0 to 10000.
                  The value is accurate to one decimal place on the NetEco. The unit is V.
                "
            ::= { hwUpsOutputEntry 1 }

        hwUpsOutputVoltageB OBJECT-TYPE
            SYNTAX Unsigned32 ( 0..10000)
	    UNITS "V"
            MAX-ACCESS read-only
            STATUS current
            DESCRIPTION
                "Rack phase B output voltage. The value ranges from 0 to 10000.
                  The value is accurate to one decimal place on the NetEco. The unit is V."
            ::= { hwUpsOutputEntry 2 }

        hwUpsOutputVoltageC OBJECT-TYPE
            SYNTAX Unsigned32 ( 0..10000)
	    UNITS "V"
            MAX-ACCESS read-only
            STATUS current
            DESCRIPTION
                "Rack phase C output voltage. The value ranges from 0 to 10000.
                  The value is accurate to one decimal place on the NetEco. The unit is V."
            ::= { hwUpsOutputEntry 3 }

        hwUpsOutputCurrentA OBJECT-TYPE
            SYNTAX Unsigned32 ( 0..10000)
	    UNITS "A"
            MAX-ACCESS read-only
            STATUS current
            DESCRIPTION
                "Rack phase A output current. The value ranges from 0 to 10000.
                  The value is accurate to one decimal place on the NetEco. The unit is A."
            ::= { hwUpsOutputEntry 4 }

        hwUpsOutputCurrentB OBJECT-TYPE
            SYNTAX Unsigned32 ( 0..10000)
            MAX-ACCESS read-only
            STATUS current
            DESCRIPTION
                "Rack phase B output current. The value ranges from 0 to 10000.
                  The value is accurate to one decimal place on the NetEco. The unit is A."
            ::= { hwUpsOutputEntry 5 }

        hwUpsOutputCurrentC OBJECT-TYPE
            SYNTAX Unsigned32 ( 0..10000)
	    UNITS "A"
            MAX-ACCESS read-only
            STATUS current
            DESCRIPTION
                "Rack phase C output current. The value ranges from 0 to 10000.
                  The value is accurate to one decimal place on the NetEco. The unit is A."
            ::= { hwUpsOutputEntry 6 }

        hwUpsOutputFrequency OBJECT-TYPE
            SYNTAX Unsigned32 ( 0..10000)
	    UNITS "Hz"
            MAX-ACCESS read-only
            STATUS current
            DESCRIPTION
                "Rack output frequency. The value ranges from 0 to 10000.
                  The value is accurate to two decimal place on the NetEco. The unit is Hz."
            ::= { hwUpsOutputEntry 7 }

        hwUpsOutputActivePowerA OBJECT-TYPE
            SYNTAX Integer32 ( -12000..12000)
	    UNITS "kW"
            MAX-ACCESS read-only
            STATUS current
            DESCRIPTION
                "Rack phase A output active power. The value ranges from -12000 to 12000.
                  The value is accurate to one decimal place on the NetEco. The unit is kW."
            ::= { hwUpsOutputEntry 8 }

        hwUpsOutputActivePowerB OBJECT-TYPE
            SYNTAX Integer32 ( -12000..12000)
	    UNITS "kW"
            MAX-ACCESS read-only
            STATUS current
            DESCRIPTION
                "Rack phase B output active power. The value ranges from -12000 to 12000.
                  The value is accurate to one decimal place on the NetEco. The unit is kW."
            ::= { hwUpsOutputEntry 9 }

        hwUpsOutputActivePowerC OBJECT-TYPE
            SYNTAX Integer32 ( -12000..12000)
	    UNITS "kW"
            MAX-ACCESS read-only
            STATUS current
            DESCRIPTION
                "Rack phase C output active power. The value ranges from -12000 to 12000.
                  The value is accurate to one decimal place on the NetEco. The unit is kW."
            ::= { hwUpsOutputEntry 10 }

        hwUpsOutputAppearancePowerA OBJECT-TYPE
            SYNTAX Integer32 ( -12000..12000)
	    UNITS "kVA"
            MAX-ACCESS read-only
            STATUS current
            DESCRIPTION
                "Rack phase A output apparent power. The value ranges from -12000 to 12000.
                  The value is accurate to one decimal place on the NetEco. The unit is kVA."
            ::= { hwUpsOutputEntry 11 }

        hwUpsOutputAppearancePowerB OBJECT-TYPE
            SYNTAX Integer32 ( -12000..12000)
	    UNITS "kVA"
            MAX-ACCESS read-only
            STATUS current
            DESCRIPTION
                "Rack phase B output apparent power. The value ranges from -12000 to 12000.
                  The value is accurate to one decimal place on the NetEco. The unit is kVA."
            ::= { hwUpsOutputEntry 12 }

        hwUpsOutputAppearancePowerC OBJECT-TYPE
            SYNTAX Integer32 ( -12000..12000)
	    UNITS "kVA"
            MAX-ACCESS read-only
            STATUS current
            DESCRIPTION
                "Rack phase C output apparent power. The value ranges from -12000 to 12000.
                  The value is accurate to one decimal place on the NetEco. The unit is kVA."
            ::= { hwUpsOutputEntry 13 }

        hwUpsOutputLoadA OBJECT-TYPE
            SYNTAX Unsigned32 (0..999)
	    UNITS "%"
            MAX-ACCESS read-only
            STATUS current
            DESCRIPTION
                "Rack phase A output load ratio. The value ranges from 0 to 5000 The value is accurate to one decimal place on the NetEco."
            ::= { hwUpsOutputEntry 14 }

        hwUpsOutputLoadB OBJECT-TYPE
            SYNTAX Unsigned32 (0..999)
	    UNITS "%"
            MAX-ACCESS read-only
            STATUS current
            DESCRIPTION
                "Rack phase B output load ratio. The value ranges from 0 to 5000 The value is accurate to one decimal place on the NetEco."
            ::= { hwUpsOutputEntry 15 }

        hwUpsOutputLoadC OBJECT-TYPE
            SYNTAX Unsigned32 (0..999)
            MAX-ACCESS read-only
            STATUS current
            DESCRIPTION
                "Rack phase C output load ratio. The value ranges from 0 to 5000 The value is accurate to one decimal place on the NetEco."
            ::= { hwUpsOutputEntry 16 }

        hwUpsOutputPowerRating OBJECT-TYPE
            SYNTAX INTEGER
                {
                level200(1),
                level208(2),
                level220(3),
                level380(4),
                level400(5),
                level415(6),
                level480(7),
                level600(8),
                level690(9)
                }
            MAX-ACCESS read-only
            STATUS current
            DESCRIPTION
                "Rated output voltage (system voltage level). Enumeration type. The default value is 6. The unit is V.
                  Value 1 indicates 200 V.
                  Value 2 indicates 208 V.
                  Value 3 indicates 220 V.
                  Value 4 indicates 380 V.
                  Value 5 indicates 400 V.
                  Value 6 indicates 415 V.
                  Value 7 indicates 480 V.
                  Value 8 indicates 600 V.
                  Value 9 indicates 690 V."
            ::= { hwUpsOutputEntry 17 }

        hwUpsOutputFrequencyRating OBJECT-TYPE
            SYNTAX INTEGER
                {
                level50(1),
                level60(2)
                }
            MAX-ACCESS read-only
            STATUS current
            DESCRIPTION
                "Rated output frequency. Enumeration type. The default value is 2. The unit is Hz.
                  Value 1 indicates 50 Hz.
                  Value 2 indicates 60 Hz."
            ::= { hwUpsOutputEntry 18 }

        hwUpsOutputPowerFactorA OBJECT-TYPE
            SYNTAX Integer32 ( -100..100)
            MAX-ACCESS read-only
            STATUS current
            DESCRIPTION
                "Rack phase A output power factor.
                  The value ranges from -100 to 100 The value is accurate to two decimal place on the NetEco."
            ::= { hwUpsOutputEntry 19 }

        hwUpsOutputPowerFactorB OBJECT-TYPE
            SYNTAX Integer32 ( -100..100)
            MAX-ACCESS read-only
            STATUS current
            DESCRIPTION
                "Rack phase B output power factor.
                  The value ranges from -100 to 100 The value is accurate to two decimal place on the NetEco.
                "
            ::= { hwUpsOutputEntry 20 }

        hwUpsOutputPowerFactorC OBJECT-TYPE
            SYNTAX Integer32 ( -100..100)
            MAX-ACCESS read-only
            STATUS current
            DESCRIPTION
                "Rack phase C output power factor.
                  The value ranges from -100 to 100 The value is accurate to two decimal place on the NetEco."
            ::= { hwUpsOutputEntry 21 }

        hwUpsOutputLineVoltageAB OBJECT-TYPE
            SYNTAX Unsigned32 (0..20000)
            MAX-ACCESS read-only
            STATUS current
            DESCRIPTION
                "Rack Line AB output voltage. The value ranges from 0 to 20000.
                    The value is accurate to one decimal place on the NetEco. The unit is V."
            ::= { hwUpsOutputEntry 22 }

        hwUpsOutputLineVoltageBC OBJECT-TYPE
            SYNTAX Unsigned32 (0..20000)
            MAX-ACCESS read-only
            STATUS current
            DESCRIPTION
                "Rack Line BC output voltage. The value ranges from 0 to 20000.
                    The value is accurate to one decimal place on the NetEco. The unit is V."
            ::= { hwUpsOutputEntry 23 }

        hwUpsOutputLineVoltageCA OBJECT-TYPE
            SYNTAX Unsigned32 (0..20000)
            MAX-ACCESS read-only
            STATUS current
            DESCRIPTION
                "Rack Line CA output voltage. The value ranges from 0 to 20000.
                    The value is accurate to one decimal place on the NetEco. The unit is V."
            ::= { hwUpsOutputEntry 24 }

        hwUpsRackOutputPeakRatioA OBJECT-TYPE
            SYNTAX Unsigned32 (0..1000)
            MAX-ACCESS read-only
            STATUS current
            DESCRIPTION
                "Rack A Out Peak Ratio. The value ranges from 0 to 1000.
                    The value is accurate to one decimal place on the NetEco. The unit is %."
            ::= { hwUpsOutputEntry 25 }

        hwUpsRackOutputPeakRatioB OBJECT-TYPE
            SYNTAX Unsigned32 (0..1000)
            MAX-ACCESS read-only
            STATUS current
            DESCRIPTION
                "Rack B Out Peak Ratio. The value ranges from 0 to 1000.
                    The value is accurate to one decimal place on the NetEco. The unit is %."
            ::= { hwUpsOutputEntry 26 }

        hwUpsRackOutputPeakRatioC OBJECT-TYPE
            SYNTAX Unsigned32 (0..1000)
            MAX-ACCESS read-only
            STATUS current
            DESCRIPTION
                "Rack C Out Peak Ratio. The value ranges from 0 to 1000.
                    The value is accurate to one decimal place on the NetEco. The unit is %."
            ::= { hwUpsOutputEntry 27 }

        hwUpsOutputRowStatus OBJECT-TYPE
            SYNTAX RowStatus
            MAX-ACCESS read-only
            STATUS current
            DESCRIPTION
                "RowStatus of UPS output information table."
            ::= { hwUpsOutputEntry 100 }

        hwUpsBypass OBJECT IDENTIFIER ::= { hwUpsMIBObjects 5 }

        hwUpsBypassTable OBJECT-TYPE
            SYNTAX SEQUENCE OF HwUpsBypassEntry
            MAX-ACCESS not-accessible
             STATUS current
             DESCRIPTION
                "UPS bypass information table. It's index is hwUpsDeviceId."
            ::= { hwUpsBypass 100 }

        hwUpsBypassEntry OBJECT-TYPE
                        SYNTAX HwUpsBypassEntry
            MAX-ACCESS not-accessible
             STATUS current
             DESCRIPTION
                "UPS bypass information table. It's index is hwUpsDeviceId."
	    INDEX { hwUpsDeviceId }
            ::= { hwUpsBypassTable 1 }

        HwUpsBypassEntry            ::= SEQUENCE {
                hwUpsBypassInputVoltageA
                    Unsigned32,
                hwUpsBypassInputVoltageB
                    Unsigned32,
                hwUpsBypassInputVoltageC
                    Unsigned32,
                hwUpsBypassInputFrequency
                    Unsigned32,
                hwUpsBypassInputCurrentA
                    Unsigned32,
                hwUpsBypassInputCurrentB
                    Unsigned32,
                hwUpsBypassInputCurrentC
                    Unsigned32,
                hwUpsBypassInputLineVoltageAB
                    Unsigned32,
                hwUpsBypassInputLineVoltageBC
                    Unsigned32,
                hwUpsBypassInputLineVoltageCA
                    Unsigned32,
                hwUpsBypassRowStatus
                    RowStatus
            }

        hwUpsBypassInputVoltageA OBJECT-TYPE
            SYNTAX Unsigned32 ( 0..10000)
	    UNITS "V"
            MAX-ACCESS read-only
            STATUS current
            DESCRIPTION
                "Bypass input voltage phase A. The value ranges from 0 to 10000
                  The value is accurate to one decimal place on the NetEco. The unit is V."
            ::= { hwUpsBypassEntry 1 }

        hwUpsBypassInputVoltageB OBJECT-TYPE
            SYNTAX Unsigned32 ( 0..10000)
	    UNITS "V"
            MAX-ACCESS read-only
            STATUS current
            DESCRIPTION
                "Bypass input voltage phase B. The value ranges from 0 to 10000
                  The value is accurate to one decimal place on the NetEco. The unit is V."
            ::= { hwUpsBypassEntry 2 }

        hwUpsBypassInputVoltageC OBJECT-TYPE
            SYNTAX Unsigned32 ( 0..10000)
	    UNITS "V"
            MAX-ACCESS read-only
            STATUS current
            DESCRIPTION
                "Bypass input voltage phase C. The value ranges from 0 to 10000
                  The value is accurate to one decimal place on the NetEco. The unit is V."
            ::= { hwUpsBypassEntry 3 }

        hwUpsBypassInputFrequency OBJECT-TYPE
            SYNTAX Unsigned32 ( 0..10000)
	    UNITS "Hz"
            MAX-ACCESS read-only
            STATUS current
            DESCRIPTION
                "Bypass input frequency. The value ranges from 0 to 10000
                  The value is accurate to two decimal place on the NetEco. The unit is Hz."
            ::= { hwUpsBypassEntry 4 }

        hwUpsBypassInputCurrentA OBJECT-TYPE
            SYNTAX Unsigned32 (0..60000)
            MAX-ACCESS read-only
            STATUS current
            DESCRIPTION
                "Bypass input current phase A. The value ranges from 0 to 60000
                    The value is accurate to one decimal place on the NetEco. The unit is A."
            ::= { hwUpsBypassEntry 5 }

        hwUpsBypassInputCurrentB OBJECT-TYPE
            SYNTAX Unsigned32 (0..60000)
            MAX-ACCESS read-only
            STATUS current
            DESCRIPTION
                "Bypass input current phase B. The value ranges from 0 to 60000
                    The value is accurate to one decimal place on the NetEco. The unit is A."
            ::= { hwUpsBypassEntry 6 }

        hwUpsBypassInputCurrentC OBJECT-TYPE
            SYNTAX Unsigned32 (0..60000)
            MAX-ACCESS read-only
            STATUS current
            DESCRIPTION
                "Bypass input current phase C. The value ranges from 0 to 60000
                    The value is accurate to one decimal place on the NetEco. The unit is A."
            ::= { hwUpsBypassEntry 7 }

        hwUpsBypassInputLineVoltageAB OBJECT-TYPE
            SYNTAX Unsigned32 (0..20000)
            MAX-ACCESS read-only
            STATUS current
            DESCRIPTION
                "Bypass Input Line voltage AB. The value ranges from 0 to 20000.
                    The value is accurate to one decimal place on the NetEco. The unit is V."
            ::= { hwUpsBypassEntry 8 }

        hwUpsBypassInputLineVoltageBC OBJECT-TYPE
            SYNTAX Unsigned32 (0..20000)
            MAX-ACCESS read-only
            STATUS current
            DESCRIPTION
                "Bypass Input Line voltage BC. The value ranges from 0 to 20000.
                    The value is accurate to one decimal place on the NetEco. The unit is V."
            ::= { hwUpsBypassEntry 9 }

        hwUpsBypassInputLineVoltageCA OBJECT-TYPE
            SYNTAX Unsigned32 (0..20000)
            MAX-ACCESS read-only
            STATUS current
            DESCRIPTION
                "Bypass Input Line voltage CA. The value ranges from 0 to 20000.
                    The value is accurate to one decimal place on the NetEco. The unit is V."
            ::= { hwUpsBypassEntry 10 }

        hwUpsBypassRowStatus OBJECT-TYPE
            SYNTAX RowStatus
            MAX-ACCESS read-only
            STATUS current
            DESCRIPTION
                "RowStatus of UPS bypass information table."
            ::= { hwUpsBypassEntry 100 }

        hwUpsBattery OBJECT IDENTIFIER ::= { hwUpsMIBObjects 6 }

        hwUpsBatteryTable OBJECT-TYPE
            SYNTAX SEQUENCE OF HwUpsBatteryEntry
            MAX-ACCESS not-accessible
             STATUS current
             DESCRIPTION
                "UPS battery information table. It's index is hwUpsDeviceId."
            ::= { hwUpsBattery 100 }

        hwUpsBatteryEntry OBJECT-TYPE
                        SYNTAX HwUpsBatteryEntry
            MAX-ACCESS not-accessible
             STATUS current
             DESCRIPTION
                "UPS battery information table. It's index is hwUpsDeviceId."
	    INDEX { hwUpsDeviceId }
            ::= { hwUpsBatteryTable 1 }

        HwUpsBatteryEntry            ::= SEQUENCE {
                hwUpsBatteryVoltage
                    Unsigned32,
                hwUpsBatteryCurrent
                    Integer32,
                hwUpsBatteryCapacityLeft
                    Unsigned32,
                hwUpsBatteryBackupTime
                    Unsigned32,
                hwUpsBatteryNumber
                    Unsigned32,
                hwUpsBatterytemperature
                    Unsigned32,
                hwUpsBatterySoh
                    INTEGER,
                hwUpsBatteryRowStatus
                    RowStatus
            }

        hwUpsBatteryVoltage OBJECT-TYPE
            SYNTAX Unsigned32 (0..10000)
	    UNITS "V"
            MAX-ACCESS read-only
            STATUS current
            DESCRIPTION
                "Battery Voltage. It is a real-time analog parameter.
                  Value range: 0 to 20000, Unit: V, and the value is accurate to one decimal place (.1)."
            ::= { hwUpsBatteryEntry 1 }

        hwUpsBatteryCurrent OBJECT-TYPE
            SYNTAX Integer32 (-60000..60000)
	    UNITS "A"
            MAX-ACCESS read-only
            STATUS current
            DESCRIPTION
                "Battery Total Current. It is a real-time analog parameter.
                  Value range: -60000 to 60000, Unit: A, and the value is accurate to one decimal place (.1)."
            ::= { hwUpsBatteryEntry 2 }

        hwUpsBatteryCapacityLeft OBJECT-TYPE
            SYNTAX Unsigned32 (0..100)
	    UNITS "%"
            MAX-ACCESS read-only
            STATUS current
            DESCRIPTION
                "Battery Capacity Left. Value range: 0 to 100, Unit: %, and the value is an integer."
            ::= { hwUpsBatteryEntry 3 }

        hwUpsBatteryBackupTime OBJECT-TYPE
            SYNTAX Unsigned32 (0..172800)
	    UNITS "S"
            MAX-ACCESS read-only
            STATUS current
            DESCRIPTION
                "Battery Backup Time. Value range: 0 to 172800, Unit: S, and the value is an integer."
            ::= { hwUpsBatteryEntry 4 }

        hwUpsBatteryNumber OBJECT-TYPE
            SYNTAX Unsigned32 (1..240)
            MAX-ACCESS read-only
            STATUS current
            DESCRIPTION
                "Battery group number.Value range: 1 to 240,and the value is an integer."
            ::= { hwUpsBatteryEntry 5 }

        hwUpsBatterytemperature OBJECT-TYPE
            SYNTAX Unsigned32 (-200..800)
	    UNITS "C"
            MAX-ACCESS read-only
            STATUS current
            DESCRIPTION
                "Battery temperature.Value range: -20 to 80, Unit:C,  and the value is accurate to one decimal place (.1)"
            ::= { hwUpsBatteryEntry 6 }

        hwUpsBatterySoh OBJECT-TYPE
            SYNTAX INTEGER
                {

                good(1),
                 requiringMaintenance(2),
                 repalceBatt(3)

                }
            MAX-ACCESS read-only
            STATUS current
            DESCRIPTION
                "Description."
            ::= { hwUpsBatteryEntry 7 }

        hwUpsBatteryRowStatus OBJECT-TYPE
            SYNTAX RowStatus
            MAX-ACCESS read-only
            STATUS current
            DESCRIPTION
                "RowStatus of UPS battery information table."
            ::= { hwUpsBatteryEntry 100 }


		-- 1.3.6.1.4.1.2011.6.174.1.10
		hwUpsParallelSystem OBJECT IDENTIFIER ::= { hwUpsMIBObjects 10 }


		-- 1.3.6.1.4.1.2011.6.174.1.10.1
		hwUpsParaSysTable OBJECT-TYPE
			SYNTAX SEQUENCE OF HwUpsParaSysEntry
			MAX-ACCESS not-accessible
			STATUS current
			DESCRIPTION
				"UPS parallel system table. Its index is hwUpsDeviceId."
			::= { hwUpsParallelSystem 1 }


		-- 1.3.6.1.4.1.2011.6.174.1.10.1.1
		hwUpsParaSysEntry OBJECT-TYPE
			SYNTAX HwUpsParaSysEntry
			MAX-ACCESS not-accessible
			STATUS current
			DESCRIPTION
				"UPS parallel system table entry."
			INDEX { hwUpsDeviceId }
			::= { hwUpsParaSysTable 1 }


		HwUpsParaSysEntry ::=
			SEQUENCE {
				hwUpsParaSysId
					Unsigned32,
				hwUpsParaSysOutActivePowA
					Integer32,
				hwUpsParaSysOutActivePowB
					Integer32,
				hwUpsParaSysOutActivePowC
					Integer32,
				hwUpsParaSysOutAppearPowA
					Integer32,
				hwUpsParaSysOutAppearPowB
					Integer32,
				hwUpsParaSysOutAppearPowC
					Integer32,
				hwUpsParaSysOutLoadFactorA
					Unsigned32,
				hwUpsParaSysOutLoadFactorB
					Unsigned32,
				hwUpsParaSysOutLoadFactorC
					Unsigned32,
				hwUpsParallelSystemRowStatus
					RowStatus
			 }

		-- 1.3.6.1.4.1.2011.6.174.1.10.1.1.1
		hwUpsParaSysId OBJECT-TYPE
			SYNTAX Unsigned32 (0..127)
			MAX-ACCESS read-only
			STATUS current
			DESCRIPTION
				"ID of the parallel system that the current rack belongs to. "
			::= { hwUpsParaSysEntry 1 }


		-- 1.3.6.1.4.1.2011.6.174.1.10.1.1.2
		hwUpsParaSysOutActivePowA OBJECT-TYPE
			SYNTAX Integer32 (-120000..120000)
			UNITS "kW"
			MAX-ACCESS read-only
			STATUS current
			DESCRIPTION
				"System phase A output active power.The value ranges from -12000 to 12000,
				The value is accurate to one decimal place on the NetEco. The unit is kW."
			::= { hwUpsParaSysEntry 2 }


		-- 1.3.6.1.4.1.2011.6.174.1.10.1.1.3
		hwUpsParaSysOutActivePowB OBJECT-TYPE
			SYNTAX Integer32 (-120000..120000)
			UNITS "kW"
			MAX-ACCESS read-only
			STATUS current
			DESCRIPTION
				"System phase B output active power.The value ranges from -12000 to 12000,
				The value is accurate to one decimal place on the NetEco. The unit is kW."
			::= { hwUpsParaSysEntry 3 }


		-- 1.3.6.1.4.1.2011.6.174.1.10.1.1.4
		hwUpsParaSysOutActivePowC OBJECT-TYPE
			SYNTAX Integer32 (-120000..120000)
			UNITS "kW"
			MAX-ACCESS read-only
			STATUS current
			DESCRIPTION
				"System phase C output active power.The value ranges from -12000 to 12000,
				The value is accurate to one decimal place on the NetEco. The unit is kW."
			::= { hwUpsParaSysEntry 4 }


		-- 1.3.6.1.4.1.2011.6.174.1.10.1.1.5
		hwUpsParaSysOutAppearPowA OBJECT-TYPE
			SYNTAX Integer32 (-120000..120000)
			UNITS "kVA"
			MAX-ACCESS read-only
			STATUS current
			DESCRIPTION
				"System phase A output apparent power.The value ranges from -12000 to 12000,
				The value is accurate to one decimal place on the NetEco. The unit is kVA."
			::= { hwUpsParaSysEntry 5 }


		-- 1.3.6.1.4.1.2011.6.174.1.10.1.1.6
		hwUpsParaSysOutAppearPowB OBJECT-TYPE
			SYNTAX Integer32 (-120000..120000)
			UNITS "kVA"
			MAX-ACCESS read-only
			STATUS current
			DESCRIPTION
				"System phase B output apparent power.The value ranges from -12000 to 12000,
				The value is accurate to one decimal place on the NetEco. The unit is kVA."
			::= { hwUpsParaSysEntry 6 }


		-- 1.3.6.1.4.1.2011.6.174.1.10.1.1.7
		hwUpsParaSysOutAppearPowC OBJECT-TYPE
			SYNTAX Integer32 (-120000..120000)
			UNITS "kVA"
			MAX-ACCESS read-only
			STATUS current
			DESCRIPTION
				"System phase C output apparent power.The value ranges from -12000 to 12000,
				The value is accurate to one decimal place on the NetEco. The unit is kVA."
			::= { hwUpsParaSysEntry 7 }


		-- 1.3.6.1.4.1.2011.6.174.1.10.1.1.8
		hwUpsParaSysOutLoadFactorA OBJECT-TYPE
			SYNTAX Unsigned32 (0..5000)
			UNITS "%"
			MAX-ACCESS read-only
			STATUS current
			DESCRIPTION
				"System phase A output reactive power.The value ranges from 0 to 500,
				The value is accurate to one decimal place on the NetEco. The unit is %."
			::= { hwUpsParaSysEntry 8 }


		-- 1.3.6.1.4.1.2011.6.174.1.10.1.1.9
		hwUpsParaSysOutLoadFactorB OBJECT-TYPE
			SYNTAX Unsigned32 (0..5000)
			UNITS "%"
			MAX-ACCESS read-only
			STATUS current
			DESCRIPTION
				"System phase B output reactive power.The value ranges from 0 to 500,
				The value is accurate to one decimal place on the NetEco. The unit is %."
			::= { hwUpsParaSysEntry 9 }


		-- 1.3.6.1.4.1.2011.6.174.1.10.1.1.10
		hwUpsParaSysOutLoadFactorC OBJECT-TYPE
			SYNTAX Unsigned32 (0..5000)
			UNITS "%"
			MAX-ACCESS read-only
			STATUS current
			DESCRIPTION
				"System phase C output reactive power.The value ranges from 0 to 500,
				The value is accurate to one decimal place on the NetEco. The unit is %."
			::= { hwUpsParaSysEntry 10 }


		-- 1.3.6.1.4.1.2011.6.174.1.10.1.1.100
		hwUpsParallelSystemRowStatus OBJECT-TYPE
			SYNTAX RowStatus
			MAX-ACCESS read-only
			STATUS current
			DESCRIPTION
				"RowStatus of ups parallel System Identification table."
			::= { hwUpsParaSysEntry 100 }

        hwUpsSiteTime OBJECT IDENTIFIER ::= { hwUpsMIBObjects 11 }

        hwUpsSiteTimeUTC OBJECT-TYPE
            SYNTAX Unsigned32 (0..4294967295)
            MAX-ACCESS read-write
            STATUS current
            DESCRIPTION
                "UTC time, ranging from 0 to 4294967295.  The unit is seconds."
            ::= { hwUpsSiteTime 1 }

        hwUpsSiteTimeZone OBJECT-TYPE
	    SYNTAX Unsigned32
            MAX-ACCESS read-write
            STATUS obsolete
            DESCRIPTION
                "UTC time zone that the current rack belongs to."
            ::= { hwUpsSiteTime 2 }

        hwUpsAlarm OBJECT IDENTIFIER ::= { hwUpsMIBObjects 12 }

        hwUpsAlarmSynchronNum OBJECT-TYPE
            SYNTAX Unsigned32 (0..4294967295)
            MAX-ACCESS read-only
            STATUS current
            DESCRIPTION
                "Alarm synchronization ID. The value ranges from 0 to 4294967295.
                    This value is used by the NetEco to obtain the active alarm synchronization ID and synchronize alarms."
            ::= { hwUpsAlarm 1 }

        hwUpsAlarmCurrActiveNum OBJECT-TYPE
            SYNTAX Unsigned32 (0..8000)
            MAX-ACCESS read-only
            STATUS current
            DESCRIPTION
                "Number of active alarms, ranging from 0 to 8000."
            ::= { hwUpsAlarm 2 }

        hwUpsAlarmCurrCriticalNum OBJECT-TYPE
            SYNTAX Unsigned32 (0..8000)
            MAX-ACCESS read-only
            STATUS current
            DESCRIPTION
                "Number of critical active alarms, ranging from 0 to 8000."
            ::= { hwUpsAlarm 3 }

        hwUpsAlarmCurrMajorNum OBJECT-TYPE
            SYNTAX Unsigned32 (0..8000)
            MAX-ACCESS read-only
            STATUS current
            DESCRIPTION
                "Number of major active alarms, ranging from 0 to 8000."
            ::= { hwUpsAlarm 4 }

        hwUpsAlarmCurrMinorNum OBJECT-TYPE
            SYNTAX Unsigned32 (0..8000)
            MAX-ACCESS read-only
            STATUS current
            DESCRIPTION
                "Number of minor active alarms, ranging from 0 to 8000."
            ::= { hwUpsAlarm 5 }

        hwUpsAlarmCurrWarningNum OBJECT-TYPE
            SYNTAX Unsigned32 (0..8000)
            MAX-ACCESS read-only
            STATUS current
            DESCRIPTION
                "Number of warning active alarms, ranging from 0 to 8000."
            ::= { hwUpsAlarm 6 }

        hwUpsActiveAlarm OBJECT IDENTIFIER ::= { hwUpsMIBObjects 13 }

        hwUpsActiveAlarmTable OBJECT-TYPE
            SYNTAX SEQUENCE OF HwUpsActiveAlarmEntry
            MAX-ACCESS not-accessible
             STATUS current
             DESCRIPTION
                "UPS active alarm table. It's indexs are hwUpsActiveAlarmDeviceId and hwUpsActiveAlarmSeqId"
            ::= { hwUpsActiveAlarm 1 }

        hwUpsActiveAlarmEntry OBJECT-TYPE
                        SYNTAX HwUpsActiveAlarmEntry
            MAX-ACCESS not-accessible
             STATUS current
             DESCRIPTION
                "UPS active alarm table. It's indexs are hwUpsActiveAlarmDeviceId and hwUpsActiveAlarmSeqId"
	    INDEX { hwUpsActiveAlarmDeviceId, hwUpsActiveAlarmSeqId }
            ::= { hwUpsActiveAlarmTable 1 }

        HwUpsActiveAlarmEntry            ::= SEQUENCE {
                hwUpsActiveAlarmDeviceId
                    Unsigned32,
                hwUpsActiveAlarmSeqId
                    Unsigned32,
                hwUpsActiveAlarmEquipID
                    Unsigned32,
                hwUpsActiveAlarmID
                    Unsigned32,
                hwUpsActiveAlarmReasonId
                    Unsigned32,
                hwUpsActiveAlarmText
                    OCTET STRING,
                hwUpsActiveAlarmLevel
                    INTEGER,
                hwUpsActiveAlarmFlag
                    INTEGER,
                hwUpsActiveAlarmSynchronNum
                    Unsigned32,
                hwUpsActiveAlarmTime
                    Unsigned32,
                hwUpsActiveAlarmRowStatus
                    RowStatus
            }

        hwUpsActiveAlarmDeviceId OBJECT-TYPE
            SYNTAX Unsigned32 (1..100)
            MAX-ACCESS read-only
            STATUS current
            DESCRIPTION
                "ID of the device on which the active alarm is generated. An integer ranging from 1 to 100."
            ::= { hwUpsActiveAlarmEntry 1 }

        hwUpsActiveAlarmSeqId OBJECT-TYPE
            SYNTAX Unsigned32 (1..4294967295)
            MAX-ACCESS read-only
            STATUS current
            DESCRIPTION
                "Sequence number of an active alarm, ranging from 1 to 4294967295."
            ::= { hwUpsActiveAlarmEntry 2 }

        hwUpsActiveAlarmEquipID OBJECT-TYPE
            SYNTAX Unsigned32 (0..10000)
            MAX-ACCESS read-only
            STATUS current
            DESCRIPTION
                "Active alarm module ID, ranging from 1 to 10000."
            ::= { hwUpsActiveAlarmEntry 3 }

        hwUpsActiveAlarmID OBJECT-TYPE
            SYNTAX Unsigned32 (0..4294967295)
            MAX-ACCESS read-only
            STATUS current
            DESCRIPTION
                "ID of an active alarm, ranging from 0 to 4294967295."
            ::= { hwUpsActiveAlarmEntry 4 }

        hwUpsActiveAlarmReasonId OBJECT-TYPE
            SYNTAX Unsigned32 (0..100)
            MAX-ACCESS read-only
            STATUS current
            DESCRIPTION
                "Reason ID of an active alarm, ranging from 1 to 100."
            ::= { hwUpsActiveAlarmEntry 5 }

        hwUpsActiveAlarmText OBJECT-TYPE
            SYNTAX OCTET STRING (SIZE (0..127))
            MAX-ACCESS read-only
            STATUS current
            DESCRIPTION
                "English name of an active alarm. A string of characters. "
            ::= { hwUpsActiveAlarmEntry 6 }

        hwUpsActiveAlarmLevel OBJECT-TYPE
            SYNTAX INTEGER
                {
                critical(1),
                major(2),
                minor(3),
                warning(4)
                }
            MAX-ACCESS read-only
            STATUS current
            DESCRIPTION
                "Severity of an active alarm. Enumeration type.
                  Value 1 indicates a critical alarm.
                  Value 2 indicates a major alarm.
                  Value 3 indicates a minor alarm.
                  Value 4 indicates a warning."
            ::= { hwUpsActiveAlarmEntry 7 }

        hwUpsActiveAlarmFlag OBJECT-TYPE
            SYNTAX INTEGER
                {
                occur(1),
                resume(2)
                }
            MAX-ACCESS read-only
            STATUS current
            DESCRIPTION
                "Flag bit of an active alarm. Enumeration type.
                  Value 1 indicates that an active alarm is generated.
                  Value 2 indicates that an active alarm is cleared."
            ::= { hwUpsActiveAlarmEntry 8 }

        hwUpsActiveAlarmSynchronNum OBJECT-TYPE
            SYNTAX Unsigned32 (0..4294967295)
            MAX-ACCESS read-only
            STATUS current
            DESCRIPTION
                "Active alarm synchronization ID, ranging from 0 to 4294967295."
            ::= { hwUpsActiveAlarmEntry 9 }

        hwUpsActiveAlarmTime OBJECT-TYPE
            SYNTAX Unsigned32 (0..4294967295)
            MAX-ACCESS read-only
            STATUS current
            DESCRIPTION
                "Time when an active alarm is generated, ranging from 0 to 4294967295. The unit is seconds.
                "
            ::= { hwUpsActiveAlarmEntry 10 }

        hwUpsActiveAlarmRowStatus OBJECT-TYPE
            SYNTAX RowStatus
            MAX-ACCESS read-only
            STATUS current
            DESCRIPTION
                "RowStatus of ups active alarm table."
            ::= { hwUpsActiveAlarmEntry 11 }

        hwUpsModule OBJECT IDENTIFIER ::= { hwUpsMIBObjects 107 }

        hwUpsModuleTable OBJECT-TYPE
            SYNTAX SEQUENCE OF HwUpsModuleEntry
            MAX-ACCESS not-accessible
             STATUS current
             DESCRIPTION
                "Description."
            ::= { hwUpsModule 1 }

        hwUpsModuleEntry OBJECT-TYPE
                        SYNTAX HwUpsModuleEntry
            MAX-ACCESS not-accessible
             STATUS current
             DESCRIPTION
                "Description."
            INDEX { hwUpsModuleRackId }
            ::= { hwUpsModuleTable 1 }

        HwUpsModuleEntry            ::= SEQUENCE {
                hwUpsModuleRackId
                    Unsigned32,
                hwUpsPowerModuleId
                    Unsigned32,
                hwUpsBusCapacitorLife
                    Unsigned32,
                hwUpsInvACur
                    Unsigned32,
                hwUpsInvBCur
                    Unsigned32,
                hwUpsInvCCur
                    Unsigned32,
                hwUpsModuleAUnevenFlow
                    Unsigned32,
                hwUpsModuleBUnevenFlow
                    Unsigned32,
                hwUpsModuleCUnevenFlow
                    Unsigned32,
                hwUpsInvPowerStat
                    INTEGER,
                hwUpsModuleUnevneCurValueTag
                    Unsigned32,
                hwUpsModuleSleepState
                    Unsigned32,
                hwUpsModuleRowStatus
                    RowStatus
            }

        hwUpsModuleRackId OBJECT-TYPE
            SYNTAX Unsigned32 (1..6)
            MAX-ACCESS read-only
            STATUS current
            DESCRIPTION
                "Ups Rack Id.Range from 1 to 6.This node is referenced as an index node
                    by hwUpsModuleTable."
            ::= { hwUpsModuleEntry 1 }

        hwUpsPowerModuleId OBJECT-TYPE
            SYNTAX Unsigned32 (1..20)
            MAX-ACCESS read-only
            STATUS current
            DESCRIPTION
                "Ups Power Module Id.Range from 1 to 20.This node is referenced as an index node
                    by hwUpsModuleTable."
            ::= { hwUpsModuleEntry 2 }

        hwUpsBusCapacitorLife OBJECT-TYPE
            SYNTAX Unsigned32 (0..10000)
            MAX-ACCESS read-only
            STATUS current
            DESCRIPTION
                "Inv C Cap Life.Value range: 0 to 10000, Unit: Y, and the value is accurate to one decimal place (.1)."
            ::= { hwUpsModuleEntry 3 }

        hwUpsInvACur OBJECT-TYPE
            SYNTAX Unsigned32 (0..10000)
            MAX-ACCESS read-only
            STATUS current
            DESCRIPTION
                "Inv A Current.Value range: 0 to 10000.The value is accurate to one decimal place (.1).The unit is A."
            ::= { hwUpsModuleEntry 4 }

        hwUpsInvBCur OBJECT-TYPE
            SYNTAX Unsigned32 (0..10000)
            MAX-ACCESS read-only
            STATUS current
            DESCRIPTION
                "Inv B Current.Value range: 0 to 10000.The value is accurate to one decimal place (.1).The unit is A."
            ::= { hwUpsModuleEntry 5 }

        hwUpsInvCCur OBJECT-TYPE
            SYNTAX Unsigned32 (0..10000)
            MAX-ACCESS read-only
            STATUS current
            DESCRIPTION
                "Inv C Current.Value range: 0 to 10000.The value is accurate to one decimal place (.1).The unit is A."
            ::= { hwUpsModuleEntry 6 }

        hwUpsModuleAUnevenFlow OBJECT-TYPE
            SYNTAX Unsigned32 (0..10000)
            MAX-ACCESS read-only
            STATUS current
            DESCRIPTION
                "Module A Uneven Flow.Value range: 0 to 10000,and the value is accurate to one decimal place (.1)."
            ::= { hwUpsModuleEntry 7 }

        hwUpsModuleBUnevenFlow OBJECT-TYPE
            SYNTAX Unsigned32 (0..10000)
            MAX-ACCESS read-only
            STATUS current
            DESCRIPTION
                "Module B Uneven Flow.Value range: 0 to 10000,and the value is accurate to one decimal place (.1)."
            ::= { hwUpsModuleEntry 8 }

        hwUpsModuleCUnevenFlow OBJECT-TYPE
            SYNTAX Unsigned32 (0..1000)
            MAX-ACCESS read-only
            STATUS current
            DESCRIPTION
                "Module C Uneven Flow.Value range: 0 to 10000,and the value is accurate to one decimal place (.1)."
            ::= { hwUpsModuleEntry 9 }

        hwUpsInvPowerStat OBJECT-TYPE
            SYNTAX INTEGER
                {
                noOutput(1),
                    bypass(2),
                    normal(3)
                }
            MAX-ACCESS read-only
            STATUS current
            DESCRIPTION
                "Inv Power Stat.Enumeration type.
                    Value 0 indicates no power supply.
                    Value 1 indicates bypass mode.
                    Value 2 indicates normal mode."
            ::= { hwUpsModuleEntry 10 }

        hwUpsModuleUnevneCurValueTag OBJECT-TYPE
            SYNTAX Unsigned32 (0..1)
            MAX-ACCESS read-only
            STATUS current
            DESCRIPTION
                "Module uneven current value tag.range 0 to 1,0 indicates invalid,1 indicates valid."
            ::= { hwUpsModuleEntry 11 }

        hwUpsModuleSleepState OBJECT-TYPE
            SYNTAX Unsigned32 (0..1)
            MAX-ACCESS read-only
            STATUS current
            DESCRIPTION
                "Module Sleep State.Range 0 to 1,0 indicates not sleep,1 indicates sleep."
            ::= { hwUpsModuleEntry 12 }

        hwUpsModuleRowStatus OBJECT-TYPE
            SYNTAX RowStatus
            MAX-ACCESS read-only
            STATUS current
            DESCRIPTION
                "RowStatus of UPS module information table."
            ::= { hwUpsModuleEntry 100 }

        hwUpsControl OBJECT IDENTIFIER ::= { hwUpsMIBObjects 102 }

        hwUpsControlTable OBJECT-TYPE
            SYNTAX SEQUENCE OF HwUpsControlEntry
            MAX-ACCESS not-accessible
             STATUS current
             DESCRIPTION
                "UPS control table. It's index is hwUpsRackId."
            ::= { hwUpsControl 100 }

        hwUpsControlEntry OBJECT-TYPE
                        SYNTAX HwUpsControlEntry
            MAX-ACCESS not-accessible
             STATUS current
             DESCRIPTION
                "UPS control table. It's index is hwUpsRackId."
	    INDEX { hwUpsDeviceId }
            ::= { hwUpsControlTable 1 }

        HwUpsControlEntry            ::= SEQUENCE {
                hwUpsCtrlECOSwitch
                    INTEGER,
                hwUpsCtrlPowerOn
                    INTEGER,
                hwUpsCtrlPowerOff
                    INTEGER,
                hwUpsCtrlPowerOffDelay
                    Unsigned32,
                hwUpsCtrlPowerBatCapacity
                    Unsigned32,
                hwUpsCtrlPowerBatType
                    INTEGER,
                hwUpsCtrlModelType
                    INTEGER,
                hwUpsCtrlInputStandard
                    INTEGER,
                hwUpsCtrlOutputStandard
                    INTEGER,
                hwUpsCtrlPowerOnState
                    INTEGER,
                hwUpsCtrlBatteryToBoostState
                    INTEGER,
                hwUpsCtrlBatteryToFloatState
                    INTEGER,
                hwUpsCtrlBatteryToTestState
                    INTEGER,
                hwUpsCtrlBatteryStopTestState
                    INTEGER,
                hwUpsCtrlBatteryManualBoostCharge
                    INTEGER,
                hwUpsCtrlBatteryManualFloatCharge
                    INTEGER,
                hwUpsCtrlBatteryShallowTest
                    INTEGER,
                hwUpsCtrlBatteryVerifyCapTest
                    INTEGER,
                hwUpsCtrlBatteryEndTest
                    INTEGER,
                hwUpsCtrlModelCapacity
                    Unsigned32,
                hwUpsCtrlEPO
                    INTEGER,
                hwUpsSmartParallelSleepMode
                    INTEGER,
                hwUpsCtrlRowStatus
                    RowStatus
            }

        hwUpsCtrlECOSwitch OBJECT-TYPE
            SYNTAX INTEGER
                {
                noECO(1),
                eco(2)
                }
            MAX-ACCESS read-only
            STATUS current
            DESCRIPTION
                "ECO settings. Enumeration type. The default value is 1.
                  Value 1 indicates ECO mode.
                  Value 2 indicates Non ECO mode."
            ::= { hwUpsControlEntry 1 }

        hwUpsCtrlPowerOn OBJECT-TYPE
            SYNTAX INTEGER
                {
                powerOn(1),
                    unknown(255)
                }
            MAX-ACCESS read-only
            STATUS current
            DESCRIPTION
                "Power on settings. Enumeration type.
                    Value 1 indicates power on .
                    Value 2 indicates unknow."
            ::= { hwUpsControlEntry 2 }

        hwUpsCtrlPowerOff OBJECT-TYPE
            SYNTAX INTEGER
                {
                powerOff(1),
                    unknown(255)
                }
            MAX-ACCESS read-only
            STATUS current
            DESCRIPTION
                "Power off settings. Enumeration type.
                    Value 1 indicates power off .
                    Value 2 indicates unknow."
            ::= { hwUpsControlEntry 3 }

        hwUpsCtrlPowerOffDelay OBJECT-TYPE
            SYNTAX Unsigned32 (0..120000000)
	    UNITS "S"
            MAX-ACCESS read-only
            STATUS obsolete
            DESCRIPTION
                "Delay power off.The value ranges from 0 to 120000000 . The unit is S."
            ::= { hwUpsControlEntry 4 }

        hwUpsCtrlPowerBatCapacity OBJECT-TYPE
            SYNTAX Unsigned32 (5..3000)
            MAX-ACCESS read-only
            STATUS current
            DESCRIPTION
                "Battery capacity, ranging from 5 to 3000.
                "
            ::= { hwUpsControlEntry 5 }

        hwUpsCtrlPowerBatType OBJECT-TYPE
            SYNTAX INTEGER
                {
                 vrla(1)
                }
            MAX-ACCESS read-only
            STATUS current
            DESCRIPTION
                "Battery type.ECO settings. Enumeration type. The default value is 1.
                  Value 1 indicates VRLA batteries."
            ::= { hwUpsControlEntry 6 }

        hwUpsCtrlModelType OBJECT-TYPE
            SYNTAX INTEGER
                {
                model6K(17),
                 mode110K(33),
                 model20K(65)
                }
            MAX-ACCESS read-only
            STATUS obsolete
            DESCRIPTION
                "Model type,Enumeration type.
                    Value 17 indicates 6K.
                    Value 33 indicates 10K.
                    Value 65 indicates 20K."
            ::= { hwUpsControlEntry 7 }

        hwUpsCtrlInputStandard OBJECT-TYPE
            SYNTAX INTEGER
                {
                singlePhase(1),
                    threePhase(2)
                }
            MAX-ACCESS read-only
            STATUS obsolete
            DESCRIPTION
                "Input Standard,Enumeration type.
                    Value 1 indicates single phase.
                    Value 2 indicates three phase."
            ::= { hwUpsControlEntry 8 }

        hwUpsCtrlOutputStandard OBJECT-TYPE
            SYNTAX INTEGER
                {
                singlePhase(1)
                    threePhase(2)
                }
            MAX-ACCESS read-only
            STATUS obsolete
            DESCRIPTION
                "Output Standard,Enumeration type.
                    Value 1 indicates single phase.
                    Value 2 indicates three phase."
            ::= { hwUpsControlEntry 9 }

        hwUpsCtrlPowerOnState OBJECT-TYPE
            SYNTAX INTEGER
                {
                powerOff(1),
                 powerOn(2),
                 powerOnFail(3),
                 powerOnComplete(4)
                }
            MAX-ACCESS read-only
            STATUS obsolete
            DESCRIPTION
                "Power On State,Enumeration type.
                    Value 1 indicates power off.
                    Value 2 indicates booting.
                    Value 3 indicates failed to power on.
                    Value 4 indicates succeed tp power on."
            ::= { hwUpsControlEntry 10 }

        hwUpsCtrlBatteryToBoostState OBJECT-TYPE
            SYNTAX INTEGER
                {
                enable(1),
                 disable(2)
                }
            MAX-ACCESS read-only
            STATUS obsolete
            DESCRIPTION
                "Battery Change to Boost Charge State,Enumeration type.
                    Value 1 indicates enabled.
                    Value 2 indicates disabled."
            ::= { hwUpsControlEntry 11 }

        hwUpsCtrlBatteryToFloatState OBJECT-TYPE
            SYNTAX INTEGER
                {
                enable(1),
                    disable(2)
                }
            MAX-ACCESS read-only
            STATUS obsolete
            DESCRIPTION
                "Battery Change to Float Charge State,Enumeration type.
                    Value 1 indicates enabled.
                    Value 2 indicates disabled."
            ::= { hwUpsControlEntry 12 }

        hwUpsCtrlBatteryToTestState OBJECT-TYPE
            SYNTAX INTEGER
                {
                enable(1),
                 disable(2),
                 shallow(3)
                }
            MAX-ACCESS read-only
            STATUS obsolete
            DESCRIPTION
                "Battery Change to Test State,Enumeration type.
                    Value 1 indicates enabled.
                    Value 2 indicates disabled."
            ::= { hwUpsControlEntry 13 }

        hwUpsCtrlBatteryStopTestState OBJECT-TYPE
            SYNTAX INTEGER
                {
                enable(1),
                 disable(2)
                }
            MAX-ACCESS read-only
            STATUS obsolete
            DESCRIPTION
                "Battery Stop Test State,Enumeration type.
                    Value 1 indicates enabled.
                    Value 2 indicates disabled."
            ::= { hwUpsControlEntry 14 }

        hwUpsCtrlBatteryManualBoostCharge OBJECT-TYPE
            SYNTAX INTEGER
                {
                toBoostCharge(1),
                    unknown(255)
                }
            MAX-ACCESS read-only
            STATUS obsolete
            DESCRIPTION
                "Battery Manual to Boost Charge,Enumeration type.
                    Value 1 indicates enabled.
                    Value 2 indicates disabled."
            ::= { hwUpsControlEntry 15 }

        hwUpsCtrlBatteryManualFloatCharge OBJECT-TYPE
            SYNTAX INTEGER
                {
                toFloatCharge(1),
                    unknown(255)
                }
            MAX-ACCESS read-only
            STATUS obsolete
            DESCRIPTION
                "Battery Manual to Float Charge,Enumeration type.
                    Value 1 indicates enabled.
                    Value 2 indicates unknown"
            ::= { hwUpsControlEntry 16 }

        hwUpsCtrlBatteryShallowTest OBJECT-TYPE
            SYNTAX INTEGER
                {
                toShallowTest(1),
                 unknown(255)
                }
            MAX-ACCESS read-only
            STATUS obsolete
            DESCRIPTION
                "Battery Shallow Test,Enumeration type.
                    Value 1 indicates enabled.
                    Value 2 indicates unknown"
            ::= { hwUpsControlEntry 17 }

        hwUpsCtrlBatteryVerifyCapTest OBJECT-TYPE
            SYNTAX INTEGER
                {
                toVerifyCapTest(1),
                 unknown(255)
                }
            MAX-ACCESS read-only
            STATUS obsolete
            DESCRIPTION
                "Battery Verify Cap Test,Enumeration type.
                    Value 1 indicates enabled.
                    Value 2 indicates unknown"
            ::= { hwUpsControlEntry 18 }

        hwUpsCtrlBatteryEndTest OBJECT-TYPE
            SYNTAX INTEGER
                {
                toEndTest(1),
                 unknown(255)
                }
            MAX-ACCESS read-only
            STATUS obsolete
            DESCRIPTION
                "Battery End Test,Enumeration type.
                    Value 1 indicates enabled.
                    Value 2 indicates unknown"
            ::= { hwUpsControlEntry 19 }

        hwUpsCtrlModelCapacity OBJECT-TYPE
            SYNTAX Unsigned32 (0..200)
            MAX-ACCESS read-only
            STATUS obsolete
            DESCRIPTION
                "Model Capacity.The value ranges from 0 to 200, The value is accurate to one decimal place on the NetEco. The unit is kVA."
            ::= { hwUpsControlEntry 20 }

        hwUpsCtrlEPO OBJECT-TYPE
            SYNTAX INTEGER
                {
                epo(1),
                    unknown(2)
                }
            MAX-ACCESS read-only
            STATUS obsolete
            DESCRIPTION
                "EPO. Enumeration type.
                    Value 1 indicates EPO .
                    Value 255 indicates unknown."
            ::= { hwUpsControlEntry 21 }

        hwUpsSmartParallelSleepMode OBJECT-TYPE
            SYNTAX INTEGER
                {
                disable(1),
                    enable(2)
                }
            MAX-ACCESS read-write
            STATUS current
            DESCRIPTION
                "Smart Parallel Sleep Mode.Enumeration type.The default value is 0.
                    Value 0 indicates disable.
                    Value 1 indicates enable."
            ::= { hwUpsControlEntry 22 }

        hwUpsCtrlRowStatus OBJECT-TYPE
            SYNTAX RowStatus
            MAX-ACCESS read-only
            STATUS current
            DESCRIPTION
                "RowStatus of UPS rack control table."
            ::= { hwUpsControlEntry 100 }

        hwUpsTest OBJECT IDENTIFIER ::= { hwUpsMIBObjects 103 }

        hwUpsBattScheduleTestTable OBJECT-TYPE
            SYNTAX SEQUENCE OF HwUpsBattScheduleTestEntry
            MAX-ACCESS not-accessible
             STATUS current
             DESCRIPTION
                "Battery schedule test table. It's index is hwUpsDeviceId."
            ::= { hwUpsTest 101 }

        hwUpsBattScheduleTestEntry OBJECT-TYPE
                        SYNTAX HwUpsBattScheduleTestEntry
            MAX-ACCESS not-accessible
             STATUS current
             DESCRIPTION
                "Battery schedule test table. It's index is hwUpsDeviceId."
	    INDEX { hwUpsDeviceId }
            ::= { hwUpsBattScheduleTestTable 1 }

        HwUpsBattScheduleTestEntry            ::= SEQUENCE {
                hwUpsBattAutoTest
                    INTEGER,
                hwUpsBattAutoTestTimeLimit
                    INTEGER,
                hwUpsBattAutoTestTimeInterval
                    Unsigned32,
                hwUpsBattAutoTestDischargeRate
                    Unsigned32,
                hwUpsBattAutoTestEndVol
                    Unsigned32,
                hwUpsBattTest
                    INTEGER,
                hwUpsBattScheduleTestRowStatus
                    RowStatus
            }

        hwUpsBattAutoTest OBJECT-TYPE
            SYNTAX INTEGER
                {
                disable(1),
                 enalbe(2)
                }
            MAX-ACCESS read-write
            STATUS current
            DESCRIPTION
                "Scheduled shallow discharge test enabled or disabled. Enumeration value.
                  The value 1 indicates that the test is disabled.
                  The value 2 indicates that the test is enabled."
            ::= { hwUpsBattScheduleTestEntry 1 }

        hwUpsBattAutoTestTimeLimit OBJECT-TYPE
            SYNTAX INTEGER
                {
                from0to6(1),
                 from6to12(2),
                from12to18(3),
                 from18to24(4)
                }
            MAX-ACCESS read-write
            STATUS current
            DESCRIPTION
                "Scheduled shallow discharge test time. Enumeration value.
                  Value 1 indicates 00:00 to 06:00.
                  Value 2 indicates 06:00 to 12:00.
                  Value 3 indicates 12:00 to 18:00.
                  Value 4 indicates 18:00 to 00:00."
            ::= { hwUpsBattScheduleTestEntry 2 }

        hwUpsBattAutoTestTimeInterval OBJECT-TYPE
            SYNTAX Unsigned32 (30..90)
	    UNITS "Day"
            MAX-ACCESS read-write
            STATUS current
            DESCRIPTION
                "Scheduled shallow discharge test interval. An integer ranging from 30 to 90. The unit is days."
            ::= { hwUpsBattScheduleTestEntry 3 }

        hwUpsBattAutoTestDischargeRate OBJECT-TYPE
            SYNTAX Unsigned32 (10..50)
            MAX-ACCESS read-write
            STATUS current
            DESCRIPTION
                "Shallow discharge test discharge ratio. An integer ranging from 10 to 50. .
                "
            ::= { hwUpsBattScheduleTestEntry 4 }

        hwUpsBattAutoTestEndVol OBJECT-TYPE
            SYNTAX Unsigned32 (160..195)
            MAX-ACCESS read-write
            STATUS obsolete
            DESCRIPTION
                "Maximum battery discharge time. An integer ranging from 160 to 195. The value is accurate to one decimal place on the NetEco. The unit is V/Cell.
                "
            ::= { hwUpsBattScheduleTestEntry 5 }

        hwUpsBattTest OBJECT-TYPE
            SYNTAX INTEGER
                {
                noTestInit(1),
                 stopTest(2),
                 scheduleTest(3),
                 shallowDsgTest(4),
                 verufyDsgTest(5)
                }
            MAX-ACCESS read-only
            STATUS obsolete
            DESCRIPTION
                "If you set the value to shallowDsgTest(4), you can perform a shallow discharge test; if you set the value to verifyDsgTest(5), you can perform a capacity test; if you set the value to stopTest(2), you can stop the test. Other settings are invalid. If you start a test when other tests are in progress, error code 4 is returned.
                  During test, you can use this node to obtain the current or previous test type.
                  If you have never started the battery test sheduleTest(3), shallowDsgTest(4), or verifyDsgTest(5), this node returns noTestInit(1)."
            ::= { hwUpsBattScheduleTestEntry 6 }

        hwUpsBattScheduleTestRowStatus OBJECT-TYPE
            SYNTAX RowStatus
            MAX-ACCESS read-only
            STATUS current
            DESCRIPTION
                "RowStatus of UPS Battery control table. "
            ::= { hwUpsBattScheduleTestEntry 100 }

        hwUpsiBOX OBJECT IDENTIFIER ::= { hwUpsMIBObjects 110 }

        hwUpsBatteryGroupNum OBJECT-TYPE
            SYNTAX Unsigned32 (0..4)
            MAX-ACCESS read-only
            STATUS current
            DESCRIPTION
                "Number of battery group in UPS,ranging from 0 to 4.
                "
            ::= { hwUpsiBOX 1 }

        hwUpsBatteryNumInBatteryGroup OBJECT-TYPE
            SYNTAX Unsigned32 (0..300)
            MAX-ACCESS read-only
            STATUS current
            DESCRIPTION
                "Number of battery in one battery group,ranging from 0 to 300.
                "
            ::= { hwUpsiBOX 2 }

        hwUpsiBOXNum OBJECT-TYPE
            SYNTAX Unsigned32 (0..4)
            MAX-ACCESS read-only
            STATUS current
            DESCRIPTION
                "Number of iBOX in UPS,ranging from 0 to 4."
            ::= { hwUpsiBOX 3 }

        hwUpsBatteryGroupTable OBJECT-TYPE
            SYNTAX SEQUENCE OF HwUpsBatteryGroupEntry
            MAX-ACCESS not-accessible
             STATUS current
             DESCRIPTION
                "UPS battery group table. It's index is hwUpsBatteryGroupNo.
                "
            ::= { hwUpsiBOX 4 }

        hwUpsBatteryGroupEntry OBJECT-TYPE
                        SYNTAX HwUpsBatteryGroupEntry
            MAX-ACCESS not-accessible
             STATUS current
             DESCRIPTION
                "UPS battery group table. It's index is hwUpsBatteryGroupNo.
                "
            INDEX { hwUpsBatteryGroupNo }
            ::= { hwUpsBatteryGroupTable 1 }

        HwUpsBatteryGroupEntry            ::= SEQUENCE {
                hwUpsBatteryGroupNo
                    Unsigned32,
                hwUpsBatteryGroupVolt
                    Unsigned32,
                hwUpsBatteryGroupCur
                    Integer32,
                hwUpsBatteryGroupSOC
                    Unsigned32,
                hwUpsBatteryGroupBackupTime
                    Unsigned32,
                hwUpsBatteryGroupSOH
                    INTEGER,
                hwUpsBatteryGroupRowStatus
                    RowStatus
            }

        hwUpsBatteryGroupNo OBJECT-TYPE
            SYNTAX Unsigned32 (1..4)
            MAX-ACCESS read-only
            STATUS current
            DESCRIPTION
                "No of battery group,ranging from 1 to 4.This node is referenced as an index node
                  by hwUpsBatteryGroupTable.
                "
            ::= { hwUpsBatteryGroupEntry 1 }

        hwUpsBatteryGroupVolt OBJECT-TYPE
            SYNTAX Unsigned32 (0..10000)
            MAX-ACCESS read-only
            STATUS current
            DESCRIPTION
                "The Voltage of battery group,ranging from 0 to 10000.
                  The value is accurate to one decimal place on the NetEco. The unit is V."
            ::= { hwUpsBatteryGroupEntry 2 }

        hwUpsBatteryGroupCur OBJECT-TYPE
            SYNTAX Integer32 (-30000..30000)
            MAX-ACCESS read-only
            STATUS current
            DESCRIPTION
                "The Current of battery group,ranging from -30000 to 30000.
                  The value is accurate to one decimal place on the NetEco. The unit is A."
            ::= { hwUpsBatteryGroupEntry 3 }

        hwUpsBatteryGroupSOC OBJECT-TYPE
            SYNTAX Unsigned32 (0..100)
            MAX-ACCESS read-only
            STATUS current
            DESCRIPTION
                "The SOC of battery group,ranging from 0 to 100.The unit is %."
            ::= { hwUpsBatteryGroupEntry 4 }

        hwUpsBatteryGroupBackupTime OBJECT-TYPE
            SYNTAX Unsigned32 ( 0..999)
            MAX-ACCESS read-only
            STATUS current
            DESCRIPTION
                "The Backup Time of battery group,ranging from 0 to 999.The unit is min.
                "
            ::= { hwUpsBatteryGroupEntry 5 }

        hwUpsBatteryGroupSOH OBJECT-TYPE
            SYNTAX INTEGER
                {
                good(1),
                requiringMaintenance(2),
                 needReplaceBatt(3)
                }
            MAX-ACCESS read-only
            STATUS current
            DESCRIPTION
                "The SOH of battery group. Enumeration type.
                  Value 0 indicates good.
                  Value 1 indicates requiring maintenance.
                  Value 2 indicates need replace batt.
                "
            ::= { hwUpsBatteryGroupEntry 6 }

        hwUpsBatteryGroupRowStatus OBJECT-TYPE
            SYNTAX RowStatus
            MAX-ACCESS read-only
            STATUS current
            DESCRIPTION
                "Row status of hwUpsBatteryGroupTable."
            ::= { hwUpsBatteryGroupEntry 100 }

        hwUpsiBOXTable OBJECT-TYPE
            SYNTAX SEQUENCE OF HwUpsiBOXEntry
            MAX-ACCESS not-accessible
             STATUS current
             DESCRIPTION
                "CIM table. It's index is hwUpsCIMNo."
            ::= { hwUpsiBOX 5 }

        hwUpsiBOXEntry OBJECT-TYPE
                        SYNTAX HwUpsiBOXEntry
            MAX-ACCESS not-accessible
             STATUS current
             DESCRIPTION
                "CIM table. It's index is hwUpsCIMNo."
            INDEX { hwUpsiBOXNo }
            ::= { hwUpsiBOXTable 1 }

        HwUpsiBOXEntry            ::= SEQUENCE {
                hwUpsiBOXNo
                    Unsigned32,
                hwUpsiBOXSoftVersion
                    Unsigned32,
                hwUpsiBOXiBATNum
                    Unsigned32,
                hwUpsiBOXRowStatus
                    RowStatus
            }

        hwUpsiBOXNo OBJECT-TYPE
            SYNTAX Unsigned32 (1..4)
            MAX-ACCESS read-only
            STATUS current
            DESCRIPTION
                "No of iBOX,ranging from 1 to 4.This node is referenced as an index node by hwUpsiBOXTable."
            ::= { hwUpsiBOXEntry 1 }

        hwUpsiBOXSoftVersion OBJECT-TYPE
            SYNTAX Unsigned32 (0..4294967295)
            MAX-ACCESS read-only
            STATUS current
            DESCRIPTION
                "The software version of iBOX,ranging from 0 to 4294967295."
            ::= { hwUpsiBOXEntry 2 }

        hwUpsiBOXiBATNum OBJECT-TYPE
            SYNTAX Unsigned32 (0..300)
            MAX-ACCESS read-only
            STATUS current
            DESCRIPTION
                "iBAT number of one iBOX,ranging from 0 to 300."
            ::= { hwUpsiBOXEntry 3 }

        hwUpsiBOXRowStatus OBJECT-TYPE
            SYNTAX RowStatus
            MAX-ACCESS read-only
            STATUS current
            DESCRIPTION
                "Row status of hwUpsiBOXTable."
            ::= { hwUpsiBOXEntry 100 }

        hwUpsBattGroupRelaiBOXTable OBJECT-TYPE
            SYNTAX SEQUENCE OF HwUpsBattGroupRelaiBOXEntry
            MAX-ACCESS not-accessible
             STATUS current
             DESCRIPTION
                "UPS battery group related CIM Table. It's index is hwUpsBattGrpNo and hwUpsBattGroupRelaCIMNo.
                "
            ::= { hwUpsiBOX 6 }

        hwUpsBattGroupRelaiBOXEntry OBJECT-TYPE
                        SYNTAX HwUpsBattGroupRelaiBOXEntry
            MAX-ACCESS not-accessible
             STATUS current
             DESCRIPTION
                "UPS battery group related CIM Table. It's index is hwUpsBattGrpNo and hwUpsBattGroupRelaCIMNo.
                "
            INDEX { hwUpsBattGrpNo }
            ::= { hwUpsBattGroupRelaiBOXTable 1 }

        HwUpsBattGroupRelaiBOXEntry            ::= SEQUENCE {
                hwUpsBattGrpNo
                    Unsigned32,
                hwUpsBattGroupRelaiBOXNo
                    Unsigned32,
                hwUpsBattGroupRelaiBATStartNo
                    Unsigned32,
                hwUpsBattGroupRelaiBATEndNo
                    Unsigned32,
                hwUpsBattGroupRelaiBOXRowStatus
                    RowStatus
            }

        hwUpsBattGrpNo OBJECT-TYPE
            SYNTAX Unsigned32 (1..4)
            MAX-ACCESS read-only
            STATUS current
            DESCRIPTION
                "No of battery group,ranging from 1 to 4.This node is referenced as an index node
                  by hwUpsBattGrpRelaiBOXTable."
            ::= { hwUpsBattGroupRelaiBOXEntry 1 }

        hwUpsBattGroupRelaiBOXNo OBJECT-TYPE
            SYNTAX Unsigned32 (1..4)
            MAX-ACCESS read-only
            STATUS current
            DESCRIPTION
                "No of iBOX,ranging from 1 to 4.This node is referenced as an index node
                  by hwUpsBattGrpRelaiBOXTable."
            ::= { hwUpsBattGroupRelaiBOXEntry 2 }

        hwUpsBattGroupRelaiBATStartNo OBJECT-TYPE
            SYNTAX Unsigned32 (1..300)
            MAX-ACCESS read-only
            STATUS current
            DESCRIPTION
                "Ups Battery Group related iBAT start no,ranging from 1 to 300."
            ::= { hwUpsBattGroupRelaiBOXEntry 3 }

        hwUpsBattGroupRelaiBATEndNo OBJECT-TYPE
            SYNTAX Unsigned32 (1..300)
            MAX-ACCESS read-only
            STATUS current
            DESCRIPTION
                "Ups Battery Group related iBAT end no,ranging from 1 to 300.
                "
            ::= { hwUpsBattGroupRelaiBOXEntry 4 }

        hwUpsBattGroupRelaiBOXRowStatus OBJECT-TYPE
            SYNTAX RowStatus
            MAX-ACCESS read-only
            STATUS current
            DESCRIPTION
                "Row status of hwUpsBattGroupRelaiBOXTable."
            ::= { hwUpsBattGroupRelaiBOXEntry 100 }

        hwUpsiBATTable OBJECT-TYPE
            SYNTAX SEQUENCE OF HwUpsiBATEntry
            MAX-ACCESS not-accessible
             STATUS current
             DESCRIPTION
                "BIM table. It's index is hwUpsBIMCIMNo and hwUpsBIMNo."
            ::= { hwUpsiBOX 7 }

        hwUpsiBATEntry OBJECT-TYPE
                        SYNTAX HwUpsiBATEntry
            MAX-ACCESS not-accessible
             STATUS current
             DESCRIPTION
                "BIM table. It's index is hwUpsBIMCIMNo and hwUpsBIMNo."
            INDEX { hwUpsiBATiBOXNo }
            ::= { hwUpsiBATTable 1 }

        HwUpsiBATEntry            ::= SEQUENCE {
                hwUpsiBATiBOXNo
                    Unsigned32,
                hwUpsiBATNo
                    Unsigned32,
                hwUpsiBATTemp
                    Integer32,
                hwUpsiBATVoltMulThousand
                    Unsigned32,
                hwUpsiBATResMulHundred
                    Unsigned32,
                hwUpsiBATCur
                    Integer32,
                hwUpsiBATSOC
                    Unsigned32,
                hwUpsiBATSOH
                    INTEGER,
                hwUpsiBATVolt
                    Unsigned32,
                hwUpsiBATRes
                    Unsigned32,
                hwUpsiBATRowStatus
                    RowStatus
            }

        hwUpsiBATiBOXNo OBJECT-TYPE
            SYNTAX Unsigned32 (1..4)
            MAX-ACCESS read-only
            STATUS current
            DESCRIPTION
                "No of iBOX,ranging from 1 to 4.This node is referenced as an index node
                  by hwUpsBIMTable."
            ::= { hwUpsiBATEntry 1 }

        hwUpsiBATNo OBJECT-TYPE
            SYNTAX Unsigned32 (1..300)
            MAX-ACCESS read-only
            STATUS current
            DESCRIPTION
                "No of iBAT,ranging from 1 to 300.
                  This node is referenced as an index node by hwUpsBIMTable."
            ::= { hwUpsiBATEntry 2 }

        hwUpsiBATTemp OBJECT-TYPE
            SYNTAX Integer32 (-200..800)
            MAX-ACCESS read-only
            STATUS current
            DESCRIPTION
                "Ups iBAT Temperature.The value ranges from -200 to 800.
                  The value is accurate to one decimal place on the NetEco. The unit is ℃."
            ::= { hwUpsiBATEntry 3 }

        hwUpsiBATVoltMulThousand OBJECT-TYPE
            SYNTAX Unsigned32 (0..300)
            MAX-ACCESS read-only
            STATUS obsolete
            DESCRIPTION
                "Ups iBAT Volt.The value ranges from 0 to 300.
                  The value is accurate to one decimal place on the NetEco. The unit is V."
            ::= { hwUpsiBATEntry 4 }

        hwUpsiBATResMulHundred OBJECT-TYPE
            SYNTAX Unsigned32 (0..3000)
            MAX-ACCESS read-only
            STATUS obsolete
            DESCRIPTION
                "Ups iBAT Resistance.The value ranges from 0 to 3000.
                  The value is accurate to one decimal place on the NetEco. The unit is mΩ."
            ::= { hwUpsiBATEntry 5 }

        hwUpsiBATCur OBJECT-TYPE
            SYNTAX Integer32 (-30000..30000)
            MAX-ACCESS read-only
            STATUS current
            DESCRIPTION
                "Ups iBAT Current.The value ranges from -30000 to 30000.
                  The value is accurate to one decimal place on the NetEco. The unit is A.
                "
            ::= { hwUpsiBATEntry 6 }

        hwUpsiBATSOC OBJECT-TYPE
            SYNTAX Unsigned32 (0..100)
            MAX-ACCESS read-only
            STATUS current
            DESCRIPTION
                "The SOC of iBAT,ranging from 0 to 100.The unit is %.
                "
            ::= { hwUpsiBATEntry 7 }

        hwUpsiBATSOH OBJECT-TYPE
            SYNTAX INTEGER
                {
                good(1),
                 requiringMaintenance(2),
                 needReplaceBatt(3)
                }
            MAX-ACCESS read-only
            STATUS current
            DESCRIPTION
                "The SOH of iBAT. Enumeration type.
                  Value 0 indicates good.
                  Value 1 indicates requiring maintenance.
                  Value 2 indicates need replace batt.
                "
            ::= { hwUpsiBATEntry 8 }

        hwUpsiBATVolt OBJECT-TYPE
            SYNTAX Unsigned32 (0..30000)
            MAX-ACCESS read-only
            STATUS current
            DESCRIPTION
                "Ups iBAT Volt.The value ranges from 0 to 30000.
                  The value is accurate to two decimal place on the NetEco. The unit is V."
            ::= { hwUpsiBATEntry 9 }

        hwUpsiBATRes OBJECT-TYPE
            SYNTAX Unsigned32 (0..30000)
            MAX-ACCESS read-only
            STATUS current
            DESCRIPTION
                "Ups iBAT Resistance.The value ranges from 0 to 30000.
                  The value is accurate to two decimal place on the NetEco. The unit is mΩ."
            ::= { hwUpsiBATEntry 10 }

        hwUpsiBATRowStatus OBJECT-TYPE
            SYNTAX RowStatus
            MAX-ACCESS read-only
            STATUS current
            DESCRIPTION
                "Row status of hwUpsiBATTable."
            ::= { hwUpsiBATEntry 100 }

        hwUpsParallelSystem OBJECT IDENTIFIER ::= { hwUpsMIBObjects 10 }

        hwUpsParaSysTable OBJECT-TYPE
            SYNTAX SEQUENCE OF HwUpsParaSysEntry
            MAX-ACCESS not-accessible
             STATUS current
             DESCRIPTION
                "/"
            ::= { hwUpsParallelSystem 1 }

        hwUpsParaSysEntry OBJECT-TYPE
                        SYNTAX HwUpsParaSysEntry
            MAX-ACCESS not-accessible
             STATUS current
             DESCRIPTION
                "/"
            INDEX { hwUpsParaSysId }
            ::= { hwUpsParaSysTable 1 }

        HwUpsParaSysEntry            ::= SEQUENCE {
                hwUpsParaSysId
                    Unsigned32,
                hwUpsParaSysOutActivePowA
                    Integer32,
                hwUpsParaSysOutActivePowB
                    Integer32,
                hwUpsParaSysOutActivePowC
                    Integer32,
                hwUpsParaSysOutAppearPowA
                    Integer32,
                hwUpsParaSysOutAppearPowB
                    Integer32,
                hwUpsParaSysOutAppearPowC
                    Integer32,
                hwUpsParaSysOutLoadFactorA
                    Unsigned32,
                hwUpsParaSysOutLoadFactorB
                    Unsigned32,
                hwUpsParaSysOutLoadFactorC
                    Unsigned32,
                hwUpsParallelSystemRowStatus
                    RowStatus
            }

        hwUpsParaSysId OBJECT-TYPE
            SYNTAX Unsigned32 (0..127)
            MAX-ACCESS read-only
            STATUS current
            DESCRIPTION
                "ID of the parallel system that the current rack belongs to."
            ::= { hwUpsParaSysEntry 1 }

        hwUpsParaSysOutActivePowA OBJECT-TYPE
            SYNTAX Integer32 (-120000..120000)
            MAX-ACCESS read-only
            STATUS current
            DESCRIPTION
                "System phase A output active power.The value ranges from -12000 to 12000,
                  The value is accurate to one decimal place on the NetEco. The unit is kW.
                "
            ::= { hwUpsParaSysEntry 2 }

        hwUpsParaSysOutActivePowB OBJECT-TYPE
            SYNTAX Integer32 (-120000..120000)
            MAX-ACCESS read-only
            STATUS current
            DESCRIPTION
                "System phase B output active power.The value ranges from -12000 to 12000,
                  The value is accurate to one decimal place on the NetEco. The unit is kW.
                "
            ::= { hwUpsParaSysEntry 3 }

        hwUpsParaSysOutActivePowC OBJECT-TYPE
            SYNTAX Integer32 (-120000..120000)
            MAX-ACCESS read-only
            STATUS current
            DESCRIPTION
                "System phase C output active power.The value ranges from -12000 to 12000,
                  The value is accurate to one decimal place on the NetEco. The unit is kW.
                "
            ::= { hwUpsParaSysEntry 4 }

        hwUpsParaSysOutAppearPowA OBJECT-TYPE
            SYNTAX Integer32 (-120000..120000)
            MAX-ACCESS read-only
            STATUS current
            DESCRIPTION
                "System phase A output apparent power.The value ranges from -12000 to 12000,
                  The value is accurate to one decimal place on the NetEco. The unit is kVA.
                "
            ::= { hwUpsParaSysEntry 5 }

        hwUpsParaSysOutAppearPowB OBJECT-TYPE
            SYNTAX Integer32 (-120000..120000)
            MAX-ACCESS read-only
            STATUS current
            DESCRIPTION
                "System phase B output apparent power.The value ranges from -12000 to 12000,
                  The value is accurate to one decimal place on the NetEco. The unit is kVA.
                "
            ::= { hwUpsParaSysEntry 6 }

        hwUpsParaSysOutAppearPowC OBJECT-TYPE
            SYNTAX Integer32 (-120000..120000)
            MAX-ACCESS read-only
            STATUS current
            DESCRIPTION
                "System phase C output apparent power.The value ranges from -12000 to 12000,
                  The value is accurate to one decimal place on the NetEco. The unit is kVA.
                "
            ::= { hwUpsParaSysEntry 7 }

        hwUpsParaSysOutLoadFactorA OBJECT-TYPE
            SYNTAX Unsigned32 (0..5000)
            MAX-ACCESS read-only
            STATUS current
            DESCRIPTION
                "System A output load factor.The value ranges from 0 to 500,
                  The value is accurate to one decimal place on the NetEco. The unit is %"
            ::= { hwUpsParaSysEntry 8 }

        hwUpsParaSysOutLoadFactorB OBJECT-TYPE
            SYNTAX Unsigned32 (0..5000)
            MAX-ACCESS read-only
            STATUS current
            DESCRIPTION
                "System B output load factor.The value ranges from 0 to 500,
                  The value is accurate to one decimal place on the NetEco. The unit is %."
            ::= { hwUpsParaSysEntry 9 }

        hwUpsParaSysOutLoadFactorC OBJECT-TYPE
            SYNTAX Unsigned32 (0..5000)
            MAX-ACCESS read-only
            STATUS current
            DESCRIPTION
                "System C output load factor.The value ranges from 0 to 500,
                  The value is accurate to one decimal place on the NetEco. The unit is %."
            ::= { hwUpsParaSysEntry 10 }

        hwUpsParallelSystemRowStatus OBJECT-TYPE
            SYNTAX RowStatus
            MAX-ACCESS read-only
            STATUS current
            DESCRIPTION
                "RowStatus of ups parallel System Identification table."
            ::= { hwUpsParaSysEntry 100 }

        hwUpsRackUnevenCur OBJECT IDENTIFIER ::= { hwUpsMIBObjects 108 }

        hwUpsRackUnevenCurTable OBJECT-TYPE
            SYNTAX SEQUENCE OF HwUpsRackUnevenCurEntry
            MAX-ACCESS not-accessible
             STATUS current
             DESCRIPTION
                ""
            ::= { hwUpsRackUnevenCur 1 }

        hwUpsRackUnevenCurEntry OBJECT-TYPE
                        SYNTAX HwUpsRackUnevenCurEntry
            MAX-ACCESS not-accessible
             STATUS current
             DESCRIPTION
                ""
            INDEX { hwUpsRackUnevenCurRackId }
            ::= { hwUpsRackUnevenCurTable 1 }

        HwUpsRackUnevenCurEntry            ::= SEQUENCE {
                hwUpsRackUnevenCurRackId
                    Unsigned32,
                hwUpsRackUnevenCurSysGrant
                    Unsigned32,
                hwUpsRackUnevenCurPowerSupplyMode
                    INTEGER,
                hwUpsRackUnevenCurPowerOnModNum
                    Unsigned32,
                hwUpsRackUnevenCurSleepModNum
                    Unsigned32,
                hwUpsRackOutputCurrentA
                    Unsigned32,
                hwUpsRackOutputCurrentB
                    Unsigned32,
                hwUpsRackOutputCurrentC
                    Unsigned32,
                hwUpsRackUnevenCurA
                    Unsigned32,
                hwUpsRackUnevenCurB
                    Unsigned32,
                hwUpsRackUnevenCurC
                    Unsigned32,
                hwUpsRackUnevenCurValueTag
                    Unsigned32,
                hwUpsRackUnevenCurRowStatus
                    RowStatus
            }

        hwUpsRackUnevenCurRackId OBJECT-TYPE
            SYNTAX Unsigned32 (1..6)
            MAX-ACCESS read-only
            STATUS current
            DESCRIPTION
                "Ups Rack Id.Range from 1 to 6.This node is referenced as an index node
                  by hwUpsRackUnevenCurTable"
            ::= { hwUpsRackUnevenCurEntry 1 }

        hwUpsRackUnevenCurSysGrant OBJECT-TYPE
            SYNTAX Unsigned32 (0..10000)
            MAX-ACCESS read-only
            STATUS current
            DESCRIPTION
                "System grant.An integer ranging from 0 to 10000."
            ::= { hwUpsRackUnevenCurEntry 2 }

        hwUpsRackUnevenCurPowerSupplyMode OBJECT-TYPE
            SYNTAX INTEGER
                {
                noOutput(1),
                 bypass(2),
                 normal(3),
                 battery(4),
                 sourceShare(5),
                 normalECO(6),
                 batteryECO(7)
                }
            MAX-ACCESS read-only
            STATUS current
            DESCRIPTION
                "Device power supply mode. Enumeration type.
                  Value 1 indicates no power supply.
                  Value 2 indicates bypass mode.
                  Value 3 indicates normal mode.
                  Value 4 indicates battery mode.
                  Value 5 indicates combined mode.
                  Value 6 indicates mains ECO mode.
                  Value 7 indicates battery ECO mode."
            ::= { hwUpsRackUnevenCurEntry 3 }

        hwUpsRackUnevenCurPowerOnModNum OBJECT-TYPE
            SYNTAX Unsigned32 (0..20)
            MAX-ACCESS read-only
            STATUS current
            DESCRIPTION
                "Rack PowerOn Module Num.Range from 0 to 20."
            ::= { hwUpsRackUnevenCurEntry 4 }

        hwUpsRackUnevenCurSleepModNum OBJECT-TYPE
            SYNTAX Unsigned32 (0..20)
            MAX-ACCESS read-only
            STATUS current
            DESCRIPTION
                "Rack Sleep Module Num.Range from 0 to 20."
            ::= { hwUpsRackUnevenCurEntry 5 }

        hwUpsRackOutputCurrentA OBJECT-TYPE
            SYNTAX Unsigned32 (0..10000)
            MAX-ACCESS read-only
            STATUS current
            DESCRIPTION
                "Rack phase A output current. The value ranges from 0 to 10000.
                  The value is accurate to one decimal place on the NetEco. The unit is A."
            ::= { hwUpsRackUnevenCurEntry 6 }

        hwUpsRackOutputCurrentB OBJECT-TYPE
            SYNTAX Unsigned32 (0..10000)
            MAX-ACCESS read-only
            STATUS current
            DESCRIPTION
                "Rack phase B output current. The value ranges from 0 to 10000.
                  The value is accurate to one decimal place on the NetEco. The unit is A."
            ::= { hwUpsRackUnevenCurEntry 7 }

        hwUpsRackOutputCurrentC OBJECT-TYPE
            SYNTAX Unsigned32 (0..10000)
            MAX-ACCESS read-only
            STATUS current
            DESCRIPTION
                "Rack phase C output current. The value ranges from 0 to 10000.
                  The value is accurate to one decimal place on the NetEco. The unit is A."
            ::= { hwUpsRackUnevenCurEntry 8 }

        hwUpsRackUnevenCurA OBJECT-TYPE
            SYNTAX Unsigned32 (0..10000)
            MAX-ACCESS read-only
            STATUS current
            DESCRIPTION
                "Rack phase A uneven current. The value ranges from 0 to 10000.
                  The value is accurate to one decimal place on the NetEco. "
            ::= { hwUpsRackUnevenCurEntry 9 }

        hwUpsRackUnevenCurB OBJECT-TYPE
            SYNTAX Unsigned32 (0..10000)
            MAX-ACCESS read-only
            STATUS current
            DESCRIPTION
                "Rack phase B uneven current. The value ranges from 0 to 10000.
                  The value is accurate to one decimal place on the NetEco. "
            ::= { hwUpsRackUnevenCurEntry 10 }

        hwUpsRackUnevenCurC OBJECT-TYPE
            SYNTAX Unsigned32 (0..10000)
            MAX-ACCESS read-only
            STATUS current
            DESCRIPTION
                "Rack phase C uneven current. The value ranges from 0 to 10000.
                  The value is accurate to one decimal place on the NetEco. "
            ::= { hwUpsRackUnevenCurEntry 11 }

        hwUpsRackUnevenCurValueTag OBJECT-TYPE
            SYNTAX Unsigned32 (0..1)
            MAX-ACCESS read-only
            STATUS current
            DESCRIPTION
                "Rack uneven current value tag.range 0 to 1,0 indicates invalid,1 indicates valid."
            ::= { hwUpsRackUnevenCurEntry 12 }

        hwUpsRackUnevenCurRowStatus OBJECT-TYPE
            SYNTAX RowStatus
            MAX-ACCESS read-only
            STATUS current
            DESCRIPTION
                "RowStatus of UPS Rack Uneven Current table."
            ::= { hwUpsRackUnevenCurEntry 100 }

        hwUpsMIBTraps OBJECT IDENTIFIER ::= { hwUpsMIB 2 }

        hwUpsTrapsVbOids OBJECT IDENTIFIER ::= { hwUpsMIBTraps 1 }

        hwUpsTrapsDeviceId OBJECT-TYPE
            SYNTAX Unsigned32 (1..100)
            MAX-ACCESS read-only
            STATUS current
            DESCRIPTION
                "ID of the device on which the active alarm is generated. An integer ranging from 1 to 100."
            ::= { hwUpsTrapsVbOids 1 }

        hwUpsTrapsModuleSeqId OBJECT-TYPE
            SYNTAX Unsigned32 (1..4294967295)
            MAX-ACCESS read-only
            STATUS current
            DESCRIPTION
                "The alarm module name, which produces alarm.
                    This name may be one of Monitor module name,Bypass module name,ECU module name and Power module name.
                    If it's value is empty, it indicates the alarm is a synthetical alarm and not belong to any module device."
            ::= { hwUpsTrapsVbOids 2 }

        hwUpsTrapsEquipID OBJECT-TYPE
            SYNTAX Unsigned32 (0..154)
            MAX-ACCESS read-only
            STATUS current
            DESCRIPTION
                "Active alarm module ID, ranging from 1 to 154."
            ::= { hwUpsTrapsVbOids 3 }

        hwUpsTrapsID OBJECT-TYPE
            SYNTAX Unsigned32 (0..4294967295)
            MAX-ACCESS read-only
            STATUS current
            DESCRIPTION
                "ID of an active alarm, ranging from 0 to 4294967295."
            ::= { hwUpsTrapsVbOids 4 }

        hwUpsTrapsReasonId OBJECT-TYPE
            SYNTAX Unsigned32 (0..100)
            MAX-ACCESS read-only
            STATUS current
            DESCRIPTION
                "Alarm reason ID.  Value range: 0 to 100, and the value is an integer (.0)."
            ::= { hwUpsTrapsVbOids 5 }

        hwUpsTrapsText OBJECT-TYPE
            SYNTAX OCTET STRING (SIZE (0..127))
            MAX-ACCESS read-only
            STATUS current
            DESCRIPTION
                "Alarm name. It is of the character string type, and used to specify the content of a specific alarm."
            ::= { hwUpsTrapsVbOids 6 }

        hwUpsTrapsLevel OBJECT-TYPE
            SYNTAX INTEGER
                {
                    critical(1),
                    major(2),
                    minor(3),
                    warning(4)
                }
            MAX-ACCESS read-only
            STATUS current
            DESCRIPTION
                "Alarm level, which users can configure the alarm severity, is an enumeration type:
                  If the enumeration value is 1, it indicates a critical alarm;
                  If the enumeration value is 2, it indicates a major alarm;
                  If the enumeration value is 3, it indicates a minor alarm;
                  If the enumeration value is 4, it indicates a warning."
            ::= { hwUpsTrapsVbOids 7 }

        hwUpsTrapsFlag OBJECT-TYPE
            SYNTAX INTEGER
                {
                occur(1),
                 resume(2)
                }
            MAX-ACCESS read-only
            STATUS current
            DESCRIPTION
                "Flag bit of an active alarm. Enumeration type.
                  Value 1 indicates that an active alarm is generated.
                  Value 2 indicates that an active alarm is cleared."
            ::= { hwUpsTrapsVbOids 8 }

        hwUpsTrapsSynchronNum OBJECT-TYPE
            SYNTAX Unsigned32
            MAX-ACCESS read-only
            STATUS current
            DESCRIPTION
                "Active alarm synchronization ID, ranging from 0 to 4294967295"
            ::= { hwUpsTrapsVbOids 9 }

        hwUpsTrapsTime OBJECT-TYPE
            SYNTAX Unsigned32 (0..4294967295)
            MAX-ACCESS read-only
            STATUS current
            DESCRIPTION
                "Time when an active alarm is generated, ranging from 0 to 4294967295. The unit is seconds."
            ::= { hwUpsTrapsVbOids 10 }

        hwUpsCommonTraps OBJECT IDENTIFIER ::= { hwUpsMIBTraps 2 }

        hwUpsCommonTrapsPrefix OBJECT IDENTIFIER ::= { hwUpsCommonTraps 0 }


--   1.3.6.1.4.1.2011.6.174.2.2.0.1
-- 1.3.6.1.4.1.2011.6.174.2.2.0.1
		-- 1.3.6.1.4.1.2011.6.174.2.2.0.1
		hwUpsSummaryAlarmTrap NOTIFICATION-TYPE
			STATUS current
			DESCRIPTION
				"UPS Summary Alarm status changed. Its correlation binding parameters: Device ID, Sequence ID, Equip ID, Trap ID,
				Trap Reason ID, Trap Text, Trap Level, Trap Flag, Synchron NO and the time.
				Additionally, in order to identify the status, UPS system operate status are also include in VB(variable bondings):
				If the enumeration value is Normal(2), it indicates that UPS system  resumes form alarm.
				If the enumeration value is Alarm(3), it indicates that a new alarm occurs on the UPS sytem."
			::= { hwUpsCommonTrapsPrefix 1 }


--   1.3.6.1.4.1.2011.6.174.2.2.0.2
-- 1.3.6.1.4.1.2011.6.174.2.2.0.2
		-- 1.3.6.1.4.1.2011.6.174.2.2.0.2
		hwUpsPowerModInslotChangeTrap NOTIFICATION-TYPE
			OBJECTS { hwUpsTrapsDeviceId, hwUpsTrapsModuleSeqId, hwUpsTrapsEquipID, hwUpsTrapsID, hwUpsTrapsReasonId,
				hwUpsTrapsText, hwUpsTrapsLevel, hwUpsTrapsFlag, hwUpsTrapsSynchronNum, hwUpsTrapsTime
				 }
			STATUS current
			DESCRIPTION
				"Power module inslot status changed.
				Its correlation binding parameters: Device ID, Sequence ID, Equip ID, Trap ID,
				Trap Reason ID, Trap Text, Trap Level, Trap Flag, Synchron NO and the time.
				Additionally, in order to identify the operation, power module operate status are also include in VB(variable bondings):
				If the enumeration value is Normal(2), it indicates that a new power module is inserted in slot;
				If the enumeration value is Alarm(3), it indicates that communication of the power module module fails or module is not in slot. "
			::= { hwUpsCommonTrapsPrefix 2 }

        hwUpsPowerStatusWarnTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "When UPS Power Status changed, a warn trap will be send.
                  Its correlation binding parameters: Device ID, Sequence ID, Equip ID, Trap ID,
                  Trap Reason ID, Trap Text, Trap Level, Trap Flag, Synchron NO and the time. "
            ::= { hwUpsCommonTrapsPrefix 3 }

        hwUpsPowerStatusWarnResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "UPS Power Status warn resume trap.
                  Its correlation binding parameters: Device ID, Sequence ID, Equip ID, Trap ID,
                  Trap Reason ID, Trap Text, Trap Level, Trap Flag, Synchron NO and the time. "
            ::= { hwUpsCommonTrapsPrefix 4 }

        hwUpsSwitchStatusWarnTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "When contactor or switch status changed, a warn trap will be send.
                  Its correlation binding parameters: Device ID, Sequence ID, Equip ID, Trap ID,
                  Trap Reason ID, Trap Text, Trap Level, Trap Flag, Synchron NO and the time. "
            ::= { hwUpsCommonTrapsPrefix 5 }

        hwUpsSwitchStatusWarnResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Contactor or switch warn resume trap.
                  Its correlation binding parameters: Device ID, Sequence ID, Equip ID, Trap ID,
                  Trap Reason ID, Trap Text, Trap Level, Trap Flag, Synchron NO and the time. "
            ::= { hwUpsCommonTrapsPrefix 6 }

        hwUpsModCommFailedTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "When module communicates failed, a trap will be send.
                  Its correlation binding parameters: Device ID, Sequence ID, Equip ID, Trap ID,
                  Trap Reason ID, Trap Text, Trap Level, Trap Flag, Synchron NO and the time. "
            ::= { hwUpsCommonTrapsPrefix 7 }

        hwUpsModCommFailedResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Module communication failed Resume.
                  Its correlation binding parameters: Device ID, Sequence ID, Equip ID, Trap ID,
                  Trap Reason ID, Trap Text, Trap Level, Trap Flag, Synchron NO and the time."
            ::= { hwUpsCommonTrapsPrefix 8 }

        hwUpsModConfigWarnTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "When module config status changed, a warn trap will be send.
                  Its correlation binding parameters: Device ID, Sequence ID, Equip ID, Trap ID,
                  Trap Reason ID, Trap Text, Trap Level, Trap Flag, Synchron NO and the time."
            ::= { hwUpsCommonTrapsPrefix 9 }

        hwUpsModConfigWarnResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Module config warn resume trap.
                  Its correlation binding parameters:Device ID, Sequence ID, Equip ID, Trap ID,
                  Trap Reason ID, Trap Text, Trap Level, Trap Flag, Synchron NO and the time. "
            ::= { hwUpsCommonTrapsPrefix 10 }

        hwUpsRecWarnTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "When rectifier status changed, a warn trap will be send.
                  Its correlation binding parameters: Device ID, Sequence ID, Equip ID, Trap ID,
                  Trap Reason ID, Trap Text, Trap Level, Trap Flag, Synchron NO and the time. "
            ::= { hwUpsCommonTrapsPrefix 11 }

        hwUpsRecWarnResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Rectifier warn resume trap.
                  Its correlation binding parameters: Device ID, Sequence ID, Equip ID, Trap ID,
                  Trap Reason ID, Trap Text, Trap Level, Trap Flag, Synchron NO and the time."
            ::= { hwUpsCommonTrapsPrefix 12 }

        hwUpsChargerPowerWarnTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "When charger power status changed, a warn trap will be send.
                  Its correlation binding parameters: Device ID, Sequence ID, Equip ID, Trap ID,
                  Trap Reason ID, Trap Text, Trap Level, Trap Flag, Synchron NO and the time."
            ::= { hwUpsCommonTrapsPrefix 13 }

        hwUpsChargerPowerWarnResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Charger power warn resume trap.
                  Its correlation binding parameters: Device ID, Sequence ID, Equip ID, Trap ID,
                  Trap Reason ID, Trap Text, Trap Level, Trap Flag, Synchron NO and the time"
            ::= { hwUpsCommonTrapsPrefix 14 }

        hwUpsGeneratorWarnTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "When generator status changed, a warn trap will be send.
                  Its correlation binding parameters: Device ID, Sequence ID, Equip ID, Trap ID,
                  Trap Reason ID, Trap Text, Trap Level, Trap Flag, Synchron NO and the time. "
            ::= { hwUpsCommonTrapsPrefix 15 }

        hwUpsGeneratorWarnResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Generator warn resume trap.
                  Its correlation binding parameters: Device ID, Sequence ID, Equip ID, Trap ID,
                  Trap Reason ID, Trap Text, Trap Level, Trap Flag, Synchron NO and the time. "
            ::= { hwUpsCommonTrapsPrefix 16 }

        hwUpsInvWarnTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "When inverter status changed, a warn trap will be send.
                  Its correlation binding parameters: Device ID, Sequence ID, Equip ID, Trap ID,
                  Trap Reason ID, Trap Text, Trap Level, Trap Flag, Synchron NO and the time."
            ::= { hwUpsCommonTrapsPrefix 17 }

        hwUpsInvWarnResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Inverter warn resume trap.
                  Its correlation binding parameters: Device ID, Sequence ID, Equip ID, Trap ID,
                  Trap Reason ID, Trap Text, Trap Level, Trap Flag, Synchron NO and the time."
            ::= { hwUpsCommonTrapsPrefix 18 }

        hwUpsLBSWarnTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "When LBS status changed, a warn trap will be send.
                  Its correlation binding parameters: Device ID, Sequence ID, Equip ID, Trap ID,
                  Trap Reason ID, Trap Text, Trap Level, Trap Flag, Synchron NO and the time. "
            ::= { hwUpsCommonTrapsPrefix 19 }

        hwUpsLBSWarnResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "LBS warn resume trap.
                  Its correlation binding parameters: Device ID, Sequence ID, Equip ID, Trap ID,
                  Trap Reason ID, Trap Text, Trap Level, Trap Flag, Synchron NO and the time."
            ::= { hwUpsCommonTrapsPrefix 20 }

        hwUpsSwitchTipWarnTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "When switch method changed or there is a switch tip, a warn trap will be send.
                  Its correlation binding parameters: Device ID, Sequence ID, Equip ID, Trap ID,
                  Trap Reason ID, Trap Text, Trap Level, Trap Flag, Synchron NO and the time. "
            ::= { hwUpsCommonTrapsPrefix 21 }

        hwUpsSwitchTipWarnResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Switch method or switch tip warn resume trap.
                  Its correlation binding parameters:Device ID, Sequence ID, Equip ID, Trap ID,
                  Trap Reason ID, Trap Text, Trap Level, Trap Flag, Synchron NO and the time."
            ::= { hwUpsCommonTrapsPrefix 22 }


--   1.3.6.1.4.1.2011.6.174.2.2.0.23
-- 1.3.6.1.4.1.2011.6.174.2.2.0.23
		-- 1.3.6.1.4.1.2011.6.174.2.2.0.23
		hwUpsBattDetachWarnTrap NOTIFICATION-TYPE
			OBJECTS { hwUpsTrapsDeviceId, hwUpsTrapsModuleSeqId, hwUpsTrapsEquipID, hwUpsTrapsID, hwUpsTrapsReasonId,
				hwUpsTrapsText, hwUpsTrapsLevel, hwUpsTrapsFlag, hwUpsTrapsSynchronNum, hwUpsTrapsTime
				 }
			STATUS current
			DESCRIPTION
				"When battery detach, a warn trap will be send.
				Its correlation binding parameters: Device ID, Sequence ID, Equip ID, Trap ID,
				Trap Reason ID, Trap Text, Trap Level, Trap Flag, Synchron NO and the time. "
			::= { hwUpsCommonTrapsPrefix 23 }


--   1.3.6.1.4.1.2011.6.174.2.2.0.24
-- 1.3.6.1.4.1.2011.6.174.2.2.0.24
		-- 1.3.6.1.4.1.2011.6.174.2.2.0.24
		hwUpsBattDetachWarnResumeTrap NOTIFICATION-TYPE
			OBJECTS { hwUpsTrapsDeviceId, hwUpsTrapsModuleSeqId, hwUpsTrapsEquipID, hwUpsTrapsID, hwUpsTrapsReasonId,
				hwUpsTrapsText, hwUpsTrapsLevel, hwUpsTrapsFlag, hwUpsTrapsSynchronNum, hwUpsTrapsTime
				 }
			STATUS current
			DESCRIPTION
				"Battery detach warn resume trap.
				Its correlation binding parameters: Device ID, Sequence ID, Equip ID, Trap ID,
				Trap Reason ID, Trap Text, Trap Level, Trap Flag, Synchron NO and the time. "
			::= { hwUpsCommonTrapsPrefix 24 }

        hwUpsBattStatusWarnTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "When battery status abnormal, a warn trap will be send through this OID.
                  Its correlation binding parameters: Device ID, Sequence ID, Equip ID, Trap ID,
                  Trap Reason ID, Trap Text, Trap Level, Trap Flag, Synchron NO and the time."
            ::= { hwUpsCommonTrapsPrefix 25 }

        hwUpsBattStatusWarnResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "When battery status abnormal resume, a trap will be send through this OID.
                  Its correlation binding parameters: Device ID, Sequence ID, Equip ID, Trap ID,
                  Trap Reason ID, Trap Text, Trap Level, Trap Flag, Synchron NO and the time."
            ::= { hwUpsCommonTrapsPrefix 26 }

        hwUpsBatteryTestWarnTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "When battery test start, a warn trap will be send through this OID.
                  Its correlation binding parameters: Device ID, Sequence ID, Equip ID, Trap ID,
                  Trap Reason ID, Trap Text, Trap Level, Trap Flag, Synchron NO and the time.
                "
            ::= { hwUpsCommonTrapsPrefix 27 }

        hwUpsBatteryTestWarnResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "When battery test end, a trap will be send through this OID.
                  Its correlation binding parameters: Device ID, Sequence ID, Equip ID, Trap ID,
                  Trap Reason ID, Trap Text, Trap Level, Trap Flag, Synchron NO and the time."
            ::= { hwUpsCommonTrapsPrefix 28 }

        hwUpsRackComFailedTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "When Rack communication fail happen, a alarm trap will be send.
                  Its correlation binding parameters: Device ID, Sequence ID, Equip ID, Trap ID,
                  Trap Reason ID, Trap Text, Trap Level, Trap Flag, Synchron NO and the time.
                "
            ::= { hwUpsCommonTrapsPrefix 29 }

        hwUpsRackComFaiedResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Rack communication fail alarm resume.
                  Its correlation binding parameters: Device ID, Sequence ID, Equip ID, Trap ID,
                  Trap Reason ID, Trap Text, Trap Level, Trap Flag, Synchron NO and the time. "
            ::= { hwUpsCommonTrapsPrefix 30 }

        hwUpsRackMasterConflictTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "When Rack Master Conflict alarm happen, a alarm trap will be send.
                  Its correlation binding parameters: Device ID, Sequence ID, Equip ID, Trap ID,
                  Trap Reason ID, Trap Text, Trap Level, Trap Flag, Synchron NO and the time. "
            ::= { hwUpsCommonTrapsPrefix 31 }

        hwUpsRackMasterConflictResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Rack Master Conflict alarm resume.
                  Its correlation binding parameters: Device ID, Sequence ID, Equip ID, Trap ID,
                  Trap Reason ID, Trap Text, Trap Level, Trap Flag, Synchron NO and the time."
            ::= { hwUpsCommonTrapsPrefix 32 }

        hwUpsRackNumNoMatchTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "UPS Rack num dismatch warn. Its correlation binding parameters: Device ID, Sequence ID, Equip ID, Trap ID,
                  Trap Reason ID, Trap Text, Trap Level, Trap Flag, Synchron NO and the time.
                  Additionally, in order to identify the status, UPS system operate status are also include in VB(variable bondings):
                  If the enumeration value is Normal(2), it indicates that UPS system  resumes form alarm.
                  If the enumeration value is Alarm(3), it indicates that a new alarm occurs on the UPS sytem."
            ::= { hwUpsCommonTrapsPrefix 33 }

        hwUpsRackNumNoMatchResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "UPS Rack num dismatch warn resume. Its correlation binding parameters: Device ID, Sequence ID, Equip ID, Trap ID,
                  Trap Reason ID, Trap Text, Trap Level, Trap Flag, Synchron NO and the time.
                  Additionally, in order to identify the status, UPS system operate status are also include in VB(variable bondings):
                  If the enumeration value is Normal(2), it indicates that UPS system  resumes form alarm.
                  If the enumeration value is Alarm(3), it indicates that a new alarm occurs on the UPS sytem.
                "
            ::= { hwUpsCommonTrapsPrefix 34 }


		-- 1.3.6.1.4.1.2011.6.174.2.2.1
		hwUpsCommonStateTrapsPrefix OBJECT IDENTIFIER ::= { hwUpsCommonTraps 1 }


--   1.3.6.1.4.1.2011.6.174.2.2.0.35
-- 1.3.6.1.4.1.2011.6.174.2.2.0.35
		-- 1.3.6.1.4.1.2011.6.174.2.2.1.1
		hwUpsRackOnlineStateChangeTrap NOTIFICATION-TYPE
			STATUS current
			DESCRIPTION
				"Ups Rack Online State Change Trap. Its correlation binding parameters: NULL"
			::= { hwUpsCommonStateTrapsPrefix 1 }


--   1.3.6.1.4.1.2011.6.174.2.2.0.36
-- 1.3.6.1.4.1.2011.6.174.2.2.0.36
		-- 1.3.6.1.4.1.2011.6.174.2.2.1.2
		hwUpsRackConfigChangeTrap NOTIFICATION-TYPE
			OBJECTS { hwUpsTrapsDeviceId }
			STATUS current
			DESCRIPTION
				"Ups Rack Config Change.Its correlation binding parameters: Device ID"
			::= { hwUpsCommonStateTrapsPrefix 2 }


--   1.3.6.1.4.1.2011.6.174.2.2.0.37
-- 1.3.6.1.4.1.2011.6.174.2.2.0.37
		-- 1.3.6.1.4.1.2011.6.174.2.2.1.3
		hwUpsRackRunningStateChangeTrap NOTIFICATION-TYPE
			OBJECTS { hwUpsDeviceRunningStatus, hwUpsTrapsDeviceId }
			STATUS current
			DESCRIPTION
				"Ups Rack Running State Change.Its correlation binding parameters: Device ID and Device running state."
			::= { hwUpsCommonStateTrapsPrefix 3 }


--   1.3.6.1.4.1.2011.6.174.2.2.0.38
-- 1.3.6.1.4.1.2011.6.174.2.2.0.38
		-- 1.3.6.1.4.1.2011.6.174.2.2.1.4
		hwUpsBatteryRunningStateChangeTrap NOTIFICATION-TYPE
			OBJECTS { hwUpsDeviceBatteryState, hwUpsTrapsDeviceId }
			STATUS current
			DESCRIPTION
				"Ups Battery Running State Change,Its correlation binding parameters: Device ID and Battery Running State"
			::= { hwUpsCommonStateTrapsPrefix 4 }


		-- 1.3.6.1.4.1.2011.6.174.2.2.1.5
		hwUpsEnergyFloatChangeTrap NOTIFICATION-TYPE
			OBJECTS { hwUpsDeviceEnergyFloatState, hwUpsTrapsDeviceId }
			STATUS current
			DESCRIPTION
				"Ups Energy Float Change,Its correlation binding parameters: Device ID and The Energy Float State"
			::= { hwUpsCommonStateTrapsPrefix 5 }


		-- 1.3.6.1.4.1.2011.6.174.2.2.1.6
		hwUpsVersionChangeTrap NOTIFICATION-TYPE
			OBJECTS { hwUpsTrapsDeviceId }
			STATUS current
			DESCRIPTION
				"Ups Version Change,Its correlation binding parameters: Device ID"
			::= { hwUpsCommonStateTrapsPrefix 6 }

        hwUpsAlarmTraps OBJECT IDENTIFIER ::= { hwUpsMIBTraps 3 }

        hwUpsAlarmTrapsPrefix OBJECT IDENTIFIER ::= { hwUpsAlarmTraps 0 }

        hwUpsModNumAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "When power module number dismatch, a alarm trap will be send.
                  Its correlation binding parameters:Device ID, Sequence ID, Equip ID, Trap ID,
                  Trap Reason ID, Trap Text, Trap Level, Trap Flag, Synchron NO and the time."
            ::= { hwUpsAlarmTrapsPrefix 1 }

        hwUpsModNumAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Power module number dismatch alarm resume trap.
                  Its correlation binding parameters: Device ID, Sequence ID, Equip ID, Trap ID,
                  Trap Reason ID, Trap Text, Trap Level, Trap Flag, Synchron NO and the time."
            ::= { hwUpsAlarmTrapsPrefix 2 }

        hwUpsBypassUnitAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Bypass Unit Abnormal Trap.
                  Its correlation binding parameters: Device ID, Sequence ID, Equip ID, Trap ID,
                  Trap Reason ID, Trap Text, Trap Level, Trap Flag, Synchron NO and the time."
            ::= { hwUpsAlarmTrapsPrefix 3 }

        hwUpsBypassUnitAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Bypass Unit Abnormal Resume Trap.
                  Its correlation binding parameters:Device ID, Sequence ID, Equip ID, Trap ID,
                  Trap Reason ID, Trap Text, Trap Level, Trap Flag, Synchron NO and the time."
            ::= { hwUpsAlarmTrapsPrefix 4 }

        hwUpsInRackParallelLineAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "In-Rack Parallel Line Abnormal Trap.
                  Its correlation binding parameters: Device ID, Sequence ID, Equip ID, Trap ID,
                  Trap Reason ID, Trap Text, Trap Level, Trap Flag, Synchron NO and the time.
                "
            ::= { hwUpsAlarmTrapsPrefix 5 }

        hwUpsInRackParallelLineAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Description: In-Rack Parallel Line Abnormal Resume Trap.
                  Its correlation binding parameters: Device ID, Sequence ID, Equip ID, Trap ID,
                  Trap Reason ID, Trap Text, Trap Level, Trap Flag, Synchron NO and the time. "
            ::= { hwUpsAlarmTrapsPrefix 6 }

        hwUpsBetweenRackParallelLineAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Between-Rack Parallel Line Abnormal Trap.
                  Its correlation binding parameters: Device ID, Sequence ID, Equip ID, Trap ID,
                  Trap Reason ID, Trap Text, Trap Level, Trap Flag, Synchron NO and the time. "
            ::= { hwUpsAlarmTrapsPrefix 7 }

        hwUpsBetweenRackParallelLineAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Between-Rack Parallel Line Abnormal Resume Trap.
                  Its correlation binding parameters: Device ID, Sequence ID, Equip ID, Trap ID,
                  Trap Reason ID, Trap Text, Trap Level, Trap Flag, Synchron NO and the time. "
            ::= { hwUpsAlarmTrapsPrefix 8 }

        hwUpsFanAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Fan Abnormal Trap.
                  Its correlation binding parameters: Device ID, Sequence ID, Equip ID, Trap ID,
                  Trap Reason ID, Trap Text, Trap Level, Trap Flag, Synchron NO and the time."
            ::= { hwUpsAlarmTrapsPrefix 9 }

        hwUpsFanAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Fan Abnormal Resume Trap.
                  Its correlation binding parameters: Device ID, Sequence ID, Equip ID, Trap ID,
                  Trap Reason ID, Trap Text, Trap Level, Trap Flag, Synchron NO and the time. "
            ::= { hwUpsAlarmTrapsPrefix 10 }

        hwUpsAuxiliaryPowerAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Auxiliary Power Abnormal Trap.
                  Its correlation binding parameters: Device ID, Sequence ID, Equip ID, Trap ID,
                  Trap Reason ID, Trap Text, Trap Level, Trap Flag, Synchron NO and the time."
            ::= { hwUpsAlarmTrapsPrefix 11 }

        hwUpsAuxiliaryPowerAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Auxiliary Power Abnormal Resume Trap.
                  Its correlation binding parameters: Device ID, Sequence ID, Equip ID, Trap ID,
                  Trap Reason ID, Trap Text, Trap Level, Trap Flag, Synchron NO and the time. "
            ::= { hwUpsAlarmTrapsPrefix 12 }

        hwUpsVersionMismatchAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "when version mismatch alarms happen, a alarm trap will be send.
                  Its correlation binding parameters:Device ID, Sequence ID, Equip ID, Trap ID,
                  Trap Reason ID, Trap Text, Trap Level, Trap Flag, Synchron NO and the time. "
            ::= { hwUpsAlarmTrapsPrefix 13 }

        hwUpsVersionMatchAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Version mismatch Abnormal Resume Trap.
                  Its correlation binding parameters: Device ID, Sequence ID, Equip ID, Trap ID,
                  Trap Reason ID, Trap Text, Trap Level, Trap Flag, Synchron NO and the time. "
            ::= { hwUpsAlarmTrapsPrefix 14 }

        hwUpsAddrConflictAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Address Conflict Trap.
                  Its correlation binding parameters: Device ID, Sequence ID, Equip ID, Trap ID,
                  Trap Reason ID, Trap Text, Trap Level, Trap Flag, Synchron NO and the time."
            ::= { hwUpsAlarmTrapsPrefix 15 }

        hwUpsAddrConflictAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Address Conflict Resume Trap.
                  Its correlation binding parameters: Device ID, Sequence ID, Equip ID, Trap ID,
                  Trap Reason ID, Trap Text, Trap Level, Trap Flag, Synchron NO and the time. "
            ::= { hwUpsAlarmTrapsPrefix 16 }

        hwUpsEmergencyPowerOffAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Emergency Power Off Abnormal Trap.
                  Its correlation binding parameters:Device ID, Sequence ID, Equip ID, Trap ID,
                  Trap Reason ID, Trap Text, Trap Level, Trap Flag, Synchron NO and the time."
            ::= { hwUpsAlarmTrapsPrefix 17 }

        hwUpsEmergencyPowerOffAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Emergency Power Off Abnormal Resume Trap.
                  Its correlation binding parameters:Device ID, Sequence ID, Equip ID, Trap ID,
                  Trap Reason ID, Trap Text, Trap Level, Trap Flag, Synchron NO and the time."
            ::= { hwUpsAlarmTrapsPrefix 18 }

        hwUpsBypassInputAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Bypass Input Abnormal Trap.
                  Its correlation binding parameters: Device ID, Sequence ID, Equip ID, Trap ID,
                  Trap Reason ID, Trap Text, Trap Level, Trap Flag, Synchron NO and the time."
            ::= { hwUpsAlarmTrapsPrefix 19 }

        hwUpsBypassInputAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Bypass Input Abnormal Resume Trap.
                  Its correlation binding parameters: Device ID, Sequence ID, Equip ID, Trap ID,
                  Trap Reason ID, Trap Text, Trap Level, Trap Flag, Synchron NO and the time. "
            ::= { hwUpsAlarmTrapsPrefix 20 }


--   1.3.6.1.4.1.2011.6.174.2.3.0.21
-- 1.3.6.1.4.1.2011.6.174.2.3.0.21
		-- 1.3.6.1.4.1.2011.6.174.2.3.0.21
		hwUpsInputIsolatingTransAlarmTrap NOTIFICATION-TYPE
			OBJECTS { hwUpsTrapsDeviceId, hwUpsTrapsModuleSeqId, hwUpsTrapsEquipID, hwUpsTrapsID, hwUpsTrapsReasonId,
				hwUpsTrapsText, hwUpsTrapsLevel, hwUpsTrapsFlag, hwUpsTrapsSynchronNum, hwUpsTrapsTime
				 }
			STATUS current
			DESCRIPTION
				"Transformer Abnormal Trap.
				Its correlation binding parameters: Device ID, Sequence ID, Equip ID, Trap ID,
				Trap Reason ID, Trap Text, Trap Level, Trap Flag, Synchron NO and the time. "
			::= { hwUpsAlarmTrapsPrefix 21 }


--   1.3.6.1.4.1.2011.6.174.2.3.0.22
-- 1.3.6.1.4.1.2011.6.174.2.3.0.22
		-- 1.3.6.1.4.1.2011.6.174.2.3.0.22
		hwUpsInputIsolatingTransAlarmResumeTrap NOTIFICATION-TYPE
			OBJECTS { hwUpsTrapsDeviceId, hwUpsTrapsModuleSeqId, hwUpsTrapsEquipID, hwUpsTrapsID, hwUpsTrapsReasonId,
				hwUpsTrapsText, hwUpsTrapsLevel, hwUpsTrapsFlag, hwUpsTrapsSynchronNum, hwUpsTrapsTime
				 }
			STATUS current
			DESCRIPTION
				"Transformer Abnormal Resume Trap.
				Its correlation binding parameters: Device ID, Sequence ID, Equip ID, Trap ID,
				Trap Reason ID, Trap Text, Trap Level, Trap Flag, Synchron NO and the time. "
			::= { hwUpsAlarmTrapsPrefix 22 }


        hwUpsInternalAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Supervision Unit Internal Fault Trap.
                  Its correlation binding parameters: Device ID, Sequence ID, Equip ID, Trap ID,
                  Trap Reason ID, Trap Text, Trap Level, Trap Flag, Synchron NO and the time."
            ::= { hwUpsAlarmTrapsPrefix 23 }

        hwUpsInternalAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Supervision Unit Internal Fault Resume Trap.
                  Its correlation binding parameters: Device ID, Sequence ID, Equip ID, Trap ID,
                  Trap Reason ID, Trap Text, Trap Level, Trap Flag, Synchron NO and the time."
            ::= { hwUpsAlarmTrapsPrefix 24 }

        hwUpsRectifierAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Rectifier Abnormal Trap.
                  Its correlation binding parameters: Device ID, Sequence ID, Equip ID, Trap ID,
                  Trap Reason ID, Trap Text, Trap Level, Trap Flag, Synchron NO and the time."
            ::= { hwUpsAlarmTrapsPrefix 25 }

        hwUpsRectifierAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Rectifier Abnormal Resume Trap.
                  Its correlation binding parameters: Device ID, Sequence ID, Equip ID, Trap ID,
                  Trap Reason ID, Trap Text, Trap Level, Trap Flag, Synchron NO and the time. "
            ::= { hwUpsAlarmTrapsPrefix 26 }

        hwUpsChargerAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Charger Abnormal Trap.
                  Its correlation binding parameters: Device ID, Sequence ID, Equip ID, Trap ID,
                  Trap Reason ID, Trap Text, Trap Level, Trap Flag, Synchron NO and the time. "
            ::= { hwUpsAlarmTrapsPrefix 27 }

        hwUpsChargerAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Charger Abnormal Resume Trap.
                  Its correlation binding parameters:Device ID, Sequence ID, Equip ID, Trap ID,
                  Trap Reason ID, Trap Text, Trap Level, Trap Flag, Synchron NO and the time."
            ::= { hwUpsAlarmTrapsPrefix 28 }

        hwUpsDischargerAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Discharger Abnormal Trap.
                  Its correlation binding parameters:Device ID, Sequence ID, Equip ID, Trap ID,
                  Trap Reason ID, Trap Text, Trap Level, Trap Flag, Synchron NO and the time. "
            ::= { hwUpsAlarmTrapsPrefix 29 }

        hwUpsDischargerAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Discharger Abnormal Resume Trap.
                  Its correlation binding parameters: Device ID, Sequence ID, Equip ID, Trap ID,
                  Trap Reason ID, Trap Text, Trap Level, Trap Flag, Synchron NO and the time."
            ::= { hwUpsAlarmTrapsPrefix 30 }

        hwUpsACAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "AC Abnormal Trap.
                  Its correlation binding parameters: Device ID, Sequence ID, Equip ID, Trap ID,
                  Trap Reason ID, Trap Text, Trap Level, Trap Flag, Synchron NO and the time. "
            ::= { hwUpsAlarmTrapsPrefix 31 }

        hwUpsACAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "AC Abnormal Resume Trap.
                  Its correlation binding parameters: Device ID, Sequence ID, Equip ID, Trap ID,
                  Trap Reason ID, Trap Text, Trap Level, Trap Flag, Synchron NO and the time. "
            ::= { hwUpsAlarmTrapsPrefix 32 }

        hwUpsModuleNotReadyAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Module Not Ready Abnormal Trap.
                  Its correlation binding parameters: Device ID, Sequence ID, Equip ID, Trap ID,
                  Trap Reason ID, Trap Text, Trap Level, Trap Flag, Synchron NO and the time."
            ::= { hwUpsAlarmTrapsPrefix 33 }

        hwUpsModuleNotReadyAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Module Not Ready Abnormal Resume Trap.
                  Its correlation binding parameters: Device ID, Sequence ID, Equip ID, Trap ID,
                  Trap Reason ID, Trap Text, Trap Level, Trap Flag, Synchron NO and the time."
            ::= { hwUpsAlarmTrapsPrefix 34 }

        hwUpsInverterAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Inverter Abnormal Trap.
                  Its correlation binding parameters: Device ID, Sequence ID, Equip ID, Trap ID,
                  Trap Reason ID, Trap Text, Trap Level, Trap Flag, Synchron NO and the time. "
            ::= { hwUpsAlarmTrapsPrefix 35 }

        hwUpsInverterAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Inverter Abnormal Resume Trap.
                  Its correlation binding parameters: Device ID, Sequence ID, Equip ID, Trap ID,
                  Trap Reason ID, Trap Text, Trap Level, Trap Flag, Synchron NO and the time."
            ::= { hwUpsAlarmTrapsPrefix 36 }

        hwUpsECUAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "ECU Abnormal Trap.
                  Its correlation binding parameters: Device ID, Sequence ID, Equip ID, Trap ID,
                  Trap Reason ID, Trap Text, Trap Level, Trap Flag, Synchron NO and the time."
            ::= { hwUpsAlarmTrapsPrefix 37 }

        hwUpsECUAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "ECU Abnormal Resume Trap.
                  Its correlation binding parameters: Device ID, Sequence ID, Equip ID, Trap ID,
                  Trap Reason ID, Trap Text, Trap Level, Trap Flag, Synchron NO and the time."
            ::= { hwUpsAlarmTrapsPrefix 38 }

        hwUpsSPDAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "SPD Abnormal Trap.
                  Its correlation binding parameters: Device ID, Sequence ID, Equip ID, Trap ID,
                  Trap Reason ID, Trap Text, Trap Level, Trap Flag, Synchron NO and the time."
            ::= { hwUpsAlarmTrapsPrefix 39 }

        hwUpsSPDAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "SPD Abnormal Resume Trap.
                  Its correlation binding parameters: Device ID, Sequence ID, Equip ID, Trap ID,
                  Trap Reason ID, Trap Text, Trap Level, Trap Flag, Synchron NO and the time."
            ::= { hwUpsAlarmTrapsPrefix 40 }

        hwUpsOperationFaultAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Operation Fault Abnormal Trap.
                  Its correlation binding parameters: Device ID, Sequence ID, Equip ID, Trap ID,
                  Trap Reason ID, Trap Text, Trap Level, Trap Flag, Synchron NO and the time."
            ::= { hwUpsAlarmTrapsPrefix 41 }

        hwUpsOperationFaultAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Operation Fault Abnormal Resume Trap.
                  Its correlation binding parameters: Device ID, Sequence ID, Equip ID, Trap ID,
                  Trap Reason ID, Trap Text, Trap Level, Trap Flag, Synchron NO and the time."
            ::= { hwUpsAlarmTrapsPrefix 42 }

        hwUpsOverLoadAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Over Load Abnormal Trap.
                  Its correlation binding parameters: Device ID, Sequence ID, Equip ID, Trap ID,
                  Trap Reason ID, Trap Text, Trap Level, Trap Flag, Synchron NO and the time."
            ::= { hwUpsAlarmTrapsPrefix 43 }

        hwUpsOverLoadAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Over Load Abnormal Resume Trap.
                  Its correlation binding parameters:Device ID, Sequence ID, Equip ID, Trap ID,
                  Trap Reason ID, Trap Text, Trap Level, Trap Flag, Synchron NO and the time. "
            ::= { hwUpsAlarmTrapsPrefix 44 }

        hwUpsOverLoadOverTimeAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Over-Load Overtime Abnormal Trap.
                  Its correlation binding parameters: Device ID, Sequence ID, Equip ID, Trap ID,
                  Trap Reason ID, Trap Text, Trap Level, Trap Flag, Synchron NO and the time."
            ::= { hwUpsAlarmTrapsPrefix 45 }

        hwUpsOverLoadOverTimeAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Over-Load Overtime Abnormal Resume Trap.
                  Its correlation binding parameters: Device ID, Sequence ID, Equip ID, Trap ID,
                  Trap Reason ID, Trap Text, Trap Level, Trap Flag, Synchron NO and the time."
            ::= { hwUpsAlarmTrapsPrefix 46 }

        hwUpsLBSAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "LBS Abnormal Trap.
                  Its correlation binding parameters: Device ID, Sequence ID, Equip ID, Trap ID,
                  Trap Reason ID, Trap Text, Trap Level, Trap Flag, Synchron NO and the time. "
            ::= { hwUpsAlarmTrapsPrefix 47 }

        hwUpsLBSAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "LBS Abnormal Resume Trap.
                  Its correlation binding parameters: Device ID, Sequence ID, Equip ID, Trap ID,
                  Trap Reason ID, Trap Text, Trap Level, Trap Flag, Synchron NO and the time. "
            ::= { hwUpsAlarmTrapsPrefix 48 }

        hwUpsBypSwitchAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Bypass Switch Abnormal Resume Trap.
                  Its correlation binding parameters: Device ID, Sequence ID, Equip ID, Trap ID,
                  Trap Reason ID, Trap Text, Trap Level, Trap Flag, Synchron NO and the time. "
            ::= { hwUpsAlarmTrapsPrefix 49 }

        hwUpsBypSwitchAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Bypass Switch Abnormal Resume Trap.
                  Its correlation binding parameters: Device ID, Sequence ID, Equip ID, Trap ID,
                  Trap Reason ID, Trap Text, Trap Level, Trap Flag, Synchron NO and the time."
            ::= { hwUpsAlarmTrapsPrefix 50 }

        hwUpsBatteryFault1AlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "When battery reversed, no Battery, battery earth fault or battery stop discharge abnormal happen, an alarm trap will be send through this OID.
                  Its correlation binding parameters: Device ID, Sequence ID, Equip ID, Trap ID,
                  Trap Reason ID, Trap Text, Trap Level, Trap Flag, Synchron NO and the time. "
            ::= { hwUpsAlarmTrapsPrefix 51 }

        hwUpsBatteryFault1AlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "When battery reversed, no Battery, battery earth fault or battery stop discharge abnormal resume, a trap will be send through this OID.
                  Its correlation binding parameters: Device ID, Sequence ID, Equip ID, Trap ID,
                  Trap Reason ID, Trap Text, Trap Level, Trap Flag, Synchron NO and the time."
            ::= { hwUpsAlarmTrapsPrefix 52 }

        hwUpsBatteryFault2AlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "When battery over temperature, battery need maintenance, or battery voltage low abnormal happen, an alarm trap will be send through this OID.
                  Its correlation binding parameters: Device ID, Sequence ID, Equip ID, Trap ID,
                  Trap Reason ID, Trap Text, Trap Level, Trap Flag, Synchron NO and the time."
            ::= { hwUpsAlarmTrapsPrefix 53 }

        hwUpsBatteryFault2AlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "When battery over temperature, battery need maintenance, or battery voltage low abnormal resume, a trap will be send through this OID.
                  Its correlation binding parameters:Device ID, Sequence ID, Equip ID, Trap ID,
                  Trap Reason ID, Trap Text, Trap Level, Trap Flag, Synchron NO and the time. "
            ::= { hwUpsAlarmTrapsPrefix 54 }

        hwUpsBatteryChangeLimitAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Battery Change Limit Trap.
                  Its correlation binding parameters: Device ID, Sequence ID, Equip ID, Trap ID,
                  Trap Reason ID, Trap Text, Trap Level, Trap Flag, Synchron NO and the time."
            ::= { hwUpsAlarmTrapsPrefix 55 }

        hwUpsBatteryChangeLimitAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Battery Change Limit Resume Trap.
                  Its correlation binding parameters: Device ID, Sequence ID, Equip ID, Trap ID,
                  Trap Reason ID, Trap Text, Trap Level, Trap Flag, Synchron NO and the time."
            ::= { hwUpsAlarmTrapsPrefix 56 }


		-- 1.3.6.1.4.1.2011.6.174.2.3.0.57
		hwUpsRectifierStartLimitAlarmTrap NOTIFICATION-TYPE
			OBJECTS { hwUpsTrapsDeviceId, hwUpsTrapsModuleSeqId, hwUpsTrapsEquipID, hwUpsTrapsID, hwUpsTrapsReasonId,
				hwUpsTrapsText, hwUpsTrapsLevel, hwUpsTrapsFlag, hwUpsTrapsSynchronNum, hwUpsTrapsTime
				 }
			STATUS current
			DESCRIPTION
				"Rectifier Start Limit Trap.
				Its correlation binding parameters: Device ID, Sequence ID, Equip ID, Trap ID,
				Trap Reason ID, Trap Text, Trap Level, Trap Flag, Synchron NO and the time. "
			::= { hwUpsAlarmTrapsPrefix 57 }


		-- 1.3.6.1.4.1.2011.6.174.2.3.0.58
		hwUpsRectifierStartLimitAlarmResumeTrap NOTIFICATION-TYPE
			OBJECTS { hwUpsTrapsDeviceId, hwUpsTrapsModuleSeqId, hwUpsTrapsEquipID, hwUpsTrapsID, hwUpsTrapsReasonId,
				hwUpsTrapsText, hwUpsTrapsLevel, hwUpsTrapsFlag, hwUpsTrapsSynchronNum, hwUpsTrapsTime
				 }
			STATUS current
			DESCRIPTION
				"Rectifier Start Limit Resume Trap.
				Its correlation binding parameters: Device ID, Sequence ID, Equip ID, Trap ID,
				Trap Reason ID, Trap Text, Trap Level, Trap Flag, Synchron NO and the time. "
			::= { hwUpsAlarmTrapsPrefix 58 }


		-- 1.3.6.1.4.1.2011.6.174.2.3.0.59
		hwUpsMainLoadCapicityAlarmTrap NOTIFICATION-TYPE
			OBJECTS { hwUpsTrapsDeviceId, hwUpsTrapsModuleSeqId, hwUpsTrapsEquipID, hwUpsTrapsID, hwUpsTrapsReasonId,
				hwUpsTrapsText, hwUpsTrapsLevel, hwUpsTrapsFlag, hwUpsTrapsSynchronNum, hwUpsTrapsTime
				 }
			STATUS current
			DESCRIPTION
				"Main Load Capicity Trap.
				Its correlation binding parameters: Device ID, Sequence ID, Equip ID, Trap ID,
				Trap Reason ID, Trap Text, Trap Level, Trap Flag, Synchron NO and the time. "
			::= { hwUpsAlarmTrapsPrefix 59 }


		-- 1.3.6.1.4.1.2011.6.174.2.3.0.60
		hwUpsMainLoadCapicityAlarmResumeTrap NOTIFICATION-TYPE
			OBJECTS { hwUpsTrapsDeviceId, hwUpsTrapsModuleSeqId, hwUpsTrapsEquipID, hwUpsTrapsID, hwUpsTrapsReasonId,
				hwUpsTrapsText, hwUpsTrapsLevel, hwUpsTrapsFlag, hwUpsTrapsSynchronNum, hwUpsTrapsTime
				 }
			STATUS current
			DESCRIPTION
				"Main Load Capicity Resume Trap.
				Its correlation binding parameters: Device ID, Sequence ID, Equip ID, Trap ID,
				Trap Reason ID, Trap Text, Trap Level, Trap Flag, Synchron NO and the time. "
			::= { hwUpsAlarmTrapsPrefix 60 }


		-- 1.3.6.1.4.1.2011.6.174.2.3.0.61
		hwUpsBatteryChangeAlarmTrap NOTIFICATION-TYPE
			OBJECTS { hwUpsTrapsDeviceId, hwUpsTrapsModuleSeqId, hwUpsTrapsEquipID, hwUpsTrapsID, hwUpsTrapsReasonId,
				hwUpsTrapsText, hwUpsTrapsLevel, hwUpsTrapsFlag, hwUpsTrapsSynchronNum, hwUpsTrapsTime
				 }
			STATUS current
			DESCRIPTION
				"Batterry Change Trap.
				Its correlation binding parameters: Device ID, Sequence ID, Equip ID, Trap ID,
				Trap Reason ID, Trap Text, Trap Level, Trap Flag, Synchron NO and the time. "
			::= { hwUpsAlarmTrapsPrefix 61 }


		-- 1.3.6.1.4.1.2011.6.174.2.3.0.62
		hwUpsBatteryChangeAlarmResumeTrap NOTIFICATION-TYPE
			OBJECTS { hwUpsTrapsDeviceId, hwUpsTrapsModuleSeqId, hwUpsTrapsEquipID, hwUpsTrapsID, hwUpsTrapsReasonId,
				hwUpsTrapsText, hwUpsTrapsLevel, hwUpsTrapsFlag, hwUpsTrapsSynchronNum, hwUpsTrapsTime
				 }
			STATUS current
			DESCRIPTION
				"Batterry Change Resume Trap.
				Its correlation binding parameters: Device ID, Sequence ID, Equip ID, Trap ID,
				Trap Reason ID, Trap Text, Trap Level, Trap Flag, Synchron NO and the time. "
			::= { hwUpsAlarmTrapsPrefix 62 }

        hwUpsBatteryMaintainAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Batterry Maintain Trap.
                  Its correlation binding parameters: Device ID, Sequence ID, Equip ID, Trap ID,
                  Trap Reason ID, Trap Text, Trap Level, Trap Flag, Synchron NO and the time."
            ::= { hwUpsAlarmTrapsPrefix 63 }

        hwUpsBatteryMaintainAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Batterry Maintain Resume Trap.
                  Its correlation binding parameters: Device ID, Sequence ID, Equip ID, Trap ID,
                  Trap Reason ID, Trap Text, Trap Level, Trap Flag, Synchron NO and the time."
            ::= { hwUpsAlarmTrapsPrefix 64 }


		-- 1.3.6.1.4.1.2011.6.174.2.3.0.65
		hwUpsMinorLoadOffAlarmTrap NOTIFICATION-TYPE
			OBJECTS { hwUpsTrapsDeviceId, hwUpsTrapsModuleSeqId, hwUpsTrapsEquipID, hwUpsTrapsID, hwUpsTrapsReasonId,
				hwUpsTrapsText, hwUpsTrapsLevel, hwUpsTrapsFlag, hwUpsTrapsSynchronNum, hwUpsTrapsTime
				 }
			STATUS current
			DESCRIPTION
				"Minor Load Off Trap.
				Its correlation binding parameters: Device ID, Sequence ID, Equip ID, Trap ID,
				Trap Reason ID, Trap Text, Trap Level, Trap Flag, Synchron NO and the time. "
			::= { hwUpsAlarmTrapsPrefix 65 }


		-- 1.3.6.1.4.1.2011.6.174.2.3.0.66
		hwUpsMinorLoadOffAlarmResumeTrap NOTIFICATION-TYPE
			OBJECTS { hwUpsTrapsDeviceId, hwUpsTrapsModuleSeqId, hwUpsTrapsEquipID, hwUpsTrapsID, hwUpsTrapsReasonId,
				hwUpsTrapsText, hwUpsTrapsLevel, hwUpsTrapsFlag, hwUpsTrapsSynchronNum, hwUpsTrapsTime
				 }
			STATUS current
			DESCRIPTION
				"Minor Load Off Resume Trap.
				Its correlation binding parameters: Device ID, Sequence ID, Equip ID, Trap ID,
				Trap Reason ID, Trap Text, Trap Level, Trap Flag, Synchron NO and the time. "
			::= { hwUpsAlarmTrapsPrefix 66 }


		-- 1.3.6.1.4.1.2011.6.174.2.3.0.67
		hwUpsParaStatusSetAlarmTrap NOTIFICATION-TYPE
			OBJECTS { hwUpsTrapsDeviceId, hwUpsTrapsModuleSeqId, hwUpsTrapsEquipID, hwUpsTrapsID, hwUpsTrapsReasonId,
				hwUpsTrapsText, hwUpsTrapsLevel, hwUpsTrapsFlag, hwUpsTrapsSynchronNum, hwUpsTrapsTime
				 }
			STATUS current
			DESCRIPTION
				"Parallel Status Set Trap.
				Its correlation binding parameters: Device ID, Sequence ID, Equip ID, Trap ID,
				Trap Reason ID, Trap Text, Trap Level, Trap Flag, Synchron NO and the time. "
			::= { hwUpsAlarmTrapsPrefix 67 }


		-- 1.3.6.1.4.1.2011.6.174.2.3.0.68
		hwUpsParaStatusSetAlarmResumeTrap NOTIFICATION-TYPE
			OBJECTS { hwUpsTrapsDeviceId, hwUpsTrapsModuleSeqId, hwUpsTrapsEquipID, hwUpsTrapsID, hwUpsTrapsReasonId,
				hwUpsTrapsText, hwUpsTrapsLevel, hwUpsTrapsFlag, hwUpsTrapsSynchronNum, hwUpsTrapsTime
				 }
			STATUS current
			DESCRIPTION
				"Parallel Status Set Resume Trap.
				Its correlation binding parameters: Device ID, Sequence ID, Equip ID, Trap ID,
				Trap Reason ID, Trap Text, Trap Level, Trap Flag, Synchron NO and the time. "
			::= { hwUpsAlarmTrapsPrefix 68 }

        hwUpsRemainCapacityAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Remain Capacity Trap.
                  Its correlation binding parameters: Device ID, Sequence ID, Equip ID, Trap ID,
                  Trap Reason ID, Trap Text, Trap Level, Trap Flag, Synchron NO and the time. "
            ::= { hwUpsAlarmTrapsPrefix 69 }

        hwUpsRemainCapacityAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Remain Capacity Resume Trap.
                  Its correlation binding parameters: Device ID, Sequence ID, Equip ID, Trap ID,
                  Trap Reason ID, Trap Text, Trap Level, Trap Flag, Synchron NO and the time."
            ::= { hwUpsAlarmTrapsPrefix 70 }

        hwUpsParParaAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Parallel Parameter Trap.
                  Its correlation binding parameters: Device ID, Sequence ID, Equip ID, Trap ID,
                  Trap Reason ID, Trap Text, Trap Level, Trap Flag, Synchron NO and the time. "
            ::= { hwUpsAlarmTrapsPrefix 71 }

        hwUpsParParaAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Parallel Parameter Resume Trap.
                  Its correlation binding parameters: Device ID, Sequence ID, Equip ID, Trap ID,
                  Trap Reason ID, Trap Text, Trap Level, Trap Flag, Synchron NO and the tim"
            ::= { hwUpsAlarmTrapsPrefix 72 }


		-- 1.3.6.1.4.1.2011.6.174.2.3.0.73
		hwUpsFlashAlarmTrap NOTIFICATION-TYPE
			OBJECTS { hwUpsTrapsDeviceId, hwUpsTrapsModuleSeqId, hwUpsTrapsEquipID, hwUpsTrapsID, hwUpsTrapsReasonId,
				hwUpsTrapsText, hwUpsTrapsLevel, hwUpsTrapsFlag, hwUpsTrapsSynchronNum, hwUpsTrapsTime
				 }
			STATUS current
			DESCRIPTION
				"Flash Trap.
				Its correlation binding parameters: Device ID, Sequence ID, Equip ID, Trap ID,
				Trap Reason ID, Trap Text, Trap Level, Trap Flag, Synchron NO and the time"
			::= { hwUpsAlarmTrapsPrefix 73 }


		-- 1.3.6.1.4.1.2011.6.174.2.3.0.74
		hwUpsFlashAlarmResumeTrap NOTIFICATION-TYPE
			OBJECTS { hwUpsTrapsDeviceId, hwUpsTrapsModuleSeqId, hwUpsTrapsEquipID, hwUpsTrapsID, hwUpsTrapsReasonId,
				hwUpsTrapsText, hwUpsTrapsLevel, hwUpsTrapsFlag, hwUpsTrapsSynchronNum, hwUpsTrapsTime
				 }
			STATUS current
			DESCRIPTION
				"Flash Resume Trap.
				Its correlation binding parameters: Device ID, Sequence ID, Equip ID, Trap ID,
				Trap Reason ID, Trap Text, Trap Level, Trap Flag, Synchron NO and the time"
			::= { hwUpsAlarmTrapsPrefix 74 }

        hwUpsManulPowerOnOffTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Manul Power On Off Trap.
                  Its correlation binding parameters: Device ID, Sequence ID, Equip ID, Trap ID,
                  Trap Reason ID, Trap Text, Trap Level, Trap Flag, Synchron NO and the time."
            ::= { hwUpsAlarmTrapsPrefix 75 }

        hwUpsManulPowerOnOffResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Manul Power On Off Resume Trap.
                  Its correlation binding parameters: Device ID, Sequence ID, Equip ID, Trap ID,
                  Trap Reason ID, Trap Text, Trap Level, Trap Flag, Synchron NO and the time"
            ::= { hwUpsAlarmTrapsPrefix 76 }

        hwUpsIOAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "IO signal Trap.
                  Its correlation binding parameters: Device ID, Sequence ID, Equip ID, Trap ID,
                  Trap Reason ID, Trap Text, Trap Level, Trap Flag, Synchron NO and the time"
            ::= { hwUpsAlarmTrapsPrefix 77 }

        hwUpsIOAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "IO Signal Resume Trap.
                  Its correlation binding parameters: Device ID, Sequence ID, Equip ID, Trap ID,
                  Trap Reason ID, Trap Text, Trap Level, Trap Flag, Synchron NO and the time"
            ::= { hwUpsAlarmTrapsPrefix 78 }

        hwUpsEnvironmentDataAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Environment Date Trap.
                  Its correlation binding parameters: Device ID, Sequence ID, Equip ID, Trap ID,
                  Trap Reason ID, Trap Text, Trap Level, Trap Flag, Synchron NO and the time"
            ::= { hwUpsAlarmTrapsPrefix 79 }

        hwUpsEnvironmentDataAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Environment Date Resume Trap.
                  Its correlation binding parameters: Device ID, Sequence ID, Equip ID, Trap ID,
                  Trap Reason ID, Trap Text, Trap Level, Trap Flag, Synchron NO and the time"
            ::= { hwUpsAlarmTrapsPrefix 80 }

        hwUpsUpdatingAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Updating Trap.
                  Its correlation binding parameters: Device ID, Sequence ID, Equip ID, Trap ID,
                  Trap Reason ID, Trap Text, Trap Level, Trap Flag, Synchron NO and the time"
            ::= { hwUpsAlarmTrapsPrefix 81 }

        hwUpsUpdatingAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Updating Resume Trap.
                  Its correlation binding parameters: Device ID, Sequence ID, Equip ID, Trap ID,
                  Trap Reason ID, Trap Text, Trap Level, Trap Flag, Synchron NO and the time"
            ::= { hwUpsAlarmTrapsPrefix 82 }

        hwUpsProgramAbnormalTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Program Abnormal Trap.
                  Its correlation binding parameters: Device ID, Sequence ID, Equip ID, Trap ID,
                  Trap Reason ID, Trap Text, Trap Level, Trap Flag, Synchron NO and the time"
            ::= { hwUpsAlarmTrapsPrefix 83 }

        hwUpsProgramAbnormalResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Program Abnormal Resume Trap.
                  Its correlation binding parameters: Device ID, Sequence ID, Equip ID, Trap ID,
                  Trap Reason ID, Trap Text, Trap Level, Trap Flag, Synchron NO and the time"
            ::= { hwUpsAlarmTrapsPrefix 84 }

        hwUpsBcbFaultAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Bcb Fault Trap.
                  Its correlation binding parameters: Device ID, Sequence ID, Equip ID, Trap ID,
                  Trap Reason ID, Trap Text, Trap Level, Trap Flag, Synchron NO and the time"
            ::= { hwUpsAlarmTrapsPrefix 85 }

        hwUpsBcbFaultAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Bcb Fault Resume Trap.
                  Its correlation binding parameters: Device ID, Sequence ID, Equip ID, Trap ID,
                  Trap Reason ID, Trap Text, Trap Level, Trap Flag, Synchron NO and the time"
            ::= { hwUpsAlarmTrapsPrefix 86 }

        hwUpsEcoRangeAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "ECO Range Trap.
                  Its correlation binding parameters: Device ID, Sequence ID, Equip ID, Trap ID,
                  Trap Reason ID, Trap Text, Trap Level, Trap Flag, Synchron NO and the time"
            ::= { hwUpsAlarmTrapsPrefix 87 }

        hwUpsEcoRangeAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "ECO Range Resume Trap.
                  Its correlation binding parameters: Device ID, Sequence ID, Equip ID, Trap ID,
                  Trap Reason ID, Trap Text, Trap Level, Trap Flag, Synchron NO and the time"
            ::= { hwUpsAlarmTrapsPrefix 88 }

        hwUpsBMUAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Bmu Trap.
                  Its correlation binding parameters: Device ID, Sequence ID, Equip ID, Trap ID,
                  Trap Reason ID, Trap Text, Trap Level, Trap Flag, Synchron NO and the time"
            ::= { hwUpsAlarmTrapsPrefix 89 }

        hwUpsBMUAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Bmu Resume Trap.
                  Its correlation binding parameters: Device ID, Sequence ID, Equip ID, Trap ID,
                  Trap Reason ID, Trap Text, Trap Level, Trap Flag, Synchron NO and the time"
            ::= { hwUpsAlarmTrapsPrefix 90 }

        hwUpsElableFailedAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Elable Failed Trap.
                  Its correlation binding parameters: Device ID, Sequence ID, Equip ID, Trap ID,
                  Trap Reason ID, Trap Text, Trap Level, Trap Flag, Synchron NO and the time"
            ::= { hwUpsAlarmTrapsPrefix 91 }

        hwUpsElableFailedAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Elable Failed Resume Trap.
                  Its correlation binding parameters: Device ID, Sequence ID, Equip ID, Trap ID,
                  Trap Reason ID, Trap Text, Trap Level, Trap Flag, Synchron NO and the time"
            ::= { hwUpsAlarmTrapsPrefix 92 }

        hwUpsDIPConflictAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "DIP Conflict Trap"
            ::= { hwUpsAlarmTrapsPrefix 93 }

        hwUpsDIPConflictAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "DIP Conflict Resume Trap."
            ::= { hwUpsAlarmTrapsPrefix 94 }

        hwUpsSystemStatusTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Ups System Status Trap."
            ::= { hwUpsAlarmTrapsPrefix 95 }

        hwUpsSystemStatusResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Ups System Status Resume Trap."
            ::= { hwUpsAlarmTrapsPrefix 96 }

        hwUpsIBOXAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Ups IBOX Alarm Trap."
            ::= { hwUpsAlarmTrapsPrefix 97 }

        hwUpsIBOXAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Ups IBOX Alarm Resume Trap"
            ::= { hwUpsAlarmTrapsPrefix 98 }

        hwUpsBattRackAlarmTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Expand Borad Alarm Trap.
                  Its correlation binding parameters: Device ID, Sequence ID, Equip ID, Trap ID,
                  Trap Reason ID, Trap Text, Trap Level, Trap Flag, Synchron NO and the time."
            ::= { hwUpsAlarmTrapsPrefix 99 }

        hwUpsBattRackAlarmResumeTrap NOTIFICATION-TYPE
            OBJECTS { hwUpsTrapsDeviceId,hwUpsTrapsModuleSeqId,hwUpsTrapsEquipID,hwUpsTrapsID,hwUpsTrapsReasonId,hwUpsTrapsText,hwUpsTrapsLevel,hwUpsTrapsFlag,hwUpsTrapsSynchronNum,hwUpsTrapsTime            }
            STATUS current
            DESCRIPTION
                "Expand Borad Alarm Resume Trap.
                  Its correlation binding parameters: Device ID, Sequence ID, Equip ID, Trap ID,
                  Trap Reason ID, Trap Text, Trap Level, Trap Flag, Synchron NO and the time."
            ::= { hwUpsAlarmTrapsPrefix 100 }

END
