-- ============================================================================
-- Copyright (C) 2019 by  HUAWEI TECHNOLOGIES. All rights reserved.
-- Description: This mib mainly provides functions of configuring and
--              querying the license parameters, and querying resource items/function items.
--              Certain functions of the device are controlled by the license of the resource items,
--              and certain functions are controlled by the license of the function items.
-- Reference:
-- Version: V1.37
-- ============================================================================
    HUAWEI-LICENSE-MIB DEFINITIONS ::= BEGIN

        IMPORTS
            NOTIFICATION-TYPE, Gauge32
                FROM SNMPv2-SMI
            huaweiUtility
                FROM HUAWEI-MIB
            ifIndex
               FROM IF-MIB
            IpAddress, Unsigned32, OBJECT-TYPE, Integer32, Gauge32, MODULE-IDENTITY
                FROM SNMPv2-SMI;


        hwLicense MODULE-IDENTITY
            LAST-UPDATED "201901150000Z"
            ORGANIZATION "Huawei Technologies Co.,Ltd."
            CONTACT-INFO
                         "Huawei Industrial Base
                          Bantian, Longgang
                          Shenzhen 518129
                          People's Republic of China
                          Website: http://www.huawei.com
                          Email: support@huawei.com
                         "
            DESCRIPTION
                "
                This mib mainly provides functions of configuring and
                querying the license parameters, and querying resource items/function items.
                Certain functions of the device are controlled by the license of the resource items,
                and certain functions are controlled by the license of the function items.
                "

 --  Revision history
            REVISION    "201901150000Z"
            DESCRIPTION "V1.37,
			             1. modified the following objects:
                            hwOxegBoardSubscriberNumLicenseAuth.
                        "

            REVISION    "201809050000Z"
            DESCRIPTION "V1.35,
			             1. Added the following objects:
                            hwMpleRtuLicControlObjects.
                         2. Added the following tables:
                            hwMpleEnhancementGlobalPara,hwMpleEnhancementPlusGlobalPara.
                         3. Added the following nodes:
						    hwMpleEnhancementLicAuth, hwMpleEnhancementUseNum, hwMpleEnhancementESN,
							hwMpleEnhancementPlusLicAuth, hwMpleEnhancementPlusUseNum, hwMpleEnhancementPlusESN.
                        "

            REVISION    "201808250000Z"
            DESCRIPTION "V1.35,
			 1. Added the following objects:
                            hwXdslVectoringProLicControlObjects,hwXdslRtuGfastVectoringLicControlObjects,hwXdslVectoringNlvLicControlObjects.
                        "

            REVISION    "201807160000Z"
            DESCRIPTION "V1.34,
			             1. Added the following objects:
                            hwOxegServiceAndSubscriberLicenseControlObjects.
                         2. Added the following tables:
                            hwOxegServiceAndSubscriberLicenseGlobalPara.
                         3. Added the following nodes:
                            hwOxegPortServicePortNumLicenseAuth, hwOxegPortServicePortNumLicenseUsedNum,
							hwOxegBoardSubscriberNumLicenseAuth, hwOxegBoardSubscriberNumLicenseUsedNum.
                        "

			REVISION    "201806270000Z"
            DESCRIPTION "V1.33,
                         1. Added the following nodes:
                            hwXponBoardFlexLvl1PortLicenseControl, hwXponBoardFlexLvl1PortLicenseUseNum,
                            hwXponBoardFlexLvl2PortLicenseControl, hwXponBoardFlexLvl2PortLicenseUseNum,
                            hwXponBoardFlexLvl3PortLicenseControl, hwXponBoardFlexLvl3PortLicenseUseNum.
	                    "
            REVISION    "201806190000Z"
            DESCRIPTION "V1.32,
                         1. Added the following objects:
                            hwXdslRtuVectoringLicControlObjects, hwXdslRtuSuperVectoringLicControlObjects.
                         2. Added the following tables:
                            hwXdslRtuVectoringLicGlobalPara, hwXdslRtuSuperVectoringLicGlobalPara.
                         3. Added the following nodes:
                            hwXdslRtuVectoringLicAuth, hwXdslRtuVectoringLicPortNum, hwXdslRtuVectoringLicEsn,
                            hwXdslRtuSuperVectoringLicAuth, hwXdslRtuSuperVectoringLicPortNum, hwXdslRtuSuperVectoringLicEsn.
                        "

            REVISION    "201805040000Z"
            DESCRIPTION "V1.31,
                         1. Added the following tables:
                            hwSRv6LicControlObjects, hwSRv6LicGlobalPara.
                         2. Added the following nodes:
                            hwSRv6LicAuth, hwSRv6UserNum.
	    		 3. Added the following tables:
                            hwEvpnLicControlObjects, hwEvpnLicGlobalPara.
                         4. Added the following nodes:
                            hwEvpnLicAuth, hwEvpnUserNum.
                         "

            REVISION    "201710160000Z"
            DESCRIPTION "V1.30,
                         1. Added the following tables:
                            hwTwampLicControlObjects, hwTwampLicGlobalPara.
                         2. Added the following nodes:
                            hwTwampLicAuth, hwTwampUserNum.
                         "

            REVISION    "201705020000Z"
            DESCRIPTION "V1.29,
                         Added node hwCmtsOpticalNodeAntitheftEnable.
                         "

            REVISION    "201703310000Z"
            DESCRIPTION "V1.28,
                         1. Added the following tables:
                            hwGreLicControlObjects, hwGreLicGlobalPara, hwVxlanLicControlObjects, hwVxlanLicGlobalPara.
                         2. Added the following nodes:
                            hwGreLicAuth, hwGreTunnelUseNum, hwVxlanLicAuth, hwVxlanUserNum.
                         "

            REVISION    "201702160000Z"
            DESCRIPTION "V1.27,
                        1. Added the following tables:
                           hwXponBoardPortLicControlObjects, hwXponBoardPortLicensePara.
                        2. Added the following nodes:
                           hwXponBoardExtra4PortLicenseControl, hwXponBoardExtra4PortLicenseUsedNumber.
                         "

            REVISION    "201702090000Z"
            DESCRIPTION "V1.26,
                         1. Added the following tables:
                            hw50GTo100GLicControlObjects, hw50GTo100GLicGlobalPara, hw100GTo200GLicControlObjects, hw100GTo200GLicGlobalPara.
                         2. Added the following nodes:
                            hw50GTo100GLicAuth, hw50GTo100GUseNum, hw100GTo200GLicAuth, hw100GTo200GUseNum.
                         "

            REVISION    "201508120000Z"
            DESCRIPTION "V1.25,
                         Modified the description of hwCmtsAntitheftLicenseKey.
                         "

            REVISION    "201508030000Z"
            DESCRIPTION "V1.24,
                         Add the table of hwCmtsD31LicensePara.
                         "

            REVISION    "201503230000Z"
            DESCRIPTION "V1.23,
                         Modified the description of these leaf nodes: hwMplsLicAuth, hwIgmpLicAuth.
                         "

            REVISION    "201501150000Z"
            DESCRIPTION "V1.22,
                         1. Added the following tables:
                            hwMplsLicControlObjects, hwMplsLicGlobalPara, hwIgmpLicControlObjects, hwIgmpLicGlobalPara.
                         2. Added the following nodes:
                            hwMplsLicAuth, hwMplsUseNum, hwIgmpLicAuth, hwIgmpUserNum, hwIPv6Dhcpv6OptionUseNum.
                         "

            REVISION    "201412090000Z"
            DESCRIPTION "V1.21,
                         1. Added the following tables:
                            hw40GTo80GLicControlObjects, hw40GTo80GLicGlobalPara, hw80GTo160GLicControlObjects, hw80GTo160GLicGlobalPara.
                         2. Added the following nodes:
                            hw40GTo80GLicAuth, hw40GTo80GUseNum, hw80GTo160GLicAuth, hw80GTo160GUseNum.
                         "

            REVISION    "201412040000Z"
            DESCRIPTION "V1.20, add the nodes hw10GponThirdPartyOntLicAuth and hw10GponThirdPartyOntOnceOnlineNum.
                         Modified the description of the node hwThirdPartyOntOnceOnlineNum."

            REVISION    "201406250000Z"
            DESCRIPTION "V1.19, add table hwXdslVectoringLicControlObjects.
                         Modified the description of these leaf nodes: hwCmtsExtendedLicenseUpChannelLack, hwCmtsExtendedLicenseDownChannelLack."

            REVISION    "201312240000Z"
            DESCRIPTION "V1.18, add the D-CMTS anti-theft license key function. Add these nodes:hwCmtsAntitheftEnable, hwCmtsAntitheftLicenseKey."

            REVISION    "201308260000Z"
            DESCRIPTION "V1.17, add the clock license function."

            REVISION    "201307240000Z"
            DESCRIPTION "V1.16, add the JumboFrame license function."

            REVISION    "201302010000Z"
            DESCRIPTION "V1.15, modify these leaf nodes:hwCmtsBasicLicenseDownChannelTotal, hwCmtsExtendedLicenseDownChannelLockFlg, hwCmtsExtendedLicenseUpChannelLockFlg."

            REVISION    "201210270000Z"
            DESCRIPTION "V1.14, add the cmts license function."

            REVISION    "201205070000Z"
            DESCRIPTION "V1.13, add the DHCPv6 option license function."

            REVISION    "201202100000Z"
            DESCRIPTION "V1.11, add the MELT test license function."

            REVISION    "201112310000Z"
            DESCRIPTION "V1.12, added the license function for the third party ONT license."

            REVISION    "201011090000Z"
            DESCRIPTION "V1.10, The description of this MIB is modified according to the tool."

            REVISION    "201008250000Z"
            DESCRIPTION "V1.09, modified the contact-info and the revision history. Modified the description of leaves."

            REVISION    "201006130000Z"
            DESCRIPTION "V1.08, 1. Modified the description of the hwLicResTable, hwLicResEntry, hwLicFuncTable, hwLicFuncEntry, hwLicComFaultTrap,
                         hwLicComRecoverTrap, hwLicLogoutTrap, hwLicRecOverLoadTrap, and hwLicFucOverLoadTrap.
                         2. Changed the object name. For instance, the name of hwLicCommenTraps is changed to hwLicCommonTraps,
                         the name of hwLicAlmTraps is changed to hwLicAlarmTraps, the name of hwLicAlmTrapsPrefix is changed to hwLicAlarmTrapsPrefix."

            REVISION    "201003310000Z"
            DESCRIPTION "V1.07, DT requirements are implemented and the syntax and semantics of SIMPLETEST are changed."

            REVISION    "201001290000Z"
            DESCRIPTION "V1.06, The system supports the definitions of standard trap nodes and associated trap parameter nodes."

            REVISION    "201001250000Z"
            DESCRIPTION "V1.05, used SimpleTest clean warning and error, used MIB browser clean warning and error, and
                         added MIB description."

            REVISION    "200708010000Z"
            DESCRIPTION "V1.03, added the basic license function."

            REVISION    "200705230000Z"
            DESCRIPTION "V1.02, added two table objects."

            REVISION    "200601040000Z"
            DESCRIPTION "V1.00, completed the draft."
            ::= { huaweiUtility 114 }


--
-- Type definitions
--

--      Time ::= OCTET STRING


--
-- Node definitions
--

        hwLicensePara OBJECT IDENTIFIER ::= { hwLicense 1 }

        hwLicSpecialtySwitch OBJECT-TYPE
            SYNTAX INTEGER
            {
                on(1),
                off(2)
            }
            MAX-ACCESS read-write
            STATUS current
            DESCRIPTION
                "
                License function switch is classified into basic function switch and
                special function switch, which are used to control basic resources
                and special resources separately. The basic functions in the system are
                registered as basic resources generally. The non-basic/non-essential
                functions are registered as special resources. This MIB object can be
                used for querying and configuring the special function switch.
                Options:
                1. on(1)  -For the status of the special function switch, on(1) indicates that the special
                           resources can be controlled by the license function. The status of the function
                           switch can be set to on(1) only because once the function is enabled it cannot be disabled.
                2. off(2) -For the status of the special function switch, off(2) indicates that the special resources
                           cannot be controlled by the license function.
                "
            ::= { hwLicensePara 1 }

        hwLicESN OBJECT-TYPE
            SYNTAX IpAddress
            MAX-ACCESS read-write
            STATUS current
            DESCRIPTION
                "
                Serial number of the device, used for identifying the device uniquely.
                The ESN of the device needs to be configured to the IP address of the
                device connected to the NMS.
                The configuration of the ESN is not restricted by the license function switch.
                "
            ::= { hwLicensePara 2 }

        hwLicFirstServerIP OBJECT-TYPE
            SYNTAX IpAddress
            MAX-ACCESS read-write
            STATUS current
            DESCRIPTION
                "
                You can configure two license servers, one as an active server,
                and the other as a standby server. This object is used to configure
                the IP address of the active license server, and the active IP object.
                The standby IP object hwLicSecondIP can be configured only after the
                hwLicFirstServerIP is configured. When the device communicates with
                the license server, it first communicates with the active server
                and communicates with the standby server only when the communication
                between the device and active server is interrupted.
                "
            ::= { hwLicensePara 3 }

        hwLicSecondServerIP OBJECT-TYPE
            SYNTAX IpAddress
            MAX-ACCESS read-write
            STATUS current
            DESCRIPTION
                "
                You can configure two license servers, one as an active server,
                and the other as a standby server. This object is used to configure
                the IP address of the standby license server. hwLicSecondIP can be
                configured only after hwLicFirstServerIP is configured.
                "
            ::= { hwLicensePara 4 }

        hwLicServerPort OBJECT-TYPE
            SYNTAX Unsigned32 (1024..65535)
            MAX-ACCESS read-write
            STATUS current
            DESCRIPTION
                "
                A fixed port ID is required for the communication between
                the license server and client.
                This object is used to query and set the port ID of the license server.
                "
            ::= { hwLicensePara 5 }

        hwLicBasicSwitch OBJECT-TYPE
            SYNTAX INTEGER
            {
                on(1),
                off(2)
            }
            MAX-ACCESS read-write
            STATUS current
            DESCRIPTION
                "
                License function switch is classified into basic function
                switch and special function switch, which are used to control
                basic resources and special resources separately. The basic functions
                in the system are registered as basic resources generally.
                The non-basic/non-essential functions are registered as special resources.
                This MIB object can be used for querying and configuring the basic function switch.
                For the status of the basic function switch.
                Options:
                1.on(1)  -indicates that the basic resources can be controlled by the license function.
                2.off(2) -indicates that the basic resources cannot be controlled by the license function.
                The status of the function switch can be set to on(1) only because once the
                function is enabled it cannot be disabled.
                "
            ::= { hwLicensePara 6 }

        hwCmtsAntitheftEnable OBJECT-TYPE
            SYNTAX INTEGER
            {
                disable(1),
                enable(2)
            }
            MAX-ACCESS read-write
            STATUS current
            DESCRIPTION
                "
                Indicates whether OLT anti-theft is enabled or disabled. Default value: disable.
                Options:
                1.disable(1)  -OLT anti-theft is disabled.
                2.enable(2)   -OLT anti-theft is enabled.
                "
            ::= { hwLicensePara 7 }

        hwCmtsAntitheftLicenseKey OBJECT-TYPE
            SYNTAX OCTET STRING (SIZE (0..32))
            MAX-ACCESS read-write
            STATUS current
            DESCRIPTION
                "
                You can set the anti-theft key of the CMTS extended frame. It supports 8-32 bytes,
                containing a-z and A to Z, 10 numbers, and 8 symbols ( ) - _ / \ . &. A null character
                string is returned for a read operation.
                "
            ::= { hwLicensePara 8 }

        hwCmtsOpticalNodeAntitheftEnable OBJECT-TYPE
            SYNTAX INTEGER
            {
                disable(1),
                enable(2)
            }
            MAX-ACCESS read-write
            STATUS current
            DESCRIPTION
                "
                Indicates whether optical node anti-theft is enabled or disabled. Default value: disable.
                Options:
                1.disable(1)  -optical node anti-theft is disabled.
                2.enable(2)   -optical node anti-theft is enabled.
                "
            ::= { hwLicensePara 9 }

        hwLicResTable OBJECT-TYPE
            SYNTAX SEQUENCE OF HwLicResEntry
            MAX-ACCESS not-accessible
            STATUS current
            DESCRIPTION
                "
                Through the table for querying the resources controlled by license, feature names, resource names,
                the number of resources controlled by license, and the number and description
                of actually used resources of the resource items can be queried.
                The indexes of this table are hwLicFeatureName and hwLicResName. hwLicFeatureName is the feature name.
                hwLicResName is the resource name. The resource name must be the resource name associated with the feature name.
                Through the index, the number of resource items controlled by license, the number
                and description of actually used resources associated with the indexes can be obtained.
                "
            ::= { hwLicense 2 }

        hwLicResEntry OBJECT-TYPE
            SYNTAX HwLicResEntry
            MAX-ACCESS not-accessible
            STATUS current
            DESCRIPTION
                "
                Through the table for querying the resources controlled by license, feature names, resource names,
                the number of resources controlled by license, and the number and description
                of actually used resources of the resource items can be queried.
                The indexes of this entry are hwLicFeatureName and hwLicResName. hwLicFeatureName is the feature name.
                hwLicResName is the resource name. The resource name must be the resource name associated with the feature name.
                Through the index, the number of resource items controlled by license, the number
                and description of actually used resources associated with the indexes can be obtained.
                "
            INDEX { hwLicFeatureName, hwLicResName }
            ::= { hwLicResTable 1 }

        HwLicResEntry ::=
            SEQUENCE
            {
                hwLicFeatureName
                    OCTET STRING,
                hwLicResName
                    OCTET STRING,
                hwLicResAuthNum
                    Unsigned32,
                hwLicResUsedNum
                    Unsigned32,
                hwLicResDesc
                    OCTET STRING
             }

        hwLicFeatureName OBJECT-TYPE
            SYNTAX OCTET STRING
            MAX-ACCESS read-only
            STATUS current
            DESCRIPTION
                "
                This object is the index of hwLicResTable.
                The function items controlled by license are all based on the feature,
                and this object is the feature name.
                "
            ::= { hwLicResEntry 1 }

        hwLicResName OBJECT-TYPE
            SYNTAX OCTET STRING
            MAX-ACCESS read-only
            STATUS current
            DESCRIPTION
                "
                This object is the index of hwLicResTable.
                The function items controlled by license are all based on one feature.
                The resource items are the entities of the features,
                and there are multiple resource items for each feature.
                This object is the resource name.
                "
            ::= { hwLicResEntry 2 }

        hwLicResAuthNum OBJECT-TYPE
            SYNTAX Unsigned32
            MAX-ACCESS read-only
            STATUS current
            DESCRIPTION
                "
                Authorization from the license server is required for using the
                resources controlled by license.
                This object is used to obtain the number of authorized resources.
                "
            ::= { hwLicResEntry 3 }

        hwLicResUsedNum OBJECT-TYPE
            SYNTAX Unsigned32
            MAX-ACCESS read-only
            STATUS current
            DESCRIPTION
                "
                For the resources controlled by license, the number of resources
                that can be used cannot exceed the number of authorized resources.
                This object is used to obtain the number of currently used resources.
                "
            ::= { hwLicResEntry 4 }

        hwLicResDesc OBJECT-TYPE
            SYNTAX OCTET STRING
            MAX-ACCESS read-only
            STATUS current
            DESCRIPTION
                "
                Each resource controlled by license has a resource description.
                This object is used to obtain the resource description.
                "
            ::= { hwLicResEntry 5 }

        hwLicFuncTable OBJECT-TYPE
            SYNTAX SEQUENCE OF HwLicFuncEntry
            MAX-ACCESS not-accessible
            STATUS current
            DESCRIPTION
                "
                Through the table for querying the functions controlled by license,
                function names, the number of functions controlled by license,
                and function description can be queried.
                The indexes of this table are hwLicFeatureName and hwLicFuncName.
                hwLicFeatureName is the feature name and hwLicFuncName is the function name.
                Through the indexes, the number and description of authorized function
                items associated with the indexes can be obtained.
                "
            ::= { hwLicense 3 }

        hwLicFuncEntry OBJECT-TYPE
            SYNTAX HwLicFuncEntry
            MAX-ACCESS not-accessible
            STATUS current
            DESCRIPTION
                "
                Through the table for querying the functions controlled by license,
                function names, the number of functions controlled by license,
                and function description can be queried.
                The indexes of this entry are hwLicFeatureName and hwLicFuncName.
                hwLicFeatureName is the feature name and hwLicFuncName is the function name.
                Through the indexes, the number and description of authorized function
                items associated with the indexes can be obtained.
                "
            INDEX { hwLicFeatureName, hwLicFuncName }
            ::= { hwLicFuncTable 1 }

        HwLicFuncEntry ::=
            SEQUENCE
            {
                hwLicFuncName
                    OCTET STRING,
                hwLicFuncAuth
                    INTEGER,
                hwLicFuncDesc
                    OCTET STRING
             }

        hwLicFuncName OBJECT-TYPE
            SYNTAX OCTET STRING
            MAX-ACCESS read-only
            STATUS current
            DESCRIPTION
                "
                This object is the index of hwLicFuncTable.
                The function items controlled by license are all based on one feature.
                The function items are the entities of the features,
                and there are multiple function items for each feature.
                This object is the name of the function item.
                "
            ::= { hwLicFuncEntry 1 }

        hwLicFuncAuth OBJECT-TYPE
            SYNTAX INTEGER
            {
                disable(1),
                enable(2)
            }
            MAX-ACCESS read-only
            STATUS current
            DESCRIPTION
                "
                Authorization from the license server is required for using the
                function items controlled by license. This object is used to obtain
                the information indicating whether the authorization is obtained.
                Options:
                1.disable(1) -indicates that the authorization is not obtained and
                              the function cannot be used;
                2.enable(2)  -indicates that the authorization is obtained and
                              the function can be used.
                "
                ::= { hwLicFuncEntry 2 }

        hwLicFuncDesc OBJECT-TYPE
            SYNTAX OCTET STRING
            MAX-ACCESS read-only
            STATUS current
            DESCRIPTION
                "
                Each resource controlled by license has a resource description.
                This object is used to obtain the function description.
                "
            ::= { hwLicFuncEntry 3 }

        hwLicTrapsVbOids      OBJECT IDENTIFIER ::= { hwLicense  4 }
        hwLicCommonTraps      OBJECT IDENTIFIER ::= { hwLicense  5 }
        hwLicAlarmTraps       OBJECT IDENTIFIER ::= { hwLicense  6 }
        hwLicAlarmTrapsPrefix OBJECT IDENTIFIER ::= { hwLicAlarmTraps 0 }
        hwLicComFaultTrap   NOTIFICATION-TYPE
            STATUS current
            DESCRIPTION
                "
                 This trap message is reported when the communication between the device and the license server fails.
                "
            ::= { hwLicAlarmTrapsPrefix 1 }

        hwLicComRecoverTrap NOTIFICATION-TYPE
            STATUS current
            DESCRIPTION
                "
                 This trap message is reported when the communication between the license client and the server is restored.
                "
            ::= { hwLicAlarmTrapsPrefix 2 }

        hwLicLogoutTrap NOTIFICATION-TYPE
            STATUS current
            DESCRIPTION
                "
                 This trap message is reported when the device license expires.
                "
            ::= { hwLicAlarmTrapsPrefix 3 }

        hwLicRecOverLoadTrap   NOTIFICATION-TYPE
            OBJECTS { hwLicFeatureName, hwLicResName,hwLicResAuthNum,hwLicResUsedNum }
            STATUS current
            DESCRIPTION
                "
                 This trap message is reported when the license resources exceed the permitted number.
                "
            ::= { hwLicAlarmTrapsPrefix 4 }

        hwLicFucOverLoadTrap NOTIFICATION-TYPE
            OBJECTS { hwLicFeatureName, hwLicFuncName }
            STATUS current
            DESCRIPTION
                "
                 This trap message is reported when the device uses a function that is not supported by the license.
                "
            ::= { hwLicAlarmTrapsPrefix 5 }

        hwThirdPartyOntLicControlObjects OBJECT IDENTIFIER ::= { hwLicense 7 }
        hwThirdPartyOntLicGlobalPara   OBJECT IDENTIFIER ::= { hwThirdPartyOntLicControlObjects 1 }
        hwThirdPartyOntLicAuth OBJECT-TYPE
            SYNTAX INTEGER
            {
                enable(1),
                disable(2)
            }
            MAX-ACCESS read-write
            STATUS current
            DESCRIPTION
                "The object indicates third party ONT license switch.
                 Options:
                 1. enable(1)  -enable third party ONT license switch
                 2. disable(2) -disable third party ONT license switch"
            ::= { hwThirdPartyOntLicGlobalPara 1 }

        hwThirdPartyOntOnceOnlineNum OBJECT-TYPE
            SYNTAX Gauge32
            MAX-ACCESS read-only
            STATUS current
            DESCRIPTION
                "The number of 1G PON third party ONTs allowed to be online."
            ::= { hwThirdPartyOntLicGlobalPara 2 }

        hw10GponThirdPartyOntLicAuth OBJECT-TYPE
            SYNTAX INTEGER
            {
                enable(1),
                disable(2)
            }
            MAX-ACCESS read-write
            STATUS current
            DESCRIPTION
                "The object indicates 10G PON third party ONT license switch.
                 Options:
                 1. enable(1)  -enable 10G PON third party ONT license switch
                 2. disable(2) -disable 10G PON third party ONT license switch"
            ::= { hwThirdPartyOntLicGlobalPara 3 }

        hw10GponThirdPartyOntOnceOnlineNum OBJECT-TYPE
            SYNTAX Gauge32
            MAX-ACCESS read-only
            STATUS current
            DESCRIPTION
                "The number of 10G PON third party ONTs allowed to be online."
            ::= { hwThirdPartyOntLicGlobalPara 4 }

        hwMeltLicControlObjects OBJECT IDENTIFIER ::= { hwLicense 8 }

        hwMeltLicGlobalPara OBJECT IDENTIFIER ::= { hwMeltLicControlObjects 1 }

        hwMeltLicenseAuth OBJECT-TYPE
            SYNTAX INTEGER
            {
                enable(1),
                disable(2)
            }
            MAX-ACCESS read-write
            STATUS current
            DESCRIPTION
                "
                 The switch of MELT license auth.
                 Options:
                 1. enable(1)   -The number of MELT test ports has reached or exceeded the license, and not allowed to start the MELT test for the new port.
                 2. disable(2)  -The number of MELT test ports has not reached the license, and allowed to start the MELT test for the new port.
                 Default: disable(2)
                "
            ::= { hwMeltLicGlobalPara 1 }

        hwMeltTestedPortNum OBJECT-TYPE
            SYNTAX Gauge32
            MAX-ACCESS read-only
            STATUS current
            DESCRIPTION
                "
                 The number of ports has been MELT tested.
                "
            ::= { hwMeltLicGlobalPara 2 }

        hwMeltLicFuncTable OBJECT-TYPE
            SYNTAX  SEQUENCE OF HwMeltLicFuncEntry
            MAX-ACCESS  not-accessible
            STATUS  current
            DESCRIPTION
                "
                 This table is used to show the information about the MELT test port.
                 The index of this table is ifindex.
                "
            ::= { hwMeltLicControlObjects 2 }

        hwMeltLicFuncEntry OBJECT-TYPE
            SYNTAX  HwMeltLicFuncEntry
            MAX-ACCESS  not-accessible
            STATUS  current
            DESCRIPTION
                "
                 This table is used to show the information about the MELT test port.
                 The index of this entry is ifindex.
                "
            INDEX { ifIndex }
            ::= { hwMeltLicFuncTable 1 }

        HwMeltLicFuncEntry ::=
            SEQUENCE
            {
                 hwPortMeltTestedFlag       INTEGER
            }

        hwPortMeltTestedFlag OBJECT-TYPE
            SYNTAX INTEGER
            {
                tested(1),
                untested(2)
            }
            MAX-ACCESS  read-only
            STATUS  current
            DESCRIPTION
                "
                 The flag that the port has been MELT tested.
                 Options:
                 1. tested(1)      -The port has been MELT tested
                 2. untested(2)    -The port has not been MELT tested
                "
            ::= { hwMeltLicFuncEntry 1 }

        hwIPv6Dhcpv6ControlObjects OBJECT IDENTIFIER ::= { hwLicense 9 }

        hwIPv6Dhcpv6OptionLicenseAuth OBJECT-TYPE
            SYNTAX INTEGER
            {
                enable(1),
                disable(2)
            }
            MAX-ACCESS  read-write
            STATUS  current
            DESCRIPTION
                "
                 Used to control whether the DHCPv6 option function can be enabled for users.
                 If it is set to enable, the DHCPv6 option function can be enabled for users.
                 Otherwise, the DHCPv6 option function cannot be enabled for users.
                 Options:
                 1. enable(1)     -Enable DHCPv6 option license switch
                 2. disable(2)    -Disable DHCPv6 option license switch
                 default: enable(1)
                "
            ::= { hwIPv6Dhcpv6ControlObjects 1 }

        hwIPv6Dhcpv6OptionUseNum OBJECT-TYPE
            SYNTAX Unsigned32
            MAX-ACCESS  read-only
            STATUS  current
            DESCRIPTION
                "
                 The number of operations for DHCPv6 option function.
                "
            ::= { hwIPv6Dhcpv6ControlObjects 2 }

        hwCmtsLicControlObjects OBJECT IDENTIFIER ::= { hwLicense 10 }

        hwCmtsLicensePara OBJECT IDENTIFIER ::= { hwCmtsLicControlObjects 1 }

        hwCmtsBasicLicenseUpChannelTotal OBJECT-TYPE
            SYNTAX Unsigned32
            MAX-ACCESS  read-only
            STATUS  current
            DESCRIPTION
                "
                Total number about the basic license of upstream channel.
                "
            ::= { hwCmtsLicensePara 1 }

        hwCmtsBasicLicenseDownChannelTotal OBJECT-TYPE
            SYNTAX Unsigned32
            MAX-ACCESS  read-only
            STATUS  current
            DESCRIPTION
                "
                Total number about the basic license of downstream channel.
                "
            ::= { hwCmtsLicensePara 2 }

        hwCmtsBasicLicenseUpChannelUsed OBJECT-TYPE
            SYNTAX Unsigned32
            MAX-ACCESS  read-only
            STATUS  current
            DESCRIPTION
                "
                Used number about the basic license of upstream channel.
                "
            ::= { hwCmtsLicensePara 3 }

        hwCmtsBasicLicenseDownChannelUsed OBJECT-TYPE
            SYNTAX Unsigned32
            MAX-ACCESS  read-only
            STATUS  current
            DESCRIPTION
                "
                Used number about the basic license of downstream channel.
                "
            ::= { hwCmtsLicensePara 4 }

        hwCmtsExtendedLicenseUpChannelUsed OBJECT-TYPE
            SYNTAX Unsigned32
            MAX-ACCESS  read-only
            STATUS  current
            DESCRIPTION
                "
                Used number about the extended license of upstream channel.
                "
            ::= { hwCmtsLicensePara 5 }

        hwCmtsExtendedLicenseDownChannelUsed OBJECT-TYPE
            SYNTAX Unsigned32
            MAX-ACCESS  read-only
            STATUS  current
            DESCRIPTION
                "
                Used number about the extended license of downstream channel.
                "
            ::= { hwCmtsLicensePara 6 }

         hwCmtsExtendedLicenseUpChannelLockFlg OBJECT-TYPE
            SYNTAX INTEGER
            {
               locked(1),
               unlocked(2)
            }
            MAX-ACCESS  read-write
            STATUS  current
            DESCRIPTION
                "
                Lock flag about the extended license of upstream channel.
                Options:
                1. locked(1)   -Indicates that the extended license of upstream channel is locked
                2. unlocked(2) -Indicates that the extended license of upstream channel is unlocked
                "
            ::= { hwCmtsLicensePara 7 }

        hwCmtsExtendedLicenseDownChannelLockFlg OBJECT-TYPE
            SYNTAX INTEGER
            {
               locked(1),
               unlocked(2)
            }
            MAX-ACCESS  read-write
            STATUS  current
            DESCRIPTION
                "
                Lock flag about the extended license of downstream channel.
                Options:
                1. locked(1)   -Indicates that the extended license of downstream channel is locked
                2. unlocked(2) -Indicates that the extended license of downstream channel is unlocked
                "
            ::= { hwCmtsLicensePara 8 }

        hwCmtsExtendedLicenseUpChannelLack OBJECT-TYPE
            SYNTAX Unsigned32
            MAX-ACCESS  read-only
            STATUS  current
            DESCRIPTION
                "
                Number of upstream channel licenses to be obtained.
                "
            ::= { hwCmtsLicensePara 9 }

        hwCmtsExtendedLicenseDownChannelLack OBJECT-TYPE
            SYNTAX Unsigned32
            MAX-ACCESS  read-only
            STATUS  current
            DESCRIPTION
                "
                Number of downstream channel licenses to be obtained.
                "
            ::= { hwCmtsLicensePara 10 }

        hwCmtsD31LicensePara OBJECT IDENTIFIER ::= { hwCmtsLicControlObjects 2 }

        hwCmtsD31BasicLicenseUpChannelFreqTotal OBJECT-TYPE
            SYNTAX Unsigned32
            MAX-ACCESS  read-only
            STATUS  current
            DESCRIPTION
                "
                Total frequencies of the basic license for the upstream channels.
                Unit: Mhz
                "
            ::= { hwCmtsD31LicensePara 1 }

        hwCmtsD31BasicLicenseDownChannelFreqTotal OBJECT-TYPE
            SYNTAX Unsigned32
            MAX-ACCESS  read-only
            STATUS  current
            DESCRIPTION
                "
                Total frequencies of the basic license for the downstream channels.
                Unit: Mhz
                "
            ::= { hwCmtsD31LicensePara 2 }

        hwCmtsD31BasicLicenseUpChannelFreqUsed OBJECT-TYPE
            SYNTAX Unsigned32
            MAX-ACCESS  read-only
            STATUS  current
            DESCRIPTION
                "
                Used frequencies of the basic license for the upstream channels.
                Unit: Mhz
                "
            ::= { hwCmtsD31LicensePara 3 }

        hwCmtsD31BasicLicenseDownChannelFreqUsed OBJECT-TYPE
            SYNTAX Unsigned32
            MAX-ACCESS  read-only
            STATUS  current
            DESCRIPTION
                "
                Used frequencies of the basic license for the downstream channels.
                Unit: Mhz
                "
            ::= { hwCmtsD31LicensePara 4 }

        hwCmtsD31ExtendedLicenseUpChannelFreqUsed OBJECT-TYPE
            SYNTAX Unsigned32
            MAX-ACCESS  read-only
            STATUS  current
            DESCRIPTION
                "
                Used frequencies of the extended license for the upstream channels.
                Unit: Mhz
                "
            ::= { hwCmtsD31LicensePara 5 }

        hwCmtsD31ExtendedLicenseDownChannelFreqUsed OBJECT-TYPE
            SYNTAX Unsigned32
            MAX-ACCESS  read-only
            STATUS  current
            DESCRIPTION
                "
                Used frequencies of the extended license for the downstream channels.
                Unit: Mhz
                "
            ::= { hwCmtsD31LicensePara 6 }

         hwCmtsD31ExtendedLicenseUpChannelLockFlg OBJECT-TYPE
            SYNTAX INTEGER
            {
               locked(1),
               unlocked(2)
            }
            MAX-ACCESS  read-write
            STATUS  current
            DESCRIPTION
                "
                Lock flag of the extended license for the upstream channels.
                Options:
                1. locked(1)   -Indicates that the extended license of the upstream channel is locked
                2. unlocked(2) -Indicates that the extended license of the upstream channel is unlocked
                Default: locked(1)
                "
            ::= { hwCmtsD31LicensePara 7 }

        hwCmtsD31ExtendedLicenseDownChannelLockFlg OBJECT-TYPE
            SYNTAX INTEGER
            {
               locked(1),
               unlocked(2)
            }
            MAX-ACCESS  read-write
            STATUS  current
            DESCRIPTION
                "
                Lock flag of the extended license for the downstream channels.
                Options:
                1. locked(1)   -Indicates that the extended license of the downstream channel is locked
                2. unlocked(2) -Indicates that the extended license of the downstream channel is unlocked
                Default: locked(1)
                "
            ::= { hwCmtsD31LicensePara 8 }

        hwCmtsD31ExtendedLicenseUpChannelFreqLack OBJECT-TYPE
            SYNTAX Unsigned32
            MAX-ACCESS  read-only
            STATUS  current
            DESCRIPTION
                "
                Frequencies of the upstream channel license to be obtained.
                Unit: Mhz
                "
            ::= { hwCmtsD31LicensePara 9 }

        hwCmtsD31ExtendedLicenseDownChannelFreqLack OBJECT-TYPE
            SYNTAX Unsigned32
            MAX-ACCESS  read-only
            STATUS  current
            DESCRIPTION
                "
                Frequencies of the downstream channel license to be obtained.
                Unit: Mhz
                "
            ::= { hwCmtsD31LicensePara 10 }

        hwJumboFrameLicControlObjects OBJECT IDENTIFIER ::= { hwLicense 11 }

        hwJumboFrameLicensePara OBJECT IDENTIFIER ::= { hwJumboFrameLicControlObjects 1 }

        hwJumboFrameLicenseAuth OBJECT-TYPE
            SYNTAX INTEGER
            {
                enable(1),
                disable(2)
            }
            MAX-ACCESS  read-only
            STATUS  current
            DESCRIPTION
                "
                 There are ports using the jumbo frame function on the device.
                 Options:
                 1. enable(1)     -Yes
                 2. disable(2)    -No
                "
            ::= { hwJumboFrameLicensePara 1 }

        hwJumboFrameLicensePortNumber OBJECT-TYPE
            SYNTAX Unsigned32
            MAX-ACCESS  read-only
            STATUS  current
            DESCRIPTION
                "
                Number of ports using the jumbo frame function on the device.
                "
            ::= { hwJumboFrameLicensePara 2 }


        -- 1.3.6.1.4.1.2011.6.114.12
        hwClockLicControlObjects OBJECT IDENTIFIER ::= { hwLicense 12 }


        -- 1.3.6.1.4.1.2011.6.114.12.1
        hwClockLicensePara OBJECT IDENTIFIER ::= { hwClockLicControlObjects 1 }


        -- 1.3.6.1.4.1.2011.6.114.12.1.1
        hwClockLicenseEth OBJECT-TYPE
            SYNTAX INTEGER
                {
                enable(1),
                disable(2)
                }
            MAX-ACCESS read-only
            STATUS current
            DESCRIPTION
                "
                There are ports using the synchronizing ethernet clock function on the device.
                Options:
                1. enable(1)     -Yes
                2. disable(2)    -No
                "
            ::= { hwClockLicensePara 1 }


        -- 1.3.6.1.4.1.2011.6.114.12.1.2
        hwClockLicense1588v2 OBJECT-TYPE
            SYNTAX INTEGER
                {
                enable(1),
                disable(2)
                }
            MAX-ACCESS read-only
            STATUS current
            DESCRIPTION
                "
                The switch state of 1588v2 function on the device.
                Options:
                1. enable(1)     -Yes
                2. disable(2)    -No
                "
            ::= { hwClockLicensePara 2 }

    -- 1.3.6.1.4.1.2011.6.114.13
    hwXdslVectoringLicControlObjects OBJECT IDENTIFIER ::= { hwLicense 13 }


    -- 1.3.6.1.4.1.2011.6.114.13.1
    hwXdslVectoringLicGlobalPara OBJECT IDENTIFIER ::= { hwXdslVectoringLicControlObjects 1 }


    -- 1.3.6.1.4.1.2011.6.114.13.1.1
    hwXdslVectoringLicAuth OBJECT-TYPE
        SYNTAX INTEGER
            {
            enable(1),
            disable(2)
            }
        MAX-ACCESS read-write
        STATUS current
        DESCRIPTION
            "
            The switch of xdsl vectoring license auth.
            Options:
            1. enable(1)     -The number of xdsl vectoring ports reach or exceed the license, and xdsl vectoring is not allowed to enable.
            2. disable(2)    -The number of xdsl vectoring ports has not reached the license, and xdsl vectoring is allowed to enable.
            Default: disable(2)
            "
        ::= { hwXdslVectoringLicGlobalPara 1 }


    -- 1.3.6.1.4.1.2011.6.114.13.1.2
    hwXdslVectoringPortNum OBJECT-TYPE
        SYNTAX Unsigned32
                MAX-ACCESS  read-only
                STATUS  current
                DESCRIPTION
                        "
                        The number of xdsl vectoring ports.
                        "
        ::= { hwXdslVectoringLicGlobalPara 2 }


    -- 1.3.6.1.4.1.2011.6.114.14
    hw40GTo80GLicControlObjects OBJECT IDENTIFIER ::= { hwLicense 14 }

    -- 1.3.6.1.4.1.2011.6.114.14.1
    hw40GTo80GLicGlobalPara OBJECT IDENTIFIER ::= { hw40GTo80GLicControlObjects 1 }

    -- 1.3.6.1.4.1.2011.6.114.14.1.1
    hw40GTo80GLicAuth OBJECT-TYPE
        SYNTAX INTEGER
            {
            enable(1),
            disable(2)
            }
        MAX-ACCESS read-write
        STATUS current
        DESCRIPTION
            "
            The switch of authorizing bandwidth mode switching from 40G to 80G.
            Options:
            1. enable(1)  - indicates that the authorization is obtained and the function can be used.
            2. disable(2) - indicates that the authorization is not obtained and the function cannot be used.
            Default: disable(2)
            "
        ::= { hw40GTo80GLicGlobalPara 1 }

    -- 1.3.6.1.4.1.2011.6.114.14.1.2
    hw40GTo80GUseNum OBJECT-TYPE
        SYNTAX Unsigned32
        MAX-ACCESS  read-only
        STATUS  current
        DESCRIPTION
            "
            The number of operations for bandwidth mode switching from 40G to 80G.
            "
        ::= { hw40GTo80GLicGlobalPara 2 }

    -- 1.3.6.1.4.1.2011.6.114.15
    hw80GTo160GLicControlObjects OBJECT IDENTIFIER ::= { hwLicense 15 }

    -- 1.3.6.1.4.1.2011.6.114.15.1
    hw80GTo160GLicGlobalPara OBJECT IDENTIFIER ::= { hw80GTo160GLicControlObjects 1 }

    -- 1.3.6.1.4.1.2011.6.114.15.1.1
    hw80GTo160GLicAuth OBJECT-TYPE
        SYNTAX INTEGER
            {
            enable(1),
            disable(2)
            }
        MAX-ACCESS read-write
        STATUS current
        DESCRIPTION
            "
            The switch of authorizing bandwidth mode switching from 80G to 160G.
            Options:
            1. enable(1)  - indicates that the authorization is obtained and the function can be used.
            2. disable(2) - indicates that the authorization is not obtained and the function cannot be used.
            Default: disable(2)
            "
        ::= { hw80GTo160GLicGlobalPara 1 }

    -- 1.3.6.1.4.1.2011.6.114.15.1.2
    hw80GTo160GUseNum OBJECT-TYPE
        SYNTAX Unsigned32
        MAX-ACCESS  read-only
        STATUS  current
        DESCRIPTION
            "
            The number of operations for bandwidth mode switching from 80G to 160G.
            "
        ::= { hw80GTo160GLicGlobalPara 2 }

    -- 1.3.6.1.4.1.2011.6.114.16
    hwMplsLicControlObjects OBJECT IDENTIFIER ::= { hwLicense 16 }


    -- 1.3.6.1.4.1.2011.6.114.16.1
    hwMplsLicGlobalPara OBJECT IDENTIFIER ::= { hwMplsLicControlObjects 1 }


    -- 1.3.6.1.4.1.2011.6.114.16.1.1
    hwMplsLicAuth OBJECT-TYPE
        SYNTAX INTEGER
            {
            enable(1),
            disable(2)
            }
        MAX-ACCESS read-write
        STATUS current
        DESCRIPTION
            "
             Used to control whether the Mpls function can be enabled for users.
             If it is set to enable, the Mpls function can be enabled for users.
             Otherwise, the mpls function cannot be enabled for users.
             Options:
             1. enable(1)     -Enable Mpls license switch
             2. disable(2)    -Disable Mpls license switch
             default: enable(1)
            "
        ::= { hwMplsLicGlobalPara 1 }


    -- 1.3.6.1.4.1.2011.6.114.16.1.2
    hwMplsUseNum OBJECT-TYPE
        SYNTAX Unsigned32
                MAX-ACCESS  read-only
                STATUS  current
                DESCRIPTION
                        "
                        The number of operations for Mpls function.
                        "
        ::= { hwMplsLicGlobalPara 2 }

    -- 1.3.6.1.4.1.2011.6.114.17
    hwIgmpLicControlObjects OBJECT IDENTIFIER ::= { hwLicense 17 }


    -- 1.3.6.1.4.1.2011.6.114.17.1
    hwIgmpLicGlobalPara OBJECT IDENTIFIER ::= { hwIgmpLicControlObjects 1 }


    -- 1.3.6.1.4.1.2011.6.114.17.1.1
    hwIgmpLicAuth OBJECT-TYPE
        SYNTAX INTEGER
            {
            enable(1),
            disable(2)
            }
        MAX-ACCESS read-write
        STATUS current
        DESCRIPTION
            "
             Used to control whether the BTV user can be added for users.
             If it is set to enable, the BTV user can be added for users.
             Otherwise, the BTV user cannot be added for users.
             Options:
             1. enable(1)     -Enable BTV license switch
             2. disable(2)    -Disable BTV license switch
             default: enable(1)
            "
        ::= { hwIgmpLicGlobalPara 1 }


    -- 1.3.6.1.4.1.2011.6.114.17.1.2
    hwIgmpUserNum OBJECT-TYPE
        SYNTAX Unsigned32
                MAX-ACCESS  read-only
                STATUS  current
                DESCRIPTION
                        "
                        The number of BTV users have been added by users.
                        "
        ::= { hwIgmpLicGlobalPara 2 }

    -- 1.3.6.1.4.1.2011.6.114.18
    hw50GTo100GLicControlObjects OBJECT IDENTIFIER ::= { hwLicense 18 }

    -- 1.3.6.1.4.1.2011.6.114.18.1
    hw50GTo100GLicGlobalPara OBJECT IDENTIFIER ::= { hw50GTo100GLicControlObjects 1 }

    -- 1.3.6.1.4.1.2011.6.114.18.1.1
    hw50GTo100GLicAuth OBJECT-TYPE
        SYNTAX INTEGER
            {
            enable(1),
            disable(2)
            }
        MAX-ACCESS read-write
        STATUS current
        DESCRIPTION
            "
            The switch of authorizing bandwidth mode switching from 50G to 100G.
            Options:
            1. enable(1)  - indicates that the authorization is obtained and the function can be used.
            2. disable(2) - indicates that the authorization is not obtained and the function cannot be used.
            Default: disable(2)
            "
        ::= { hw50GTo100GLicGlobalPara 1 }

    -- 1.3.6.1.4.1.2011.6.114.18.1.2
    hw50GTo100GUseNum OBJECT-TYPE
        SYNTAX Unsigned32
        MAX-ACCESS  read-only
        STATUS  current
        DESCRIPTION
            "
            The number of operations for bandwidth mode switching from 50G to 100G.
            "
        ::= { hw50GTo100GLicGlobalPara 2 }

    -- 1.3.6.1.4.1.2011.6.114.19
    hw100GTo200GLicControlObjects OBJECT IDENTIFIER ::= { hwLicense 19 }

    -- 1.3.6.1.4.1.2011.6.114.19.1
    hw100GTo200GLicGlobalPara OBJECT IDENTIFIER ::= { hw100GTo200GLicControlObjects 1 }

    -- 1.3.6.1.4.1.2011.6.114.19.1.1
    hw100GTo200GLicAuth OBJECT-TYPE
        SYNTAX INTEGER
            {
            enable(1),
            disable(2)
            }
        MAX-ACCESS read-write
        STATUS current
        DESCRIPTION
            "
            The switch of authorizing bandwidth mode switching from 100G to 200G.
            Options:
            1. enable(1)  - indicates that the authorization is obtained and the function can be used.
            2. disable(2) - indicates that the authorization is not obtained and the function cannot be used.
            Default: disable(2)
            "
        ::= { hw100GTo200GLicGlobalPara 1 }

    -- 1.3.6.1.4.1.2011.6.114.19.1.2
    hw100GTo200GUseNum OBJECT-TYPE
        SYNTAX Unsigned32
        MAX-ACCESS  read-only
        STATUS  current
        DESCRIPTION
            "
            The number of operations for bandwidth mode switching from 100G to 200G.
            "
        ::= { hw100GTo200GLicGlobalPara 2 }

    -- 1.3.6.1.4.1.2011.6.114.20
    hwXponBoardPortLicControlObjects OBJECT IDENTIFIER ::= { hwLicense 20 }

    -- 1.3.6.1.4.1.2011.6.114.20.1
    hwXponBoardPortLicensePara OBJECT IDENTIFIER ::= { hwXponBoardPortLicControlObjects 1 }

    -- 1.3.6.1.4.1.2011.6.114.20.1.1
    hwXponBoardExtra4PortLicenseControl OBJECT-TYPE
        SYNTAX INTEGER
        {
            enableAll(1),
            disableNew(2)
        }
        MAX-ACCESS read-write
        STATUS current
        DESCRIPTION
            "
             Controls whether 8 ports are enabled on the H801GPND board.
             If enableAll is set, the newly added and online H801GPND board allows usage of 8 ports.
             If disableNew is set, the newly added H801GPND board allows usage of only 4 ports. This setting does not affect the online H801GPND board.
             Options:
             1. enableAll(1)      -The newly added and online H801GPND board allows usage of 8 ports.
             2. disableNew(2)     -The newly added H801GPND board allows usage of only 4 ports. This setting does not affect the online H801GPND board.
             default: disableNew(2)
            "
        ::= { hwXponBoardPortLicensePara 1 }

    -- 1.3.6.1.4.1.2011.6.114.20.1.2
    hwXponBoardExtra4PortLicenseUsedNumber OBJECT-TYPE
        SYNTAX Unsigned32
        MAX-ACCESS read-only
        STATUS current
        DESCRIPTION
            "
             Indicates the number of online H801GPND boards that are using 8 ports.
             Note: H801GPND boards that are not online are excluded. This number is provided for the NMS for license consumption determination.
            "
        ::= { hwXponBoardPortLicensePara 2 }

    -- 1.3.6.1.4.1.2011.6.114.20.1.3
    hwXponBoardFlexLvl1PortLicenseControl OBJECT-TYPE
        SYNTAX INTEGER
        {
            enableAll(1),
            disableNew(2)
        }
        MAX-ACCESS read-write
        STATUS current
        DESCRIPTION
            "
             Controls whether port are enabled on the OLT.
		     Options:
			 1. enableAll(1)      -The newly inserted laser allows usage of  GPON.
			 2. disableNew(2)     -The newly inserted optical module's port is not available. This setting does not affect the online pon port.
			 default: disableNew(2)
			 "
        ::= { hwXponBoardPortLicensePara 3 }

    -- 1.3.6.1.4.1.2011.6.114.20.1.4
    hwXponBoardFlexLvl1PortLicenseUseNum OBJECT-TYPE
        SYNTAX Unsigned32
        MAX-ACCESS read-only
        STATUS current
        DESCRIPTION
            "
              Indicates the number of flex2.0 pon ports using Gpon mode.
            "
        ::= { hwXponBoardPortLicensePara 4 }

   	-- 1.3.6.1.4.1.2011.6.114.20.1.5
    hwXponBoardFlexLvl2PortLicenseControl OBJECT-TYPE
        SYNTAX INTEGER
        {
            enableAll(1),
            disableNew(2)
        }
        MAX-ACCESS read-write
        STATUS current
        DESCRIPTION
            "
             Controls whether port are enabled on the OLT.
		     Options:
			 1. enableAll(1)      -The newly inserted laser allows usage of  10G GPON.
			 2. disableNew(2)     -The newly inserted optical module's port is not allows usage of 10G GPON This setting does not affect the online pon port.
			 default: disableNew(2)
			 "
        ::= { hwXponBoardPortLicensePara 5 }

    -- 1.3.6.1.4.1.2011.6.114.20.1.6
    hwXponBoardFlexLvl2PortLicenseUseNum OBJECT-TYPE
        SYNTAX Unsigned32
        MAX-ACCESS read-only
        STATUS current
        DESCRIPTION
            "
              Indicates the number of flex2.0 pon ports using 10G GPON mode.
            "
        ::= { hwXponBoardPortLicensePara 6 }

    -- 1.3.6.1.4.1.2011.6.114.20.1.7
    hwXponBoardFlexLvl3PortLicenseControl OBJECT-TYPE
        SYNTAX INTEGER
        {
            enableAll(1),
            disableNew(2)
        }
        MAX-ACCESS read-write
        STATUS current
        DESCRIPTION
            "
            Controls whether port are enabled on the OLT.
			Options:
			1. enableAll(1)      -The newly inserted laser allows usage of  TWDM PON.
			2. disableNew(2)     -The newly inserted optical module's port is not allows usage of TWDM PON This setting does not affect the online pon port.
			default: disableNew(2)
			"
        ::= { hwXponBoardPortLicensePara 7 }

    -- 1.3.6.1.4.1.2011.6.114.20.1.8
    hwXponBoardFlexLvl3PortLicenseUseNum OBJECT-TYPE
        SYNTAX Unsigned32
        MAX-ACCESS read-only
        STATUS current
        DESCRIPTION
            "
               Indicates the number of flex2.0 pon ports using TWDM PON mode.
            "
        ::= { hwXponBoardPortLicensePara 8 }

    -- 1.3.6.1.4.1.2011.6.114.21
    hwGreLicControlObjects OBJECT IDENTIFIER ::= { hwLicense 21 }

    -- 1.3.6.1.4.1.2011.6.114.21.1
    hwGreLicGlobalPara OBJECT IDENTIFIER ::= { hwGreLicControlObjects 1 }

    -- 1.3.6.1.4.1.2011.6.114.21.1.1
    hwGreLicAuth OBJECT-TYPE
        SYNTAX INTEGER
            {
            enable(1),
            disable(2)
            }
        MAX-ACCESS read-write
        STATUS current
        DESCRIPTION
            "
             Used to control whether the Gre function can be enabled for users.
             If it is set to enable, the Gre function can be enabled for users.
             Otherwise, the Gre function cannot be enabled for users.
             Options:
             1. enable(1)     -Enable Gre license switch
             2. disable(2)    -Disable Gre license switch
             default: disable(2)
            "
        ::= { hwGreLicGlobalPara 1 }

    -- 1.3.6.1.4.1.2011.6.114.21.1.2
    hwGreTunnelUseNum OBJECT-TYPE
        SYNTAX Unsigned32
                MAX-ACCESS  read-only
                STATUS  current
                DESCRIPTION
                        "
                        The number of tunnel for Gre function.
                        "
        ::= { hwGreLicGlobalPara 2 }

    -- 1.3.6.1.4.1.2011.6.114.22
    hwVxlanLicControlObjects OBJECT IDENTIFIER ::= { hwLicense 22 }

    -- 1.3.6.1.4.1.2011.6.114.22.1
    hwVxlanLicGlobalPara OBJECT IDENTIFIER ::= { hwVxlanLicControlObjects 1 }

    -- 1.3.6.1.4.1.2011.6.114.22.1.1
    hwVxlanLicAuth OBJECT-TYPE
        SYNTAX INTEGER
            {
            enable(1),
            disable(2)
            }
        MAX-ACCESS read-write
        STATUS current
        DESCRIPTION
            "
             Used to control whether the Vxlan function can be enabled for users.
             If it is set to enable, the Vxlan function can be enabled for users.
             Otherwise, the Vxlan function cannot be enabled for users.
             Options:
             1. enable(1)     -Enable Vxlan license switch
             2. disable(2)    -Disable Vxlan license switch
             default: disable(2)
            "
        ::= { hwVxlanLicGlobalPara 1 }

    -- 1.3.6.1.4.1.2011.6.114.22.1.2
    hwVxlanUseNum OBJECT-TYPE
        SYNTAX Unsigned32
                MAX-ACCESS  read-only
                STATUS  current
                DESCRIPTION
                        "
                        The number of vni for Vxlan function.
                        "
        ::= { hwVxlanLicGlobalPara 2 }

    -- 1.3.6.1.4.1.2011.6.114.23
    hwTwampLicControlObjects OBJECT IDENTIFIER ::= { hwLicense 23 }

    -- 1.3.6.1.4.1.2011.6.114.23.1
    hwTwampLicGlobalPara OBJECT IDENTIFIER ::= { hwTwampLicControlObjects 1 }

    -- 1.3.6.1.4.1.2011.6.114.23.1.1
    hwTwampLicAuth OBJECT-TYPE
        SYNTAX INTEGER
            {
            enable(1),
            disable(2)
            }
        MAX-ACCESS read-write
        STATUS current
        DESCRIPTION
            "
             Used to control whether the Twamp function can be enabled for users.
             If it is set to enable, the Twamp function can be enabled for users.
             Otherwise, the Twamp function cannot be enabled for users.
             Options:
             1. enable(1)     -Enable Twamp license switch
             2. disable(2)    -Disable Twamp license switch
             default: disable(2)
            "
        ::= { hwTwampLicGlobalPara 1 }

    -- 1.3.6.1.4.1.2011.6.114.23.1.2
    hwTwampUseNum OBJECT-TYPE
        SYNTAX Unsigned32
        MAX-ACCESS  read-only
        STATUS  current
        DESCRIPTION
          "
           The number of operations for Twamp function.
          "
        ::= { hwTwampLicGlobalPara 2 }

    -- 1.3.6.1.4.1.2011.6.114.24
    hwSRv6LicControlObjects OBJECT IDENTIFIER ::= { hwLicense 24 }

    -- 1.3.6.1.4.1.2011.6.114.24.1
    hwSRv6LicGlobalPara OBJECT IDENTIFIER ::= { hwSRv6LicControlObjects 1 }

    -- 1.3.6.1.4.1.2011.6.114.24.1.1
    hwSRv6LicAuth OBJECT-TYPE
        SYNTAX INTEGER
            {
            enable(1),
            disable(2)
            }
        MAX-ACCESS read-write
        STATUS current
        DESCRIPTION
            "
             Used to control whether the SRv6 function can be enabled for users.
             If it is set to enable, the SRv6 function can be enabled for users.
             Otherwise, the SRv6 function cannot be enabled for users.
             Options:
             1. enable(1)     -Enable SRv6 license switch
             2. disable(2)    -Disable SRv6 license switch
             default: disable(2)
            "
        ::= { hwSRv6LicGlobalPara 1 }

    -- 1.3.6.1.4.1.2011.6.114.24.1.2
    hwSRv6UseNum OBJECT-TYPE
        SYNTAX Unsigned32
        MAX-ACCESS  read-only
        STATUS  current
        DESCRIPTION
          "
           The number of operations for SRv6 function.
          "
        ::= { hwSRv6LicGlobalPara 2 }


    -- 1.3.6.1.4.1.2011.6.114.25
    hwEvpnLicControlObjects OBJECT IDENTIFIER ::= { hwLicense 25 }

    -- 1.3.6.1.4.1.2011.6.114.25.1
    hwEvpnLicGlobalPara OBJECT IDENTIFIER ::= { hwEvpnLicControlObjects 1 }

    -- 1.3.6.1.4.1.2011.6.114.25.1.1
    hwEvpnLicAuth OBJECT-TYPE
        SYNTAX INTEGER
            {
            enable(1),
            disable(2)
            }
        MAX-ACCESS read-write
        STATUS current
        DESCRIPTION
            "
             Used to control whether the EVPN function can be enabled for users.
             If it is set to enable, the EVPN function can be enabled for users.
             Otherwise, the EVPN function cannot be enabled for users.
             Options:
             1. enable(1)     -Enable EVPN license switch
             2. disable(2)    -Disable EVPN license switch
             default: disable(2)
            "
        ::= { hwEvpnLicGlobalPara 1 }

    -- 1.3.6.1.4.1.2011.6.114.25.1.2
    hwEvpnUseNum OBJECT-TYPE
        SYNTAX Unsigned32
        MAX-ACCESS  read-only
        STATUS  current
        DESCRIPTION
          "
           The number of operations for EVPN function.
          "
        ::= { hwEvpnLicGlobalPara 2 }

    -- 1.3.6.1.4.1.2011.6.114.26
    hwXdslRtuVectoringLicControlObjects OBJECT IDENTIFIER ::= { hwLicense 26 }


    -- 1.3.6.1.4.1.2011.6.114.26.1
    hwXdslRtuVectoringLicGlobalPara OBJECT IDENTIFIER ::= { hwXdslRtuVectoringLicControlObjects 1 }


    -- 1.3.6.1.4.1.2011.6.114.26.1.1
    hwXdslRtuVectoringLicAuth OBJECT-TYPE
        SYNTAX INTEGER
            {
            enable(1),
            disable(2)
            }
        MAX-ACCESS read-write
        STATUS current
        DESCRIPTION
            "
            The switch of xDSL RTU vectoring license auth.
            Options:
            1. enable(1)     -The number of xDSL RTU vectoring ports reach or exceed the license, and xDSL RTU vectoring is not allowed to enable.
            2. disable(2)    -The number of xDSL RTU vectoring ports has not reached the license, and xDSL RTU vectoring is allowed to enable.
            Default: disable(2)
            "
        ::= { hwXdslRtuVectoringLicGlobalPara 1 }


    -- 1.3.6.1.4.1.2011.6.114.26.1.2
    hwXdslRtuVectoringLicPortNum OBJECT-TYPE
        SYNTAX OCTET STRING (SIZE (0..128))
                MAX-ACCESS  read-only
                STATUS  current
                DESCRIPTION
                        "
                        The number of xDSL RTU vectoring ports.
                        "
        ::= { hwXdslRtuVectoringLicGlobalPara 2 }


    -- 1.3.6.1.4.1.2011.6.114.26.1.3
    hwXdslRtuVectoringLicEsn OBJECT-TYPE
        SYNTAX OCTET STRING (SIZE (0..1024))
                MAX-ACCESS  read-only
                STATUS  current
                DESCRIPTION
                        "
                        The electronic serial number of xDSL RTU vectoring VP board.
                        "
        ::= { hwXdslRtuVectoringLicGlobalPara 3 }


        -- 1.3.6.1.4.1.2011.6.114.27
    hwXdslRtuSuperVectoringLicControlObjects OBJECT IDENTIFIER ::= { hwLicense 27 }


    -- 1.3.6.1.4.1.2011.6.114.27.1
    hwXdslRtuSuperVectoringLicGlobalPara OBJECT IDENTIFIER ::= { hwXdslRtuSuperVectoringLicControlObjects 1 }


    -- 1.3.6.1.4.1.2011.6.114.27.1.1
    hwXdslRtuSuperVectoringLicAuth OBJECT-TYPE
        SYNTAX INTEGER
            {
            enable(1),
            disable(2)
            }
        MAX-ACCESS read-write
        STATUS current
        DESCRIPTION
            "
            The switch of xDSL RTU super vectoring license auth.
            Options:
            1. enable(1)     -The number of xDSL RTU super vectoring ports reach or exceed the license, and xDSL RTU super vectoring is not allowed to enable.
            2. disable(2)    -The number of xDSL RTU super vectoring ports has not reached the license, and xDSL RTU super vectoring is allowed to enable.
            Default: disable(2)
            "
        ::= { hwXdslRtuSuperVectoringLicGlobalPara 1 }


    -- 1.3.6.1.4.1.2011.6.114.27.1.2
    hwXdslRtuSuperVectoringLicPortNum OBJECT-TYPE
        SYNTAX OCTET STRING (SIZE (0..128))
                MAX-ACCESS  read-only
                STATUS  current
                DESCRIPTION
                        "
                        The number of xDSL RTU super vectoring ports.
                        "
        ::= { hwXdslRtuSuperVectoringLicGlobalPara 2 }


    -- 1.3.6.1.4.1.2011.6.114.27.1.3
    hwXdslRtuSuperVectoringLicEsn OBJECT-TYPE
        SYNTAX OCTET STRING (SIZE (0..1024))
                MAX-ACCESS  read-only
                STATUS  current
                DESCRIPTION
                        "
                        The electronic serial number of xDSL RTU super vectoring VP board.
                        "
        ::= { hwXdslRtuSuperVectoringLicGlobalPara 3 }


    -- 1.3.6.1.4.1.2011.6.114.28
    hwOxegServiceAndSubscriberLicenseControlObjects OBJECT IDENTIFIER ::= { hwLicense 28 }


    -- 1.3.6.1.4.1.2011.6.114.28.1
    hwOxegServiceAndSubscriberLicenseGlobalPara OBJECT IDENTIFIER ::= { hwOxegServiceAndSubscriberLicenseControlObjects 1 }


    -- 1.3.6.1.4.1.2011.6.114.28.1.1
    hwOxegPortServicePortNumLicenseAuth OBJECT-TYPE
        SYNTAX INTEGER
            {
            enable(1),
            disable(2)
            }
        MAX-ACCESS read-write
        STATUS current
        DESCRIPTION
            "
            The switch of OXEG board service port license auth.
            Options:
            1. enable(1)     -Enable service port license switch.
            2. disable(2)    -Disable service port license switch.
            Default: disable(2)
            "
        ::= { hwOxegServiceAndSubscriberLicenseGlobalPara 1 }


    -- 1.3.6.1.4.1.2011.6.114.28.1.2
    hwOxegPortServicePortNumLicenseUsedNum OBJECT-TYPE
        SYNTAX Unsigned32
        MAX-ACCESS  read-only
        STATUS  current
        DESCRIPTION
            "
            The service port license number of oxeg port.
            "
        ::= { hwOxegServiceAndSubscriberLicenseGlobalPara 2 }


    -- 1.3.6.1.4.1.2011.6.114.28.1.3
    hwOxegBoardSubscriberNumLicenseAuth OBJECT-TYPE
        SYNTAX INTEGER
            {
            enable(1),
            disable(2)
            }
        MAX-ACCESS read-write
        STATUS current
        DESCRIPTION
            "
            The switch of OXEG board subscriber license auth.
            Options:
            1. enable(1)     -Enable subscriber license switch.
            2. disable(2)    -Disable subscriber license switch.
            Default: disable(2)
            "
        ::= { hwOxegServiceAndSubscriberLicenseGlobalPara 3 }


	-- 1.3.6.1.4.1.2011.6.114.28.1.4
    hwOxegBoardSubscriberNumLicenseUsedNum OBJECT-TYPE
        SYNTAX Unsigned32
        MAX-ACCESS  read-only
        STATUS  current
        DESCRIPTION
            "
            The subscriber license number of oxeg board.
            "
        ::= { hwOxegServiceAndSubscriberLicenseGlobalPara 4 }


    -- 1.3.6.1.4.1.2011.6.114.29
    hwXdslRtuGfastVectoringLicControlObjects OBJECT IDENTIFIER ::= { hwLicense 29 }


    -- 1.3.6.1.4.1.2011.6.114.29.1
    hwXdslRtuGfastVectoringLicGlobalPara OBJECT IDENTIFIER ::= { hwXdslRtuGfastVectoringLicControlObjects 1 }

    -- 1.3.6.1.4.1.2011.6.114.29.1.1
    hwXdslRtuGfastVectoringLicAuth OBJECT-TYPE
        SYNTAX INTEGER
            {
            enable(1),
            disable(2)
            }
        MAX-ACCESS read-write
        STATUS current
        DESCRIPTION
            "
            The switch of xDSL RTU G.fast vectoring license auth.
            Options:
            1. enable(1)     -The number of xDSL RTU G.fast vectoring ports reach or exceed the license, and xDSL RTU G.fast vectoring is not allowed to enable.
            2. disable(2)    -The number of xDSL RTU G.fast vectoring ports has not reached the license, and xDSL RTU G.fast vectoring is allowed to enable.
            Default: disable(2)
            "
        ::= { hwXdslRtuGfastVectoringLicGlobalPara 1 }

    -- 1.3.6.1.4.1.2011.6.114.29.1.2
    hwXdslRtuGfastVectoringLicPortNum OBJECT-TYPE
        SYNTAX OCTET STRING (SIZE (0..128))
                MAX-ACCESS  read-only
                STATUS  current
                DESCRIPTION
                        "
                        The number of xDSL RTU G.fast vectoring ports.
                        "
        ::= { hwXdslRtuGfastVectoringLicGlobalPara 2 }

    -- 1.3.6.1.4.1.2011.6.114.29.1.3
    hwXdslRtuGfastVectoringLicEsn OBJECT-TYPE
        SYNTAX OCTET STRING (SIZE (0..1024))
                MAX-ACCESS  read-only
                STATUS  current
                DESCRIPTION
                        "
                        The electronic serial number of xDSL RTU G.fast vectoring VP board.
                        "
        ::= { hwXdslRtuGfastVectoringLicGlobalPara 3 }

    -- 1.3.6.1.4.1.2011.6.114.30
    hwXdslVectoringProLicControlObjects OBJECT IDENTIFIER ::= { hwLicense 30 }


    -- 1.3.6.1.4.1.2011.6.114.30.1
    hwXdslVectoringProLicGlobalPara OBJECT IDENTIFIER ::= { hwXdslVectoringProLicControlObjects 1 }


    -- 1.3.6.1.4.1.2011.6.114.30.1.1
    hwXdslVectoringProLicAuth OBJECT-TYPE
        SYNTAX INTEGER
            {
            enable(1),
            disable(2)
            }
        MAX-ACCESS read-write
        STATUS current
        DESCRIPTION
            "
            The switch of Vector Pro Enable license auth.
            Options:
            1. enable(1)     -The number of ports supporting Vector Pro reach or exceed the license, and Vector Pro is not allowed to enable.
            2. disable(2)    -The number of ports supporting Vector Pro has not reached the license, and Vector Pro is allowed to enable.
            Default: disable(2)
            "
        ::= { hwXdslVectoringProLicGlobalPara 1 }


    -- 1.3.6.1.4.1.2011.6.114.30.1.2
    hwXdslVectoringProLicPortNum OBJECT-TYPE
        SYNTAX Unsigned32
        MAX-ACCESS  read-only
        STATUS  current
        DESCRIPTION
            "
            The number of ports supporting Vector Pro.
            "
        ::= { hwXdslVectoringProLicGlobalPara 2 }

    -- 1.3.6.1.4.1.2011.6.114.31
    hwXdslVectoringNlvLicControlObjects OBJECT IDENTIFIER ::= { hwLicense 31 }


    -- 1.3.6.1.4.1.2011.6.114.31.1
    hwXdslVectoringNlvLicGlobalPara OBJECT IDENTIFIER ::= { hwXdslVectoringNlvLicControlObjects 1 }


    -- 1.3.6.1.4.1.2011.6.114.31.1.1
    hwXdslVectoringNlvLicAuth OBJECT-TYPE
        SYNTAX INTEGER
            {
            enable(1),
            disable(2)
            }
        MAX-ACCESS read-write
        STATUS current
        DESCRIPTION
            "
            The switch of vectoring NLV license auth.
            Options:
            1. enable(1)     -indicates that the NLV license function is enabled, and the licenses are used up. The system cannot work in NLV vectoring mode.
            2. disable(2)    -indicates that the NLV license function is disabled, and the system can work in NLV vectoring mode.
            Default: disable(2)
            "
        ::= { hwXdslVectoringNlvLicGlobalPara 1 }

    -- 1.3.6.1.4.1.2011.6.114.31.1.2
    hwXdslVectoringNlvLicNum OBJECT-TYPE
        SYNTAX Unsigned32
        MAX-ACCESS read-only
        STATUS current
        DESCRIPTION
            "
            Indicates the number of occupied NLV license resources. If the NLV function is enabled in the system, one NLV license resource is occupied.
            "
        ::= { hwXdslVectoringNlvLicGlobalPara 2 }

	-- 1.3.6.1.4.1.2011.6.114.32
	hwMpleRtuLicControlObjects OBJECT IDENTIFIER ::= { hwLicense 32 }

	-- 1.3.6.1.4.1.2011.6.114.32.1
	hwMpleEnhancementGlobalPara OBJECT IDENTIFIER ::= { hwMpleRtuLicControlObjects 1 }

	-- 1.3.6.1.4.1.2011.6.114.32.1.1
	hwMpleEnhancementLicAuth OBJECT-TYPE
	    SYNTAX INTEGER
	        {
	           enable(1),
	           disable(2)
	           }
	    MAX-ACCESS read-write
	    STATUS current
		DESCRIPTION
		"
		The switch of large capacity license auth.
		Options:
		1. enable(1)
		2. disable(2)
		"
		::= { hwMpleEnhancementGlobalPara 1 }

	-- 1.3.6.1.4.1.2011.6.114.32.1.2
	hwMpleEnhancementUseNum OBJECT-TYPE
	    SYNTAX Gauge32
	    MAX-ACCESS read-only
	    STATUS current
        DESCRIPTION
            "
            The number of boards using middle capacity license
            "
		::= { hwMpleEnhancementGlobalPara 2 }

	-- 1.3.6.1.4.1.2011.6.114.32.1.3
	hwMpleEnhancementESN OBJECT-TYPE
	    SYNTAX OCTET STRING (SIZE (0..4096))
	    MAX-ACCESS read-only
	    STATUS current
	    DESCRIPTION
	        "
			ESN of boards
	        Options:
	        0~4096
	        "
	    ::= { hwMpleEnhancementGlobalPara 3 }

	-- 1.3.6.1.4.1.2011.6.114.32.2
	hwMpleEnhancementPlusGlobalPara OBJECT IDENTIFIER ::= { hwMpleRtuLicControlObjects 2 }

	-- 1.3.6.1.4.1.2011.6.114.32.2.1
	hwMpleEnhancementPlusLicAuth OBJECT-TYPE
	    SYNTAX INTEGER
	        {
            enable(1),
            disable(2)
            }
	    MAX-ACCESS read-write
	    STATUS current
		DESCRIPTION
		"
		The switch of large capacity license auth.
		Options:
		1. enable(1)
		2. disable(2)
		"
		::= { hwMpleEnhancementPlusGlobalPara 1 }

	-- 1.3.6.1.4.1.2011.6.114.32.2.2
	hwMpleEnhancementPlusUseNum OBJECT-TYPE
	    SYNTAX Gauge32
	    MAX-ACCESS read-only
	    STATUS current
		DESCRIPTION
            "
            The number of boards using large capacity license
            "
		::= { hwMpleEnhancementPlusGlobalPara 2 }

	-- 1.3.6.1.4.1.2011.6.114.32.2.3
	hwMpleEnhancementPlusESN OBJECT-TYPE
	    SYNTAX OCTET STRING (SIZE (0..4096))
	    MAX-ACCESS read-only
	    STATUS current
        DESCRIPTION
	        "
	        ESN of boards
			Options:
	        0~4096
	        "
	    ::= { hwMpleEnhancementPlusGlobalPara 3 }
    END

--
-- HUAWEI-LICENSE-MIB.my
--
