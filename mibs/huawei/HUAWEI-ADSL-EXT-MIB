-- ============================================================================
-- Copyright (C) 2012 by  HUAWEI TECHNOLOGIES. All rights reserved.
-- Description:  This MIB is used for defining Huawei's ADSL management MIB objects.
-- Reference:
-- Version: V1.23
-- ============================================================================

    HUAWEI-ADSL-EXT-MIB DEFINITIONS ::= BEGIN
        IMPORTS
             adslLineMib,adslLineConfProfileEntry, adslLineConfProfileName, adslLineEntry,
             adslAturChanEntry, adslAtucChanEntry, adslAtucChanPerfDataEntry,
             adslAturChanPerfDataEntry, adslAtucChanIntervalEntry, adslAturChanIntervalEntry,
             adslTraps, adslAturPhysEntry, adslAtucPhysEntry, adslAtucPerfDataEntry,
             adslAtucIntervalEntry, adslLineAlarmConfProfileEntry, adslAturChanIntervalNumber,
             adslLineAlarmConfProfileName, adslAtucIntervalNumber, adslAturIntervalNumber,adslAtucChanIntervalNumber,
             adslAtucConfRateMode, adslAtucConfTargetSnrMgn, adslAtucConfMaxSnrMgn, adslAtucConfMinSnrMgn,
             adslAtucConfDownshiftSnrMgn, adslAtucConfUpshiftSnrMgn, adslAtucConfMinUpshiftTime,
             adslAtucConfMinDownshiftTime, adslAtucChanConfFastMinTxRate, adslAtucChanConfInterleaveMinTxRate,
             adslAtucChanConfFastMaxTxRate, adslAtucChanConfInterleaveMaxTxRate, adslAtucChanConfMaxInterleaveDelay,
             adslAturConfRateMode, adslAturConfRateChanRatio, adslAturConfTargetSnrMgn, adslAturConfMaxSnrMgn,
             adslAturConfMinSnrMgn, adslAturConfDownshiftSnrMgn, adslAturConfUpshiftSnrMgn, adslAturConfMinUpshiftTime,
             adslAturConfMinDownshiftTime, adslAturChanConfFastMinTxRate, adslAturChanConfInterleaveMinTxRate,
             adslAturChanConfFastMaxTxRate, adslAturChanConfInterleaveMaxTxRate, adslAturChanConfMaxInterleaveDelay,
             adslLineConfProfileRowStatus, adslAtucThresh15MinLofs, adslAtucThresh15MinLoss, adslAtucThresh15MinLols,
             adslAtucThresh15MinLprs, adslAtucThresh15MinESs, adslAtucThreshFastRateUp,
             adslAtucThreshInterleaveRateUp, adslAtucThreshFastRateDown, adslAtucThreshInterleaveRateDown,
             adslAtucInitFailureTrapEnable, adslAturThresh15MinLofs, adslAturThresh15MinLoss,
             adslAturThresh15MinLprs, adslAturThresh15MinESs, adslAturThreshFastRateUp, adslAturThreshInterleaveRateUp,
             adslAturThreshFastRateDown, adslAturThreshInterleaveRateDown, adslLineAlarmConfProfileRowStatus
                 FROM ADSL-LINE-MIB
             ifIndex
                 FROM IF-MIB
             ifType
                 FROM RFC1213-MIB
             hwFrameIndex, hwSlotIndex,hwSubslotIndex,hwPortIndex,hwPortOperStatus,hwPortPrimaryStatus,hwPortSecondaryStatus,
             hwConfigChangeIP
                 FROM HUAWEI-DEVICE-MIB
             hwIasConfigChangeTrapID
                 FROM HWMUSA-DEV-MIB
             Integer32, Unsigned32, Gauge32, Counter32, OBJECT-TYPE, NOTIFICATION-TYPE, MODULE-IDENTITY
                 FROM SNMPv2-SMI
             Adsl2TransmissionModeType, Adsl2PsdMaskDs, Adsl2PsdMaskUs, Adsl2SymbolProtection
                 FROM ADSL2-LINE-TC-MIB
             adslLineExtEntry, adslConfProfileLineType,adslAtucThreshold15MinFailedFastR,
             adslAtucThreshold15MinSesL, adslAtucThreshold15MinUasL, adslAturThreshold15MinSesL,
             adslAturThreshold15MinUasL
                 FROM ADSL-LINE-EXT-MIB
             PerfIntervalCount
                 FROM PerfHist-TC-MIB
             HCPerfIntervalThreshold
                 FROM HC-PerfHist-TC-MIB   -- [RFC3705]
             sysName
                 FROM SNMPv2-MIB
             RowStatus, PhysAddress, TruthValue, DateAndTime,TEXTUAL-CONVENTION
                 FROM SNMPv2-TC
             hwAlarmId, hwAlarmTime, hwAlarmSn, hwCauseId, hwTrapType
                 FROM HUAWEI-TC-MIB
             huaweiUtility
                 FROM HUAWEI-MIB
             HWADSLSYMBOLPROTECTION, HWADSLTRANSMISSIONMODETYPE, HWADSL2ANNEXMSCOPE,
             hwAdsllinePvcVpi, hwAdslLinePvcVci, hwAdslAtucConfDownBitSwap,
             hwAdslAtucConfUpBitSwap, hwAdslTrellionsModeEnable
                 FROM HUAWEI-ADSL-MIB
             hwBTSSAdslDeltTestOperResult
                 FROM HUAWEI-BTEST-MIB;

        hwAdsl MODULE-IDENTITY
            LAST-UPDATED "201306250000Z"
            ORGANIZATION "Huawei Technologies Co.,Ltd."
            CONTACT-INFO
                "Huawei Industrial Base
                Bantian, Longgang
                Shenzhen 518129
                People's Republic of China
                Website: http://www.huawei.com
                Email: support@huawei.com
                "
            DESCRIPTION  "This MIB is used for defining Huawei's ADSL management MIB objects."

	 --  Revision history
	 REVISION     "201306250000Z"
         DESCRIPTION  "V1.23, Add leaf node hwADSLExtLineProfChangeTrap in hwAdslCommonTrapsPrefix."

	 REVISION     "201212270000Z"
         DESCRIPTION  "V1.22, modify the status of the nodes to deprecated:hwXdslDynamicInfoCollectInfoTable.
                       hwAdslAtucConfDownBitSwap, hwAdslAtucConfUpBitSwap, hwAdslTrellionsModeEnable are not defined in ADSL-LINE_MIB, but in HUAWEI-ADSL-MIB"

	 REVISION     "201207010000Z"
         DESCRIPTION  "V1.21, modify the node name from hwdslAtucChanPerfPrev1DayCrcBlksInfo to hwadslAtucChanPerfPrev1DayCrcBlksInfo.
                       Modify the description of the leaf node: HwadslLineAlarmConfProfileCfgEntry, hwadsl2LExtLineProfForceInpUs, hwadsl2LExtLineProfForceInpDs"

	 REVISION     "201205020000Z"
         DESCRIPTION  "V1.20, modify the description of the leaf nodes:hwxdslDynamicProfMaxNomPsdDsCfg, hwxdslDynamicProfMaxNomPsdUsCfg.
                       Add leaf node hwadslAturChanL2NetDataRate, hwadslAtucChanL2NetDataRate"

	 REVISION     "201203200000Z"
         DESCRIPTION  "V1.19, Add the definition of the leaf node hwadsl2MaximumInterleavedDepth.
                       Modify the defination of the trap node hwAdslPortStatReachThresholdAlarmTrap.
                       Add the leaf nodes in table hwAdslTrapsVbOids as follow:hwadslLinePMCurrentValue, hwadslLinePMThresholdValue."

	 REVISION     "201112050000Z"
         DESCRIPTION  "V1.18, add the definition of the leaf node hwAdslLineAlarmConfProfileActiveFailAlarmSwitch,
                       add the definition of the leaf node hwadslLineStatusLineRateDs, hwadslLineStatusLineRateUs.
                       Modify the definition of the trap node hwADSLAlarmProfChangeTrap."

	 REVISION     "201107070000Z"
         DESCRIPTION  "V1.17, modify the description of the leaf nodes:hwadsl2TranMissionStardardMaskCfg, hwadsl2TransMissionAnnexMaskCfg, hwAdslTransmissionModeCfg.
                       modify the unit of the leaf nodes from bps to Kbps:hwadsl2L2ModeMinDataRateCfg, hwadsl2L2ModeMaxDataRateCfg, hwadsl2L2ModePayloadRateThresholdCfg."

         REVISION     "201105100000Z"
         DESCRIPTION  "V1.16, add the definition of the leaf node hwadslLineStatusLastRetrainInfo for getting the last retrained information."

	 REVISION     "201104070000Z"
         DESCRIPTION  "V1.15, add annexA998-D-48, annexA998-D-128, annexB998ADE17-M2x-M in hwxdslDynamicProfClassMaskCfg.
                       modify the description of hwxdslDynamicProfClassMaskCfg."

         REVISION     "201102120000Z"
         DESCRIPTION  "V1.14, Add leaf node hwadsl2LExtLineProfReferenceClock,hwadsl2LExtLineProfL3Time,hwadsl2LExtLineProfRfiBands,
                       hwadsl2LExtLineProfDpboEPsd,hwadsl2LExtLineProfDpboEsEL,hwadsl2LExtLineProfDpboEselMin,hwadsl2LExtLineProfDpboEsCableModelA,
                       hwadsl2LExtLineProfDpboEsCableModelB,hwadsl2LExtLineProfDpboEsCableModelC,hwadsl2LExtLineProfDpboMus,
                       hwadsl2LExtLineProfDpboFMin,hwadsl2LExtLineProfDpboFMax,hwadsl2LExtLineProfMaxNomPsdUs,hwadsl2LExtLineProfMaxNomAtpDs,
                       hwadsl2LExtLineProfMaxNomAtpUs,hwadsl2LExtLineProfInmIatoDs,hwadsl2LExtLineProfInmIatsDs,hwadsl2LExtLineProfInmCcDs,
                       hwadsl2LExtLineProfInmInpeqModeDs, hwadsl2LExtLineProfForceInpDs,hwadsl2LExtLineProfForceInpUs,hwadsl2LExtLineProfInitPolicy,
                       hwadsl2LExtLineProfL3ModeState,hwAdslAturPerfCurr15MLeftrs,hwAdslAturPerfCurr15MEfb,hwAdslAturPerfCurr15MMinEftr,
                       hwAdslAturPerfCurr1DayLeftrs,hwAdslAturPerfCurr1DayEfb,hwAdslAturPerfCurr1DayMinEftr,hwAdslAturPerfPrev1DayLeftrs,
                       hwAdslAturPerfPrev1DayEfb,hwAdslAturPerfPrev1DayMinEftr,hwAdslAturPerfCurrEverBeforeLeftrs,hwAdslAturPerfCurrEverBeforeEfb,
                       hwAdslAturPerfCurrEverBeforeMinEftr,hwAdslAturIntervalLeftrs,hwAdslAturIntervalEfb,hwAdslAturIntervalMinEftr.
                       Modify the description of the leaf node:hwAdslAtucPerfCurr15MLeftrs,hwAdslAtucPerfCurr15MEfb,hwAdslAtucPerfCurr15MMinEftr,
                       hwAdslAtucPerfCurr1DayLeftrs,hwAdslAtucPerfCurr1DayEfb,hwAdslAtucPerfCurr1DayMinEftr,hwAdslAtucPerfPrev1DayLeftrs,
                       hwAdslAtucPerfPrev1DayEfb,hwAdslAtucPerfPrev1DayMinEftr,hwAdslAtucPerfCurrEverBeforeLeftrs,hwAdslAtucPerfCurrEverBeforeEfb,
                       hwAdslAtucPerfCurrEverBeforeMinEftr,hwAdslAtucIntervalLeftrs,hwAdslAtucIntervalEfb,hwAdslAtucIntervalMinEftr.
                       modify the leaf name from hwadslLineAlarmConfProfXtucThresh15MinLeftrs to hwadslLineAlarmConfProfXturThresh15MinLeftrs.
                       modify syntax from annexB997E17-M2x-NUS0 to annexB997E17-M2x-A in hwxdslDynamicProfClassMaskCfg.
                       "

	 REVISION     "201101120000Z"
         DESCRIPTION  "V1.13, Add leaf node hwadslLineStatusInitResult,hwadslLineStatusSigAttenDs,hwadslLineStatusSigAttenUs,hwadslLineStatusActPsdDs,
                       hwadslLineStatusActPsdUs,hwadslAtucChanCurr15MStartTime,hwadslAtucChanCurr1DayStartTime,hwadslAturChanCurr15MStartTime,hwadslAturChanCurr1DayStartTime,
                       hwAdslAturChanIntervalStartTime,hwAdslAtucPerfCurr15MStartTime,hwAdslAtucPerfCurr1DayStartTime,hwAdslAtucPerfCurr15MInmainpeq,hwAdslAtucPerfCurr15MInmame,
                       hwAdslAtucPerfCurr15MInmaiat,hwAdslAtucPerfCurr1DayInmainpeq,hwAdslAtucPerfCurr1DayInmame,hwAdslAtucPerfCurr1DayInmaiat,hwAdslAtucPerfPre1DayInmainpeq,
                       hwAdslAtucPerfPre1DayInmame,hwAdslAtucPerfPre1DayInmaiat,hwAdslAtucPerfCurrEverBeforeInmainpeq,hwAdslAtucPerfCurrEverBeforeInmame,
                       hwAdslAtucPerfCurrEverBeforeInmaiat,hwAdslAtucIntervalStartTime,hwAdslAtucIntervalInmainpeq,hwAdslAtucIntervalInmame,hwAdslAtucIntervalInmaiat,
                       hwAdslAtucChanIntervalStartTime,hwAdslAturPerfCurr15MStartTime,hwAdslAturPerfCurr1DayStartTime,hwAdslAturPerfCurr15MInmainpeq,
                       hwAdslAturPerfCurr15MInmame,hwAdslAturPerfCurr15MInmaiat,hwAdslAturPerfCurr1DayInmainpeq,hwAdslAturPerfCurr1DayInmame,hwAdslAturPerfCurr1DayInmaiat,
                       hwAdslAturPerfPre1DayInmainpeq,hwAdslAturPerfPre1DayInmame,hwAdslAturPerfPre1DayInmaiat,hwAdslAturPerfCurrEverBeforeInmainpeq,
                       hwAdslAturPerfCurrEverBeforeInmame,hwAdslAturPerfCurrEverBeforeInmaiat,hwAdslAturIntervalStartTime,hwAdslAturIntervalInmainpeq,
                       hwAdslAturIntervalInmame,hwAdslAturIntervalInmaiat,hwadslAtucTransmissionCapabilitiesInfo."

	 REVISION     "201012190000Z"
         DESCRIPTION  "V1.12, Add leaf node hwadslAtucChanActNetDataRate,hwadslAtucChanActINPAgainstREIN,hwadslLineExtConfProfRtxModeDs,hwadslLineExtConfProfLeftrThreshDs,
                       hwadslLineExtConfProfMinEtrRtxDs,hwadslLineExtConfProfMaxEtrRtxDs,hwadslLineExtConfProfMaxNdrRtxDs,hwadslLineExtConfProfMaxDelayRtxDs,
                       hwadslLineExtConfProfMinDelayRtxDs,hwadslLineExtConfProfMinInpShineRtxDs,hwadslLineExtConfProfShineRatioRtxDs,hwadslLineExtConfProfMinInpReinRtxDs,
                       hwadslLineExtConfProfIatReinRtxDs,hwadslLineStatusRtxUsedDs,hwadslLineAlarmConfProfXtucThresh15MinLeftrs,hwAdslAtucPerfCurr15MLeftrs,
                       hwAdslAtucPerfCurr15MEfb,hwAdslAtucPerfCurr15MMinEftr,hwAdslAtucPerfCurr1DayLeftrs,hwAdslAtucPerfCurr1DayEfb,hwAdslAtucPerfCurr1DayMinEftr,
                       hwAdslAtucPerfPrev1DayLeftrs,hwAdslAtucPerfPrev1DayEfb,hwAdslAtucPerfPrev1DayMinEftr,hwAdslAtucPerfCurrEverBeforeLeftrs,hwAdslAtucPerfCurrEverBeforeEfb,
                       hwAdslAtucPerfCurrEverBeforeMinEftr,hwAdslAtucIntervalLeftrs,hwAdslAtucIntervalEfb,hwAdslAtucIntervalMinEftr for G.998.4 retransmission function."

	 REVISION     "201010140000Z"
         DESCRIPTION  "V1.11, Add leaf node hwXdslDynamicInfoCollectPortList in table hwXdslDynamicInfoCollectInfoTable for collecting dynamic info with port list."

	 REVISION     "201009280000Z"
         DESCRIPTION  "V1.10, Modify the output string length range of hwadslAturInvG994VendorId and hwadslAtucInvG994VendorId nodes."

	 REVISION     "201009260000Z"
         DESCRIPTION  "V1.09, Add invalid value: hwXdslPortIopCaptureOperTypeCfg, hwXdslPortIopCaptureOperStatusInfo, hwXdslDynamicInfoCollectInfo.
                              modify the description of the whole MIB file."

	 REVISION     "201009070000Z"
         DESCRIPTION  "V1.08, Modify the OBJECTS list of node hwadslAturPhysInfoTable.
                              Add the definition of the node: hwadslAturInvG994VendorId, hwadslAturLInvSelfTestResult.
                              Add leaf node hwadslAturInvG994VendorId and hwadslAturLInvSelfTestResult in table hwadslAturPhysInfoTable.
                              Modify the OBJECTS list of node hwadslAtucPhysInfoTable.
                              Add the definition of the node: hwadslAtucInvG994VendorId, hwadslAtucLInvSelfTestResult.
                              Add leaf node hwadslAtucInvG994VendorId and hwadslAtucLInvSelfTestResult in table hwadslAtucPhysInfoTable.
                              Modify the OBJECTS list of node hwadslAtucPerfDataInfoTable.
                              Add the definition of the node: hwAdslAtucPerfFullInitsInfo, hwAdslAtucPerfCurr15MinFullInitsInfo,
			      hwAdslAtucPerfCurr1DayFullInitsInfo, hwAdslAtucPerfPrev1DayFullInitsInfo.
                              Add leaf node hwAdslAtucPerfFullInitsInfo, hwAdslAtucPerfCurr15MinFullInitsInfo, hwAdslAtucPerfCurr1DayFullInitsInfo,
			      hwAdslAtucPerfPrev1DayFullInitsInfo. in table hwadslAtucPerfDataInfoTable.
                              Modify the name of the node: hwAdslAtucPerfFailFullInitsInfo, hwAdslAtucPerfCurr15MinFailFullInitsInfo,
			      hwAdslAtucPerfCurr1DayFailFullInitsInfo, hwAdslAtucPerfPrev1DayFailFullInitsInfo for trap optimization.
                             "

	 REVISION     "201008140000Z"
         DESCRIPTION  "V1.07, Modify the name of the node hwAdslChipsetNotAvailbaleAlarmTrap.The new name is
                              hwAdslChipsetNotAvailableAlarmTrap."

	 REVISION     "201007190900Z"
         DESCRIPTION  "V1.06, Modify the OBJECTS list of node hwADSLLineProfChangeTrap.
                              Add the definition of the trap node: hwADSLLineProfChangeTrap, hwADSLAlarmProfChangeTrap.
                              Add leaf node hwADSLProfOperType in table hwAdslTrapsVbOids.
                              Modify the definition of the trap node: hwAdslDeltOperResultInfoTrap for trap optimization.
                              The description of hwXdslPortPowerStateCfg is changed and enumerated value l1(4) is added."

	 REVISION     "201006220000Z"
         DESCRIPTION  "V1.05, Modify chinese character."

	 REVISION     "201005200000Z"
         DESCRIPTION  "V1.04, Modify the OBJECTS list of node hwAdslPortActRateLowerThresholdAlarmTrap.
                              Add the definition of the trap node: hwAdslSeltStartResultTrap.
                              Add leaf nodes hwAdslRequestID, hwadslSeltTestStartResult in table hwAdslTrapsVbOids.
                              Modify the definition of the trap node hwAdslPortStatusChangeInfoTrap."

	 REVISION     "201003220000Z"
         DESCRIPTION  "V1.03, Modify the SYNTAX string.
                              Add invalid value.
                              Modify the description."

	 REVISION     "201002080000Z"
         DESCRIPTION  "V1.02, modify the description of the leaf node,
                              and delete the parameter hwPortDesc of the alarm trap."

	 REVISION     "201001120000Z"
         DESCRIPTION  "V1.01, add the definition of the trap node.
                              Change the data type of nodes hwXdslPortLastUpTimeCfg, hwXdslPortLastDownTimeCfg,
                              and hwXdslPortRetrainCntCfg from PortDateAndTime to DateAndTime."

         REVISION     "200208220000Z"
         DESCRIPTION  "V1.00, initial version."

	     	::= { huaweiUtility 31 }

-- hwAdslMibObjects

    hwAdslMibObjects OBJECT IDENTIFIER ::= { hwAdsl 1}

-- hwadslAturChanInfoTable

    hwadslAturChanInfoTable OBJECT-TYPE
        SYNTAX  SEQUENCE OF HwadslAturChanInfoEntry
        MAX-ACCESS  not-accessible
        STATUS  current
        DESCRIPTION
                   "This table provides the channel parameters of the ATUR end of each port.
                    The index of this table is ifIndex.
                   "
        ::= { hwAdslMibObjects 1 }

    hwadslAturChanInfoEntry OBJECT-TYPE
        SYNTAX  HwadslAturChanInfoEntry
        MAX-ACCESS  not-accessible
        STATUS  current
        DESCRIPTION
                   "This table provides the channel parameters of the ATUR end of each port.
                    The index of this entry is ifIndex.
                   "
        INDEX { ifIndex }
        ::= { hwadslAturChanInfoTable 1 }

    HwadslAturChanInfoEntry ::=
        SEQUENCE {
                     hwadslAturChanCurrINPInfo                 Gauge32,
                     hwadslAturChanRsSymbolsInfo               Gauge32,
                     hwadslAturChanRsRedundancyInfo            Gauge32,
                     hwadslAturChanRsDepthInfo                 Gauge32,
                     hwadslAturChanSymbolLengthInfo            Gauge32,
                     hwadslAturChanPhyRrrcBitsInfo             Gauge32,
                     hwadslAturChanPhyRtxQueueInfo             Gauge32,
                     hwadslAturChanRsSizeInfo                  Gauge32,
                     hwadslAturChanCodeGainInfo                Gauge32,
                     hwadslAturChanL2NetDataRate               Gauge32
                 }

    hwadslAturChanCurrINPInfo OBJECT-TYPE
        SYNTAX      Gauge32
        UNITS       "DMT Symbol"
        MAX-ACCESS  read-only
        STATUS      current
        DESCRIPTION
                   "Indicates Impulse Noise Protection on upstream direction.
                    The value multiply 1/10000 is the real value.
                    Unit: DMT Symbol
                   "
        ::= { hwadslAturChanInfoEntry 1 }

    hwadslAturChanRsSymbolsInfo OBJECT-TYPE
        SYNTAX      Gauge32
        UNITS        "byte"
        MAX-ACCESS  read-only
        STATUS      current
        DESCRIPTION
                   "Indicates Reed-Solomon symbols on upstream direction.
                    The value multiply 1/10000 is the real value.
                    Unit: byte
                   "
        ::= { hwadslAturChanInfoEntry 2 }

    hwadslAturChanRsRedundancyInfo OBJECT-TYPE
        SYNTAX      Gauge32
        UNITS        "byte"
        MAX-ACCESS  read-only
        STATUS      current
        DESCRIPTION
                   "Indicates Reed-Solomon redundancy on upstream direction.
                    Unit: byte
                   "
        ::= { hwadslAturChanInfoEntry 3 }

    hwadslAturChanRsDepthInfo OBJECT-TYPE
        SYNTAX      Gauge32
        UNITS        "byte"
        MAX-ACCESS  read-only
        STATUS      current
        DESCRIPTION
                   "Indicates Reed-Solomon depth on upstream direction.
                    Unit: byte
                   "
        ::= { hwadslAturChanInfoEntry 4 }

    hwadslAturChanSymbolLengthInfo OBJECT-TYPE
        SYNTAX      Gauge32
        UNITS        "bit"
        MAX-ACCESS  read-only
        STATUS      current
        DESCRIPTION
                   "Indicates the Bit Number of the DMT Symbol on upstream direction.
                    Unit: bit
                   "
        ::= { hwadslAturChanInfoEntry 5 }

    hwadslAturChanPhyRrrcBitsInfo OBJECT-TYPE
        SYNTAX      Gauge32
        MAX-ACCESS  read-only
        STATUS      current
        DESCRIPTION
                   "The bits in the channel that used to retransmission on upstream direction."
        ::= { hwadslAturChanInfoEntry 6 }

    hwadslAturChanPhyRtxQueueInfo OBJECT-TYPE
        SYNTAX      Gauge32
        MAX-ACCESS  read-only
        STATUS      current
        DESCRIPTION
                   "Queues in send buffer on upstream direction."
        ::= { hwadslAturChanInfoEntry 7 }

    hwadslAturChanRsSizeInfo OBJECT-TYPE
        SYNTAX      Gauge32
        UNITS        "byte"
        MAX-ACCESS  read-only
        STATUS      current
        DESCRIPTION
                   "Indicates Reed-Solomon Codeword Size on upstream direction.
                    Range: 0-255
                    Unit: byte
                   "
        ::= { hwadslAturChanInfoEntry 8 }

    hwadslAturChanCodeGainInfo OBJECT-TYPE
        SYNTAX      Gauge32
        MAX-ACCESS  read-only
        STATUS      current
        DESCRIPTION
                   "Indicates Code Gain on upstream direction.
                    It ranges from 0 to 16 units of 0.5 dB (physical values are 0 to 8 dB).
                   "
        ::= { hwadslAturChanInfoEntry 9 }

    hwadslAturChanL2NetDataRate OBJECT-TYPE
        SYNTAX      Gauge32
        MAX-ACCESS  read-only
        STATUS      current
        DESCRIPTION
                   "In L2 state, this parameter reports the Net Data Rate in low power state.
 	            The data rate is coded in steps of 1000 bit/s.
                   "
        ::= { hwadslAturChanInfoEntry 10}

-- hwadslAturPhysInfoTable
    hwadslAturPhysInfoTable OBJECT-TYPE
        SYNTAX  SEQUENCE OF HwadslAturPhysInfoEntry
        MAX-ACCESS  not-accessible
        STATUS  current
        DESCRIPTION
                   "This object provides the physical layer parameters of each ATUR.
                    The index of this table is ifIndex.
                   "
        ::= { hwAdslMibObjects 2 }

    hwadslAturPhysInfoEntry OBJECT-TYPE
        SYNTAX  HwadslAturPhysInfoEntry
        MAX-ACCESS  not-accessible
        STATUS  current
        DESCRIPTION
                   "This object provides the physical layer parameters of each ATUR.
                    The index of this entry is ifIndex.
                   "
        INDEX { ifIndex }
        ::= { hwadslAturPhysInfoTable 1 }

    HwadslAturPhysInfoEntry ::=
        SEQUENCE {
                     hwadslAturTransmissionCapabilitiesInfo    Adsl2TransmissionModeType,
                     hwAdslAturCurrSignalAtnInfo               Gauge32,
                     hwadslAturInvG994VendorId                 OCTET STRING,
                     hwadslAturLInvSelfTestResult              Unsigned32
                 }

    hwadslAturTransmissionCapabilitiesInfo OBJECT-TYPE
        SYNTAX      Adsl2TransmissionModeType
        MAX-ACCESS  read-only
        STATUS      current
        DESCRIPTION
                   "The ATU transmission system capability list of the different
                    coding types. It is coded in a bit-map representation with 1
                    or more bits set. A bit set to '1' means that the ATU
                    supports the respective coding. The value may be derived
                    from the handshaking procedures defined in G.994.1.
                   "
        ::= { hwadslAturPhysInfoEntry 1 }

    hwAdslAturCurrSignalAtnInfo OBJECT-TYPE
        SYNTAX Gauge32 (0..630)
        UNITS "tenth dB"
        MAX-ACCESS read-only
        STATUS current
        DESCRIPTION
                   "The signal attenuation value on ATUR: It indicates the difference between the transmit signal of the ATU-C and the receive signal of the ATU-R.
                    Range: 0-630
                    Unit: tenth dB
                   "
        ::= { hwadslAturPhysInfoEntry 2 }

    hwadslAturInvG994VendorId  OBJECT-TYPE
        SYNTAX      OCTET STRING  (SIZE (0..16))
        MAX-ACCESS  read-only
        STATUS      current
        DESCRIPTION
           "The ATU G.994.1 Vendor ID as inserted in the G.994.1 CL/CLR
            message.  It consists of 8 binary octets, including a country
            code followed by a (regionally allocated) provider code, as
            defined in Recommendation T.35."
        REFERENCE    "ITU-T G.997.1, paragraph 7.4"
        ::= { hwadslAturPhysInfoEntry 3 }

    hwadslAturLInvSelfTestResult  OBJECT-TYPE
      SYNTAX      Unsigned32
      MAX-ACCESS  read-only
      STATUS      current
      DESCRIPTION
         "The ATU self-test result, coded as a 32-bit value.  The
          most significant octet of the result is '0' if the self-test
          passed, and '1' if the self-test failed.  The interpretation
          of the other octets is vendor discretionary."
      REFERENCE    "ITU-T G.997.1, paragraph 7.4"
      ::= { hwadslAturPhysInfoEntry 4 }

-- hwadslAtucChanInfoTable

    hwadslAtucChanInfoTable OBJECT-TYPE
        SYNTAX  SEQUENCE OF HwadslAtucChanInfoEntry
        MAX-ACCESS  not-accessible
        STATUS  current
        DESCRIPTION
                   "This object provides the channel parameters of each ATUC.
                    The index of this table is ifIndex.
                   "
        ::= { hwAdslMibObjects 3 }

    hwadslAtucChanInfoEntry OBJECT-TYPE
        SYNTAX  HwadslAtucChanInfoEntry
        MAX-ACCESS  not-accessible
        STATUS  current
        DESCRIPTION
                   "This object provides the channel parameters of each ATUC.
                    The index of this entry is ifIndex."
        INDEX { ifIndex }
        ::= { hwadslAtucChanInfoTable 1 }

    HwadslAtucChanInfoEntry ::=
        SEQUENCE {
                     hwadslAtucChanCurrINPInfo                 Gauge32,
                     hwadslAtucChanRsSymbolsInfo               Gauge32,
                     hwadslAtucChanRsRedundancyInfo            Gauge32,
                     hwadslAtucChanRsDepthInfo                 Gauge32,
                     hwadslAtucChanSymbolLengthInfo            Gauge32,
                     hwadslAtucChanPhyRrrcBitsInfo             Gauge32,
                     hwadslAtucChanPhyRtxQueueInfo             Gauge32,
                     hwadslAtucChanRsSizeInfo                  Gauge32,
                     hwadslAtucChanCodeGainInfo                Gauge32,
                     hwadslAtucChanPcbInfo                     Gauge32,
                     hwadslAtucChanActNetDataRate              Gauge32,
                     hwadslAtucChanActINPAgainstREIN           Gauge32,
                     hwadslAtucChanL2NetDataRate               Gauge32
                 }

    hwadslAtucChanCurrINPInfo OBJECT-TYPE
        SYNTAX      Gauge32
        UNITS       "DMT Symbol"
        MAX-ACCESS  read-only
        STATUS      current
        DESCRIPTION
                   "Indicates Impulse Noise Protection on downstream direction.
                    The value multiply 1/10000 is the real value.
                    If retransmission is used in a given transmit direction, this parameter reports
                    the actual impulse noise protection (INP) against SHINE (under specific conditions detailed in G.998.4)
                    on the bearer channel in the L0 state.In the L2 state, the parameter contains the INP in the previous L0 state.
                    Unit: DMT Symbol
                   "
        ::= { hwadslAtucChanInfoEntry 1 }

    hwadslAtucChanRsSymbolsInfo OBJECT-TYPE
        SYNTAX      Gauge32
        UNITS        "byte"
        MAX-ACCESS  read-only
        STATUS      current
        DESCRIPTION
                   "Indicates Reed-Solomon symbols on downstream direction.
                    The value multiply 1/10000 is the real value.
                    Unit: byte
                   "
	::= { hwadslAtucChanInfoEntry 2 }

    hwadslAtucChanRsRedundancyInfo OBJECT-TYPE
        SYNTAX      Gauge32
        UNITS        "byte"
        MAX-ACCESS  read-only
        STATUS      current
        DESCRIPTION
                   "Indicates Reed-Solomon redundancy on downstream direction.
                    Unit: byte
                   "
        ::= { hwadslAtucChanInfoEntry 3 }

    hwadslAtucChanRsDepthInfo OBJECT-TYPE
        SYNTAX      Gauge32
        UNITS        "byte"
        MAX-ACCESS  read-only
        STATUS      current
        DESCRIPTION
                   "Indicates Reed-Solomon depth on downstream direction.
                    Unit: byte
                   "
        ::= { hwadslAtucChanInfoEntry 4 }

    hwadslAtucChanSymbolLengthInfo OBJECT-TYPE
        SYNTAX      Gauge32
        UNITS        "bit"
        MAX-ACCESS  read-only
        STATUS      current
        DESCRIPTION
                   "Indicates the Bit Number of the DMT Symbol on downstream direction.
                    Unit: bit
                   "
        ::= { hwadslAtucChanInfoEntry 5 }

    hwadslAtucChanPhyRrrcBitsInfo OBJECT-TYPE
        SYNTAX      Gauge32
        MAX-ACCESS  read-only
        STATUS      current
        DESCRIPTION
                   "The bits in the channel that used to retransmission on downstream direction."
        ::= { hwadslAtucChanInfoEntry 6 }

    hwadslAtucChanPhyRtxQueueInfo OBJECT-TYPE
        SYNTAX      Gauge32
        MAX-ACCESS  read-only
        STATUS      current
        DESCRIPTION
                   "Queues in send buffer on downstream direction."
        ::= { hwadslAtucChanInfoEntry 7 }

    hwadslAtucChanRsSizeInfo OBJECT-TYPE
        SYNTAX      Gauge32
        UNITS        "byte"
        MAX-ACCESS  read-only
        STATUS      current
        DESCRIPTION
                   "Indicates Reed-Solomon Codeword Size on downstream direction.
                    Range: 0-255
                    Unit: byte
                   "
        ::= { hwadslAtucChanInfoEntry 8 }

    hwadslAtucChanCodeGainInfo OBJECT-TYPE
        SYNTAX      Gauge32
        MAX-ACCESS  read-only
        STATUS      current
        DESCRIPTION
                   "Indicates Code Gain on downstream direction.
                    It ranges from 0 to 16 units of 0.5 dB (physical values are 0 to 8 dB).
                   "
        ::= { hwadslAtucChanInfoEntry 9 }

    hwadslAtucChanPcbInfo OBJECT-TYPE
        SYNTAX      Gauge32
        UNITS        "tenth dB"
        MAX-ACCESS  read-only
        STATUS      current
        DESCRIPTION
	           "Indicates Power Cut-back on downstream direction.
	            It ranges from 0 to 400 units of 0.1 dB (physical values are 0 to 40 dB)
	            Unit: tenth dB
	           "
        ::= { hwadslAtucChanInfoEntry 10 }

    hwadslAtucChanActNetDataRate OBJECT-TYPE
        SYNTAX      Gauge32
        UNITS       "bits/second"
        MAX-ACCESS  read-only
        STATUS      current
        DESCRIPTION
	           "Independent whether retransmission is used or not in a given transmit direction:
                    In L0 state, this parameter reports the Net Data Rate (as specified in G.992.3, G.992.5 or G.993.2)
                    at which the bearer channel is operating. In L2 state, the parameter contains the Net Data
                    Rate (as specified in G.992.3, G.992.5 or G.993.2) in the previous L0 state.
                    The data rate is coded in steps of 1000 bit/s.
	           "
	    REFERENCE    "ITU-T G.997.1, paragraph 7.5.2.8"
        ::= { hwadslAtucChanInfoEntry 11 }

	hwadslAtucChanActINPAgainstREIN OBJECT-TYPE
        SYNTAX      Gauge32
        MAX-ACCESS  read-only
        STATUS      current
        DESCRIPTION
	           "If retransmission is used in a given transmit direction,
	            this parameter reports the actual impulse noise protection (INP) against
	            REIN (under specific conditions detailed in G.998.4) on the bearer channel
	            in the L0 state. In the L2 state, the parameter contains the INP in the previous L0 state.
	            The value is coded in fractions of DMT symbols with a granularity of 0.1 symbols.
	           "
	    REFERENCE    "ITU-T G.997.1, paragraph 7.5.2.9"
        ::= { hwadslAtucChanInfoEntry 12 }

     hwadslAtucChanL2NetDataRate OBJECT-TYPE
        SYNTAX      Gauge32
        MAX-ACCESS  read-only
        STATUS      current
        DESCRIPTION
                   "In L2 state, this parameter reports the Net Data Rate in low power state.
 	            The data rate is coded in steps of 1000 bit/s.
                   "
        ::= { hwadslAtucChanInfoEntry 13}

-- hwadslLineConfProfileCfgTable

    hwadslLineConfProfileCfgTable OBJECT-TYPE
        SYNTAX  SEQUENCE OF HwadslLineConfProfileCfgEntry
        MAX-ACCESS  not-accessible
        STATUS  current
        DESCRIPTION
                   "This table contains information on the ADSL line configuration.
                    The index of this table is adslLineConfProfileName.
                   "
        ::= { hwAdslMibObjects 4 }

    hwadslLineConfProfileCfgEntry OBJECT-TYPE
        SYNTAX  HwadslLineConfProfileCfgEntry
        MAX-ACCESS  not-accessible
        STATUS  current
        DESCRIPTION
                   "This table contains information on the ADSL line configuration.
                    The index of this entry is adslLineConfProfileName.
                   "
        INDEX { adslLineConfProfileName }
        ::= { hwadslLineConfProfileCfgTable 1 }

    HwadslLineConfProfileCfgEntry ::=
        SEQUENCE {
                     hwAdslAtucConfDownBitSwapCfg                 INTEGER,
                     hwAdslAtucConfUpBitSwapCfg                   INTEGER,
                     hwAdslTrellionsModeEnableCfg                 INTEGER,
                     hwAdslTransmissionModeCfg                    INTEGER
                 }

    hwAdslAtucConfDownBitSwapCfg OBJECT-TYPE
        SYNTAX INTEGER {
                           enabled(1),
                           disabled(2)
                       }
        MAX-ACCESS read-create
        STATUS current
        DESCRIPTION
                   "Enables and disables the down bitswap of a template.
                    Options:
                    1. enabled(1)  - Indicates that the downstream bit swap is enabled
                    2. disabled(2) - Indicates that the downstream bit swap is disabled
                    Default: enabled(1)
                   "
        ::= { hwadslLineConfProfileCfgEntry 1 }

    hwAdslAtucConfUpBitSwapCfg OBJECT-TYPE
        SYNTAX INTEGER {
                           enabled(1),
                           disabled(2)
                       }
        MAX-ACCESS read-create
        STATUS current
        DESCRIPTION
                   "Enables and disables the up bitswap of a template.
                    Options:
                    1. enabled(1)  - Indicates that the upstream bit swap is enabled
                    2. disabled(2) - Indicates that the upstream bit swap is disabled
                    Default: enabled(1)
                   "
        ::= { hwadslLineConfProfileCfgEntry 2 }

    hwAdslTrellionsModeEnableCfg OBJECT-TYPE
        SYNTAX INTEGER {
                           enabled(1),
                           disabled(2)
                       }
        MAX-ACCESS read-create
        STATUS current
        DESCRIPTION
                   "Enables and disables the Trellions mode.
                    Options:
                    1. enabled(1)  - Indicates that the trellis coding is enabled.
                    2. disabled(2) - Indicates that the trellis coding is disabled.
                    Default: enabled(1)
                   "
        ::= { hwadslLineConfProfileCfgEntry 3 }

    hwAdslTransmissionModeCfg OBJECT-TYPE
        SYNTAX INTEGER {
                           all(1),
                           fullRate(2),
                           gliteOnly(3),
                           t1413Only(4),
                           gdmtOnly(5),
                           ghs(6),
                           g992Dot1(7),
                           g992Dot2(8),
                           g992Dot3(9),
                           g992Dot4(10),
                           g992Dot5(11),
                           adslAllOnly(12),
                           adslAndAdsl2(13)
                       }
        MAX-ACCESS read-create
        STATUS current
        DESCRIPTION
                   "Indicates the transmission mode of this channel.
                    Options:
                    1. all(1)            - All (G992.1, G992.2, T1.413)(Default)
                    2. fullRate(2)       - Full rate(G992.1 or T1.413)
                    3. gliteOnly(3)      - G992.2(g.lite) only
                    4. t1413Only(4)      - T1.413 only
                    5. gdmtOnly(5)       - G992.1,G992.3,G992.5,(g.dmt) only
                    6. ghs(6)            - g.hs (G992.1,G992.2,G992.3,G992.4,G992.5,G992.5 is prior)
                    7. g992Dot1(7)       - G992.1
                    8. g992Dot2(8)       - G992.2
                    9. g992Dot3(9)       - G992.3
                    10. g992Dot4(10)     - G992.4
                    11. g992Dot5(11)     - G992.5
                    12. adslAllOnly(12)  - ADSL ALL ONLY
                    13. adslAndAdsl2(13) - G.992.1,G.992.3,T1.413(Not support)
                    Default: all(1)
                   "
        ::= { hwadslLineConfProfileCfgEntry 4 }

-- hwAdslLinePvcCfgTable

    hwAdslLinePvcCfgTable OBJECT-TYPE
        SYNTAX SEQUENCE OF HwAdslLinePvcCfgEntry
        MAX-ACCESS not-accessible
        STATUS current
        DESCRIPTION
                   "PVC configuration table of the ADSL port.
                    The indexes of this table are ifIndex,hwAdsllinePvcVpi,and hwAdsllinePvcVci.
                   "
        ::= { hwAdslMibObjects 5 }

    hwAdslLinePvcCfgEntry OBJECT-TYPE
        SYNTAX HwAdslLinePvcCfgEntry
        MAX-ACCESS not-accessible
        STATUS current
        DESCRIPTION
                   "PVC configuration table of the ADSL port.
                    The indexes of this entry are ifIndex,hwAdsllinePvcVpi,and hwAdsllinePvcVci.
                   "
        INDEX { ifIndex, hwAdsllinePvcVpi, hwAdslLinePvcVci }
        ::= { hwAdslLinePvcCfgTable 1 }

    HwAdslLinePvcCfgEntry ::=
        SEQUENCE {
                     hwAdslLinePvcVlanIdCfg           Integer32,
                     hwAdslLinePvcPriorityCfg         Integer32,
                     hwAdslLinePvcDsBandCfg           Integer32,
                     hwAdslLinePvcUsBandCfg           Integer32,
                     hwAdslLinePvcMCastEnableCfg      INTEGER,
                     hwAdslLinePvcIGMPEnableCfg       INTEGER,
                     hwAdslLinePvcIndexCfg            Integer32,
                     hwAdslLinePvcConnectTypeCfg      INTEGER,
                     hwAdslLinePvcRowStatusCfg        RowStatus
                 }

    hwAdslLinePvcVlanIdCfg OBJECT-TYPE
        SYNTAX Integer32 (1..4000)
        MAX-ACCESS read-write
        STATUS current
        DESCRIPTION
                   "The VLAN ID of the adsl line PVC.
                    Range: 1-4000
                   "
        ::= { hwAdslLinePvcCfgEntry 3 }

    hwAdslLinePvcPriorityCfg OBJECT-TYPE
        SYNTAX Integer32 (0..7)
        MAX-ACCESS read-write
        STATUS current
        DESCRIPTION
                   "The Priority value of the adsl line PVC.
                    Range: 0-7
                    Default: 0
                   "
        DEFVAL { 0 }
        ::= { hwAdslLinePvcCfgEntry 4 }

    hwAdslLinePvcDsBandCfg OBJECT-TYPE
        SYNTAX Integer32 (0..450)
        MAX-ACCESS read-write
        STATUS current
        DESCRIPTION
                   "The down stream band of the adsl line PVC.
                    Range: 0-450
                    Default: 0
                   "
        DEFVAL { 0 }
        ::= { hwAdslLinePvcCfgEntry 5 }

    hwAdslLinePvcUsBandCfg OBJECT-TYPE
        SYNTAX Integer32 (0..450)
        MAX-ACCESS read-write
        STATUS current
        DESCRIPTION
                   "The up stream band of the adsl line PVC.
                    Range: 0-450
                   "
        ::= { hwAdslLinePvcCfgEntry 6 }

    hwAdslLinePvcMCastEnableCfg OBJECT-TYPE
        SYNTAX INTEGER {
                           enable(1),
                           disable(2)
                       }
        MAX-ACCESS read-write
        STATUS current
        DESCRIPTION
                   "This object allows the adsl line PVC to support multicast.
                    Options:
                    1. enable(1)  - Indicates that the PVC of the ADSL port is enabled to support the multicast
                    2. disable(2) - Indicates that the PVC of the ADSL port is disabled to support the multicast
                    Default: disable(2)
                   "
        DEFVAL { disable }
        ::= { hwAdslLinePvcCfgEntry 7 }

    hwAdslLinePvcIGMPEnableCfg OBJECT-TYPE
        SYNTAX INTEGER {
                           enable(1),
                           disable(2)
                       }
        MAX-ACCESS read-write
        STATUS current
        DESCRIPTION
                   "This object allows the adsl line PVC to support IGMP.
                    Options:
                    1. enable(1)  - Indicates that the PVC of the ADSL port is enabled to support IGMP
                    2. disable(2) - Indicates that the PVC of the ADSL port is disabled to support IGMP
                    Default: disable(2)
                   "
        DEFVAL { disable }
        ::= { hwAdslLinePvcCfgEntry 8 }

    hwAdslLinePvcIndexCfg OBJECT-TYPE
        SYNTAX Integer32 (1..8)
        MAX-ACCESS read-write
        STATUS current
        DESCRIPTION
                   "The index of the adsl line PVC.
                    Range: 1-8
                   "
        ::= { hwAdslLinePvcCfgEntry 9 }

    hwAdslLinePvcConnectTypeCfg OBJECT-TYPE
        SYNTAX INTEGER {
                           auto(0),
                           llc1483B(1),
                           pppoaLLC(2),
                           pppoaVcmux(3),
                           ipoaLLc(4),
                           ipoaVcmux(5)
                       }
        MAX-ACCESS read-only
        STATUS current
        DESCRIPTION
                   "The Connected type of the adsl line PVC
                    Options:
                    1. auto(0)     - The Connected type of the adsl line PVC is auto
                    2. llc1483B(1) - The Connected type of the adsl line PVC is llc1483B
                    3. pppoaLLC(2) - The Connected type of the adsl line PVC is pppoaLLC
                    4. pppoaVcmux(3) - The Connected type of the adsl line PVC is pppoaVcmux
                    5. ipoaLLc(4)    - The Connected type of the adsl line PVC is ipoaLLc
                    6. ipoaVcmux(5)  - The Connected type of the adsl line PVC is ipoaVcmux
                   "
        ::= { hwAdslLinePvcCfgEntry 10 }

    hwAdslLinePvcRowStatusCfg OBJECT-TYPE
        SYNTAX RowStatus
        MAX-ACCESS read-create
        STATUS current
        DESCRIPTION
                   "Row status. Add or delete a table item."
        ::= { hwAdslLinePvcCfgEntry 11 }

-- hwadslLineCfgTable

    hwadslLineCfgTable OBJECT-TYPE
        SYNTAX SEQUENCE OF HwadslLineCfgEntry
        MAX-ACCESS not-accessible
        STATUS current
        DESCRIPTION
                   "This table includes common attributes describing both ends of the line.
                    The index of this table is ifIndex.
                   "
        ::= { hwAdslMibObjects 6 }

    hwadslLineCfgEntry OBJECT-TYPE
        SYNTAX HwadslLineCfgEntry
        MAX-ACCESS not-accessible
        STATUS current
        DESCRIPTION
                   "This table includes common attributes describing both ends of the line.
                    The index of this entry is ifIndex.
                   "
        INDEX { ifIndex }
        ::= { hwadslLineCfgTable 1 }

    HwadslLineCfgEntry ::=
        SEQUENCE {
                     hwadslLineExtConfProfileCfg      OCTET STRING,
                     hwadslLineDynamicProfileCfg      OCTET STRING
                 }

    hwadslLineExtConfProfileCfg OBJECT-TYPE
        SYNTAX  OCTET STRING (SIZE (0..32))
        MAX-ACCESS  read-write
        STATUS      current
        DESCRIPTION
                   "The value of this object identifies the row
                    in the ADSL Extend Line Configuration Profile Table,
                    (adslLineExtConfProfileTable), which applies to this
                    ADSL line, and channels if applicable.

                    NULL - indicates that there is no extend line profile
                    bound to this port.
                    Range: 0-32
                   "
        ::= { hwadslLineCfgEntry 1 }

    hwadslLineDynamicProfileCfg OBJECT-TYPE
        SYNTAX  OCTET STRING (SIZE (0..32))
        MAX-ACCESS  read-write
        STATUS      current
        DESCRIPTION
                   "The value of this object identifies the row
                    in the ADSL Dynamic Profile Table,which applies to this
                    ADSL line, and channels if applicable.

                    NULL - indicates that there is no Dynamic profile
                    bound to this port.
                    Range: 0-32
                   "
        ::= { hwadslLineCfgEntry 2 }

-- hwAdslLineBitAllocationInfoTable

    hwAdslLineBitAllocationInfoTable OBJECT-TYPE
        SYNTAX SEQUENCE OF HwAdslLineBitAllocationInfoEntry
        MAX-ACCESS not-accessible
        STATUS current
        DESCRIPTION
                   "This hwAdslLineBitAllocationInfoTable contains the detailed bit-allocation
                    information for the current link. This information can be used to determine
                    whether a given sub-carrier loop has sufficient margin to support ADSL
                    data rates, and possibly to determine whether certain specific types
                    of interference or line attenuation exist. The bit allocation information
                    are only valid when the ATU-C is in the C-ACTIVE state.
                    The index of this table is ifIndex."
        ::= { hwAdslMibObjects 7 }

    hwAdslLineBitAllocationInfoEntry OBJECT-TYPE
        SYNTAX HwAdslLineBitAllocationInfoEntry
        MAX-ACCESS not-accessible
        STATUS current
        DESCRIPTION
                   "This hwAdslLineBitAllocationInfoTable contains the detailed bit-allocation
                    information for the current link. This information can be used to determine
                    whether a given sub-carrier loop has sufficient margin to support ADSL
                    data rates, and possibly to determine whether certain specific types
                    of interference or line attenuation exist. The bit allocation information
                    are only valid when the ATU-C is in the C-ACTIVE state.
	            The index of this entry is ifIndex."
        INDEX { ifIndex }
        ::= { hwAdslLineBitAllocationInfoTable 1 }

    HwAdslLineBitAllocationInfoEntry ::=
        SEQUENCE {
                     hwAdslLineDownStreamBitsPerFrameInfo     Integer32,
                     hwAdslLineUpStreamBitsPerFrameInfo       Integer32,
                     hwAdslLineDownStreamBitAllocLowInfo      OCTET STRING,
                     hwAdslLineDownStreamBitAllocHighInfo     OCTET STRING,
                     hwAdslLineUpStreamBitAllocInfo           OCTET STRING
                 }

    hwAdslLineDownStreamBitsPerFrameInfo OBJECT-TYPE
        SYNTAX Integer32
        MAX-ACCESS read-only
        STATUS current
        DESCRIPTION
                   "Number of bits required per frame in the downstream data path for the
                    current configuration.
                   "
        ::= { hwAdslLineBitAllocationInfoEntry 1 }

    hwAdslLineUpStreamBitsPerFrameInfo OBJECT-TYPE
        SYNTAX Integer32
        MAX-ACCESS read-only
        STATUS current
        DESCRIPTION
                   "Number of bits required per frame in the upstream data path for the
                    current configuration.
                   "
        ::= { hwAdslLineBitAllocationInfoEntry 2 }

    hwAdslLineDownStreamBitAllocLowInfo OBJECT-TYPE
        SYNTAX OCTET STRING (SIZE (256))
        MAX-ACCESS read-only
        STATUS current
        DESCRIPTION
	           "when used to Adsl board
	            This object contains the first 128 downstream sub-carrier bit allocations
	            (sub-carrier # 1-128). This object is 64 bytes in length, where each byte
	            contains 2 sub-carrier values.

	             Byte 1 - 64           Downstream bit allocation (first 128 sub-carriers),
	                                   one byte for two sub-carriers.

	               1        Bits 4 - 7 # bits in 1st downstream sub-carrier
	               1        Bits 0 - 3 # bits in 2nd downstream sub-carrier
	                        ...
	               64       Bits 4 - 7 # bits in 127th downstream sub-carrier
	               64       Bits 0 - 3 # bits in 128th downstream sub-carrier

	            when used to Adsl2+ board
	            This object contains the first 256 downstream sub-carrier bit allocations
	            (sub-carrier # 1-256). This object is 256 bytes in length, where each byte
	            contains 1 sub-carrier values.

	             Byte 1 - 256          Downstream bit allocation (first 256 sub-carriers),
	                                   one byte for one sub-carriers.

	               1        Bits 0 - 7 # bits in 1st downstream sub-carrier
	                        ...
	               255      Bits 0 - 7 # bits in 255th downstream sub-carrier
	               256      Bits 0 - 7 # bits in 256th downstream sub-carrier
	           "
        ::= { hwAdslLineBitAllocationInfoEntry 3 }

    hwAdslLineDownStreamBitAllocHighInfo OBJECT-TYPE
        SYNTAX OCTET STRING (SIZE (256))
        MAX-ACCESS read-only
        STATUS current
        DESCRIPTION
	           "when used to Adsl board
	            This object contains the second 128 downstream sub-carrier bit allocations
	            (sub-carrier # 129-256). This object is 64 bytes in length, where each byte
	            contains 2 sub-carrier values.

	             Byte 1 - 64           Downstream bit allocation (second 128 sub-carriers),
	                                   one byte for two sub-carriers.

	               1        Bits 4 - 7 # bits in 129th downstream sub-carrier
	               1        Bits 0 - 3 # bits in 130th downstream sub-carrier
	                        ...
	               64       Bits 4 - 7 # bits in 255th downstream sub-carrier
	               64       Bits 0 - 3 # bits in 256th downstream sub-carrier

	            when used to Adsl2+ board
	            This object contains the second 256 downstream sub-carrier bit allocations
	            (sub-carrier # 257-512). This object is 256 bytes in length, where each byte
	            contains 1 sub-carrier values.

	             Byte 1 - 256         Downstream bit allocation (second 256 sub-carriers),
	                                  one byte for one sub-carriers.

	               1       Bits 0 - 7 # bits in 1st downstream sub-carrier
	                       ...
	               255     Bits 0 - 7 # bits in 255th downstream sub-carrier
	               256     Bits 0 - 7 # bits in 256th downstream sub-carrier
	           "
        ::= { hwAdslLineBitAllocationInfoEntry 4 }

    hwAdslLineUpStreamBitAllocInfo OBJECT-TYPE
        SYNTAX OCTET STRING (SIZE (64))
        MAX-ACCESS read-only
        STATUS current
        DESCRIPTION
                   "when used to Adsl board
                    This Object contains 64 upstream sub-carrier bit allocations (sub-carrier # 1-64).
                    This Object is 32 bytes in length, where each byte contains 2 sub-carrier values.

                     Byte 1 - 32           Upstream bit allocation information, total: 32 bytes,
                                           one byte for two sub-carriers.

                       1        Bits 7 - 4 # bits in 1st upstream sub-carrier
                       1        Bits 3 - 0 # bits in 2nd upstream sub-carrier
                                ...
                       32       Bits 7 - 4 # bits in 63rd upstream sub-carrier
                       32       Bits 3 - 0 # bits in 64th upstream sub-carrier

                    when used to Adsl2+ board
                    This Object contains 64 upstream sub-carrier bit allocations (sub-carrier # 1-64).
                    This Object is 64 bytes in length, where each byte contains 1 sub-carrier values.

                     Byte 1 - 64           Upstream bit allocation information, total: 64 bytes,
                                           one byte for one sub-carriers.

                       1        Bits 7 - 0 # bits in 1st upstream sub-carrier
                                ...
                       64       Bits 7 - 0 # bits in 64th upstream sub-carrier
                   "
        ::= { hwAdslLineBitAllocationInfoEntry 5 }

-- hwXdslPortCfgTable

    hwXdslPortCfgTable OBJECT-TYPE
        SYNTAX SEQUENCE OF HwXdslPortCfgEntry
        MAX-ACCESS not-accessible
        STATUS current
        DESCRIPTION
                   "This table includes xDSL(e.g. adsl,g.shdsl,vdsl...)port information.
                    Used to support common attributes of the ADSL, G.SHDSL, and VDSL ports
                    The index of this table is ifIndex.
                   "
        ::= { hwAdslMibObjects 8 }

    hwXdslPortCfgEntry OBJECT-TYPE
        SYNTAX HwXdslPortCfgEntry
        MAX-ACCESS not-accessible
        STATUS current
        DESCRIPTION
                   "This table includes xDSL(e.g. adsl,g.shdsl,vdsl...)port information.
                    Used to support common attributes of the ADSL, G.SHDSL, and VDSL ports
                    The index of this entry is ifIndex.
                   "
        INDEX { ifIndex }
        ::= { hwXdslPortCfgTable 1 }

    HwXdslPortCfgEntry ::=
        SEQUENCE {
                     hwXdslPortMaxMacLearnCfg                Integer32,
                     hwXdslPortRateMonitorThresholdCfg       Integer32,
                     hwXdslPortUpThresholdTxRateCfg          Gauge32,
                     hwXdslPortDownThresholdTxRateCfg        Gauge32,
                     hwXdslPortRateMonitorAlarmEnableCfg     INTEGER,
                     hwXdslPortUpTimeCfg                     Counter32,
                     hwXdslPortNTEPowerStatusCfg             INTEGER,
                     hwXdslPortCurrentUpRateCfg              Integer32 ,
                     hwXdslPortCurrentDownRateCfg            Integer32 ,
                     hwXdslPortFarEndRunStateCfg             INTEGER,
                     hwXdslPortPowerStateCfg                 INTEGER,
                     hwXdslPortUpCntCfg                      Unsigned32 ,
                     hwXdslPortUpCntAdminStatusCfg           INTEGER ,
                     hwXdslPortLastUpTimeCfg                 DateAndTime,
                     hwXdslPortLastDownTimeCfg               DateAndTime,
                     hwXdslPortClearUpCntTimeCfg             DateAndTime,
                     hwXdslPortRetrainCntCfg                 Unsigned32 ,
                     hwXdslPortLastRetrainReasonCfg          Unsigned32,
                     hwXdslPortLoopFlagCfg 	             INTEGER,
                     hwXdslPortUpThresholdCfg                Integer32,
                     hwXdslPortDownThresholdCfg              Integer32
                }

    hwXdslPortMaxMacLearnCfg OBJECT-TYPE
        SYNTAX Integer32 (0..255)
        MAX-ACCESS read-write
        STATUS current
        DESCRIPTION
                   "Set Max MAC count on the xDSL port.
                    Range: 0-255
                    Default: 255
                   "
        DEFVAL { 255 }
        ::= { hwXdslPortCfgEntry 1 }

    hwXdslPortRateMonitorThresholdCfg OBJECT-TYPE
        SYNTAX Integer32 (0..100)
        MAX-ACCESS read-write
        STATUS current
        DESCRIPTION
                   "Set Port monitoring rate threshold percent. Including upstream and downstream.
                    Range: 0-100
                    Default: 0
                   "
        DEFVAL { 0 }
        ::= { hwXdslPortCfgEntry 2 }

    hwXdslPortUpThresholdTxRateCfg  OBJECT-TYPE
        SYNTAX Gauge32
        UNITS "bps"
        MAX-ACCESS read-write
        STATUS current
        DESCRIPTION
                   "Set Port monitoring upstream rate threshold value.
                    Default: 0
                    Unit:bps
                   "
        DEFVAL { 0 }
        ::= { hwXdslPortCfgEntry 3 }

    hwXdslPortDownThresholdTxRateCfg  OBJECT-TYPE
        SYNTAX Gauge32
        UNITS "bps"
        MAX-ACCESS read-write
        STATUS current
        DESCRIPTION
                   "Set Port monitoring downstream rate threshold value.
                    Default: 0
                    Unit:bps
                   "
        DEFVAL { 0 }
        ::= { hwXdslPortCfgEntry 4 }

    hwXdslPortRateMonitorAlarmEnableCfg  OBJECT-TYPE
        SYNTAX INTEGER {
                           enabled(1),
                           disabled(2)
                       }
        MAX-ACCESS read-write
        STATUS current
        DESCRIPTION
                   "Enables or disables port rate monitor alarm.
                    Options:
                    1. enabled(1)  - Enables port rate monitor alarm
                    2. disabled(2) - Disables port rate monitor alarm
                   "
        ::= { hwXdslPortCfgEntry 5 }

    hwXdslPortUpTimeCfg OBJECT-TYPE
        SYNTAX Counter32
        MAX-ACCESS read-only
        STATUS current
        DESCRIPTION
                   "Duration of the xDSL port activation
                    Unit: second
                   "
        ::= { hwXdslPortCfgEntry 6 }

    hwXdslPortNTEPowerStatusCfg OBJECT-TYPE
        SYNTAX INTEGER {
                           on(1),
                           off(2),
                           unknown(3)
                       }
        MAX-ACCESS read-only
        STATUS current
        DESCRIPTION
                   "NTE power status, this object is defaulted off(2).
                    Options:
                    1. on(1)      - NTE power status is on
                    2. off(2)     - NTE power status is off
                    3. unknown(3) - NTE power is in unknown status
                   "
        ::= { hwXdslPortCfgEntry 7 }

    hwXdslPortCurrentUpRateCfg  OBJECT-TYPE
        SYNTAX Integer32 (0..30000)
        MAX-ACCESS accessible-for-notify
        STATUS current
        DESCRIPTION
                   "Xdsl port current upstream value.
                    Range: 0-30000
                    Default: 0
                   "
        ::= { hwXdslPortCfgEntry 8 }

    hwXdslPortCurrentDownRateCfg  OBJECT-TYPE
        SYNTAX Integer32 (0..30000)
        MAX-ACCESS accessible-for-notify
        STATUS current
        DESCRIPTION
                   "Xdsl port current downstream value.
                    Range: 0-30000
                    Default: 0
                   "
        ::= { hwXdslPortCfgEntry 9 }

    hwXdslPortFarEndRunStateCfg OBJECT-TYPE
        SYNTAX INTEGER {
                           unknown(1),
                           noModem(2),
                           handshake(3),
                           showtime(4)
                       }
        MAX-ACCESS read-only
        STATUS current
        DESCRIPTION
                   "Remote running status of the xDSL port. This object is defaulted unknown(1).
                    Options:
                    1. unknown(1)   - Unknown status
                    2. noModem(2)   - Port is not connected to modem
                    3. handshake(3) - Handshake status
                    4. showtime(4)  - Port is activated
                   "
        ::= { hwXdslPortCfgEntry 10 }

    hwXdslPortPowerStateCfg OBJECT-TYPE
         SYNTAX INTEGER {
                           l0(1),
                           l2(2),
                           l3(3),
                           l1(4),
                           invalidValue(-1)
                        }
         MAX-ACCESS read-only
         STATUS current
         DESCRIPTION "Xdsl port power state.
                      Options:
                      1. l0(1)            - Full-on state
                      2. l2(2)            - Low power state
                      3. l3(3)            - Idle state
                      4. l1(4)            - Low power state
                      5. invalidValue(-1) - Invalid state
                      Default: l0(1)
                     "
         ::= { hwXdslPortCfgEntry 11 }

    hwXdslPortUpCntCfg OBJECT-TYPE
        SYNTAX Unsigned32
        MAX-ACCESS read-only
        STATUS current
        DESCRIPTION "The up counts of xDSL port."
        ::= { hwXdslPortCfgEntry 12 }

    hwXdslPortUpCntAdminStatusCfg   OBJECT-TYPE
        SYNTAX INTEGER {
                          reset(0)
                       }
        MAX-ACCESS read-write
        STATUS current
        DESCRIPTION "Admin the up counts of xDSL port.
                     Options:
                      1. reset(0) - Reset the up counts of xDSL port
                    "
        ::= { hwXdslPortCfgEntry 13 }

    hwXdslPortLastUpTimeCfg OBJECT-TYPE
        SYNTAX DateAndTime
        MAX-ACCESS read-only
        STATUS current
        DESCRIPTION "Last up time of a xDSL port."
        ::= { hwXdslPortCfgEntry 14 }

    hwXdslPortLastDownTimeCfg OBJECT-TYPE
        SYNTAX DateAndTime
        MAX-ACCESS read-only
        STATUS current
        DESCRIPTION "Last down time of a xDSL port."
        ::= { hwXdslPortCfgEntry 15 }

    hwXdslPortClearUpCntTimeCfg OBJECT-TYPE
        SYNTAX DateAndTime
        MAX-ACCESS read-only
        STATUS current
        DESCRIPTION "The time when up counts of a xDSL port is cleared."
        ::= { hwXdslPortCfgEntry 16 }

    hwXdslPortRetrainCntCfg  OBJECT-TYPE
        SYNTAX Unsigned32
        MAX-ACCESS read-only
        STATUS current
        DESCRIPTION "The retrain counts of xDSL Line."
        ::= { hwXdslPortCfgEntry 17 }

    hwXdslPortLastRetrainReasonCfg OBJECT-TYPE
        SYNTAX Unsigned32
        MAX-ACCESS read-only
        STATUS current
        DESCRIPTION
                   "The last retrain reson of xDSL Line, coded as bit mask.
                    Only one bit can be set valid, all bits set valid means invalid retrain reason.
                   "
        ::= { hwXdslPortCfgEntry 18 }

    hwXdslPortLoopFlagCfg OBJECT-TYPE
        SYNTAX INTEGER {
                           false(0),
                           true(1)
                       }
        MAX-ACCESS read-only
        STATUS current
        DESCRIPTION
                   "Loop flag.
                    Options:
                    1. false(0) - No loop
                    2. true (1) - Loop
                   "
        ::= { hwXdslPortCfgEntry 19 }

    hwXdslPortUpThresholdCfg OBJECT-TYPE
        SYNTAX Integer32 (0..100)
        MAX-ACCESS read-write
        STATUS current
        DESCRIPTION
                   "Set Port monitoring upstream rate threshold percent value.
                    Range: 0-100
                    Default: 0
                   "
        DEFVAL { 0 }
        ::= { hwXdslPortCfgEntry 20 }

    hwXdslPortDownThresholdCfg OBJECT-TYPE
        SYNTAX Integer32 (0..100)
        MAX-ACCESS read-write
        STATUS current
        DESCRIPTION
                   "Set Port monitoring downstream rate threshold percent value.
                    Range: 0-100
                    Default: 0
                   "
        DEFVAL { 0 }
        ::= { hwXdslPortCfgEntry 21 }

-- hwAdslLinePreActParaInfoTable

    hwAdslLinePreActParaInfoTable OBJECT-TYPE
        SYNTAX SEQUENCE OF HwAdslLinePreActParaInfoEntry
        MAX-ACCESS not-accessible
        STATUS current
        DESCRIPTION
                   "This table provides one row for each ADSL PORT.
                    Each row contains the preactived parameters.
                    The index of this table is ifIndex."
        ::= { hwAdslMibObjects 9 }

    hwAdslLinePreActParaInfoEntry OBJECT-TYPE
        SYNTAX HwAdslLinePreActParaInfoEntry
        MAX-ACCESS not-accessible
        STATUS current
        DESCRIPTION
                   "This table provides one row for each ADSL PORT.
                    Each row contains the preactived parameters.
                    The index of this entry is ifIndex."
        INDEX { ifIndex }
        ::= { hwAdslLinePreActParaInfoTable 1 }

    HwAdslLinePreActParaInfoEntry ::=
        SEQUENCE {
                     hwAdslAtucPrevSnrMgnInfo            Integer32,
                     hwAdslAturPrevSnrMgnInfo             Integer32,
                     hwAdslAtucPrevAttainableRateInfo     Unsigned32,
                     hwAdslAturPrevAttainableRateInfo     Unsigned32,
                     hwAdslAtucPreAtnInfo                Gauge32,
                     hwAdslAturPreAtnInfo                Gauge32,
                     hwAdslPreActiveTimeInfo              DateAndTime
                 }

    hwAdslAtucPrevSnrMgnInfo OBJECT-TYPE
        SYNTAX Integer32
        UNITS "tenth dB"
        MAX-ACCESS read-only
        STATUS current
        DESCRIPTION
                   "Noise Margin as seen by this ATU-C at the
                    time of the last adslAtucRateChangeTrap event.
                    Unit: tenth dB
                   "
        ::= { hwAdslLinePreActParaInfoEntry 1 }

    hwAdslAturPrevSnrMgnInfo OBJECT-TYPE
        SYNTAX Integer32
        UNITS "tenth dB"
        MAX-ACCESS read-only
        STATUS current
        DESCRIPTION
                   "Noise Margin as seen by this ATU-R at
                    the time of the last adslAtucRateChangeTrap event.
                    Unit: tenth dB
                   "
        ::= { hwAdslLinePreActParaInfoEntry 2 }

    hwAdslAtucPrevAttainableRateInfo OBJECT-TYPE
        SYNTAX Unsigned32
        UNITS "bps"
        MAX-ACCESS read-only
        STATUS current
        DESCRIPTION
                   "Indicates the maximum attainable data rate
                    by the ATU-C at the time of the last
                    adslAtucRateChangeTrap event.
                    Unit: bps
                   "
        ::= { hwAdslLinePreActParaInfoEntry 3 }

    hwAdslAturPrevAttainableRateInfo OBJECT-TYPE
        SYNTAX Unsigned32
        UNITS "bps"
        MAX-ACCESS read-only
        STATUS current
        DESCRIPTION
                   "Indicates the maximum attainable data rate
                    by the ATU-R at the time of the last
                    adslAtucRateChangeTrap event.
                    Unit: bps
                   "
        ::= { hwAdslLinePreActParaInfoEntry 4 }

    hwAdslAtucPreAtnInfo OBJECT-TYPE
        SYNTAX Gauge32
        UNITS "tenth dB"
        MAX-ACCESS read-only
        STATUS current
        DESCRIPTION
                   "Measured difference in the total power
                    transmitted as seen by this ATU-C at the time
                    of the last adslAtucRateChangeTrap event.
                    Unit: tenth dB
                   "
        ::= { hwAdslLinePreActParaInfoEntry 5 }

    hwAdslAturPreAtnInfo OBJECT-TYPE
        SYNTAX Gauge32
        UNITS "tenth dB"
        MAX-ACCESS read-only
        STATUS current
        DESCRIPTION
                   "Measured difference in the total power
                    transmitted as seen by this ATU-R at the time of the
                    last adslAtucRateChangeTrap event.
                    Unit: tenth dB
                   "
        ::= { hwAdslLinePreActParaInfoEntry 6 }

    hwAdslPreActiveTimeInfo OBJECT-TYPE
        SYNTAX      DateAndTime
        MAX-ACCESS  read-only
        STATUS      current
        DESCRIPTION "The last time at that the port was activated."
        ::= { hwAdslLinePreActParaInfoEntry 7 }

-- hwPortThreePriorityCfgTable

    hwPortThreePriorityCfgTable OBJECT-TYPE
        SYNTAX SEQUENCE OF HwPortThreePriorityCfgEntry
        MAX-ACCESS not-accessible
        STATUS obsolete
        DESCRIPTION
                   "Adsl port three priority table.
                    The index of this table is ifIndex.
                   "
        ::= { hwAdslMibObjects 10 }

    hwPortThreePriorityCfgEntry OBJECT-TYPE
        SYNTAX HwPortThreePriorityCfgEntry
        MAX-ACCESS not-accessible
        STATUS obsolete
        DESCRIPTION
                   "Adsl port three priority table.
                    The index of this entry is ifIndex.
                   "
        INDEX { ifIndex }
        ::= { hwPortThreePriorityCfgTable 1 }

    HwPortThreePriorityCfgEntry ::=
        SEQUENCE {
                     hwPortThreePriorityEnableCfg    INTEGER
		 }

    hwPortThreePriorityEnableCfg OBJECT-TYPE
        SYNTAX INTEGER {
                           enable(1),
                           disable(2)
                       }
        MAX-ACCESS read-write
        STATUS obsolete
        DESCRIPTION
                   "Three Priority status of the interface.
                    Options:
                    1. enable(1)  - Adsl port three priority is enabled
                    2. disable(2) - Adsl port three priority is disabled
                   "
        ::= { hwPortThreePriorityCfgEntry 1 }

-- hwSlotMacMaxNoLimitCfgTable

    hwSlotMacMaxNoLimitCfgTable OBJECT-TYPE
        SYNTAX SEQUENCE OF HwSlotMacMaxNoLimitCfgEntry
        MAX-ACCESS not-accessible
        STATUS obsolete
        DESCRIPTION
                   "Max mac learning no limit table.
                    The indexes of this table are hwFrameIndex and hwSlotIndex.
                   "
        ::= { hwAdslMibObjects 11 }

    hwSlotMacMaxNoLimitCfgEntry OBJECT-TYPE
        SYNTAX HwSlotMacMaxNoLimitCfgEntry
        MAX-ACCESS not-accessible
        STATUS obsolete
        DESCRIPTION
                   "Max mac learning no limit table.
                    The indexes of this entry are hwFrameIndex and hwSlotIndex.
                   "
        INDEX { hwFrameIndex, hwSlotIndex }
        ::= { hwSlotMacMaxNoLimitCfgTable 1 }

    HwSlotMacMaxNoLimitCfgEntry ::=
        SEQUENCE {
                     hwSlotMacMaxNoLimitEnableCfg    INTEGER
                 }

    hwSlotMacMaxNoLimitEnableCfg OBJECT-TYPE
        SYNTAX INTEGER {
                           enable(1),
                           disable(2)
                       }
        MAX-ACCESS read-write
        STATUS obsolete
        DESCRIPTION
                   "This object is used to set whether all the ports in the slot limits the maximum number of learning MAC addresses.
                    Options:
                    1. enable(1)  - Don't limit the max NO. of learning mac addresses in the slot
                    2. disable(2) - Limit the max NO. of learning mac addresses in the slot
                   "
        ::= { hwSlotMacMaxNoLimitCfgEntry 1 }

--  hwXdslPortStateStatisticInfoTable

    hwXdslPortStateStatisticInfoTable OBJECT-TYPE
        SYNTAX SEQUENCE OF HwXdslPortStateStatisticInfoEntry
        MAX-ACCESS not-accessible
        STATUS current
        DESCRIPTION
                   "XDSL port state staticstic table.
                    Used to support the statistics information about the status mapping and status of ports on service boards, such as the ADSL, G.SHDSL, and VDSL boards
                    The indexes of this table are ifType, hwFrameIndex, hwSlotIndex.
                   "
        ::= { hwAdslMibObjects 12 }

    hwXdslPortStateStatisticInfoEntry OBJECT-TYPE
        SYNTAX HwXdslPortStateStatisticInfoEntry
        MAX-ACCESS not-accessible
        STATUS current
        DESCRIPTION
                   "XDSL port state staticstic table.
                    Used to support the statistics information about the status mapping and status of ports on service boards, such as the ADSL, G.SHDSL, and VDSL boards
                    The indexes of this entry are ifType, hwFrameIndex, hwSlotIndex.
                   "
        INDEX { ifType, hwFrameIndex, hwSlotIndex }
        ::= { hwXdslPortStateStatisticInfoTable 1 }

    HwXdslPortStateStatisticInfoEntry ::=
        SEQUENCE{
                    hwXdslPortStatePortNumberInfo            Unsigned32,
                    hwXdslPortStateBitmapListInfo            OCTET STRING,
                    hwXdslTotalOfActivatedPortsInfo          Unsigned32,
                    hwXdslTotalOfDeactivatedPortsInfo        Unsigned32,
                    hwXdslTotalOfActivatingPortsInfo         Unsigned32,
                    hwXdslTotalOfTestingPortsInfo            Unsigned32,
                    hwXdslTotalOfBlockedPortsInfo            Unsigned32,
                    hwXdslTotalOfLocalLoopbackPortsInfo      Unsigned32,
                    hwXdslTotalOfRemoteLoopbackPortsInfo     Unsigned32,
                    hwXdslTotalOfFailedPortsInfo             Unsigned32,
                    hwXdslTotalOfUnknownPortsInfo            Unsigned32
                }

    hwXdslPortStatePortNumberInfo OBJECT-TYPE
        SYNTAX Unsigned32
        MAX-ACCESS read-only
        STATUS current
        DESCRIPTION
                   "This object is port number of one slot."
        ::= { hwXdslPortStateStatisticInfoEntry 1 }

    hwXdslPortStateBitmapListInfo OBJECT-TYPE
        SYNTAX OCTET STRING
        MAX-ACCESS read-only
        STATUS current
        DESCRIPTION
                   "The type of port status:
                    2  failed;
                    8  testing;
                    9  activated;
                    10  activating;
                    11  deactivated;
                    18  localloopback;
                    19  remoteloopback;
                    20  blocked;
                    37  utopialoopback;
                    38  afeloopback;
                    39  hybridloopback;
                    255 unknown;
                    The hwXdslPortStateBitmapListInfo describes the states of all ports.
                    Every byte describe the current state of every port.
                    The length is equal to the value of the hwXdslPortStatePortNumberInfo.
                   "
        ::= { hwXdslPortStateStatisticInfoEntry 2 }

    hwXdslTotalOfActivatedPortsInfo OBJECT-TYPE
        SYNTAX Unsigned32
        MAX-ACCESS read-only
        STATUS current
        DESCRIPTION
                   "The total of the activated ports."
        ::= { hwXdslPortStateStatisticInfoEntry 3 }

    hwXdslTotalOfDeactivatedPortsInfo OBJECT-TYPE
        SYNTAX Unsigned32
        MAX-ACCESS read-only
        STATUS current
        DESCRIPTION
                   "The total of the deactivated ports."
        ::= { hwXdslPortStateStatisticInfoEntry 4 }

    hwXdslTotalOfActivatingPortsInfo OBJECT-TYPE
        SYNTAX Unsigned32
        MAX-ACCESS read-only
        STATUS current
        DESCRIPTION
                   "The total of the activating ports."
        ::= { hwXdslPortStateStatisticInfoEntry 5 }

    hwXdslTotalOfTestingPortsInfo OBJECT-TYPE
        SYNTAX Unsigned32
        MAX-ACCESS read-only
        STATUS current
        DESCRIPTION
                   "The total of the Testing ports."
        ::= { hwXdslPortStateStatisticInfoEntry 6 }

    hwXdslTotalOfBlockedPortsInfo OBJECT-TYPE
        SYNTAX Unsigned32
        MAX-ACCESS read-only
        STATUS current
        DESCRIPTION
                   "The total of the blocked ports."
        ::= { hwXdslPortStateStatisticInfoEntry 7 }

    hwXdslTotalOfLocalLoopbackPortsInfo OBJECT-TYPE
        SYNTAX Unsigned32
        MAX-ACCESS read-only
        STATUS current
        DESCRIPTION
                   "The total of the local testing ports."
        ::= { hwXdslPortStateStatisticInfoEntry 8 }

    hwXdslTotalOfRemoteLoopbackPortsInfo OBJECT-TYPE
        SYNTAX Unsigned32
        MAX-ACCESS read-only
        STATUS current
        DESCRIPTION
                   "The total of the remote testing ports."
        ::= { hwXdslPortStateStatisticInfoEntry 9 }

    hwXdslTotalOfFailedPortsInfo OBJECT-TYPE
        SYNTAX Unsigned32
        MAX-ACCESS read-only
        STATUS current
        DESCRIPTION
                   "The total of the failed ports."
        ::= { hwXdslPortStateStatisticInfoEntry 10 }

    hwXdslTotalOfUnknownPortsInfo OBJECT-TYPE
        SYNTAX Unsigned32
        MAX-ACCESS read-only
        STATUS current
        DESCRIPTION
                   "The total of the unknown xDSL ports."
        ::= { hwXdslPortStateStatisticInfoEntry 11 }

--  hwadslLineExtConfProfileCfgTable

    hwadslLineExtConfProfileCfgTable OBJECT-TYPE
        SYNTAX SEQUENCE OF HwadslLineExtConfProfileCfgEntry
        MAX-ACCESS not-accessible
        STATUS current
        DESCRIPTION
                   "This table contains information on the ADSL extend line
                    configuration. One entry in this table reflects a
                    extend line profile defined by a manager which can be used to
                    configure the ADSL line.
                    The index of this table is hwadslLineExtConfProfileNameCfg.
                   "
        ::= { hwAdslMibObjects 13 }

    hwadslLineExtConfProfileCfgEntry OBJECT-TYPE
        SYNTAX HwadslLineExtConfProfileCfgEntry
        MAX-ACCESS not-accessible
        STATUS current
        DESCRIPTION
                   "This table contains information on the ADSL extend line
                    configuration. One entry in this table reflects a
                    extend line profile defined by a manager which can be used to
                    configure the ADSL line.
                    The index of this entry is hwadslLineExtConfProfileNameCfg.
                   "
        INDEX {IMPLIED hwadslLineExtConfProfileNameCfg }
        ::= { hwadslLineExtConfProfileCfgTable 1 }

    HwadslLineExtConfProfileCfgEntry ::=
        SEQUENCE {
                     hwadslLineExtConfProfileNameCfg                OCTET STRING,
                     hwadslLineDisableToneSection1BeginCfg          Integer32,
                     hwadslLineDisableToneSection1EndCfg	    Integer32,
                     hwadslLineDisableToneSection1FlagCfg	    INTEGER,
                     hwadslLineDisableToneSection2BeginCfg	    Integer32,
                     hwadslLineDisableToneSection2EndCfg            Integer32,
                     hwadslLineDisableToneSection2FlagCfg           INTEGER,
                     hwadslLineDisableToneSection3BeginCfg          Integer32,
                     hwadslLineDisableToneSection3EndCfg            Integer32,
                     hwadslLineDisableToneSection3FlagCfg           INTEGER,
                     hwadslLineDisableToneSection4BeginCfg          Integer32,
                     hwadslLineDisableToneSection4EndCfg            Integer32,
                     hwadslLineDisableToneSection4FlagCfg           INTEGER,
                     hwadsl2ChConfProfMinProtectionDsCfg            HWADSLSYMBOLPROTECTION,
                     hwadsl2ChConfProfMinProtectionUsCfg            HWADSLSYMBOLPROTECTION,
                     hwAdslExtDsMinTrainSnrMgnCfg                   Integer32,
                     hwAdslExtUsMinTrainSnrMgnCfg                   Integer32,
                     hwAdslExtDsMaxPsdCfg                           Integer32,
                     hwadsl2TSSiPsdMaskDsCfg                        Adsl2PsdMaskDs,
                     hwadsl2TranMissionStardardMaskCfg              Unsigned32,
                     hwadsl2TransMissionAnnexMaskCfg                Unsigned32,
                     hwadsl2TransMissionAnnexMScopeCfg              HWADSL2ANNEXMSCOPE,
                     hwadsl2L2ModeStateCfg                          INTEGER,
                     hwadsl2L2ModeMinDataRateCfg                    Integer32,
                     hwadsl2L2ModeMaxDataRateCfg                    Integer32,
                     hwadsl2L2ModePayloadRateThresholdCfg           Integer32,
                     hwadsl2L2ModeGuardTimeCfg                      Integer32,
                     hwadsl2L2ModeIntervalTimeCfg                   Integer32,
                     hwadsl2L2ModeIntervalPowerValueCfg             Integer32,
                     hwadsl2L2ModeTotalPowerValueCfg                Integer32,
                     hwadslExtUsPhyRcontrolCfg                      INTEGER,
                     hwadslExtUsINPmaxCfg                           Adsl2SymbolProtection,
                     hwadslExtUsMinRtxRatioCfg                      Integer32,
                     hwadslExtUsMinRSoverheadCfg                    Integer32,
                     hwadslExtDsPhyRcontrolCfg                      INTEGER,
                     hwadslExtDsINPmaxCfg                           Adsl2SymbolProtection,
                     hwadslExtDsMinRtxRatioCfg                      Integer32,
                     hwadslExtDsMinRSoverheadCfg                    Integer32,
                     hwadsl2TSSiPsdMaskUsCfg                        Adsl2PsdMaskUs,
                     hwadslLConfProfAdslModeCfg                     INTEGER,
                     hwadslLineExtConfProfileRowStatusCfg           RowStatus,
                     hwadsl2L2ModeL2TimeCfg                         Integer32,
                     hwadslLineExtConfProfRtxModeDs                 INTEGER,
                     hwadslLineExtConfProfLeftrThreshDs             Unsigned32,
                     hwadslLineExtConfProfMinEtrRtxDs               Unsigned32,
                     hwadslLineExtConfProfMaxEtrRtxDs               Unsigned32,
                     hwadslLineExtConfProfMaxNdrRtxDs               Unsigned32,
                     hwadslLineExtConfProfMaxDelayRtxDs             Unsigned32,
                     hwadslLineExtConfProfMinDelayRtxDs             Unsigned32,
                     hwadslLineExtConfProfMinInpShineRtxDs          Unsigned32,
                     hwadslLineExtConfProfShineRatioRtxDs           Unsigned32,
                     hwadslLineExtConfProfMinInpReinRtxDs           Unsigned32,
                     hwadslLineExtConfProfIatReinRtxDs              INTEGER,
                     hwadsl2LExtLineProfReferenceClock              INTEGER,
                     hwadsl2LExtLineProfRfiBands                    OCTET STRING,
                     hwadsl2LExtLineProfDpboEPsd                    OCTET STRING,
                     hwadsl2LExtLineProfDpboEsEL                    Unsigned32,
                     hwadsl2LExtLineProfDpboEselMin                 Unsigned32,
                     hwadsl2LExtLineProfDpboEsCableModelA           Unsigned32,
                     hwadsl2LExtLineProfDpboEsCableModelB           Unsigned32,
                     hwadsl2LExtLineProfDpboEsCableModelC           Unsigned32,
                     hwadsl2LExtLineProfDpboMus                     Unsigned32,
                     hwadsl2LExtLineProfDpboFMin                    Unsigned32,
                     hwadsl2LExtLineProfDpboFMax                    Unsigned32,
                     hwadsl2LExtLineProfMaxNomPsdUs                 Integer32,
                     hwadsl2LExtLineProfMaxNomAtpDs                 Unsigned32,
                     hwadsl2LExtLineProfMaxNomAtpUs                 Unsigned32,
                     hwadsl2LExtLineProfInmIatoDs                   Unsigned32,
                     hwadsl2LExtLineProfInmIatsDs                   Unsigned32,
                     hwadsl2LExtLineProfInmCcDs                     Unsigned32,
                     hwadsl2LExtLineProfInmInpeqModeDs              Unsigned32,
                     hwadsl2LExtLineProfForceInpDs                  TruthValue,
                     hwadsl2LExtLineProfForceInpUs                  TruthValue,
                     hwadsl2LExtLineProfInitPolicy                  INTEGER,
                     hwadsl2LExtLineProfL3Time                      Unsigned32,
                     hwadsl2LExtLineProfL3ModeState                 INTEGER
                 }

    hwadslLineExtConfProfileNameCfg OBJECT-TYPE
        SYNTAX          OCTET STRING (SIZE (1..32))
        MAX-ACCESS      not-accessible
        STATUS          current
        DESCRIPTION
                   "This object is used by the hwadslLineExtConfProfileTable
                    in order to identify a row of this table.
                    Indicates the name of the extended line profile.
                   "
        ::= { hwadslLineExtConfProfileCfgEntry 1 }

    hwadslLineDisableToneSection1BeginCfg OBJECT-TYPE
        SYNTAX Integer32(0..511)
        MAX-ACCESS read-create
        STATUS current
        DESCRIPTION
                   "The begin index of the first section.
                    Range: 0-511
                   "
        ::= { hwadslLineExtConfProfileCfgEntry 2 }

    hwadslLineDisableToneSection1EndCfg OBJECT-TYPE
        SYNTAX Integer32(0..511)
        MAX-ACCESS read-create
        STATUS current
        DESCRIPTION
                   "The end index of the first section.
                    Range: 0-511
                   "
        ::= { hwadslLineExtConfProfileCfgEntry 3 }

    hwadslLineDisableToneSection1FlagCfg OBJECT-TYPE
        SYNTAX INTEGER {
                           enabled(1),
                           disabled(2)
                       }
        MAX-ACCESS read-create
        STATUS current
        DESCRIPTION
                   "The enable flag of the first section.
                    Options:
                    1. enabled(1)  - The first tone section is enabled
                    2. disabled(2) - The first tone section is disabled
                   "
        ::= { hwadslLineExtConfProfileCfgEntry 4 }

    hwadslLineDisableToneSection2BeginCfg OBJECT-TYPE
        SYNTAX Integer32(0..511)
        MAX-ACCESS read-create
        STATUS current
        DESCRIPTION
                   "The begin index of the second section.
                    Range: 0-511
                   "
        ::= { hwadslLineExtConfProfileCfgEntry 5 }

    hwadslLineDisableToneSection2EndCfg OBJECT-TYPE
        SYNTAX Integer32(0..511)
        MAX-ACCESS read-create
        STATUS current
        DESCRIPTION
                   "The end index of the second section.
                    Range: 0-511
                   "
        ::= { hwadslLineExtConfProfileCfgEntry 6 }

    hwadslLineDisableToneSection2FlagCfg OBJECT-TYPE
        SYNTAX INTEGER {
                           enabled(1),
                           disabled(2)
                       }
        MAX-ACCESS read-create
        STATUS current
        DESCRIPTION
                   "The enable flag of the second section.
                    Options:
                    1. enabled(1)  - The second tone section is enabled
                    2. disabled(2) - The second tone section is disabled
                   "
        ::= { hwadslLineExtConfProfileCfgEntry 7 }

    hwadslLineDisableToneSection3BeginCfg OBJECT-TYPE
        SYNTAX Integer32(0..511)
        MAX-ACCESS read-create
        STATUS current
        DESCRIPTION
                   "The begin index of the third section.
                    Range: 0-511
                   "
        ::= { hwadslLineExtConfProfileCfgEntry 8 }

    hwadslLineDisableToneSection3EndCfg OBJECT-TYPE
        SYNTAX Integer32(0..511)
        MAX-ACCESS read-create
        STATUS current
        DESCRIPTION
                   "The end index of the third section.
                    Range: 0-511
                   "
        ::= { hwadslLineExtConfProfileCfgEntry 9 }

    hwadslLineDisableToneSection3FlagCfg OBJECT-TYPE
        SYNTAX INTEGER {
                           enabled(1),
                           disabled(2)
                       }
        MAX-ACCESS read-create
        STATUS current
        DESCRIPTION
                   "The enable flag of the third section.
                    Options:
                    1. enabled(1)  - The third tone section is enabled
                    2. disabled(2) - The third tone section is disabled
                   "
        ::= { hwadslLineExtConfProfileCfgEntry 10 }

    hwadslLineDisableToneSection4BeginCfg OBJECT-TYPE
        SYNTAX Integer32(0..511)
        MAX-ACCESS read-create
        STATUS current
        DESCRIPTION
                   "The begin index of the fourth section.
                    Range: 0-511
                   "
        ::= { hwadslLineExtConfProfileCfgEntry 11 }

    hwadslLineDisableToneSection4EndCfg OBJECT-TYPE
        SYNTAX Integer32(0..511)
        MAX-ACCESS read-create
        STATUS current
        DESCRIPTION
                   "The end index of the fourth section.
                    Range: 0-511
                   "
        ::= { hwadslLineExtConfProfileCfgEntry 12 }

    hwadslLineDisableToneSection4FlagCfg OBJECT-TYPE
        SYNTAX INTEGER {
                           enabled(1),
                           disabled(2)
                       }
        MAX-ACCESS read-create
        STATUS current
        DESCRIPTION
                   "The enable flag of the fourth section.
                    Options:
                    1. enabled(1)  - The fourth tone section is enabled
                    2. disabled(2) - The fourth tone section is disabled
                   "
        ::= { hwadslLineExtConfProfileCfgEntry 13 }

    hwadsl2ChConfProfMinProtectionDsCfg  OBJECT-TYPE
        SYNTAX      HWADSLSYMBOLPROTECTION
        MAX-ACCESS  read-write
        STATUS      current
        DESCRIPTION
                   "If retransmission is not used in downstream direction,this parameter
                    is minimum impulse noise protection on downstream direction. The
		    minimum impulse noise protection for the bearer channel, expressed
		    in symbols. The parameter can take the following values:
		      noProtection(0),
		      halfSymbol(1),
		      singleSymbol(2),
		      twoSymbols(4),
		      threeSymbols(6),
		      fourSymbols(8),
		      fiveSymbols(10),
		      sixSymbols(12),
		      sevenSymbols(14),
		      eightSymbols(16),
		      nineSymbols(18),
		      tenSymbols(20),
		      elevenSymbols(22),
		      twelveSymbols(24),
		      thirteenSymbols(26),
		      fourteenSymbols(28),
		      fifteenSymbols(30),
		      sixteenSymbols(32),
		      null(65535)

		    The value multiply 1/2 is the real value of Noise Protection values.
		   "
        ::= { hwadslLineExtConfProfileCfgEntry 14 }

    hwadsl2ChConfProfMinProtectionUsCfg  OBJECT-TYPE
        SYNTAX      HWADSLSYMBOLPROTECTION
        MAX-ACCESS  read-write
        STATUS      current
        DESCRIPTION
                   "If retransmission is not used in upstream direction,this parameter
                    is minimum impulse noise protection on upstream direction. The
		    minimum impulse noise protection for the bearer channel, expressed
		    in symbols. The parameter can take the following values:
		      noProtection(0),
		      halfSymbol(1),
		      singleSymbol(2),
		      twoSymbols(4),
		      threeSymbols(6),
		      fourSymbols(8),
		      fiveSymbols(10),
		      sixSymbols(12),
		      sevenSymbols(14),
		      eightSymbols(16),
		      nineSymbols(18),
		      tenSymbols(20),
		      elevenSymbols(22),
		      twelveSymbols(24),
		      thirteenSymbols(26),
		      fourteenSymbols(28),
		      fifteenSymbols(30),
		      sixteenSymbols(32),
		      null(65535)
		    The value multiply 1/2 is the real value of Noise Protection values.
		   "
        ::= { hwadslLineExtConfProfileCfgEntry 15 }

    hwAdslExtDsMinTrainSnrMgnCfg OBJECT-TYPE
        SYNTAX      Integer32  (0..310)
        UNITS       "tenth dB"
        MAX-ACCESS  read-create
        STATUS      current
        DESCRIPTION
                   "Maximum Trainning Margin in downstream.
                    Range: 0-310
                    Default: 30
                    Unit: tenth dB
                   "
        DEFVAL { 30 }
        ::= { hwadslLineExtConfProfileCfgEntry 16 }

    hwAdslExtUsMinTrainSnrMgnCfg OBJECT-TYPE
        SYNTAX      Integer32  (0..310)
        UNITS       "tenth dB"
        MAX-ACCESS  read-create
        STATUS      current
        DESCRIPTION
	           "Maximum Trainning Margin in upstream.
	            Range: 0-310
	            Default: 30
                    Unit: tenth dB
                   "
        DEFVAL { 30 }
        ::= { hwadslLineExtConfProfileCfgEntry 17 }

    hwAdslExtDsMaxPsdCfg  OBJECT-TYPE
        SYNTAX      Integer32  (-60..-30)
        UNITS       "dBm/Hz"
        MAX-ACCESS  read-create
        STATUS      current
        DESCRIPTION
		   "Maximum PSD margin in downstream."
        DEFVAL { -40 }
        ::= { hwadslLineExtConfProfileCfgEntry 18 }

    hwadsl2TSSiPsdMaskDsCfg   OBJECT-TYPE
        SYNTAX      Adsl2PsdMaskDs
        MAX-ACCESS  read-write
        STATUS      current
        DESCRIPTION
 		   "The downstream PSD mask applicable at the U-C2 reference
 		    point.
 		    This parameter is used only for G992.3 or G992.5 and it may
 		    impose PSD restrictions (breakpoints) in addition to the
 		    Limit PSD mask defined in G992.5.
 		    This is a string of 32 pairs of values in the following
 		    structure:
 		    Octets 0-1 - Index of 1st sub-carrier used in the context
 		    of a first breakpoint.
 		    Octet  2   - The PSD reduction for the sub-carrier indicated in
 		                 octets 0 and 1.
 		    Octets 3-5 - Same, for a 2nd breakpoint.
 		    Octets 6-8 - Same, for a 3rd breakpoint.
 		    This architecture continues until octets 94-95, which are
 		    associated with a 32nd breakpoint.
 		    Each subcarrier index is an unsigned number in the range 1 and
 		    NSCds.  Each PSD reduction value is in the range 0 (0dBm/Hz) to
 		    255 (-127.5dBm/Hz) with steps of 0.5dBm/Hz.  Valid values are
 		    in the range 0 to 190 (0 to -95dBm/Hz).
 		    When the number of breakpoints is less than 32, all remaining
 		    octets are set to the value 0.  Note that the content of this
 		    object should be correlated with the sub-carriers mask and with
 		    the RFI setup.
 		   "
        REFERENCE    "ITU-T G.997.1, paragraph 7.3.1.2"
        ::= { hwadslLineExtConfProfileCfgEntry 19 }

    hwadsl2TranMissionStardardMaskCfg OBJECT-TYPE
        SYNTAX Unsigned32
        MAX-ACCESS read-write
        STATUS current
        DESCRIPTION
                   "The transmission stardard mask .
                    The Mask bit and the corresponding Transmission Standard:
                    0x 1       1       1       1       1       1
                    ETSI  T1.413  G992.5  G992.3  G992.2  G992.1
                    The Default BitMask: 0X0.
                   "
        ::= { hwadslLineExtConfProfileCfgEntry 20 }

    hwadsl2TransMissionAnnexMaskCfg OBJECT-TYPE
        SYNTAX Unsigned32
        MAX-ACCESS read-write
        STATUS current
        DESCRIPTION
                   "The transMission annex Mask.
                    The Mask bit and the corresponding Transmission Annex:
                    0x     1         1         1         1         1
                    Annex .J  Annex .M  Annex .L  Annex .B  Annex .A
                    The Default BitMask:  0X0.
                   "
        ::= { hwadslLineExtConfProfileCfgEntry 21 }

    hwadsl2TransMissionAnnexMScopeCfg  OBJECT-TYPE
        SYNTAX      HWADSL2ANNEXMSCOPE
        MAX-ACCESS  read-create
        STATUS      current
        DESCRIPTION
		   "Annex M expand scope:
		    1-Tone Index(7~32)
		    2-Tone Index(7~36)
		    3-Tone Index(7~40)
		    4-Tone Index(7~44)
		    5-Tone Index(7~48)
		    6-Tone Index(7~52)
		    7-Tone Index(7~56)
		    8-Tone Index(7~60)
		    9-Tone Index(7~64)
		    -1-invalidValue
		   "
        ::= { hwadslLineExtConfProfileCfgEntry 22 }

    hwadsl2L2ModeStateCfg OBJECT-TYPE
        SYNTAX INTEGER {
                           disabled(1),
                           enabled(2),
                           forced(3)
                       }
        MAX-ACCESS read-create
        STATUS current
        DESCRIPTION
                   "The state of L2 power management mode.
                    Options:
                    1. disabled(1) - The L2 power management mode is disabled
                    2. enabled(2)  - The L2 power management mode is enabled
                    3. forced(3)   - The L2 power management mode is forced
                    Default: disabled(1)
                   "
        DEFVAL { disabled }
        ::= { hwadslLineExtConfProfileCfgEntry 23 }

    hwadsl2L2ModeMinDataRateCfg  OBJECT-TYPE
        SYNTAX Integer32 (128..16384)
        UNITS "Kbps"
        MAX-ACCESS read-create
        STATUS current
        DESCRIPTION
                   "Minimum data rate in L2 mode.
                    Range: 128-16384
	            Default: 256
                    Unit: Kbps
                   "
        DEFVAL { 256 }
        ::= { hwadslLineExtConfProfileCfgEntry 24 }

    hwadsl2L2ModeMaxDataRateCfg  OBJECT-TYPE
        SYNTAX Integer32 (128..16384)
        UNITS "Kbps"
        MAX-ACCESS read-create
        STATUS current
        DESCRIPTION
                   "Maximum data rate in L2 mode.
                    Range: 128-16384
	            Default: 1024
                    Unit: Kbps
                   "
        DEFVAL { 1024 }
        ::= { hwadslLineExtConfProfileCfgEntry 25 }

    hwadsl2L2ModePayloadRateThresholdCfg  OBJECT-TYPE
        SYNTAX Integer32 (128..16384)
        UNITS "Kbps"
        MAX-ACCESS read-create
        STATUS current
        DESCRIPTION
                   "Threshold for the Payload Rate Ratio.
                    Range: 128-16384
	            Default: 128
                    Unit: Kbps
                   "
        DEFVAL { 128 }
        ::= { hwadslLineExtConfProfileCfgEntry 26 }

    hwadsl2L2ModeGuardTimeCfg  OBJECT-TYPE
        SYNTAX Integer32 (0..1024)
        UNITS "seconds"
        MAX-ACCESS read-create
        STATUS current
        DESCRIPTION
                   "Guard time before entering L2 mode.
                    Range: 0-1024
	            Default: 60
                    Unit: seconds
                   "
        DEFVAL { 60 }
        ::= { hwadslLineExtConfProfileCfgEntry 27 }

    hwadsl2L2ModeIntervalTimeCfg  OBJECT-TYPE
        SYNTAX Integer32 (0..255)
        UNITS "seconds"
        MAX-ACCESS read-create
        STATUS current
        DESCRIPTION
                   "The minimum interval between two records of L2 mode.
                    Range: 0-255
	            Default: 255
                    Unit: seconds
                   "
        DEFVAL { 255 }
        ::= { hwadslLineExtConfProfileCfgEntry 28 }

    hwadsl2L2ModeIntervalPowerValueCfg  OBJECT-TYPE
        SYNTAX Integer32 (0..31)
        UNITS "db"
        MAX-ACCESS read-create
        STATUS current
        DESCRIPTION
                   "Maximum aggregate transmit power reduction per L2 request or L2 power trim.
                    Range: 0-31
	            Default: 3
                    Unit: db
                   "
        DEFVAL { 3 }
        ::= { hwadslLineExtConfProfileCfgEntry 29 }

    hwadsl2L2ModeTotalPowerValueCfg  OBJECT-TYPE
        SYNTAX Integer32 (0..31)
        UNITS "db"
        MAX-ACCESS read-create
        STATUS current
        DESCRIPTION
                   "Total maximum aggregate transmit power reduction in L2.
                    Range: 0-31
	            Default: 9
                    Unit: db
                   "
        DEFVAL { 9 }
        ::= { hwadslLineExtConfProfileCfgEntry 30 }

    hwadslExtUsPhyRcontrolCfg OBJECT-TYPE
        SYNTAX  INTEGER {
                            enable(1),
                            disable(2)
                        }
        MAX-ACCESS  read-write
        STATUS      current
        DESCRIPTION
                   "To enable or disable the PHY-R function on upstream direction.
                    Options:
                    1. enable(1)  - The PHY-R function on upstream direction is enabled
                    2. disable(2) - The PHY-R function on upstream direction is disabled
	            Default: disable(2)
                   "
        DEFVAL { disable }
        ::= { hwadslLineExtConfProfileCfgEntry 31 }

    hwadslExtUsINPmaxCfg OBJECT-TYPE
        SYNTAX      Adsl2SymbolProtection
        UNITS       "DMT Symbol"
        MAX-ACCESS  read-write
        STATUS      current
        DESCRIPTION
                   "Maximum Impulse Noise Protection on upstream direction.
                    The parameter can take the following values:
                    noProtection(1),
                    halfSymbol(2),
                    singleSymbol(3),
                    twoSymbols(4),
                    threeSymbols(5),
                    fourSymbols(6),
                    fiveSymbols(7),
                    sixSymbols(8),
                    sevenSymbols(9),
                    eightSymbols(10),
                    nineSymbols(11),
                    tenSymbols(12),
                    elevenSymbols(13),
                    twelveSymbols(14),
                    thirteenSymbols(15),
                    fourteenSymbols(16),
                    fifteenSymbols(17),
                    sixteenSymbols(18)

                    The value multiply 1/2 is the real value of Noise Protection values.

                    Default: 1
                    Unit: DMT Symbol
                   "
        DEFVAL { 1 }
        ::= { hwadslLineExtConfProfileCfgEntry 32 }

    hwadslExtUsMinRtxRatioCfg OBJECT-TYPE
        SYNTAX      Integer32 (0..255)
        UNITS       "1/256"
        MAX-ACCESS  read-write
        STATUS      current
        DESCRIPTION
                   "Minimum rtx ratio on upstream direction.
                    Range: 0-255
                    Default: 0
                    Unit: 1/256
                   "
        DEFVAL { 0 }
        ::= { hwadslLineExtConfProfileCfgEntry 33 }

    hwadslExtUsMinRSoverheadCfg OBJECT-TYPE
        SYNTAX      Integer32 (0..128)
        UNITS       "1/256"
        MAX-ACCESS  read-write
        STATUS      current
        DESCRIPTION
                   "The minimum value of R/N on upstream direction.
                    Range: 0-128
                    Default: 0
                    Unit: 1/256
                   "
        DEFVAL { 0 }
        ::= { hwadslLineExtConfProfileCfgEntry 34 }

    hwadslExtDsPhyRcontrolCfg OBJECT-TYPE
        SYNTAX  INTEGER {
                            enable(1),
                            disable(2)
                        }
        MAX-ACCESS  read-write
        STATUS      current
        DESCRIPTION
                   "To enable or disable the PHY-R function on downstream direction.
                    Options:
                    1. enable(1)  - The PHY-R function on downstream direction is enabled
                    2. disable(2) - The PHY-R function on downstream direction is disabled
	            Default: disable(2)
	           "
        DEFVAL { disable }
        ::= { hwadslLineExtConfProfileCfgEntry 35 }

    hwadslExtDsINPmaxCfg OBJECT-TYPE
        SYNTAX      Adsl2SymbolProtection
        UNITS       "DMT Symbol"
        MAX-ACCESS  read-write
        STATUS      current
        DESCRIPTION
                   "Maximum Impulse Noise Protection on downstream direction.
                    The parameter can take the following values:
                    noProtection(1),
                    halfSymbol(2),
                    singleSymbol(3),
                    twoSymbols(4),
                    threeSymbols(5),
                    fourSymbols(6),
                    fiveSymbols(7),
                    sixSymbols(8),
                    sevenSymbols(9),
                    eightSymbols(10),
                    nineSymbols(11),
                    tenSymbols(12),
                    elevenSymbols(13),
                    twelveSymbols(14),
                    thirteenSymbols(15),
                    fourteenSymbols(16),
                    fifteenSymbols(17),
                    sixteenSymbols(18)

                    The value multiply 1/2 is the real value of Noise Protection values.

                    Default: 1
                    Unit: DMT Symbol
                   "
        DEFVAL { 1 }
        ::= { hwadslLineExtConfProfileCfgEntry 36 }

    hwadslExtDsMinRtxRatioCfg OBJECT-TYPE
        SYNTAX      Integer32 (0..255)
        UNITS       "1/256"
        MAX-ACCESS  read-write
        STATUS      current
        DESCRIPTION
                   "Minimum rtx ratio on downstream direction.
                    Range: 0-255
	            Default: 0
                    Unit: 1/256
                   "
        DEFVAL { 0 }
        ::= { hwadslLineExtConfProfileCfgEntry 37 }

    hwadslExtDsMinRSoverheadCfg OBJECT-TYPE
        SYNTAX      Integer32 (0..128)
        UNITS       "1/256"
        MAX-ACCESS  read-write
        STATUS      current
        DESCRIPTION
                   "The minimum value of R/N on downstream direction.
                    Range: 0-128
	            Default: 0
                    Unit: 1/256
                   "
        DEFVAL { 0 }
        ::= { hwadslLineExtConfProfileCfgEntry 38 }

    hwadsl2TSSiPsdMaskUsCfg OBJECT-TYPE
        SYNTAX      Adsl2PsdMaskUs
        MAX-ACCESS  read-write
        STATUS      current
        DESCRIPTION
 		   "The upstream PSD mask applicable at the U-C2 reference
 		    point.
 		    This parameter is used only for G992.3 or G992.5 and it may impose PSD
 		    restrictions (breakpoints) in addition to the Limit PSD mask
 		    defined in G992.5.
 		    This is a string of 32 pairs of values in the following
  		    structure:
 		    Octets 0+1 - Index of 1st sub-carrier used in the context
 		                 of a first breakpoint.
 		    Octet 2    - The PSD reduction for the sub-carrier indicated in
 		                 octets 0 and 1.
 		    Octets 3-5 - Same, for a 2nd breakpoint.
 		    Octets 6-8 - Same, for a 3rd breakpoint.
 		    This architecture continues until octets 9-11, which are
 		    associated with a fourth breakpoint.
 		    Each subcarrier index is an unsigned number in the range 1 and
 		    NSCus.  Each PSD reduction value is in the range 0 (0dBm/Hz) to
 		    255 (-127.5dBm/Hz) with steps of 0.5dBm/Hz. Valid values are
 		    in the range 0 to 190 (0 to -95dBm/Hz).
 		    When the number of breakpoints is less than 4, all remaining
 		    octets are set to the value 0. Note that the content of this
 		    object should be correlated with the sub-carriers mask and with
 		    the RFI setup.
 		   "
        REFERENCE    "ITU-T G.997.1, paragraph 7.3.1.2"
        ::= { hwadslLineExtConfProfileCfgEntry 39 }

    hwadslLConfProfAdslModeCfg OBJECT-TYPE
        SYNTAX INTEGER {
                          defMode (1),
                          adsl (2),
                          adsl2Pots (3),
                          adsl2Isdn (4),
                          adsl2PlusPots (5),
                          adsl2PlusIsdn (6),
                          adsl2ReachExtended (7),
                          invalidValue(-1)
                       }
        MAX-ACCESS      read-write
        STATUS      current
        DESCRIPTION
                   "The ADSL2 management model specified includes an ADSL Mode
                    attribute which identifies an instance of ADSL Mode-Specific
                    PSD Configuration object in the ADSL Line Profile. The
                    following classes of ADSL operating mode are defined.
                    Options:
                    1. defMode(1)            - ADSL transmit mode is defMode
                    2. adsl(2)               - ADSL transmit mode is adsl
                    3. adsl2Pots(3)          - ADSL transmit mode is adsl2Pots
                    4. adsl2Isdn(4)          - ADSL transmit mode is adsl2Isdn
                    5. adsl2PlusPots(5)      - ADSL transmit mode is adsl2PlusPots
                    6. adsl2PlusIsdn(6)      - ADSL transmit mode is adsl2PlusIsdn
                    7. adsl2ReachExtended(7) - ADSL transmit mode is adsl2ReachExtended
                    8. invalidValue(-1)      - Invalid value
	           "
        ::= { hwadslLineExtConfProfileCfgEntry 40 }

    hwadslLineExtConfProfileRowStatusCfg OBJECT-TYPE
         SYNTAX          RowStatus
         MAX-ACCESS      read-create
         STATUS          current
         DESCRIPTION
                    "This object is used to create a new row or modify or
                     delete an existing row in this table.
                     A profile activated by setting this object to
                     'active'. When 'active' is set, the system
                     will validate the profile.

                     Before a profile can be deleted or taken out of
                     service, (by setting this object to 'destroy' or
                     'outOfService') it must be first unreferenced
                     from all associated lines.

                     If the implementator of this MIB has chosen not
                     to implement 'dynamic assignment' of profiles, this
                     object's MIN-ACCESS is read-only and its value
                     is always to be 'active'.
                    "
       ::= { hwadslLineExtConfProfileCfgEntry 41 }

    hwadsl2L2ModeL2TimeCfg OBJECT-TYPE
        SYNTAX Integer32 (0..255)
        UNITS "seconds"
        MAX-ACCESS read-create
        STATUS current
        DESCRIPTION
                   "This minimum time (in seconds) between an entry into the
                    L2 state and the first power trim in the L2 state and between
                    two consecutive power trims in the L2 State.
                    It ranges from 0 to 255 seconds.
                    Range: 0-255
	            Default: 30
                    Unit: seconds
                   "
        DEFVAL { 30 }
        ::= { hwadslLineExtConfProfileCfgEntry 42 }

    hwadslLineExtConfProfRtxModeDs  OBJECT-TYPE
        SYNTAX      INTEGER
                    {
                     forbidden(0),
                     preferred(1),
                     forced(2),
                     testmode(3)
                    }
        MAX-ACCESS  read-create
        STATUS      current
        DESCRIPTION
            "The mode of operation of G.998.4 retransmission in downstream direction.
             Options:
             1. forbidden(0)   - G.998.4 retransmission not allowed.
             2. preferred(1)   - G.998.4 retransmission is preferred.
             3. forced(2)      - Force the use of the G.998.4 retransmission.
             4. testmode(3)    - Force the use of the G.998.4 retransmission in test mode.
            "
        REFERENCE    "ITU-T G.997.1, paragraph 7.3.1.11"
        DEFVAL       { forbidden }
        ::= { hwadslLineExtConfProfileCfgEntry 43 }

    hwadslLineExtConfProfLeftrThreshDs  OBJECT-TYPE
        SYNTAX      Unsigned32(0..99)
        UNITS       "0.01"
        MAX-ACCESS  read-create
        STATUS      current
        DESCRIPTION
            "If retransmission is used in downstream direction, this parameter specifies the
             threshold for declaring a near-end leftr defect. The value is coded as a fraction of the
             NDR with valid range from 0.01 to 0.99 with increments of 0.01. A special value means the
             ETR shall be used as the default threshold for declaring a leftr defect.
            "
        REFERENCE    "ITU-T G.997.1, paragraph 7.3.1.12"
        DEFVAL       { 0 }
        ::= { hwadslLineExtConfProfileCfgEntry 44 }

    hwadslLineExtConfProfMinEtrRtxDs  OBJECT-TYPE
        SYNTAX      Unsigned32(32000..32000000)
        UNITS       "bits/second"
        MAX-ACCESS  read-create
        STATUS      current
        DESCRIPTION
           "If retransmission is used in downstream direction, this parameter specifies the
            minimum expected throughput for the bearer channel.The values range in steps of
            1000 bit/s.
           "
        REFERENCE    "ITU-T G.997.1, paragraph 7.3.2.1.8"
        ::= { hwadslLineExtConfProfileCfgEntry 45 }

    hwadslLineExtConfProfMaxEtrRtxDs  OBJECT-TYPE
        SYNTAX      Unsigned32(32000..32000000)
        UNITS       "bits/second"
        MAX-ACCESS  read-create
        STATUS      current
        DESCRIPTION
           "If retransmission is used in downstream direction, this parameter specifies the
            maxmum expected throughput for the bearer channel.The values range in steps of
            1000 bit/s.
           "
        REFERENCE    "ITU-T G.997.1, paragraph 7.3.2.1.9"
        ::= { hwadslLineExtConfProfileCfgEntry 46 }

    hwadslLineExtConfProfMaxNdrRtxDs  OBJECT-TYPE
        SYNTAX      Unsigned32(32000..32000000)
        UNITS       "bits/second"
        MAX-ACCESS  read-create
        STATUS      current
        DESCRIPTION
           "If retransmission is used in downstream direction, this parameter specifies the
            maximum net data rate for the bearer channel. The values range in steps of 1000 bit/s.
           "
        REFERENCE    "ITU-T G.997.1, paragraph 7.3.2.1.10"
        ::= { hwadslLineExtConfProfileCfgEntry 47 }

    hwadslLineExtConfProfMaxDelayRtxDs  OBJECT-TYPE
        SYNTAX      Unsigned32(1..63)
        UNITS       "milliseconds"
        MAX-ACCESS  read-create
        STATUS      current
        DESCRIPTION
           "If retransmission is used in downstream direction, this parameter specifies
            the maximum for the instantaneous delay due to the effect of retransmission only
            (see G.998.4 for detailed specification). The delay ranges from 1 to 63 ms by steps of 1 ms.
            Unit: milliseconds
           "
        REFERENCE    "ITU-T G.997.1, paragraph 7.3.2.11"
        ::= { hwadslLineExtConfProfileCfgEntry 48 }

    hwadslLineExtConfProfMinDelayRtxDs  OBJECT-TYPE
        SYNTAX      Unsigned32(0..63)
        UNITS       "milliseconds"
        MAX-ACCESS  read-create
        STATUS      current
        DESCRIPTION
           "If retransmission is used in downstream direction, this parameter specifies
            the minimum for the instantaneous delay due to the effect of retransmission only
            (see G.998.4 for detailed specification). The delay ranges from 0 to 63 ms by steps of 1 ms.
            Unit: milliseconds
           "
        REFERENCE    "ITU-T G.997.1, paragraph 7.3.2.12"
        ::= { hwadslLineExtConfProfileCfgEntry 49 }

    hwadslLineExtConfProfMinInpShineRtxDs  OBJECT-TYPE
        SYNTAX      Unsigned32(0..63)
        UNITS       "symbols"
        MAX-ACCESS  read-create
        STATUS      current
        DESCRIPTION
           "If retransmission is used in downstream direction, this parameter specifies
            the minimum impulse noise protection against SHINE for the bearer channel if it is
            transported over DMT symbols with a subcarrier spacing of 4.3125 kHz. The impulse
            noise protection is expressed in DMT symbols with a subcarrier spacing of 4.3125 kHz
            and can take any integer value from 0 to 63, inclusive.
            Unit: symbols
           "
        REFERENCE    "ITU-T G.997.1, paragraph 7.3.2.13"
        DEFVAL       { 0 }
        ::= { hwadslLineExtConfProfileCfgEntry 50 }

    hwadslLineExtConfProfShineRatioRtxDs  OBJECT-TYPE
        SYNTAX      Unsigned32(0..100)
        MAX-ACCESS  read-create
        STATUS      current
        DESCRIPTION
           "If retransmission is used in downstream direction, this parameter specifies
            the SHINE ratio (detailed definition see G.998.4).
            The values range from 0 to 0.100 in increments of 0.001.
           "
        REFERENCE    "ITU-T G.997.1, paragraph 7.3.2.15"
        DEFVAL       { 0 }
        ::= { hwadslLineExtConfProfileCfgEntry 51 }

    hwadslLineExtConfProfMinInpReinRtxDs  OBJECT-TYPE
        SYNTAX      Unsigned32(0..7)
        MAX-ACCESS  read-create
        STATUS      current
        DESCRIPTION
           "If retransmission is used in downstream direction, this parameter specifies
            the minimum impulse noise protection against REIN for the bearer channel if it is
            transported over DMT symbols with a subcarrier spacing of 4.3125 kHz. The impulse
            noise protection is expressed in DMT symbols with a subcarrier spacing of 4.3125 kHz
            and can take any integer value from 0 to 7, inclusive.
           "
        REFERENCE    "ITU-T G.997.1, paragraph 7.3.2.16"
        DEFVAL       { 0 }
        ::= { hwadslLineExtConfProfileCfgEntry 52 }

    hwadslLineExtConfProfIatReinRtxDs  OBJECT-TYPE
        SYNTAX      INTEGER
                    {
                         frequency100Hz(0),
                         frequency120Hz(1)
                    }
        MAX-ACCESS  read-create
        STATUS      current
        DESCRIPTION
           "If retransmission is used in downstream direction, this parameter specifies
            the inter-arrival time that shall be assumed for REIN protection.
            Options:
            1. frequency100Hz(0)   - an inter-arrival time derived from a REIN at 100 Hz
            2. frequency120Hz(1)   - an inter-arrival time derived from a REIN at 120 Hz
           "
        REFERENCE    "ITU-T G.997.1, paragraph 7.3.2.18"
        DEFVAL       { frequency100Hz }
        ::= { hwadslLineExtConfProfileCfgEntry 53 }

    hwadsl2LExtLineProfReferenceClock OBJECT-TYPE
        SYNTAX  INTEGER
                {
                    freeRun(1),
                    system(2)
                }
        MAX-ACCESS  read-create
        STATUS      current
        DESCRIPTION
            "This object configures the clock reference for the ATU-C
             in an ADSL line. Represented as an enumeration.
             Options:
             1. freeRun(1) - Indicates the local clock
             2. system(2)  - Indicates the system clock
            "
        DEFVAL       { freeRun }
        ::= { hwadslLineExtConfProfileCfgEntry 54 }

    hwadsl2LExtLineProfRfiBands    OBJECT-TYPE
        SYNTAX       OCTET STRING (SIZE(0..16))
        MAX-ACCESS  read-create
        STATUS      current
        DESCRIPTION
            "The RFI notch parameter.
             It is a string consist of begin tone index,
             end tone index.
             This is a string of 4 groups of values in the following
             structure:
             Octets 0+1  - Index of start sub-carrier used in the context
                           of a first group
             Octets 2+3  - Index of end sub-carrier used in the context
                           of a first group
             Octets 4-7 - Same, for a 2nd group
             This architecture continues until octets 12-15, which are
             associated with a 4th group.It can contain as most as 4 groups.
            "
        ::= { hwadslLineExtConfProfileCfgEntry 55 }

    hwadsl2LExtLineProfDpboEPsd  OBJECT-TYPE
        SYNTAX      OCTET STRING (SIZE(0..48))
        MAX-ACCESS  read-create
        STATUS      current
        DESCRIPTION
            "This parameter defines the PSD mask that is assumed to be permitted at the exchange.
             This parameter shall use the same format as PSDMASKds.The maximum number of breakpoints
             for DPBOEPSD is 16.
             This is a string of 16 pairs of values in the following
             structure:
             Octets 0+1 - Index of 1st sub-carrier used in the context
                          of a first breakpoint.
             Octet 2    - The PSD reduction for the sub-carrier indicated in
                          octets 0 and 1
             Octets 3-5 - Same, for a 2nd breakpoint
             Octets 6-8 - Same, for a 3rd breakpoint
             This architecture continues until octets 45-47, which are
             associated with a 16th breakpoint.
             Each subcarrier index is an unsigned number in the range 1 and
             NSCds.  Each PSD reduction value is in the range 0 (0dBm/Hz) to
             255 (-127.5dBm/Hz) with steps of 0.5dBm/Hz. Valid values are
             in the range 0 to 190 (0 to -95dBm/Hz).
             When the number of breakpoints is less than 16, all remaining
             octets are set to the value 0xff.
            "
        REFERENCE    "ITU-T G.997.1(200604), paragraph 7.3.1.2.13"
        ::= { hwadslLineExtConfProfileCfgEntry 56 }

    hwadsl2LExtLineProfDpboEsEL OBJECT-TYPE
        SYNTAX      Unsigned32 (0..511)
        UNITS       "0.5dB"
        MAX-ACCESS  read-create
        STATUS      current
        DESCRIPTION
            "This configuration parameter defines the assumed electrical length of
             cables (E-side cables) connecting exchange based DSL services to a remote
             flexibility point (cabinet), that hosts the xTU-C that is subject to
             spectrally shaped downstream power back-off depending on this length.
             For this parameter the electrical length is defined as the loss (in dB)
             of an equivalent length of hypothetical cable at a reference frequency
             defined by the network operator or in spectrum management regulations.
             DPBOESEL shall be coded as an unsigned integer representing an electrical
             length from 0 dB (coded as 0) to 255.5 dB (coded as 511) in steps of 0.5 dB.
             All values in the range are valid.If DPBOESEL is set to zero, the DPBO in
             this section shall be disabled.
            "
        REFERENCE    "ITU-T G.997.1(200604), paragraph 7.3.1.2.13"
        DEFVAL       { 0 }
        ::= { hwadslLineExtConfProfileCfgEntry 57 }

    hwadsl2LExtLineProfDpboEselMin OBJECT-TYPE
        SYNTAX      Unsigned32 (0..511)
        UNITS       "0.5dB"
        MAX-ACCESS  read-create
        STATUS      current
        DESCRIPTION
            "DPBOESELMIN in dB is the minimum of all main cable losses for the KVz supplied when using
             the SOL model (expansion of a KVz and ADSL2 provision of additional KVz areas from this KVz
             using cross-cables to additional KVz), including the KVz at the MSAN site. This value must
             be adjustable as the minimum requirement via the SNMP interface in the configuration profile
             for each ADSL2 port, and is set individually for each MSAN site and usage. As an option,
             adjustment can be done for each MSAN or line card, thus taking effect for
             entire port groups. It is used only for determining the MUF.
            "
        DEFVAL       { 0 }
        ::= { hwadslLineExtConfProfileCfgEntry 58 }

    hwadsl2LExtLineProfDpboEsCableModelA  OBJECT-TYPE
        SYNTAX      Unsigned32 (0..640)
        MAX-ACCESS  read-create
        STATUS      current
        DESCRIPTION
            "This configuration parameter defines a cable model in terms of three scalars
             DPBOESCMA, DPBOESCMB and DPBOESCMC that shall be used to describe the frequency
             dependent loss of E-side cables.Parameters DPBOESCMA, DPBOESCMB, DPBOESCMC shall be
             coded as unsigned integers representing a scalar value from -1 (coded as 0) to 1.5
             (coded as 640) in step of 1/256. All values in the range are valid.
            "
        REFERENCE    "ITU-T G.997.1(200604), paragraph 7.3.1.2.13"
        DEFVAL       { 256 }
        ::= { hwadslLineExtConfProfileCfgEntry 59 }

    hwadsl2LExtLineProfDpboEsCableModelB   OBJECT-TYPE
        SYNTAX      Unsigned32 (0..640)
        MAX-ACCESS  read-create
        STATUS      current
        DESCRIPTION
            "This configuration parameter defines a cable model in terms of three scalars
             DPBOESCMA, DPBOESCMB and DPBOESCMC that shall be used to describe the frequency
             dependent loss of E-side cables.Parameters DPBOESCMA, DPBOESCMB, DPBOESCMC shall be
             coded as unsigned integers representing a scalar value from -1 (coded as 0) to 1.5
             (coded as 640) in step of 1/256. All values in the range are valid.
            "
        REFERENCE    "ITU-T G.997.1(200604), paragraph 7.3.1.2.13"
        DEFVAL       { 512 }
        ::= { hwadslLineExtConfProfileCfgEntry 60 }

    hwadsl2LExtLineProfDpboEsCableModelC  OBJECT-TYPE
        SYNTAX      Unsigned32 (0..640)
        MAX-ACCESS  read-create
        STATUS      current
        DESCRIPTION
            "This configuration parameter defines a cable model in terms of three scalars
             DPBOESCMA, DPBOESCMB and DPBOESCMC that shall be used to describe the frequency
             dependent loss of E-side cables.Parameters DPBOESCMA, DPBOESCMB, DPBOESCMC shall be
             coded as unsigned integers representing a scalar value from -1 (coded as 0) to 1.5
             (coded as 640) in step of 1/256. All values in the range are valid.
            "
        REFERENCE    "ITU-T G.997.1(200604), paragraph 7.3.1.2.13"
        DEFVAL       { 256 }
        ::= { hwadslLineExtConfProfileCfgEntry 61 }

    hwadsl2LExtLineProfDpboMus    OBJECT-TYPE
        SYNTAX      Unsigned32 (0..255)
        UNITS       "0.5dBm/Hz"
        MAX-ACCESS  read-create
        STATUS      current
        DESCRIPTION
            "DPBOMUS defines the assumed minimum usable receive signal PSD (in dBm/Hz) for
             exchange based services, used to modify parameter DPBOFMAX defined below. It
             shall be coded as an unsigned integer representing a PSD level from 0 dBm/Hz
             (coded as 0) to -127.5 dBm/Hz (coded as 255) in steps of 0.5 dBm/Hz.
             All values in the range are valid.
            "
        REFERENCE    "ITU-T G.997.1(200604), paragraph 7.3.1.2.13"
        DEFVAL       { 180 }
        ::= { hwadslLineExtConfProfileCfgEntry 62 }

    hwadsl2LExtLineProfDpboFMin  OBJECT-TYPE
        SYNTAX      Unsigned32 (0..511)
        UNITS       "4.3125 KHz"
        MAX-ACCESS  read-create
        STATUS      current
        DESCRIPTION
            "DPBOFMIN defines the minimum frequency from which the DPBO shall be applied.
             It shall be coded as a 16 bits unsigned integer representing a frequency in
             multiple of 4.3125 KHz. The range of valid values is from 0 kHz (coded as 0)
             to 2203.6875 kHz (coded as 511).
            "
        REFERENCE    "ITU-T G.997.1(200604), paragraph 7.3.1.2.13"
        DEFVAL       { 0 }
        ::= { hwadslLineExtConfProfileCfgEntry 63 }

    hwadsl2LExtLineProfDpboFMax  OBJECT-TYPE
        SYNTAX      Unsigned32 (32..511)
        UNITS       "4.3125 KHz"
        MAX-ACCESS  read-create
        STATUS      current
        DESCRIPTION
            "DPBOFMAX defines the maximum frequency at which DPBO may be applied. It shall be
             coded as a 16 bits unsigned integer representing a frequency in multiple of 4.3125 KHz.
             The range of valid values is from 138 kHz (coded as 32) to 2203.6875 kHz (coded as 511).
            "
        REFERENCE    "ITU-T G.997.1(200604), paragraph 7.3.1.2.13"
        DEFVAL       { 511 }
        ::= { hwadslLineExtConfProfileCfgEntry 64 }

    hwadsl2LExtLineProfMaxNomPsdUs OBJECT-TYPE
        SYNTAX      Integer32  (-60..-30)
        UNITS       "dBm/Hz"
        MAX-ACCESS  read-create
        STATUS      current
        DESCRIPTION
		   "Maximum PSD margin in upstream."
        DEFVAL { -38 }
        ::= { hwadslLineExtConfProfileCfgEntry 65 }

    hwadsl2LExtLineProfMaxNomAtpDs OBJECT-TYPE
        SYNTAX      Unsigned32 (0..255)
        UNITS       "0.1 dBm"
        MAX-ACCESS  read-create
        STATUS      current
        DESCRIPTION
           "The maximum nominal aggregate transmit power in the
            downstream direction during initialization and showtime. It
            ranges from 0 to 255 units of 0.1 dBm (physical values are 0
            to 25.5 dBm)."
        REFERENCE    "ITU-T G.997.1, paragraph 7.3.1.2"
        DEFVAL       { 204 }
        ::= { hwadslLineExtConfProfileCfgEntry 66 }

    hwadsl2LExtLineProfMaxNomAtpUs  OBJECT-TYPE
        SYNTAX      Unsigned32 (0..255)
        UNITS       "0.1 dBm"
        MAX-ACCESS  read-create
        STATUS      current
        DESCRIPTION
           "The maximum nominal aggregate transmit power in the upstream
            direction during initialization and showtime. It ranges from
            0 to 255 units of 0.1 dBm (physical values are 0 to 25.5
            dBm)."
        REFERENCE    "ITU-T G.997.1, paragraph 7.3.1.2"
        DEFVAL       { 125 }
        ::= { hwadslLineExtConfProfileCfgEntry 67 }

    hwadsl2LExtLineProfInmIatoDs   OBJECT-TYPE
        SYNTAX      Unsigned32(3..511)
        MAX-ACCESS  read-create
        STATUS      current
        DESCRIPTION
            "The parameter of downstream impulse noise monitoring inter arrival time offset.
             This is the inter arrival time offset that the xTU receiver shall use to determine
             in which bin of the inter arrival time histogram the IAT is reported.
             The valid values for INMIATO ranges from 3 to 511 DMT symbols in steps of 1 DMT symbol.
            "
        REFERENCE    "ITU-T G.997.1, paragraph 7.3.1.9.1"
        DEFVAL       { 3 }
        ::= { hwadslLineExtConfProfileCfgEntry 68 }

    hwadsl2LExtLineProfInmIatsDs  OBJECT-TYPE
        SYNTAX      Unsigned32(0..7)
        MAX-ACCESS  read-create
        STATUS      current
        DESCRIPTION
            "The parameter of downstream impulse noise monitoring inter arrival time step.
             This is the inter arrival time step that the xTU receiver shall use to determine
             in which bin of the inter arrival time histogram the IAT is reported.
             The valid values for INMIATS ranges from 0 to 7 in steps of 1.
            "
        REFERENCE    "ITU-T G.997.1, paragraph 7.3.1.9.2"
        DEFVAL       { 0 }
        ::= { hwadslLineExtConfProfileCfgEntry 69 }

    hwadsl2LExtLineProfInmCcDs  OBJECT-TYPE
        SYNTAX      Unsigned32(0..64)
        MAX-ACCESS  read-create
        STATUS      current
        DESCRIPTION
            "The parameter of downstream impulse noise monitoring cluster continuation value.
             This is the cluster continuation value that the xTU receiver shall use
             in the cluster indication process described in the relevant ITU-T Recommendation.
             The valid values for INMCC range from 0 to 64 DMT symbols in steps of 1 DMT symbol.
            "
        REFERENCE    "ITU-T G.997.1, paragraph 7.3.1.9.3"
        DEFVAL       { 0 }
        ::= { hwadslLineExtConfProfileCfgEntry 70 }

    hwadsl2LExtLineProfInmInpeqModeDs   OBJECT-TYPE
        SYNTAX      Unsigned32(0..4)
        MAX-ACCESS  read-create
        STATUS      current
        DESCRIPTION
            "The parameter of downstream impulse noise monitoring equivalent impulse noise protect mode.
             This is the INM Equivalent INP Mode that the xTU receiver shall use in the computation of the Equivalent INP,
             as defined in the relevant ITU-T Recommendation. The valid values for INM_INPEQ_MODE are 0, 1, 2, 3, and 4.
            "
        REFERENCE    "ITU-T G.997.1, paragraph 7.3.1.9.4"
        DEFVAL       { 0 }
        ::= { hwadslLineExtConfProfileCfgEntry 71 }

    hwadsl2LExtLineProfForceInpDs  OBJECT-TYPE
        SYNTAX TruthValue
        MAX-ACCESS  read-create
        STATUS      current
        DESCRIPTION
            "The parameter indicates that the framer settings of the upstream bearer
             shall be selected such that the impulse noise protection computed according
             to the formula specified in the relevant recommendation is greater than or
             equal to the minimal impulse noise protection requirement. This flag shall
             have the same value for all the bearers of one line in the same direction.
            "
        DEFVAL       { false }
        ::= { hwadslLineExtConfProfileCfgEntry 72 }

    hwadsl2LExtLineProfForceInpUs  OBJECT-TYPE
        SYNTAX  TruthValue
        MAX-ACCESS  read-create
        STATUS      current
        DESCRIPTION
            "The parameter indicates that the framer settings of the upstream bearer
             shall be selected such that the impulse noise protection computed according
             to the formula specified in the relevant recommendation is greater than or
             equal to the minimal impulse noise protection requirement. This flag shall
             have the same value for all the bearers of one line in the same direction.
            "
        DEFVAL       { false }
        ::= { hwadslLineExtConfProfileCfgEntry 73 }

    hwadsl2LExtLineProfInitPolicy   OBJECT-TYPE
        SYNTAX INTEGER
               {
                   policy0(1),
                   policy1(2),
                   policy2(3)
               }
        MAX-ACCESS read-create
        STATUS current
        DESCRIPTION
            "If retransmission is not used in a given transmit direction, this parameter indicates
             which policy shall be applied to determine the transceiver configuration parameters at
             initialization. The valid values for CIPOLICY are 0,1 and 2.
             Those policies are defined in the respective recommendations.
             Options:
             1. policy0 (1)      - Policy 0 according to the applicable standard
             2. policy1 (2)      - Policy 1 according to the applicable standard
             3. policy2 (3)      - Policy 2 according to the applicable standard
            "
        REFERENCE
            "ITU-T G.997.1 Amendment 1, paragraph #7.3.2.10 (CIPOLICY)"
        DEFVAL { policy0 }
        ::= { hwadslLineExtConfProfileCfgEntry 74 }

    hwadsl2LExtLineProfL3Time OBJECT-TYPE
        SYNTAX      Unsigned32 (0..65535)
        UNITS       "seconds"
        MAX-ACCESS  read-create
        STATUS      current
        DESCRIPTION
            "This minimum time (in seconds) between an entry into the
             L3 state and the L0 or L2 state.
            "
        DEFVAL       { 255 }
        ::= { hwadslLineExtConfProfileCfgEntry 75 }

    hwadsl2LExtLineProfL3ModeState OBJECT-TYPE
        SYNTAX INTEGER {
                           enabled(1),
                           disabled(2)
                       }
        MAX-ACCESS read-create
        STATUS current
        DESCRIPTION
            "Power management state enabling. The state of L3 power management mode.
             Options:
             1. enabled(1)  - The L3 power management mode is enabled
             2. disabled(2) - The L3 power management mode is disabled
            "
        DEFVAL { disabled }
        ::= { hwadslLineExtConfProfileCfgEntry 76 }

-- hwAdslLineLatestActParaInfoTable

    hwAdslLineLatestActParaInfoTable OBJECT-TYPE
        SYNTAX SEQUENCE OF HwAdslLineLatestActParaInfoEntry
        MAX-ACCESS not-accessible
        STATUS current
        DESCRIPTION
                   "This table provides one row for each ADSL port.
                    Each row contains the latest actived parameters.
                    The index of this table is ifIndex.
                   "
        ::= { hwAdslMibObjects 14 }

    hwAdslLineLatestActParaInfoEntry OBJECT-TYPE
        SYNTAX HwAdslLineLatestActParaInfoEntry
        MAX-ACCESS not-accessible
        STATUS current
        DESCRIPTION
                   "This table provides one row for each ADSL port.
                    Each row contains the latest actived parameters.
                    The index of this entry is ifIndex.
                   "
        INDEX { ifIndex }
        ::= { hwAdslLineLatestActParaInfoTable 1 }

    HwAdslLineLatestActParaInfoEntry ::=
        SEQUENCE {
                     hwAdslLineLatestActiveTimeInfo             DateAndTime,
                     hwAdslLineLatestDeactiveTimeInfo           DateAndTime,
                     hwAdslAtucLatestTxRateInfo                 Gauge32,
                     hwAdslAturLatestTxRateInfo                 Gauge32,
                     hwAdslAtucLatestSnrMgnInfo                 Integer32,
                     hwAdslAturLatestSnrMgnInfo                 Integer32,
                     hwAdslAtucLatestAtnInfo                    Gauge32,
                     hwAdslAturLatestAtnInfo                    Gauge32,
                     hwAdslAtucLatestAttainableRateInfo         Gauge32,
                     hwAdslAturLatestAttainableRateInfo         Gauge32,
                     hwAdslAtucLatestConfTxRateInfo             Gauge32,
                     hwAdslAturLatestConfTxRateInfo             Gauge32,
                     hwAdslAtucLatestInterleaveDelayInfo        Gauge32,
                     hwAdslAturLatestInterleaveDelayInfo        Gauge32,
                     hwAdslAtucLatestTargetSnrMgnInfo           Integer32,
                     hwAdslAturLatestTargetSnrMgnInfo           Integer32,
                     hwAdslAtucLatestTxRateThresholdInfo        Gauge32,
                     hwAdslAturLatestTxRateThresholdInfo	Gauge32
                 }

    hwAdslLineLatestActiveTimeInfo OBJECT-TYPE
        SYNTAX      DateAndTime
        MAX-ACCESS  read-only
        STATUS      current
        DESCRIPTION
                   "Actual time when latest actived."
        ::= { hwAdslLineLatestActParaInfoEntry 1 }

    hwAdslLineLatestDeactiveTimeInfo OBJECT-TYPE
        SYNTAX      DateAndTime
        MAX-ACCESS  read-only
        STATUS      current
        DESCRIPTION
                   "Actual time when latest deactived. If port is actived, the value is invalid."
        ::= { hwAdslLineLatestActParaInfoEntry 2 }

    hwAdslAtucLatestTxRateInfo  OBJECT-TYPE
        SYNTAX      Gauge32
        UNITS       "bps"
        MAX-ACCESS  read-only
        STATUS      current
        DESCRIPTION
                   "Actual transmit rate on this channel when latest actived.
                    Unit: bps
                   "
        ::= { hwAdslLineLatestActParaInfoEntry 3 }

    hwAdslAturLatestTxRateInfo  OBJECT-TYPE
        SYNTAX      Gauge32
        UNITS       "bps"
        MAX-ACCESS  read-only
        STATUS      current
        DESCRIPTION
                   "Actual transmit rate on this channel when latest actived.
                    Unit: bps
                   "
        ::= { hwAdslLineLatestActParaInfoEntry 4 }

    hwAdslAtucLatestSnrMgnInfo OBJECT-TYPE
        SYNTAX Integer32
        UNITS "tenth dB"
        MAX-ACCESS read-only
        STATUS current
        DESCRIPTION
                   "Noise Margin as seen by this ATU-C at the time of the last adslAtucRateChangeTrap event.
                    Unit: tenth dB.
                   "
        ::= { hwAdslLineLatestActParaInfoEntry 5 }

    hwAdslAturLatestSnrMgnInfo OBJECT-TYPE
        SYNTAX Integer32
        UNITS "tenth dB"
        MAX-ACCESS read-only
        STATUS current
        DESCRIPTION
                   "Noise Margin as seen by this ATU-R at the time of the last adslAtucRateChangeTrap event.
                    Unit: tenth dB.
                   "
        ::= { hwAdslLineLatestActParaInfoEntry 6 }

    hwAdslAtucLatestAtnInfo OBJECT-TYPE
        SYNTAX Gauge32
        UNITS "tenth dB"
        MAX-ACCESS read-only
        STATUS current
        DESCRIPTION
                   "Measured difference in the total power transmitted as seen by this ATU-C at the time of the last adslAtucRateChangeTrap event.
                    Unit: tenth dB.
                   "
        ::= { hwAdslLineLatestActParaInfoEntry 7 }

    hwAdslAturLatestAtnInfo OBJECT-TYPE
        SYNTAX Gauge32
        UNITS "tenth dB"
        MAX-ACCESS read-only
        STATUS current
        DESCRIPTION
                   "Measured difference in the total power transmitted as seen by this ATU-R at the time of the last adslAtucRateChangeTrap event.
                    Unit: tenth dB.
                   "
        ::= { hwAdslLineLatestActParaInfoEntry 8 }

    hwAdslAtucLatestAttainableRateInfo OBJECT-TYPE
        SYNTAX Gauge32
        UNITS "bps"
        MAX-ACCESS read-only
        STATUS current
        DESCRIPTION
                   "Indicates the maximum attainable data rate by the ATU-C at the time of the last adslAtucRateChangeTrap event.
                    Unit: bps
                   "
        ::= { hwAdslLineLatestActParaInfoEntry 9 }

    hwAdslAturLatestAttainableRateInfo OBJECT-TYPE
        SYNTAX Gauge32
        UNITS "bps"
        MAX-ACCESS read-only
        STATUS current
        DESCRIPTION
                   "Indicates the maximum attainable data rate by the ATU-R at the time of the last adslAtucRateChangeTrap event.
                    Unit: bps
                   "
        ::= { hwAdslLineLatestActParaInfoEntry 10 }

    hwAdslAtucLatestConfTxRateInfo  OBJECT-TYPE
        SYNTAX      Gauge32
        UNITS       "bps"
        MAX-ACCESS  read-only
        STATUS      current
        DESCRIPTION
                   "Configured transmit rate for ADSL port. See adslAtucConfRateChanRatio for information
                    regarding RADSL mode and ATUR transmit rate for ATUC receive rates.
                    Unit: bps.
                   "
        ::= { hwAdslLineLatestActParaInfoEntry 11 }

    hwAdslAturLatestConfTxRateInfo  OBJECT-TYPE
        SYNTAX      Gauge32
        UNITS       "bps"
        MAX-ACCESS  read-only
        STATUS      current
        DESCRIPTION
                   "Configured receive rate for ADSL port. See adslAtucConfRateChanRatio for information
                    regarding RADSL mode and ATUR transmit rate for ATUC receive rates.
                    Unit: bps.
                   "
        ::= { hwAdslLineLatestActParaInfoEntry 12 }

    hwAdslAtucLatestInterleaveDelayInfo OBJECT-TYPE
        SYNTAX      Gauge32
        UNITS       "milliseconds"
        MAX-ACCESS  read-only
        STATUS      current
        DESCRIPTION
                   "Interleave delay for this channel when latest actived.
                    Unit: milliseconds
                   "
        ::= { hwAdslLineLatestActParaInfoEntry 13 }

    hwAdslAturLatestInterleaveDelayInfo OBJECT-TYPE
        SYNTAX      Gauge32
        UNITS       "milliseconds"
        MAX-ACCESS  read-only
        STATUS      current
        DESCRIPTION
                   "Interleave delay for this channel when latest actived.
                    Unit: milliseconds
                   "
        ::= { hwAdslLineLatestActParaInfoEntry 14 }

    hwAdslAtucLatestTargetSnrMgnInfo OBJECT-TYPE
        SYNTAX      Integer32 (0..310)
        UNITS       "tenth dB"
        MAX-ACCESS  read-only
        STATUS      current
        DESCRIPTION
                   "Port Signal/Noise Margin.
                    Range: 0-310
                    Unit: tenth dB
                   "
        ::= { hwAdslLineLatestActParaInfoEntry 15 }

    hwAdslAturLatestTargetSnrMgnInfo OBJECT-TYPE
        SYNTAX      Integer32 (0..310)
        UNITS       "tenth dB"
        MAX-ACCESS  read-only
        STATUS      current
        DESCRIPTION
                   "Port Signal/Noise Margin.
                    Range: 0-310
                    Unit: tenth dB
                   "
        ::= { hwAdslLineLatestActParaInfoEntry 16 }

    hwAdslAtucLatestTxRateThresholdInfo OBJECT-TYPE
        SYNTAX Gauge32
        UNITS "bps"
        MAX-ACCESS read-only
        STATUS      current
        DESCRIPTION
                   "Port down stream threshold.
                    Unit: bps
                   "
        ::= { hwAdslLineLatestActParaInfoEntry 17 }

    hwAdslAturLatestTxRateThresholdInfo OBJECT-TYPE
        SYNTAX Gauge32
        UNITS "bps"
        MAX-ACCESS read-only
        STATUS      current
        DESCRIPTION
                   "Port up stream threshold.
                    Unit: bps
                   "
        ::= { hwAdslLineLatestActParaInfoEntry 18 }

--  hwXdslPortPerformanceStatInfoTable

    hwXdslPortPerformanceStatInfoTable OBJECT-TYPE
        SYNTAX SEQUENCE OF HwXdslPortPerformanceStatInfoEntry
        MAX-ACCESS not-accessible
        STATUS current
        DESCRIPTION
                   "XDSL port performance staticstic table.
                    The indexes of this table are ifIndex and hwXdslPort15minutesPerformanceIntervalInfo.
                   "
        ::= { hwAdslMibObjects 15 }

    hwXdslPortPerformanceStatInfoEntry OBJECT-TYPE
        SYNTAX HwXdslPortPerformanceStatInfoEntry
        MAX-ACCESS not-accessible
        STATUS current
        DESCRIPTION
                   "XDSL port performance staticstic table.
                    The indexes of this entry are ifIndex and hwXdslPort15minutesPerformanceIntervalInfo.
                   "
        INDEX {ifIndex, hwXdslPort15minutesPerformanceIntervalInfo }
        ::= { hwXdslPortPerformanceStatInfoTable 1 }

    HwXdslPortPerformanceStatInfoEntry ::=
        SEQUENCE {
                     hwXdslPort15minutesPerformanceIntervalInfo          Integer32,
                     hwXdslPort15minutesPerformanceInBytesInfo           Counter32,
                     hwXdslPort15minutesPerformanceOutBytesInfo          Counter32,
                     hwXdslPortSyncSuccNumberInfo                        Counter32,
                     hwXdslPortSyncFailNumberInfo                        Counter32,
                     hwXdslPortAtucCodeViolationInfo                     Counter32,
                     hwXdslPortAturCodeViolationInfo                     Counter32,
                     hwXdslPortAtucFecSecondsInfo                        Counter32,
                     hwXdslPortAturFecSecondsInfo                        Counter32,
                     hwXdslPortCurrent15minutesStatTimeInfo              Counter32
                 }

    hwXdslPort15minutesPerformanceIntervalInfo OBJECT-TYPE
        SYNTAX Integer32(0..96)
        MAX-ACCESS not-accessible
        STATUS current
        DESCRIPTION
                   "The index of the interval which is queried.
                    Range: 0-96
                   "
        ::= { hwXdslPortPerformanceStatInfoEntry 1 }

    hwXdslPort15minutesPerformanceInBytesInfo OBJECT-TYPE
        SYNTAX Counter32
        MAX-ACCESS read-only
        STATUS current
        DESCRIPTION
                   "Read the receive bytes of xDSL port during 15 minutes."
        ::= { hwXdslPortPerformanceStatInfoEntry 2 }

    hwXdslPort15minutesPerformanceOutBytesInfo OBJECT-TYPE
        SYNTAX Counter32
        MAX-ACCESS read-only
        STATUS current
        DESCRIPTION
                   "Read the transmit bytes of xDSL port during 15 minutes."
        ::= { hwXdslPortPerformanceStatInfoEntry 3 }

    hwXdslPortSyncSuccNumberInfo OBJECT-TYPE
        SYNTAX Counter32
        MAX-ACCESS read-only
        STATUS current
        DESCRIPTION
                   "Number of successful activations of the ADSL/G.SHDSL port within 15 minutes"
        ::= { hwXdslPortPerformanceStatInfoEntry 4 }

    hwXdslPortSyncFailNumberInfo OBJECT-TYPE
        SYNTAX Counter32
        MAX-ACCESS read-only
        STATUS current
        DESCRIPTION
                   "Number of failed activations of the ADSL/G.SHDSL port within 15 minutes"
        ::= { hwXdslPortPerformanceStatInfoEntry 5 }

    hwXdslPortAtucCodeViolationInfo OBJECT-TYPE
        SYNTAX Counter32
        MAX-ACCESS read-only
        STATUS current
        DESCRIPTION
                   "Number of head errors of the ATUC cell within 15 minutes."
        ::= { hwXdslPortPerformanceStatInfoEntry 6 }

    hwXdslPortAturCodeViolationInfo OBJECT-TYPE
        SYNTAX Counter32
        MAX-ACCESS read-only
        STATUS current
        DESCRIPTION
                   "Number of head errors of the ATUR cell within 15 minutes."
        ::= { hwXdslPortPerformanceStatInfoEntry 7 }

    hwXdslPortAtucFecSecondsInfo OBJECT-TYPE
        SYNTAX Counter32
        MAX-ACCESS read-only
        STATUS current
        DESCRIPTION
                   "Seconds of the ATUC FEC errors within 15 minutes."
        ::= { hwXdslPortPerformanceStatInfoEntry 8 }

    hwXdslPortAturFecSecondsInfo OBJECT-TYPE
        SYNTAX Counter32
        MAX-ACCESS read-only
        STATUS current
        DESCRIPTION
                   "Seconds of the ATUR FEC errors within 15 minutes."
        ::= { hwXdslPortPerformanceStatInfoEntry 9 }

    hwXdslPortCurrent15minutesStatTimeInfo OBJECT-TYPE
        SYNTAX Counter32
        MAX-ACCESS read-only
        STATUS current
        DESCRIPTION
                   "Read the Stat. time of current 15 minutes."
        ::= { hwXdslPortPerformanceStatInfoEntry 10 }

-- hwadslAtucPhysInfoTable

    hwadslAtucPhysInfoTable OBJECT-TYPE
        SYNTAX SEQUENCE OF HwadslAtucPhysInfoEntry
        MAX-ACCESS not-accessible
        STATUS current
        DESCRIPTION
                   "This table provides the physical layer parameters of each ATUC.
                    The index of this table is ifIndex.
                   "
        ::= { hwAdslMibObjects 16 }

    hwadslAtucPhysInfoEntry OBJECT-TYPE
        SYNTAX HwadslAtucPhysInfoEntry
        MAX-ACCESS not-accessible
        STATUS current
        DESCRIPTION
                   "This table provides the physical layer parameters of each ATUC.
                    The index of this entry is ifIndex.
                   "
        INDEX {ifIndex }
        ::= { hwadslAtucPhysInfoTable 1 }

    HwadslAtucPhysInfoEntry ::=
        SEQUENCE {
                     hwAdslAtucCurrTransModeInfo             HWADSLTRANSMISSIONMODETYPE,
                     hwAdslAtucCurrSignalAtnInfo             Gauge32,
                     hwadslAtucInvG994VendorId               OCTET STRING,
                     hwadslAtucLInvSelfTestResult            Unsigned32,
                     hwadslAtucTransmissionCapabilitiesInfo  Adsl2TransmissionModeType
                 }

    hwAdslAtucCurrTransModeInfo OBJECT-TYPE
        SYNTAX      HWADSLTRANSMISSIONMODETYPE
        MAX-ACCESS  read-only
        STATUS      current
        DESCRIPTION
                   "A set of ADSL line transmission modes."
        ::= { hwadslAtucPhysInfoEntry 1 }

    hwAdslAtucCurrSignalAtnInfo OBJECT-TYPE
        SYNTAX Gauge32 (0..630)
        UNITS "tenth dB"
        MAX-ACCESS read-only
        STATUS current
        DESCRIPTION
                   "Current signal attenuation of the ATU-C, indicating the difference between the transmit signal of the ATU-R and the receive signal of the ATU-C.
                    Range: 0-630
                    Unit: tenth dB
                   "
        ::= { hwadslAtucPhysInfoEntry 2 }

    hwadslAtucInvG994VendorId  OBJECT-TYPE
        SYNTAX      OCTET STRING  (SIZE (0..16))
        MAX-ACCESS  read-only
        STATUS      current
        DESCRIPTION
            "The ATU G.994.1 Vendor ID as inserted in the G.994.1 CL/CLR
            message.  It consists of 8 binary octets, including a country
            code followed by a (regionally allocated) provider code, as
            defined in Recommendation T.35."
        REFERENCE    "ITU-T G.997.1, paragraph 7.4"
        ::= { hwadslAtucPhysInfoEntry 3 }

    hwadslAtucLInvSelfTestResult  OBJECT-TYPE
      SYNTAX      Unsigned32
      MAX-ACCESS  read-only
      STATUS      current
      DESCRIPTION
         "The ATU self-test result, coded as a 32-bit value.  The
          most significant octet of the result is '0' if the self-test
          passed, and '1' if the self-test failed.  The interpretation
          of the other octets is vendor discretionary."
      REFERENCE    "ITU-T G.997.1, paragraph 7.4"
      ::= { hwadslAtucPhysInfoEntry 4 }

    hwadslAtucTransmissionCapabilitiesInfo OBJECT-TYPE
      SYNTAX      Adsl2TransmissionModeType
      MAX-ACCESS  read-only
      STATUS      current
      DESCRIPTION
                 "The ATU transmission system capability list of the different
                  coding types. It is coded in a bit-map representation with 1
                  or more bits set. A bit set to '1' means that the ATU
                  supports the respective coding. The value may be derived
                  from the handshaking procedures defined in G.994.1.
                 "
      ::= { hwadslAtucPhysInfoEntry 5 }

-- hwadslLineExtInfoTable

	hwadslLineExtInfoTable   OBJECT-TYPE
        SYNTAX    SEQUENCE OF HwadslLineExtInfoEntry
        MAX-ACCESS      not-accessible
        STATUS          current
        DESCRIPTION
                   "This table is an extension of RFC 2662. It
                    contains ADSL line configuration and
                    monitoring information. This includes the ADSL
                    line's capabilities and actual ADSL transmission
                    system. An entry extends the adslLineEntry defined in
                    [RFC2662]. Each entry corresponds to an ADSL
                    line.
                    The index of this table is ifIndex.
                   "
        ::= { hwAdslMibObjects 17 }

    hwadslLineExtInfoEntry   OBJECT-TYPE
        SYNTAX          HwadslLineExtInfoEntry
        MAX-ACCESS      not-accessible
        STATUS          current
        DESCRIPTION
                   "This table is an extension of RFC 2662. It
                    contains ADSL line configuration and
                    monitoring information. This includes the ADSL
                    line's capabilities and actual ADSL transmission
                    system. An entry extends the adslLineEntry defined in
                    [RFC2662]. Each entry corresponds to an ADSL
                    line.
                    The index of this entry is ifIndex.
                   "
        AUGMENTS { adslLineEntry }
        ::= { hwadslLineExtInfoTable 1 }

    HwadslLineExtInfoEntry ::=
        SEQUENCE {
                      hwadsl2LineTransAtucActualInfo        Adsl2TransmissionModeType,
                      hwadslLineStatusRtxUsedDs             INTEGER,
                      hwadslLineStatusInitResult            INTEGER,
                      hwadslLineStatusSigAttenDs            Unsigned32,
                      hwadslLineStatusSigAttenUs            Unsigned32,
                      hwadslLineStatusActPsdDs              Integer32,
                      hwadslLineStatusActPsdUs              Integer32,
                      hwadslLineStatusLastRetrainInfo       INTEGER,
                      hwadslLineStatusLineRateDs            Unsigned32,
                      hwadslLineStatusLineRateUs            Unsigned32
                 }

    hwadsl2LineTransAtucActualInfo OBJECT-TYPE
        SYNTAX      Adsl2TransmissionModeType
        MAX-ACCESS  read-only
        STATUS      current
        DESCRIPTION
                   "The actual transmission mode of the ATU-C.
                    During ADSL line initialization, the ADSL
                    Transceiver Unit - Remote terminal end (ATU-R)
                    will determine the mode used for the link.
                    This value will be limited a single transmission
                    mode that is a subset of those modes enabled
                    by the ATU-C and denoted by
                    adslLineTransAtucConfig. After an initialization
                    has occurred, its mode is saved as the 'Current'
                    mode and is persistence should the link go
                    down. This object returns 0 (i.e. BITS with no
                    mode bit set) if the mode is not known.
                   "
        REFERENCE "Section 7.3.2 ITU G.997.1 "
        ::= { hwadslLineExtInfoEntry 1 }

        hwadslLineStatusRtxUsedDs OBJECT-TYPE
        SYNTAX      INTEGER{
                               rtxInuse(1),
                               rtxUnusedModeForbidden(2),
                               rtxUnusedNotSupportedXtuc(3),
                               rtxUnusedNotSupportedXtur(4),
                               rtxUnusedNotSupportedXtucAndXtur(5),
                               invalidValue(-1)
                           }
        MAX-ACCESS  read-only
        STATUS      current
        DESCRIPTION
                   "This parameter specifies whether G.998.4 retransmission is used (i.e., active in Showtime)
                    in a given transmit direction. The parameter in downstream is  RTX_USED_ds, and the parameter
                    in upstream is RTX_USED_us. In G.992.3 and G992.5 only the  downstream parameter RTX_USED_ds
                    is relevant, the value in the upstream direction shall be ignored. In G.993.2, both parameters are relevant.
                    Options:
                    1. rtxInuse(1)                             - RTX in use
                    2. rtxUnusedModeForbidden(2)               - RTX not in use, due to RTX_MODE = FORBIDDEN
                    3. rtxUnusedNotSupportedXtuc(3)            - RTX not in use, due to not supported by the XTU-C
                    4. rtxUnusedNotSupportedXtur(4)            - RTX not in use, due to not supported by the XTU-R
                    5. rtxUnusedNotSupportedXtucAndXtur(5)     - RTX not in use, due to not supported by the XTU-C and XTU-R
                    6. invalidValue(-1)                        - Invalid value
                    This parameter shall also be reported in the case of RTX_MODE=RTX_FORCED with INIT FAILURE
                    or with RTX_MODE=RTX_TESTMODE with INIT FAILURE.
                   "
        REFERENCE "ITU-T G.997.1, paragraph 7.5.1.38"
        ::= { hwadslLineExtInfoEntry 2 }

      hwadslLineStatusInitResult  OBJECT-TYPE
      SYNTAX INTEGER
                {
                    noFail(0),
                    configError(1),
                    configNotFeasible(2),
                    commFail(3),
                    noPeerXtu(4),
                    otherCause(5),
                    ginpNotSelected(6),
                    invalidValue(-1)
                }
      MAX-ACCESS  read-only
      STATUS      current
      DESCRIPTION
         "Indicates the result of the last full initialization performed
                 on the line.
                 Options:
                 1. noFail(0)            - Successful initialization
                 2. configError(1)       - Configuration failure
                 3. configNotFeasible(2) - Configuration details not supported
                 4. commFail(3)          - Communication failure
                 5. noPeerXtu(4)         - Peer xTU not detected
                 6. otherCause(5)        - Other initialization failure reason
                 7. ginpNotSelected(6)   - G.998.4 Retransmission mode was not selected
                                           while RTX_MODE = FORCED or with RTX_MODE = RTX_TESTMODE
                 8. invalidValue(-1)     - Invalid value"
      REFERENCE    "ITU-T G.997.1, paragraph 7.5.1.3"
      ::= { hwadslLineExtInfoEntry 3 }


      hwadslLineStatusSigAttenDs  OBJECT-TYPE
      SYNTAX      Unsigned32 (0..1270 | 2147483646 | 2147483647)
      UNITS       "0.1 dB"
      MAX-ACCESS  read-only
      STATUS      current
      DESCRIPTION
         "The measured difference in the total power transmitted by the
          ATU-C and the total power received by the ATU-R over all sub-
          carriers during Showtime.  It ranges from 0 to 1270 units of
          0.1 dB (physical values are 0 to 127 dB).
          A special value of 0x7FFFFFFF (2147483647) indicates the
          signal attenuation is out of range to be represented.
          A special value of 0x7FFFFFFE (2147483646) indicates the
          signal attenuation measurement is currently unavailable."
      REFERENCE    "ITU-T G.997.1, paragraph 7.5.1.8"
      ::= { hwadslLineExtInfoEntry 4 }

   hwadslLineStatusSigAttenUs  OBJECT-TYPE
      SYNTAX      Unsigned32 (0..1270 | 2147483646 | 2147483647)
      UNITS       "0.1 dB"
      MAX-ACCESS  read-only
      STATUS      current
      DESCRIPTION
         "The measured difference in the total power transmitted by the
          ATU-R and the total power received by the ATU-C over all sub-
          carriers during Showtime.  It ranges from 0 to 1270 units of
          0.1 dB (physical values are 0 to 127 dB).
          A special value of 0x7FFFFFFF (2147483647) indicates the
          signal attenuation is out of range to be represented.
          A special value of 0x7FFFFFFE (2147483646) indicates the
          signal attenuation measurement is currently unavailable."
      REFERENCE    "ITU-T G.997.1, paragraph 7.5.1.9"
      ::= { hwadslLineExtInfoEntry 5 }


   hwadslLineStatusActPsdDs OBJECT-TYPE
      SYNTAX      Integer32 (-900..0 | 2147483647)
      UNITS       "0.1 dB"
      MAX-ACCESS  read-only
      STATUS      current
      DESCRIPTION
         "Actual Power Spectrum Density (PSD) Downstream.  The average
          downstream transmit PSD over the sub-carriers used for
          downstream.  It ranges from -900 to 0 units of 0.1 dB
          (physical values are -90 to 0 dBm/Hz).
          A value of 0x7FFFFFFF (2147483647) indicates the measurement
          is out of range to be represented."
      REFERENCE    "ITU-T G.997.1, paragraph 7.5.1.14"
      ::= { hwadslLineExtInfoEntry 6 }

   hwadslLineStatusActPsdUs OBJECT-TYPE
      SYNTAX      Integer32 (-900..0 | 2147483647)
      UNITS       "0.1 dB"
      MAX-ACCESS  read-only
      STATUS      current
      DESCRIPTION
         "Actual Power Spectrum Density (PSD) Upstream.  The average
          upstream transmit PSD over the sub-carriers used for upstream.
          It ranges from -900 to 0 units of 0.1 dB (physical values
          are -90 to 0 dBm/Hz).
          A value of 0x7FFFFFFF (2147483647) indicates the measurement
          is out of range to be represented."
      REFERENCE    "ITU-T G.997.1, paragraph 7.5.1.15"
      ::= { hwadslLineExtInfoEntry 7 }

   hwadslLineStatusLastRetrainInfo  OBJECT-TYPE
      SYNTAX INTEGER
                {
                 none(1),
                 cpe-l3-trigger(2),
                 lom-us-trigger-dra(3),
                 lom-ds-trigger-dra(4),
                 cpe-never-answer-oam(5),
                 cpe-no-more-answer-oam(6),
                 persistent-ncd-us(7),
                 persistent-ncd-ds(8),
                 persistent-lcd-us(9),
                 persistent-lcd-ds(10),
                 l2-problem-co-drop(11),
                 l2-problem-cpe-drop(12),
                 bitswap-refused-us-co-drop(13),
                 bitswap-refused-us-cpe-drop(14),
                 channel-change-us-co-drop(15),
                 channel-change-us-cpe-drop(16),
                 noise-increase-us-co-drop(17),
                 noise-increase-us-cpe-drop(18),
                 bitswap-refused-ds-co-drop(19),
                 bitswap-refused-ds-cpe-drop(20),
                 channel-change-ds-co-drop(21),
                 channel-change-ds-cpe-drop(22),
                 noise-increase-ds-co-drop(23),
                 noise-increase-ds-cpe-drop(24),
                 lom-us-co-drop(25),
                 lom-us-cpe-drop(26),
                 lom-ds-co-drop(27),
                 lom-ds-cpe-drop(28),
                 sra-problem-us-co-drop(29),
                 sra-problem-us-cpe-drop(30),
                 sra-failed-us-co-drop(31),
                 sra-failed-us-cpe-drop(32),
                 sra-problem-ds-co-drop(33),
                 sra-problem-ds-cpe-drop(34),
                 sra-rejected-ds-co-drop(35),
                 sra-rejected-ds-cpe-drop(36),
                 bitswap-problem-us-co-drop(37),
                 bitswap-problem-us-cpe-drop(38),
                 bitswap-failed-us-co-drop(39),
                 bitswap-failed-us-cpe-drop(40),
                 bitswap-problem-ds-co-drop(41),
                 bitswap-problem-ds-cpe-drop(42),
                 bitswap-rejected-ds-co-drop(43),
                 bitswap-rejected-ds-cpe-drop(44),
                 cpe-switched-off(45),
                 cpe-lost(46),
                 co-reset(47),
                 co-stop(48),
                 unknown(49)
                }
      MAX-ACCESS  read-only
      STATUS      current
      DESCRIPTION
         "Indicates the last retrained information performed on the line.
          Options:
          1. none(1)                           - No record is available
          2. cpe-l3-trigger(2)                 - The terminal initiates a low power consumption L3 request
          3. lom-us-trigger-dra(3)             - The upstream noise margin is smaller than the minimum noise margin in rate dynamic adjustment
          4. lom-ds-trigger-dra(4)             - The downstream noise margin is smaller than the minimum noise margin in rate dynamic adjustment
          5. cpe-never-answer-oam(5)           - No OAM response is received from the CPE all the time
          6. cpe-no-more-answer-oam(6)         - No OAM response is received from the CPE
          7. persistent-ncd-us(7)              - Upstream continuous no cell delineation
          8. persistent-ncd-ds(8)              - Downstream continuous no cell delineation
          9. persistent-lcd-us(9)              - Upstream continuous loss of cell delineation
          10.persistent-lcd-ds(10)             - Downstream continuous loss of cell delineation
          11.l2-problem-co-drop(11)            - The CO is faulty during the switching from L0 to L2
          12.l2-problem-cpe-drop(12)           - The CPE is faulty during the switching from L0 to L2
          13.bitswap-refused-us-co-drop(13)    - The CO goes offline when the upstream bit swap fault occurs 10 times consecutively
          14.bitswap-refused-us-cpe-drop(14)   - The CPE goes offline when the downstream bit swap fault occurs 10 times consecutively
          15.channel-change-us-co-drop(15)     - The CO goes offline when the upstream net rate changes
          16.channel-change-us-cpe-drop(16)    - The CPE goes offline when the upstream net rate changes
          17.noise-increase-us-co-drop(17)     - The CO goes offline when the upstream noise increases
          18.noise-increase-us-cpe-drop(18)    - The CPE goes offline when the upstream noise increases
          19.bitswap-refused-ds-co-drop(19)    - The CO goes offline when the downstream bit swap fault occurs 10 times consecutively
          20.bitswap-refused-ds-cpe-drop(20)   - The CPE goes offline when the downstream bit swap fault occurs 10 times consecutively
          21.channel-change-ds-co-drop(21)     - The CO goes offline when the downstream net rate changes
          22.channel-change-ds-cpe-drop(22)    - The CPE goes offline when the downstream net rate changes
          23.noise-increase-ds-co-drop(23)     - The CO goes offline when the downstream noise increases
          24.noise-increase-ds-cpe-drop(24)    - The CPE goes offline when the downstream noise increases
          25.lom-us-co-drop(25)                - The CO goes offline when the upstream noise margin is smaller than the minimum noise margin
          26.lom-us-cpe-drop(26)               - The CPE goes offline when the upstream noise margin is smaller than the minimum noise margin
          27.lom-ds-co-drop(27)                - The CO goes offline when the downstream noise margin is smaller than the minimum noise margin
          28.lom-ds-cpe-drop(28)               - The CPE goes offline when the downstream noise margin is smaller than the minimum noise margin
          29.sra-problem-us-co-drop(29)        - The CO goes offline when the upstream SRA is faulty
          30.sra-problem-us-cpe-drop(30)       - The CPE goes offline when the upstream SRA is faulty
          31.sra-failed-us-co-drop(31)         - The CO goes offline when the upstream SRA fails
          32.sra-failed-us-cpe-drop(32)        - The CPE goes offline when the upstream SRA fails
          33.sra-problem-ds-co-drop(33)        - The CO goes offline when the downstream SRA is fault
          34.sra-problem-ds-cpe-drop(34)       - The CPE goes offline when the downstream SRA is faulty
          35.sra-rejected-ds-co-drop(35)       - The CO goes offline when the downstream SRA is rejected
          36.sra-rejected-ds-cpe-drop(36)      - The CPE goes offline when the downstream SRA is rejected
          37.bitswap-problem-us-co-drop(37)    - The CO goes offline when the upstream bit swap is faulty
          38.bitswap-problem-us-cpe-drop(38)   - The CPE goes offline when the upstream bit swap is faulty
          39.bitswap-failed-us-co-drop(39)     - The CO goes offline when the upstream bit swap fails
          40.bitswap-failed-us-cpe-drop(40)    - The CPE goes offline when the upstream bit swap fails
          41.bitswap-problem-ds-co-drop(41)    - The CO goes offline when the downstream bit swap is faulty
          42.bitswap-problem-ds-cpe-drop(42)   - The CPE goes offline when the downstream bit swap is faulty
          43.bitswap-rejected-ds-co-drop(43)   - The CO goes offline when the downstream bit swap is rejected
          44.bitswap-rejected-ds-cpe-drop(44)  - The CPE goes offline when the downstream bit swap is rejected
          45.cpe-switched-off(45)              - The CPE power supply is shut down
          46.cpe-lost(46)                      - The CPE is disconnected
          47.co-reset(47)                      - The CO resets the chipset or line
          48.co-stop(48)                       - The CO actively deactivate the port
          49.unknown(49)                       - Unknown reason
          "
      ::= { hwadslLineExtInfoEntry 8 }

      hwadslLineStatusLineRateDs  OBJECT-TYPE
            SYNTAX      Unsigned32
            UNITS       "bits/second"
            MAX-ACCESS  read-only
            STATUS      current
            DESCRIPTION
                "The actual line rate downstream.
                 Unit: bits/second
                "
      ::= { hwadslLineExtInfoEntry 9 }

      hwadslLineStatusLineRateUs  OBJECT-TYPE
            SYNTAX      Unsigned32
            UNITS       "bits/second"
            MAX-ACCESS  read-only
            STATUS      current
            DESCRIPTION
                "The actual line rate upstream.
                 Unit: bits/second
                "
      ::= { hwadslLineExtInfoEntry 10 }

--  hwadslAtucChanPerfDataInfoTable

    hwadslAtucChanPerfDataInfoTable OBJECT-TYPE
        SYNTAX SEQUENCE OF HwadslAtucChanPerfDataInfoEntry
        MAX-ACCESS not-accessible
        STATUS current
        DESCRIPTION
                   "Parameter table of the ATUC channel performance: This table is used to query the performance statistics of the ATUC channel.
                    The index of this table is ifIndex.
                   "
        ::= { hwAdslMibObjects 18 }

    hwadslAtucChanPerfDataInfoEntry OBJECT-TYPE
        SYNTAX HwadslAtucChanPerfDataInfoEntry
        MAX-ACCESS not-accessible
        STATUS current
        DESCRIPTION
                   "Parameter table of the ATUC channel performance: This table is used to query the performance statistics of the ATUC channel.
                    The index of this entry is ifIndex.
                   "
        INDEX {ifIndex }
        ::= { hwadslAtucChanPerfDataInfoTable 1 }

    HwadslAtucChanPerfDataInfoEntry ::=
        SEQUENCE {
                     hwadslAtucChanFecBlksInfo                           Counter32,
                     hwadslAtucChanHecBlksInfo                           Counter32,
                     hwadslAtucChanCrcBlksInfo                           Counter32,
                     hwadslAtucChanPerfCurr15MinFecBlksInfo              Counter32,
                     hwadslAtucChanPerfCurr15MinHecBlksInfo              Counter32,
                     hwadslAtucChanPerfCurr15MinCrcBlksInfo              Counter32,
                     hwadslAtucChanPerfCurr1DayFecBlksInfo               Counter32,
                     hwadslAtucChanPerfCurr1DayHecBlksInfo               Counter32,
                     hwadslAtucChanPerfCurr1DayCrcBlksInfo               Counter32,
                     hwadslAtucChanPerfPrev1DayFecBlksInfo               Counter32,
                     hwadslAtucChanPerfPrev1DayHecBlksInfo               Counter32,
                     hwadslAtucChanPerfPrev1DayCrcBlksInfo               Counter32,
                     hwadslAtucChanRtxCWInfo                             Gauge32,
                     hwadslAtucChanRtxCorrectedCWInfo                    Gauge32,
                     hwadslAtucChanRtxUncorrectedCWInfo                  Gauge32,
                     hwadslAtucChanPerfCurr15MinRtxCWInfo                Gauge32,
                     hwadslAtucChanPerfCurr15MinRtxCorrectedCWInfo       Gauge32,
                     hwadslAtucChanPerfCurr15MinRtxUncorrectedCWInfo     Gauge32,
                     hwadslAtucChanPerfCurr1DayRtxCWInfo                 Gauge32,
                     hwadslAtucChanPerfCurr1DayRtxCorrectedCWInfo        Gauge32,
                     hwadslAtucChanPerfCurr1DayRtxUncorrectedCWInfo      Gauge32,
                     hwadslAtucChanPerfPrev1DayRtxCWInfo                 Gauge32,
                     hwadslAtucChanPerfPrev1DayRtxCorrectedCWInfo        Gauge32,
                     hwadslAtucChanPerfPrev1DayRtxUncorrectedCWInfo      Gauge32,
                     hwadslAtucChanCurr15MStartTime                      DateAndTime,
                     hwadslAtucChanCurr1DayStartTime                     DateAndTime
                 }

    hwadslAtucChanFecBlksInfo  OBJECT-TYPE
        SYNTAX      Counter32
        MAX-ACCESS  read-only
        STATUS      current
        DESCRIPTION
                   "The count of all blocks received with FEC anomalies
                    since agent reset.
                   "
        ::= { hwadslAtucChanPerfDataInfoEntry 1 }

    hwadslAtucChanHecBlksInfo  OBJECT-TYPE
        SYNTAX      Counter32
        MAX-ACCESS  read-only
        STATUS      current
        DESCRIPTION
                   "The count of all blocks received with HEC anomalies
                    since agent reset.
                   "
        ::= { hwadslAtucChanPerfDataInfoEntry 2 }

    hwadslAtucChanCrcBlksInfo  OBJECT-TYPE
        SYNTAX      Counter32
        MAX-ACCESS  read-only
        STATUS      current
        DESCRIPTION
                   "The count of all blocks received with CRC anomalies
                    since agent reset.
                   "
        ::= { hwadslAtucChanPerfDataInfoEntry 3 }

    hwadslAtucChanPerfCurr15MinFecBlksInfo  OBJECT-TYPE
        SYNTAX      Counter32
        MAX-ACCESS  read-only
        STATUS      current
        DESCRIPTION
                   "The count of all blocks received with FEC anomalies
                    on this channel within the current 15 minutes
                    interval.
                   "
        ::= { hwadslAtucChanPerfDataInfoEntry 4 }

    hwadslAtucChanPerfCurr15MinHecBlksInfo  OBJECT-TYPE
        SYNTAX      Counter32
        MAX-ACCESS  read-only
        STATUS      current
        DESCRIPTION
                   "The count of all blocks received with HEC anomalies
                    on this channel within the current 15 minutes
                    interval.
                   "
        ::= { hwadslAtucChanPerfDataInfoEntry 5 }

    hwadslAtucChanPerfCurr15MinCrcBlksInfo  OBJECT-TYPE
        SYNTAX      Counter32
        MAX-ACCESS  read-only
        STATUS      current
        DESCRIPTION
                   "The count of all blocks received with CRC anomalies
                    on this channel within the current 15 minutes
                    interval.
                   "
        ::= { hwadslAtucChanPerfDataInfoEntry 6 }

    hwadslAtucChanPerfCurr1DayFecBlksInfo  OBJECT-TYPE
        SYNTAX      Counter32
        MAX-ACCESS  read-only
        STATUS      current
        DESCRIPTION
                   "The count of all blocks received with FEC anomalies
                    on this channel during the current day as
                    measured by adslAtucChanPerfCurr1DayTimeElapsed.
                   "
        ::= { hwadslAtucChanPerfDataInfoEntry 7 }

    hwadslAtucChanPerfCurr1DayHecBlksInfo  OBJECT-TYPE
        SYNTAX      Counter32
        MAX-ACCESS  read-only
        STATUS      current
        DESCRIPTION
                   "The count of all blocks received with HEC anomalies
                    on this channel during the current day as
                    measured by adslAtucChanPerfCurr1DayTimeElapsed.
                   "
        ::= { hwadslAtucChanPerfDataInfoEntry 8 }

    hwadslAtucChanPerfCurr1DayCrcBlksInfo  OBJECT-TYPE
        SYNTAX      Counter32
        MAX-ACCESS  read-only
        STATUS      current
        DESCRIPTION
                   "The count of all blocks received with CRC anomalies
                    on this channel during the current day as
                    measured by adslAtucChanPerfCurr1DayTimeElapsed.
                   "
        ::= { hwadslAtucChanPerfDataInfoEntry 9 }

    hwadslAtucChanPerfPrev1DayFecBlksInfo  OBJECT-TYPE
        SYNTAX      Counter32
        MAX-ACCESS  read-only
        STATUS      current
        DESCRIPTION
                   "The count of all blocks received with FEC anomalies
                    on this channel within the most recent previous
                    1-day period.
                   "
        ::= { hwadslAtucChanPerfDataInfoEntry 10 }

    hwadslAtucChanPerfPrev1DayHecBlksInfo  OBJECT-TYPE
        SYNTAX      Counter32
        MAX-ACCESS  read-only
        STATUS      current
        DESCRIPTION
                   "The count of all blocks received with HEC anomalies
                    on this channel within the most recent previous
                    1-day period.
                   "
        ::= { hwadslAtucChanPerfDataInfoEntry 11 }

    hwadslAtucChanPerfPrev1DayCrcBlksInfo  OBJECT-TYPE
        SYNTAX      Counter32
        MAX-ACCESS  read-only
        STATUS      current
        DESCRIPTION
                   "The count of all blocks received with CRC anomalies
                    on this channel within the most recent previous
                    1-day period.
                   "
        ::= { hwadslAtucChanPerfDataInfoEntry 12 }

    hwadslAtucChanRtxCWInfo OBJECT-TYPE
        SYNTAX      Gauge32
        MAX-ACCESS  read-only
        STATUS      current
        DESCRIPTION
                   "The count of units request retransmission since agent reset."
        ::= { hwadslAtucChanPerfDataInfoEntry 13 }

    hwadslAtucChanRtxCorrectedCWInfo OBJECT-TYPE
        SYNTAX      Gauge32
        MAX-ACCESS  read-only
        STATUS      current
        DESCRIPTION
                   "The count of units corrected by retransmission since agent reset."
        ::= { hwadslAtucChanPerfDataInfoEntry 14 }

    hwadslAtucChanRtxUncorrectedCWInfo OBJECT-TYPE
        SYNTAX      Gauge32
        MAX-ACCESS  read-only
        STATUS      current
        DESCRIPTION
                   "The count of units uncorrected by retransmission since agent reset."
        ::= { hwadslAtucChanPerfDataInfoEntry 15 }

    hwadslAtucChanPerfCurr15MinRtxCWInfo OBJECT-TYPE
        SYNTAX      Gauge32
        MAX-ACCESS  read-only
        STATUS      current
        DESCRIPTION
                   "The count of units request retransmission on this
                    channel within the current 15 minutes interval.
                   "
        ::= { hwadslAtucChanPerfDataInfoEntry 16 }

    hwadslAtucChanPerfCurr15MinRtxCorrectedCWInfo OBJECT-TYPE
        SYNTAX      Gauge32
        MAX-ACCESS  read-only
        STATUS      current
        DESCRIPTION
                  "The count of units corrected by retransmission on this
                   channel within the current 15 minutes interval.
                  "
        ::= { hwadslAtucChanPerfDataInfoEntry 17 }

    hwadslAtucChanPerfCurr15MinRtxUncorrectedCWInfo OBJECT-TYPE
        SYNTAX      Gauge32
        MAX-ACCESS  read-only
        STATUS      current
        DESCRIPTION
                   "The count of units uncorrected by retransmission on
                    this channel within the current 15 minutes interval.
                   "
        ::= { hwadslAtucChanPerfDataInfoEntry 18 }

    hwadslAtucChanPerfCurr1DayRtxCWInfo OBJECT-TYPE
        SYNTAX      Gauge32
        MAX-ACCESS  read-only
        STATUS      current
        DESCRIPTION
                   "The count of units request retransmission on
                    this channel during the current day.
                   "
        ::= { hwadslAtucChanPerfDataInfoEntry 19 }

    hwadslAtucChanPerfCurr1DayRtxCorrectedCWInfo OBJECT-TYPE
        SYNTAX      Gauge32
        MAX-ACCESS  read-only
        STATUS      current
        DESCRIPTION
                   "The count of units corrected by retransmission
                    on this channel during the current day.
                   "
        ::= { hwadslAtucChanPerfDataInfoEntry 20 }

    hwadslAtucChanPerfCurr1DayRtxUncorrectedCWInfo OBJECT-TYPE
        SYNTAX      Gauge32
        MAX-ACCESS  read-only
        STATUS      current
        DESCRIPTION
                   "The count of units uncorrected by retransmission
                    on this channel during the current day.
                   "
        ::= { hwadslAtucChanPerfDataInfoEntry 21 }

    hwadslAtucChanPerfPrev1DayRtxCWInfo OBJECT-TYPE
        SYNTAX      Gauge32
        MAX-ACCESS  read-only
        STATUS      current
        DESCRIPTION
                   "The count of units request retransmission on this channel
                    within the most recent previous 1-day period.
                   "
        ::= { hwadslAtucChanPerfDataInfoEntry 22 }

   hwadslAtucChanPerfPrev1DayRtxCorrectedCWInfo OBJECT-TYPE
       SYNTAX      Gauge32
       MAX-ACCESS  read-only
       STATUS      current
       DESCRIPTION
                  "The count of units corrected by retransmission on this
                   channel within the most recent previous 1-day period.
                  "
       ::= { hwadslAtucChanPerfDataInfoEntry 23 }

    hwadslAtucChanPerfPrev1DayRtxUncorrectedCWInfo OBJECT-TYPE
        SYNTAX      Gauge32
        MAX-ACCESS  read-only
        STATUS      current
        DESCRIPTION
                   "The count of units uncorrected by retransmission on this
                    channel within the most recent previous 1-day period.
                   "
        ::= { hwadslAtucChanPerfDataInfoEntry 24 }

   hwadslAtucChanCurr15MStartTime  OBJECT-TYPE
       SYNTAX      DateAndTime
       MAX-ACCESS  read-only
       STATUS      current
       DESCRIPTION
           "Start time of the current 15-minute performance statistics."
       ::= { hwadslAtucChanPerfDataInfoEntry 25 }

   hwadslAtucChanCurr1DayStartTime  OBJECT-TYPE
       SYNTAX      DateAndTime
       MAX-ACCESS  read-only
       STATUS      current
       DESCRIPTION
           "Start time of the current 1-day performance statistics."
       ::= { hwadslAtucChanPerfDataInfoEntry 26 }

--  hwadslAturChanPerfDataInfoTable

    hwadslAturChanPerfDataInfoTable       OBJECT-TYPE
        SYNTAX   SEQUENCE OF HwadslAturChanPerfDataInfoEntry
        MAX-ACCESS      not-accessible
        STATUS          current
        DESCRIPTION
                   "Parameter table of the ATUR channel performance: This table is used to query the performance statistics of the ATUR channel.
                    The index of this table is ifIndex.
                   "
        ::= { hwAdslMibObjects 19 }

    hwadslAturChanPerfDataInfoEntry       OBJECT-TYPE
        SYNTAX  HwadslAturChanPerfDataInfoEntry
        MAX-ACCESS      not-accessible
        STATUS          current
        DESCRIPTION
                   "Parameter table of the ATUR channel performance: This table is used to query the performance statistics of the ATUR channel.
                    The index of this entry is ifIndex.
                   "
        INDEX           { ifIndex }
        ::= { hwadslAturChanPerfDataInfoTable 1 }

    HwadslAturChanPerfDataInfoEntry ::=
        SEQUENCE {
                      hwadslAturChanFecBlksInfo                       Counter32,
                      hwadslAturChanHecBlksInfo                       Counter32,
                      hwadslAturChanCrcBlksInfo                       Counter32,
                      hwadslAturChanPerfCurr15MinFecBlksInfo          Counter32,
                      hwadslAturChanPerfCurr15MinHecBlksInfo          Counter32,
                      hwadslAturChanPerfCurr15MinCrcBlksInfo          Counter32,
                      hwadslAturChanPerfCurr1DayFecBlksInfo           Counter32,
                      hwadslAturChanPerfCurr1DayHecBlksInfo           Counter32,
                      hwadslAturChanPerfCurr1DayCrcBlksInfo           Counter32,
                      hwadslAturChanPerfPrev1DayFecBlksInfo           Counter32,
                      hwadslAturChanPerfPrev1DayHecBlksInfo           Counter32,
                      hwadslAturChanPerfPrev1DayCrcBlksInfo           Counter32,
                      hwadslAturChanRtxCWInfo                         Gauge32,
                      hwadslAturChanRtxCorrectedCWInfo                Gauge32,
                      hwadslAturChanRtxUncorrectedCWInfo              Gauge32,
                      hwadslAturChanPerfCurr15MinRtxCWInfo            Gauge32,
                      hwadslAturChanPerfCurr15MinRtxCorrectedCWInfo   Gauge32,
                      hwadslAturChanPerfCurr15MinRtxUncorrectedCWInfo Gauge32,
                      hwadslAturChanPerfCurr1DayRtxCWInfo             Gauge32,
                      hwadslAturChanPerfCurr1DayRtxCorrectedCWInfo    Gauge32,
                      hwadslAturChanPerfCurr1DayRtxUncorrectedCWInfo  Gauge32,
                      hwadslAturChanPerfPrev1DayRtxCWInfo             Gauge32,
                      hwadslAturChanPerfPrev1DayRtxCorrectedCWInfo    Gauge32,
                      hwadslAturChanPerfPrev1DayRtxUncorrectedCWInfo  Gauge32,
                      hwadslAturChanCurr15MStartTime                  DateAndTime,
                      hwadslAturChanCurr1DayStartTime                 DateAndTime
                  }

    hwadslAturChanFecBlksInfo  OBJECT-TYPE
         SYNTAX      Counter32
         MAX-ACCESS  read-only
         STATUS      current
         DESCRIPTION
                    "The count of all blocks received with FEC anomalies
                     since agent reset.
                    "
        ::= { hwadslAturChanPerfDataInfoEntry 1 }

    hwadslAturChanHecBlksInfo  OBJECT-TYPE
        SYNTAX      Counter32
        MAX-ACCESS  read-only
        STATUS      current
        DESCRIPTION
                   "The count of all blocks received with HEC anomalies
                    since agent reset.
                   "
        ::= { hwadslAturChanPerfDataInfoEntry 2 }

    hwadslAturChanCrcBlksInfo  OBJECT-TYPE
        SYNTAX      Counter32
        MAX-ACCESS  read-only
        STATUS      current
        DESCRIPTION
                   "The count of all blocks received with CRC anomalies
                    since agent reset.
                   "
        ::= { hwadslAturChanPerfDataInfoEntry 3 }

    hwadslAturChanPerfCurr15MinFecBlksInfo  OBJECT-TYPE
        SYNTAX      Counter32
        MAX-ACCESS  read-only
        STATUS      current
        DESCRIPTION
                   "The count of all blocks received with FEC anomalies
                    on this channel within the current 15 minutes
                    interval.
                   "
        ::= { hwadslAturChanPerfDataInfoEntry 4 }

    hwadslAturChanPerfCurr15MinHecBlksInfo  OBJECT-TYPE
        SYNTAX      Counter32
        MAX-ACCESS  read-only
        STATUS      current
        DESCRIPTION
                   "The count of all blocks received with HEC anomalies
                    on this channel within the current 15 minutes
                    interval.
                   "
        ::= { hwadslAturChanPerfDataInfoEntry 5 }

    hwadslAturChanPerfCurr15MinCrcBlksInfo  OBJECT-TYPE
        SYNTAX      Counter32
        MAX-ACCESS  read-only
        STATUS      current
        DESCRIPTION
                   "The count of all blocks received with CRC anomalies
                    on this channel within the current 15 minutes
                    interval.
                   "
        ::= { hwadslAturChanPerfDataInfoEntry 6 }

    hwadslAturChanPerfCurr1DayFecBlksInfo  OBJECT-TYPE
        SYNTAX      Counter32
        MAX-ACCESS  read-only
        STATUS      current
        DESCRIPTION
                   "The count of all blocks received with FEC anomalies
                    on this channel during the current day as
                    measured by adslAturChanPerfCurr1DayTimeElapsed.
                   "
        ::= { hwadslAturChanPerfDataInfoEntry 7 }

    hwadslAturChanPerfCurr1DayHecBlksInfo  OBJECT-TYPE
        SYNTAX      Counter32
        MAX-ACCESS  read-only
        STATUS      current
        DESCRIPTION
                   "The count of all blocks received with HEC anomalies
                    on this channel during the current day as
                    measured by adslAturChanPerfCurr1DayTimeElapsed.
                   "
        ::= { hwadslAturChanPerfDataInfoEntry 8 }

    hwadslAturChanPerfCurr1DayCrcBlksInfo  OBJECT-TYPE
        SYNTAX      Counter32
        MAX-ACCESS  read-only
        STATUS      current
        DESCRIPTION
                   "The count of all blocks received with CRC anomalies
                    on this channel during the current day as
                    measured by adslAturChanPerfCurr1DayTimeElapsed.
                   "
        ::= { hwadslAturChanPerfDataInfoEntry 9 }

    hwadslAturChanPerfPrev1DayFecBlksInfo  OBJECT-TYPE
        SYNTAX      Counter32
        MAX-ACCESS  read-only
        STATUS      current
        DESCRIPTION
                   "The count of all blocks received with FEC anomalies
                    on this channel within the most recent previous
                    1-day period.
                   "
        ::= { hwadslAturChanPerfDataInfoEntry 10 }

    hwadslAturChanPerfPrev1DayHecBlksInfo  OBJECT-TYPE
        SYNTAX      Counter32
        MAX-ACCESS  read-only
        STATUS      current
        DESCRIPTION
                   "The count of all blocks received with HEC anomalies
                    on this channel within the most recent previous
                    1-day period.
                   "
        ::= { hwadslAturChanPerfDataInfoEntry 11 }

    hwadslAturChanPerfPrev1DayCrcBlksInfo OBJECT-TYPE
        SYNTAX      Counter32
        MAX-ACCESS  read-only
        STATUS      current
        DESCRIPTION
                   "The count of all blocks received with HEC anomalies
                    on this channel within the most recent previous
                    1-day period.
                   "
        ::= { hwadslAturChanPerfDataInfoEntry 12 }

    hwadslAturChanRtxCWInfo OBJECT-TYPE
        SYNTAX      Gauge32
        MAX-ACCESS  read-only
        STATUS      current
        DESCRIPTION
                   "The count of units request retransmission since agent reset."
        ::= { hwadslAturChanPerfDataInfoEntry 13 }

    hwadslAturChanRtxCorrectedCWInfo OBJECT-TYPE
        SYNTAX      Gauge32
        MAX-ACCESS  read-only
        STATUS      current
        DESCRIPTION
                   "The count of units corrected by retransmission since agent reset."
        ::= { hwadslAturChanPerfDataInfoEntry 14 }

    hwadslAturChanRtxUncorrectedCWInfo OBJECT-TYPE
        SYNTAX      Gauge32
        MAX-ACCESS  read-only
        STATUS      current
        DESCRIPTION
                   "The count of units uncorrected by retransmission since agent reset."
        ::= { hwadslAturChanPerfDataInfoEntry 15 }

    hwadslAturChanPerfCurr15MinRtxCWInfo OBJECT-TYPE
        SYNTAX      Gauge32
        MAX-ACCESS  read-only
        STATUS      current
        DESCRIPTION
                   "The count of units request retransmission on this
                    channel within the current 15 minutes interval.
                   "
        ::= { hwadslAturChanPerfDataInfoEntry 16 }

    hwadslAturChanPerfCurr15MinRtxCorrectedCWInfo OBJECT-TYPE
        SYNTAX      Gauge32
        MAX-ACCESS  read-only
        STATUS      current
        DESCRIPTION
                   "The count of units corrected by retransmission on
                    this channel within the current 15 minutes interval.
                   "
        ::= { hwadslAturChanPerfDataInfoEntry 17 }

    hwadslAturChanPerfCurr15MinRtxUncorrectedCWInfo OBJECT-TYPE
        SYNTAX      Gauge32
        MAX-ACCESS  read-only
        STATUS      current
        DESCRIPTION
                   "The count of units uncorrected by retransmission on
                    this channel within the current 15 minutes interval.
                   "
        ::= { hwadslAturChanPerfDataInfoEntry 18 }

    hwadslAturChanPerfCurr1DayRtxCWInfo OBJECT-TYPE
        SYNTAX      Gauge32
        MAX-ACCESS  read-only
        STATUS      current
        DESCRIPTION
                   "The count of units request retransmission on
                    this channel during the current day.
                   "
        ::= { hwadslAturChanPerfDataInfoEntry 19 }

    hwadslAturChanPerfCurr1DayRtxCorrectedCWInfo OBJECT-TYPE
        SYNTAX      Gauge32
        MAX-ACCESS  read-only
        STATUS      current
        DESCRIPTION
                   "The count of units corrected by retransmission
                    on this channel during the current day.
                   "
        ::= { hwadslAturChanPerfDataInfoEntry 20 }

    hwadslAturChanPerfCurr1DayRtxUncorrectedCWInfo OBJECT-TYPE
        SYNTAX      Gauge32
        MAX-ACCESS  read-only
        STATUS      current
        DESCRIPTION
                   "The count of units uncorrected by retransmission
                    on this channel during the current day.
                   "
        ::= { hwadslAturChanPerfDataInfoEntry 21 }

    hwadslAturChanPerfPrev1DayRtxCWInfo OBJECT-TYPE
        SYNTAX      Gauge32
        MAX-ACCESS  read-only
        STATUS      current
        DESCRIPTION
                   "The count of units request retransmission on this
                    channel within the most recent previous 1-day period.
                   "
        ::= { hwadslAturChanPerfDataInfoEntry 22 }

    hwadslAturChanPerfPrev1DayRtxCorrectedCWInfo OBJECT-TYPE
        SYNTAX      Gauge32
        MAX-ACCESS  read-only
        STATUS      current
        DESCRIPTION
                   "The count of units corrected by retransmission on this
                    channel within the most recent previous 1-day period.
                   "
        ::= { hwadslAturChanPerfDataInfoEntry 23 }

    hwadslAturChanPerfPrev1DayRtxUncorrectedCWInfo OBJECT-TYPE
        SYNTAX      Gauge32
        MAX-ACCESS  read-only
        STATUS      current
        DESCRIPTION
                   "The count of units uncorrected by retransmission on this
                    channel within the most recent previous 1-day period.
                   "
        ::= { hwadslAturChanPerfDataInfoEntry 24 }

    hwadslAturChanCurr15MStartTime  OBJECT-TYPE
        SYNTAX      DateAndTime
        MAX-ACCESS  read-only
        STATUS      current
        DESCRIPTION
            "Start time of the current 15-minute performance statistics."
        ::= { hwadslAturChanPerfDataInfoEntry 25 }

    hwadslAturChanCurr1DayStartTime  OBJECT-TYPE
        SYNTAX      DateAndTime
        MAX-ACCESS  read-only
        STATUS      current
        DESCRIPTION
            "Start time of the current 1-day performance statistics."
        ::= { hwadslAturChanPerfDataInfoEntry 26 }


         -- hwadslAturChanPerfPrev1DayCrcBlks  OBJECT-TYPE
         --     SYNTAX      Counter32
         --     MAX-ACCESS  read-only
         --     STATUS      current
         --     DESCRIPTION
         --         "Count of all blocks received with CRC anomalies
         --         on this channel within the most recent previous
         --         1-day period."
         -- ::= { adslAturChanPerfDataEntry 65547 }

--  hwadslAturChanIntervalInfoTable

    hwadslAturChanIntervalInfoTable   OBJECT-TYPE
        SYNTAX  SEQUENCE OF HwadslAturChanIntervalInfoEntry
        MAX-ACCESS      not-accessible
        STATUS          current
        DESCRIPTION
                   "Period table of collecting the ATUR channel performance data.
                    This table is used to query the ATUR channel performance data collected in each period (a day is divided into 96 15-minute periods).
                    The indexes of this table are ifIndex and adslAturChanIntervalNumber.
                   "
        ::= { hwAdslMibObjects 20 }

    hwadslAturChanIntervalInfoEntry   OBJECT-TYPE
        SYNTAX  HwadslAturChanIntervalInfoEntry
        MAX-ACCESS      not-accessible
        STATUS          current
        DESCRIPTION
                   "Period table of collecting the ATUR channel performance data.
                    This table is used to query the ATUR channel performance data collected in each period (a day is divided into 96 15-minute periods).
                    The indexes of this entry are ifIndex and adslAturChanIntervalNumber.
                   "
        INDEX   { ifIndex, adslAturChanIntervalNumber }
        ::= { hwadslAturChanIntervalInfoTable 1 }

    HwadslAturChanIntervalInfoEntry ::=
        SEQUENCE {
                     hwadslAturChanIntervalFecBlksInfo             PerfIntervalCount,
                     hwadslAturChanIntervalHecBlksInfo             PerfIntervalCount,
                     hwadslAturChanIntervalCrcBlksInfo             PerfIntervalCount,
                     hwadslAturChanIntervalRtxCWInfo               Gauge32,
                     hwadslAturChanIntervalRtxCorrectedCWInfo      Gauge32,
                     hwadslAturChanIntervalRtxUncorrectedCWInfo    Gauge32,
                     hwAdslAturChanIntervalStartTime               DateAndTime
                 }

    hwadslAturChanIntervalFecBlksInfo OBJECT-TYPE
        SYNTAX  PerfIntervalCount
        MAX-ACCESS  read-only
        STATUS      current
        DESCRIPTION
                   "The count of all blocks received with FRC anomalies
                    on this channel during this interval.
                   "
       ::= { hwadslAturChanIntervalInfoEntry 1 }

    hwadslAturChanIntervalHecBlksInfo OBJECT-TYPE
        SYNTAX      PerfIntervalCount
        MAX-ACCESS  read-only
        STATUS      current
        DESCRIPTION
                   "The count of all blocks received with HRC anomalies
                    on this channel during this interval.
                   "
        ::= { hwadslAturChanIntervalInfoEntry 2 }

    hwadslAturChanIntervalCrcBlksInfo OBJECT-TYPE
        SYNTAX      PerfIntervalCount
        MAX-ACCESS  read-only
        STATUS      current
        DESCRIPTION
                   "The count of all blocks received with CRC anomalies
                    on this channel during this interval.
                   "
        ::= { hwadslAturChanIntervalInfoEntry 3 }

    hwadslAturChanIntervalRtxCWInfo OBJECT-TYPE
        SYNTAX      Gauge32
        MAX-ACCESS  read-only
        STATUS      current
        DESCRIPTION
                   "The count of units request retransmission on this channel during this interval."
        ::= { hwadslAturChanIntervalInfoEntry 4 }

    hwadslAturChanIntervalRtxCorrectedCWInfo OBJECT-TYPE
        SYNTAX      Gauge32
        MAX-ACCESS  read-only
        STATUS      current
        DESCRIPTION
                   "The count of units corrected by retransmission on this channel during this interval."
        ::= { hwadslAturChanIntervalInfoEntry 5 }

    hwadslAturChanIntervalRtxUncorrectedCWInfo OBJECT-TYPE
        SYNTAX      Gauge32
        MAX-ACCESS  read-only
        STATUS      current
        DESCRIPTION
                   "The count of units uncorrected by retransmission on this channel during this interval."
        ::= { hwadslAturChanIntervalInfoEntry 6 }

    hwAdslAturChanIntervalStartTime  OBJECT-TYPE
       SYNTAX      DateAndTime
       MAX-ACCESS  read-only
       STATUS      current
       DESCRIPTION
           "Start time of the historical 15-minute performance statistics."
       ::= { hwadslAturChanIntervalInfoEntry 7 }

--  hwadslLineAlarmConfProfileCfgTable

    hwadslLineAlarmConfProfileCfgTable    OBJECT-TYPE
        SYNTAX  SEQUENCE OF HwadslLineAlarmConfProfileCfgEntry
        MAX-ACCESS      not-accessible
        STATUS          current
        DESCRIPTION
                   "This table contains information on the ADSL line configuration.
                    One entry in this table reflects a profile defined by a manager
                    which can be used to configure the modem for a physical line.
                    The entry contains information on the ADSL line configuration.
                    Each entry consists of a list of parameters that represents the
                    configuration of an ADSL modem.
                    When 'dynamic' profiles are implemented, a default profile will always exist.
                    This profile's name will be set to 'DEFVAL' and its parameters will be set to
                    vendor specific values, unless otherwise specified in this document.
                    When 'static' profiles are implemented, profiles are automatically created or
                    destroyed as ADSL physical lines are discovered and removed by the system.
                    The name of the profile will be equivalent to the decimal value of the line's
                    interface index.
                    The index of this table is adslLineAlarmConfProfileName.
                   "
        ::= { hwAdslMibObjects 21 }

    hwadslLineAlarmConfProfileCfgEntry    OBJECT-TYPE
        SYNTAX HwadslLineAlarmConfProfileCfgEntry
        MAX-ACCESS      not-accessible
        STATUS          current
        DESCRIPTION
                   "This table contains information on the ADSL line configuration.
                    One entry in this table reflects a profile defined by a manager
                    which can be used to configure the modem for a physical line.
                    The entry contains information on the ADSL line configuration.
                    Each entry consists of a list of parameters that represents the
                    configuration of an ADSL modem.
                    When 'dynamic' profiles are implemented, a default profile will always exist.
                    This profile's name will be set to 'DEFVAL' and its parameters will be set to
                    vendor specific values, unless otherwise specified in this document.
                    When 'static' profiles are implemented, profiles are automatically created or
                    destroyed as ADSL physical lines are discovered and removed by the system.
                    The name of the profile will be equivalent to the decimal value of the line's
                    interface index.
                    The index of this entry is adslLineAlarmConfProfileName.
                   "
        INDEX { IMPLIED adslLineAlarmConfProfileName }
        ::= { hwadslLineAlarmConfProfileCfgTable 1}

    HwadslLineAlarmConfProfileCfgEntry ::=
        SEQUENCE {
                     hwadslLineAlarmConfProfileDyingGaspCfg          INTEGER,
                     hwadslLineAlarmConfProfXturThresh15MinLeftrs    HCPerfIntervalThreshold,
                     hwAdslLineAlarmConfProfileActiveFailAlarmSwitch INTEGER
                 }

    hwadslLineAlarmConfProfileDyingGaspCfg OBJECT-TYPE
        SYNTAX INTEGER {
                           enable (1),
                           disable (2)
                       }
        MAX-ACCESS  read-create
        STATUS      current
        DESCRIPTION
                   "This object enables/disables the report of LOSS-OF-POWER
                    alarm in an ADSL line. This object is defaulted enable(1).
                    Options:
                    1. enable(1)  - The report of LOSS-OF-POWER alarm in an ADSL line is enabled
                    2. disable(2) - The report of LOSS-OF-POWER alarm in an ADSL line is disabled
                    Default: enable(1)
                   "

        ::= { hwadslLineAlarmConfProfileCfgEntry 1 }

    hwadslLineAlarmConfProfXturThresh15MinLeftrs  OBJECT-TYPE
        SYNTAX      HCPerfIntervalThreshold
        UNITS       "seconds"
        MAX-ACCESS  read-create
        STATUS      current
        DESCRIPTION
           "A threshold for the hwAdslAturPerfCurr15MLeftrs counter,
            The value 0 means that no threshold is specified for the
            associated counter.
            Unit: seconds
           "
        REFERENCE    "ITU-T G.997.1, paragraph 7.3.1"
        DEFVAL       { 0 }
        ::= { hwadslLineAlarmConfProfileCfgEntry 2 }

    hwAdslLineAlarmConfProfileActiveFailAlarmSwitch OBJECT-TYPE
        SYNTAX INTEGER {
                           enable (1),
                           disable (2)
                       }
        MAX-ACCESS  read-create
        STATUS      current
        DESCRIPTION
                   "This object enable/disable the active fail alarm switch.
                    Options:
                    1. enable(1)  - The active fail alarm switch is enabled
                    2. disable(2) - The active fail alarm switch is disabled
                   "
        DEFVAL       { enable }
        ::= { hwadslLineAlarmConfProfileCfgEntry 3 }

--  hwAdslPortPerformanceStatTable

    hwAdslPortPerformanceStatInfoTable OBJECT-TYPE
        SYNTAX SEQUENCE OF HwAdslPortPerformanceStatInfoEntry
        MAX-ACCESS not-accessible
        STATUS current
        DESCRIPTION
                   "This table is used to describe the performance statistics of the ADSL port within 15 minutes.
                    The indexes of this table are ifIndex and hwAdslPort15minutesPerformanceIntervalIndex.
                   "
        ::= { hwAdslMibObjects 22 }

    hwAdslPortPerformanceStatInfoEntry OBJECT-TYPE
        SYNTAX HwAdslPortPerformanceStatInfoEntry
        MAX-ACCESS not-accessible
        STATUS current
        DESCRIPTION
                   "This table is used to describe the performance statistics of the ADSL port within 15 minutes.
                    The indexes of this entry are ifIndex and hwAdslPort15minutesPerformanceIntervalIndex.
                   "
        INDEX { ifIndex, hwAdslPort15minutesPerformanceIntervalIndex }
        ::= { hwAdslPortPerformanceStatInfoTable 1 }

    HwAdslPortPerformanceStatInfoEntry ::=
        SEQUENCE{
                    hwAdslPort15minutesPerformanceIntervalIndex    Integer32,
                    hwAdslPort15minutesPerformanceInBytesInfo      Counter32,
                    hwAdslPort15minutesPerformanceOutBytesInfo     Counter32,
                    hwAdslPortSyncSuccNumberInfo                   Counter32,
                    hwAdslPortSyncFailNumberInfo                   Counter32,
                    hwAdslPortAtucCodeViolationInfo                Counter32,
                    hwAdslPortAturCodeViolationInfo                Counter32,
                    hwAdslPortAtucFecSecondsInfo                   Counter32,
                    hwAdslPortAturFecSecondsInfo                   Counter32,
                    hwAdslPortCurrent15minutesTimeElapseInfo       Counter32,
                    hwAdslPortAtucHecDropCellsCntInfo              Counter32,
                    hwAdslPortAturHecDropCellsCntInfo              Counter32,
                    hwAdslLineConfProfileInfo                      OCTET STRING,
                    hwAdslPort15minUpTimeInfo                      Counter32,
                    hwAdslAtucCurrAtnInfo                          Gauge32,
                    hwAdslAtucCurrSnrMgnInfo                       Integer32,
                    hwAdslAtucCurrAttainableRateInfo               Gauge32,
                    hwAdslAtucChanCurrTxRateInfo                   Gauge32,
                    hwAdslAturCurrAtnInfo                          Gauge32,
                    hwAdslAturCurrSnrMgnInfo                       Integer32,
                    hwAdslAturCurrAttainableRateInfo               Gauge32,
                    hwAdslAturChanCurrTxRateInfo                   Gauge32,
                    hwAdslAtucIntervalESsInfo                      PerfIntervalCount,
                    hwAdslAtucIntervalLofsInfo                     PerfIntervalCount,
                    hwAdslAtucIntervalLolsInfo                     PerfIntervalCount,
                    hwAdslAtucIntervalLossInfo                     PerfIntervalCount,
                    hwAdslAtucIntervalLprsInfo                     PerfIntervalCount,
                    hwAdslAturIntervalESsInfo                      PerfIntervalCount,
                    hwAdslAturIntervalLofsInfo                     PerfIntervalCount,
                    hwAdslAturIntervalLossInfo                     PerfIntervalCount,
                    hwAdslAturIntervalLprsInfo                     PerfIntervalCount,
                    hwAdslAtucChanIntervalReceivedBlksInfo         PerfIntervalCount,
                    hwAdslAtucChanIntervalTransmittedBlksInfo      PerfIntervalCount,
                    hwAdslAtucChanIntervalCorrectedBlksInfo        PerfIntervalCount,
                    hwAdslAtucChanIntervalUncorrectBlksInfo        PerfIntervalCount,
                    hwAdslAturChanIntervalReceivedBlksInfo         PerfIntervalCount,
                    hwAdslAturChanIntervalTransmittedBlksInfo      PerfIntervalCount,
                    hwAdslAturChanIntervalCorrectedBlksInfo        PerfIntervalCount,
                    hwAdslAturChanIntervalUncorrectBlksInfo        PerfIntervalCount,
                    hwAdslAtucIntervalSesLInfo                     PerfIntervalCount,
                    hwAdslAtucIntervalUasLInfo                     PerfIntervalCount,
                    hwAdslAturIntervalSesLInfo                     PerfIntervalCount,
                    hwAdslAturIntervalUasLInfo                     PerfIntervalCount,
                    hwAdslPortCurrentActModeInfo                   INTEGER
                }

    hwAdslPort15minutesPerformanceIntervalIndex OBJECT-TYPE
        SYNTAX Integer32(0..96)
        MAX-ACCESS not-accessible
        STATUS current
        DESCRIPTION
                   "The index of the interval which is queried.
                    Range: 0-96
                   "
        ::= { hwAdslPortPerformanceStatInfoEntry 1 }

    hwAdslPort15minutesPerformanceInBytesInfo OBJECT-TYPE
        SYNTAX Counter32
        MAX-ACCESS read-only
        STATUS current
        DESCRIPTION
                   "Read the received bytes of xDSL port during 15 minutes."
        ::= { hwAdslPortPerformanceStatInfoEntry 2 }

    hwAdslPort15minutesPerformanceOutBytesInfo OBJECT-TYPE
        SYNTAX Counter32
        MAX-ACCESS read-only
        STATUS current
        DESCRIPTION
                   "Read the transmitted bytes of xDSL port during 15 minutes."
        ::= { hwAdslPortPerformanceStatInfoEntry 3 }

    hwAdslPortSyncSuccNumberInfo OBJECT-TYPE
        SYNTAX Counter32
        MAX-ACCESS read-only
        STATUS current
        DESCRIPTION
                   "Number of successful activations within 15 minutes."
        ::= { hwAdslPortPerformanceStatInfoEntry 4 }

    hwAdslPortSyncFailNumberInfo OBJECT-TYPE
        SYNTAX Counter32
        MAX-ACCESS read-only
        STATUS current
        DESCRIPTION
                   "Number of failed activations within 15 minutes."
        ::= { hwAdslPortPerformanceStatInfoEntry 5 }

    hwAdslPortAtucCodeViolationInfo OBJECT-TYPE
        SYNTAX Counter32
        MAX-ACCESS read-only
        STATUS current
        DESCRIPTION
                   "Seconds of head errors of the ATUC cell within 15 minutes."
        ::= { hwAdslPortPerformanceStatInfoEntry 6 }

    hwAdslPortAturCodeViolationInfo OBJECT-TYPE
        SYNTAX Counter32
        MAX-ACCESS read-only
        STATUS current
        DESCRIPTION
                   "Seconds of the head errors of the ATUC cell within 15 minutes."
        ::= { hwAdslPortPerformanceStatInfoEntry 7 }

    hwAdslPortAtucFecSecondsInfo OBJECT-TYPE
        SYNTAX Counter32
        MAX-ACCESS read-only
        STATUS current
        DESCRIPTION
                   "Seconds of the ATUC FEC errors within 15 minutes."
        ::= { hwAdslPortPerformanceStatInfoEntry 8 }

    hwAdslPortAturFecSecondsInfo OBJECT-TYPE
        SYNTAX Counter32
        MAX-ACCESS read-only
        STATUS current
        DESCRIPTION
                   "Seconds of the ATUR FEC errors within 15 minutes."
        ::= { hwAdslPortPerformanceStatInfoEntry 9 }

    hwAdslPortCurrent15minutesTimeElapseInfo OBJECT-TYPE
        SYNTAX Counter32
        MAX-ACCESS read-only
        STATUS current
        DESCRIPTION
                   "Seconds that is passed within the current 15 minutes."
        ::= { hwAdslPortPerformanceStatInfoEntry 10 }

    hwAdslPortAtucHecDropCellsCntInfo OBJECT-TYPE
        SYNTAX Counter32
        MAX-ACCESS read-only
        STATUS current
        DESCRIPTION
                   "ATUC cells discarded with HEC Errors."
        ::= { hwAdslPortPerformanceStatInfoEntry 11 }

    hwAdslPortAturHecDropCellsCntInfo OBJECT-TYPE
        SYNTAX Counter32
        MAX-ACCESS read-only
        STATUS current
        DESCRIPTION
                   "ATUR cells discarded with HEC Errors."
        ::= { hwAdslPortPerformanceStatInfoEntry 12 }

    hwAdslLineConfProfileInfo OBJECT-TYPE
        SYNTAX      OCTET STRING (SIZE (0..32))
        MAX-ACCESS  read-only
        STATUS      current
        DESCRIPTION
                   "The value of this object identifies the row
                    in the ADSL Line Configuration Profile Table,
                    (adslLineConfProfileTable), which applies for this
                    ADSL line, and channels if applicable.
                    For 'dynamic' mode, in the case which the
                    configuration profile has not been set, the
                    value will be set to 'DEFVAL'.
                    If the implementator of this MIB has chosen not
                    to implement 'dynamic assignment' of profiles, this
                    object's MIN-ACCESS is read-only.
                   "
        ::= { hwAdslPortPerformanceStatInfoEntry 13 }

    hwAdslPort15minUpTimeInfo OBJECT-TYPE
        SYNTAX Counter32
        MAX-ACCESS read-only
        STATUS current
        DESCRIPTION
                   "The up time in the interval.
                    Unit: seconds
                   "
        ::= { hwAdslPortPerformanceStatInfoEntry 14 }

    hwAdslAtucCurrAtnInfo  OBJECT-TYPE
        SYNTAX      Gauge32(0..630)
        UNITS       "tenth dB"
        MAX-ACCESS  read-only
        STATUS      current
        DESCRIPTION
                   "Measured difference in the total power transmitted by
                    the peer ATU and the total power received by this ATU.
                    Range: 0-630
                    Unit: tenth dB
                   "
        ::= { hwAdslPortPerformanceStatInfoEntry 15 }

    hwAdslAtucCurrSnrMgnInfo OBJECT-TYPE
        SYNTAX      Integer32 (-640..640)
        UNITS       "tenth dB"
        MAX-ACCESS  read-only
        STATUS      current
        DESCRIPTION
                   "Noise Margin as seen by this ATU with respect to its
                    received signal.
                    Unit: tenth dB
                   "
        ::= { hwAdslPortPerformanceStatInfoEntry 16 }

    hwAdslAtucCurrAttainableRateInfo OBJECT-TYPE
        SYNTAX      Gauge32
        UNITS       "bps"
        MAX-ACCESS  read-only
        STATUS      current
        DESCRIPTION
                   "Indicates the maximum currently attainable data rate
                    by the ATU. This value will be equal or greater than
                    the current line rate.
                    Unit: bps
                   "
        ::= { hwAdslPortPerformanceStatInfoEntry 17 }

    hwAdslAtucChanCurrTxRateInfo  OBJECT-TYPE
        SYNTAX      Gauge32
        UNITS       "bps"
        MAX-ACCESS  read-only
        STATUS      current
        DESCRIPTION
                   "The actual transmitted rate on this channel.
                    Unit: bps
                   "
        ::= { hwAdslPortPerformanceStatInfoEntry 18 }

    hwAdslAturCurrAtnInfo OBJECT-TYPE
        SYNTAX      Gauge32(0..630)
        UNITS       "tenth dB"
        MAX-ACCESS  read-only
        STATUS      current
        DESCRIPTION
                   "Measured difference in the total power transmitted by
                    the peer ATU and the total power received by this ATU.
                    Range: 0-630
                    Unit: tenth dB
                   "
        ::= { hwAdslPortPerformanceStatInfoEntry 19 }

    hwAdslAturCurrSnrMgnInfo OBJECT-TYPE
        SYNTAX      Integer32 (-640..640)
        UNITS       "tenth dB"
        MAX-ACCESS  read-only
        STATUS      current
        DESCRIPTION
                   "Noise Margin as seen by this ATU with respect to its
                    received signal.
                    Range: (-640)-(640)
                    Unit: tenth dB
                   "
        ::= { hwAdslPortPerformanceStatInfoEntry 20 }

    hwAdslAturCurrAttainableRateInfo OBJECT-TYPE
        SYNTAX      Gauge32
        UNITS       "bps"
        MAX-ACCESS  read-only
        STATUS      current
        DESCRIPTION
                   "Indicates the maximum currently attainable data rate
                    by the ATU. This value will be equal or greater than
                    the current line rate.
                    Unit: bps
                   "
        ::= { hwAdslPortPerformanceStatInfoEntry 21 }

    hwAdslAturChanCurrTxRateInfo  OBJECT-TYPE
        SYNTAX      Gauge32
        UNITS       "bps"
        MAX-ACCESS  read-only
        STATUS      current
        DESCRIPTION
                   "The actual transmitted rate on this channel.
                    Unit: bps
                   "
        ::= { hwAdslPortPerformanceStatInfoEntry 22 }

    hwAdslAtucIntervalESsInfo OBJECT-TYPE
        SYNTAX      PerfIntervalCount
        UNITS       "seconds"
        MAX-ACCESS  read-only
        STATUS      current
        DESCRIPTION
                   "Seconds of the ATU-C errors at the interval.
                    Unit: seconds
                   "
        ::= { hwAdslPortPerformanceStatInfoEntry 23 }

    hwAdslAtucIntervalLofsInfo OBJECT-TYPE
        SYNTAX      PerfIntervalCount
        UNITS       "seconds"
        MAX-ACCESS  read-only
        STATUS      current
        DESCRIPTION
                   "The count of seconds in the interval when there was Loss
                    of Framing.
                    Unit: seconds
                   "
        ::= { hwAdslPortPerformanceStatInfoEntry 24 }

    hwAdslAtucIntervalLolsInfo  OBJECT-TYPE
        SYNTAX      PerfIntervalCount
        UNITS       "seconds"
        MAX-ACCESS  read-only
        STATUS      current
        DESCRIPTION
                   "The count of seconds in the interval when there was Loss
                    of Link.
                    Unit: seconds
                   "
        ::= { hwAdslPortPerformanceStatInfoEntry 25 }

    hwAdslAtucIntervalLossInfo  OBJECT-TYPE
        SYNTAX      PerfIntervalCount
        UNITS       "seconds"
        MAX-ACCESS  read-only
        STATUS      current
        DESCRIPTION
                   "The count of seconds in the interval when there was Loss
                    of Signal.
                    Unit: seconds
                   "
        ::= { hwAdslPortPerformanceStatInfoEntry 26 }

    hwAdslAtucIntervalLprsInfo  OBJECT-TYPE
        SYNTAX      PerfIntervalCount
        UNITS       "seconds"
        MAX-ACCESS  read-only
        STATUS      current
        DESCRIPTION
                   "The count of seconds in the interval when there was Loss
                    of Power.
                    Unit: seconds
                   "
        ::= { hwAdslPortPerformanceStatInfoEntry 27 }

    hwAdslAturIntervalESsInfo OBJECT-TYPE
        SYNTAX      PerfIntervalCount
        UNITS       "seconds"
        MAX-ACCESS  read-only
        STATUS      current
        DESCRIPTION
                   "Seconds of the ATU-R errors at the interval.
                    Unit: seconds
                   "
        ::= { hwAdslPortPerformanceStatInfoEntry 28 }

    hwAdslAturIntervalLofsInfo OBJECT-TYPE
        SYNTAX      PerfIntervalCount
        UNITS       "seconds"
        MAX-ACCESS  read-only
        STATUS      current
        DESCRIPTION
                   "The count of seconds in the interval when there was
                    Loss of Framing.
                    Unit: seconds
                   "
        ::= { hwAdslPortPerformanceStatInfoEntry 29 }

    hwAdslAturIntervalLossInfo  OBJECT-TYPE
        SYNTAX      PerfIntervalCount
        UNITS       "seconds"
        MAX-ACCESS  read-only
        STATUS      current
        DESCRIPTION
                   "The count of seconds in the interval when there was
                    Loss of Signal.
                    Unit: seconds
                   "
        ::= { hwAdslPortPerformanceStatInfoEntry 30 }

    hwAdslAturIntervalLprsInfo  OBJECT-TYPE
        SYNTAX      PerfIntervalCount
        UNITS       "seconds"
        MAX-ACCESS  read-only
        STATUS      current
        DESCRIPTION
                   "The count of seconds in the interval when there was
                    Loss of Power.
                    Unit: seconds
                   "
        ::= { hwAdslPortPerformanceStatInfoEntry 31 }

    hwAdslAtucChanIntervalReceivedBlksInfo OBJECT-TYPE
        SYNTAX      PerfIntervalCount
        MAX-ACCESS  read-only
        STATUS      current
        DESCRIPTION
                   "The count of all encoded blocks received on this channel
                    during this interval.
                   "
        ::= { hwAdslPortPerformanceStatInfoEntry 32 }

    hwAdslAtucChanIntervalTransmittedBlksInfo  OBJECT-TYPE
        SYNTAX      PerfIntervalCount
        MAX-ACCESS  read-only
        STATUS      current
        DESCRIPTION
                   "The count of all encoded blocks transmitted on this
                    channel during this interval.
                   "
        ::= { hwAdslPortPerformanceStatInfoEntry 33 }

    hwAdslAtucChanIntervalCorrectedBlksInfo  OBJECT-TYPE
        SYNTAX      PerfIntervalCount
        MAX-ACCESS  read-only
        STATUS      current
        DESCRIPTION
                   "The count of all blocks received with errors that were
                    corrected on this channel during this interval.
                   "
        ::= { hwAdslPortPerformanceStatInfoEntry 34 }

    hwAdslAtucChanIntervalUncorrectBlksInfo  OBJECT-TYPE
        SYNTAX      PerfIntervalCount
        MAX-ACCESS  read-only
        STATUS      current
        DESCRIPTION
                   "The count of all blocks received with uncorrectable
                    errors on this channel during this interval.
                   "
        ::= { hwAdslPortPerformanceStatInfoEntry 35 }

    hwAdslAturChanIntervalReceivedBlksInfo OBJECT-TYPE
        SYNTAX      PerfIntervalCount
        MAX-ACCESS  read-only
        STATUS      current
        DESCRIPTION
                   "The count of all encoded blocks received on this channel
                    during this interval.
                   "
        ::= { hwAdslPortPerformanceStatInfoEntry 36 }

    hwAdslAturChanIntervalTransmittedBlksInfo  OBJECT-TYPE
        SYNTAX      PerfIntervalCount
        MAX-ACCESS  read-only
        STATUS      current
        DESCRIPTION
                   "The count of all encoded blocks transmitted on this
                    channel during this interval.
                   "
        ::= { hwAdslPortPerformanceStatInfoEntry 37 }

    hwAdslAturChanIntervalCorrectedBlksInfo  OBJECT-TYPE
        SYNTAX      PerfIntervalCount
        MAX-ACCESS  read-only
        STATUS      current
        DESCRIPTION
                   "The count of all blocks received with errors that were
                    corrected on this channel during this interval.
                   "
        ::= { hwAdslPortPerformanceStatInfoEntry 38 }

    hwAdslAturChanIntervalUncorrectBlksInfo  OBJECT-TYPE
        SYNTAX      PerfIntervalCount
        MAX-ACCESS  read-only
        STATUS      current
        DESCRIPTION
                  "The count of all blocks received with uncorrectable
                   errors on this channel during this interval.
                  "
        ::= { hwAdslPortPerformanceStatInfoEntry 39 }

    hwAdslAtucIntervalSesLInfo OBJECT-TYPE
        SYNTAX      PerfIntervalCount
        UNITS       "seconds"
        MAX-ACCESS  read-only
        STATUS      current
        DESCRIPTION
                  "For the each interval, adslAtucIntervalSesL
                   reports the number of seconds during which
                   there have been severely errored seconds-line.
                   Unit: seconds
                  "
        ::= { hwAdslPortPerformanceStatInfoEntry 40 }

    hwAdslAtucIntervalUasLInfo OBJECT-TYPE
        SYNTAX      PerfIntervalCount
        UNITS       "seconds"
        MAX-ACCESS  read-only
        STATUS      current
        DESCRIPTION
                   "For the each interval, adslAtucIntervalUasL
                    reports the number of seconds during which
                    there have been unavailable seconds-line.
                    Unit: seconds
                   "
        ::= { hwAdslPortPerformanceStatInfoEntry 41 }

    hwAdslAturIntervalSesLInfo OBJECT-TYPE
        SYNTAX      PerfIntervalCount
        UNITS       "seconds"
        MAX-ACCESS  read-only
        STATUS      current
        DESCRIPTION
                   "For the each interval, adslAturIntervalSesL
                    reports the number of seconds during which
                    there have been severely errored seconds-line.
                    Unit: seconds
                   "
        ::= { hwAdslPortPerformanceStatInfoEntry 42 }

    hwAdslAturIntervalUasLInfo OBJECT-TYPE
        SYNTAX      PerfIntervalCount
        UNITS       "seconds"
        MAX-ACCESS  read-only
        STATUS      current
        DESCRIPTION
                   "For the each interval, adslAturIntervalUasL
                    reports the number of seconds during which
                    there have been unavailable seconds-line.
                    Unit: seconds
                   "
        ::= { hwAdslPortPerformanceStatInfoEntry 43 }

    hwAdslPortCurrentActModeInfo OBJECT-TYPE
        SYNTAX INTEGER {
                          adsl(1),
                          adsl2(2),
                          adsl2plus(3)
                       }
        MAX-ACCESS  read-only
        STATUS      current
        DESCRIPTION
                   "Instantaneous value of the technology type
                    that line is currently trained up under.
                    Options:
                    1. adsl(1)      - Indicates that line is currently trained up under adsl type
                    2. adsl2(2)     - Indicates that line is currently trained up under adsl2 type
	            2. adsl2plus(3) - Indicates that line is currently trained up under adsl2+ type
	           "
        ::= { hwAdslPortPerformanceStatInfoEntry 44 }

--  hwAdslPortRateChangeTrapParaTable

    hwadslPortRateChangeTrapParaInfoTable OBJECT-TYPE
        SYNTAX SEQUENCE OF HwadslPortRateChangeTrapParaInfoEntry
        MAX-ACCESS not-accessible
        STATUS current
        DESCRIPTION
                   "ADSL line rate change trap parameter table.
                    The index of this table is ifIndex.
                   "
        ::= { hwAdslMibObjects 23 }

    hwadslPortRateChangeTrapParaInfoEntry OBJECT-TYPE
        SYNTAX HwadslPortRateChangeTrapParaInfoEntry
        MAX-ACCESS not-accessible
        STATUS current
        DESCRIPTION
                   "ADSL line rate change trap parameter table.
                    The index of this entry is ifIndex.
                   "
        INDEX { ifIndex }
        ::= { hwadslPortRateChangeTrapParaInfoTable 1 }

    HwadslPortRateChangeTrapParaInfoEntry ::=
        SEQUENCE{
                    hwAdslPortRateChangeTrapIPIAIDInfo        OCTET STRING,
                    hwAdslPortRateChangeTrapMUXIDInfo         OCTET STRING,
                    hwAdslPortRateChangeTrapTimeStampInfo     Counter32,
                    hwAdslPortRateChangeTrapDSLineRateInfo    Gauge32,
                    hwAdslPortRateChangeTrapUSLineRateInfo    Gauge32,
                    hwAdslPortRateChangeTrapEventTypeInfo     OCTET STRING,
                    hwAdslPortRateChangeTrapDslTypeInfo       OCTET STRING
                }

    hwAdslPortRateChangeTrapIPIAIDInfo OBJECT-TYPE
        SYNTAX OCTET STRING (SIZE (0..63))
        MAX-ACCESS accessible-for-notify
        STATUS current
        DESCRIPTION
                   "The port IPIAID is reported when the port rate changes."
        ::= { hwadslPortRateChangeTrapParaInfoEntry 1 }

    hwAdslPortRateChangeTrapMUXIDInfo OBJECT-TYPE
        SYNTAX OCTET STRING (SIZE (0..20))
        MAX-ACCESS accessible-for-notify
        STATUS current
        DESCRIPTION
                   "The port MUXID is reported when the port rate changes.
                    Range: 0-20
                   "
        ::= { hwadslPortRateChangeTrapParaInfoEntry 2 }

    hwAdslPortRateChangeTrapTimeStampInfo OBJECT-TYPE
        SYNTAX Counter32
        UNITS "seconds"
        MAX-ACCESS accessible-for-notify
        STATUS current
        DESCRIPTION
                   "The time stamp of Line rate change trap.
                    Standard Unix format; as the number of seconds since 1/1/1970.
                    Unit:Seconds.
                   "
        ::= { hwadslPortRateChangeTrapParaInfoEntry 3 }

    hwAdslPortRateChangeTrapDSLineRateInfo OBJECT-TYPE
        SYNTAX Gauge32
        MAX-ACCESS accessible-for-notify
        STATUS current
        DESCRIPTION
                   "Down stream line rate after line rate change."
        ::= { hwadslPortRateChangeTrapParaInfoEntry 4 }

    hwAdslPortRateChangeTrapUSLineRateInfo OBJECT-TYPE
        SYNTAX Gauge32
        MAX-ACCESS accessible-for-notify
        STATUS current
        DESCRIPTION
                   "Up stream line rate after line rate change."
        ::= { hwadslPortRateChangeTrapParaInfoEntry 5 }

    hwAdslPortRateChangeTrapEventTypeInfo OBJECT-TYPE
        SYNTAX OCTET STRING (SIZE (0..2))
        MAX-ACCESS accessible-for-notify
        STATUS current
        DESCRIPTION
                   "Event type reported during the previous change of the rate
                    If both the upstream and downstream rates change, this leaf outputs character string 'DU'.
                    If only the upstream rates changes, this leaf outputs character string 'US'.
                    If only the downstream rates changes, this leaf outputs character string 'DS'.
                   "
        ::= { hwadslPortRateChangeTrapParaInfoEntry 6 }

    hwAdslPortRateChangeTrapDslTypeInfo OBJECT-TYPE
        SYNTAX OCTET STRING (SIZE (0..5))
        MAX-ACCESS accessible-for-notify
        STATUS current
        DESCRIPTION
                   "DSL line type of the port whose rate changes."
        ::= { hwadslPortRateChangeTrapParaInfoEntry 7 }

--  hwadslSysManagementParaCfgTable
    hwadslSysManagementParaCfgTable OBJECT IDENTIFIER ::= { hwAdslMibObjects 24 }
    hwadslPortRateChangeTrapCfgConfig OBJECT-TYPE
        SYNTAX INTEGER {
                           enabled(1),
                           disabled(2)
                       }
        MAX-ACCESS read-write
        STATUS current
        DESCRIPTION
                   "Enables or disables ADSL port line-rate change trap feature.
                    Options:
                    1. enabled(1)  - ADSL port line-rate change trap feature is enabled
                    2. disabled(2) - ADSL port line-rate change trap feature is disabled
                   "
        ::= { hwadslSysManagementParaCfgTable 1 }

    hwadsl2MaximumInterleavedDepth OBJECT-TYPE
        SYNTAX INTEGER {
                           maxInterleavedDepth64(1),
                           maxInterleavedDepth511(2)
                       }
        MAX-ACCESS read-write
        STATUS current
        DESCRIPTION
                "Set the ADSL2 maximum interleaved depth function.
                 Default values:maxInterleavedDepth511(2).
                 Options:
                 1. maxInterleavedDepth64(1)  - it means the interleaving depth up to 64 can be selected
                 2. maxInterleavedDepth511(2) - it means the interleaving depth up to 512 can be selected
                "
        ::= { hwadslSysManagementParaCfgTable 2 }

--  hwadslAtucPerfDataInfoTable
    hwadslAtucPerfDataInfoTable   OBJECT-TYPE
        SYNTAX          SEQUENCE OF HwadslAtucPerfDataInfoEntry
        MAX-ACCESS      not-accessible
        STATUS          current
        DESCRIPTION
                   "Table of querying the performance statistics of the ATUC port.
                    ADSL physical interfaces are
                    those ifEntries where ifType is equal to adsl(94).
                    The index of this table is ifIndex.
                   "
        ::= { hwAdslMibObjects 25 }

    hwadslAtucPerfDataInfoEntry       OBJECT-TYPE
        SYNTAX          HwadslAtucPerfDataInfoEntry
        MAX-ACCESS      not-accessible
        STATUS          current
        DESCRIPTION
                   "Table of querying the performance statistics of the ATUC port.
                    ADSL physical interfaces are
                    those ifEntries where ifType is equal to adsl(94).
                    The index of this entry is ifIndex.
                   "
        INDEX           { ifIndex }
        ::= { hwadslAtucPerfDataInfoTable 1 }

    HwadslAtucPerfDataInfoEntry ::=
        SEQUENCE {
                     hwAdslAtucPerfFailFullInitsInfo             Counter32,
                     hwAdslAtucPerfCurr15MinFailFullInitsInfo    Counter32,
                     hwAdslAtucPerfCurr1DayFailFullInitsInfo     Counter32,
                     hwAdslAtucPerfPrev1DayFailFullInitsInfo     Counter32,
                     hwAdslAtucPerfFullInitsInfo                 Counter32,
                     hwAdslAtucPerfCurr15MinFullInitsInfo        Counter32,
                     hwAdslAtucPerfCurr1DayFullInitsInfo         Counter32,
                     hwAdslAtucPerfPrev1DayFullInitsInfo         Counter32,
                     hwAdslAtucPerfCurr15MLeftrs                 Counter32,
                     hwAdslAtucPerfCurr15MEfb                    Counter32,
                     hwAdslAtucPerfCurr15MMinEftr                Counter32,
                     hwAdslAtucPerfCurr1DayLeftrs                Counter32,
                     hwAdslAtucPerfCurr1DayEfb                   Counter32,
                     hwAdslAtucPerfCurr1DayMinEftr               Counter32,
                     hwAdslAtucPerfPrev1DayLeftrs                Counter32,
                     hwAdslAtucPerfPrev1DayEfb                   Counter32,
                     hwAdslAtucPerfPrev1DayMinEftr               Counter32,
                     hwAdslAtucPerfCurrEverBeforeLeftrs          Counter32,
                     hwAdslAtucPerfCurrEverBeforeEfb             Counter32,
                     hwAdslAtucPerfCurrEverBeforeMinEftr         Counter32,
                     hwAdslAtucPerfCurr15MStartTime              DateAndTime,
                     hwAdslAtucPerfCurr1DayStartTime             DateAndTime,
                     hwAdslAtucPerfCurr15MInmainpeq              OCTET STRING,
                     hwAdslAtucPerfCurr15MInmame                 Counter32,
                     hwAdslAtucPerfCurr15MInmaiat                OCTET STRING,
                     hwAdslAtucPerfCurr1DayInmainpeq             OCTET STRING,
                     hwAdslAtucPerfCurr1DayInmame                Counter32,
                     hwAdslAtucPerfCurr1DayInmaiat               OCTET STRING,
                     hwAdslAtucPerfPre1DayInmainpeq              OCTET STRING,
                     hwAdslAtucPerfPre1DayInmame                 Counter32,
                     hwAdslAtucPerfPre1DayInmaiat                OCTET STRING,
                     hwAdslAtucPerfCurrEverBeforeInmainpeq       OCTET STRING,
                     hwAdslAtucPerfCurrEverBeforeInmame          Counter32,
                     hwAdslAtucPerfCurrEverBeforeInmaiat         OCTET STRING
                 }

    hwAdslAtucPerfFailFullInitsInfo OBJECT-TYPE
        SYNTAX Counter32
        MAX-ACCESS read-only
        STATUS current
        DESCRIPTION
                   "The count of the line initialization failed attempts since agent reset."
        ::= { hwadslAtucPerfDataInfoEntry 1 }

    hwAdslAtucPerfCurr15MinFailFullInitsInfo OBJECT-TYPE
        SYNTAX Counter32
        MAX-ACCESS read-only
        STATUS current
        DESCRIPTION
                   "The count of the line initialization failed attempts in the current 15 minutes interval. "
        ::= { hwadslAtucPerfDataInfoEntry 2 }

    hwAdslAtucPerfCurr1DayFailFullInitsInfo OBJECT-TYPE
        SYNTAX Counter32
        MAX-ACCESS read-only
        STATUS current
        DESCRIPTION
                   "The count of the line initialization failed attempts in the day
                    as measured by adslAtucPerfCurr1DayTimeElapsed.
                   "
        ::= { hwadslAtucPerfDataInfoEntry 3 }

    hwAdslAtucPerfPrev1DayFailFullInitsInfo OBJECT-TYPE
        SYNTAX Counter32
        MAX-ACCESS read-only
        STATUS current
        DESCRIPTION
                   "The count of the line initialization failed attempts in the most recent previous 1-day period."
        ::= { hwadslAtucPerfDataInfoEntry 4 }

    hwAdslAtucPerfFullInitsInfo OBJECT-TYPE
        SYNTAX Counter32
        MAX-ACCESS read-only
        STATUS current
        DESCRIPTION
                   "Count of the line initialization full attempts since agent reset."
        ::= { hwadslAtucPerfDataInfoEntry 5 }

    hwAdslAtucPerfCurr15MinFullInitsInfo OBJECT-TYPE
        SYNTAX Counter32
        MAX-ACCESS read-only
        STATUS current
        DESCRIPTION
                   "Count of the line initialization full attempts in the current 15 minute interval. "
        ::= { hwadslAtucPerfDataInfoEntry 6 }

    hwAdslAtucPerfCurr1DayFullInitsInfo OBJECT-TYPE
        SYNTAX Counter32
        MAX-ACCESS read-only
        STATUS current
        DESCRIPTION
                   "Count of the line initialization full attempts in the day as measured by adslAtucPerfCurr1DayTimeElapsed."
        ::= { hwadslAtucPerfDataInfoEntry 7 }

    hwAdslAtucPerfPrev1DayFullInitsInfo OBJECT-TYPE
        SYNTAX Counter32
        MAX-ACCESS read-only
        STATUS current
        DESCRIPTION
                   "Count of the line initialization full attempts in the most recent previous 1-day period."
        ::= { hwadslAtucPerfDataInfoEntry 8 }

    hwAdslAtucPerfCurr15MLeftrs OBJECT-TYPE
        SYNTAX Counter32
        MAX-ACCESS read-only
        STATUS current
        DESCRIPTION
                   "If retransmission is used in a given transmit direction, this parameter is a count of
                    the seconds with a near-end leftr defect present observed over the current 15 minutes
                    accumulation period.
                   "
        REFERENCE  "ITU-T G.997.1, paragraph 7.2.1.1.6 7.2.1.1.6 "
        ::= { hwadslAtucPerfDataInfoEntry 9 }

    hwAdslAtucPerfCurr15MEfb OBJECT-TYPE
        SYNTAX Counter32
        MAX-ACCESS read-only
        STATUS current
        DESCRIPTION
                "If retransmission is used in a given transmit direction, this parameter
                 is a count of the number of error-free bits observed over the current 15 minutes
                 accumulation period.
                 The near-end counter is only defined in upstream.
                "
        REFERENCE  "ITU-T G.997.1, paragraph 7.2.1.1.7 7.2.1.1.7 "
        ::= { hwadslAtucPerfDataInfoEntry 10 }

   hwAdslAtucPerfCurr15MMinEftr OBJECT-TYPE
        SYNTAX Counter32
        MAX-ACCESS read-only
        STATUS current
        DESCRIPTION
                   "If retransmission is used in a given transmit direction, this parameter MINEFTR reports
                    the minimum of the EFTR(Error-free throughput rate) observed over the current 15 minutes
                    accumulation period.
                    The near-end value is only defined in upstream.
                   "
        REFERENCE   "ITU-T G.997.1, paragraph 7.2.1.1.8 7.2.1.1.8 "
        ::= { hwadslAtucPerfDataInfoEntry 11 }

    hwAdslAtucPerfCurr1DayLeftrs OBJECT-TYPE
        SYNTAX Counter32
        MAX-ACCESS read-only
        STATUS current
        DESCRIPTION
                   "If retransmission is used in a given transmit direction, this parameter is a count of
                    the seconds with a near-end leftr defect present observed over the current 24 hours
                    accumulation period.
                   "
        REFERENCE   "ITU-T G.997.1, paragraph 7.2.1.1.6 7.2.1.1.6 "
        ::= { hwadslAtucPerfDataInfoEntry 12 }

    hwAdslAtucPerfCurr1DayEfb OBJECT-TYPE
        SYNTAX Counter32
        MAX-ACCESS read-only
        STATUS current
        DESCRIPTION
                "If retransmission is used in a given transmit direction, this parameter
                 is a count of the number of error-free bits current observed over the current 24 hours
                 accumulation period.
                 The near-end counter is only defined in upstream.
                "
        REFERENCE   "ITU-T G.997.1, paragraph 7.2.1.1.7 7.2.1.1.7 "
        ::= { hwadslAtucPerfDataInfoEntry 13 }

   hwAdslAtucPerfCurr1DayMinEftr OBJECT-TYPE
        SYNTAX Counter32
        MAX-ACCESS read-only
        STATUS current
        DESCRIPTION
                   "If retransmission is used in a given transmit direction, this parameter MINEFTR reports
                    the minimum of the EFTR(Error-free throughput rate) observed over the current 24 hours
                    accumulation period.
                    The near-end value is only defined in upstream.
                   "
        REFERENCE   "ITU-T G.997.1, paragraph 7.2.1.1.8 7.2.1.1.8 "
        ::= { hwadslAtucPerfDataInfoEntry 14 }

   hwAdslAtucPerfPrev1DayLeftrs OBJECT-TYPE
        SYNTAX Counter32
        MAX-ACCESS read-only
        STATUS current
        DESCRIPTION
                   "If retransmission is used in a given transmit direction, this parameter is a count of
                    the seconds with a near-end leftr defect present over the previous 24 hours
                    accumulation period during this interval.
                   "
        REFERENCE   "ITU-T G.997.1, paragraph 7.2.1.1.6 7.2.1.1.6 "
        ::= { hwadslAtucPerfDataInfoEntry 15 }

   hwAdslAtucPerfPrev1DayEfb OBJECT-TYPE
        SYNTAX Counter32
        MAX-ACCESS read-only
        STATUS current
        DESCRIPTION
                "If retransmission is used in a given transmit direction, this parameter
                 is a count of the number of error-free bits observed over the previous 24 hours
                 accumulation period during this interval.
                 The near-end counter is only defined in upstream.
                "
        REFERENCE   "ITU-T G.997.1, paragraph 7.2.1.1.7 7.2.1.1.7 "
        ::= { hwadslAtucPerfDataInfoEntry 16 }

   hwAdslAtucPerfPrev1DayMinEftr OBJECT-TYPE
        SYNTAX Counter32
        MAX-ACCESS read-only
        STATUS current
        DESCRIPTION
                   "If retransmission is used in a given transmit direction, this parameter MINEFTR reports
                    the minimum of the EFTR(Error-free throughput rate) observed over the previous 24 hours
                    accumulation period during this interval.
                    The near-end value is only defined in upstream.
                   "
        REFERENCE   "ITU-T G.997.1, paragraph 7.2.1.1.8 7.2.1.1.8 "
        ::= { hwadslAtucPerfDataInfoEntry 17 }

    hwAdslAtucPerfCurrEverBeforeLeftrs OBJECT-TYPE
        SYNTAX Counter32
        MAX-ACCESS read-only
        STATUS current
        DESCRIPTION
                   "If retransmission is used in a given transmit direction, this parameter is a count of
                    the seconds with a near-end leftr defect present observed ever before.
                   "
        REFERENCE   "ITU-T G.997.1, paragraph 7.2.1.1.6 7.2.1.1.6 "
        ::= { hwadslAtucPerfDataInfoEntry 18 }

   hwAdslAtucPerfCurrEverBeforeEfb OBJECT-TYPE
        SYNTAX Counter32
        MAX-ACCESS read-only
        STATUS current
        DESCRIPTION
                "If retransmission is used in a given transmit direction, this parameter
                 is a count of the number of error-free bits observed ever before.
                 The near-end counter is only defined in upstream.
                "
        REFERENCE   "ITU-T G.997.1, paragraph 7.2.1.1.7 7.2.1.1.7 "
        ::= { hwadslAtucPerfDataInfoEntry 19 }

   hwAdslAtucPerfCurrEverBeforeMinEftr OBJECT-TYPE
        SYNTAX Counter32
        MAX-ACCESS read-only
        STATUS current
        DESCRIPTION
                   "If retransmission is used in a given transmit direction, this parameter MINEFTR reports
                    the minimum of the EFTR(Error-free throughput rate) observed ever before.
                    The near-end value is only defined in upstream.
                   "
        REFERENCE  "ITU-T G.997.1, paragraph 7.2.1.1.8 7.2.1.1.8 "
        ::= { hwadslAtucPerfDataInfoEntry 20 }

   hwAdslAtucPerfCurr15MStartTime  OBJECT-TYPE
       SYNTAX      DateAndTime
       MAX-ACCESS  read-only
       STATUS      current
       DESCRIPTION
           "Start time of the current 15-minute performance statistics."
       ::= { hwadslAtucPerfDataInfoEntry 21 }

   hwAdslAtucPerfCurr1DayStartTime  OBJECT-TYPE
       SYNTAX      DateAndTime
       MAX-ACCESS  read-only
       STATUS      current
       DESCRIPTION
           "Start time of the current 1-day performance statistics."
       ::= { hwadslAtucPerfDataInfoEntry 22 }


   hwAdslAtucPerfCurr15MInmainpeq  OBJECT-TYPE
       SYNTAX      OCTET STRING  (SIZE(0..68))
       MAX-ACCESS  read-only
       STATUS      current
       DESCRIPTION
           "This parameter is a count of the INMAINPEQi anomalies
            occurring on the line during current 15 minutes.
            Each INMAINPEQ needs 4 bytes.
           "
       REFERENCE    "ITU-T G.997.1, paragraph 7.2.1"
       ::= { hwadslAtucPerfDataInfoEntry 23 }

   hwAdslAtucPerfCurr15MInmame  OBJECT-TYPE
       SYNTAX      Counter32
       MAX-ACCESS  read-only
       STATUS      current
       DESCRIPTION
           "This parameter is a count of the INMAME anomalies
            occurring on the line during current 15 minutes.
           "
       REFERENCE    "ITU-T G.997.1, paragraph 7.2.1"
       ::= { hwadslAtucPerfDataInfoEntry 24 }

   hwAdslAtucPerfCurr15MInmaiat  OBJECT-TYPE
       SYNTAX      OCTET STRING  (SIZE(0..32))
       MAX-ACCESS  read-only
       STATUS      current
       DESCRIPTION
           "This parameter is a count of the INMAIATi anomalies
            occurring on the line during current 15 minutes.
            Each INMAIAT needs 4 bytes.
           "
       REFERENCE    "ITU-T G.997.1, paragraph 7.2.1"
       ::= { hwadslAtucPerfDataInfoEntry 25 }

   hwAdslAtucPerfCurr1DayInmainpeq  OBJECT-TYPE
       SYNTAX      OCTET STRING  (SIZE(0..68))
       MAX-ACCESS  read-only
       STATUS      current
       DESCRIPTION
           "This parameter is a count of the INMAINPEQi anomalies
            occurring on the line during current 1 day.
            Each INMAINPEQ needs 4 bytes.
           "
       REFERENCE    "ITU-T G.997.1, paragraph 7.2.1"
       ::= { hwadslAtucPerfDataInfoEntry 26 }

   hwAdslAtucPerfCurr1DayInmame  OBJECT-TYPE
       SYNTAX      Counter32
       MAX-ACCESS  read-only
       STATUS      current
       DESCRIPTION
           "This parameter is a count of the INMAME anomalies
            occurring on the line during current 1 day.
           "
       REFERENCE    "ITU-T G.997.1, paragraph 7.2.1"
       ::= { hwadslAtucPerfDataInfoEntry 27 }

   hwAdslAtucPerfCurr1DayInmaiat  OBJECT-TYPE
       SYNTAX      OCTET STRING  (SIZE(0..32))
       MAX-ACCESS  read-only
       STATUS      current
       DESCRIPTION
           "This parameter is a count of the INMAIATi anomalies
            occurring on the line during current 1 day.
            Each INMAIAT needs 4 bytes.
           "
       REFERENCE    "ITU-T G.997.1, paragraph 7.2.1"
       ::= { hwadslAtucPerfDataInfoEntry 28 }

   hwAdslAtucPerfPre1DayInmainpeq  OBJECT-TYPE
       SYNTAX      OCTET STRING  (SIZE(0..68))
       MAX-ACCESS  read-only
       STATUS      current
       DESCRIPTION
           "This parameter is a count of the INMAINPEQi anomalies
            occurring on the line during the most recent previous 1-day period.
            Each INMAINPEQ needs 4 bytes.
           "
       REFERENCE    "ITU-T G.997.1, paragraph 7.2.1"
       ::= { hwadslAtucPerfDataInfoEntry 29 }

   hwAdslAtucPerfPre1DayInmame  OBJECT-TYPE
       SYNTAX      Counter32
       MAX-ACCESS  read-only
       STATUS      current
       DESCRIPTION
           "This parameter is a count of the INMAME anomalies
            occurring on the line during the most recent previous 1-day period.
           "
       REFERENCE    "ITU-T G.997.1, paragraph 7.2.1"
       ::= { hwadslAtucPerfDataInfoEntry 30 }

   hwAdslAtucPerfPre1DayInmaiat  OBJECT-TYPE
       SYNTAX      OCTET STRING  (SIZE(0..32))
       MAX-ACCESS  read-only
       STATUS      current
       DESCRIPTION
           "This parameter is a count of the INMAIATi anomalies
            occurring on the line during the most recent previous 1-day period.
            Each INMAIAT needs 4 bytes.
           "
       REFERENCE    "ITU-T G.997.1, paragraph 7.2.1"
       ::= { hwadslAtucPerfDataInfoEntry 31 }

   hwAdslAtucPerfCurrEverBeforeInmainpeq  OBJECT-TYPE
       SYNTAX      OCTET STRING  (SIZE(0..68))
       MAX-ACCESS  read-only
       STATUS      current
       DESCRIPTION
           "This parameter is a count of the INMAINPEQi anomalies
            occurring on the line ever before.
            Each INMAINPEQ needs 4 bytes.
           "
       REFERENCE    "ITU-T G.997.1, paragraph 7.2.1"
       ::= { hwadslAtucPerfDataInfoEntry 32 }

   hwAdslAtucPerfCurrEverBeforeInmame  OBJECT-TYPE
       SYNTAX      Counter32
       MAX-ACCESS  read-only
       STATUS      current
       DESCRIPTION
           "This parameter is a count of the INMAME anomalies
            occurring on the line ever before.
           "
       REFERENCE    "ITU-T G.997.1, paragraph 7.2.1"
       ::= { hwadslAtucPerfDataInfoEntry 33 }

   hwAdslAtucPerfCurrEverBeforeInmaiat  OBJECT-TYPE
       SYNTAX      OCTET STRING  (SIZE(0..32))
       MAX-ACCESS  read-only
       STATUS      current
       DESCRIPTION
           "This parameter is a count of the INMAIATi anomalies
            occurring on the line ever before.
            Each INMAIAT needs 4 bytes.
           "
       REFERENCE    "ITU-T G.997.1, paragraph 7.2.1"
       ::= { hwadslAtucPerfDataInfoEntry 34 }

-- hwadslAtucIntervalInfoTable
    hwadslAtucIntervalInfoTable   OBJECT-TYPE
        SYNTAX SEQUENCE OF HwadslAtucIntervalInfoEntry
        MAX-ACCESS      not-accessible
        STATUS          current
        DESCRIPTION
                   "This table provides one row for each ATUC
                    performance data collection interval.
                    ADSL physical interfaces are
                    those ifEntries where ifType is equal to adsl(94).
                    The index of this table is ifIndex.
                   "
        ::= { hwAdslMibObjects 26 }

    hwadslAtucIntervalInfoEntry   OBJECT-TYPE
        SYNTAX  HwadslAtucIntervalInfoEntry
        MAX-ACCESS      not-accessible
        STATUS          current
        DESCRIPTION
                   "This table provides one row for each ATUC
                    performance data collection interval.
                    ADSL physical interfaces are
                    those ifEntries where ifType is equal to adsl(94).
                    The index of this entry is ifIndex.
                   "
        INDEX  { ifIndex, adslAtucIntervalNumber }
        ::= { hwadslAtucIntervalInfoTable 1 }

    HwadslAtucIntervalInfoEntry ::=
        SEQUENCE {
                     hwAdslAtucIntervalFailFullInitsInfo    Counter32,
                     hwAdslAtucIntervalFullInitsInfo        Counter32,
                     hwAdslAtucIntervalLeftrs               Counter32,
                     hwAdslAtucIntervalEfb                  Counter32,
                     hwAdslAtucIntervalMinEftr              Counter32,
                     hwAdslAtucIntervalStartTime            DateAndTime,
                     hwAdslAtucIntervalInmainpeq            OCTET STRING,
                     hwAdslAtucIntervalInmame               Counter32,
                     hwAdslAtucIntervalInmaiat              OCTET STRING
                 }

    hwAdslAtucIntervalFailFullInitsInfo OBJECT-TYPE
        SYNTAX Counter32
        MAX-ACCESS read-only
        STATUS current
        DESCRIPTION
                   "The count of the line initialization failed attempts during the interval."
        ::= { hwadslAtucIntervalInfoEntry 1 }

    hwAdslAtucIntervalFullInitsInfo OBJECT-TYPE
        SYNTAX Counter32
        MAX-ACCESS read-only
        STATUS current
        DESCRIPTION
                   "Count of the line initialization full attempts during the interval."
        ::= { hwadslAtucIntervalInfoEntry 2 }

    hwAdslAtucIntervalLeftrs OBJECT-TYPE
        SYNTAX Counter32
        MAX-ACCESS read-only
        STATUS current
        DESCRIPTION
                   "If retransmission is used in a given transmit direction, this parameter is a count of
                    the seconds with a near-end leftr defect present observed over the previous 15 minutes
                    accumulation period during the interval.
                   "
        REFERENCE  "ITU-T G.997.1, paragraph 7.2.1.1.6 7.2.1.1.6"
        ::= { hwadslAtucIntervalInfoEntry 3 }

    hwAdslAtucIntervalEfb OBJECT-TYPE
        SYNTAX Counter32
        MAX-ACCESS read-only
        STATUS current
        DESCRIPTION
                "If retransmission is used in a given transmit direction, this parameter
                 is a count of the number of error-free bits observed over the previous 15 minutes
                 accumulation period during the interval.
                 The near-end counter is only defined in upstream.
                "
        REFERENCE  "ITU-T G.997.1, paragraph 7.2.1.1.6 7.2.1.1.7"
        ::= { hwadslAtucIntervalInfoEntry 4 }

    hwAdslAtucIntervalMinEftr OBJECT-TYPE
        SYNTAX Counter32
        MAX-ACCESS read-only
        STATUS current
        DESCRIPTION
                   "If retransmission is used in a given transmit direction, this parameter MINEFTR reports
                    the minimum of the EFTR(Error-free throughput rate) observed over the previous 15 minutes
                    accumulation period during the interval.
                    The near-end value is only defined in upstream.
                   "
        REFERENCE  "ITU-T G.997.1, paragraph 7.2.1.1.6 7.2.1.1.8"
        ::= { hwadslAtucIntervalInfoEntry 5 }

    hwAdslAtucIntervalStartTime  OBJECT-TYPE
       SYNTAX      DateAndTime
       MAX-ACCESS  read-only
       STATUS      current
       DESCRIPTION
           "Start time of the historical 15-minute performance statistics."
       ::= { hwadslAtucIntervalInfoEntry 6 }

    hwAdslAtucIntervalInmainpeq  OBJECT-TYPE
        SYNTAX      OCTET STRING  (SIZE(0..68))
        MAX-ACCESS  read-only
        STATUS      current
        DESCRIPTION
            "This parameter is a count of the INMAINPEQi anomalies
             occurring on the line at 15 minutes interval.
            "
        REFERENCE    "ITU-T G.997.1, paragraph 7.2.1"
        ::= { hwadslAtucIntervalInfoEntry 7 }

    hwAdslAtucIntervalInmame  OBJECT-TYPE
        SYNTAX      Counter32
        MAX-ACCESS  read-only
        STATUS      current
        DESCRIPTION
            "This parameter is a count of the INMAME anomalies
             occurring on the line at 15 minutes interval.
            "
        REFERENCE    "ITU-T G.997.1, paragraph 7.2.1"
        ::= { hwadslAtucIntervalInfoEntry 8}

    hwAdslAtucIntervalInmaiat  OBJECT-TYPE
        SYNTAX      OCTET STRING  (SIZE(0..32))
        MAX-ACCESS  read-only
        STATUS      current
        DESCRIPTION
            "This parameter is a count of the INMAIATi anomalies
             occurring on the line at 15 minutes interval.
             Each INMAIAT needs 4 bytes.
            "
        REFERENCE    "ITU-T G.997.1, paragraph 7.2.1"
        ::= { hwadslAtucIntervalInfoEntry 9}

-- adslAtucChanIntervalTable
    hwadslAtucChanIntervalInfoTable   OBJECT-TYPE
        SYNTAX          SEQUENCE OF HwadslAtucChanIntervalInfoEntry
        MAX-ACCESS      not-accessible
        STATUS          current
        DESCRIPTION
                   "Period table of collecting the ATUC channel performance data
                    This table is used to query the ATUC channel performance data collected in each period (a day is divided into 96 15-minute periods).
                    The indexes of this table are ifIndex and adslAtucChanIntervalNumber.
                   "
        ::= { hwAdslMibObjects 28 }

    hwadslAtucChanIntervalInfoEntry   OBJECT-TYPE
        SYNTAX          HwadslAtucChanIntervalInfoEntry
        MAX-ACCESS      not-accessible
        STATUS          current
        DESCRIPTION
                   "Period table of collecting the ATUC channel performance data
                    This table is used to query the ATUC channel performance data collected in each period (a day is divided into 96 15-minute periods).
                    The indexes of this entry are ifIndex and adslAtucChanIntervalNumber.
                   "
        INDEX  { ifIndex, adslAtucChanIntervalNumber }
        ::= { hwadslAtucChanIntervalInfoTable 1 }

    HwadslAtucChanIntervalInfoEntry ::=
        SEQUENCE {
                     hwadslAtucChanIntervalFecBlksInfo             PerfIntervalCount,
                     hwadslAtucChanIntervalHecBlksInfo             PerfIntervalCount,
                     hwadslAtucChanIntervalCrcBlksInfo             PerfIntervalCount,
                     hwadslAtucChanIntervalRtxCWInfo               Gauge32,
                     hwadslAtucChanIntervalRtxCorrectedCWInfo      Gauge32,
                     hwadslAtucChanIntervalRtxUncorrectedCWInfo    Gauge32,
                     hwAdslAtucChanIntervalStartTime               DateAndTime
                  }
    hwadslAtucChanIntervalFecBlksInfo OBJECT-TYPE
        SYNTAX      PerfIntervalCount
        MAX-ACCESS  read-only
        STATUS      current
        DESCRIPTION
                   "The count of all blocks received with FRC anomalies
                    on this channel during this interval.
                   "
        ::= { hwadslAtucChanIntervalInfoEntry 1 }

    hwadslAtucChanIntervalHecBlksInfo OBJECT-TYPE
        SYNTAX      PerfIntervalCount
        MAX-ACCESS  read-only
        STATUS      current
        DESCRIPTION
                   "The count of all blocks received with HRC anomalies
                    on this channel during this interval.
                   "
        ::= { hwadslAtucChanIntervalInfoEntry 2 }

    hwadslAtucChanIntervalCrcBlksInfo OBJECT-TYPE
        SYNTAX      PerfIntervalCount
        MAX-ACCESS  read-only
        STATUS      current
        DESCRIPTION
                   "The count of all blocks received with CRC anomalies
                    on this channel during this interval.
                   "
        ::= { hwadslAtucChanIntervalInfoEntry 3 }

    hwadslAtucChanIntervalRtxCWInfo OBJECT-TYPE
        SYNTAX      Gauge32
        MAX-ACCESS  read-only
        STATUS      current
        DESCRIPTION
                   "The count of units request retransmission on this channel during this interval."
        ::= { hwadslAtucChanIntervalInfoEntry 4 }

    hwadslAtucChanIntervalRtxCorrectedCWInfo OBJECT-TYPE
        SYNTAX      Gauge32
        MAX-ACCESS  read-only
        STATUS      current
        DESCRIPTION
                   "The count of units corrected by retransmission on this channel during this interval."
        ::= { hwadslAtucChanIntervalInfoEntry 5 }

    hwadslAtucChanIntervalRtxUncorrectedCWInfo OBJECT-TYPE
        SYNTAX      Gauge32
        MAX-ACCESS  read-only
        STATUS      current
        DESCRIPTION
                   "The count of units uncorrected by retransmission on this channel during this interval."
        ::= { hwadslAtucChanIntervalInfoEntry 6 }

    hwAdslAtucChanIntervalStartTime  OBJECT-TYPE
       SYNTAX      DateAndTime
       MAX-ACCESS  read-only
       STATUS      current
       DESCRIPTION
           "Start time of the historical 15-minute performance statistics."
       ::= { hwadslAtucChanIntervalInfoEntry 7 }

--hwAdsl2SCStatusInfoTable

    hwAdsl2SCStatusInfoTable OBJECT-TYPE
        SYNTAX SEQUENCE OF HwAdsl2SCStatusInfoEntry
        MAX-ACCESS not-accessible
        STATUS current
        DESCRIPTION
                   "The table hwAdsl2SCStatusInfoTable contains status parameters
                    of the ADSL2 sub-carriers.
                    The indexes of this table are ifIndex and hwAdsl2SCStatusDirectionInfo.
                   "
        ::= { hwAdslMibObjects 29 }

    hwAdsl2SCStatusInfoEntry OBJECT-TYPE
        SYNTAX HwAdsl2SCStatusInfoEntry
        MAX-ACCESS not-accessible
        STATUS current
        DESCRIPTION
                   "The table hwAdsl2SCStatusInfoTable contains status parameters
                    of the ADSL2 sub-carriers.
                    The indexes of this entry are ifIndex and hwAdsl2SCStatusDirectionInfo.
                   "
        INDEX { ifIndex, hwAdsl2SCStatusDirectionInfo }
        ::= { hwAdsl2SCStatusInfoTable 1 }

    HwAdsl2SCStatusInfoEntry ::=
        SEQUENCE {
                     hwAdsl2SCStatusDirectionInfo    INTEGER,
                     hwAdsl2SCStatusSnrInfo          OCTET STRING,
                     hwAdsl2SCStatusBitsAllocInfo    OCTET STRING,
                     hwAdsl2SCStatusGainAllocInfo    OCTET STRING,
                     hwAdsl2SCStatusLogInfo          OCTET STRING,
                     hwAdsl2SCStatusQlnInfo          OCTET STRING,
                     hwAdsl2SCStatusSnrMarginInfo    OCTET STRING,
                     hwAdsl2SCStatusTxPSDInfo        OCTET STRING
                 }

    hwAdsl2SCStatusDirectionInfo  OBJECT-TYPE
        SYNTAX INTEGER
                     {
                         upstream(1),
                         downstream(2)
                     }
        MAX-ACCESS  not-accessible
        STATUS      current
        DESCRIPTION
                   "The direction of the sub-carrier is either
                    upstream or downstream.
                    Options:
                    1. upstream(1)   - The direction of the sub-carrier is upstream
                    2. downstream(2) - The direction of the sub-carrier is downstream
                   "
        ::= { hwAdsl2SCStatusInfoEntry 1 }

    hwAdsl2SCStatusSnrInfo  OBJECT-TYPE
        SYNTAX OCTET STRING  (SIZE(0..512))
        MAX-ACCESS  read-only
        STATUS      current
        DESCRIPTION
                   "The SNR Margin per sub-carrier, expressing the ratio between
                    the received signal power and received noise power per
                    subscriber.  It is an array of 512 octets, designed for
                    supporting up to 512 (downstream) sub-carriers.
                    The number of utilized octets on downstream direction depends
                    on NSCds, and on upstream direction it depends on NSCus.  This
                    value is referred to here as NSC.
                    Octet i (0 <= i < NSC) is set to a value in the range 0 to
                    254 to indicate that the respective downstream or upstream sub-
                    carrier i has SNR of: (-32 + Adsl2SubcarrierSnr(i)/2) in dB
                    (i.e., -32 to 95dB).
                    The special value 255 means that no measurement could be done
                    for the subcarrier because it is out of the PSD mask passband
                    or that the noise PSD is out of range to be represented.
                    Each value in this array is 8 bits wide.
                   "
        ::= { hwAdsl2SCStatusInfoEntry 2 }

    hwAdsl2SCStatusBitsAllocInfo  OBJECT-TYPE
        SYNTAX OCTET STRING  (SIZE(0..256))
        MAX-ACCESS  read-only
        STATUS      current
        DESCRIPTION
                   "The bits allocation per sub-carrier. An array of 256 octets
                    (512 nibbles), designed for supporting up to 512 (downstream)
                    sub-carriers.
                    The number of utilized nibbles on downstream direction depends
                    on NSCds, and on upstream direction it depends on NSCus. This
                    value is referred to here as NSC.
                    Nibble i (0 <= i < NSC) is set to a value in the range 0
                    to 15 to indicate that the respective downstream or upstream
                    sub-carrier i has the same amount of bits allocation.
                   "
        ::= { hwAdsl2SCStatusInfoEntry 3 }

    hwAdsl2SCStatusGainAllocInfo  OBJECT-TYPE
        SYNTAX OCTET STRING  (SIZE(0..1024))
        MAX-ACCESS  read-only
        STATUS      current
        DESCRIPTION
                   "The gain allocation per sub-carrier. An array of 512 16-bits
                    values, designed for supporting up to 512 (downstream) sub-
                    carriers.
                    The number of utilized octets on downstream direction depends
                    on NSCds, and on upstream direction it depends on NSCus. This
                    value is referred to here as NSC.
                    Value i (0 <= i < NSC) is in the range 0 to 4093 to indicate
                    that the respective downstream or upstream sub-carrier i has the
                    same amount of gain value.
                    The gain value is represented as a multiple of 1/512 on a
                    linear scale. Each value in this array is 16 bits wide and is
                    stored in big endian format.
                   "
        ::= { hwAdsl2SCStatusInfoEntry 4 }

    hwAdsl2SCStatusLogInfo  OBJECT-TYPE
        SYNTAX OCTET STRING  (SIZE(0..1024))
        MAX-ACCESS  read-only
        STATUS      current
        DESCRIPTION
                   "An array of up to 512 real H(f) logarithmic representation
                    values in dB for the respective transmission direction. It is
                    designed to support up to 512 (downstream) sub-carriers.
                    The number of utilized values on downstream direction depends
                    on NSCds, and on upstream direction it depends on NSCus. This
                    value is referred to here as NSC.
                    Each array entry represents the real Hlog(f = i*Df) value for a
                    particular sub-carrier index i, (0 <= i < NSC).
                    The real Hlog(f) value is represented as (6-m(i)/10), with m(i)
                    in the range 0 to 1022. A special value m=1023 indicates that
                    no measurement could be done for the subcarrier because it is
                    out of the passband or that the attenuation is out of range to
                    be represented. This parameter is applicable in loop
                    diagnostic procedure and initialization.
                    Each value in this array is 16 bits wide and is stored
                    in big endian format.
                   "
        ::= { hwAdsl2SCStatusInfoEntry 5 }

    hwAdsl2SCStatusQlnInfo  OBJECT-TYPE
        SYNTAX OCTET STRING  (SIZE(0..512))
        MAX-ACCESS  read-only
        STATUS      current
        DESCRIPTION
                   "An array of up to 512 real Quiet Line Noise values in dBm/Hz
                    for the respective transmission direction. It is designed for
                    up to 512 (downstream) sub-carriers.
                    The number of utilized values on downstream direction depends
                    on NSCds, and on upstream direction it depends on NSCus. This
                    value is referred to here as NSC.
                    Each array entry represents the QLN(f = i*Df) value for a
                    particular sub-carrier index i, (0 <= i < NSC).
                    The QLN(f) is represented as (-23-n(i)/2), with n(i) in the
                    range 0 to 254. A special value n(i)=255 indicates that no
                    measurement could be done for the subcarrier because it is out
                    of the passband or that the noise PSD is out of range to be
                    represented.
                    This parameter is applicable in loop diagnostic procedure and
                    initialization. Each value in this array is 8 bits wide.
                   "
        ::= { hwAdsl2SCStatusInfoEntry 6 }

    hwAdsl2SCStatusSnrMarginInfo  OBJECT-TYPE
        SYNTAX OCTET STRING  (SIZE(0..1024))
        MAX-ACCESS  read-only
        STATUS      current
        DESCRIPTION
                   "SNR Margin is the maximum increase in dB of the noise power
                    received at the ATU (ATU-R on downstream direction and ATU-C
                    on upstream direction), such that the BER requirements are met
                    for all bearer channels received at the ATU. It ranges from
                    -640 to 630 units of 0.1 dB (physical values are -64 to 63 dB).
                   "
        ::= { hwAdsl2SCStatusInfoEntry 7 }

    hwAdsl2SCStatusTxPSDInfo  OBJECT-TYPE
        SYNTAX OCTET STRING  (SIZE(0..1024))
        MAX-ACCESS  read-only
        STATUS      current
        DESCRIPTION
                   "The PSD MASK per sub-carrier. An array of 512 16-bits
                    values, designed for supporting up to 512 (downstream) sub-carriers.
                    It ranges from -1400 to -300 units of 0.1 dBm/Hz (physical values
                    are -140 to -30 dBm/Hz)
                   "
        ::= { hwAdsl2SCStatusInfoEntry 8 }

--hwxdslDynamicProfCfgTable

    hwxdslDynamicProfCfgTable   OBJECT-TYPE
        SYNTAX          SEQUENCE OF HwxdslDynamicProfCfgEntry
        MAX-ACCESS      not-accessible
        STATUS          current
        DESCRIPTION
                   "This table includes common parameters of the xDSL Dynamic profile.
                    The index of this table is hwxdslDynamicProfProfileNameCfg.
                   "
        ::= { hwAdslMibObjects 30  }

    hwxdslDynamicProfCfgEntry   OBJECT-TYPE
        SYNTAX          HwxdslDynamicProfCfgEntry
        MAX-ACCESS      not-accessible
        STATUS          current
        DESCRIPTION
                   "This table includes common parameters of the xDSL Dynamic profile.
                    The index of this entry is hwxdslDynamicProfProfileNameCfg.
                   "
        INDEX  {hwxdslDynamicProfProfileNameCfg }
        ::= { hwxdslDynamicProfCfgTable 1 }

    HwxdslDynamicProfCfgEntry ::=
        SEQUENCE {
                     hwxdslDynamicProfProfileNameCfg           OCTET STRING,
                     hwxdslDynamicProfXtuTransSysEnaCfg        BITS,
                     hwxdslDynamicProfBitSwapDSCfg             INTEGER,
                     hwxdslDynamicProfBitSwapUSCfg             INTEGER,
                     hwxdslDynamicProfTargetSnrmDsCfg          Unsigned32,
                     hwxdslDynamicProfTargetSnrmUsCfg          Unsigned32,
                     hwxdslDynamicProfMaxSnrmDsCfg             Unsigned32,
                     hwxdslDynamicProfMaxSnrmUsCfg             Unsigned32,
                     hwxdslDynamicProfMinSnrmDsCfg             Unsigned32,
                     hwxdslDynamicProfMinSnrmUsCfg             Unsigned32,
                     hwxdslDynamicProfCh1MinProtectionDsCfg    INTEGER,
                     hwxdslDynamicProfCh1MinProtectionUsCfg    INTEGER,
                     hwxdslDynamicProfCh1MaxDelayDsCfg         Unsigned32,
                     hwxdslDynamicProfCh1MaxDelayUsCfg         Unsigned32,
                     hwxdslDynamicProfCh2MinProtectionDsCfg    INTEGER,
                     hwxdslDynamicProfCh2MinProtectionUsCfg    INTEGER,
                     hwxdslDynamicProfCh2MaxDelayDsCfg         Unsigned32,
                     hwxdslDynamicProfCh2MaxDelayUsCfg         Unsigned32,
                     hwxdslDynamicProfPmModeCfg                BITS,
                     hwxdslDynamicProfL0TimeCfg                Unsigned32,
                     hwxdslDynamicProfL2TimeCfg                Unsigned32,
                     hwxdslDynamicProfL2AtprCfg                Unsigned32,
                     hwxdslDynamicProfL2AtprtCfg               Unsigned32,
                     hwxdslDynamicProfDpboEPsdCfg              OCTET STRING,
                     hwxdslDynamicProfDpboEsELCfg              Unsigned32,
                     hwxdslDynamicProfDpboEscmCfg              OCTET STRING,
                     hwxdslDynamicProfDpboMusCfg               Unsigned32,
                     hwxdslDynamicProfDpboFMinCfg              Unsigned32,
                     hwxdslDynamicProfDpboFMaxCfg              Unsigned32,
                     hwxdslDynamicProfUpboPsdBandCfg           OCTET STRING,
                     hwxdslDynamicProfUpboKLFCfg               INTEGER,
                     hwxdslDynamicProfUpboKLCfg                Unsigned32,
                     hwxdslDynamicProfRfiBandsCfg              OCTET STRING,
                     hwxdslDynamicProfToneBlackOutCfg          OCTET STRING,
                     hwxdslDynamicProfCarMaskDSCfg             OCTET STRING,
                     hwxdslDynamicProfCarMaskUSCfg             OCTET STRING,
                     hwxdslDynamicProfXdslModeCfg              INTEGER,
                     hwxdslDynamicProfMaxNomPsdDsCfg           Integer32,
                     hwxdslDynamicProfMaxNomPsdUsCfg           Integer32,
                     hwxdslDynamicProfMaxNomAtpDsCfg           Unsigned32,
                     hwxdslDynamicProfMaxNomAtpUsCfg           Unsigned32,
                     hwxdslDynamicProfPsdMaskDsCfg             OCTET STRING,
                     hwxdslDynamicProfPsdMaskUsCfg             OCTET STRING,
                     hwxdslDynamicProfLimitMaskCfg             INTEGER,
                     hwxdslDynamicProfClassMaskCfg             INTEGER,
                     hwxdslDynamicProfBandOptUsageCfg          INTEGER,
                     hwxdslDynamicProfVirtualNoiseModeDsCfg    INTEGER,
                     hwxdslDynamicProfVirtualNoiseModeUsCfg    INTEGER,
                     hwxdslDynamicProfVirtualNoiseDsCfg        OCTET STRING,
                     hwxdslDynamicProfVirtualNoiseUsCfg        OCTET STRING,
                     hwxdslDynamicProfRowStatusCfg             RowStatus
                 }

    hwxdslDynamicProfProfileNameCfg OBJECT-TYPE
        SYNTAX      OCTET STRING(SIZE(1..32))
        MAX-ACCESS  not-accessible
        STATUS      current
        DESCRIPTION
                   "The name of xDSL Dynamic Profile."
        ::= { hwxdslDynamicProfCfgEntry 1 }

    hwxdslDynamicProfXtuTransSysEnaCfg OBJECT-TYPE
    SYNTAX  BITS {
                     ansit1413(0),
                     etsi(1),
                     g9921PotsNonOverlapped(2),
                     g9921PotsOverlapped(3),
                     g9921IsdnNonOverlapped(4),
                     g9921isdnOverlapped(5),
                     g9921tcmIsdnNonOverlapped(6),
                     g9921tcmIsdnOverlapped(7),
                     g9922potsNonOverlapped(8),
                     g9922potsOverlapped(9),
                     g9922tcmIsdnNonOverlapped(10),
                     g9922tcmIsdnOverlapped(11),
                     g9921tcmIsdnSymmetric(12),
                     reserved1(13),
                     reserved2(14),
                     reserved3(15),
                     reserved4(16),
                     reserved5(17),
                     g9923PotsNonOverlapped(18),
                     g9923PotsOverlapped(19),
                     g9923IsdnNonOverlapped(20),
                     g9923isdnOverlapped(21),
                     reserved6(22),
                     reserved7(23),
                     g9924potsNonOverlapped(24),
                     g9924potsOverlapped(25),
                     reserved8(26),
                     reserved9(27),
                     g9923AnnexIAllDigNonOverlapped(28),
                     g9923AnnexIAllDigOverlapped(29),
                     g9923AnnexJAllDigNonOverlapped(30),
                     g9923AnnexJAllDigOverlapped(31),
                     g9924AnnexIAllDigNonOverlapped(32),
                     g9924AnnexIAllDigOverlapped(33),
                     g9923AnnexLMode1NonOverlapped(34),
                     g9923AnnexLMode2NonOverlapped(35),
                     g9923AnnexLMode3Overlapped(36),
                     g9923AnnexLMode4Overlapped(37),
                     g9923AnnexMPotsNonOverlapped(38),
                     g9923AnnexMPotsOverlapped(39),
                     g9925PotsNonOverlapped(40),
                     g9925PotsOverlapped(41),
                     g9925IsdnNonOverlapped(42),
                     g9925isdnOverlapped(43),
                     reserved10(44),
                     reserved11(45),
                     g9925AnnexIAllDigNonOverlapped(46),
                     g9925AnnexIAllDigOverlapped(47),
                     g9925AnnexJAllDigNonOverlapped(48),
                     g9925AnnexJAllDigOverlapped(49),
                     g9925AnnexMPotsNonOverlapped(50),
                     g9925AnnexMPotsOverlapped(51),
                     reserved12(52),
                     reserved13(53),
                     reserved14(54),
                     reserved15(55),
                     reserved16(56),
                     reserved17(57),
                     reserved18(58),
                     reserved19(59),
                     reserved20(60),
                     reserved21(61),
                     reserved22(62),
                     reserved23(63),
                     reserved24(64),
                     reserved25(65),
                     reserved26(66),
                     reserved27(67),
                     reserved28(68),
                     reserved29(69),
                     reserved30(70),
                     reserved31(71),
                     g9932AnnexAPots(72),
                     g9932AnnexAIsdn(73),
                     g9932AnnexBPots(74),
                     g9932AnnexBIsdn(75),
                     g9932AnnexCPots(76),
                     g9932AnnexCIsdn(77),
                     reserved32(78),
                     reserved33(79)
                 }
        MAX-ACCESS  read-create
        STATUS      current
        DESCRIPTION
                   "XTU Transmission System Enabling (ATSE). A list of the
                    different coding types enabled in this profile. It is coded
                    in a bit-map representation with 1 or more bits set. A bit
                    set to '1' means that the XTUs may apply the respective
                    coding for the xDSL line. A bit set to '0' means that
                    the XTUs cannot apply the respective coding for the XDSL
                    line. All 'reserved' bits should be set to '0'.
                   "
        ::= { hwxdslDynamicProfCfgEntry 2 }

    hwxdslDynamicProfBitSwapDSCfg OBJECT-TYPE
        SYNTAX INTEGER {
                           disable(1),
                           enable(2),
                           invalidValue(-1)
                       }
        MAX-ACCESS  read-create
        STATUS      current
        DESCRIPTION
                   "Enables or disables the bit swap downstream of a line.
                    Options:
                    1. disable(1)       - The bit swap downstream of a line is disabled
                    2. enable(2)        - The bit swap downstream of a line is enabled
                    3. invalidValue(-1) - Invalid value
                   "
        ::= { hwxdslDynamicProfCfgEntry 3 }

    hwxdslDynamicProfBitSwapUSCfg OBJECT-TYPE
        SYNTAX      INTEGER {
                                disable(1),
                                enable(2),
                                invalidValue(-1)
                            }
        MAX-ACCESS  read-create
        STATUS      current
        DESCRIPTION
                   "Enables or disables the bit swap upstream of a line.
                    Options:
                    1. disable(1)       - The bit swap upstream of a line is disabled
                    2. enable(2)        - The bit swap upstream of a line is enabled
                    3. invalidValue(-1) - Invalid value
                   "
        ::= { hwxdslDynamicProfCfgEntry 4 }

    hwxdslDynamicProfTargetSnrmDsCfg OBJECT-TYPE
        SYNTAX      Unsigned32(0..310)
        UNITS       "0.1 dB"
        MAX-ACCESS  read-create
        STATUS      current
        DESCRIPTION
                  "The target Noise Margin the xTU-R receiver shall achieve,
                   relative to the BER requirement for each of the downstream
                   bearer channels, to successfully complete initialization.
                   The target noise margin ranges from 0 to 310 units of 0.1 dB
                   (Physical values are 0 to 31 dB).
                   Range: 0-310
                   Unit: 0.1 dB
                  "
        ::= { hwxdslDynamicProfCfgEntry 5 }

    hwxdslDynamicProfTargetSnrmUsCfg OBJECT-TYPE
        SYNTAX      Unsigned32(0..310)
        UNITS       "0.1 dB"
        MAX-ACCESS  read-create
        STATUS      current
        DESCRIPTION
                  "The target Noise Margin the xTU-C receiver shall achieve,
                   relative to the BER requirement for each of the downstream
                   bearer channels, to successfully complete initialization.
                   The target noise margin ranges from 0 to 310 units of 0.1 dB
                   (Physical values are 0 to 31 dB).
                   Range: 0-310
                   Unit: 0.1 dB
                  "
        ::= { hwxdslDynamicProfCfgEntry 6 }

    hwxdslDynamicProfMaxSnrmDsCfg OBJECT-TYPE
        SYNTAX      Unsigned32(0..310)
        UNITS       "0.1 dB"
        MAX-ACCESS  read-create
        STATUS      current
        DESCRIPTION
                   "The maximum Noise Margin the xTU-R receiver shall achieve,
                    relative to the BER requirement for each of the downstream
                    bearer channels, to successfully complete initialization.
                    The target noise margin ranges from 0 to 310 units of 0.1 dB
                    (Physical values are 0 to 31 dB).
                    Range: 0-310
                    Unit: 0.1 dB
                   "
        ::= { hwxdslDynamicProfCfgEntry 7 }

    hwxdslDynamicProfMaxSnrmUsCfg OBJECT-TYPE
        SYNTAX      Unsigned32(0..310)
        UNITS       "0.1 dB"
        MAX-ACCESS  read-create
        STATUS      current
        DESCRIPTION
                   "The maximum Noise Margin the xTU-C receiver shall achieve,
                    relative to the BER requirement for each of the downstream
                    bearer channels, to successfully complete initialization.
                    The target noise margin ranges from 0 to 310 units of 0.1 dB
                    (Physical values are 0 to 31 dB).
                    Range: 0-310
                    Unit: 0.1 dB
                   "
        ::= { hwxdslDynamicProfCfgEntry 8 }

    hwxdslDynamicProfMinSnrmDsCfg OBJECT-TYPE
        SYNTAX      Unsigned32(0..310)
        UNITS       "0.1 dB"
        MAX-ACCESS  read-create
        STATUS      current
        DESCRIPTION
                   "The minimum Noise Margin the xTU-R receiver shall achieve,
                    relative to the BER requirement for each of the downstream
                    bearer channels, to successfully complete initialization.
                    The target noise margin ranges from 0 to 310 units of 0.1 dB
                    (Physical values are 0 to 31 dB).
                    Range: 0-310
                    Unit: 0.1 dB
                   "
        ::= { hwxdslDynamicProfCfgEntry 9 }

    hwxdslDynamicProfMinSnrmUsCfg OBJECT-TYPE
        SYNTAX      Unsigned32(0..310)
        UNITS       "0.1 dB"
        MAX-ACCESS  read-create
        STATUS      current
        DESCRIPTION
                   "The minimum Noise Margin the xTU-C receiver shall achieve,
                    relative to the BER requirement for each of the downstream
                    bearer channels, to successfully complete initialization.
                    The target noise margin ranges from 0 to 310 units of 0.1 dB
                    (Physical values are 0 to 31 dB).
                    Range: 0-310
                    Unit: 0.1 dB
                   "
        ::= { hwxdslDynamicProfCfgEntry 10 }

    hwxdslDynamicProfCh1MinProtectionDsCfg OBJECT-TYPE
        SYNTAX      INTEGER {
                                noProtection (1),
                                halfSymbol (2),
                                singleSymbol (3),
                                twoSymbols (4),
                                threeSymbols (5),
                                fourSymbols (6),
                                fiveSymbols (7),
                                sixSymbols (8),
                                sevenSymbols (9),
                                eightSymbols (10),
                                nineSymbols (11),
                                tenSymbols (12),
                                elevenSymbols (13),
                                twelveSymbols (14),
                                thirteenSymbols (15),
                                fourteenSymbols (16),
                                fifteenSymbols (17),
                                sixteenSymbols (18),
                                invalidValue(-1)
                            }
        MAX-ACCESS  read-create
        STATUS      current
        DESCRIPTION
                   "Minimum Impulse Noise Protection on Downstream direction. The
                    minimum impulse noise protection for the bearer channel,
                    expressed in symbols. The parameter can take the following
                    values: noProtection (i.e., INP not required), halfSymbol
                    (i.e., INP length is 1/2 symbol) and 1-16 symbols in steps
                    of 1 symbol.
                    Options:
                    1. noProtection (1)      - Indicates that the INP value is 0
                    2. halfSymbol (2)        - Indicates that the INP value is 0.5
                    3. singleSymbol (3)      - Indicates that the INP value is 1
                    4. twoSymbols (4)        - Indicates that the INP value is 2
                    5. threeSymbols (5)      - Indicates that the INP value is 3
                    6. fourSymbols (6)       - Indicates that the INP value is 4
                    7. fiveSymbols (7)       - Indicates that the INP value is 5
                    8. sixSymbols (8)        - Indicates that the INP value is 6
                    9. sevenSymbols (9)      - Indicates that the INP value is 7
                    10. eightSymbols (10)    - Indicates that the INP value is 8
                    11. nineSymbols (11)     - Indicates that the INP value is 9
                    12. tenSymbols (12)      - Indicates that the INP value is 10
                    13. elevenSymbols (13)   - Indicates that the INP value is 11
                    14. twelveSymbols (14)   - Indicates that the INP value is 12
                    15. thirteenSymbols (15) - Indicates that the INP value is 13
                    16. fourteenSymbols (16) - Indicates that the INP value is 14
                    17. fifteenSymbols (17)  - Indicates that the INP value is 15
                    18. sixteenSymbols (18)  - Indicates that the INP value is 16
                    19. invalidValue(-1)     - Invalid value
                   "
        REFERENCE    "ITU-T G.997.1, paragraph 7.3.2.3"
        ::= { hwxdslDynamicProfCfgEntry 11 }

    hwxdslDynamicProfCh1MinProtectionUsCfg OBJECT-TYPE
SYNTAX INTEGER {
                   noProtection (1),
                   halfSymbol (2),
                   singleSymbol (3),
                   twoSymbols (4),
                   threeSymbols (5),
                   fourSymbols (6),
                   fiveSymbols (7),
                   sixSymbols (8),
                   sevenSymbols (9),
                   eightSymbols (10),
                   nineSymbols (11),
                   tenSymbols (12),
                   elevenSymbols (13),
                   twelveSymbols (14),
                   thirteenSymbols (15),
                   fourteenSymbols (16),
                   fifteenSymbols (17),
                   sixteenSymbols (18),
                   invalidValue(-1)
               }
        MAX-ACCESS  read-create
        STATUS      current
        DESCRIPTION
                   "Minimum Impulse Noise Protection on Upstream direction. The
                    minimum impulse noise protection for the bearer channel,
                    expressed in symbols. The parameter can take the following
                    values: noProtection (i.e., INP not required), halfSymbol
                    (i.e., INP length is 1/2 symbol) and 1-16 symbols in steps
                    of 1 symbol.
                    Options:
                    1. noProtection (1)      - Indicates that the INP value is 0
                    2. halfSymbol (2)        - Indicates that the INP value is 0.5
                    3. singleSymbol (3)      - Indicates that the INP value is 1
                    4. twoSymbols (4)        - Indicates that the INP value is 2
                    5. threeSymbols (5)      - Indicates that the INP value is 3
                    6. fourSymbols (6)       - Indicates that the INP value is 4
                    7. fiveSymbols (7)       - Indicates that the INP value is 5
                    8. sixSymbols (8)        - Indicates that the INP value is 6
                    9. sevenSymbols (9)      - Indicates that the INP value is 7
                    10. eightSymbols (10)    - Indicates that the INP value is 8
                    11. nineSymbols (11)     - Indicates that the INP value is 9
                    12. tenSymbols (12)      - Indicates that the INP value is 10
                    13. elevenSymbols (13)   - Indicates that the INP value is 11
                    14. twelveSymbols (14)   - Indicates that the INP value is 12
                    15. thirteenSymbols (15) - Indicates that the INP value is 13
                    16. fourteenSymbols (16) - Indicates that the INP value is 14
                    17. fifteenSymbols (17)  - Indicates that the INP value is 15
                    18. sixteenSymbols (18)  - Indicates that the INP value is 16
                    19. invalidValue(-1)     - Invalid value
                   "
        REFERENCE    "ITU-T G.997.1, paragraph 7.3.2.3"
        ::= { hwxdslDynamicProfCfgEntry 12 }

    hwxdslDynamicProfCh1MaxDelayDsCfg OBJECT-TYPE
        SYNTAX      Unsigned32(0..200)
        UNITS       "milliseconds"
        MAX-ACCESS  read-create
        STATUS      current
        DESCRIPTION
                   "Maximum Interleave Delay on Downstream direction. The maximum
                    one-way interleaving delay introduced by the PMS-TC on
                    Downstream direction. The XTUs shall choose the S (factor) and
                    D (depth) values such that the actual one-way interleaving
                    delay is as close as possible to, but less than or equal to,
                    hwxdslDynamicProfCh1MaxDelayDs. The delay is coded in ms,
                    with the value 0 indicating no delay bound is being imposed.
                    Range: 0-200
                    Unit: milliseconds
                   "
        REFERENCE    "ITU-T G.997.1, paragraph 7.3.2.2"
        ::= { hwxdslDynamicProfCfgEntry 13 }

    hwxdslDynamicProfCh1MaxDelayUsCfg OBJECT-TYPE
        SYNTAX      Unsigned32(0..200)
        UNITS       "milliseconds"
        MAX-ACCESS  read-create
        STATUS      current
        DESCRIPTION
                   "Maximum Interleave Delay on Upstream direction. The maximum
                    one-way interleaving delay introduced by the PMS-TC on
                    Upstream direction. The XTUs shall choose the S (factor) and
                    D (depth) values such that the actual one-way interleaving
                    delay is as close as possible to, but less than or equal to,
                    hwxdslDynamicProfCh1MaxDelayUs. The delay is coded in ms,
                    with the value 0 indicating no delay bound is being imposed.
                    Range: 0-200
                    Unit: milliseconds
                   "
        REFERENCE "ITU-T G.997.1, paragraph 7.3.2.2"
        ::= { hwxdslDynamicProfCfgEntry 14 }

    hwxdslDynamicProfCh2MinProtectionDsCfg OBJECT-TYPE
        SYNTAX INTEGER {
                           noProtection (1),
                           halfSymbol (2),
                           singleSymbol (3),
                           twoSymbols (4),
                           threeSymbols (5),
                           fourSymbols (6),
                           fiveSymbols (7),
                           sixSymbols (8),
                           sevenSymbols (9),
                           eightSymbols (10),
                           nineSymbols (11),
                           tenSymbols (12),
                           elevenSymbols (13),
                           twelveSymbols (14),
                           thirteenSymbols (15),
                           fourteenSymbols (16),
                           fifteenSymbols (17),
                           sixteenSymbols (18),
                           invalidValue(-1)
                       }
        MAX-ACCESS  read-create
        STATUS      current
        DESCRIPTION
                   "Minimum Impulse Noise Protection on Downstream direction. The
                    minimum impulse noise protection for the bearer channel,
                    expressed in symbols. The parameter can take the following
                    values: noProtection (i.e., INP not required), halfSymbol
                    (i.e., INP length is 1/2 symbol) and 1-16 symbols in steps
                    of 1 symbol.
                    Options:
                    1. noProtection (1)      - Indicates that the INP value is 0
                    2. halfSymbol (2)        - Indicates that the INP value is 0.5
                    3. singleSymbol (3)      - Indicates that the INP value is 1
                    4. twoSymbols (4)        - Indicates that the INP value is 2
                    5. threeSymbols (5)      - Indicates that the INP value is 3
                    6. fourSymbols (6)       - Indicates that the INP value is 4
                    7. fiveSymbols (7)       - Indicates that the INP value is 5
                    8. sixSymbols (8)        - Indicates that the INP value is 6
                    9. sevenSymbols (9)      - Indicates that the INP value is 7
                    10. eightSymbols (10)    - Indicates that the INP value is 8
                    11. nineSymbols (11)     - Indicates that the INP value is 9
                    12. tenSymbols (12)      - Indicates that the INP value is 10
                    13. elevenSymbols (13)   - Indicates that the INP value is 11
                    14. twelveSymbols (14)   - Indicates that the INP value is 12
                    15. thirteenSymbols (15) - Indicates that the INP value is 13
                    16. fourteenSymbols (16) - Indicates that the INP value is 14
                    17. fifteenSymbols (17)  - Indicates that the INP value is 15
                    18. sixteenSymbols (18)  - Indicates that the INP value is 16
                    19. invalidValue(-1)     - Invalid value
                   "
        REFERENCE    "ITU-T G.997.1, paragraph 7.3.2.3"
        ::= { hwxdslDynamicProfCfgEntry 15 }

    hwxdslDynamicProfCh2MinProtectionUsCfg OBJECT-TYPE
        SYNTAX INTEGER {
                           noProtection (1),
                           halfSymbol (2),
                           singleSymbol (3),
                           twoSymbols (4),
                           threeSymbols (5),
                           fourSymbols (6),
                           fiveSymbols (7),
                           sixSymbols (8),
                           sevenSymbols (9),
                           eightSymbols (10),
                           nineSymbols (11),
                           tenSymbols (12),
                           elevenSymbols (13),
                           twelveSymbols (14),
                           thirteenSymbols (15),
                           fourteenSymbols (16),
                           fifteenSymbols (17),
                           sixteenSymbols (18),
                           invalidValue(-1)
                       }
        MAX-ACCESS  read-create
        STATUS      current
        DESCRIPTION
                   "Minimum Impulse Noise Protection on Upstream direction. The
                    minimum impulse noise protection for the bearer channel,
                    expressed in symbols. The parameter can take the following
                    values: noProtection (i.e., INP not required), halfSymbol
                    (i.e., INP length is 1/2 symbol) and 1-16 symbols in steps
                    of 1 symbol.
                    Options:
                    1. noProtection (1)      - Indicates that the INP value is 0
                    2. halfSymbol (2)        - Indicates that the INP value is 0.5
                    3. singleSymbol (3)      - Indicates that the INP value is 1
                    4. twoSymbols (4)        - Indicates that the INP value is 2
                    5. threeSymbols (5)      - Indicates that the INP value is 3
                    6. fourSymbols (6)       - Indicates that the INP value is 4
                    7. fiveSymbols (7)       - Indicates that the INP value is 5
                    8. sixSymbols (8)        - Indicates that the INP value is 6
                    9. sevenSymbols (9)      - Indicates that the INP value is 7
                    10. eightSymbols (10)    - Indicates that the INP value is 8
                    11. nineSymbols (11)     - Indicates that the INP value is 9
                    12. tenSymbols (12)      - Indicates that the INP value is 10
                    13. elevenSymbols (13)   - Indicates that the INP value is 11
                    14. twelveSymbols (14)   - Indicates that the INP value is 12
                    15. thirteenSymbols (15) - Indicates that the INP value is 13
                    16. fourteenSymbols (16) - Indicates that the INP value is 14
                    17. fifteenSymbols (17)  - Indicates that the INP value is 15
                    18. sixteenSymbols (18)  - Indicates that the INP value is 16
                    19. invalidValue(-1)     - Invalid value
                   "
        REFERENCE    "ITU-T G.997.1, paragraph 7.3.2.3"
        ::= { hwxdslDynamicProfCfgEntry 16 }

    hwxdslDynamicProfCh2MaxDelayDsCfg OBJECT-TYPE
        SYNTAX      Unsigned32(0..200)
        UNITS       "milliseconds"
        MAX-ACCESS  read-create
        STATUS      current
        DESCRIPTION
                  "Maximum Interleave Delay on Downstream direction. The maximum
                   one-way interleaving delay introduced by the PMS-TC on
                   Downstream direction. The XTUs shall choose the S (factor) and
                   D (depth) values such that the actual one-way interleaving
                   delay is as close as possible to, but less than or equal to,
                   hwxdslDynamicProfCh2MaxDelayDs. The delay is coded in ms,
                   with the value 0 indicating no delay bound is being imposed.
                   Range: 0-200
                   Unit: milliseconds
                  "
        REFERENCE    "ITU-T G.997.1, paragraph 7.3.2.2"
        ::= { hwxdslDynamicProfCfgEntry 17 }

    hwxdslDynamicProfCh2MaxDelayUsCfg OBJECT-TYPE
        SYNTAX      Unsigned32(0..200)
        UNITS       "milliseconds"
        MAX-ACCESS  read-create
        STATUS      current
        DESCRIPTION
                   "Maximum Interleave Delay on Upstream direction. The maximum
                    one-way interleaving delay introduced by the PMS-TC on
                    Upstream direction. The XTUs shall choose the S (factor) and
                    D (depth) values such that the actual one-way interleaving
                    delay is as close as possible to, but less than or equal to,
                    hwxdslDynamicProfCh2MaxDelayUs. The delay is coded in ms,
                    with the value 0 indicating no delay bound is being imposed.
                    Range: 0-200
                    Unit: milliseconds
                   "
        REFERENCE    "ITU-T G.997.1, paragraph 7.3.2.2"
        ::= { hwxdslDynamicProfCfgEntry 18 }

    hwxdslDynamicProfPmModeCfg OBJECT-TYPE
        SYNTAX BITS {
                         allowTransitionsToIdle(0),
                         allowTransitionsToLowPower(1)
                    }
        MAX-ACCESS  read-create
        STATUS      current
        DESCRIPTION
                   "Power management state Enabling. Defines the power states the
                    xTU-C or xTU-R may autonomously transition to on this line.
                    The various bit positions are: allowTransitionsToIdle (0) and
                    allowTransitionsToLowPower (1). A bit with a '1' value means
                    that the xTU is allowed to transit into the respective state
                    and a '0' value means that the xTU is not allowed
                    to transit into the respective state.
                   "
        REFERENCE    "ITU-T G.997.1, paragraph 7.3.1.1.4"
        ::= { hwxdslDynamicProfCfgEntry 19 }

    hwxdslDynamicProfL0TimeCfg OBJECT-TYPE
        SYNTAX Unsigned32 (0..255)
        MAX-ACCESS  read-create
        STATUS      current
        DESCRIPTION
                   "This minimum time (in seconds) between an exit from the L2
                    state and the next Entry into the L2 state. It ranges from 0
                    to 255 seconds.
                    Range: 0-255
                   "
        REFERENCE    "ITU-T G.997.1, paragraph 7.3.1.1.5"
        ::= { hwxdslDynamicProfCfgEntry 20 }

    hwxdslDynamicProfL2TimeCfg OBJECT-TYPE
        SYNTAX Unsigned32 (0..255)
        MAX-ACCESS  read-create
        STATUS      current
        DESCRIPTION
                   "This minimum time (in seconds) between an entry into the
                    L2 state and the first power trim in the L2 state and between
                    two consecutive power trims in the L2 State.
                    It ranges from 0 to 255 seconds.
                    Range: 0-255
                   "
        REFERENCE    "ITU-T G.997.1, paragraph 7.3.1.1.6"
        ::= { hwxdslDynamicProfCfgEntry 21 }

    hwxdslDynamicProfL2AtprCfg  OBJECT-TYPE
        SYNTAX      Unsigned32 (0..31)
        UNITS       "dB"
        MAX-ACCESS  read-create
        STATUS      current
        DESCRIPTION
                   "The maximum aggregate transmit power reduction (in dB) that
                    can be performed at transition of L0 to L2 state or through a
                    single power trim in the L2 state.
                    It ranges from 0 dB to 31 dB.
                    Range: 0-31
                    Unit: dB
                   "
        REFERENCE    "ITU-T G.997.1 (amendment 1), 7.3.1.1.7"
        ::= { hwxdslDynamicProfCfgEntry 22 }

    hwxdslDynamicProfL2AtprtCfg  OBJECT-TYPE
        SYNTAX      Unsigned32 (0..31)
        UNITS       "dB"
        MAX-ACCESS  read-create
        STATUS      current
        DESCRIPTION
                   "The total maximum aggregate transmit power reduction
                    (in dB) that can be performed in an L2 state. This is the
                    sum of all reductions of L2 Request (i.e., at transition of
                    L0 to L2 state) and power trims.
                    Range: 0-31
                    Unit: dB
                   "
        REFERENCE    "ITU-T G.997.1 (amendment 1), 7.3.1.1.9"
        ::= { hwxdslDynamicProfCfgEntry 23 }

    hwxdslDynamicProfDpboEPsdCfg  OBJECT-TYPE
        SYNTAX      OCTET STRING (SIZE(0..48))
        MAX-ACCESS  read-create
        STATUS      current
        DESCRIPTION
                   "This parameter defines the PSD mask that is assumed to be permitted at the exchange.
                    This parameter shall use the same format as PSDMASKds. The maximum number of breakpoints
                    for DPBOEPSD is 16.
                    This is a string of 16 pairs of values in the following
                    structure:
                    Octets 0+1 - Index of 1st sub-carrier used in the context
                                 of a first breakpoint.
                    Octet 2    - The PSD reduction for the sub-carrier indicated in
                                 octets 0 and 1.
                    Octets 3-5 - Same, for a 2nd breakpoint.
                    Octets 6-8 - Same, for a 3rd breakpoint.
                    This architecture continues until octets 45-47, which are
                    associated with a 16th breakpoint.
                    Each subcarrier index is an unsigned number in the range 1 and
                    NSCds.  Each PSD reduction value is in the range 0 (0dBm/Hz) to
                    255 (-127.5dBm/Hz) with steps of 0.5dBm/Hz. Valid values are
                    in the range 0 to 190 (0 to -95dBm/Hz).
                    When the number of breakpoints is less than 16, all remaining
                    octets are set to the value 0xff.
                   "
        REFERENCE    "ITU-T G.997.1(200604), paragraph 7.3.1.2.13"
        ::= { hwxdslDynamicProfCfgEntry 24 }

    hwxdslDynamicProfDpboEsELCfg  OBJECT-TYPE
        SYNTAX      Unsigned32 (0..511)
        UNITS       "0.5dB"
        MAX-ACCESS  read-create
        STATUS      current
        DESCRIPTION
                   "This configuration parameter defines the assumed electrical length of
                    cables (E-side cables) connecting exchange based DSL services to a remote
                    flexibility point (cabinet), that hosts the xTU-C that is subject to
                    spectrally shaped downstream power back-off depending on this length.
                    For this parameter the electrical length is defined as the loss (in dB)
                    of an equivalent length of hypothetical cable at a reference frequency
                    defined by the network operator or in spectrum management regulations.
                    DPBOESEL shall be coded as an unsigned integer representing an electrical
                    length from 0 dB (coded as 0) to 255.5 dB (coded as 511) in steps of 0.5 dB.
                    All values in the range are valid.If DPBOESEL is set to zero, the DPBO in
                    this section shall be disabled.
                    Range: 0-511
                    Unit: 0.5dB
                   "
        REFERENCE    "ITU-T G.997.1(200604), paragraph 7.3.1.2.13"
        ::= { hwxdslDynamicProfCfgEntry 25 }

    hwxdslDynamicProfDpboEscmCfg  OBJECT-TYPE
        SYNTAX      OCTET STRING (SIZE(0..6))
        MAX-ACCESS  read-create
        STATUS      current
        DESCRIPTION
                   "This configuration parameter defines a cable model in terms of three scalars
                    DPBOESCMA, DPBOESCMB and DPBOESCMC that shall be used to describe the frequency
                    dependent loss of E-side cables.Parameters DPBOESCMA, DPBOESCMB, DPBOESCMC shall be
                    coded as unsigned integers representing a scalar value from -1 (coded as 0) to 1.5
                    (coded as 640) in step of 1/256. All values in the range are valid.
                    Octets 0+1 DPBOESCMA
                    Octets 2+3 DPBOESCMB
                    Octets 4+5 DPBOESCMC
                   "
        REFERENCE    "ITU-T G.997.1(200604), paragraph 7.3.1.2.13"
        ::= { hwxdslDynamicProfCfgEntry 26 }

    hwxdslDynamicProfDpboMusCfg  OBJECT-TYPE
        SYNTAX      Unsigned32 (0..255)
        UNITS       "0.5dBm/Hz"
        MAX-ACCESS  read-create
        STATUS      current
        DESCRIPTION
                   "DPBOMUS defines the assumed Minimum Usable receive Signal PSD (in dBm/Hz) for
                    exchange based services, used to modify parameter DPBOFMAX defined below. It
                    shall be coded as an unsigned integer representing a PSD level from 0 dBm/Hz
                    (coded as 0) to -127.5 dBm/Hz (coded as 255) in steps of 0.5 dBm/Hz.
                    All values in the range are valid.
                    Range: 0-255
                    Unit: 0.5dBm/Hz
                   "
        REFERENCE  "ITU-T G.997.1(200604), paragraph 7.3.1.2.13"
        ::= { hwxdslDynamicProfCfgEntry 27 }

    hwxdslDynamicProfDpboFMinCfg  OBJECT-TYPE
        SYNTAX      Unsigned32 (0..2048)
        UNITS       "4.3125 KHz"
        MAX-ACCESS  read-create
        STATUS      current
        DESCRIPTION
                   "DPBOFMIN defines the minimum frequency from which the DPBO shall be applied.
                    It shall be coded as a 16 bits unsigned integer representing a frequency in
                    multiple of 4.3125 KHz. The range of valid values is from 0 kHz (coded as 0)
                    to 8832 kHz (coded as 2048).
                    Range: 0-2048
                    Unit: 4.3125 KHz
                   "
        REFERENCE    "ITU-T G.997.1(200604), paragraph 7.3.1.2.13"
        ::= { hwxdslDynamicProfCfgEntry 28 }

    hwxdslDynamicProfDpboFMaxCfg  OBJECT-TYPE
        SYNTAX      Unsigned32 (32..6956)
        UNITS       "4.3125 KHz"
        MAX-ACCESS  read-create
        STATUS      current
        DESCRIPTION
                   "DPBOFMAX defines the maximum frequency at which DPBO may be applied. It shall be
                    coded as a 16 bits unsigned integer representing a frequency in multiple of 4.3125 KHz.
                    The range of valid values is from 138 kHz (coded as 32) to 29997.75 kHz (coded as 6956).
                    Range: 32-6956
                    Unit: 4.3125 KHz
                   "
        REFERENCE    "ITU-T G.997.1(200604), paragraph 7.3.1.2.13"
        ::= { hwxdslDynamicProfCfgEntry 29 }

    hwxdslDynamicProfUpboPsdBandCfg  OBJECT-TYPE
        SYNTAX      OCTET STRING (SIZE(0..16))
        MAX-ACCESS  read-create
        STATUS      current
        DESCRIPTION
                   "This parameter defines the UPBO reference PSD used to compute the upstream power back-off
                    for each upstream band except US0. A UPBOPSD defined for each band ahsll consist of two
                    parameters [a, b]. Parameter a shall be coded as an unsigned 12-bit number from 40 dBm/Hz
                    (coded as 0) to 80.95 dBm/Hz (coded as 4095) in steps of 0.01 dBm/Hz; and b shall be coded
                    as an unsigned 12 bit number from 0 (coded as 0) to 40.95 dBm/Hz (coded as 4095) in steps
                    of 0.01 dBm/Hz. The UPBO reference PSD at the frequency f expressed in MHz shall be equal
                    to '-a-b(SQRT(f))'. The set of parameter values a = 40 dBm/Hz, b = 0 dBm/Hz is a special
                    configuration to disable UPBO in the respective upstream band.
                    Octets 0+1   - a[0]
                    Octets 2+3   - b[0]
                    Octets 4+5   - a[1]
                    Octets 6+7   - b[1]
                    Octets 8+9   - a[2]
                    Octets 10+11 - b[2]
                    Octets 12+13 - a[3]
                    Octets 14+15 - b[3]"
        REFERENCE    "ITU-T G.997.1(200604), paragraph 7.3.1.2.14"
        ::= { hwxdslDynamicProfCfgEntry 30 }

    hwxdslDynamicProfUpboKLFCfg  OBJECT-TYPE
        SYNTAX INTEGER {
                          forced(1),
                          auto(2),
                          invalidValue(-1)
                       }
        MAX-ACCESS  read-create
        STATUS      current
        DESCRIPTION
                   "This parameter is a flag that forces the VTU-R to use the electrical loop length of the CO-MIB
                    (UPBOKL) to compute the UPBO. The value shall be forced if the flag is set to 1. Otherwise, the
                    electrical loop length shall be autonomously selected by the VTU-O.
                    Options:
                    1. forced(1)        - Force the CPE to use the electrical length of the CO(UPBOKL) to compute the UPBO
                    2. auto(2)          - Electrical length shall be autonomously selected by the CO
                    3. invalidValue(-1) - Invalid value
                   "
        REFERENCE    "ITU-T G.997.1(200604), paragraph 7.3.1.2.14"
        ::= { hwxdslDynamicProfCfgEntry 31 }

    hwxdslDynamicProfUpboKLCfg  OBJECT-TYPE
        SYNTAX      Unsigned32 (0..1280)
        UNITS       "0.1 dB"
        MAX-ACCESS  read-create
        STATUS      current
        DESCRIPTION
                   "This parameter defines the electrical loop length expressed in dB at 1MHz, kl0, configured by
                    the CO-MIB. The value shall be coded as an unsigned 16 bit number in the range 0 (coded as 0)
                    to 128 dB (coded as 1280) in steps of 0.1 dB.
                    Range: 0-1280
                    Unit: 0.1 dB
                   "
        REFERENCE    "ITU-T G.997.1(200604), paragraph 7.3.1.2.14"
        ::= { hwxdslDynamicProfCfgEntry 32 }

    hwxdslDynamicProfRfiBandsCfg  OBJECT-TYPE
        SYNTAX      OCTET STRING(SIZE(0..159))
        MAX-ACCESS  read-create
        STATUS      current
        DESCRIPTION
                   "The subset of PSD mask breakpoints that shall be
                   used to notch an RFI band.
                   It is a string of bands consist of begin tone index
                   and end tone index.
                   for example :0-10,20-50,100-4095
                   It can contain as most as 16 bands.
                  "
        REFERENCE    "ITU-T G.997.1(200604), paragraph 7.3.1.2.10"
        ::= { hwxdslDynamicProfCfgEntry 33 }

    hwxdslDynamicProfToneBlackOutCfg  OBJECT-TYPE
       SYNTAX      OCTET STRING(SIZE(0..79))
       MAX-ACCESS  read-create
       STATUS      current
       DESCRIPTION
             "The subset of subcarriermask that shall be
              used to mask the subcarriers.
              It is a string of bands consist of begin tone index
              and end tone index.
              For example :0-10,20-50,100-4095.
              It can contain as most as 8 bands.
             "
       REFERENCE    "ITU-T G.997.1(200604), paragraph 7.3.1.2.8"
       ::= { hwxdslDynamicProfCfgEntry 34 }

    hwxdslDynamicProfCarMaskDSCfg  OBJECT-TYPE
        SYNTAX      OCTET STRING (SIZE(0..64))
        MAX-ACCESS  read-create
        STATUS      current
        DESCRIPTION
                   "Sub-carriers mask. A bitmap of 512 bits that allows masking
                    up to 512 downstream sub-carriers, depending on NSCds. If bit
                    i (0 &lt;= i &lt; NSCds) is set to '1', the respective
                    downstream sub-carrier i is masked, and if set to '0', the
                    respective sub-carrier is unmasked. Note that there should
                    always be unmasked sub-carriers (i.e., the object cannot be
                    all 1's). Also note that if NSCds &lt; 512, all bits
                    i (NSCds i &lt;= 512) should be set to '1'.
                   "
        REFERENCE    "ITU-T G.997.1, paragraph 7.3.1.2.6"
        ::= { hwxdslDynamicProfCfgEntry 35 }

    hwxdslDynamicProfCarMaskUSCfg  OBJECT-TYPE
        SYNTAX      OCTET STRING (SIZE(0..8))
        MAX-ACCESS  read-create
        STATUS      current
        DESCRIPTION
                  "Sub-carriers mask. A bitmap of 64 bits that allows masking
                   up to 64 downstream sub-carriers, depending on NSCds. If
                   bit i (0 &lt;= i &lt; NSCus) is set to '1', the respective
                   upstream sub-carrier i is masked, and if set to '0', the
                   respective sub-carrier is unmasked. Note that there
                   should always be unmasked sub-carriers (i.e., the object
                   cannot be all 1's). Also note that if NSCus &lt;
                   64, all bits i (NSCus &lt; i &lt;= 64) should be set to '1'.
                  "
        REFERENCE    "ITU-T G.997.1, paragraph 7.3.1.2.7"
        ::= { hwxdslDynamicProfCfgEntry 36 }

    hwxdslDynamicProfXdslModeCfg    OBJECT-TYPE
        SYNTAX  INTEGER {
                            defMode (1),
                            adsl (2),
                            adsl2Pots (3),
                            adsl2Isdn (4),
                            adsl2PlusPots (5),
                            adsl2PlusIsdn (6),
                            adsl2ReachExtended (7),
                            g9923PotsNonOverlapped(8),
                            g9923PotsOverlapped(9),
                            g9923IsdnNonOverlapped(10),
                            g9923isdnOverlapped(11),
                            g9924potsNonOverlapped(14),
                            g9924potsOverlapped(15),
                            g9923AnnexIAllDigNonOverlapped(18),
                            g9923AnnexIAllDigOverlapped(19),
                            g9923AnnexJAllDigNonOverlapped(20),
                            g9923AnnexJAllDigOverlapped(21),
                            g9924AnnexIAllDigNonOverlapped(22),
                            g9924AnnexIAllDigOverlapped(23),
                            g9923AnnexLMode1NonOverlapped(24),
                            g9923AnnexLMode2NonOverlapped(25),
                            g9923AnnexLMode3Overlapped(26),
                            g9923AnnexLMode4Overlapped(27),
                            g9923AnnexMPotsNonOverlapped(28),
                            g9923AnnexMPotsOverlapped(29),
                            g9925PotsNonOverlapped(30),
                            g9925PotsOverlapped(31),
                            g9925IsdnNonOverlapped(32),
                            g9925isdnOverlapped(33),
                            g9925AnnexIAllDigNonOverlapped(36),
                            g9925AnnexIAllDigOverlapped(37),
                            g9925AnnexJAllDigNonOverlapped(38),
                            g9925AnnexJAllDigOverlapped(39),
                            g9925AnnexMPotsNonOverlapped(40),
                            g9925AnnexMPotsOverlapped(41),
                            vdsl2Pots (42),
                            vdsl2Isdn (43),
                            invalidValue(-1)
                        }
        MAX-ACCESS  read-create
        STATUS      current
        DESCRIPTION
                   "The xDSL mode is a way of categorizing the various XDSL
                    transmission modes into groups, each group (XDSL Mode) shares
                    the same PSD configuration.
                    Options:
                    1. defMode (1)                          - XDSL transmit mode is defMode
                    2. adsl (2)                             - XDSL transmit mode is adsl
                    3. adsl2Pots (3)                        - XDSL transmit mode is adsl2Pots
                    4. adsl2Isdn (4)                        - XDSL transmit mode is adsl2Isdn
                    5. adsl2PlusPots (5)                    - XDSL transmit mode is adsl2PlusPots
                    6. adsl2PlusIsdn (6)                    - XDSL transmit mode is adsl2PlusIsdn
                    7. adsl2ReachExtended (7)               - XDSL transmit mode is adsl2ReachExtended
                    8. g9923PotsNonOverlapped(8)            - XDSL transmit mode is g9923PotsNonOverlapped
                    9. g9923PotsOverlapped(9)               - XDSL transmit mode is g9923PotsOverlapped
                    10. g9923IsdnNonOverlapped(10)          - XDSL transmit mode is g9923IsdnNonOverlapped
                    11. g9923isdnOverlapped(11)             - XDSL transmit mode is g9923isdnOverlapped
                    12. g9924potsNonOverlapped(14)          - XDSL transmit mode is g9924potsNonOverlapped
                    13. g9924potsOverlapped(15)             - XDSL transmit mode is g9924potsOverlapped
                    14. g9923AnnexIAllDigNonOverlapped(18)  - XDSL transmit mode is g9923AnnexIAllDigNonOverlapped
                    15. g9923AnnexIAllDigOverlapped(19)     - XDSL transmit mode is g9923AnnexIAllDigOverlapped
                    16. g9923AnnexJAllDigNonOverlapped(20)  - XDSL transmit mode is g9923AnnexJAllDigNonOverlapped
                    17. g9923AnnexJAllDigOverlapped(21)     - XDSL transmit mode is g9923AnnexJAllDigOverlapped
                    18. g9924AnnexIAllDigNonOverlapped(22)  - XDSL transmit mode is g9924AnnexIAllDigNonOverlapped
                    19. g9924AnnexIAllDigOverlapped(23)     - XDSL transmit mode is g9924AnnexIAllDigOverlapped
                    20. g9923AnnexLMode1NonOverlapped(24)   - XDSL transmit mode is g9923AnnexLMode1NonOverlapped
                    21. g9923AnnexLMode2NonOverlapped(25)   - XDSL transmit mode is g9923AnnexLMode2NonOverlapped
                    22. g9923AnnexLMode3Overlapped(26)      - XDSL transmit mode is g9923AnnexLMode3Overlapped
                    23. g9923AnnexLMode4Overlapped(27)      - XDSL transmit mode is g9923AnnexLMode4Overlapped
                    24. g9923AnnexMPotsNonOverlapped(28)    - XDSL transmit mode is g9923AnnexMPotsNonOverlapped
                    25. g9923AnnexMPotsOverlapped(29)       - XDSL transmit mode is g9923AnnexMPotsOverlapped
                    26. g9925PotsNonOverlapped(30)          - XDSL transmit mode is g9925PotsNonOverlapped
                    27. g9925PotsOverlapped(31)             - XDSL transmit mode is g9925PotsOverlapped
                    28. g9925IsdnNonOverlapped(32)          - XDSL transmit mode is g9925IsdnNonOverlapped
                    29. g9925isdnOverlapped(33)             - XDSL transmit mode is g9925isdnOverlapped
                    30. g9925AnnexIAllDigNonOverlapped(36)  - XDSL transmit mode is g9925AnnexIAllDigNonOverlapped
                    31. g9925AnnexIAllDigOverlapped(37)     - XDSL transmit mode is g9925AnnexIAllDigOverlapped
                    32. g9925AnnexJAllDigNonOverlapped(38)  - XDSL transmit mode is g9925AnnexJAllDigNonOverlapped
                    33. g9925AnnexJAllDigOverlapped(39)     - XDSL transmit mode is g9925AnnexJAllDigOverlapped
                    34. g9925AnnexMPotsNonOverlapped(40)    - XDSL transmit mode is g9925AnnexMPotsNonOverlapped
                    35. g9925AnnexMPotsOverlapped(41)       - XDSL transmit mode is g9925AnnexMPotsOverlapped
                    36. vdsl2Pots (42)                      - XDSL transmit mode is vdsl2Pots
                    37. vdsl2Isdn (43)                      - XDSL transmit mode is vdsl2Isdn
                    38. invalidValue(-1)                    - Invalid value
                   "
        REFERENCE    "DSL Forum TR-90, paragraph 5.1.8"
        ::= { hwxdslDynamicProfCfgEntry 37 }

    hwxdslDynamicProfMaxNomPsdDsCfg OBJECT-TYPE
        SYNTAX      Integer32(-600..-300 | -1)
        UNITS       "0.1 dB"
        MAX-ACCESS  read-create
        STATUS      current
        DESCRIPTION
                   "The maximum nominal transmit PSD in the downstream
                    direction during initialization and show time. It ranges from
                    -600 to -300 units of 0.1 dBm/Hz(physical values are -60 to
                    -30 dBm/Hz). The invalid value is -1. If data is invalid, the invalid value will be returned.
                    Unit: 0.1 dB
                   "
        ::= { hwxdslDynamicProfCfgEntry 38 }

    hwxdslDynamicProfMaxNomPsdUsCfg OBJECT-TYPE
        SYNTAX      Integer32(-600..-300 | -1)
        UNITS       "0.1 dB"
        MAX-ACCESS  read-create
        STATUS      current
        DESCRIPTION
                   "The maximum nominal transmit PSD in the upstream
                    direction during initialization and show time. It ranges from
                    -600 to -300 units of 0.1 dBm/Hz(physical values are -60 to
                    -30 dBm/Hz). The invalid value is -1. If data is invalid, the invalid value will be returned.
                    Unit: 0.1 dB
                   "
        ::= { hwxdslDynamicProfCfgEntry 39 }

    hwxdslDynamicProfMaxNomAtpDsCfg  OBJECT-TYPE
        SYNTAX      Unsigned32 (0..255)
        UNITS       "0.1 dBm"
        MAX-ACCESS  read-create
        STATUS      current
        DESCRIPTION
                   "The maximum nominal aggregate transmit power in the
                    downstream direction during initialization and show time. It
                    ranges from 0 to 255 units of 0.1 dBm (physical values are 0
                    to 25.5 dBm).
                    Range: 0-255
                    Unit: 0.1 dBm
                   "
        REFERENCE    "ITU-T G.997.1, paragraph 7.3.1.2"
        ::= { hwxdslDynamicProfCfgEntry 40 }

    hwxdslDynamicProfMaxNomAtpUsCfg  OBJECT-TYPE
        SYNTAX      Unsigned32 (0..255)
        UNITS       "0.1 dBm"
        MAX-ACCESS  read-create
        STATUS      current
        DESCRIPTION
                   "The maximum nominal aggregate transmit power in the
                    upstream direction during initialization and show time. It
                    ranges from 0 to 255 units of 0.1 dBm (physical values are 0
                    to 25.5 dBm).
                    Range: 0-255
                    Unit: 0.1 dBm
                   "
        REFERENCE    "ITU-T G.997.1, paragraph 7.3.1.2"
        ::= { hwxdslDynamicProfCfgEntry 41 }

    hwxdslDynamicProfPsdMaskDsCfg   OBJECT-TYPE
        SYNTAX      OCTET STRING (SIZE(0..96))
        MAX-ACCESS  read-create
        STATUS      current
        DESCRIPTION
                  "This configuration parameter defines the downstream PSD mask
                   applicable at the U C2 reference point.
                   This MIB PSD mask may impose PSD restrictions in addition
                   to the Limit PSD mask defined in the relevant Recommendation
                   (e.g., G.992.5, G.993.2).
                   This is a string of 32 pairs of values in the following
                   structure:
                   Octets 0+1 - Index of 1st sub-carrier used in the context
                                of a first breakpoint.
                   Octet 2    - The PSD reduction for the sub-carrier indicated in
                                octets 0 and 1.
                   Octets 3-5 - Same, for a 2nd breakpoint.
                   Octets 6-8 - Same, for a 3rd breakpoint.
                   This architecture continues until octets 94-95, which are
                   associated with a 32nd breakpoint.
                   Each subcarrier index is an unsigned number in the range 0 and
                   (NSCds - 1). Each PSD reduction value is in the range 0 (0dBm/Hz) to
                   255 (-127.5dBm/Hz) with steps of 0.5dBm/Hz. Valid values are
                   in the range 0 to 190 (0 to -95dBm/Hz).
                   When the number of breakpoints is less than 32, all remaining
                   octets are set to the value 0xff.  Note that the content of this
                   object should be correlated with the sub-carriers mask and with
                   the RFI setup.
                  "
        REFERENCE    "ITU-T G.997.1(200604), paragraph 7.3.1.2.9"
        ::= { hwxdslDynamicProfCfgEntry 42 }

    hwxdslDynamicProfPsdMaskUsCfg   OBJECT-TYPE
        SYNTAX      OCTET STRING (SIZE(0..48))
        MAX-ACCESS  read-create
        STATUS      current
        DESCRIPTION
                   "This configuration parameter defines the upstream PSD
                    mask applicable at the U R2 reference point. This MIB
                    PSD mask may impose PSD restrictions in addition to the
                    Limit PSD mask defined in the relevant Recommendations
                    (e.g., ITU-T Recommendations G.992.3, G.993.2).
                    This is a string of 16 pairs of values in the following
                    structure:
                    Octets 0+1 - Index of 1st sub-carrier used in the context
                                 of a first breakpoint.
                    Octet 2    - The PSD reduction for the sub-carrier indicated in
                                 octets 0 and 1.
                    Octets 3-5 - Same, for a 2nd breakpoint.
                    Octets 45-47 - Same, for a 3rd breakpoint.
                    This architecture continues until octets 45-47, which are
                    associated with a 16th breakpoint.
                    Each subcarrier index is an unsigned number in the range 0 and
                    (NSCus - 1). Each PSD reduction value is in the range 0 (0dBm/Hz) to
                    255 (-127.5dBm/Hz) with steps of 0.5dBm/Hz. Valid values are
                    in the range 0 to 190 (0 to -95dBm/Hz).
                    When the number of breakpoints is less than 16, all remaining
                    octets are set to the value 0xff. Note that the content of this
                    object should be correlated with the sub-carriers mask and with
                    the RFI setup.
                   "
        REFERENCE    "ITU-T G.997.1(200604), paragraph 7.3.1.2.12"
        ::= { hwxdslDynamicProfCfgEntry 43 }

    hwxdslDynamicProfLimitMaskCfg  OBJECT-TYPE
        SYNTAX INTEGER {
                           profile8a (1),
                           profile8b (2),
                           profile8c (3),
                           profile8d (4),
                           profile12a (5),
                           profile12b (6),
                           profile17a (7),
                           profile30a (8),
                           invalidValue(-1)
                       }
        MAX-ACCESS  read-create
        STATUS      current
        DESCRIPTION "This configuration parameter contains the G.993.2
                     profiles to be allowed by the near-end xTU on this line.
                     Options:
                     1. profile8a (1)     - The G.993.2 profile is profile8a
                     2. profile8b (2)     - The G.993.2 profile is profile8b
                     3. profile8c (3)     - The G.993.2 profile is profile8c
                     4. profile8d (4)     - The G.993.2 profile is profile8d
                     5. profile12a (5)    - The G.993.2 profile is profile12a
                     6. profile12b (6)    - The G.993.2 profile is profile12b
                     7. profile17a (7)    - The G.993.2 profile is profile17a
                     8. profile30a (8)    - The G.993.2 profile is profile30a
                     9. invalidValue(-1)  - Invalid value
                    "
        REFERENCE    "ITU-T G.997.1(200604), paragraph 7.3.1.1.11"
        ::= { hwxdslDynamicProfCfgEntry 44 }

    hwxdslDynamicProfClassMaskCfg  OBJECT-TYPE
        SYNTAX INTEGER {
                           annexA998-D-32              (1),
                           annexA998-D-64              (2),
                           annexB997-M1c-A-7           (3),
                           annexB997-M1x-M-8           (4),
                           annexB997-M1x-M             (5),
                           annexB997-M2x-M-8           (6),
                           annexB997-M2x-A             (7),
                           annexB997-M2x-M             (8),
                           annexB998-M1x-A             (9),
                           annexB998-M1x-B             (10),
                           annexB998-M1x-NUS0          (11),
                           annexB998-M2x-A             (12),
                           annexB998-M2x-M             (13),
                           annexB998-M2x-B             (14),
                           annexB998-M2x-NUS0          (15),
                           annexBHPE17-M1              (16),
                           annexBHPE30-M1              (17),
                           annexB997E17-M2x-A          (18),
                           annexB997E30-M2x-NUS0       (19),
                           annexB998E17-M2x-NUS0       (20),
                           annexB998E17-M2x-NUS0-M     (21),
                           annexB998ADE17-M2x-NUS0-M   (22),
                           annexB998ADE17-M2x-B        (23),
                           annexB998E30-M2x-NUS0       (24),
                           annexB998E30-M2x-NUS0-M     (25),
                           annexB998ADE30-M2x-NUS0-M   (26),
                           annexB998ADE17-M2x-A        (27),
                           annexB998ADE30-M2x-NUS0-A   (28),
            	           annexA998-D-48              (29),
            	           annexA998-D-128             (30),
            	           annexB998ADE17-M2x-M        (31),
                           invalidValue(-1)
                       }
        MAX-ACCESS  read-create
        STATUS      current
        DESCRIPTION "In order to reduce the number of configuration possibilities,
                     the limit PSD masks are grouped in the following PSD mask classes:
                     Options:
                     1. annexA998-D-32(1)               - Class 998 Annex A: D-32, D-64, D-48, D-128
                     2. annexA998-D-64(2)               - Class 998 Annex A: D-32, D-64, D-48, D-128
                     3. annexB997-M1c-A-7(3)            - Class 997-M1c Annex B: 997-M1c-A-7
                     4. annexB997-M1x-M-8(4)            - Class 997-M1x Annex B: 997-M1x-M-8, 997-M1x-M
                     5. annexB997-M1x-M(5)              - Class 997-M1x Annex B: 997-M1x-M-8, 997-M1x-M
                     6. annexB997-M2x-M-8(6)            - Class 997-M2x Annex B: 997-M2x-M-8, 997-M2x-A, 997-M2x-M
                     7. annexB997-M2x-A(7)              - Class 997-M2x Annex B: 997-M2x-M-8, 997-M2x-A, 997-M2x-M
                     8. annexB997-M2x-M(8)              - Class 997-M2x Annex B: 997-M2x-M-8, 997-M2x-A, 997-M2x-M
                     9. annexB998-M1x-A(9)              - Class 998-M1x Annex B: 998-M1x-A, 998-M1x-B, 998-M1x-NUS0
                     10. annexB998-M1x-B(10)            - Class 998-M1x Annex B: 998-M1x-A, 998-M1x-B, 998-M1x-NUS0
                     11. annexB998-M1x-NUS0(11)         - Class 998-M1x Annex B: 998-M1x-A, 998-M1x-B, 998-M1x-NUS0
                     12. annexB998-M2x-A(12)            - Class 998-M2x Annex B: 998-M2x-A, 998-M2x-M, 998-M2x-B, 998-M2x-NUS0
                     13. annexB998-M2x-M(13)            - Class 998-M2x Annex B: 998-M2x-A, 998-M2x-M, 998-M2x-B, 998-M2x-NUS0
                     14. annexB998-M2x-B(14)            - Class 998-M2x Annex B: 998-M2x-A, 998-M2x-M, 998-M2x-B, 998-M2x-NUS0
                     15. annexB998-M2x-NUS0(15)         - Class 998-M2x Annex B: 998-M2x-A, 998-M2x-M, 998-M2x-B, 998-M2x-NUS0
                     16. annexBHPE17-M1(16)             - Class HPE17 Annex B: HPE17-M1
                     17. annexBHPE30-M1(17)             - Class HPE30 Annex B: HPE30-M1
                     18. annexB997E17-M2x-A(18)         - Class 997E17-M2x Annex B: 997E17-M2x-A
                     19. annexB997E30-M2x-NUS0(19)      - Class 997E30-M2x Annex B: 997E30-M2x-NUS0
                     20. annexB998E17-M2x-NUS0(20)      - Class 998E17-M2x Annex B: 998E17-M2x-NUS0, 998E17-M2x-NUS0-M
                     21. annexB998E17-M2x-NUS0-M(21)    - Class 998E17-M2x Annex B: 998E17-M2x-NUS0, 998E17-M2x-NUS0-M
                     22. annexB998ADE17-M2x-NUS0-M(22)  - Class 998ADE17-M2x Annex B: 998ADE17-M2x-NUS0-M, 998ADE17-M2x-A, 998ADE17-M2x-B, 998ADE17-M2x-M.
                     23. annexB998ADE17-M2x-B(23)       - Class 998ADE17-M2x Annex B: 998ADE17-M2x-NUS0-M, 998ADE17-M2x-A, 998ADE17-M2x-B, 998ADE17-M2x-M.
                     24. annexB998E30-M2x-NUS0(24)      - Class 998E30-M2x Annex B: 998E30-M2x-NUS0, 998E30-M2x-NUS0-M
                     25. annexB998E30-M2x-NUS0-M(25)    - Class 998E30-M2x Annex B: 998E30-M2x-NUS0, 998E30-M2x-NUS0-M
                     26. annexB998ADE30-M2x-NUS0-M(26)  - Class 998ADE30-M2x Annex B: 998ADE30-M2x-NUS0-M, 998ADE30-M2x-NUS0-A
                     27. annexB998ADE17-M2x-A(27)       - Class 998ADE17-M2x Annex B: 998ADE17-M2x-NUS0-M, 998ADE17-M2x-A, 998ADE17-M2x-B, 998ADE17-M2x-M.
                     28. annexB998ADE30-M2x-NUS0-A(28)  - Class 998ADE30-M2x Annex B: 998ADE30-M2x-NUS0-M, 998ADE30-M2x-NUS0-A
                     29. annexA998-D-48(29)             - Class 998 Annex A: D-32, D-64, D-48, D-128
                     30. annexA998-D-128(30)            - Class 998 Annex A: D-32, D-64, D-48, D-128
                     31. annexB998ADE17-M2x-M(31)       - Class 998ADE17-M2x Annex B: 998ADE17-M2x-NUS0-M, 998ADE17-M2x-A, 998ADE17-M2x-B, 998ADE17-M2x-M.
                     32. invalidValue(-1)               - Invalid value
                    "
        REFERENCE    "ITU-T G.997.1(200604), paragraph 7.3.1.1.12"
        ::= { hwxdslDynamicProfCfgEntry 45 }

    hwxdslDynamicProfBandOptUsageCfg  OBJECT-TYPE
        SYNTAX      INTEGER {
                                 disable(1),
                                 enable(2),
                                 invalidValue(-1)
                            }
        MAX-ACCESS  read-create
        STATUS      current
        DESCRIPTION
                   "Defines the VDSL link use of the optional frequency
                    range [25kHz - 138kHz] (Opt).
                    Options:
                    1. disable(1)       - Indicates Opt is unused
                    2. enable(2)        - Indicates Opt usage is for upstream
                    3. invalidValue(-1) - Invalid value
                    Huawei defined.
                   "
       ::= { hwxdslDynamicProfCfgEntry 46 }

    hwxdslDynamicProfVirtualNoiseModeDsCfg  OBJECT-TYPE
        SYNTAX INTEGER {
                           disable(1),
                           enable(2),
                           invalidValue(-1)
                       }
        MAX-ACCESS  read-create
        STATUS      current
        DESCRIPTION "Defines the Virtual Noise of downsteam.
                     Options:
                     1. disable(1) -unused
                     2. enable(2)  -used
                     3. invalidValue(-1) -invalid Value
                     Huawei defined.
                    "
        ::= { hwxdslDynamicProfCfgEntry 47 }

    hwxdslDynamicProfVirtualNoiseModeUsCfg  OBJECT-TYPE
        SYNTAX INTEGER {
                          disable(1),
                          enable(2),
                          invalidValue(-1)
                       }
        MAX-ACCESS  read-create
        STATUS      current
        DESCRIPTION "Defines the Virtual Noise of upstream.
                     Options:
                     1. disable(1) -unused
                     2. enable(2)  -used
                     3. invalidValue(-1) -invalid Value
                     Huawei defined.
                    "
        ::= { hwxdslDynamicProfCfgEntry 48 }

    hwxdslDynamicProfVirtualNoiseDsCfg  OBJECT-TYPE
        SYNTAX      OCTET STRING (SIZE(0..96))
        MAX-ACCESS  read-create
        STATUS      current
        DESCRIPTION
                   "The Virtual Noise of downsteam.
                    This is a string of 32 pairs of values in the following
                    structure:
                    Octets 0+1 - Index of 1st sub-carrier used in the context
                                 of a first breakpoint.
                    Octet 2    - The PSD reduction for the sub-carrier indicated in
                                 octets 0 and 1.
                    Octets 3-5 - Same, for a 2nd breakpoint.
                    Octets 6-8 - Same, for a 3rd breakpoint.
                    This architecture continues until octets 94-95, which are
                    associated with a 32nd breakpoint.
                    Each subcarrier index is an unsigned number in the range 0 and
                    (NSCds - 1). Each PSD reduction value is in the range 0 (0dBm/Hz) to
                    255 (127.5dBm/Hz) with steps of 0.5dBm/Hz.
                   "
        ::= { hwxdslDynamicProfCfgEntry 49 }

    hwxdslDynamicProfVirtualNoiseUsCfg  OBJECT-TYPE
        SYNTAX      OCTET STRING(SIZE(0..48))
        MAX-ACCESS  read-create
        STATUS      current
        DESCRIPTION
                   "The Virtual Noise of upsteam.
                    This is a string of 16 pairs of values in the following
                    structure:
                    Octets 0+1 - Index of 1st sub-carrier used in the context
                                 of a first breakpoint.
                    Octet 2    - The PSD reduction for the sub-carrier indicated in
                                 octets 0 and 1.
                    Octets 3-5 - Same, for a 2nd breakpoint.
                    Octets 6-8 - Same, for a 3rd breakpoint.
                    This architecture continues until octets 45-47, which are
                    associated with a 16th breakpoint.
                    Each subcarrier index is an unsigned number in the range 0 and
                    (NSCds - 1). Each PSD reduction value is in the range 0 (0dBm/Hz) to
                    255 (127.5dBm/Hz) with steps of 0.5dBm/Hz.
                   "
        ::= { hwxdslDynamicProfCfgEntry 50 }

    hwxdslDynamicProfRowStatusCfg  OBJECT-TYPE
        SYNTAX      RowStatus
        MAX-ACCESS  read-create
        STATUS      current
        DESCRIPTION
                   "This object is used to create a new row or to modify or
                    delete an existing row in this table.
                    A profile is activated by setting this object to 'active'.
                    When 'active' is set, the system will validate the profile.
                    Before a profile can be deleted or taken out of service
                    (by setting this object to 'destroy' or 'outOfService'),
                    it must be first unreferenced from all associated
                    templates.
                   "
        ::= { hwxdslDynamicProfCfgEntry 51 }

--hwXdslPortIopCaptureTable

    hwXdslPortIopCaptureInfoTable OBJECT-TYPE
        SYNTAX SEQUENCE OF HwXdslPortIopCaptureInfoEntry
        MAX-ACCESS not-accessible
        STATUS current
        DESCRIPTION
                   "The table hwXdslPortIopCaptureInfoTable implement xDSL port IOP information capture.
                    The index of this table is ifIndex.
                   "
        ::= { hwAdslMibObjects 31 }

    hwXdslPortIopCaptureInfoEntry OBJECT-TYPE
        SYNTAX HwXdslPortIopCaptureInfoEntry
        MAX-ACCESS not-accessible
        STATUS current
        DESCRIPTION
                   "The table hwXdslPortIopCaptureInfoTable implement xDSL port IOP information capture.
                    The index of this entry is ifIndex.
                   "
        INDEX{
                 ifIndex
             }
        ::= { hwXdslPortIopCaptureInfoTable 1 }

    HwXdslPortIopCaptureInfoEntry ::=
        SEQUENCE{
                   hwXdslPortIopCaptureOperTypeCfg     INTEGER,
                   hwXdslPortIopCaptureOperStatusInfo  INTEGER
                }

    hwXdslPortIopCaptureOperTypeCfg OBJECT-TYPE
        SYNTAX INTEGER
                      {
                          start(1),
                          stop(2),
                          invalid(-1)
                      }
        MAX-ACCESS  read-write
        STATUS      current
        DESCRIPTION
                   "Start or stop IOP information capture of xDSL port.
                    Options:
                    1. start(1)     - Start IOP information capture of xDSL port
                    2. stop(2)      - Stop IOP information capture of xDSL port
                    3. invalid(-1)  - Invalid value
                   "
        ::= { hwXdslPortIopCaptureInfoEntry 1 }

    hwXdslPortIopCaptureOperStatusInfo OBJECT-TYPE
        SYNTAX INTEGER
                      {
                          noCapture(1),
                          capturing(2),
                          iop-generate(3),
                          captured(4),
                          invalid(-1)
                      }
        MAX-ACCESS read-only
        STATUS     current
        DESCRIPTION
                   "Port IOP capture status
                    Options:
                    1. noCapture(1)    - Indicates that the capture is not performed
                    2. capturing(2)    - Indicates that the capture is being performed
                    3. iop-generate(3) - Indicates that the IOP file is generated
                    4. captured(4)     - Indicates that the capture is completed
                    5. invalid(-1)     - Invalid value
                   "
        ::= { hwXdslPortIopCaptureInfoEntry 2 }

--hwXdslDynamicInfoCollectInfoTable

    hwXdslDynamicInfoCollectInfoTable OBJECT-TYPE
        SYNTAX SEQUENCE OF HwXdslDynamicInfoCollectInfoEntry
        MAX-ACCESS not-accessible
        STATUS deprecated
        DESCRIPTION
                   "The table hwXdslDynamicInfoCollectTable implement xDSL port Dynamic information collect.
                    The indexes of this table are hwFrameIndex and hwSlotIndex.
                   "
        ::= { hwAdslMibObjects 32 }

    hwXdslDynamicInfoCollectInfoEntry OBJECT-TYPE
        SYNTAX HwXdslDynamicInfoCollectInfoEntry
        MAX-ACCESS not-accessible
        STATUS deprecated
        DESCRIPTION
                   "The table hwXdslDynamicInfoCollectTable implement xDSL port Dynamic information collect.
                    The indexes of this entry are hwFrameIndex and hwSlotIndex.
                   "
        INDEX{
                 hwFrameIndex,
                 hwSlotIndex
             }
        ::= { hwXdslDynamicInfoCollectInfoTable 1 }

    HwXdslDynamicInfoCollectInfoEntry ::=
        SEQUENCE{
        		hwXdslDynamicInfoCollectInfo       INTEGER,
        		hwXdslDynamicInfoCollectStatusInfo INTEGER,
        		hwXdslDynamicInfoCollectTimeInfo   DateAndTime,
        		hwXdslDynamicInfoCollectPortList   OCTET STRING
                }

    hwXdslDynamicInfoCollectInfo OBJECT-TYPE
        SYNTAX INTEGER
                      {
                          start(1),
                          invalid(-1)
                      }
        MAX-ACCESS  read-write
        STATUS      deprecated
        DESCRIPTION
                   "Start Dynamic information collecting of xDSL port.
                    Options:
                    1. start(1)    - Indicates the collecting starts
                    2. invalid(-1) - Invalid value
                   "
        ::= { hwXdslDynamicInfoCollectInfoEntry 1 }

    hwXdslDynamicInfoCollectStatusInfo OBJECT-TYPE
        SYNTAX INTEGER
                      {
                          noCollect(1),
                          collecting(2),
                          collected(3)
                      }
        MAX-ACCESS read-only
        STATUS     deprecated
        DESCRIPTION
                   "Board Dynamic information collecting status.
                    Options:
                    1. noCollect(1)  - Indicates that collecting data is not performed
                    2. collecting(2) - Indicates that collecting data is being performed
                    3. collected(3)  - Indicates that collecting data is complete
                   "
        ::= { hwXdslDynamicInfoCollectInfoEntry 2 }

    hwXdslDynamicInfoCollectTimeInfo OBJECT-TYPE
        SYNTAX DateAndTime
        MAX-ACCESS  read-only
        STATUS     deprecated
        DESCRIPTION "Time at which collecting the optimization information is complete."
        ::= { hwXdslDynamicInfoCollectInfoEntry 3 }

    hwXdslDynamicInfoCollectPortList OBJECT-TYPE
        SYNTAX      OCTET STRING (SIZE(0..16))
        MAX-ACCESS  read-write
        STATUS      deprecated
        DESCRIPTION
                "This object defines the operating port list of certain xDSL board.
                 Each bit of this string specifies a port. If that bit has a value of '1', then that port is
                 included in the set of ports; the port is not included if its bit has a value of '0'. For example,
                 if 0xFE is set to this node, then port 0 to port 6 will start collection.
                 If this node is not configed, collection will be started on all ports of the board.
                "
        ::= { hwXdslDynamicInfoCollectInfoEntry 4 }

--  hwadslAturPerfDataInfoTable
    hwadslAturPerfDataInfoTable   OBJECT-TYPE
        SYNTAX          SEQUENCE OF HwadslAturPerfDataInfoEntry
        MAX-ACCESS      not-accessible
        STATUS          current
        DESCRIPTION
		   "This table provides one row for each ATUR.
                    ADSL physical interfaces are
                    those ifEntries where ifType is equal to adsl(94).
                    The index of this table is ifIndex.
                   "
        ::= { hwAdslMibObjects 33 }

    hwadslAturPerfDataInfoEntry       OBJECT-TYPE
        SYNTAX          HwadslAturPerfDataInfoEntry
        MAX-ACCESS      not-accessible
        STATUS          current
        DESCRIPTION
                   "This table provides one row for each ATUR.
                    ADSL physical interfaces are
                    those ifEntries where ifType is equal to adsl(94).
                    The index of this entry is ifIndex.
                   "
        INDEX           { ifIndex }
        ::= { hwadslAturPerfDataInfoTable 1 }

    HwadslAturPerfDataInfoEntry ::=
        SEQUENCE {
                     hwAdslAturPerfCurr15MStartTime              DateAndTime,
                     hwAdslAturPerfCurr1DayStartTime             DateAndTime,
                     hwAdslAturPerfCurr15MInmainpeq              OCTET STRING,
                     hwAdslAturPerfCurr15MInmame                 Counter32,
                     hwAdslAturPerfCurr15MInmaiat                OCTET STRING,
                     hwAdslAturPerfCurr1DayInmainpeq             OCTET STRING,
                     hwAdslAturPerfCurr1DayInmame                Counter32,
                     hwAdslAturPerfCurr1DayInmaiat               OCTET STRING,
                     hwAdslAturPerfPre1DayInmainpeq              OCTET STRING,
                     hwAdslAturPerfPre1DayInmame                 Counter32,
                     hwAdslAturPerfPre1DayInmaiat                OCTET STRING,
                     hwAdslAturPerfCurrEverBeforeInmainpeq       OCTET STRING,
                     hwAdslAturPerfCurrEverBeforeInmame          Counter32,
                     hwAdslAturPerfCurrEverBeforeInmaiat         OCTET STRING,
                     hwAdslAturPerfCurr15MLeftrs                 Counter32,
                     hwAdslAturPerfCurr15MEfb                    Counter32,
                     hwAdslAturPerfCurr15MMinEftr                Counter32,
                     hwAdslAturPerfCurr1DayLeftrs                Counter32,
                     hwAdslAturPerfCurr1DayEfb                   Counter32,
                     hwAdslAturPerfCurr1DayMinEftr               Counter32,
                     hwAdslAturPerfPrev1DayLeftrs                Counter32,
                     hwAdslAturPerfPrev1DayEfb                   Counter32,
                     hwAdslAturPerfPrev1DayMinEftr               Counter32,
                     hwAdslAturPerfCurrEverBeforeLeftrs          Counter32,
                     hwAdslAturPerfCurrEverBeforeEfb             Counter32,
                     hwAdslAturPerfCurrEverBeforeMinEftr         Counter32
                 }

   hwAdslAturPerfCurr15MStartTime  OBJECT-TYPE
       SYNTAX      DateAndTime
       MAX-ACCESS  read-only
       STATUS      current
       DESCRIPTION
           "Start time of the current 15-minute performance statistics."
       ::= { hwadslAturPerfDataInfoEntry 1 }

   hwAdslAturPerfCurr1DayStartTime  OBJECT-TYPE
       SYNTAX      DateAndTime
       MAX-ACCESS  read-only
       STATUS      current
       DESCRIPTION
           "Start time of the current 1-day performance statistics."
       ::= { hwadslAturPerfDataInfoEntry 2 }


   hwAdslAturPerfCurr15MInmainpeq  OBJECT-TYPE
       SYNTAX      OCTET STRING  (SIZE(0..68))
       MAX-ACCESS  read-only
       STATUS      current
       DESCRIPTION
           "This parameter is a count of the INMAINPEQi anomalies
            occurring on the line during current 15 minutes.
            Each INMAINPEQ needs 4 bytes.
           "
       REFERENCE    "ITU-T G.997.1, paragraph 7.2.1"
       ::= { hwadslAturPerfDataInfoEntry 3 }

   hwAdslAturPerfCurr15MInmame  OBJECT-TYPE
       SYNTAX      Counter32
       MAX-ACCESS  read-only
       STATUS      current
       DESCRIPTION
           "This parameter is a count of the INMAME anomalies
            occurring on the line during current 15 minutes.
           "
       REFERENCE    "ITU-T G.997.1, paragraph 7.2.1"
       ::= { hwadslAturPerfDataInfoEntry 4 }

   hwAdslAturPerfCurr15MInmaiat  OBJECT-TYPE
       SYNTAX      OCTET STRING  (SIZE(0..32))
       MAX-ACCESS  read-only
       STATUS      current
       DESCRIPTION
           "This parameter is a count of the INMAIATi anomalies
            occurring on the line during current 15 minutes.
            Each INMAIAT needs 4 bytes.
           "
       REFERENCE    "ITU-T G.997.1, paragraph 7.2.1"
       ::= { hwadslAturPerfDataInfoEntry 5 }

   hwAdslAturPerfCurr1DayInmainpeq  OBJECT-TYPE
       SYNTAX      OCTET STRING  (SIZE(0..68))
       MAX-ACCESS  read-only
       STATUS      current
       DESCRIPTION
           "This parameter is a count of the INMAINPEQi anomalies
            occurring on the line during current 1 day.
            Each INMAINPEQ needs 4 bytes.
           "
       REFERENCE    "ITU-T G.997.1, paragraph 7.2.1"
       ::= { hwadslAturPerfDataInfoEntry 6 }

   hwAdslAturPerfCurr1DayInmame  OBJECT-TYPE
       SYNTAX      Counter32
       MAX-ACCESS  read-only
       STATUS      current
       DESCRIPTION
           "This parameter is a count of the INMAME anomalies
            occurring on the line during current 1 day.
           "
       REFERENCE    "ITU-T G.997.1, paragraph 7.2.1"
       ::= { hwadslAturPerfDataInfoEntry 7 }

   hwAdslAturPerfCurr1DayInmaiat  OBJECT-TYPE
       SYNTAX      OCTET STRING  (SIZE(0..32))
       MAX-ACCESS  read-only
       STATUS      current
       DESCRIPTION
           "This parameter is a count of the INMAIATi anomalies
            occurring on the line during current 1 day.
            Each INMAIAT needs 4 bytes.
           "
       REFERENCE    "ITU-T G.997.1, paragraph 7.2.1"
       ::= { hwadslAturPerfDataInfoEntry 8 }

   hwAdslAturPerfPre1DayInmainpeq  OBJECT-TYPE
       SYNTAX      OCTET STRING  (SIZE(0..68))
       MAX-ACCESS  read-only
       STATUS      current
       DESCRIPTION
           "This parameter is a count of the INMAINPEQi anomalies
            occurring on the line during the most recent previous 1-day period.
            Each INMAINPEQ needs 4 bytes.
           "
       REFERENCE    "ITU-T G.997.1, paragraph 7.2.1"
       ::= { hwadslAturPerfDataInfoEntry 9 }

   hwAdslAturPerfPre1DayInmame  OBJECT-TYPE
       SYNTAX      Counter32
       MAX-ACCESS  read-only
       STATUS      current
       DESCRIPTION
           "This parameter is a count of the INMAME anomalies
            occurring on the line during the most recent previous 1-day period.
           "
       REFERENCE    "ITU-T G.997.1, paragraph 7.2.1"
       ::= { hwadslAturPerfDataInfoEntry 10 }

   hwAdslAturPerfPre1DayInmaiat  OBJECT-TYPE
       SYNTAX      OCTET STRING  (SIZE(0..32))
       MAX-ACCESS  read-only
       STATUS      current
       DESCRIPTION
           "This parameter is a count of the INMAIATi anomalies
            occurring on the line during the most recent previous 1-day period.
            Each INMAIAT needs 4 bytes.
           "
       REFERENCE    "ITU-T G.997.1, paragraph 7.2.1"
       ::= { hwadslAturPerfDataInfoEntry 11 }

   hwAdslAturPerfCurrEverBeforeInmainpeq  OBJECT-TYPE
       SYNTAX      OCTET STRING  (SIZE(0..68))
       MAX-ACCESS  read-only
       STATUS      current
       DESCRIPTION
           "This parameter is a count of the INMAINPEQi anomalies
            occurring on the line ever before.
            Each INMAINPEQ needs 4 bytes.
           "
       REFERENCE    "ITU-T G.997.1, paragraph 7.2.1"
       ::= { hwadslAturPerfDataInfoEntry 12 }

   hwAdslAturPerfCurrEverBeforeInmame  OBJECT-TYPE
       SYNTAX      Counter32
       MAX-ACCESS  read-only
       STATUS      current
       DESCRIPTION
           "This parameter is a count of the INMAME anomalies
            occurring on the line ever before.
           "
       REFERENCE    "ITU-T G.997.1, paragraph 7.2.1"
       ::= { hwadslAturPerfDataInfoEntry 13 }

   hwAdslAturPerfCurrEverBeforeInmaiat  OBJECT-TYPE
       SYNTAX      OCTET STRING  (SIZE(0..32))
       MAX-ACCESS  read-only
       STATUS      current
       DESCRIPTION
           "This parameter is a count of the INMAIATi anomalies
            occurring on the line ever before.
            Each INMAIAT needs 4 bytes.
           "
       REFERENCE    "ITU-T G.997.1, paragraph 7.2.1"
       ::= { hwadslAturPerfDataInfoEntry 14 }

    hwAdslAturPerfCurr15MLeftrs OBJECT-TYPE
        SYNTAX Counter32
        MAX-ACCESS read-only
        STATUS current
        DESCRIPTION
                   "If retransmission is used in a given transmit direction, this parameter is a count of
                    the seconds with a far-end leftr defect present observed over the current 15 minutes
                    accumulation period.
                   "
        REFERENCE  "ITU-T G.997.1, paragraph 7.2.1.1.6 7.2.1.2.6 "
        ::= { hwadslAturPerfDataInfoEntry 15 }

    hwAdslAturPerfCurr15MEfb OBJECT-TYPE
        SYNTAX Counter32
        MAX-ACCESS read-only
        STATUS current
        DESCRIPTION
                "If retransmission is used in a given transmit direction, this parameter
                 is a count of the number of error-free bits observed over the current 15 minutes
                 accumulation period.
                 The far-end counter is only defined in downstream.
                "
        REFERENCE  "ITU-T G.997.1, paragraph 7.2.1.1.7 7.2.1.2.7 "
        ::= { hwadslAturPerfDataInfoEntry 16 }

   hwAdslAturPerfCurr15MMinEftr OBJECT-TYPE
        SYNTAX Counter32
        MAX-ACCESS read-only
        STATUS current
        DESCRIPTION
                   "If retransmission is used in a given transmit direction, this parameter MINEFTR reports
                    the minimum of the EFTR(Error-free throughput rate) observed over the current 15 minutes
                    accumulation period.
                    The far-end value is only defined in downstream.
                   "
        REFERENCE   "ITU-T G.997.1, paragraph 7.2.1.1.8 7.2.1.2.8 "
        ::= { hwadslAturPerfDataInfoEntry 17 }

    hwAdslAturPerfCurr1DayLeftrs OBJECT-TYPE
        SYNTAX Counter32
        MAX-ACCESS read-only
        STATUS current
        DESCRIPTION
                   "If retransmission is used in a given transmit direction, this parameter is a count of
                    the seconds with a far-end leftr defect present observed over the current 24 hours
                    accumulation period.
                   "
        REFERENCE   "ITU-T G.997.1, paragraph 7.2.1.1.6 7.2.1.2.6 "
        ::= { hwadslAturPerfDataInfoEntry 18 }

    hwAdslAturPerfCurr1DayEfb OBJECT-TYPE
        SYNTAX Counter32
        MAX-ACCESS read-only
        STATUS current
        DESCRIPTION
                "If retransmission is used in a given transmit direction, this parameter
                 is a count of the number of error-free bits current observed over the current 24 hours
                 accumulation period.
                 The far-end counter is only defined in downstream.
                "
        REFERENCE   "ITU-T G.997.1, paragraph 7.2.1.1.7 7.2.1.2.7 "
        ::= { hwadslAturPerfDataInfoEntry 19 }

   hwAdslAturPerfCurr1DayMinEftr OBJECT-TYPE
        SYNTAX Counter32
        MAX-ACCESS read-only
        STATUS current
        DESCRIPTION
                   "If retransmission is used in a given transmit direction, this parameter MINEFTR reports
                    the minimum of the EFTR(Error-free throughput rate) observed over the current 24 hours
                    accumulation period.
                    The far-end value is only defined in downstream.
                   "
        REFERENCE   "ITU-T G.997.1, paragraph 7.2.1.1.8 7.2.1.2.8 "
        ::= { hwadslAturPerfDataInfoEntry 20 }

   hwAdslAturPerfPrev1DayLeftrs OBJECT-TYPE
        SYNTAX Counter32
        MAX-ACCESS read-only
        STATUS current
        DESCRIPTION
                   "If retransmission is used in a given transmit direction, this parameter is a count of
                    the seconds with a far-end leftr defect present over the previous 24 hours
                    accumulation period during this interval.
                   "
        REFERENCE   "ITU-T G.997.1, paragraph 7.2.1.1.6 7.2.1.2.6 "
        ::= { hwadslAturPerfDataInfoEntry 21 }

   hwAdslAturPerfPrev1DayEfb OBJECT-TYPE
        SYNTAX Counter32
        MAX-ACCESS read-only
        STATUS current
        DESCRIPTION
                "If retransmission is used in a given transmit direction, this parameter
                 is a count of the number of error-free bits observed over the previous 24 hours
                    accumulation period during this interval.
                 The far-end counter is only defined in downstream.
                "
        REFERENCE   "ITU-T G.997.1, paragraph 7.2.1.1.7 7.2.1.2.7 "
        ::= { hwadslAturPerfDataInfoEntry 22 }

   hwAdslAturPerfPrev1DayMinEftr OBJECT-TYPE
        SYNTAX Counter32
        MAX-ACCESS read-only
        STATUS current
        DESCRIPTION
                   "If retransmission is used in a given transmit direction, this parameter MINEFTR reports
                    the minimum of the EFTR(Error-free throughput rate) observed over the previous 24 hours
                    accumulation period during this interval.
                    The far-end value is only defined in downstream.
                   "
        REFERENCE   "ITU-T G.997.1, paragraph 7.2.1.1.8 7.2.1.2.8 "
        ::= { hwadslAturPerfDataInfoEntry 23 }

    hwAdslAturPerfCurrEverBeforeLeftrs OBJECT-TYPE
        SYNTAX Counter32
        MAX-ACCESS read-only
        STATUS current
        DESCRIPTION
                   "If retransmission is used in a given transmit direction, this parameter is a count of
                    the seconds with a far-end leftr defect present observed ever before.
                   "
        REFERENCE   "ITU-T G.997.1, paragraph 7.2.1.1.6 7.2.1.2.6 "
        ::= { hwadslAturPerfDataInfoEntry 24 }

   hwAdslAturPerfCurrEverBeforeEfb OBJECT-TYPE
        SYNTAX Counter32
        MAX-ACCESS read-only
        STATUS current
        DESCRIPTION
                "If retransmission is used in a given transmit direction, this parameter
                 is a count of the number of error-free bits observed ever before.
                 The far-end counter is only defined in downstream.
                "
        REFERENCE   "ITU-T G.997.1, paragraph 7.2.1.1.7 7.2.1.2.7 "
        ::= { hwadslAturPerfDataInfoEntry 25 }

   hwAdslAturPerfCurrEverBeforeMinEftr OBJECT-TYPE
        SYNTAX Counter32
        MAX-ACCESS read-only
        STATUS current
        DESCRIPTION
                   "If retransmission is used in a given transmit direction, this parameter MINEFTR reports
                    the minimum of the EFTR(Error-free throughput rate) observed ever before.
                    The far-end value is only defined in downstream.
                   "
        REFERENCE  "ITU-T G.997.1, paragraph 7.2.1.1.8 7.2.1.2.8 "
        ::= { hwadslAturPerfDataInfoEntry 26 }

-- hwadslAturIntervalInfoTable
    hwadslAturIntervalInfoTable   OBJECT-TYPE
        SYNTAX SEQUENCE OF HwadslAturIntervalInfoEntry
        MAX-ACCESS      not-accessible
        STATUS          current
        DESCRIPTION
                   "This table provides one row for each Atur
                    performance data collection interval.
                    ADSL physical interfaces are
                    those ifEntries where ifType is equal to adsl(94).
                    The indexes of this table are ifIndex and adslAturIntervalNumber.
                   "
        ::= { hwAdslMibObjects 34 }

    hwadslAturIntervalInfoEntry   OBJECT-TYPE
        SYNTAX  HwadslAturIntervalInfoEntry
        MAX-ACCESS      not-accessible
        STATUS          current
        DESCRIPTION
                   "This table provides one row for each Atur
                    performance data collection interval.
                    ADSL physical interfaces are
                    those ifEntries where ifType is equal to adsl(94).
                    The indexes of this entry are ifIndex and adslAturIntervalNumber.
                   "
        INDEX  { ifIndex, adslAturIntervalNumber }
        ::= { hwadslAturIntervalInfoTable 1 }

    HwadslAturIntervalInfoEntry ::=
        SEQUENCE {
                     hwAdslAturIntervalStartTime            DateAndTime,
                     hwAdslAturIntervalInmainpeq            OCTET STRING,
                     hwAdslAturIntervalInmame               Counter32,
                     hwAdslAturIntervalInmaiat              OCTET STRING,
                     hwAdslAturIntervalLeftrs               Counter32,
                     hwAdslAturIntervalEfb                  Counter32,
                     hwAdslAturIntervalMinEftr              Counter32
                 }

    hwAdslAturIntervalStartTime  OBJECT-TYPE
       SYNTAX      DateAndTime
       MAX-ACCESS  read-only
       STATUS      current
       DESCRIPTION
           "Start time of the historical 15-minute performance statistics."
       ::= { hwadslAturIntervalInfoEntry 1 }

    hwAdslAturIntervalInmainpeq  OBJECT-TYPE
        SYNTAX      OCTET STRING  (SIZE(0..68))
        MAX-ACCESS  read-only
        STATUS      current
        DESCRIPTION
            "This parameter is a count of the INMAINPEQi anomalies
             occurring on the line at 15 minutes interval.
             Each INMAINPEQ needs 4 bytes.
            "
        REFERENCE    "ITU-T G.997.1, paragraph 7.2.1"
        ::= { hwadslAturIntervalInfoEntry 2 }

    hwAdslAturIntervalInmame  OBJECT-TYPE
        SYNTAX      Counter32
        MAX-ACCESS  read-only
        STATUS      current
        DESCRIPTION
            "This parameter is a count of the INMAME anomalies
             occurring on the line at 15 minutes interval.
            "
        REFERENCE    "ITU-T G.997.1, paragraph 7.2.1"
        ::= { hwadslAturIntervalInfoEntry 3 }

    hwAdslAturIntervalInmaiat  OBJECT-TYPE
        SYNTAX      OCTET STRING  (SIZE(0..32))
        MAX-ACCESS  read-only
        STATUS      current
        DESCRIPTION
            "This parameter is a count of the INMAIATi anomalies
             occurring on the line at 15 minutes interval.
             Each INMAIAT needs 4 bytes.
            "
        REFERENCE    "ITU-T G.997.1, paragraph 7.2.1"
        ::= { hwadslAturIntervalInfoEntry 4 }

    hwAdslAturIntervalLeftrs OBJECT-TYPE
        SYNTAX Counter32
        MAX-ACCESS read-only
        STATUS current
        DESCRIPTION
                   "If retransmission is used in a given transmit direction, this parameter is a count of
                    the seconds with a far-end leftr defect present observed over the previous 15 minutes
                    accumulation period during the interval.
                   "
        REFERENCE  "ITU-T G.997.1, paragraph 7.2.1.1.6 7.2.1.2.6"
        ::= { hwadslAturIntervalInfoEntry 5 }

    hwAdslAturIntervalEfb OBJECT-TYPE
        SYNTAX Counter32
        MAX-ACCESS read-only
        STATUS current
        DESCRIPTION
                "If retransmission is used in a given transmit direction, this parameter
                 is a count of the number of error-free bits observed over the previous 15 minutes
                 accumulation period during the interval.
                 The far-end counter is only defined in downstream.
                "
        REFERENCE  "ITU-T G.997.1, paragraph 7.2.1.1.6 7.2.1.2.7"
        ::= { hwadslAturIntervalInfoEntry 6 }

    hwAdslAturIntervalMinEftr OBJECT-TYPE
        SYNTAX Counter32
        MAX-ACCESS read-only
        STATUS current
        DESCRIPTION
                   "If retransmission is used in a given transmit direction, this parameter MINEFTR reports
                    the minimum of the EFTR(Error-free throughput rate) observed over the 15 minutes
                    accumulation period during the interval.
                    The far-end value is only defined in downstream.
                   "
        REFERENCE  "ITU-T G.997.1, paragraph 7.2.1.1.6 7.2.1.2.8"
        ::= { hwadslAturIntervalInfoEntry 7 }

--ADSL traps description

    hwAdslTrapsVbOids OBJECT IDENTIFIER ::= { hwAdsl 3 }

    hwadslPMThresholdItem OBJECT-TYPE
        SYNTAX OCTET STRING (SIZE (0..1024))
        MAX-ACCESS accessible-for-notify
        STATUS current
        DESCRIPTION "Indicates the threshold item."
    ::= { hwAdslTrapsVbOids 0 }

    hwadslChipsetID OBJECT-TYPE
        SYNTAX Integer32
        MAX-ACCESS accessible-for-notify
        STATUS current
        DESCRIPTION "The chipset id of the board."
    ::= { hwAdslTrapsVbOids 1 }

    hwAdslRequestID OBJECT-TYPE
        SYNTAX Integer32
        MAX-ACCESS accessible-for-notify
        STATUS current
        DESCRIPTION "RequestID."
    ::= { hwAdslTrapsVbOids 2 }

    hwadslSeltTestStartResult OBJECT-TYPE
        SYNTAX Integer32
        MAX-ACCESS accessible-for-notify
        STATUS current
        DESCRIPTION
                   "ADSL selt test start result.
                   Options:
                   1. normal - A message is returned indicating that the SELT is successful.
                   2. failed - A message is returned indicating that the SELT fails."
    ::= { hwAdslTrapsVbOids 3 }

    hwADSLProfOperType OBJECT-TYPE
        SYNTAX INTEGER
                      {
                          add(1),
                          modify(2),
                          delete(3)
                      }
        MAX-ACCESS accessible-for-notify
        STATUS current
        DESCRIPTION "ADSL profile operate type.
                     Options:
                     1.add(1)    - Add an ADSL profile
                     2.modify(2) - Modify an ADSL profile
                     3.delete(3) - Delete an ADSL profile
                    "
    ::= { hwAdslTrapsVbOids 4 }

    hwadslLinePMThresholdValue OBJECT-TYPE
        SYNTAX Integer32
        MAX-ACCESS accessible-for-notify
        STATUS current
        DESCRIPTION
                   "Indicate the threshold value of threshold item."
    ::= { hwAdslTrapsVbOids 5 }

    hwadslLinePMCurrentValue OBJECT-TYPE
        SYNTAX Integer32
        MAX-ACCESS accessible-for-notify
        STATUS current
        DESCRIPTION
                   "Indicate the current value of threshold item."
    ::= { hwAdslTrapsVbOids 6 }

    hwAdslExtTraps OBJECT IDENTIFIER ::= { hwAdsl 2 }
    hwAdslCommonTraps OBJECT IDENTIFIER ::= { hwAdslExtTraps 1 }
    hwAdslCommonTrapsPrefix OBJECT IDENTIFIER ::= { hwAdslCommonTraps 0 }

    hwAdslPortActRateMonitorInfoTrap NOTIFICATION-TYPE
        OBJECTS {
                hwFrameIndex,
                hwSlotIndex,
                hwPortIndex,
                hwAdslAtucLatestTxRateInfo,
                hwAdslAturLatestTxRateInfo,
                hwAdslAtucLatestTxRateThresholdInfo,
                hwAdslAturLatestTxRateThresholdInfo,
                hwAdslLineLatestActiveTimeInfo,
                hwAdslAtucLatestSnrMgnInfo,
                hwAdslAturLatestSnrMgnInfo,
                hwAdslAtucLatestAtnInfo,
                hwAdslAturLatestAtnInfo,
                hwAdslAtucLatestAttainableRateInfo,
                hwAdslAturLatestAttainableRateInfo,
                hwAdslAtucLatestConfTxRateInfo,
                hwAdslAturLatestConfTxRateInfo,
                hwAdslAtucLatestInterleaveDelayInfo,
                hwAdslAturLatestInterleaveDelayInfo,
                hwAdslAtucLatestTargetSnrMgnInfo,
                hwAdslAturLatestTargetSnrMgnInfo,
                hwSubslotIndex,
                hwAlarmId,
                hwAlarmTime,
                hwAlarmSn,
                hwCauseId,
                hwTrapType
            }
        STATUS current
        DESCRIPTION
            "If ADSL act rate is lower than threshold,
             hwTrapType is 1. Otherwise, hwTrapType is 2.
             This trap message is generated when the ADSL port rate fails to meet the requirement.
            "

        ::= { hwAdslCommonTraps 0 1 }

    hwAdslPortRateChangeInfoTrap NOTIFICATION-TYPE
        OBJECTS {
                hwFrameIndex,
                hwSlotIndex,
                hwPortIndex,
                hwIasConfigChangeTrapID,
                hwAdslPortRateChangeTrapIPIAIDInfo,
                hwAdslPortRateChangeTrapMUXIDInfo,
                hwAdslPortRateChangeTrapTimeStampInfo,
                hwAdslPortRateChangeTrapDSLineRateInfo,
    	        hwAdslPortRateChangeTrapUSLineRateInfo,
    	        hwAdslPortRateChangeTrapEventTypeInfo,
    	        hwAdslPortRateChangeTrapDslTypeInfo
    	    }
        STATUS current
        DESCRIPTION "ADSL act rate is change trap.
                     This trap message is generated when the ADSL port rate changed.
                    "
        ::= { hwAdslCommonTraps 0 2 }
    hwAdslDynamicCollectInfoTrap NOTIFICATION-TYPE
        OBJECTS {
                hwXdslDynamicInfoCollectStatusInfo,
                hwFrameIndex,
                hwSlotIndex,
                hwXdslDynamicInfoCollectTimeInfo
    	    }
        STATUS current
        DESCRIPTION "XDSL dynamic collect trap.
                     This trap message is generated when xDSL port Dynamic information collect.
                    "
        ::= { hwAdslCommonTraps 0 3 }

    hwAdslDeltOperResultInfoTrap NOTIFICATION-TYPE
        OBJECTS {
                hwBTSSAdslDeltTestOperResult,
                hwAdslRequestID,
                ifIndex
    	    }
        STATUS current
        DESCRIPTION "ADSL delt trap.
                     This trap message is generated when the ADSL port delt test finish.
                    "
        ::= { hwAdslCommonTraps 0 4 }

    hwAdslPortStatusChangeInfoTrap NOTIFICATION-TYPE
        OBJECTS {
                hwFrameIndex,
                hwSlotIndex,
                hwPortIndex,
                hwPortOperStatus,
                hwPortPrimaryStatus,
                hwPortSecondaryStatus
    	    }
        STATUS current
        DESCRIPTION "ADSL port status change trap.
                     This trap message is generated when the ADSL port status changed.
                    "
        ::= { hwAdslCommonTraps 0 5 }

    hwAdslSeltStartResultTrap NOTIFICATION-TYPE
        OBJECTS {
                hwadslSeltTestStartResult,
                hwAdslRequestID
    	        }
        STATUS current
        DESCRIPTION "ADSL selt test start trap.
                     This trap message is generated when the ADSL port selt test finish.
                    "
        ::= { hwAdslCommonTraps 0 6 }

    hwADSLLineProfChangeTrap NOTIFICATION-TYPE
        OBJECTS {
                hwConfigChangeIP,
                hwADSLProfOperType,
                adslLineConfProfileName,
                adslAtucConfRateMode,
                adslConfProfileLineType,
                adslAtucConfTargetSnrMgn,
                adslAtucConfMaxSnrMgn,
                adslAtucConfMinSnrMgn,
                adslAtucConfDownshiftSnrMgn,
                adslAtucConfUpshiftSnrMgn,
                adslAtucConfMinUpshiftTime,
                adslAtucConfMinDownshiftTime,
                adslAtucChanConfFastMinTxRate,
                adslAtucChanConfInterleaveMinTxRate,
                adslAtucChanConfFastMaxTxRate,
                adslAtucChanConfInterleaveMaxTxRate,
                adslAtucChanConfMaxInterleaveDelay,
                adslAturConfTargetSnrMgn,
                adslAturConfMaxSnrMgn,
                adslAturConfMinSnrMgn,
                adslAturConfDownshiftSnrMgn,
                adslAturConfUpshiftSnrMgn,
                adslAturConfMinUpshiftTime,
                adslAturConfMinDownshiftTime,
                adslAturChanConfFastMinTxRate,
                adslAturChanConfInterleaveMinTxRate,
                adslAturChanConfFastMaxTxRate,
                adslAturChanConfInterleaveMaxTxRate,
                adslAturChanConfMaxInterleaveDelay,
                hwAdslAtucConfDownBitSwap,
                hwAdslAtucConfUpBitSwap,
                hwAdslTrellionsModeEnable,
                hwAdslTransmissionModeCfg,
                adslConfProfileLineType
    	        }
        STATUS current
        DESCRIPTION "ADSL line profile change trap.
                     This trap message is generated when the ADSL line profile changed.
                    "
        ::= { hwAdslCommonTraps 0 7 }

    hwADSLAlarmProfChangeTrap NOTIFICATION-TYPE
        OBJECTS {
                hwConfigChangeIP,
                hwADSLProfOperType,
                adslLineAlarmConfProfileName,
                adslAtucThresh15MinLofs,
                adslAtucThresh15MinLoss,
                adslAtucThresh15MinLols,
                adslAtucThresh15MinLprs,
                adslAtucThresh15MinESs,
                adslAtucThreshFastRateUp,
                adslAtucThreshInterleaveRateUp,
                adslAtucThreshFastRateDown,
                adslAtucThreshInterleaveRateDown,
                adslAtucInitFailureTrapEnable,
                adslAturThresh15MinLofs,
                adslAturThresh15MinLoss,
                adslAturThresh15MinLprs,
                adslAturThresh15MinESs,
                adslAturThreshFastRateUp,
                adslAturThreshInterleaveRateUp,
                adslAturThreshFastRateDown,
                adslAturThreshInterleaveRateDown,
                adslLineAlarmConfProfileRowStatus,
                adslAtucThreshold15MinFailedFastR,
                adslAtucThreshold15MinSesL,
                adslAtucThreshold15MinUasL,
                adslAturThreshold15MinSesL,
                adslAturThreshold15MinUasL,
                hwadslLineAlarmConfProfileDyingGaspCfg,
                hwadslLineAlarmConfProfXturThresh15MinLeftrs,
                hwAdslLineAlarmConfProfileActiveFailAlarmSwitch
    	        }
        STATUS current
        DESCRIPTION "ADSL alarm profile change trap.
                     This trap message is generated when the ADSL alarm profile changed.
                    "
        ::= { hwAdslCommonTraps 0 8 }

    hwADSLExtLineProfChangeTrap NOTIFICATION-TYPE
        OBJECTS {
                hwConfigChangeIP,
                hwADSLProfOperType,
                hwadslLineExtConfProfileNameCfg
    	        }
        STATUS current
        DESCRIPTION "ADSL extended line profile change trap.
                     This trap message is generated when the ADSL extended line profile changed.
                    "
        ::= { hwAdslCommonTraps 0 9 }


    -- Alarm Trap
    hwAdslAlarmTraps OBJECT IDENTIFIER ::= { hwAdslExtTraps 2 }
    hwAdslAlarmTrapsPrefix OBJECT IDENTIFIER ::= { hwAdslAlarmTraps 0 }

    hwAdslPortActRateFailThresholdAlarmTrap NOTIFICATION-TYPE
        OBJECTS {
                hwFrameIndex,
                hwSlotIndex,
                hwPortIndex
                }
        STATUS current
        DESCRIPTION "This trap message is generated when the ADSL port activation rate
                     fails to reach the rate threshold.
                    "
        ::= { hwAdslAlarmTraps 0 1 }

    hwAdslPortActRateReachThresholdAlarmTrap NOTIFICATION-TYPE
        OBJECTS {
                hwFrameIndex,
                hwSlotIndex,
                hwPortIndex
                }
        STATUS current
        DESCRIPTION "This trap message is generated when the ADSL port activation rate
                     succeeds in reaching the rate threshold.
                    "
        ::= { hwAdslAlarmTraps 0 2 }

    hwAdslPortAutoDeactiveAlarmTrap NOTIFICATION-TYPE
        OBJECTS {
                hwFrameIndex,
                hwSlotIndex,
                hwPortIndex
                }
        STATUS current
        DESCRIPTION "This trap message is generated when the ADSL port
                     is automatically deactivated due to the line fault."
        ::= { hwAdslAlarmTraps 0 3 }

    hwAdslPortReactiveAlarmTrap NOTIFICATION-TYPE
        OBJECTS {
                hwFrameIndex,
                hwSlotIndex,
                hwPortIndex
                }
        STATUS current
        DESCRIPTION "This trap message is generated when the ADSL port
                     is re-activated after the ADSL line recovers."
        ::= { hwAdslAlarmTraps 0 4 }

        hwAdslPortStatReachThresholdAlarmTrap NOTIFICATION-TYPE
        OBJECTS {
                hwFrameIndex,
                hwSlotIndex,
                hwPortIndex,
                hwadslPMThresholdItem,
                hwadslLinePMThresholdValue,
                hwadslLinePMCurrentValue
                }
        STATUS current
        DESCRIPTION "This trap message is generated when the performance
                     statistics of the ADSL port reach the threshold."
        ::= { hwAdslAlarmTraps 0 5 }

        hwAdslPortATURPowerOffAlarmTrap NOTIFICATION-TYPE
        OBJECTS {
                hwFrameIndex,
                hwSlotIndex,
                hwPortIndex
                }
        STATUS current
        DESCRIPTION "This trap message is generated when the ATU-R is powered off."
        ::= { hwAdslAlarmTraps 0 6 }

        hwAdslPortActRateLowerThresholdAlarmTrap  NOTIFICATION-TYPE
        OBJECTS {
                hwFrameIndex,
                hwSlotIndex,
                hwPortIndex,
                hwAdslAtucLatestTxRateInfo,
                hwAdslAturLatestTxRateInfo
                }
        STATUS current
        DESCRIPTION "This trap message is generated when the activation
                     rate of the xDSL line is lower than the threshold."
        ::= { hwAdslAlarmTraps 0 7 }

        hwAdslChipsetNotAvailableAlarmTrap NOTIFICATION-TYPE
        OBJECTS {
                hwFrameIndex,
                hwSlotIndex,
                hwadslChipsetID
                }
        STATUS current
        DESCRIPTION "This trap message is generated when the ADSL chipset is not available."
        ::= { hwAdslAlarmTraps 0 8 }

        hwAdslChipsetRecoverAlarmTrap NOTIFICATION-TYPE
        OBJECTS {
                hwFrameIndex,
                hwSlotIndex,
                hwadslChipsetID
                }
        STATUS current
        DESCRIPTION "This trap message is generated when the ADSL chipset recovers."
        ::= { hwAdslAlarmTraps 0 9 }

        hwAdslPortDeactiveAlarmTrap NOTIFICATION-TYPE
        OBJECTS {
                hwFrameIndex,
                hwSlotIndex
                }
        STATUS current
        DESCRIPTION "Some xDSL ports or all the xDSL ports are automatically deactivated due to lack of licenses.
                     This trap message is generated when the xDSL ports are automatically deactivated."
        ::= { hwAdslAlarmTraps 0 10 }


END
