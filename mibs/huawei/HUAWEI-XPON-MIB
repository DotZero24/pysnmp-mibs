-- =================================================================
-- Copyright (C) 2019 by HUAWEI TECHNOLOGIES. All rights reserved.
-- Description:  The MIB module defines MIB objects which provides GPON and EPON management NMS interfaces.
-- Reference:
-- Version: V2.14
-- ================================================================

    HUAWEI-XPON-MIB DEFINITIONS ::= BEGIN
        IMPORTS
            MODULE-IDENTITY, mib-2, OBJECT-TYPE, Counter32, Counter64, Unsigned32,
            Integer32, zeroDotZero, IpAddress, Gauge32, NOTIFICATION-TYPE
                FROM SNMPv2-SMI
            TruthValue, DateAndTime, RowStatus, MacAddress, TEXTUAL-CONVENTION
                FROM SNMPv2-TC
            ifIndex
                FROM IF-MIB
            MODULE-COMPLIANCE, OBJECT-GROUP
                FROM SNMPv2-CONF
            SnmpAdminString
                FROM SNMP-FRAMEWORK-MIB
            OwnerString, EntryStatus
                FROM RMON-MIB
            huaweiMgmt, huaweiUtility
                FROM HUAWEI-MIB;

        hwXponDeviceMIB MODULE-IDENTITY
            LAST-UPDATED "201908221000Z"
            ORGANIZATION "Huawei Technologies Co.,Ltd."
            CONTACT-INFO
                         "Huawei Industrial Base
                          Bantian, Longgang
                          Shenzhen 518129
                          People's Republic of China
                          Website: http://www.huawei.com
                          Email: support@huawei.com
                         "
            DESCRIPTION "The MIB module defines MIB objects which provides GPON and EPON management NMS interfaces."
    --  Revision history
            REVISION     "201908221000Z"
            DESCRIPTION  "V2.14, changes in this revision:
                         - Add the leaf hwGponOltOpticsModuleInfoPartNum in table hwGponOltOpticsModuleInfoEntry.
                         "
            REVISION     "201906271000Z"
            DESCRIPTION  "V2.13, changes in this revision:
                         - Modify the description of the leaf hwGponDeviceSrvProfPortVlanCfgPortCVlan in table hwGponDeviceSrvProfPortVlanCfgTable.
                         "
            REVISION     "201906241000Z"
            DESCRIPTION  "V2.12, changes in this revision:
                         - Add the table of hwGponDeviceLineProfGemBundleCfgTable.
                         "
            REVISION     "201905251000Z"
            DESCRIPTION  "V2.11, changes in this revision:
                         - Add the leaf hwGponOntObjectSnmpStaticRouteOutputPort in table hwGponDeviceOntSnmpStaticRouteConfigTable.
                          "
            REVISION     "201904081000Z"
            DESCRIPTION  "V2.10, changes in this revision:
                         - Add a enum value of the leaf node hwGponDeviceSrvProfileUpIgmpTransmitMode.
                          "
            REVISION     "201902251000Z"
            DESCRIPTION  "V2.09, changes in this revision:
                         - Add a enum value of the leaf node hwGponOltOpticsModuleXponSubType.
                          "
            REVISION     "201812161000Z"
            DESCRIPTION  "V2.08, changes in this revision:
                         - Add a enum value of the leaf node hwEponOltXFPOpticsModuleXponSubType.
                          "
            REVISION     "201808201000Z"
            DESCRIPTION  "V2.07, changes in this revision:
                         - Add the leaf hwGponDeviceAutoFindOntInfoEquipmentSn in table hwGponDeviceAutoFindOntInfoTable.
                         - Add the leaf hwGponDeviceAutoFindOntInfoMac in table hwGponDeviceAutoFindOntInfoTable.
                         - Add the leaf hwGponDeviceOntEquipmentSn in table hwGponDeviceOntVersionInfoTable.
                         - Add the leaf hwGponDeviceOntMac in table hwGponDeviceOntVersionInfoTable.
                         - Add seven enum values of the leaf node hwGponDeviceOntRegisterInfoDownCause.
                         "

            REVISION     "201806131000Z"
            DESCRIPTION  "V2.06, changes in this revision:
                         - Add a enum value of the leaf node hwGponDeviceOntRegisterInfoDownCause.
                         "
            REVISION     "201806061000Z"
            DESCRIPTION  "V2.05, changes in this revision:
                         - Add the leaf hwGponOltEthernetStatisticSendGreenOctets in table hwGponOltEthernetStatisticTable.
                         - Add the leaf hwGponOltEthernetStatisticSendGreenPakts in table hwGponOltEthernetStatisticTable.
                         - Add the leaf hwGponOltEthernetStatisticGreenDropPakts in table hwGponOltEthernetStatisticTable.
                         - Add the leaf hwGponOltEthernetStatisticSendYellowOctets in table hwGponOltEthernetStatisticTable.
                         - Add the leaf hwGponOltEthernetStatisticSendYellowPakts in table hwGponOltEthernetStatisticTable.
                         - Add the leaf hwGponOltEthernetStatisticYellowDropPakts in table hwGponOltEthernetStatisticTable.
                         "
    		REVISION     "201803121000Z"
            DESCRIPTION  "V2.04, changes in this revision:
                         - Add the leaft hwXponDeviceDbaProfileAsynCommit in table hwXponDeviceDbaProfileInfoTable.
                         "
            REVISION     "201802061000Z"
            DESCRIPTION  "V2.03, changes in this revision:
                         - Add the enumerate of leaf hwEponOltXFPOpticsModuleXponEncapsulationType in table hwEponOltXFPOpticsModuleInfoTable.
                         - Add the enumerate of leaf hwGponOltOpticsModuleXponType in table hwGponOltOpticsModuleInfoTable.
                         - Add the enumerate of leaf hwGponOltOpticsModuleXponSubType in table hwGponOltOpticsModuleInfoTable.
                         - Add the enumerate of leaf hwGponOltOpticsModuleXponUsedType in table hwGponOltOpticsModuleInfoTable.
                         - Add the enumerate of leaf hwGponOltOpticsModuleXponEncapsulationType in table hwGponOltOpticsModuleInfoTable.
                         "
            REVISION     "201801311000Z"
            DESCRIPTION  "V2.02, changes in this revision:
                         - Add the leaft hwXponDeviceDbaProfileOperateResult in table hwXponDeviceDbaProfileInfoTable.
    			 "

            REVISION     "201801032029Z"
            DESCRIPTION  "V2.01, changes in this revision:
                         - Add two enum values of the leaf node hwEponDeviceOntRegisterInfoDownCause.
                         "

            REVISION     "201711181000Z"
            DESCRIPTION  "V1.20, changes in this revision:
                         - Add the leaf hwEponDeviceOltControlPortReset in table hwEponDeviceOltControlInfoTable.
                         - Add the leaf hwGponDeviceOltControlPortReset in table hwGponDeviceOltControlInfoTable.
                         - Modify the description of the leaf hwGponDeviceSrvProfPortVlanCfgPortCVlan in table hwGponDeviceSrvProfPortVlanCfgTable.
                         "

            REVISION     "201711021700Z"
            DESCRIPTION  "V1.99, changes in this revision:
                         - Add the leaf hwGponDeviceSrvProfOntPortCfgL2IsolateSwitch in table hwGponDeviceSrvProfOntPortCfgTable.
                         "

            REVISION     "201710191000Z"
            DESCRIPTION  "V1.98, changes in this revision:
                         - Modify the description of the leaf hwXponDeviceDbaProfilePriority in table hwXponDeviceDbaProfileInfoTable.
                         "

            REVISION     "201708101000Z"
            DESCRIPTION  "V1.97, changes in this revision:
                         - Modify the value range of the leaf hwGponDeviceSrvProfileMTU in table hwGponDeviceSrvProfileOntCfgTable.
                         "

            REVISION     "201707271000Z"
            DESCRIPTION  "V1.96, changes in this revision:
                         - Add the leaf hwGponDeviceSrvProfOntPortCfgUnknownUnicastRate in table hwGponDeviceSrvProfOntPortCfgTable.
                         - Add the leaf hwGponDeviceSrvProfOntPortCfgBroadcastRate in table hwGponDeviceSrvProfOntPortCfgTable.
                         - Add the leaf hwGponDeviceSrvProfOntPortCfgUnknownMulticastRate in table hwGponDeviceSrvProfOntPortCfgTable.
                         - Modify the description of the leaf hwGponDeviceSrvProfOntPortCfgClassProfileIndex in table hwGponDeviceSrvProfOntPortCfgTable.
                         "

            REVISION     "201707210900Z"
            DESCRIPTION  "V1.95, changes in this revision:
                         - Add the enumerate of leaf hwGponOltOpticsModuleXponSubType in table hwGponOltOpticsModuleInfoTable.
                         - Add the enumerate of leaf hwEponOltOpticsModuleXponSubType in table hwEponOltOpticsModuleInfoTable.
                         "

            REVISION     "201707071600Z"
            DESCRIPTION  "V1.94, changes in this revision:
                          - Add the leaf hwGponDeviceSrvProfOntPortCfgClassProfileIndex in table hwGponDeviceSrvProfOntPortCfgTable.
			  - Modify the description of the leaf hwXponDeviceOntPortClassProfileQueuemapped in table hwXponDeviceOntPortClassTable.
			  - Modify the description of the leaf hwXponDeviceOntPortClassProfilePriMark in table hwXponDeviceOntPortClassTable.
			  - Modify the description of the leaf hwXponDeviceOntPortClassProfileFieldselect in table hwXponDeviceOntPortClassTable.
                          - Modify the description of the leaf hwXponDeviceOntPortClassProfileOperator in table hwXponDeviceOntPortClassTable.
                         "

            REVISION     "201706291600Z"
            DESCRIPTION  "V1.93, changes in this revision:
                         - Modify the string length of the leaf hwGponDeviceOltControlDespt.
                         - Modify the string length of the leaf hwEponDeviceOltControlDespt.
                         "

            REVISION     "201706281000Z"
            DESCRIPTION  "V1.92, changes in this revision:
                         - Modify the range of leaf hwEponDeviceOntExtendedModel.
                         - Modify the range of leaf hwEponDeviceOntOuiVersion.
                         - Modify the MAX-ACCESS value of the leaf hwEponOltChannelId.
                         "

            REVISION     "201705261000Z"
            DESCRIPTION  "V1.91, changes in this revision:
                         - Add the leaf hwXponOntLoadServerPort in table hwXponOntLoadCtrlTable.
	    		 "

            REVISION     "201704220900Z"
            DESCRIPTION  "V1.90, changes in this revision:
                         - Add the leaf hwGponOntEthernetStatisticStateChangeTimes in table hwGponOntEthernetStatisticTable.
                         - Add the leaf hwGponOntEthernetStatisticDuration in table hwGponOntEthernetStatisticTable.
                         - Add the leaf hwGponDeviceOntEthernetMode in table hwGponDeviceOntEthernetPortCfgTable.
                         - Add the leaf hwGponDeviceOntEthernetOpticalModuleStatus in table hwGponDeviceOntEthernetPortCfgTable.
                         - Add the leaf hwGponDeviceOntEthernetOnlineDuration in table hwGponDeviceOntEthernetPortCfgTable.
                         - Add the leaf hwGponDeviceSrvProfileMTU in table hwGponDeviceSrvProfileOntCfgTable.
                         - Add the leaf hwGponDeviceSrvProfileMonitorLinkSwitch in table hwGponDeviceSrvProfileOntCfgTable.
                         "

            REVISION     "201704170900Z"
            DESCRIPTION  "V1.89, changes in this revision:
                         - Modify the description of the leaf hwGponDeviceOntControlLastRanging in table hwGponDeviceOntControlInfoTable.
                         "

            REVISION     "201702090900Z"
            DESCRIPTION  "V1.88, changes in this revision:
                         - Modify the description of the leaf hwGponDeviceOntEntryStatus in table hwGponDeviceOntConfigInfoTable.
                         - Modify the description of the leaf hwGponDeviceOntControlRanging in table hwGponDeviceOntControlInfoTable.
                         "

            REVISION     "201701060900Z"
            DESCRIPTION  "V1.87, changes in this revision:
                         - Add the leaf hwGponDeviceOntManualSwitchChannelIfindex in table hwGponDeviceOntConfigInfoTable.
                         "
            REVISION     "201611020900Z"
            DESCRIPTION  "V1.86, changes in this revision:
                         - Add the leaf hwGponDeviceOntEthernetRouteSwitch in table hwGponDeviceOntEthernetPortCfgTable.
                         "
            REVISION     "201608200900Z"
            DESCRIPTION  "V1.85, changes in this revision:
                         - Add the enumerate of leaf hwEponDeviceOntNniType in table hwEponDeviceOntConfigInfoTable.
                         - Add the enumerate of leaf hwEponDeviceOntActualNniType in table hwEponDeviceOntControlInfoTable.
                         - Add the enumerate of leaf hwEponDeviceOntLastActualNniType in table hwEponDeviceOntControlInfoTable.
                         - Add the enumerate of leaf hwEponDeviceAutoFindOntNniType in table hwEponDeviceAutoFindOntInfoTable.
                         - Add the enumerate of leaf hwEponDeviceRegOntRateType in table hwEponDeviceOntRegInfoTable.
                         - Add the enumerate of leaf hwEponOltChannelId in table hwEponOltChannelEthernetStatisticTable.
                         "
            REVISION     "201608040900Z"
            DESCRIPTION  "V1.84, changes in this revision:
                         - Modify the description of the leaf hwGponDeviceOntObjectNniType in table hwGponDeviceOntConfigTable.
                         - Modify the description of the leaf hwGponDeviceAutoFindOntNniType in table hwGponDeviceOntConfigTable.
                         - Modify the description of the leaf hwGponDeviceOntRegisterOntNniType in table hwGponDeviceOntRegisterInfoTable.
                         "
            REVISION     "201607210900Z"
            DESCRIPTION  "V1.83, changes in this revision:
                         - Add a enum values of the leaf node hwGponDeviceOntPortVlanPhyType.
                         - Add a enum values of the leaf node hwGponDeviceSrvProfPortVlanCfgOntPhyType.
                         - Add leaf hwGponDeviceSrvProfileWifiPortNum in table hwGponDeviceSrvProfileOntCfgTable.
                         "
            REVISION     "201606300900Z"
            DESCRIPTION  "V1.82, changes in this revision:
                         - Add the enumerate of leaf hwGponOltOpticsModuleXponSubType in table hwGponOltOpticsModuleInfoTable.
                         - Add the enumerate of leaf hwEponOltOpticsModuleXponSubType in table hwEponOltOpticsModuleInfoTable.
                         - Add the enumerate of leaf hwEponOltXFPOpticsModuleXponSubType in table hwEponOltXFPOpticsModuleInfoTable.
                         "

            REVISION     "201606021100Z"
            DESCRIPTION  "V1.81, changes in this revision:
                         - Add a enum value of the leaf node hwGponDeviceOntEthernetSpeed.
                         - Modify the range of leaf hwXponOntLoadXmlOntObjectIndex.
                         - Modify the description of the leaf node hwEponDeviceOntLastDownCause.
                         - Modify the description of the leaf node hwGponDeviceOntControlLastDownCause.
                         - Add a enum value of the leaf node hwGponDeviceOntRegisterInfoDownCause.
                         - Add a enum value of the leaf node hwEponDeviceOntRegisterInfoDownCause.
                         "

            REVISION     "201603280900Z"
            DESCRIPTION  "V1.80, changes in this revision:
                         - Add the leaf hwGponDeviceOntRegisterOntNniType in table hwGponDeviceOntRegisterInfoTable.
                         - Modify the enmu name and the description of the leaf hwGponDeviceOntNniType in table hwGponDeviceOntConfigInfoTable.
                         - Modify the description of the leaf hwGponDeviceAutoFindOntInfoOntNniType in table hwGponDeviceAutoFindOntInfoTable.
                         "

            REVISION     "201601040900Z"
	        DESCRIPTION  "V1.79, changes in this revision:
                         - Add the leaf hwGponDeviceOntNniType in table hwGponDeviceOntConfigInfoTable.
                         - Add the leaf hwGponDeviceAutoFindOntInfoOntNniType in table hwGponDeviceAutoFindOntInfoTable.
			 "

	        REVISION     "201512220900Z"
            DESCRIPTION  "V1.78, changes in this revision:
                         - Add the leaf hwGponOltEtherStatisticSendBufferOverflowDropPakts in table hwGponOltEthernetStatisticTable.
			 "

	        REVISION     "201509300900Z"
            DESCRIPTION  "V1.77, changes in this revision:
                         - Add a enum value of the leaf node hwGponDeviceOntAuthMethod in table hwGponDeviceOntConfigInfoTable.
                         - Modify the description of the leaf hwGponDeviceOntSn  in table hwGponDeviceOntConfigInfoTable.
                         - Add the leaf hwGponDeviceOntControlActualSn in table hwGponDeviceOntControlInfoTable.
			 "

            REVISION     "201507290900Z"
            DESCRIPTION  "V1.76, changes in this revision:
                         - Modify the description of row status.
			 "
            REVISION     "201506120900Z"
            DESCRIPTION  "V1.75, changes in this revision:
                         - Add the leaf hwGponDeviceSrvProfileMaxNumOfAdapPotsPort,hwGponDeviceSrvProfileMaxNumOfAdapEthPort,hwGponDeviceSrvProfileMaxNumOfAdapVdslPort,hwGponDeviceSrvProfileMaxNumOfAdapCatvPort in table hwGponDeviceSrvProfileOntCfgTable.
                         - Add the leaf hwEponDeviceSrvProfileMaxNumOfAdapPotsPort,hwEponDeviceSrvProfileMaxNumOfAdapEthPort in table hwEponDeviceSrvProfileOntCfgTable.
			 "
            REVISION     "201504250900Z"
            DESCRIPTION  "V1.74, changes in this revision:
                         - Add the leaf hwEponDeviceOntLastDistance in table hwEponDeviceOntControlInfoTable.
                         - Add the leaf hwGponDeviceOntControlLastRanging in table hwGponDeviceOntControlInfoTable.
			 "
            REVISION     "201504220900Z"
            DESCRIPTION  "V1.73, changes in this revision:
                        - Modify the enmu value of the leaf hwGponDeviceLineProfMappingCfgMappingMode in table hwGponDeviceLineProfMappingCfgTable.
			 "

            REVISION     "201503300900Z"
            DESCRIPTION  "V1.72, changes in this revision:
                        - Modify the enmu value of the leaf hwGponDeviceOntCfgCapManagementMode in table HwGponDeviceOntCfgCapabilityTable.
			 "
            REVISION     "201503040900Z"
            DESCRIPTION  "V1.71, changes in this revision:
                         - Modify the enmu value of the leaf hwGponDeviceOntEthernetSpeed in table hwGponDeviceOntEthernetPortCfgTable.
                         - Modify the enmu value of the leaf hwEponDeviceOntEthernetSpeed in table hwEponDeviceOntEthernetPortCfgTable.
                         - Add the leaf hwEponDeviceOnt10GEPortsNum in table hwEponDeviceOntCapabilityInfoTable.
			 "
            REVISION     "201412230900Z"
            DESCRIPTION  "V1.70, changes in this revision:
                         - Modify the description of the leaf hwGponOntOpticalDdmOltRxOntPower in table hwGponDeviceOntOpticalDdmInfoTable.
                         - Modify the description of the leaf hwEponOntOpticalDdmOltRxOntPower in table hwEponDeviceOntOpticsDdmInfoTable.
                         - Modify the description of the leaf hwGponDeviceOntControlLastDownCause in table hwGponDeviceOntControlInfoTable.
                         - Modify the description of the leaf hwGponDeviceOntRegisterInfoDownCause in table hwGponDeviceOntRegisterInfoDownCause.
                         - Modify the value range of the leaf node hwGponDeviceLineProfMappingCfgOntPhyIndex in table hwGponDeviceLineProfMappingCfgTable.
                         - Modify the description of the leaf hwXponOntUniPhyIndex in table hwXponDeviceOntUniLoopbackTable and hwXponDeviceOntUniLineTestTable.
                         - Modify the description of the leaf hwEponOntPortVlanCfgOntPhyIndex in table hwEponDeviceOntPortVlanTable.
                         - Modify the description of the leaf hwGponDeviceOntControlLastDownCause in table hwGponDeviceOntControlInfoTable.
                         - Add a enum value of the leaf node hwGponDeviceOntRegisterInfoDownCause in table hwGponDeviceOntRegisterInfoDownCause.
			 "

            REVISION     "201411260900Z"
            DESCRIPTION  "V1.69, changes in this revision:
                         - Modify the value of hwXponDeviceOntSnmpProfilePrivacyMode.
                         - Modify the value of hwXponDeviceOntSnmpProfileAuthenticationMode.
                         "



            REVISION     "201411250900Z"
            DESCRIPTION  "V1.68, changes in this revision:
                         - Add the leaf hwGponDeviceAutoFindOntInfoCustomizedInfo in table hwGponDeviceAutoFindOntInfoTable.
                         - Add the leaf hwEponDeviceAutoFindOntInfoCustomizedInfo in table hwEponDeviceAutoFindOntInfoTable.
                         - Add the leaf hwEponDeviceOntCustomizedInfo in table hwEponDeviceOntVersionInfoTable
                         - Add the leaf hwGponDeviceOntCustomizedInfo in table hwGponDeviceOntVersionInfoTable
			 "

            REVISION     "201410240900Z"
            DESCRIPTION  "V1.67, changes in this revision:
                         - Modify the MAX-ACCESS value of the leaf hwXponOntLoadSelectRowStatus, hwEponDeviceOntIpConfigRowStatus, hwXponDeviceOntSnmpProfileRowStatus, hwXponDeviceOntPortClassProfileRowStatus,
			   hwGponDeviceAlarmProfileRowStatus, hwGponOntObjectSnmpStaticRouteRowStatus, hwEponOntSnmpStaticRouteRowStatus, hwGponDeviceSrvProfileOntUpIgmpMsgCfgRowStatus, hwGponDeviceOntGemPortBindEntryStatus,
			   hwEponDeviceAlarmProfileRowStatus.
                         - Modify the implied value of the leaf hwXponDeviceOntPortClassProfileIdIndex, hwEponLineProfLlidCfgLineProfNameIndex, hwEponDeviceSrvProfMulticastVlanCfgSrvProfNameIndex, hwEponDeviceSrvProfPortVlanCfgSrvProfNameIndex,
			   hwEponDeviceSrvProfOntPortCfgSrvProfNameIndex, hwGponDeviceLineProfTcontCfgLineProfNameIndex, hwGponDeviceLineProfTcontCfgTcontIndex, hwGponDeviceLineProfGemCfgLineProfNameIndex, hwGponDeviceLineProfMappingCfgLineProfNameIndex,
			   hwGponDeviceSrvProfOntPortCfgSrvProfNameIndex, hwGponDeviceSrvProfPortVlanCfgSrvProfNameIndex, hwXponDeviceLineProfEthPortBundleCfgLineProfNameIndex, hwGponDeviceSrvProfileOntIgmpCfgNameIndex,
			   hwEponDeviceAlarmProfileInfoNameIndex, hwGponDeviceLineProfileInfoNameIndex.
                         "

            REVISION     "201407310900Z"
            DESCRIPTION  "V1.66, changes in this revision:
                         - Add the leaf hwXponDeviceOpticsDdmAlarmProfileOntCatvRxOpticAlarmUpper and hwXponDeviceOpticsDdmAlarmProfileOntCatvRxOpticAlarmLower in table hwXponDeviceOpticsDdmAlarmProfileInfoTable.
                         - Modify the value range of the leaf hwXponDeviceOntSnmpProfileVersion, hwXponDeviceOntSnmpProfileReadCommunityName, hwXponDeviceOntSnmpProfileWriteCommunityName in table hwXponDeviceOntSnmpProfileInfoTable.
                         - Add the leaf hwXponDeviceOntSnmpProfileUsmUsername, hwXponDeviceOntSnmpProfileAuthenticationMode, hwXponDeviceOntSnmpProfileAuthenticationPassword, hwXponDeviceOntSnmpProfilePrivacyMode, hwXponDeviceOntSnmpProfilePrivacyPassword, hwXponDeviceOntSnmpProfileSecurityLevel in table hwXponDeviceOntSnmpProfileInfoTable.
                         "

            REVISION     "201407100900Z"
            DESCRIPTION  "V1.65, changes in this revision:
                         - Add the leaf hwGponDeviceOntCatvTxPower in table hwGponDeviceOntCatvPortCfgTable.
                         "

            REVISION     "201407060900Z"
            DESCRIPTION  "V1.64, changes in this revision:
                         - Add a enum values of the leaf node hwXponDeviceDbaProfileAdditionalBW.
                         "

            REVISION     "201406160900Z"
            DESCRIPTION  "V1.63, changes in this revision:
                         - Fix the errors for OMSYS.
                         "

            REVISION     "201403140900Z"
            DESCRIPTION "V1.62, changes in this revision:
                         - Add the leaf hwEponDeviceLineProfileTr069ManagementIpIndex in table hwEponDeviceLineProfileInfoTable.
                         - Modify the value range of leaf hwGponOltOpticsModuleXponSubType in table hwGponOltOpticsModuleInfoTable.
                         - Modify the value range of leaf hwEponOltOpticsModuleXponSubType in table hwEponOltOpticsModuleInfoTable.
                         - Add a enum values of the leaf node hwGponDeviceOntRegisterInfoDownCause.
                         - Add a enum values of the leaf node hwEponDeviceOntRegisterInfoDownCause.
                         - Add a enum values of the leaf node hwGponDeviceOntControlLastDownCause.
                         - Add a enum values of the leaf node hwEponDeviceOntLastDownCause.
                         - Add a enum values of the leaf node hwXponDynamicMacQueryType.
                         - Add the leaf hwEponDeviceOltControlManualCheckRogueOnt in table HwEponDeviceOltControlInfoTable.
                         - Add the leaf hwGponDeviceOltControlManualCheckRogueOnt in table hwGponDeviceOltControlInfoTable.
                         - Modify the description of the leaf hwGponDeviceOntAlarmSDi in table hwGponDeviceOntAlarmStateInfoTable.
                         - Modify the description of the leaf hwGponDeviceOntAlarmSFi in table hwGponDeviceOntAlarmStateInfoTable.
                         - Modify the description of the leaf hwGponDeviceOntAlarmDOWi in table hwGponDeviceOntAlarmStateInfoTable.
                         - Modify the description of the leaf hwGponDeviceOntAlarmLOSi in table hwGponDeviceOntAlarmStateInfoTable.
                         - Modify the description of the leaf hwGponDeviceOntObjAlarmStateRDIi in table hwGponDeviceOntAlarmStateInfoTable.
                         - Modify the leaf hwXponDynamicMacVlanId from read-only to not-accessible.
                         - Modify the leaf hwXponDynamicMacIndex from read-only to not-accessible.
                         - Modify the leaf hwXponDynamicMacQueryType from read-only to not-accessible.
                         - Modify the leaf hwXponDynamicMacQueryPara0 from read-only to not-accessible.
                         - Modify the leaf hwXponDynamicMacQueryPara1 from read-only to not-accessible.
                         - Modify the leaf hwXponDynamicMacQueryPara2 from read-only to not-accessible.
                         - Modify the leaf hwXponDynamicMacQueryPara3 from read-only to not-accessible.
                         - Modify the description of hwGponDeviceOntControlLastDownCause.
                         - Modify the description of hwEponDeviceOntLastDownCause.
                         - Add a enum values of the leaf node hwGponDeviceOntRegisterInfoDownCause.
                         - Add a enum values of the leaf node hwEponDeviceOntRegisterInfoDownCause.
                         - Add leaf hwXponDeviceDbaProfileFixDelay in table hwXponDeviceDbaProfileInfoTable.
                         - Add leaf hwXponDeviceDbaProfileAdditionalBW in table hwXponDeviceDbaProfileInfoTable.
                         - Add leaf hwXponDeviceDbaProfilePriority in table hwXponDeviceDbaProfileInfoTable.
                         - Add leaf hwXponDeviceDbaProfileWeight in table hwXponDeviceDbaProfileInfoTable.
                         "

            REVISION     "201308270900Z"
            DESCRIPTION "V1.61, changes in this revision:
                         - Modify the value range of leaf hwXponDeviceLineProfEthPortBundleCfgGroupIndex in table hwXponDeviceLineProfEthPortBundleCfgTable.
                         - Add the leaf hwGponDeviceOntTDMPortOperateStatus in table hwGponDeviceOntTDMPortCfgTable.
                         - Add the leaf hwGponDeviceSrvProfOntPortCfgTDMPortTxClockMode in table hwGponDeviceSrvProfOntPortCfgTable.
                         - Add the leaf hwGponDeviceLineProfileTr069ManagementIpIndex in table hwGponDeviceLineProfileInfoTable.
                         - Add two enum values of the leaf node hwGponOltOpticsModuleInfoConnector.
                         - Add two enum values of the leaf node hwEponOltOpticsModuleInfoConnector.
                         - Modify the description of the leaf hwGponOltOpticsModuleInfoIdentifier in table hwGponOltOpticsModuleInfoTable.
                         - Modify the description of the leaf hwEponOltOpticsModuleInfoIdentifier in table hwEponOltOpticsModuleInfoTable.
                         - Modify the enum name from bySerialIDOnly to byTwowireOnly and the description of the leaf hwGponOltOpticsModuleInfoExtID in table hwGponOltOpticsModuleInfoTable.
                         - Modify the enum name from bySerialIDOnly to byTwowireOnly and the description of the leaf hwEponOltOpticsModuleInfoExtID in table hwEponOltOpticsModuleInfoTable.
                         - Add a enum values of the leaf node hwGponOltOpticsModuleInfoEncoding.
                         - Add a enum values of the leaf node hwEponOltOpticsModuleInfoEncoding.
                         - Modify the description of the leaf hwGponOltOpticsModuleInfoOptions in table hwGponOltOpticsModuleInfoTable.
                         - Modify the description of the leaf hwEponOltOpticsModuleInfoOptions in table hwEponOltOpticsModuleInfoTable.
                         - Modify the description of the leaf hwGponOltOpticsModuleInfoEnhancedOptions in table hwGponOltOpticsModuleInfoTable.
                         - Modify the description of the leaf hwEponOltOpticsModuleInfoEnhancedOptions in table hwEponOltOpticsModuleInfoTable.
                         - Modify the enum name from includesRev94SFF8472 to includesRev95SFF8472 and the description of the leaf hwGponOltOpticsModuleInfoSFF8472Compliance
                           in table hwGponOltOpticsModuleInfoTable.
                         - Modify the enum name from includesRev94SFF8472 to includesRev95SFF8472 and the description of the leaf hwEponOltOpticsModuleInfoSFF8472Compliance
                           in table hwEponOltOpticsModuleInfoTable.
                         - Add three enum values of the leaf node hwGponOltOpticsModuleInfoSFF8472Compliance.
                         - Add three enum values of the leaf node hwEponOltOpticsModuleInfoSFF8472Compliance.
                         - Rename hwGponDeviceSrvProfOntPortCfgEthPortPriorityPolicy to hwGponDeviceSrvProfOntPortCfgPortPriorityPolicy.
                         - Rename hwGponDeviceSrvProfOntPortCfgEthPortQinQMode to hwGponDeviceSrvProfOntPortCfgPortQinQMode.
                         - Add a enum values of the leaf node hwGponDeviceSrvProfOntPortCfgOntPhyType.
                         - Add a enum values of the leaf node hwGponDeviceLineProfMappingCfgOntPhyType.
                         - Add leaf hwGponDeviceOntCfgCapVdslPortNum in table hwGponDeviceOntCfgCapabilityTable.
                         - Add leaf hwGponDeviceSrvProfileVdslPortNum in table hwGponDeviceSrvProfileOntCfgTable.
                         - Add a value (4096) of the leaf node hwGponDeviceSrvProfileMulticastVlan.
                         - Add a enum values of the leaf node hwGponDeviceSrvProfPortVlanCfgOntPhyType.
                         - Add a table hwGponDeviceSrvProfileOntUpIgmpMsgCfgTable.
                         - Add a enum values of the leaf node hwXponOntUniPhyType.
                         - Add a enum values of the leaf node hwGponDeviceOntPortVlanPhyType.
                         - Add the leaf hwGponDeviceSrvProfOntPortCfgDownstreamMode in table hwGponDeviceSrvProfOntPortCfgTable.
                         - Add the leaf hwGponDeviceOntEthernetPortRingStatus in table HwGponDeviceOntEthernetPortCfgEntry.
                         - Add the leaf hwGponDeviceSrvProfileRingCheckSwitch,hwGponDeviceSrvProfileRingCheckAutoShutdownSwitch,hwGponDeviceSrvProfileRingCheckDetectingFrequency
                           and and hwGponDeviceSrvProfileRingCheckResumeInterval in table HwGponDeviceSrvProfileOntCfgEntry.
                         - Modify the leaf name from hwGponDeviceOntGemPortBindTrafficTblId to hwGponDeviceOntGemPortBindTrafficTableId in table hwGponDeviceOntGemPortBindTable.
                         - Add the leaf hwGponDeviceOntGemPortBindTrafficTableName in table hwGponDeviceOntGemPortBindTable.
                         - Modify the leaf name from hwGponDeviceOntEthernetUpStreamCarProfile to hwGponDeviceOntEthernetUpStreamCarTrafficTableId in table hwGponDeviceOntEthernetPortCfgTable
                         - Add the leaf hwGponDeviceOntEthernetUpStreamCarTrafficTableName in table hwGponDeviceOntEthernetPortCfgTable.
                         - Modify the leaf name from hwGponDeviceOntEthernetDownStreamCarProfile to hwGponDeviceOntEthernetDownStreamCarTrafficTableId in table hwGponDeviceOntEthernetPortCfgTable
                         - Add the leaf hwGponDeviceOntEthernetDownStreamCarTrafficTableName in table hwGponDeviceOntEthernetPortCfgTable.
                         - Modify the leaf name from hwGponDeviceLineProfMappingCfgCarProfileIndex to hwGponDeviceLineProfMappingCfgCarTrafficTableId in table hwGponDeviceLineProfMappingCfgTable.
                         - Add the leaf hwGponDeviceLineProfMappingCfgCarTrafficTableName in table hwGponDeviceLineProfMappingCfgTable.
                         - Modify the leaf name from hwGponDeviceLineProfGemCfgCarProfileIndex to hwGponDeviceLineProfGemCfgCarTrafficTableId in table hwGponDeviceLineProfGemCfgTable.
                         - Add the leaf hwGponDeviceLineProfGemCfgCarTrafficTableName in table hwGponDeviceLineProfGemCfgTable.
                         - Modify the leaf name from hwGponDeviceSrvProfOntPortCfgUpStreamCarProfile to hwGponDeviceSrvProfOntPortCfgUpStreamCarTrafficTableId in table hwGponDeviceSrvProfOntPortCfgTable.
                         - Add the leaf hwGponDeviceSrvProfOntPortCfgUpStreamCarTrafficTableName in table hwGponDeviceSrvProfOntPortCfgTable.
                         - Modify the leaf name from hwGponDeviceSrvProfOntPortCfgDownStreamCarProfile to hwGponDeviceSrvProfOntPortCfgDownStreamCarTrafficTableId in table hwGponDeviceSrvProfOntPortCfgTable.
                         - Add the leaf hwGponDeviceSrvProfOntPortCfgDownStreamCarTrafficTableName in table hwGponDeviceSrvProfOntPortCfgTable.
                         - Modify the leaf name from hwEponDeviceOntLlidCarProfileIndex to hwEponDeviceOntLlidCarTrafficTableId in table hwEponDeviceOntLlidTable.
                         - Add the leaf hwEponDeviceOntLlidCarTrafficTableName in table hwEponDeviceOntLlidTable.
                         - Modify the leaf name from hwEponLineProfLlidCfgCarProfileIndex to hwEponLineProfLlidCfgCarTrafficTableId in table hwEponDeviceLineProfLlidCfgTable.
                         - Add the leaf hwEponLineProfLlidCfgCarTrafficTableName in table hwEponDeviceLineProfLlidCfgTable.
                         - Modify the leaf name from hwEponDeviceSrvProfOntPortCfgUpStreamCarProfile to hwEponDeviceSrvProfOntPortCfgUpStreamCarTrafficTableId in table hwEponDeviceSrvProfOntPortCfgTable.
                         - Add the leaf hwEponDeviceSrvProfOntPortCfgUpStreamCarTrafficTableName in table hwEponDeviceSrvProfOntPortCfgTable.
                         - Modify the leaf name from hwEponDeviceSrvProfOntPortCfgDownStreamCarProfile to hwEponDeviceSrvProfOntPortCfgDownStreamCarTrafficTableId in table hwEponDeviceSrvProfOntPortCfgTable.
                         - Add the leaf hwEponDeviceSrvProfOntPortCfgDownStreamCarTrafficTableName in table hwEponDeviceSrvProfOntPortCfgTable.
                         - Modify the leaf name from hwEponDeviceOntEthernetPortCfgUpStreamCarProfile to hwEponDeviceOntEthernetPortCfgUpStreamCarTrafficTableId in table hwEponDeviceOntLlidTable.
                         - Add the leaf hwEponDeviceOntEthernetPortCfgUpStreamCarTrafficTableName in table hwEponDeviceOntLlidTable.
                         - Modify the leaf name from hwEponDeviceOntEthernetPortCfgDownStreamCarProfile to hwEponDeviceOntEthernetPortCfgDownStreamCarTrafficTableId in table hwEponDeviceOntLlidTable.
                         - Add the leaf hwEponDeviceOntEthernetPortCfgDownStreamCarTrafficTableName in table hwEponDeviceOntLlidTable.
                         - modify the description of hwGponDeviceOntControlLastDownCause.
                         - modify the description of hwEponDeviceOntLastDownCause.
                         "

            REVISION     "201301070900Z"
            DESCRIPTION "V1.60, changes in this revision:
                         - Add a table of hwGponDeviceLineProfMulticastGemCfgTable.
                         - Add the leaf hwGponDeviceOntCatvFrequency in table hwGponDeviceOntCatvPortCfgTable.
                         - Add a enum values of the leaf node hwGponDeviceOntManagementMode.
                         - Add leaves hwGponOntTrafficFlowStatisticUpFcsErrorCnt, hwGponOntTrafficFlowStatisticUpFrameBitErrorRatio,
                           hwGponOntTrafficFlowStatisticUpEthFrameErrorRatio, hwGponOntTrafficFlowStatisticUpGemFrameErrorRatio
                           in table hwGponOntTrafficFlowStatisticTable.
                         "

            REVISION     "201212040900Z"
            DESCRIPTION "V1.59, changes in this revision:
                         - Add the leaf hwGponDeviceOltControlEnergySavingFlag in table hwGponDeviceOltControlInfoTable.
                         - Add the leaf hwEponDeviceOltControlEnergySavingFlag in table hwEponDeviceOltControlInfoTable.
                         "
            REVISION     "201211160900Z"
            DESCRIPTION "V1.58, changes in this revision:
                         - Add a enum values of the leaf node hwGponDeviceLineProfMappingCfgOntPhyType.
                         "

            REVISION     "201209071905Z"
            DESCRIPTION "V1.57, changes in this revision:
                        - Modify the value range of leaf hwGponDeviceOntControlLastDownCause in table hwGponDeviceOntControlInfoTable.
                         "

            REVISION     "201208280900Z"
            DESCRIPTION "V1.56, changes in this revision:
                         - Modify leaf hwEponDeviceAutoFindOntRateType name to hwEponDeviceAutoFindOntNniType in table hwEponDeviceAutoFindOntInfoTable.
                         "

            REVISION     "201207040900Z"
            DESCRIPTION "V1.55, changes in this revision:
                         - Add leaf hwEponDeviceOntExtendedFirmwareVersion in table hwEponDeviceOntVersionInfoTable.
                         "

            REVISION     "201206280900Z"
            DESCRIPTION "V1.54, changes in this revision:
                         - Modify the definition of the leaf hwXponDeviceOntSnmpProfileVersion in table hwXponDeviceOntSnmpProfileInfoTable.
                         - Modify the description of the leaf hwXponDeviceOntSnmpProfileVersion in table hwXponDeviceOntSnmpProfileInfoTable.
                        "

            REVISION     "201206150900Z"
            DESCRIPTION "V1.53, changes in this revision:
                         - Add leaf hwGponDeviceOntGemPortBindDownPQIndex in table hwGponDeviceOntGemPortBindTable.
                         - Modify leaf hwGponDeviceOntGemPortBindPQIndex name to hwGponDeviceOntGemPortBindUpPQIndex in table hwGponDeviceOntGemPortBindTable.
                         - Add the table of hwEponOltChannelEthernetStatisticTable for the OLT channel ETH statisitcs.
                         - Add the leaf hwEponOntOpticalDdmOltTxPower in table hwEponDeviceOntOpticsDdmInfoTable.
                         - Modify leaf hwEponDeviceOntOpticsDdmOltRxOntOpticPower name to hwEponOntOpticalDdmOltRxOntPower.
                         - Add leafs hwXponDeviceOpticsDdmAlarmProfile10GTxOpticAlarmUpper, hwXponDeviceOpticsDdmAlarmProfile10GTxOpticAlarmLower,
                           hwXponDeviceOpticsDdmAlarmProfile10GTxOpticWarnUpper, hwXponDeviceOpticsDdmAlarmProfile10GTxOpticWarnLower,
                           hwXponDeviceOpticsDdmAlarmProfile10GBiasCurrentAlarmUpper, hwXponDeviceOpticsDdmAlarmProfile10GBiasCurrentAlarmLower,
                           hwXponDeviceOpticsDdmAlarmProfile10GBiasCurrentWarnUpper, hwXponDeviceOpticsDdmAlarmProfile10GBiasCurrentWarnLower in table hwXponDeviceOpticsDdmAlarmProfileInfoTable.
                         - Add leaf hwEponDeviceOntActualNniType and hwEponDeviceOntLastActualNniType in hwEponDeviceOltControlInfoTable.
                         - Change the leaf hwEponDeviceOntRateType names to hwEponDeviceOntNniType.
                         - Modify the enum values of the leaf node hwEponDeviceOntNniType.
                         - Delete the leaf node hwGponDeviceLineProfileVoipCfgMethod in table hwGponDeviceLineProfileInfoTable, the leaf node hwGponDeviceLineProfileVoipCfgMethod has never been used.
                         - Add table hwGponDeviceOntPortVlanTable for GPON ONT's distributed port vlan configuration.
                        "

            REVISION     "201206010900Z"
            DESCRIPTION "V1.52, changes in this revision:
                         - Add the leaf hwXponOntLoadXmlAES128Key in table hwXponOntLoadCtrlTable.
                         "

            REVISION     "201204200900Z"
            DESCRIPTION "V1.51, changes in this revision:
                         - Modify the leaf hwGponDeviceLineProfGemCfgDownPQIndex in table hwGponDeviceLineProfGemCfgTable.
                         "

            REVISION     "201201190900Z"
            DESCRIPTION "V1.50, changes in this revision:
                        - Modify the value range of leaf hwXponOntLoadSelectActiveMode in table hwXponOntLoadSelectTable.
                        - Modify the value range of leaf hwXponOntLoadImageActiveMode in table hwXponOntLoadCtrlTable.
                        - Modify the leaf hwEponDeviceAlarmProfileRxCRCerrorThreshold ,
                          hwEponDeviceAlarmProfileRxCRCerrorRestoreThreshold to hwEponDeviceAlarmProfileRxCRCErrorFramesThreshold and
                          hwEponDeviceAlarmProfileRxCRCErrorFramesRestoreThreshold
                        - Add leafs hwEponDeviceRegOntPasswordValue, hwEponDeviceRegOntVendorId, hwEponDeviceRegOntSoftwareVersion,
                          hwEponDeviceRegOntHardwareVersion, hwEponDeviceRegOntModel, hwEponDeviceRegOntLoid,
                          hwEponDeviceRegOntCheckcode, hwEponDeviceRegOntRateType,hwEponDeviceRegOntExtendedModel,
                          hwEponDeviceRegOntOuiVersion in table hwEponDeviceOntRegInfoTable.
                        - Modify the leaf hwEponDeviceOntCfgCapIPSupport and hwGponDeviceOntCfgCapIPSupport.
                        "

            REVISION     "201112280900Z"
            DESCRIPTION "V1.49, changes in this revision:
                        - Add leaf hwGponDeviceSrvProfileUpPqColorPolicy and hwGponDeviceSrvProfileDownPqColorPolicy in table hwGponDeviceSrvProfileOntCfgTable.
                        - Modify the value range of leaf hwGponDeviceLineProfMappingCfgVlanId in table hwGponDeviceLineProfMappingCfgTable.
                        - Add leaf hwEponDeviceOltControlAlarmProfileName in table hwEponDeviceOltControlInfoTable.
                        - Add leaf hwEponDeviceOltControlWarningProfileName in table hwEponDeviceOltControlInfoTable.
                        - Add leaf hwEponDeviceOntExtCfgAlarmProfileName in table hwEponDeviceOntExtendConfigTable.
                        - Add leaf hwEponDeviceOntExtCfgWarningProfileName in table hwEponDeviceOntExtendConfigTable.
                        - Add leaf hwGponTDMPortStatisticClear in table hwGponTDMPortStatisticTable.
                        - Add leaf hwGponDeviceLineProfGemCfgDownPQIndex in table hwGponDeviceOntPortidControlTable.
                        - Modify the definition of the leaf hwGponDeviceLineProfGemCfgUpPQIndex in table hwGponDeviceOntPortidControlTable
                        - Modify the description of the leaf hwGponDeviceLineProfGemCfgUpPQIndex in table hwGponDeviceOntPortidControlTable
                        - Add table hwEponDeviceAlarmProfileInfoTable.
                        - Add leaf hwXponOntLoadSelectPriority and hwXponOntLoadSelectActiveMode in table hwXponOntLoadSelectTable.
                        - Add leaf hwEponDeviceAutoFindOntInfoOntExtendedModel in table hwEponDeviceAutoFindOntInfoTable.
                        - Add leaf hwEponDeviceAutoFindOntInfoOuiVersion in table hwEponDeviceAutoFindOntInfoTable.
                        - Add leaf hwEponOltEthernetStatisticRcvErrorFrames in table hwEponOltEthernetStatisticTable.
                        - Add leaf hwEponOltEthernetStatisticRcvFragments in table hwEponOltEthernetStatisticTable.
                        - Add leaf hwEponOltEthernetStatisticRcvJabbers in table hwEponOltEthernetStatisticTable.
                        - Add leaf hwEponOltEthernetStatisticRcvDropEvents in table hwEponOltEthernetStatisticTable.
                        - Add leaf hwEponOltEthernetStatisticSendDropEvents in table hwEponOltEthernetStatisticTable.
                        - Add leaf hwEponOltEthernetStatisticSendDiscardFrames in table hwEponOltEthernetStatisticTable.
                        - Add leaf hwEponOltEthernetStatisticSendErrorFrames in table hwEponOltEthernetStatisticTable.
                        - Add leaf hwEponOltEthernetStatisticSendCrcErrorFrames in table hwEponOltEthernetStatisticTable.
                        - Add leaf hwEponOltEthernetStatisticSendUndersizeFrames in table hwEponOltEthernetStatisticTable.
                        - Add leaf hwEponOltEthernetStatisticSendOversizeFrames in table hwEponOltEthernetStatisticTable.
                        - Add leaf hwEponOltEthernetStatisticSendFragments in table hwEponOltEthernetStatisticTable.
                        - Add leaf hwEponOltEthernetStatisticSendJabbers in table hwEponOltEthernetStatisticTable.
                        - Add leaf hwEponOltLlidStatisticRecvCrcErrorFrames in table hwEponOltLlidStatisticTable.
                        - Add leaf hwEponOltLlidStatisticRecvFragments in table hwEponOltLlidStatisticTable.
                        - Add leaf hwEponOltLlidStatisticRecvJabbers in table hwEponOltLlidStatisticTable.
                        - Add leaf hwEponOltLlidStatisticRecvDiscardFrames in table hwEponOltLlidStatisticTable.
                        - Add leaf hwEponOltLlidStatisticRecvDropEvents in table hwEponOltLlidStatisticTable.
                        - Add leaf hwEponOltLlidStatisticTransDropEvents in table hwEponOltLlidStatisticTable.
                        - Add leaf hwEponOltLlidStatisticTransDiscardFrames in table hwEponOltLlidStatisticTable.
                        - Add leaf hwEponOltLlidStatisticTransErrorFrames in table hwEponOltLlidStatisticTable.
                        - Add leaf hwEponOltLlidStatisticTransCrcErrorFrames in table hwEponOltLlidStatisticTable.
                        - Add leaf hwEponOltLlidStatisticTransUndersizeFrames in table hwEponOltLlidStatisticTable.
                        - Add leaf hwEponOltLlidStatisticTransOversizeFrames in table hwEponOltLlidStatisticTable.
                        - Add leaf hwEponOltLlidStatisticTransFragments in table hwEponOltLlidStatisticTable.
                        - Add leaf hwEponOltLlidStatisticTransJabbers in table hwEponOltLlidStatisticTable.
                        - Add leaf hwEponOntEthernetPortStatisticRecvUnicastFrames in the table hwEponOntEthernetPortStatisticTable.
                        - Add leaf hwEponOntEthernetPortStatisticRecvOver in the table hwEponOntEthernetPortStatisticTable.
                        - Add leaf hwEponOntEthernetPortStatisticRecvErrorFrames in the table hwEponOntEthernetPortStatisticTable.
                        - Add leaf hwEponOntEthernetPortStatisticRecvCrcErrorFrames in the table hwEponOntEthernetPortStatisticTable.
                        - Add leaf hwEponOntEthernetPortStatisticRecvDropEvents in the table hwEponOntEthernetPortStatisticTable.
                        - Add leaf hwEponOntEthernetPortStatisticTransDropEvents in the table hwEponOntEthernetPortStatisticTable.
                        - Add leaf hwEponOntEthernetPortStatisticTransDiscardFrames in the table hwEponOntEthernetPortStatisticTable.
                        - Add leaf hwEponOntEthernetPortStatisticTransErrorFrames in the table hwEponOntEthernetPortStatisticTable.
                        - Add leaf hwEponOntEthernetPortStatisticTransCrcErrorFrames in the table hwEponOntEthernetPortStatisticTable.
                        - Add leaf hwEponOntEthernetPortStatisticTransUndersizeFrames in the table hwEponOntEthernetPortStatisticTable.
                        - Add leaf hwEponOntEthernetPortStatisticTransOversizeFrames in the table hwEponOntEthernetPortStatisticTable.
                        - Add leaf hwEponOntEthernetPortStatisticTransFragments in the table hwEponOntEthernetPortStatisticTable.
                        - Add leaf hwEponOntEthernetPortStatisticTransJabbers in the table hwEponOntEthernetPortStatisticTable.
                        - Add leaf hwEponOntEthernetPortStatisticTrans64OctetFrames in the table hwEponOntEthernetPortStatisticTable.
                        - Add leaf hwEponOntEthernetPortStatisticTrans65to127OctetFrames in the table hwEponOntEthernetPortStatisticTable.
                        - Add leaf hwEponOntEthernetPortStatisticTrans128to255OctetFrames in the table hwEponOntEthernetPortStatisticTable.
                        - Add leaf hwEponOntEthernetPortStatisticTrans256to511OctetFrames in the table hwEponOntEthernetPortStatisticTable.
                        - Add leaf hwEponOntEthernetPortStatisticTrans512to1023OctetFrames in the table hwEponOntEthernetPortStatisticTable.
                        - Add leaf hwEponOntEthernetPortStatisticTrans1024to1518OctetFrames in the table hwEponOntEthernetPortStatisticTable.
                        - Add leaf hwEponOntEthernetPortStatisticTransOver1518OctetFrames in the table hwEponOntEthernetPortStatisticTable.
                        - Add leaf hwXponOntLoadSelectPriority and hwXponOntLoadSelectActiveMode in table hwXponOntLoadSelectTable.
                        - Add leafs hwGponDeviceOntRegisterOntPassword, hwGponDeviceOntRegisterOntVendorId, hwGponDeviceOntRegisterOntVersion,
                          hwGponDeviceOntRegisterOntMainSoftVersion, hwGponDeviceOntRegisterOntEquipmentId, hwGponDeviceOntRegisterOntLoid,
                          hwGponDeviceOntRegisterOntCheckcode in table hwGponDeviceOntRegisterInfoTable.
                        - Add leaf hwEponDeviceSrvProfileRingCheckAutoShutdownSwitch in table hwEponDeviceSrvProfileOntCfgTable.
                        - Add leaf hwEponDeviceOntSupportIPv6Aware in table hwEponDeviceOntCapabilityInfoTable.
                        - Add leaf hwEponDeviceOntSupportPowerSupplyControl in table hwEponDeviceOntCapabilityInfoTablel
                        - Add leaf hwEponDeviceOntSupportServiceSLA in table hwEponDeviceOntCapabilityInfoTable.
                        - Add leaf hwEponDeviceOntExtendedModel in table hwEponDeviceOntVersionInfoTable.
                        - Add leaf hwEponDeviceOntOuiVersion in table hwEponDeviceOntVersionInfoTable.
                        - Modify the length of the leaf node hwXponDeviceOntPortClassTable value.
                        - Modify the description of leaf hwXponDeviceOntPortClassProfileFieldselect.
                        "

            REVISION     "201112051050Z"
            DESCRIPTION "V1.48, changes in this revision:
                        - Modify the type and description of leaf hwGponDeviceSrvProfPortVlanCfgEtherType.
                        - Modify the description of leaf hwGponDeviceOltControlNearest.
                        - Modify the description of leaf hwGponDeviceOltControlFarthest.
                        - Add leaf hwGponOntTrafficFlowStatisticUpFecCodeDecodCorrectCnt in table hwGponOntTrafficFlowStatisticTable.
                        - Add leaf hwGponOntTrafficFlowStatisticUpFecCodeCnt in table hwGponOntTrafficFlowStatisticTable.
                        - Add leaf hwGponOntGemIndexStatisticTransmittedGemFrames in table hwGponOntGemIndexStatisticTable.
                        - Add leaf hwGponDeviceLineProfileCommitResult in table hwGponDeviceLineProfileInfoTable.
                        - Add the enum values of the leaf node hwGponDeviceLineProfileCommit.
                        - Modified description of the hwGponOntStatisticTable.
                        - Modify the definition of the leaf hwGponDeviceOltControlDnFecEnabled in table hwGponDeviceOltControlInfoTable.
                        - Add leafs hwGponDeviceAlarmProfileUpstreamPQDiscardedBytesThreshold and hwGponDeviceAlarmProfileDownstreamPQDiscardedBytesThreshold in table hwGponDeviceAlarmProfileInfoTable.
                        "

            REVISION     "201110060900Z"
            DESCRIPTION "V1.47, changes in this revision:
                        - Modify the word hybirdpon to hybridpon.
                        - Modify the word Vender to Vendor.
                        "

            REVISION     "201109060900Z"
            DESCRIPTION "V1.46, changes in this revision:
                        - Modify the spelling mistake of the word --porfile.
                        "

            REVISION     "201108090900Z"
            DESCRIPTION "V1.45, changes in this revision:
                        - Modify the definition of the leaf node hwGponDeviceOntRegisterResult.
                        - Modify the definition of the leaf node hwEponDeviceRegOntResult.
                        "

            REVISION     "201107200900Z"
            DESCRIPTION "V1.44, changes in this revision:
                        - Add leaf hwGponOntEthernetStatisticRecvPkts1519toOversizeOctets in table hwGponOntEthernetStatisticTable.
                        - Add leaf hwEponOntEthernetPortStatisticRecv1519toOversizeOctetFrames in table hwEponOntEthernetPortStatisticTable.
                        - Add leaf hwGponDeviceOntRegisterConflictedIfindex in table hwGponDeviceOntRegisterInfoTable.
                        - Add leaf hwGponDeviceOntRegisterConflictedOntIndex in table hwGponDeviceOntRegisterInfoTable.
                        - Modify the definition of the leaf node hwGponDeviceOntRegisterResult.
                        - Add leaf hwEponDeviceRegConflictedIfindex in table hwEponDeviceOntRegInfoTable.
                        - Add leaf hwEponDeviceRegConflictedOntIndex in table hwEponDeviceOntRegInfoTable.
                        - Modify the definition of the leaf node hwEponDeviceRegOntResult.
                        - Modify the description of the leaf node hwGponDeviceOntCfgCapEthNum in table hwGponDeviceOntCfgCapabilityTable.
                        - Modify the description of the leaf node hwGponDeviceOntCfgCapPotsNum in table hwGponDeviceOntCfgCapabilityTable.
                        - Modify the description of the leaf node hwGponDeviceOntCfgCapCatvUniNum in table hwGponDeviceOntCfgCapabilityTable.
                        - Modify the description of the leaf node hwEponDeviceOntCfgCapPotsNum in table hwEponDeviceOntCfgCapabilityTable.
                        - Modify the description of the leaf node hwEponDeviceOntCfgCapEthNum in table hwEponDeviceOntCfgCapabilityTable.
                        "

            REVISION     "201106230900Z"
            DESCRIPTION "V1.43, changes in this revision:
                        - Add leaf hwGponDeviceSrvProfOntPortCfgMaxMacAddressNum in table hwGponDeviceSrvProfOntPortCfgTable.
                        - Add leaf hwGponOntEthernetStatisticSendOctets in table hwGponOntEthernetStatisticTable for indicates the sent Octets.
                        - Add leaf hwGponOntEthernetStatisticForwardDropEvents in table hwGponOntEthernetStatisticTable for indicates the sent DropEvents.
                        - Add leaf hwGponOntEthernetStatisticSendPkts64Octets in table hwGponOntEthernetStatisticTable for indicates the sent 65~127-octet frames.
                        - Add leaf hwGponOntEthernetStatisticSendPkts65to127Octets in table hwGponOntEthernetStatisticTable for indicates the sent 65~127-octet frames .
                        - Add leaf hwGponOntEthernetStatisticSendPkts128to255Octets  in table hwGponOntEthernetStatisticTable for indicates the sent 128~255-octet frames.
                        - Add leaf hwGponOntEthernetStatisticSendPkts256to511Octets in table hwGponOntEthernetStatisticTable for indicates the sent 256~511-octet frames.
                        - Add leaf hwGponOntEthernetStatisticSendPkts512to1023Octets in table hwGponOntEthernetStatisticTable for indicates the sent 512~1023-octet frames.
                        - Add leaf hwGponOntEthernetStatisticSendPkts1024to1518Octets in table hwGponOntEthernetStatisticTable for indicates the sent 1024~1518-octet frames.
                        - Add leaf hwGponOntEthernetStatisticSendPktsOversize in table hwGponOntEthernetStatisticTable for indicates the sent oversize frames.
                        - Modify the description of the leaf node hwEponDeviceSrvProfilePotsNum in table hwEponDeviceSrvProfileOntCfgTable.
                        - Modify the description of the leaf node hwEponDeviceSrvProfileEthNum in table hwEponDeviceSrvProfileOntCfgTable.
                        - Modify the description of the leaf node hwGponDeviceSrvProfilePotsNum in table hwGponDeviceSrvProfileOntCfgTable.
                        - Modify the description of the leaf node hwGponDeviceSrvProfileEthNum in table hwGponDeviceSrvProfileOntCfgTable.
                        - Modify the description of the leaf node hwGponDeviceSrvProfileCatvNum in table hwGponDeviceSrvProfileOntCfgTable.
                        - Modify the value range of the leaf node hwGponDeviceLineProfMappingCfgOntPhyIndex in table hwGponDeviceLineProfMappingCfgTable.
                        - Move all TRAP objects from HUAWEI-XPON-MIB.mib to HUAWEI-XPON-TRAP-MIB.mib.
                        - Add leaf hwGponOntTrafficFlowStatisticDowiAlarmCnt in table hwGponOntTrafficFlowStatisticTable.
                        "

            REVISION     "201105050900Z"
            DESCRIPTION  "V1.42, changes in this revision:
                         - Add invalid value for the leaf hwXponDynamicMacVlanId in table hwXponDynamicMacQueryTable.
                         - Add leaf hwGponDeviceLineProfileVoipCfgMethod int hwGponDeviceLineProfileInfoTable for ont service config mode.
                         - Modify the description of leaf hwXponOntLoadCrcValue.
                         - Delete trap hwGponProfOntVersionTrap.
                         - Delete trap hwEponProfOntUpVersionTrap.
                         - Modify the description of leaf hwEponDeviceOntFECSupport.
                         - Modify the description of leaf hwGponDeviceOntAuthMethod.
                         - Modify the enum values of the leaf node hwXponDynamicMacQueryType.
                         - Modify the definition of the leaf node hwXponDynamicMacAddr.
                         - Modify the name of the leaf node hwGponProfOntHardwareFaultyAlarmTrap(new name:hwXponProfOntHardwareFaultyAlarmTrap).
                         - Modify the name of the leaf node hwGponProfOntHardwareFaultRecoverAlarmTrap(new name:hwXponProfOntHardwareFaultRecoverAlarmTrap).
                         - Modify the name of the leaf node hwGponProfOntStandbyBatteryLostAlarmTrap(new name:hwXponProfOntStandbyBatteryLostAlarmTrap).
                         - Modify the name of the leaf node hwGponProfOntLossOfStandbyBatteryRecoverAlarmTrap(new name:hwXponProfOntLossOfStandbyBatteryRecoverAlarmTrap).
                         - Modify the name of the leaf node hwGponProfOntStandbyBatteryCannotChargedAlarmTrap(new name:hwXponProfOntStandbyBatteryCannotChargedAlarmTrap).
                         - Modify the name of the leaf node hwGponProfOntStandbyBatteryRecoverAlarmTrap(new name:hwXponProfOntStandbyBatteryRecoverAlarmTrap).
                         - Modify the name of the leaf node hwGponProfOntVoltageOfStandbyBatteryTooLowAlarmTrap(new name:hwXponProfOntVoltageOfStandbyBatteryTooLowAlarmTrap).
                         - Modify the name of the leaf node hwGponProfOntVoltageOfStandbyBatteryRecoverAlarmTrap(new name:hwXponProfOntVoltageOfStandbyBatteryRecoverAlarmTrap).
                         - Modify the name of the leaf node hwGponProfPortHasRogueOntsAlarmTrap(new name:hwXponProfPortHasRogueOntsAlarmTrap).
                         - Modify the name of the leaf node hwGponProfPortNotHaveRogueOntsAlarmTrap(new name:hwXponProfPortNotHaveRogueOntsAlarmTrap).
                         - Modify the name of the leaf node hwGponProfOntIsRogueOntAlarmTrap(new name:hwXponProfOntIsRogueOntAlarmTrap).
                         - Modify the name of the leaf node hwGponProfRogueOntDisapearAlarmTrap(new name:hwXponProfRogueOntDisapearAlarmTrap).
                         - modify the description of the leaf node hwEponOltXFPOpticsModuleInfoSupportXFIMode.
                         - modify the type of the leaf node hwEponOltXFPOpticsModuleInfoEnhancedOptions.
                         - Add leaf hwGponDeviceAlarmProfileFECCorrectCodeWordsThreshold in table hwGponDeviceAlarmProfileInfoTable.
                         - Modify the type of hwGponDeviceAlarmProfileFECUncorrectCodeWordsThreshold from Integer32 to Gauge32.
                         - Modify the name of the leaf node hwGponProfNumerousOntsPowerOffAlarmTrap(new name:hwXponNumerousOntsPowerOffAlarmTrap).
                         - Modify the name of the leaf node hwGponProfOntMask(new name:hwXponOntMask).
                         - Modify the description of the leaf node hwEponOltXFPOpticsModuleInfoEnhancedOptions.
                         - Modify the description of the leaf node hwEponOltXFPOpticsModuleXponTemperatureLevel.
                         - Modify the length of the leaf node hwEponDeviceAutoFindOntInfoHardwareVersion.
                         - Modify the enum values of the leaf node hwEponDeviceOntRegisterInfoDownCause.
                         - Modify the enum values of the leaf node hwGponDeviceOntRegisterInfoDownCause.
                         - Modify the enum values of the leaf node hwGponDeviceOntIpConfigVlan.
                         - Modify the enum values of the leaf node hwGponDeviceOntIpconfigDscpDefaultPriority.
                         - Modify the description of leaf hwGponProfOntAuthInfoConflictAlarmTrap.
                         - Modify the definition of the leaf node hwGponDeviceSrvProfOntPortCfgEthPortQinQMode.
                         - Modify the definition of the leaf node hwGponDeviceSrvProfOntPortCfgEthPortPriorityPolicy.
                         - Add a table hwEponOltXFPOpticsModuleInfoTable.
                         - Add trap hwXponProfOntPortLearnedHGInfoTrap to report the VLAN and MAC address
                           of the home gateway that are learned on the ONT port.
                         - Add parameters hwXponProfOntPortLearnedHGVlan and hwXponProfOntPortLearnedHGMacAddr.
                         - Modify the type of hwEponDeviceOntMultiLLID to support multiple LLIDs
                         - Modify the enum values and definition of the leaf node hwGponDeviceOntRegisterInfoDownCause and hwEponDeviceOntRegisterInfoDownCause.
                         - Modify the definition of the leaf node hwGponDeviceOntControlLastDownCause and hwEponDeviceOntLastDownCause.
                         - Modify the type and description of leaf hwGponDeviceSrvProfPortVlanCfgEtherType.
                         "

            REVISION     "201101280900Z"
            DESCRIPTION  "V1.41, changes in this revision:
                         - Modify the enum values of the node of hwGponDeviceOntEthernetDuplexMode, hwGponDeviceOntEthernetSpeed,
                           hwEponDeviceOntEthernetDuplexMode and hwEponDeviceOntEthernetSpeed.
                         - Add the node of hwEponOntEthernetPortStatisticTransUnicastFrames
                           hwEponOntEthernetPortStatisticTransBroadcastFrames
                           and hwEponOntEthernetPortStatisticTransMulticastFrames
                           in table hwEponOntEthernetPortStatisticTable.
                         "

            REVISION     "201101180900Z"
            DESCRIPTION  "V1.40, changes in this revision:
                         - Modify the description of leaf hwEponDeviceOltControlfarthest, hwXponDeviceOntIndex and hwXponOntLoadOperType,
                         - Change the OID names of hwXponProfLocalOpticalModuleExeedAlramThresAlarmTrap,
                           hwXponProfRemoteOpticalModuleExeedAlarmThresAlarmTrap,
                           hwXponProfLocalOpticalModuleExeedWarnThresAlarmTrap,
                           and hwXponProfRemoteOpticalModuleExeedWarnThresAlarmTrap.
                         - Delete the default value of the following leaves:
                           hwGponDeviceOntControlReRegister, hwGponDeviceOntControlReDiscovery,
                           hwEponDeviceOntReset, hwEponDeviceOntReRegister,
                           hwGponGemOntLoopbackType, hwXponOntUniLoopbackType, hwEponDeviceOntReDiscovery.
                         - Change the OID names of hwXponProfLocalOpticalModuleExeedAlramThresAlarmTrap,
                           hwXponProfRemoteOpticalModuleExeedAlarmThresAlarmTrap,
                           hwXponProfLocalOpticalModuleExeedWarnThresAlarmTrap,
                           and hwXponProfRemoteOpticalModuleExeedWarnThresAlarmTrap.
                         - Add leaf node hwEponDeviceOntRateType in table hwEponDeviceOntConfigInfoTable
                           to obtain the ONT rate type
                         - Add leaf node hwEponDeviceAutoFindOntRateType in table hwEponDeviceAutoFindOntInfoTable
                           to obtain the ONT rate type
                         - Modify the description of leaf hwXponDeviceOntIndex,hwEponDeviceOntIndex,hwEponDeviceAutoFindOntInfoOntIndex and hwXponDynamicMacQueryPara0.
                         - Modify the range of leaf hwXponOntLoadXmlOntObjectIndex, hwXponDeviceDbaProfileFixedRate.
                           hwXponDeviceDbaProfileAssuredRate, hwXponDeviceDbaProfileMaxRate.
                         - Add leaf hwGponDeviceAlarmProfileFECUncorrectCodeWordsThreshold in table hwGponDeviceAlarmProfileInfoTable.
                         - Add the node of hwEponDeviceOltLeftBandWidth10GUpstream and hwEponDeviceOltAvailableBandWidth10GUpstream.
                         - Modify the description of leaf hwEponDeviceOltControlLeftBandWidth and hwEponDeviceOltControlAvailableBandWidth.
                         - Add leaf hwGponDeviceOntEthernetPortIgmpForwardMode in hwGponDeviceOntEthernetPortCfgTable for ONT port IGMP forward mode switch.
                         - Add leaf hwGponDeviceSrvProfOntPortCfgUpIgmpTransmitMode in hwGponDeviceSrvProfOntPortCfgTable for setting the upstream igmp packets transmit mode profile of GPON ONT port.
                         - Add leaf hwGponDeviceSrvProfOntPortCfgUpIgmpMsgTranslationVlan in hwGponDeviceSrvProfOntPortCfgTable for the translation VLAN profile of GPON ONT port,when the upstream igmp transmit mode profile is translation or default in the GPON ONT port.
                         - Add leaf hwGponDeviceSrvProfOntPortCfgUpIgmpMsgPriority in hwGponDeviceSrvProfOntPortCfgTable for setting the priority of upstream igmp packets.
                        "

            REVISION     "201012130900Z"
            DESCRIPTION  "V1.39, changes in this revision:
                         - Add the node of hwGponDeviceOntInfoAuthEffectMode and hwEponDeviceOntAuthEffectMode
                           to set the effect taking mode.
                        "

            REVISION     "201011250900Z"
            DESCRIPTION  "V1.38, changes in this revision:
                         - Modify the description of the node hwXponOntUniLineTestSrvFlowIndex.
                         - Modify the description of the following leaves:
                           hwXponDeviceDbaProfileType
                           hwXponDeviceOntSnmpProfileVersion
                           hwXponOntLoadCrcValue.
                        "

            REVISION     "201011030900Z"
            DESCRIPTION  "V1.37, changes in this revision:
                         - Modify the node of hwGponDeviceOntAuthMethod.
                         - Add the node of hwGponDeviceOntLoid, hwGponDeviceOntCheckcode
                           to support the LOID and checkcode authentication modes of the ONT.
                         - Add hwEponDeviceOntSoftwareWorkMode and hwGponDeviceOntSoftwareWorkMode.
                         - Add leaf nodes hwGponDeviceAutoFindOntInfoLoid and hwGponDeviceAutoFindOntInfoCheckcode
                           in table hwGponDeviceAutoFindOntControlTable to obtain the LOID and checkcode of the ONT
                         - Modify the definition of the trap node hwGponProfOntDiscoveryAlarmTrap, hwGponProfDiscoveredOntDeletedAlarmTrap,
                           hwGponConfigChangeProfModeOntTrap, hwGponProfOntAutoFindTrap.
                         - Add leaf nodes hwGponDeviceOntRegisterInfoLoid and hwGponDeviceOntRegisterInfoCheckcode
                           in table hwGponDeviceOntRegisterExInfoTable.
                         - Add leaf hwGponDeviceOntReregisterAuthMode in hwGponDeviceOntConfigInfoTable for Re-Register.
                         - Modify the definition of the leaf node hwGponConfigChangeProfModeOntTrap.
                        "

            REVISION     "201010130900Z"
            DESCRIPTION  "V1.36, changes in this revision:
                         - Add invalid value for the MIB standardization.
                         - Change the  description of leaf hwXponDeviceOntPortRunStatus.
                         - Modify the definition of the leaf node hwGponProfOltTFAlarmTrap.
                         - Delete the trap node hwXponTrapSerialNo.
                         - Add leaf hwGponDeviceOntIpconfigDhcpReset in hwGponDeviceOntIpConfigTable for config gpon reset IP host in the DHCP mode.
                         - Change the  description of leaf hwGponDeviceOntTimeOut, hwGponDeviceOntControlLastDownCause and hwGponDeviceOntEthernetNegotiate.
                        "

            REVISION     "201009280900Z"
            DESCRIPTION  "V1.35, changes in this revision:
                         - Change the OID of hwXponDeviceRogueOntTable.
                         - Change the range of leaf hwEponLineProfLlidCfgCarProfileIndex in hwEponDeviceLineProfLlidCfgTable.
                         - Change the length of leaf hwEponLineProfLlidCfgDbaProfileName in hwEponDeviceLineProfLlidCfgTable.
                         - Change the range of leaf hwEponDeviceSrvProfPortVlanCfgPortCVlan and hwEponDeviceSrvProfPortVlanCfgPortSVlan in hwEponDeviceLineProfLlidCfgTable.
                         - Add hwEponDeviceOntLlidTable for config epon ont llid dba and car.
                         - Add hwEponConfigOntLlidDbaCarTrap and hwEponConfigOntPortVlanTrap.
                         - Add hwEponDeviceOntPortVlanTable for config epon ont port vlan.
                         - Add the trap node for TYPE B member port upstream signal detecting, include:hwXponTypeBUpstreamSDFaultAlarmTrap
                         - Add the trap node for TYPE B member port upstream signal detecting, include:hwXponTypeBUpstreamSDRestoreAlarmTrap
                        "

            REVISION     "201009160900Z"
            DESCRIPTION  "V1.34, changes in this revision:
                          - Modify the definition of the leaf node hwGponDeviceOntControlBatteryCurStatus.
                         "

            REVISION     "201009140900Z"
            DESCRIPTION  "V1.33, changes in this revision:
                          - Add the table of hwEponOntLineQualityStatisticTable
                            for the statistic information of the ONT error code.
                         "

            REVISION     "201008250900Z"
            DESCRIPTION  "V1.32, changes in this revision:
                          - Modify the value type of the leaf hwGponProfOltDualparentWorkState.
                          - Add the definition of the trap node, include: hwXponProfOltLOSAlarmTrap,hwXponProfOltLOSRecoverAlarmTrap.
                          - Modify the value range of the leaf hwEponDeviceOntExtCfgOpticAlarmProfileName.
                          - Modify the value range of the leaf hwEponDeviceOntCfgSnmpProfileName.
                          "

            REVISION     "201008110900Z"
            DESCRIPTION  "V1.31, changes in this revision:
                          - Add leaf nodes hwXponDeviceConfigChangeSnmpProfileTrap.
                          - Modify the value range of the leaf hwEponDeviceOntAuthMode, hwEponDeviceOntDbaStatus, hwEponDeviceOntManagementMode, hwGponDeviceOntControlDbaStatus, hwGponDeviceOntTDMPortState.
                          - Add leaf hwGponDeviceOltControlTcontNumCombined in hwGponDeviceOltControlInfoTable for T-CONT auto-combine.
                          - Add leaf hwGponDeviceOltControlTcontNumInCard in hwGponDeviceOltControlInfoTable for T-CONT auto-combine.
                          - Add leaf hwGponDeviceOntControlTcontNumCombined in hwGponDeviceOntControlInfoTable for T-CONT auto-combine.
                          - Modify the description of the lead hwXponDeviceAutoFindOntAge.
                          "

            REVISION     "201007130900Z"
            DESCRIPTION  "V1.30, changes in this revision:
                          - Add leaf nodes hwEponDeviceOntPortManageStatus, hwXponDeviceAccessType, hwEponDeviceOntDbaStatus,
                            hwXponDeviceLineProfileName, hwEponDeviceAlarmProfileName, hwXponDeviceServiceProfileName
                            hwEponConfigChangeOntDiscTrap, hwEponConfigChangeOntPortAttrTrap, hwXponConfigChangeSrvProfileTrap,
                            hwXponConfigChangeLineProfileTrap, hwEponConfigChangeProfModeOntTrap, hwGponConfigChangeProfModeOntTrap,
                            hwEponConfigOltTypeBDparenttTrap, hwEponConfigOntPortNativeVlanTrap for standard traps.
                          - Modify the data type of the leaf hwGponProfOntOpticalMoudleAlarmType.
                          - Modify the definition of the leaf node, include: hwGponProfOntVersionTrap, hwEponProfOntUpVersionTrap,
                            hwGponProfTypeBDParentRogueOntDetectTrap, hwXponProfOntRunStateChangeTrap, hwXponProfOntPortStatusTrap,
                            hwXponUpLoadReportTrap, hwEponProfTypeBDParentRogueOntDetectTrap, hwGponProfOntVersionTrap,
                            hwEponProfOntUpVersionTrap, hwGponDeviceOntEthernetDuplexMode, hwGponDeviceOntEthernetSpeed,
                            hwXponOntNniInnerLoopback, hwXponOntTdmLocalInnerLoopback, hwXponOntTdmLocalOuterLoopback.
                          - Add leaf nodes hwGponDeviceOntPGMemberRole and hwEponDeviceOntPGMemberRole for trap optimization.
                          - Add leaf nodes hwGponDeviceLineProfMappingTransparent in table hwGponDeviceLineProfMappingCfgEntry.
                          - Add leaf nodes hwXponProfOltOpticalTransceiverAbsentAlarmTrap, hwXponProfOltOpticalTransceiverNormalAlarmTrap.
                         "

            REVISION     "201006220900Z"
            DESCRIPTION  "V1.29, changes in this revision:
                          - Modify module name.
                          - Modify the definition difference between MIB file and code.
                         "

            REVISION     "201005190000Z"
            DESCRIPTION  "V1.28, changes in this revision:
                          - Add leaf nodes hwGponDeviceOntEthernetUpStreamCarProfile, hwGponDeviceOntEthernetDownStreamCarProfile
                            in table hwGponDeviceOntEthernetPortCfgTable.
                          - Add hwXponDeviceRogueOntTable to obtain the rogue ONT list.
                         "

            REVISION     "201005050900Z"
            DESCRIPTION  "V1.27, changes in this revision:
                          - Add leaf node hwEponOntEthernetPortStatisticStateChange in table hwEponOntEthernetPortStatisticTable
                            for getting the number of the port changed.
                          - Add hwEponOntEthernetPortStatisticStateChange to obtain the times of port state changes.
                          - Add leaf nodes hwEponDeviceOntEthernetPortCfgDownStreamCarProfile, hwEponDeviceOntEthernetPortCfgUpStreamCarProfile
                            in table hwEponDeviceOntEthernetPortCfgTable.
                          - Modify the value range of the leaf hwGponDeviceLineProfTcontCfgDbaProfileName.
                          - Modify the data type of the leaf hwGponDeviceSrvProfOntPortCfgUpStreamCarProfile.
                            and hwGponDeviceSrvProfOntPortCfgDownStreamCarProfile.
                         "

            REVISION     "201004140000Z"
            DESCRIPTION  "V1.26, changes in this revision:
                         - Add an enum ippath (61) for the leaf hwGponDeviceLineProfMappingCfgOntPhyType.
                         - Add leaf node hwGponDeviceSrvProfPortVlanCfgDscpDefaultPriority in table hwGponDeviceSrvProfPortVlanCfgTable
                           for setting the default priority for the dscpMapping policy.
                         - Add leaf hwEponDeviceOntIsolationStatus in hwEponDeviceOltControlInfoTable.
                         - Add leaf hwEponDeviceOltControlManualDetectRogueOnt,hwEponDeviceOltRogueOntExist
                           in hwEponDeviceOltControlInfoTable.
                         - Add trap hwEponProfTypeBDParentRogueOntDetectTrap for EPON device typeBD parent rogue ont detect.
                         - Modify the leaf name from hwGponDeviceAutoDetectRogueOntNew to hwXponDeviceAutoDetectRogueOntNew.
                         - Add leaf node hwGponDeviceOntIpIndex in table hwGponDeviceOntIpConfigInfoTable
                           for setting the ip inteface index.
                         - Add leaf node hwGponDeviceOntIpconfigDscpProfIndex in table hwGponDeviceOntIpConfigInfoTable
                           for setting the dscp profile of the ip interface.
                         - Add leaf node hwGponDeviceOntIpconfigDscpDefaultPriority in table hwGponDeviceOntIpConfigInfoTable
                           for setting the default priority for the dscpMapping policy
                         - Modify the description of the leaf node hwGponDeviceOntIpConfigVlan and hwGponDeviceOntIpConfigPriority
                         - Add leaf hwGponDeviceSrvProfPortVlanCfgPortVlanTlsSwitch in table hwGponDeviceSrvProfPortVlanCfgTable
                           for config the vlan attribute of transparent.
                         - Modify the length of the attribute value for the node, include: hwGponDeviceOltObjectOpticAlarmProfileName,
                           hwGponDeviceOntPassword, hwEponDeviceOltControlOpticAlarmProfileName, hwXponOntLoadFileName,
                           hwXponOntLoadUserName,hwXponOntLoadPassword.
                         - Modify the attribute value,include node:hwEponDeviceOltLastDownCause, hwXponOntLoadFileType,
                           hwXponOntLoadProtocol, hwGponDeviceOltLastDownCause,hwEponDeviceOltControlVlanTagMode.
                         - Modify the node of hwGponDeviceMinimumBandwidth from read-write to read-only.
                         - Add leaf node hwGponOntOpticalDdmAniCATRxPower in table hwGponDeviceOntOpticalDdmInfoTable
                           for obtaining the CATV receiving optical power of the optical module.
                         - Add leaf node hwGponDeviceLineProfileTr069ManagementSwitch in table hwGponDeviceLineProfileInfoTable
                           for non_OMCI management config of the ONT.
                         - Add leaf node hwEponDeviceOltControlLeftBandWidth in table hwEponDeviceOltControlInfoTable
                           for querying the left bandwidth of the port
                         - Add leaf node hwEponDeviceOltControlAvailableBandWidth in table hwEponDeviceOltControlInfoTable
                           for querying the available bandwidth of the port
                         - Add leaf node hwGponDeviceSrvProfOntPortCfgDscpProfIndex in table hwGponDeviceSrvProfOntPortCfgTable
                           for setting the dscp profile of the ont port
                         - Add leaf node hwGponDeviceSrvProfPortVlanCfgPortVlanSPriPolicy in table
                           hwGponDeviceSrvProfPortVlanCfgTable for config s-vlan priority policy.
                         - Add the definition of the trap node, include: hwEponOpticalTransceiverStateFaultAlarmTrap,
                           hwEponOpticalTransceiverStateRestoreAlarmTrap, hwXponUpLoadReportTrap.
                        "

            REVISION     "201003220900Z"
            DESCRIPTION  "V1.25, changes in this revision:
                          - Add leaf nodes hwGponOltOpticsModuleXponType, hwGponOltOpticsModuleXponSubType,
                            hwGponOltOpticsModuleXponUsedType and hwGponOltOpticsModuleXponEncapsulationType in table
                            hwGponOltOpticsModuleInfoTable for the query of Huawei extended information of optical module.
                          - Add leaf nodes hwEponOltOpticsModuleXponType, hwEponOltOpticsModuleXponSubType,
                            hwEponOltOpticsModuleXponUsedType and hwEponOltOpticsModuleXponEncapsulationType in table
                            hwEponOltOpticsModuleInfoTable for the query of Huawei extended information of optical module.
                         "

            REVISION     "201001270900Z"
            DESCRIPTION  "V1.24, changes in this revision:
                          - Modify the definition of the trap node, include:hwEponProfOntUpVersionTrap, hwXponProfOntPortStatusTrap,
                            hwEponProfOntAutoFindTrap, hwGponProfOntDiscoveryStateTrap, hwGponProfDiscoveredOntDeletedAlarmTrap,
                            hwGponProfOntDiscoveryAlarmTrap.
                          - Modify the data type from OCTET STRING to MacAddress,include node: hwEponDeviceAutoFindOntInfoMacAddress,
                            hwEponDeviceOntMacAddress, hwGponDeviceOntPhyAddress.
                         "

            REVISION     "201001270900Z"
            DESCRIPTION  "V1.23, changes in this revision:
                          - Add hwXponDeviceSLAProfileInfoTable to configure the SLA profile.
                         "

            REVISION     "201001120900Z"
            DESCRIPTION  "V1.22, changes in this revision:
                          - Add the definition of the trap node.
                         "

            REVISION     "200912310900Z"
            DESCRIPTION  "V1.21, changes in this revision:
                          - Add a enumeration of the leaf hwGponDeviceOntIpConfigMode
                            for querying the IP configuration of the ONT.
                         "

            REVISION     "200912140900Z"
            DESCRIPTION  "V1.19, changes in this revision:
                          - Add table hwXponDeviceLineProfEthPortBundleCfgTable for setting PORT-BUNDLE configuration group.
                          - Add leaf nodes hwEponDeviceOntRegisterInfoLoid and hwEponDeviceOntRegisterInfoCheckcode
                            in table hwEponDeviceOntRegisterExInfoTable for getting ONT LOID and ONT CHECKCODE.
                          - Add leaf node hwGponDeviceSrvProfPortVlanCfgEtherType in table hwGponDeviceSrvProfPortVlanCfgTable
                            as the index of the table.
                          - Add leaf nodes hwGponDeviceSrvProfOntPortCfgUpStreamCarProfile and
                            hwGponDeviceSrvProfOntPortCfgDownStreamCarProfile in table hwGponDeviceSrvProfOntPortCfgTable
                            for setting ONT's upstream CAR profile and downstream CAR profile.
                          - Add leaf nodes hwGponDeviceSrvProfileUpIgmpMsgPriority and hwGponDeviceSrvProfileNativeVlanOption
                            in table hwGponDeviceSrvProfileOntCfgTable for setting the priority of upstream igmp packets
                            and native VLAN option.
                          - Add leaf node hwGponDeviceLineProfileOMCCEncrypt in table hwGponDeviceLineProfileInfoTable
                            for OMCC downstream encrypt.
                         "

            REVISION     "200910090900Z"
            DESCRIPTION  "V1.15, changes in this revision:
                          - Add table hwGponDeviceLineProfTcontRefTable for setting TCONTS which are not bound to a dba-profile.
                         "

            REVISION     "200906050900Z"
            DESCRIPTION  "V1.10, changes in this revision:
                          - Add leaf nodes hwXponOntLoadXmlIndex and hwONTLoadXmlOntObjectIndex in table hwXponOntLoadCtrlTable
                            for supporting ONT collateral loading.
                         "

            REVISION     "200902030900Z"
            DESCRIPTION  "V1.05, changes in this revision:
                          - Add leaf nodes hwGponOntTrafficFlowStatisticUpFecDecodCorrectCnt,
                            hwGponOntTrafficFlowStatisticUpFecDecodUnCorrectCnt
                            and hwGponOntTrafficFlowStatisticUpHecCheckErrCnt in table hwGponOntTrafficFlowStatisticTable
                            for obtaining ONT traffic stream statistics information.
                          - Add leaf node hwGponDeviceSrvProfileMulticastMode in table hwGponDeviceSrvProfileOntCfgTable
                            for setting ONT multicast mode.
                          - Add leaf node hwGponOntOpticalDdmOltRxOntPower in table hwGponDeviceOntOpticalDdmInfoTable
                            for obtaining the ONT power received by the OLT.
                          - Add leaf node hwGponDeviceOntExtCfgOpticAlarmProfileName in table hwGponDeviceOntExtendConfigTable
                            for setting optical alarm profile which the ONT is bound to.
                          - Add leaf node hwGponDeviceOltObjectOpticAlarmProfileName in table hwGponDeviceOltControlInfoTable
                            for setting optical alarm profile which the GPON port is bound to.
                          - Add scalar hwGponDeviceDbaBandwidthType for setting the type of bandwidth.
                          - Add scalar hwGponDeviceDbaAssignmentMode for setting the DBA assignment mode.
                         "

            REVISION     "200809280900Z"
            DESCRIPTION  "V1.01, Initial version."
            ::= { huaweiUtility  128 }

        hwXponDeviceObjectMIB OBJECT IDENTIFIER ::= { hwXponDeviceMIB 1}

        hwXponDeviceObjects OBJECT IDENTIFIER ::= { hwXponDeviceObjectMIB  1}

        hwXponDeviceGlobalObjects OBJECT IDENTIFIER ::= { hwXponDeviceObjects 1}

        hwXponDeviceControlObjects OBJECT IDENTIFIER ::= { hwXponDeviceObjects 2}

        hwXponDeviceProfileObjects OBJECT IDENTIFIER ::= { hwXponDeviceObjects 3}

        hwXponDeviceStatisticObjects OBJECT IDENTIFIER ::= { hwXponDeviceObjects 4}

        hwXponDeviceLoopbackObjects OBJECT IDENTIFIER ::= { hwXponDeviceObjects 5}

        hwXponDeviceLineTestObjects OBJECT IDENTIFIER ::= { hwXponDeviceObjects 6}


        VlanIndex ::= TEXTUAL-CONVENTION
            STATUS current
            DESCRIPTION
                "A value used to index per-VLAN tables: values of 0 and 4095 are not permitted;
                 if the value is between 1 and 4094 inclusive, it represents an IEEE 802.1Q VLAN-ID with
                 global scope within a given bridged domain (see VlanId textual convention).
                 If the value is greater than 4095 then it represents a VLAN with scope local to the
                 particular agent, i.e. one without a global VLAN-ID assigned to it.
                 Such VLANs are outside the scope of IEEE 802.1Q but it is convenient to be able to manage them
                 in the same way using this MIB.
                "
            SYNTAX Unsigned32

        PortList ::= TEXTUAL-CONVENTION
            STATUS current
            DESCRIPTION
                "Each octet within this value specifies a set of eight ports, with the first
                 octet specifying ports 1 through 8, the second octet specifying ports 9 through 16 and others.
                 Within each octet, the most significant bit represents the lowest numbered port,
                 and the least significant bit represents the highest numbered port.
                 Thus, each port of the bridge is represented by a single bit within the value of this object.
                 If that bit has a value of '1' then that port is included in the set of ports;
                 the port is not included if its bit has a value of '0'.
                "
            SYNTAX OCTET STRING

        OntList ::= TEXTUAL-CONVENTION
            STATUS current
            DESCRIPTION
                "Each octet within this value specifies a set of eight onts, with the first
                 octet specifying ports 0 through 7, the second octet specifying ports 8 through 15 and others.
                 Within each octet, the most significant bit represents the lowest numbered ont,
                 and the least significant bit represents the highest numbered ont.
                 Thus, each ont of the bridge is represented by a single bit within the value of this object.
                 If that bit has a value of '1' then that ont is included in the set of onts;
                 the ont is not included if its bit has a value of '0'.
                "
            SYNTAX OCTET STRING

-- hwXponDeviceGlobalObjects   begin
        hwXponDeviceAutoFindOntAge OBJECT-TYPE
            SYNTAX Integer32
            MAX-ACCESS read-write
            STATUS current
            DESCRIPTION
                "The aging time of the auto-found ONT, which can be 0s (indicating that the ONT will not aging) or a value from 100s to 300s."
            ::= { hwXponDeviceGlobalObjects 1 }

        hwXponDeviceAutoFindInterval OBJECT-TYPE
            SYNTAX Integer32
            MAX-ACCESS read-write
            STATUS current
            DESCRIPTION
                "Indicates the SN request interval, ranging from 1(s) to 10(s)."
            ::= { hwXponDeviceGlobalObjects 2 }

        hwXponDeviceModeCfgSwitch  OBJECT-TYPE
            SYNTAX  INTEGER {
                distributingmode(1),
                profilemode(2)
            }
            MAX-ACCESS  read-write
            STATUS  current
            DESCRIPTION
                "This object is used to change XPON management mode.
                 When xpon mode is changed from profile mode to distributing mode and there are xpon data or xpon board information in system,
                 the system will automatically save data and reboot,and will cause all configuration of XPON lost.
                 When the mode is changed from distributing mode to profile mode, the system will automatically save data and reboot. The operation
                 can not cause the configuration of XPON lost.
                 Options:
                 1. distributingmode(1) - XPON distributing mode
                 2. profilemode(2)      - XPON profile mode
                "
            ::= { hwXponDeviceGlobalObjects 3 }

        hwGponDeviceMulticastGemportId OBJECT-TYPE
            SYNTAX Integer32
            MAX-ACCESS read-write
            STATUS current
            DESCRIPTION
                "The special GEM port ID is used for the multicast service, ranging from 4000 to 4095."
            ::= { hwXponDeviceGlobalObjects 21 }


        hwGponDeviceBaseGemportId  OBJECT-TYPE
            SYNTAX Integer32
            MAX-ACCESS read-write
            STATUS current
            DESCRIPTION
                "The base GEM port is used when the board's car-mode is port-cos, ranging from 128 to 3872."
            ::= { hwXponDeviceGlobalObjects 22 }

        hwGponDeviceMinimumBandwidth OBJECT-TYPE
            SYNTAX Integer32
            MAX-ACCESS read-only
            STATUS current
            DESCRIPTION
                "The scalar is used to configure the minimum bandwidth of the T-CONTs in the system,
                 ranging from 384 to 1024.
                "
            ::= { hwXponDeviceGlobalObjects 23 }

        hwXponDeviceAutoDetectRogueOntNew  OBJECT-TYPE
            SYNTAX  INTEGER {
                on(1),
                off(2)
            }
            MAX-ACCESS read-write
            STATUS  current
            DESCRIPTION
                "This object is used to open or close the switch of rogue ONT automatic detection.
                 Options:
                 1.on(1)     - Open the switch of rogue ONT automatic detection
                 2.off(2)    - Close the switch of rogue ONT automatic detection
                 The default value is off(2).
                "
            ::= { hwXponDeviceGlobalObjects 24 }

        hwGponDeviceDbaBandwidthType  OBJECT-TYPE
            SYNTAX  INTEGER {
                gpon(1),
                ethernet(2)
            }
            MAX-ACCESS read-write
            STATUS  current
            DESCRIPTION
                "This object is used to select the type of bandwidth.
                 Options:
                 1.gpon(1)            - Indicates that the type of bandwidth is GPON
                 2.ethernet(2)        - Indicates that the type of bandwidth is ETH
                 The default value is gpon(1).
                "
            ::= { hwXponDeviceGlobalObjects 25 }

        hwGponDeviceDbaAssignmentMode  OBJECT-TYPE
            SYNTAX  INTEGER {
                maxbandwidthusage(1),
                minloopdelay(2),
                manual(3)
            }
            MAX-ACCESS read-write
            STATUS  current
            DESCRIPTION
                "This object is used to select the DBA assignment mode.
                 Options:
                 1.maxbandwidthusage(1)    - Indicates that the usage of bandwidth is maximum
                 2.minloopdelay(2)         - Indicates that the loop delay is minimum
                 3.manual(3)               - Indicates that the DBA assignment mode is manual,this value can not set now
                "
            ::= { hwXponDeviceGlobalObjects 26 }

        hwEponDeviceCtcOuiId  OBJECT-TYPE
            SYNTAX OCTET STRING (SIZE (0..3))
            MAX-ACCESS read-write
            STATUS current
            DESCRIPTION
                "This object is used to set the Organizationally Unique Identifier."
            ::= { hwXponDeviceGlobalObjects 41 }

        hwEponDeviceChangePasswordIntervalTime  OBJECT-TYPE
            SYNTAX Integer32
            MAX-ACCESS read-write
            STATUS current
            DESCRIPTION
                   "The interval time of ONT's password renew, ranging from 1(s) to 254(s)."
            ::= { hwXponDeviceGlobalObjects 42 }
-- hwXponDeviceGlobalObjects  end

-- hwXponDeviceControlObjects  begin

-- Table hwGponDeviceOltControlInfoTable
        hwGponDeviceOltControlInfoTable OBJECT-TYPE
            SYNTAX  SEQUENCE OF HwGponDeviceOltControlInfoEntry
            MAX-ACCESS  not-accessible
            STATUS  current
            DESCRIPTION
                "The control table of the GPON OLT. The index of this table is ifIndex."
            ::= { hwXponDeviceControlObjects 21 }

        hwGponDeviceOltControlInfoEntry OBJECT-TYPE
            SYNTAX  HwGponDeviceOltControlInfoEntry
            MAX-ACCESS  not-accessible
            STATUS  current
            DESCRIPTION
                "The control table of the GPON OLT. The index of this entry is ifIndex."
            INDEX { ifIndex }
            ::= { hwGponDeviceOltControlInfoTable 1 }

        HwGponDeviceOltControlInfoEntry ::=
            SEQUENCE {
                hwGponDeviceOltControlNearest                      Integer32,
                hwGponDeviceOltControlFarthest                     Integer32,
                hwGponDeviceOltControlDnFecEnabled                 INTEGER,
                hwGponDeviceOltControlAutofindOntEnable            INTEGER,
                hwGponDeviceOltControlChangePasswordAge            Integer32,
                hwGponDeviceOltControlDespt                        OCTET STRING,
                hwGponDeviceOltControlLeftBandWidth                Integer32,
                hwGponDeviceOltControlMinBandwidth                 Integer32,
                hwGponDeviceOltControlLaserSwitch                  INTEGER,
                hwGponDeviceOltControlStatus                       INTEGER,
                hwGponDeviceOltControlManualDetectRogueOnt         INTEGER,
                hwGponDeviceOltControlIlegalIncurRogueOntExt       INTEGER,
                hwGponDeviceOltControlOpticModuleStatus            INTEGER,
                hwGponDeviceOltControlAvailableBandWidth           Integer32,
                hwGponDeviceOltObjectOpticAlarmProfileName         OCTET STRING,
                hwGponDeviceOltControlOntNum                       Integer32,
                hwGponDeviceOltLastUpTime                          DateAndTime,
                hwGponDeviceOltLastDownTime                        DateAndTime,
                hwGponDeviceOltLastDownCause                       INTEGER,
                hwGponDeviceOltControlTcontNumCombined             Integer32,
                hwGponDeviceOltControlTcontNumInCard               Integer32,
                hwGponDeviceOltControlEnergySavingFlag             INTEGER,
                hwGponDeviceOltControlManualCheckRogueOnt          INTEGER,
                hwGponDeviceOltControlPortReset                    INTEGER
            }

        hwGponDeviceOltControlNearest OBJECT-TYPE
            SYNTAX  Integer32
            MAX-ACCESS  read-write
            STATUS  current
            DESCRIPTION
                "This is the fiber distance between the OLT and the nearest ONT.
                 For GPON, the fiber distance between the OLT and the nearest ONT
                 is 0 km to 40 km while the maximum fiber distance between the farthest
                 and the nearest ONTs is 20 km.
                 For XG-PON, the fiber distance between the OLT and the nearest ONT
                 is 0 km to 60 km while the maximum fiber distance between the farthest
                 and the nearest ONTs is 40 km.
                "
            ::= { hwGponDeviceOltControlInfoEntry 1 }

        hwGponDeviceOltControlFarthest OBJECT-TYPE
            SYNTAX  Integer32
            MAX-ACCESS read-write
            STATUS  current
            DESCRIPTION
                "This is the fiber distance between the OLT and the farthest ONT.
                 For GPON, the fiber distance between the OLT and the nearest ONT
                 is 0 km to 60 km while the maximum fiber distance between the farthest
                 and the nearest ONTs is 20 km.
                 For XG-PON, the fiber distance between the OLT and the nearest ONT
                 is 0 km to 100 km while the maximum fiber distance between the farthest
                 and the nearest ONTs is 40 km.
                "
            ::= { hwGponDeviceOltControlInfoEntry 2 }

        hwGponDeviceOltControlDnFecEnabled OBJECT-TYPE
            SYNTAX  INTEGER {
                enable(1),
                disable(2),
                invalid(-1)
            }
            MAX-ACCESS  read-write
            STATUS  current
            DESCRIPTION
                "This object indicates the downstream FEC switch.
                 Options:
                 1. enable(1)        - Enable the downstream FEC switch
                 2. disable(2)       - Disable the downstream FEC switch
                 3. invalid(-1)      - Indicates that the query fails or no information is detected
                 For GPON, the default value is disable(2).
                 For XG-PON, the default value is enable(1).
                "
            ::= { hwGponDeviceOltControlInfoEntry 3 }

        hwGponDeviceOltControlAutofindOntEnable OBJECT-TYPE
            SYNTAX  INTEGER {
                enable(1),
                disable(2),
                invalid(-1)
            }
            MAX-ACCESS read-write
            STATUS  current
            DESCRIPTION
                "This object indicates the ONT auto find switch.
                 Options:
                 1. enable(1)         - Enable the ONT auto find switch
                 2. disable(2)        - Disable the ONT auto find switch
                 3. invalid(-1)       - Indicates that the query fails or no information is detected
                 The default value is disable(2).
                "
            DEFVAL { disable }
            ::= { hwGponDeviceOltControlInfoEntry 4 }

        hwGponDeviceOltControlChangePasswordAge OBJECT-TYPE
            SYNTAX  Integer32
            MAX-ACCESS  read-write
            STATUS  current
            DESCRIPTION
                "This object indicates the ONT password update period.
                 0 means no update, range: 0 or 5~1440 minutes.
                "
            DEFVAL { 0 }
            ::= { hwGponDeviceOltControlInfoEntry 5 }

        hwGponDeviceOltControlDespt OBJECT-TYPE
            SYNTAX  OCTET STRING (SIZE (0..80))
            MAX-ACCESS  read-write
            STATUS  current
            DESCRIPTION
                "This object indicates the description of GPON port."
            ::= { hwGponDeviceOltControlInfoEntry 6 }

        hwGponDeviceOltControlLeftBandWidth OBJECT-TYPE
            SYNTAX  Integer32
            MAX-ACCESS  read-only
            STATUS  current
            DESCRIPTION
                "This object indicates the untapped bandwidth of the port."
            ::= { hwGponDeviceOltControlInfoEntry 7 }

        hwGponDeviceOltControlMinBandwidth OBJECT-TYPE
            SYNTAX  Integer32
            MAX-ACCESS  read-write
            STATUS  current
            DESCRIPTION
                "This object indicates the minimum bandwidth of T-CONTs in the OLT port."
            ::= { hwGponDeviceOltControlInfoEntry 8 }

        hwGponDeviceOltControlLaserSwitch OBJECT-TYPE
            SYNTAX  INTEGER {
                on (1),
                off (2),
                invalid (-1)
            }
            MAX-ACCESS  read-write
            STATUS  current
            DESCRIPTION
                "This object indicates the laser switch of the GPON port.
                 Options:
                 1. on(1)                       - Open the laser switch of the GPON port
                 2. off(2)                      - Close the laser switch of the GPON port
                 3. invalid(-1)                 - Indicates that the query fails or no information is detected
                "
            DEFVAL { on }
            ::= { hwGponDeviceOltControlInfoEntry 9 }

        hwGponDeviceOltControlStatus OBJECT-TYPE
            SYNTAX  INTEGER {
                up(1),
                down(2)
            }
            MAX-ACCESS  read-only
            STATUS  current
            DESCRIPTION
                "This object indicates the GPON port status in the OLT.
                 Options:
                 1. up(1)         - Indicates that the GPON port is normal
                 2. down(2)       - Indicates that the GPON port is fault
                "
            ::= { hwGponDeviceOltControlInfoEntry 10 }

        hwGponDeviceOltControlManualDetectRogueOnt OBJECT-TYPE
            SYNTAX  INTEGER {
                startup(1),
                invalid(-1)
            }
            MAX-ACCESS  read-write
            STATUS  current
            DESCRIPTION
                "This object indicates the switch of the rogue ONT manual detection.
                 Options:
                 1. startup(1)    - Start up the switch of the rogue ONT manual detection
                 2. invalid(-1)   - Indicates that the query fails or no information is detected
                "
            ::= { hwGponDeviceOltControlInfoEntry 11 }

        hwGponDeviceOltControlIlegalIncurRogueOntExt OBJECT-TYPE
            SYNTAX  INTEGER {
                inexistent (0),
                existent (1),
                invalid (-1)
            }
            MAX-ACCESS  read-only
            STATUS  current
            DESCRIPTION
                "This object is used to query whether there are Illegal incursionary rogue ONTs under port.
                 Options:
                 1. inexistent(0)    - Indicates that there are not Illegal incursionary rogue ONTs under port
                 2. existent(1)      - Indicates that there are Illegal incursionary rogue ONTs under port
                 3. invalid(-1)      - Indicates that the query fails or no information is detected
                "
            ::= { hwGponDeviceOltControlInfoEntry 12 }

        hwGponDeviceOltControlOpticModuleStatus OBJECT-TYPE
            SYNTAX  INTEGER {
                online  (1),
                offline (2),
                invalid (-1)
            }
            MAX-ACCESS  read-only
            STATUS  current
            DESCRIPTION
                "This object indicates the optical module status on GPON port.
                 Options:
                 1. online(1)          - Indicates that the optical module is online
                 2. offline(2)         - Indicates that the optical module is offline
                 3. invalid(-1)        - Indicates that the query fails or no information is detected
                "
            ::= { hwGponDeviceOltControlInfoEntry 13 }

        hwGponDeviceOltControlAvailableBandWidth OBJECT-TYPE
            SYNTAX  Integer32
            MAX-ACCESS  read-only
            STATUS  current
            DESCRIPTION
                "This object indicates the available bandwidth of the port."
            ::= { hwGponDeviceOltControlInfoEntry 14 }

        hwGponDeviceOltObjectOpticAlarmProfileName  OBJECT-TYPE
            SYNTAX     OCTET STRING (SIZE (0..32))
            MAX-ACCESS   read-write
            STATUS      current
            DESCRIPTION
                "This object indicates the name of the optical alarm profile that is bound to the port."
            ::= { hwGponDeviceOltControlInfoEntry 15 }

        hwGponDeviceOltControlOntNum OBJECT-TYPE
            SYNTAX  Integer32
            MAX-ACCESS  read-only
            STATUS  current
            DESCRIPTION
                "This object indicates the number of ONTs that are added to the port."
            ::= { hwGponDeviceOltControlInfoEntry 16 }

        hwGponDeviceOltLastUpTime OBJECT-TYPE
            SYNTAX DateAndTime
            MAX-ACCESS  read-only
            STATUS current
            DESCRIPTION
                "This object indicates the time when the port last went online."
            ::= { hwGponDeviceOltControlInfoEntry 17 }

        hwGponDeviceOltLastDownTime OBJECT-TYPE
            SYNTAX DateAndTime
            MAX-ACCESS  read-only
            STATUS current
            DESCRIPTION
                "This object indicates the time when the port last went offline."
            ::= { hwGponDeviceOltControlInfoEntry 18 }

        hwGponDeviceOltLastDownCause OBJECT-TYPE
            SYNTAX INTEGER{
                los(1),
                opticModuleAbsence(2),
                opticModuleFault(3),
                opticPortClosed(4),
                otherCause(-1)
            }
            MAX-ACCESS  read-only
            STATUS current
            DESCRIPTION
                "This object indicates the reason why the port last went offline.
                 Options:
                 1. los(1)                - Loss of signal
                 2. opticModuleAbsence(2) - The optic module is absence
                 3. opticModuleFault(3)   - The optic module is fault
                 4. opticPortClosed(4)    - The optic port is closed
                 5. otherCause(-1)        - Other cause
                "
            ::= { hwGponDeviceOltControlInfoEntry 19 }

        hwGponDeviceOltControlTcontNumCombined OBJECT-TYPE
            SYNTAX Integer32
            MAX-ACCESS read-only
            STATUS current
            DESCRIPTION
                "The number of the combined T-CONTs."
            ::= { hwGponDeviceOltControlInfoEntry 20 }

        hwGponDeviceOltControlTcontNumInCard OBJECT-TYPE
            SYNTAX Integer32
            MAX-ACCESS read-only
            STATUS current
            DESCRIPTION
                "The number of T-CONTs in the card."
            ::= { hwGponDeviceOltControlInfoEntry 21 }

        hwGponDeviceOltControlEnergySavingFlag OBJECT-TYPE
            SYNTAX  INTEGER {
                yes (1),
                no (2)
            }
            MAX-ACCESS  read-only
            STATUS  current
            DESCRIPTION
                "Energy saving state of the GPON port.
                 Options:
                 1. yes (1)  - The GPON port is in energy saving state
                 2. no (2)   - The GPON port is not in energy saving state
                "
            ::= { hwGponDeviceOltControlInfoEntry 22 }

        hwGponDeviceOltControlManualCheckRogueOnt OBJECT-TYPE
            SYNTAX  INTEGER {
                startup(1),
                invalid(-1)
            }
            MAX-ACCESS  read-write
            STATUS  current
            DESCRIPTION
                "This object indicates the switch of the rogue ONT manual check.
                 Options:
                 1. startup(1)    - Start up the switch of the rogue ONT manual checked
                 2. invalid(-1)   - Indicates that the query fails or no information is checked
                "
            ::= { hwGponDeviceOltControlInfoEntry 23 }

        hwGponDeviceOltControlPortReset OBJECT-TYPE
            SYNTAX  INTEGER {
                reset(1),
                invalid(-1)
            }
            MAX-ACCESS  read-write
            STATUS  current
            DESCRIPTION
                "This parameter is used to reset the port.
                 Options:
                 1. reset(1)      - Indicates that the port resets
                 2. invalid(-1)   - Indicates that the query fails or no information is checked
                "
            ::= { hwGponDeviceOltControlInfoEntry 24 }

 -- Table : hwGponOltOpticsModuleInfoTable
        hwGponOltOpticsModuleInfoTable OBJECT-TYPE
            SYNTAX     SEQUENCE OF HwGponOltOpticsModuleInfoEntry
            MAX-ACCESS not-accessible
            STATUS     current
            DESCRIPTION
                "This table is used to query the information about the optical transceiver.
                 The index of this table is ifIndex.
                "
            ::= { hwXponDeviceControlObjects 22 }

        hwGponOltOpticsModuleInfoEntry OBJECT-TYPE
            SYNTAX     HwGponOltOpticsModuleInfoEntry
            MAX-ACCESS not-accessible
            STATUS     current
            DESCRIPTION
                "This table is used to query the information about the optical transceiver.
                 The index of this entry is ifIndex.
                "
            INDEX       { ifIndex }
            ::= { hwGponOltOpticsModuleInfoTable 1 }

        HwGponOltOpticsModuleInfoEntry ::=
            SEQUENCE {
                hwGponOltOpticsModuleInfoIdentifier                    INTEGER,
                hwGponOltOpticsModuleInfoExtID                         INTEGER,
                hwGponOltOpticsModuleInfoConnector                     INTEGER,
                hwGponOltOpticsModuleInfoEncoding                      INTEGER,
                hwGponOltOpticsModuleInfoBrNominal                     Integer32,
                hwGponOltOpticsModuleInfoLength9Micronkm               Integer32,
                hwGponOltOpticsModuleInfoLength9Micron                 Integer32,
                hwGponOltOpticsModuleInfoLength50Micron                Integer32,
                hwGponOltOpticsModuleInfoLength62Micron5               Integer32,
                hwGponOltOpticsModuleInfoLengthCopper                  Integer32,
                hwGponOltOpticsModuleInfoVendorName                    OCTET STRING,
                hwGponOltOpticsModuleInfoVendorOUI                     OCTET STRING,
                hwGponOltOpticsModuleInfoVendorPN                      OCTET STRING,
                hwGponOltOpticsModuleInfoVendorRev                     OCTET STRING,
                hwGponOltOpticsModuleInfoWaveLength                    Integer32,
                hwGponOltOpticsModuleInfoCcBase                        Integer32,
                hwGponOltOpticsModuleInfoOptions                       Integer32,
                hwGponOltOpticsModuleInfoBrMax                         Integer32,
                hwGponOltOpticsModuleInfoBrMin                         Integer32,
                hwGponOltOpticsModuleInfoVendorSN                      OCTET STRING,
                hwGponOltOpticsModuleInfoDateCode                      OCTET STRING,
                hwGponOltOpticsModuleInfoDiagnosticMonitoringType      Integer32,
                hwGponOltOpticsModuleInfoEnhancedOptions               Integer32,
                hwGponOltOpticsModuleInfoSFF8472Compliance             INTEGER,
                hwGponOltOpticsModuleInfoCcExt                         Integer32,
                hwGponOltOpticsModuleInfoVendorSpecific                OCTET STRING,
                hwGponOltOpticsModuleXponType                          INTEGER,
                hwGponOltOpticsModuleXponSubType                       INTEGER,
                hwGponOltOpticsModuleXponUsedType                      INTEGER,
                hwGponOltOpticsModuleXponEncapsulationType             INTEGER,
                hwGponOltOpticsModuleInfoPartNum                       OCTET STRING
            }

        hwGponOltOpticsModuleInfoIdentifier OBJECT-TYPE
            SYNTAX INTEGER {
                unknown(1),
                gbic(2),
                solderedToMotherboard(3),
                sfp(4),
                invalid(-1)
            }
            MAX-ACCESS read-only
            STATUS current
            DESCRIPTION
                "This object indicates the type of serial transceiver.
                 Options:
                 1. unknown(1)                      - Unknown or unspecified
                 2. gbic(2)                         - GBIC
                 3. solderedToMotherboard(3)        - Module soldered to motherboard
                 4. sfp(4)                          - SFP or SFP Plus
                 5. invalid(-1)                     - Indicates that the query fails or no information is detected
                "
            ::= { hwGponOltOpticsModuleInfoEntry 1 }

        hwGponOltOpticsModuleInfoExtID OBJECT-TYPE
            SYNTAX INTEGER {
                notSpecifiedOrNotCompliant(1),
                moddef1(2),
                moddef2(3),
                moddef3(4),
                byTwowireOnly(5),
                moddef5(6),
                moddef6(7),
                moddef7(8),
                invalid(-1)
            }
            MAX-ACCESS read-only
            STATUS current
            DESCRIPTION
                "This object indicates the extended identifier of type of serial transceiver.
                 Options:
                 1. notSpecifiedOrNotCompliant(1)   - Not specified or not compliant with a defined MOD_DEF
                 2. moddef1(2)                      - GBIC is compliant with MOD_DEF 1
                 3. moddef2(3)                      - GBIC is compliant with MOD_DEF 2
                 4. moddef3(4)                      - GBIC is compliant with MOD_DEF 3
                 5. byTwowireOnly(5)                - GBIC/SFP function is defined by two-wire interface ID only
                 6. moddef5(6)                      - GBIC is compliant with MOD_DEF 5
                 7. moddef6(7)                      - GBIC is compliant with MOD_DEF 6
                 8. moddef7(8)                      - GBIC is compliant with MOD_DEF 7
                 9. invalid(-1)                     - Indicates that the query fails or no information is detected
                "
            ::= { hwGponOltOpticsModuleInfoEntry 2 }

        hwGponOltOpticsModuleInfoConnector OBJECT-TYPE
            SYNTAX INTEGER {
                unknown(1),
                sc(2),
                copperConnector1(3),
                copperConnector2(4),
                bnctnc(5),
                coaxialHeaders(6),
                fiberJack(7),
                lc(8),
                mtrj(9),
                mu(10),
                sg(11),
                opticalPigtail(12),
                hssdcII(13),
                copperPigtail(14),
                mpoParallelOptic(15),
                rj45(16),
                invalid(-1)
            }
            MAX-ACCESS read-only
            STATUS current
            DESCRIPTION
                "This object indicates the code for connector type.
                 Options:
                 1.  unknown(1)              - Unknown
                 2.  sc(2)                   - SC
                 3.  copperConnector1(3)     - Fibre Channel Style 1 copper connector
                 4.  copperConnector2(4)     - Fibre Channel Style 2 copper connector
                 5.  bnctnc(5)               - BNC/TNC
                 6.  coaxialHeaders(6)       - Fibre Channel coaxial headers
                 7.  fiberJack(7)            - FiberJack
                 8.  lc(8)                   - LC
                 9.  mtrj(9)                 - MT-RJ
                 10. mu(10)                  - MU
                 11. sg(11)                  - SG
                 12. opticalPigtail(12)      - Optical pigtail
                 13. hssdcII(13)             - HSSDC II
                 14. copperPigtail(14)       - Copper Pigtail
                 15. mpoParallelOptic(15)    - MPO Parallel Optic
                 16. rj45(16)                - RJ45
                 17. invalid(-1)             - Indicates that the query fails or no information is detected
                "
            ::= { hwGponOltOpticsModuleInfoEntry 3 }

        hwGponOltOpticsModuleInfoEncoding OBJECT-TYPE
            SYNTAX INTEGER {
                unspecified(1),
                encodingMethod8B10B(2),
                encodingMethod4B5B(3),
                nrz(4),
                manchester(5),
                sonetScrambled(6),
                encodingMethod64B66B (7),
                invalid(-1)
            }
            MAX-ACCESS read-only
            STATUS current
            DESCRIPTION
                "This object indicates the code for serial encoding algorithm.
                 Options:
                 1. unspecified(1)            - Unspecified
                 2. encodingMethod8B10B(2)    - 8B10B
                 3. encodingMethod4B5B(3)     - 4B5B
                 4. nrz(4)                    - NRZ
                 5. manchester(5)             - Manchester
                 6. sonetScrambled(6)         - SONET Scrambled
                 7. encodingMethod64B66B(7)   - 64B66B
                 8. invalid(-1)               - Indicates that the query fails or no information is detected
                "
            ::= { hwGponOltOpticsModuleInfoEntry 4 }

        hwGponOltOpticsModuleInfoBrNominal OBJECT-TYPE
            SYNTAX Integer32
            MAX-ACCESS read-only
            STATUS current
            DESCRIPTION
                "This object indicates the nominal bit rate, units of 100 MBits/sec."
            ::= { hwGponOltOpticsModuleInfoEntry 5 }

        hwGponOltOpticsModuleInfoLength9Micronkm OBJECT-TYPE
            SYNTAX Integer32
            MAX-ACCESS read-only
            STATUS current
            DESCRIPTION
                "This object indicates the link length supported for 9/125 micron fiber, units of 1000 m."
            ::= { hwGponOltOpticsModuleInfoEntry 6 }

        hwGponOltOpticsModuleInfoLength9Micron OBJECT-TYPE
            SYNTAX Integer32
            MAX-ACCESS read-only
            STATUS current
            DESCRIPTION
                "This object indicates the link length supported for 9/125 micron fiber, units of 100 m."
            ::= { hwGponOltOpticsModuleInfoEntry 7 }

        hwGponOltOpticsModuleInfoLength50Micron OBJECT-TYPE
            SYNTAX Integer32
            MAX-ACCESS read-only
            STATUS current
            DESCRIPTION
                "This object indicates the link length supported for 50/125 micron fiber, units of 10 m."
            ::= { hwGponOltOpticsModuleInfoEntry 8 }

        hwGponOltOpticsModuleInfoLength62Micron5 OBJECT-TYPE
            SYNTAX Integer32
            MAX-ACCESS read-only
            STATUS current
            DESCRIPTION
                "This object indicates the link length supported for 62.5/125 micron fiber, units of 10 m."
            ::= { hwGponOltOpticsModuleInfoEntry 9 }

        hwGponOltOpticsModuleInfoLengthCopper OBJECT-TYPE
            SYNTAX Integer32
            MAX-ACCESS read-only
            STATUS current
            DESCRIPTION
                "This object indicates the link length supported for copper, units of meters."
            ::= { hwGponOltOpticsModuleInfoEntry 10 }

        hwGponOltOpticsModuleInfoVendorName OBJECT-TYPE
            SYNTAX OCTET STRING (SIZE (0..17))
            MAX-ACCESS read-only
            STATUS current
            DESCRIPTION
                "This object indicates the SFP vendor name (ASCII)."
            ::= { hwGponOltOpticsModuleInfoEntry 11 }

        hwGponOltOpticsModuleInfoVendorOUI OBJECT-TYPE
            SYNTAX OCTET STRING (SIZE (0..9))
            MAX-ACCESS read-only
            STATUS current
            DESCRIPTION
                "This object indicates the SFP vendor IEEE company ID."
            ::= { hwGponOltOpticsModuleInfoEntry 12 }

        hwGponOltOpticsModuleInfoVendorPN OBJECT-TYPE
            SYNTAX OCTET STRING (SIZE (0..17))
            MAX-ACCESS read-only
            STATUS current
            DESCRIPTION
                "This object indicates the part number provided by SFP vendor (ASCII)."
            ::= { hwGponOltOpticsModuleInfoEntry 13 }

        hwGponOltOpticsModuleInfoVendorRev OBJECT-TYPE
            SYNTAX OCTET STRING (SIZE (0..5))
            MAX-ACCESS read-only
            STATUS current
            DESCRIPTION
                "This object indicates the revision level for part number provided by vendor (ASCII)."
            ::= { hwGponOltOpticsModuleInfoEntry 14 }

        hwGponOltOpticsModuleInfoWaveLength OBJECT-TYPE
            SYNTAX Integer32
            MAX-ACCESS read-only
            STATUS current
            DESCRIPTION
                "This object indicates the laser wavelength, units of nm."
            ::= { hwGponOltOpticsModuleInfoEntry 15 }

        hwGponOltOpticsModuleInfoCcBase OBJECT-TYPE
            SYNTAX Integer32
            MAX-ACCESS read-only
            STATUS current
            DESCRIPTION
                "This object indicates the check code for Base ID Fields."
            ::= { hwGponOltOpticsModuleInfoEntry 16 }

        hwGponOltOpticsModuleInfoOptions OBJECT-TYPE
            SYNTAX Integer32
            MAX-ACCESS read-only
            STATUS current
            DESCRIPTION
                "Indicates which optional transceiver signals are implemented.
                  bit                 Description of option
                   10                 Cooled laser transmitter
                   9                  Power Level 2 requirement
                   8                  Linear Receiver Output
                  7-6                 Reserved
                   5                  RATE_SELECT
                   4                  TX_DISABLE
                   3                  TX_FAULT
                   2                  LOS (signal inverted from standard definition)
                   1                  LOS (signal as defined in SFP MSA)
                   0                  Reserved
                "
            ::= { hwGponOltOpticsModuleInfoEntry 17 }

        hwGponOltOpticsModuleInfoBrMax OBJECT-TYPE
            SYNTAX Integer32
            MAX-ACCESS read-only
            STATUS current
            DESCRIPTION
                "This object indicates the upper bit rate margin, units of %."
            ::= { hwGponOltOpticsModuleInfoEntry 18 }

        hwGponOltOpticsModuleInfoBrMin OBJECT-TYPE
            SYNTAX Integer32
            MAX-ACCESS read-only
            STATUS current
            DESCRIPTION
                "This object indicates the lower bit rate margin, units of %."
            ::= { hwGponOltOpticsModuleInfoEntry 19 }

        hwGponOltOpticsModuleInfoVendorSN OBJECT-TYPE
            SYNTAX OCTET STRING (SIZE (0..17))
            MAX-ACCESS read-only
            STATUS current
            DESCRIPTION
                "This object indicates the serial number provided by vendor (ASCII)."
            ::= { hwGponOltOpticsModuleInfoEntry 20 }

        hwGponOltOpticsModuleInfoDateCode OBJECT-TYPE
            SYNTAX OCTET STRING (SIZE (0..9))
            MAX-ACCESS read-only
            STATUS current
            DESCRIPTION
                "This object indicates manufacturing date code of the vendor (ASCII)."
            ::= { hwGponOltOpticsModuleInfoEntry 21 }

        hwGponOltOpticsModuleInfoDiagnosticMonitoringType OBJECT-TYPE
            SYNTAX Integer32
            MAX-ACCESS read-only
            STATUS current
            DESCRIPTION
                "Indicates which type of diagnostic monitoring is implemented.
                 bit                 Description of Diagnostic Monitoring Type
                  7                  Reserved
                  6                  Digital diagnostic monitoring
                  5                  Internally Calibrated
                  4                  Externally Calibrated
                  3                  Received power measurement type:(0 = OMA, 1 = Average)
                  2                  Address change required
                  1-0                Reserved
                "
            ::= { hwGponOltOpticsModuleInfoEntry 22 }

        hwGponOltOpticsModuleInfoEnhancedOptions OBJECT-TYPE
            SYNTAX Integer32
            MAX-ACCESS read-only
            STATUS current
            DESCRIPTION
                "Indicates which optional enhanced features are implemented.
                 bit                 Description of Enhanced Options
                  7                  Alarm/warning flags
                  6                  TX_DISABLE control and monitoring
                  5                  TX_FAULT monitoring
                  4                  RX_LOS monitoring
                  3                  RATE_SELECT control and monitoring
                  2                  Application Select control
                  1                  Rate Select control
                  0                  Reserved
                "
            ::= { hwGponOltOpticsModuleInfoEntry 23 }

        hwGponOltOpticsModuleInfoSFF8472Compliance OBJECT-TYPE
            SYNTAX INTEGER {
                undefined(1),
                includesRev93SFF8472(2),
                includesRev95SFF8472(3),
                includesRev102SFF8472(4),
                includesRev104SFF8472(5),
                includesRev110SFF8472(6),
                invalid(-1)
            }
            MAX-ACCESS read-only
            STATUS current
            DESCRIPTION
                "Indicates which revision of SFF-8472 the transceiver complies
                 Options:
                 1. undefined(1)               - Not included or undefined
                 2. includesRev93SFF8472(2)    - Includes functionality described in Rev 9.3
                 3. includesRev95SFF8472(3)    - Includes functionality described in Rev 9.5
                 4. includesRev102SFF8472(4)   - Includes functionality described in Rev 10.2
                 5. includesRev104SFF8472(5)   - Includes functionality described in Rev 10.4
                 6. includesRev110SFF8472(6)   - Includes functionality described in Rev 11.0
                 7. invalid(-1)                - Indicates that the query fails or no information is detected
                "
            ::= { hwGponOltOpticsModuleInfoEntry 24 }

        hwGponOltOpticsModuleInfoCcExt OBJECT-TYPE
            SYNTAX Integer32
            MAX-ACCESS read-only
            STATUS current
            DESCRIPTION
                "This object indicates the check code for the Extended ID Fields."
            ::= { hwGponOltOpticsModuleInfoEntry 25 }

        hwGponOltOpticsModuleInfoVendorSpecific OBJECT-TYPE
            SYNTAX OCTET STRING (SIZE (0..33))
            MAX-ACCESS read-only
            STATUS current
            DESCRIPTION
                "This object indicates the vendor Specific EEPROM."
            ::= { hwGponOltOpticsModuleInfoEntry 26 }

        hwGponOltOpticsModuleXponType OBJECT-TYPE
            SYNTAX INTEGER {
                unknown(1),
                gpon(2),
                epon(3),
                epon10g(4),
                gpon10g(5),
                wdmpon(6),
                hybridpon(7),
                gponepon(8),
                xgspon(9),
                gponandxgpon(10),
                gponandxgspon(11),
                twdmpon(15),
                invalid(-1)
            }
            MAX-ACCESS read-only
            STATUS current
            DESCRIPTION
                "This object indicates the type of the optical transceiver.
                 Options:
                 1. unknown(1)        - Unknown
                 2. gpon(2)           - GPON
                 3. epon(3)           - EPON
                 4. epon10g(4)        - 10G EPON
                 5. gpon10g(5)        - 10G GPON
                 6. wdmpon(6)         - WDM PON
                 7. hybridpon(7)      - Hybrid PON
                 8. gponepon(8)       - GPON/EPON
                 9. xgspon(9)         - XGS-PON
                 10.gponandxgpon(10)  - GPON+XG-PON
                 11.gponandxgspon(11) - GPON+XGS-PON
                 12.twdmpon(15)       - TWDM-PON
                 13.invalid(-1)       - Indicates that the query fails or no information is detected
                "
            ::= { hwGponOltOpticsModuleInfoEntry 27 }

        hwGponOltOpticsModuleXponSubType OBJECT-TYPE
            SYNTAX INTEGER {
                unknown(1),
                classbplus(101),
                classcplus(102),
                classb(103),
                classcplusplus(104),
                classd(105),
                px20(201),
                px20plus(202),
                px20plusplus(203),
                pr30(301),
                pr20(302),
                prx30(303),
                prx20(304),
                prx40(305),
                pr40(306),
                prx30e(307),
                prx40e(308),
                pr30plus(309),
                n2a(405),
                n2b(406),
                n1(407),
                e1(408),
                e2a(409),
                e2b(410),
                d1(411),
                d2(412),
                n2(413),
                e2(414),
                classbPlusAndPx20Plus(501),
                classbAndPx20(502),
                invalid(-1)
            }
            MAX-ACCESS read-only
            STATUS current
            DESCRIPTION
                "This object indicates the sub type of the optical transceiver.
                 Options:
                 1. unknown(1)                 - Unknown
                 2. classbplus(101)            - CLASS B+
                 3. classcplus(102)            - CLASS C+
                 4. classb(103)                - CLASS B
                 5. classcplusplus(104)        - CLASS C++
                 6. classcd(105)        - CLASS D
                 7. px20(201)                  - PX20
                 8. px20plus(202)              - PX20+
                 9. px20plusplus(203)          - PX20++
                 10. pr30(301)                  - PR30
                 11.pr20(302)                  - PR20
                 12.prx30(303)                 - PRX30
                 13.prx20(304)                 - PRX20
                 14.prx40(305)                 - PRX40
                 15.pr40(306)                  - PR40
                 16.prx30e(307)                - PRX30-E
                 17.prx40e(308)                - PRX40-E
                 18.pr30plus(309)              - PR30+
                 19.n2a(405)                   - N2a
                 20.n2b(406)                   - N2b
                 21.n1(407)                    - N1
                 22.e1(408)                    - E1
                 23.e2a(409)                   - E2a
                 24.e2b(410)                   - E2b
                 25.d1(411)                    - D1
                 26.d2(412)                    - D2
                 27.n2(413)                    - N2
                 28.e2(414)                    - E2
                 29.classbPlusAndPx20Plus(501) - GPON CLASS B+/EPON PX20+
                 30.classbAndPx20(502)         - GPON CLASS B/EPON PX20
                 31.invalid(-1)                - Indicates that the query fails or no information is detected
                "
            ::= { hwGponOltOpticsModuleInfoEntry 28 }

        hwGponOltOpticsModuleXponUsedType OBJECT-TYPE
            SYNTAX INTEGER {
                unknown(1),
                olt(2),
                ont(3),
                onu(4),
                catvtriplex(5),
                invalid(-1)
            }
            MAX-ACCESS read-only
            STATUS current
            DESCRIPTION
                "This object indicates the application scenario of the optical transceiver.
                 Options:
                 1. unknown(1)             - Unknown
                 2. olt(2)                 - OLT
                 3. ont(3)                 - ONT
                 4. onu(4)                 - ONU
                 5. catvtriplex(5)         - CATV TriPlex
                 6. invalid(-1)            - Indicates that the query fails or no information is detected
                "
            ::= { hwGponOltOpticsModuleInfoEntry 29 }

        hwGponOltOpticsModuleXponEncapsulationType OBJECT-TYPE
            SYNTAX INTEGER {
                unknown(1),
                sff2x5(2),
                sff2x10(3),
                sfp(4),
                xfp(5),
                lxfp(6),
                bosaonboard(7),
                sfpplus(8),
                invalid(-1)
            }
            MAX-ACCESS read-only
            STATUS current
            DESCRIPTION
                "This object indicates the encapsulation information about the optical transceiver.
                 Options:
                 1. unknown(1)              - Unknown
                 2. sff2x5(2)               - SFF 2x5
                 3. sff2x10(3)              - SFF 2x10
                 4. sfp(4)                  - SFP
                 5. xfp(5)                  - XFP
                 6. lxfp(6)                 - LXFP
                 7. bosaonboard(7)          - BOSA ON BOARD
                 8. sfpplus(8)              - SFP+
                 9. invalid(-1)             - Indicates that the query fails or no information is detected
                "
            ::= { hwGponOltOpticsModuleInfoEntry 30 }

          hwGponOltOpticsModuleInfoPartNum OBJECT-TYPE
            SYNTAX OCTET STRING (SIZE (0..16))
            MAX-ACCESS read-only
            STATUS current
            DESCRIPTION
               "Indicate the part number of a optical module provided by Huawei."
          ::= { hwGponOltOpticsModuleInfoEntry 31 }

    -- Table : hwGponOltOpticsDdmInfoTable
        hwGponOltOpticsDdmInfoTable OBJECT-TYPE
            SYNTAX     SEQUENCE OF HwGponOltOpticsDdmInfoEntry
            MAX-ACCESS not-accessible
            STATUS     current
            DESCRIPTION
                "This table is used to query the diagnostic information about the optical transceiver of the GPON port.
                 The index of this table is ifIndex.
                "
            ::= { hwXponDeviceControlObjects 23 }

        hwGponOltOpticsDdmInfoEntry OBJECT-TYPE
            SYNTAX     HwGponOltOpticsDdmInfoEntry
            MAX-ACCESS not-accessible
            STATUS     current
            DESCRIPTION
                "This table is used to query the diagnostic information about the optical transceiver of the GPON port.
                 The index of this entry is ifIndex.
                "
            INDEX       { ifIndex }
            ::= { hwGponOltOpticsDdmInfoTable 1 }

        HwGponOltOpticsDdmInfoEntry ::=
            SEQUENCE {
                hwGponOltOpticsDdmInfoTemperature     Integer32,
                hwGponOltOpticsDdmInfoSupplyVoltage   Integer32,
                hwGponOltOpticsDdmInfoTxBiasCurrent   Integer32,
                hwGponOltOpticsDdmInfoTxPower         Integer32,
                hwGponOltOpticsDdmInfoRxPower         Integer32
            }

        hwGponOltOpticsDdmInfoTemperature OBJECT-TYPE
            SYNTAX Integer32
            MAX-ACCESS read-only
            STATUS current
            DESCRIPTION
                "This object indicates the optics temperature, units of C(centigrade)."
            ::= { hwGponOltOpticsDdmInfoEntry 1 }

        hwGponOltOpticsDdmInfoSupplyVoltage OBJECT-TYPE
            SYNTAX Integer32
            MAX-ACCESS read-only
            STATUS current
            DESCRIPTION
                "This object indicates the supply voltage, units of 0.01V."
            ::= { hwGponOltOpticsDdmInfoEntry 2 }

        hwGponOltOpticsDdmInfoTxBiasCurrent OBJECT-TYPE
            SYNTAX Integer32
            MAX-ACCESS read-only
            STATUS current
            DESCRIPTION
                "This object indicates the optics current, units of mA."
            ::= { hwGponOltOpticsDdmInfoEntry 3 }

        hwGponOltOpticsDdmInfoTxPower OBJECT-TYPE
            SYNTAX Integer32
            MAX-ACCESS read-only
            STATUS current
            DESCRIPTION
                "This object indicates the optics send power, units of 0.01dBm."
            ::= { hwGponOltOpticsDdmInfoEntry 4 }

        hwGponOltOpticsDdmInfoRxPower OBJECT-TYPE
            SYNTAX Integer32
            MAX-ACCESS read-only
            STATUS current
            DESCRIPTION
                "This object indicates the optics received power, units of 0.01dBm."
            ::= { hwGponOltOpticsDdmInfoEntry 5 }

    -- Table : hwEponOltXFPOpticsModuleInfoTable
        hwEponOltXFPOpticsModuleInfoTable OBJECT-TYPE
            SYNTAX     SEQUENCE OF HwEponOltXFPOpticsModuleInfoEntry
            MAX-ACCESS not-accessible
            STATUS     current
            DESCRIPTION
                "This table is used to query the optics module informationof the 10G EPON port.
                 The index of this table is ifIndex.
                "
            ::= { hwXponDeviceControlObjects 24 }

        hwEponOltXFPOpticsModuleInfoEntry OBJECT-TYPE
            SYNTAX     HwEponOltXFPOpticsModuleInfoEntry
            MAX-ACCESS not-accessible
            STATUS     current
            DESCRIPTION
                "This table is used to query the optics module informationof the 10G EPON port.
                 The index of this entry is ifIndex.
                "
            INDEX       { ifIndex }
            ::= { hwEponOltXFPOpticsModuleInfoTable 1 }

        HwEponOltXFPOpticsModuleInfoEntry ::=
            SEQUENCE {
                hwEponOltXFPOpticsModuleInfoIdentifier                    INTEGER,
                hwEponOltXFPOpticsModuleInfoExtCLEICode                   INTEGER,
                hwEponOltXFPOpticsModuleInfoExtTXRefClock                 INTEGER,
                hwEponOltXFPOpticsModuleInfoExtCDRFunc                    INTEGER,
                hwEponOltXFPOpticsModuleInfoExtPowerLevel                 INTEGER,
                hwEponOltXFPOpticsModuleInfoConnector                     INTEGER,
                hwEponOltXFPOpticsModuleInfoEncodingRZ                    INTEGER,
                hwEponOltXFPOpticsModuleInfoEncodingNRZ                   INTEGER,
                hwEponOltXFPOpticsModuleInfoEncoding8B10B                 INTEGER,
                hwEponOltXFPOpticsModuleInfoEncoding64B                   INTEGER,
                hwEponOltXFPOpticsModuleInfoBrMin                         Integer32,
                hwEponOltXFPOpticsModuleInfoBrMax                         Integer32,
                hwEponOltXFPOpticsModuleInfoSupportLenSMF                 Integer32,
                hwEponOltXFPOpticsModuleInfoSupportLenE50um               Integer32,
                hwEponOltXFPOpticsModuleInfoSupportLen50um                Integer32,
                hwEponOltXFPOpticsModuleInfoSupportLen62p5um              Integer32,
                hwEponOltXFPOpticsModuleInfoSupportLenCopper              Integer32,
                hwEponOltXFPOpticsModuleInfoTransmitterSupport            INTEGER,
                hwEponOltXFPOpticsModuleInfoDetector                      INTEGER,
                hwEponOltXFPOpticsModuleInfoWavelengthControl             INTEGER,
                hwEponOltXFPOpticsModuleInfoCooledTransmitterDevice       INTEGER,
                hwEponOltXFPOpticsModuleInfoTransmitterTechnologySupport  INTEGER,
                hwEponOltXFPOpticsModuleInfoVendorName                    OCTET STRING,
                hwEponOltXFPOpticsModuleInfoSupportXFIMode                INTEGER,
                hwEponOltXFPOpticsModuleInfoSupportLinesideMode           INTEGER,
                hwEponOltXFPOpticsModuleInfoMaxBitRateSupportedByCDR      INTEGER,
                hwEponOltXFPOpticsModuleInfoVendorOUI                     Integer32,
                hwEponOltXFPOpticsModuleInfoVendorPN                      OCTET STRING,
                hwEponOltXFPOpticsModuleInfoVendorRev                     OCTET STRING,
                hwEponOltXFPOpticsModuleInfoF51                           Integer32,
                hwEponOltXFPOpticsModuleInfoWaveTolerance                 Integer32,
                hwEponOltXFPOpticsModuleInfoMaxCaseTemperature            Integer32,
                hwEponOltXFPOpticsModuleInfoCcbase                        Integer32,
                hwEponOltXFPOpticsModuleInfoMaxDissipation                Integer32,
                hwEponOltXFPOpticsModuleInfoMaxDissipationPowerDownMode   Integer32,
                hwEponOltXFPOpticsModuleInfoMaximum5P0VSupply             Integer32,
                hwEponOltXFPOpticsModuleInfoMaximum3P3VSupply             Integer32,
                hwEponOltXFPOpticsModuleInfoMaximum1P8VSupply             Integer32,
                hwEponOltXFPOpticsModuleInfoMaximum5P2VSupply             Integer32,
                hwEponOltXFPOpticsModuleInfoVendorSN                      OCTET STRING,
                hwEponOltXFPOpticsModuleInfoDateCode                      OCTET STRING,
                hwEponOltXFPOpticsModuleInfoDiagnoMonitorPowerMeasure     INTEGER,
                hwEponOltXFPOpticsModuleInfoDiagnoMonitorTypeFECBER       INTEGER,
                hwEponOltXFPOpticsModuleInfoEnhancedOptions               Integer32,
                hwEponOltXFPOpticsModuleInfoAuxInputOne                   INTEGER,
                hwEponOltXFPOpticsModuleInfoAuxInputTwo                   INTEGER,
                hwEponOltXFPOpticsModuleInfoCCEXT                         Integer32,
                hwEponOltXFPOpticsModuleInfoWavelengthFor2d5G             Integer32,
                hwEponOltXFPOpticsModuleInfoWavelengthFor1d25G            Integer32,
                hwEponOltXFPOpticsModuleInfoVendorSpecific                OCTET STRING,
                hwEponOltXFPOpticsModuleXponType                          INTEGER,
                hwEponOltXFPOpticsModuleXponSubType                       INTEGER,
                hwEponOltXFPOpticsModuleXponUsedType                      INTEGER,
                hwEponOltXFPOpticsModuleXponEncapsulationType             INTEGER,
                hwEponOltXFPOpticsModuleXponTemperatureLevel              INTEGER,
                hwEponOltXFPOpticsModuleXponOPMprecision                  INTEGER
            }

        hwEponOltXFPOpticsModuleInfoIdentifier OBJECT-TYPE
            SYNTAX INTEGER {
                 invalid(-1),
                 unknown(0),
                 gbic(1),
                 solderedToMotherboard(2),
                 sfp(3),
                 pin300XBI(4),
                 xenpak(5),
                 xfp(6),
                 xff(7),
                 xfep(8),
                 xpak(9),
                 x2(10)
            }
            MAX-ACCESS read-only
            STATUS current
            DESCRIPTION
                "This object indicates the type of serial transceiver.
                 Options:
                 1. unknown(0)                      - Unknown or unspecified
                 2. gbic(1)                         - GBIC
                 3. solderedToMotherboard(2)        - Module soldered to motherboard
                 4. sfp(3)                          - SFP
                 5. pin300XBI(4)                    - PIN300XBI
                 6. xenpak(5)                       - XENPAK
                 7. xfp(6)                          - XFP
                 8. xff(7)                          - XFF
                 9. xfep(8)                         - XFEP
                 10. xpak(9)                        - XPAK
                 11. x2(10)                         - X2
                 12. invalid(-1)                    - Indicates that the query fails or no information is detected
                "
            ::= { hwEponOltXFPOpticsModuleInfoEntry 1 }

        hwEponOltXFPOpticsModuleInfoExtCLEICode OBJECT-TYPE
            SYNTAX INTEGER {
                nonExtCLEICode(0),
                extCLEICode(1),
                invalid(-1)
            }
            MAX-ACCESS read-only
            STATUS current
            DESCRIPTION
                "This object indicates the extclei code.
                 Options:
                 1. nonExtCLEICode(0)                - No CLEI code present in Table 02h
                 2. extCLEICode(1)                   - CLEI code present in Table 02h
                 3. invalid(-1)                      - Indicates that the query fails or no information is detected
                "
            ::= { hwEponOltXFPOpticsModuleInfoEntry 2 }

        hwEponOltXFPOpticsModuleInfoExtTXRefClock OBJECT-TYPE
            SYNTAX INTEGER {
                nonExtTXRefClock(0),
                extTXRefClock(1),
                invalid(-1)
            }
            MAX-ACCESS read-only
            STATUS current
            DESCRIPTION
                "This object indicates the txref clock.
                 Options:
                 1. nonExtTXRefClock(0)              - TX Ref Clock Input Not Required
                 2. extTXRefClock(1)                 - TX Ref Clock Input Required
                 3. invalid(-1)                      - Indicates that the query fails or no information is detected
                "
            ::= { hwEponOltXFPOpticsModuleInfoEntry 3 }

        hwEponOltXFPOpticsModuleInfoExtCDRFunc OBJECT-TYPE
            SYNTAX INTEGER {
                nonExtCDRFunc(0),
                extCDRFunc(1),
                invalid(-1)
            }
            MAX-ACCESS read-only
            STATUS current
            DESCRIPTION
                "This object indicates the CDR function.
                 Options:
                 1. nonExtCDRFunc(0)               - Non-CDR version of XFP
                 2. extCDRFunc(1)                  - Module with CDR function
                 3. invalid(-1)                    - Indicates that the query fails or no information is detected
                "
            ::= { hwEponOltXFPOpticsModuleInfoEntry 4 }

        hwEponOltXFPOpticsModuleInfoExtPowerLevel OBJECT-TYPE
            SYNTAX INTEGER {
                extPowerLevel1(0),
                extPowerLevel2(1),
                extPowerLevel3(2),
                extPowerLevel4(3),
                invalid(-1)
            }
            MAX-ACCESS read-only
            STATUS current
            DESCRIPTION
                "This object indicates the power level.
                 Options:
                 1. extPowerLevel1(0)           - Power Level 1 Module (1.5 W max. power dissipation.)
                 2. extPowerLevel2(1)           - Power Level 2 Module (2.5W Max)
                 3. extPowerLevel3(2)           - Power Level 3 Module (3.5W max. power dissipation.)
                 4. extPowerLevel4(3)           - Power Level 4 Module (>3.5W max. power dissipation.)
                 5. invalid(-1)                 - Indicates that the query fails or no information is detected
                "
            ::= { hwEponOltXFPOpticsModuleInfoEntry 5 }

        hwEponOltXFPOpticsModuleInfoConnector OBJECT-TYPE
            SYNTAX INTEGER {
                unknown(1),
                sc(2),
                copperConnector1(3),
                copperConnector2(4),
                bnctnc(5),
                coaxialHeaders(6),
                fiberJack(7),
                lc(8),
                mtrj(9),
                mu(10),
                sg(11),
                opticalPigtail(12),
                hssdcII(13),
                copperPigtail(14),
                invalid(-1)
            }
            MAX-ACCESS read-only
            STATUS current
            DESCRIPTION
                "This object indicates the code for connector type.
                 Options:
                 1.  unknown(1)              - Unknown
                 2.  sc(2)                   - SC
                 3.  copperConnector1(3)     - Fibre Channel Style 1 copper connector
                 4.  copperConnector2(4)     - Fibre Channel Style 2 copper connector
                 5.  bnctnc(5)               - BNC/TNC
                 6.  coaxialHeaders(6)       - Fibre Channel coaxial headers
                 7.  fiberJack(7)            - FiberJack
                 8.  lc(8)                   - LC
                 9.  mtrj(9)                 - MT-RJ
                 10. mu(10)                  - MU
                 11. sg(11)                  - SG
                 12. opticalPigtail(12)      - Optical pigtail
                 13. hssdcII(13)             - HSSDC II
                 14. copperPigtail(14)       - Copper Pigtail
                 15. invalid(-1)             - Indicates that the query fails or no information is detected
                "
            ::= { hwEponOltXFPOpticsModuleInfoEntry 6 }

        hwEponOltXFPOpticsModuleInfoEncodingRZ OBJECT-TYPE
            SYNTAX INTEGER {
                nonEncodingRZ(0),
                encodingRZ(1),
                invalid(-1)
            }
            MAX-ACCESS read-only
            STATUS current
            DESCRIPTION
                "This object indicates the EncodingRZ.
                 Options:
                 1. nonEncodingRZ(0)         - Encoding Don't Support RZ
                 2. encodingRZ(1)            - Encoding Support RZ
                 3. invalid(-1)              - Indicates that the query fails or no information is detected
                "
            ::= { hwEponOltXFPOpticsModuleInfoEntry 7 }

        hwEponOltXFPOpticsModuleInfoEncodingNRZ OBJECT-TYPE
            SYNTAX INTEGER {
                nonEncodingNRZ(0),
                encodingNRZ(1),
                invalid(-1)
            }
            MAX-ACCESS read-only
            STATUS current
            DESCRIPTION
                "This object indicates the EncodingNRZ.
                 Options:
                 1. nonEncodingNRZ(0)       - Encoding Don't Support NRZ
                 2. encodingNRZ(1)          - Encoding Support NRZ
                 3. invalid(-1)             - Indicates that the query fails or no information is detected
                "
            ::= { hwEponOltXFPOpticsModuleInfoEntry 8 }

        hwEponOltXFPOpticsModuleInfoEncoding8B10B OBJECT-TYPE
            SYNTAX INTEGER {
                nonEncoding8B10B(0),
                encoding8B10B(1),
                invalid(-1)
            }
            MAX-ACCESS read-only
            STATUS current
            DESCRIPTION
                "This object indicates the Encoding8B10B.
                 Options:
                 1. nonEncoding8B10B(0)      - Encoding Don't Support 8B10B
                 2. encoding8B10B(1)         - Encoding Support 8B10B
                 3. invalid(-1)              - Indicates that the query fails or no information is detected
                "
            ::= { hwEponOltXFPOpticsModuleInfoEntry 9 }

        hwEponOltXFPOpticsModuleInfoEncoding64B OBJECT-TYPE
            SYNTAX INTEGER {
                nonEncoding64B(0),
                encoding64B(1),
                invalid(-1)
            }
            MAX-ACCESS read-only
            STATUS current
            DESCRIPTION
                "This object indicates the Encoding64B.
                 Options:
                 1. nonEncoding64B(0)      - Encoding Don't Support 64B/66B
                 2. encoding64B(1)         - Encoding Support 64B/66B
                 3. invalid(-1)            - Indicates that the query fails or no information is detected
                "
            ::= { hwEponOltXFPOpticsModuleInfoEntry 10 }

        hwEponOltXFPOpticsModuleInfoBrMin OBJECT-TYPE
            SYNTAX Integer32
            MAX-ACCESS read-only
            STATUS current
            DESCRIPTION
                "Minimum bit rate, units of 100 MBits/s."
            ::= { hwEponOltXFPOpticsModuleInfoEntry 11 }

        hwEponOltXFPOpticsModuleInfoBrMax OBJECT-TYPE
            SYNTAX Integer32
            MAX-ACCESS read-only
            STATUS current
            DESCRIPTION
                "Maximum bit rate, units of 100 MBits/s."
            ::= { hwEponOltXFPOpticsModuleInfoEntry 12 }

        hwEponOltXFPOpticsModuleInfoSupportLenSMF OBJECT-TYPE
            SYNTAX Integer32
            MAX-ACCESS read-only
            STATUS current
            DESCRIPTION
                "Link length supported for SMF fiber in km."
            ::= { hwEponOltXFPOpticsModuleInfoEntry 13 }

        hwEponOltXFPOpticsModuleInfoSupportLenE50um OBJECT-TYPE
            SYNTAX Integer32
            MAX-ACCESS read-only
            STATUS current
            DESCRIPTION
                "Link length supported for EBW 50/125 um fiber, units of 2 m."
            ::= { hwEponOltXFPOpticsModuleInfoEntry 14 }

        hwEponOltXFPOpticsModuleInfoSupportLen50um OBJECT-TYPE
            SYNTAX Integer32
            MAX-ACCESS read-only
            STATUS current
            DESCRIPTION
                "Link length supported for 50/125 um fiber, units of 1 m."
            ::= { hwEponOltXFPOpticsModuleInfoEntry 15 }

        hwEponOltXFPOpticsModuleInfoSupportLen62p5um OBJECT-TYPE
            SYNTAX Integer32
            MAX-ACCESS read-only
            STATUS current
            DESCRIPTION
                "Link length supported for 62.5/125 um fiber, units of 1 m."
            ::= { hwEponOltXFPOpticsModuleInfoEntry 16 }

        hwEponOltXFPOpticsModuleInfoSupportLenCopper OBJECT-TYPE
            SYNTAX Integer32
            MAX-ACCESS read-only
            STATUS current
            DESCRIPTION
                "Link length supported for copper, units of 1m."
            ::= { hwEponOltXFPOpticsModuleInfoEntry 17 }

        hwEponOltXFPOpticsModuleInfoTransmitterSupport OBJECT-TYPE
            SYNTAX INTEGER {
                nonTunable(0),
                tunable(1),
                invalid(-1)
            }
            MAX-ACCESS read-only
            STATUS current
            DESCRIPTION
                "This object indicates the transmitter support.
                 Options:
                 1. nonTunable(0)      - Transmitter Not Support Tunable
                 2. tunable(1)         - Transmitter Support Tunable
                 3. invalid(-1)        - Indicates that the query fails or no information is detected
                "
            ::= { hwEponOltXFPOpticsModuleInfoEntry 18 }

        hwEponOltXFPOpticsModuleInfoDetector OBJECT-TYPE
            SYNTAX INTEGER {
                pin(0),
                apd(1),
                invalid(-1)
            }
            MAX-ACCESS read-only
            STATUS current
            DESCRIPTION
                "This object indicates the transmitter support.
                 Options:
                 1. pin(0)             - PIN
                 2. apd(1)             - APD
                 3. invalid(-1)        - Indicates that the query fails or no information is detected
                "
            ::= { hwEponOltXFPOpticsModuleInfoEntry 19 }

        hwEponOltXFPOpticsModuleInfoWavelengthControl OBJECT-TYPE
            SYNTAX INTEGER {
                nonSupport(0),
                support(1),
                invalid(-1)
            }
            MAX-ACCESS read-only
            STATUS current
            DESCRIPTION
                "This object indicates the wavelength control.
                 Options:
                 1. nonSupport(0)       - Wavelength control NonSupport
                 2. support(1)          - Wavelength control Support
                 3. invalid(-1)         - Indicates that the query fails or no information is detected
                "
            ::= { hwEponOltXFPOpticsModuleInfoEntry 20 }

        hwEponOltXFPOpticsModuleInfoCooledTransmitterDevice OBJECT-TYPE
            SYNTAX INTEGER {
                nonSupport(0),
                support(1),
                invalid(-1)
            }
            MAX-ACCESS read-only
            STATUS current
            DESCRIPTION
                "This object indicates the cooled transmitter device.
                 Options:
                 1. nonSupport(0)       - Cooled transmitter device NonSupport
                 2. support(1)          - Cooled transmitter device Support
                 3. invalid(-1)         - Indicates that the query fails or no information is detected
                "
            ::= { hwEponOltXFPOpticsModuleInfoEntry 21 }

        hwEponOltXFPOpticsModuleInfoTransmitterTechnologySupport OBJECT-TYPE
            SYNTAX INTEGER {
                 vCSEL850(0),
                 vCSEL1310(1),
                 vCSEL1550(2),
                 fP1310(3),
                 dFB1310(4),
                 dFB1550(5),
                 eML1310(6),
                 eML1550(7),
                 cOPPER(8),
                 invalid(-1)
            }
            MAX-ACCESS read-only
            STATUS current
            DESCRIPTION
                "This object indicates the transmitter technology support.
                 Options:
                 1. vCSEL850(0)          - vCSEL850
                 2. vCSEL1310(1)         - vCSEL1310
                 3. vCSEL1550(2)         - vCSEL1550
                 4. fP1310(3)            - fP1310
                 5. dFB1310(4)           - dFB1310
                 6. dFB1550(5)           - dFB1550
                 7. eML1310(6)           - eML1310
                 8. eML1550(7)           - eML1550
                 9. cOPPER(8)            - cOPPER
                 10. invalid(-1)         - Indicates that the query fails or no information is detected
                "
            ::= { hwEponOltXFPOpticsModuleInfoEntry 22 }

        hwEponOltXFPOpticsModuleInfoVendorName OBJECT-TYPE
            SYNTAX OCTET STRING(SIZE (0..17))
            MAX-ACCESS read-only
            STATUS current
            DESCRIPTION
                "This object indicates the XFP vendor name (ASCII)."
            ::= { hwEponOltXFPOpticsModuleInfoEntry 23 }

        hwEponOltXFPOpticsModuleInfoSupportXFIMode OBJECT-TYPE
            SYNTAX INTEGER {
                nonSupportXFIMode(0),
                supportXFIMode(1),
                invalid(-1)
            }
            MAX-ACCESS read-only
            STATUS current
            DESCRIPTION
                "This object indicates the XFI mode.
                 Options:
                 1. nonSupportXFIMode(0)      - Don't Support XFI Loopback Mode
                 2. supportXFIMode(1)         - XFI Loopback Mode Supported
                 3. invalid(-1)               - Indicates that the query fails or no information is detected
                "
            ::= { hwEponOltXFPOpticsModuleInfoEntry 24 }

        hwEponOltXFPOpticsModuleInfoSupportLinesideMode OBJECT-TYPE
            SYNTAX INTEGER {
                nonSupportLinesideMode(0),
                supportLinesideMode(1),
                invalid(-1)
            }
            MAX-ACCESS read-only
            STATUS current
            DESCRIPTION
                "This object indicates the XFI mode.
                 Options:
                 1. nonSupportLinesideMode(0)     - Don't Support Lineside Loopback Mode
                 2. supportLinesideMode(1)        - Lineside Loopback Mode Supported
                 3. invalid(-1)                   - Indicates that the query fails or no information is detected
                "
            ::= { hwEponOltXFPOpticsModuleInfoEntry 25 }

        hwEponOltXFPOpticsModuleInfoMaxBitRateSupportedByCDR OBJECT-TYPE
            SYNTAX INTEGER {
                 cDRNosupport(0),
                 maxBitRateSupportedByCDR11p1(1),
                 maxBitRateSupportedByCDR10p7(3),
                 maxBitRateSupportedByCDR10p5(7),
                 maxBitRateSupportedByCDR10p3(15),
                 maxBitRateSupportedByCDR9p95(31),
                 invalid(-1)
            }
            MAX-ACCESS read-only
            STATUS current
            DESCRIPTION
                "This object indicates the max bit rate by CDR.
                 Options:
                 1. cDRNosupport(0)                       - CDR not support
                 2. maxBitRateSupportedByCDR11p1(1)       - CDR support for 11.1 Gb/s
                 3. maxBitRateSupportedByCDR10p7(3)       - CDR support for 10.7 Gb/s
                 4. maxBitRateSupportedByCDR10p5(7)       - CDR support for 10.5 Gb/s
                 5. maxBitRateSupportedByCDR10p3(15)      - CDR support for 10.3 Gb/s
                 6. maxBitRateSupportedByCDR9p95(31)      - CDR support for 9.95 Gb/s
                 7. invalid(-1)                           - Indicates that the query fails or no information is detected
                "
            ::= { hwEponOltXFPOpticsModuleInfoEntry 26 }

        hwEponOltXFPOpticsModuleInfoVendorOUI OBJECT-TYPE
            SYNTAX Integer32
            MAX-ACCESS read-only
            STATUS current
            DESCRIPTION
                "This object indicates the Vendor OUI."
            ::= { hwEponOltXFPOpticsModuleInfoEntry 27 }

        hwEponOltXFPOpticsModuleInfoVendorPN OBJECT-TYPE
            SYNTAX OCTET STRING
            MAX-ACCESS read-only
            STATUS current
            DESCRIPTION
                "This object indicates the Vendor PN."
            ::= { hwEponOltXFPOpticsModuleInfoEntry 28 }

        hwEponOltXFPOpticsModuleInfoVendorRev OBJECT-TYPE
            SYNTAX OCTET STRING
            MAX-ACCESS read-only
            STATUS current
            DESCRIPTION
                "This object indicates the Vendor rev."
            ::= { hwEponOltXFPOpticsModuleInfoEntry 29 }

        hwEponOltXFPOpticsModuleInfoF51 OBJECT-TYPE
            SYNTAX Integer32
            MAX-ACCESS read-only
            STATUS current
            DESCRIPTION
                "This object indicates the Wavelength."
            ::= { hwEponOltXFPOpticsModuleInfoEntry 30 }

        hwEponOltXFPOpticsModuleInfoWaveTolerance OBJECT-TYPE
            SYNTAX Integer32
            MAX-ACCESS read-only
            STATUS current
            DESCRIPTION
                "This object indicates the WaveTolerance."
            ::= { hwEponOltXFPOpticsModuleInfoEntry 31 }

        hwEponOltXFPOpticsModuleInfoMaxCaseTemperature OBJECT-TYPE
            SYNTAX Integer32
            MAX-ACCESS read-only
            STATUS current
            DESCRIPTION
                "This object indicates the Maximum Case Temperature in Degrees C."
            ::= { hwEponOltXFPOpticsModuleInfoEntry 32 }

        hwEponOltXFPOpticsModuleInfoCcbase OBJECT-TYPE
            SYNTAX Integer32
            MAX-ACCESS read-only
            STATUS current
            DESCRIPTION
                "This object indicates the Cc_base."
            ::= { hwEponOltXFPOpticsModuleInfoEntry 33 }

        hwEponOltXFPOpticsModuleInfoMaxDissipation OBJECT-TYPE
            SYNTAX Integer32
            MAX-ACCESS read-only
            STATUS current
            DESCRIPTION
                "This object indicates the Maximum Power Dissipation."
            ::= { hwEponOltXFPOpticsModuleInfoEntry 34 }

        hwEponOltXFPOpticsModuleInfoMaxDissipationPowerDownMode OBJECT-TYPE
            SYNTAX Integer32
            MAX-ACCESS read-only
            STATUS current
            DESCRIPTION
                "This object indicates the Maximum Total Power Dissipation in Power Down Mode."
            ::= { hwEponOltXFPOpticsModuleInfoEntry 35 }

        hwEponOltXFPOpticsModuleInfoMaximum5P0VSupply OBJECT-TYPE
            SYNTAX Integer32
            MAX-ACCESS read-only
            STATUS current
            DESCRIPTION
                "This object indicates the Maximum current required by +5V Supply."
            ::= { hwEponOltXFPOpticsModuleInfoEntry 36 }

        hwEponOltXFPOpticsModuleInfoMaximum3P3VSupply OBJECT-TYPE
            SYNTAX Integer32
            MAX-ACCESS read-only
            STATUS current
            DESCRIPTION
                "This object indicates the Maximum current required by +3.3V Supply."
            ::= { hwEponOltXFPOpticsModuleInfoEntry 37 }

        hwEponOltXFPOpticsModuleInfoMaximum1P8VSupply OBJECT-TYPE
            SYNTAX Integer32
            MAX-ACCESS read-only
            STATUS current
            DESCRIPTION
                "This object indicates the Maximum current required by +1.8V Supply."
            ::= { hwEponOltXFPOpticsModuleInfoEntry 38 }

        hwEponOltXFPOpticsModuleInfoMaximum5P2VSupply OBJECT-TYPE
            SYNTAX Integer32
            MAX-ACCESS read-only
            STATUS current
            DESCRIPTION
                "This object indicates the Maximum current required by -5.2V Supply."
            ::= { hwEponOltXFPOpticsModuleInfoEntry 39 }

        hwEponOltXFPOpticsModuleInfoVendorSN OBJECT-TYPE
            SYNTAX OCTET STRING
            MAX-ACCESS read-only
            STATUS current
            DESCRIPTION
                "This object indicates the Vendor SN."
            ::= { hwEponOltXFPOpticsModuleInfoEntry 40 }

        hwEponOltXFPOpticsModuleInfoDateCode OBJECT-TYPE
            SYNTAX OCTET STRING
            MAX-ACCESS read-only
            STATUS current
            DESCRIPTION
                "This object indicates the Date code."
            ::= { hwEponOltXFPOpticsModuleInfoEntry 41 }

        hwEponOltXFPOpticsModuleInfoDiagnoMonitorPowerMeasure  OBJECT-TYPE
            SYNTAX INTEGER {
                  supportOMA(0),
                  supportAveragePower(1),
                  invalid(-1)
            }
            MAX-ACCESS read-only
            STATUS current
            DESCRIPTION
                "This object indicates the Received power measurement type.
                 Options:
                 1. supportOMA(0)              - OMA
                 2. supportAveragePower(1)     - Average Power
                 3. invalid(-1)                - Indicates that the query fails or no information is detected
                "
            ::= { hwEponOltXFPOpticsModuleInfoEntry 42 }

        hwEponOltXFPOpticsModuleInfoDiagnoMonitorTypeFECBER OBJECT-TYPE
            SYNTAX INTEGER {
                  nonSupportBER(0),
                  supportBER(1),
                  invalid(-1)
            }
            MAX-ACCESS read-only
            STATUS current
            DESCRIPTION
                "This object indicates the Module Respond to FEC BER.
                 Options:
                 1. nonSupportBER(0)        - No BER Support
                 2. supportBER(1)           - BER Support
                 3. invalid(-1)             - Indicates that the query fails or no information is detected
                "
            ::= { hwEponOltXFPOpticsModuleInfoEntry 43 }

        hwEponOltXFPOpticsModuleInfoEnhancedOptions OBJECT-TYPE
            SYNTAX Integer32
            MAX-ACCESS read-only
            STATUS current
            DESCRIPTION
                "Indicates which optional enhanced features are implemented.
                 bit                Description of Enhanced Options
                  7                  Module Supports Optional VPS
                  6                  Optional Soft TX_DISABLE implemented
                  5                  Optional Soft P_down implemented
                  4                  Supports VPS LV regulator mode
                  3                  Supports VPS bypassed regulator Mode
                  2                  Active FEC control functions implemented
                  1                  Wavelength tunability implemented
                  0                  Optional CMU Support Mode
                  invalid(-1)        - Indicates that the query fails or no information is detected
                "
            ::= { hwEponOltXFPOpticsModuleInfoEntry 44 }

        hwEponOltXFPOpticsModuleInfoAuxInputOne OBJECT-TYPE
            SYNTAX INTEGER {
                 auxInputType1(0),
                 auxInputType2(1),
                 auxInputType3(2),
                 auxInputType4(3),
                 auxInputType5(4),
                 auxInputType6(5),
                 auxInputType7(6),
                 auxInputType8(7),
                 auxInputType9(8),
                 auxInputType10(9),
                 auxInputType11(10),
                 auxInputType14(13),
                 auxInputType15(14),
                 auxInputType16(15),
                 invalid(-1)
            }
            MAX-ACCESS read-only
            STATUS current
            DESCRIPTION
                "This object indicates the optics Aux Input One.
                 Options:
                 1. auxInputType1(0)          - Auxiliary monitoring not implemented
                 2. auxInputType2(1)          - APD Bias Voltage
                 3. auxInputType3(2)          - 1G Tx Bias Current
                 4. auxInputType4(3)          - TEC Current (mA)
                 5. auxInputType5(4)          - Laser Temperature
                 6. auxInputType6(5)          - Laser Wavelength
                 7. auxInputType7(6)          - +5V Supply Voltage
                 8. auxInputType8(7)          - 1G Tx Power
                 9. auxInputType9(8)          - +1.8V Supply Voltage
                 10. auxInputType10(9)        - -5.2V Supply Voltage
                 11. auxInputType11(10)       - +5V Supply Current
                 12. auxInputType14(13)       - +3.3V Supply Current
                 13. auxInputType15(14)       - +1.8V Supply Current
                 14. auxInputType16(15)       - -5.2V Supply Current
                 15. invalid(-1)              - Indicates that the query fails or no information is detected
                "
            ::= { hwEponOltXFPOpticsModuleInfoEntry 45 }

        hwEponOltXFPOpticsModuleInfoAuxInputTwo OBJECT-TYPE
            SYNTAX INTEGER {
                 auxInputType1(0),
                 auxInputType2(1),
                 auxInputType3(2),
                 auxInputType4(3),
                 auxInputType5(4),
                 auxInputType6(5),
                 auxInputType7(6),
                 auxInputType8(7),
                 auxInputType9(8),
                 auxInputType10(9),
                 auxInputType11(10),
                 auxInputType14(13),
                 auxInputType15(14),
                 auxInputType16(15),
                 invalid(-1)
            }
            MAX-ACCESS read-only
            STATUS current
            DESCRIPTION
                "This object indicates the optics Aux Input two.
                 Options:
                 1. auxInputType1(0)          - Auxiliary monitoring not implemented
                 2. auxInputType2(1)          - APD Bias Voltage
                 3. auxInputType3(2)          - 1G Tx Bias Current
                 4. auxInputType4(3)          - TEC Current (mA)
                 5. auxInputType5(4)          - Laser Temperature
                 6. auxInputType6(5)          - Laser Wavelength
                 7. auxInputType7(6)          - +5V Supply Voltage
                 8. auxInputType8(7)          - 1G Tx Power
                 9. auxInputType9(8)          - +1.8V Supply Voltage
                 10. auxInputType10(9)        - -5.2V Supply Voltage
                 11. auxInputType11(10)       - +5V Supply Current
                 12. auxInputType14(13)       - +3.3V Supply Current
                 13. auxInputType15(14)       - +1.8V Supply Current
                 14. auxInputType16(15)       - -5.2V Supply Current
                 15. invalid(-1)              - Indicates that the query fails or no information is detected
                "
            ::= { hwEponOltXFPOpticsModuleInfoEntry 46 }

        hwEponOltXFPOpticsModuleInfoCCEXT OBJECT-TYPE
            SYNTAX Integer32
            MAX-ACCESS read-only
            STATUS current
            DESCRIPTION
                "This object indicates the CC_EXT ."
            ::= { hwEponOltXFPOpticsModuleInfoEntry 47 }

        hwEponOltXFPOpticsModuleInfoWavelengthFor2d5G OBJECT-TYPE
            SYNTAX Integer32
            MAX-ACCESS read-only
            STATUS current
            DESCRIPTION
                "This object indicates the Wavelength for 2.5G."
            ::= { hwEponOltXFPOpticsModuleInfoEntry 48 }

        hwEponOltXFPOpticsModuleInfoWavelengthFor1d25G OBJECT-TYPE
            SYNTAX Integer32
            MAX-ACCESS read-only
            STATUS current
            DESCRIPTION
                "This object indicates the Wavelength for 1.25G."
            ::= { hwEponOltXFPOpticsModuleInfoEntry 49 }

        hwEponOltXFPOpticsModuleInfoVendorSpecific OBJECT-TYPE
            SYNTAX OCTET STRING
            MAX-ACCESS read-only
            STATUS current
            DESCRIPTION
                "This object indicates the Vendor specific."
            ::= { hwEponOltXFPOpticsModuleInfoEntry 50 }

        hwEponOltXFPOpticsModuleXponType OBJECT-TYPE
            SYNTAX INTEGER {
                unknown(1),
                gpon(2),
                epon(3),
                epon10g(4),
                gpon10g(5),
                wdmpon(6),
                hybridpon(7),
                gponepon(8),
                invalid(-1)
            }
            MAX-ACCESS read-only
            STATUS current
            DESCRIPTION
                "This object indicates the module type.
                 Options:
                 1. unknown(1)            - Unknown
                 2. gpon(2)               - GPON
                 3. epon(3)               - EPON
                 4. epon10g(4)            - 10G EPON
                 5. gpon10g(5)            - 10G GPON
                 6. wdmpon(6)             - WDM PON
                 7. hybridpon(7)          - Hybrid PON
                 8. gponepon(8)           - GPON/EPON
                 9. invalid(-1)           - Indicates that the query fails or no information is detected
                "
            ::= { hwEponOltXFPOpticsModuleInfoEntry 51 }

        hwEponOltXFPOpticsModuleXponSubType OBJECT-TYPE
            SYNTAX INTEGER {
                unknown(1),
                classbplus(101),
                classcplus(102),
                classb(103),
                classcplusplus(104),
                px20(201),
                px20plus(202),
                px20plusplus(203),
                pr30(301),
                pr20(302),
                prx30(303),
                prx20(304),
                prx40(305),
                pr40(306),
                prx30e(307),
                prx40e(308),
                pr30plus(309),
                n2a(405),
                n2b(406),
                n1(407),
                e1(408),
                e2a(409),
                e2b(410),
                invalid(-1)
            }
            MAX-ACCESS read-only
            STATUS current
            DESCRIPTION
                "This object indicates the sub module type.
                 Options:
                 1. unknown(1)            - Unknown
                 2. classbplus(101)       - CLASS B+
                 3. classcplus(102)       - CLASS C+
                 4. classb(103)           - CLASS B
                 5. classcplusplus(104)    - CLASS C++
                 6. px20(201)              - PX20
                 7. px20plus(202)          - PX20+
                 8. px20plusplus(203)      - PX20++
                 9. pr30(301)              - PR30
                 10.pr20(302)              - PR20
                 11.prx30(303)             - PRX30
                 12.prx20(304)             - PRX20
                 13.prx40(305)             - PRX40
                 14.pr40(306)              - PR40
		 15.prx30e(307)            - PRX30E
		 16.prx40e(308)            - PRX40E
		 17.pr30plus(309)          - PR3PLUS
                 18.n2a(405)               - N2a
                 19.n2b(406)               - N2b
                 20.n1(407)                - N1
                 21.e1(408)                - E1
                 22.e2a(409)               - E2a
                 23.e2b(410)               - E2b
                 24.invalid(-1)            - Indicates that the query fails or no information is detected
                "
            ::= { hwEponOltXFPOpticsModuleInfoEntry 52 }

        hwEponOltXFPOpticsModuleXponUsedType OBJECT-TYPE
            SYNTAX INTEGER {
                unknown(1),
                olt(2),
                ont(3),
                onu(4),
                invalid(-1)
            }
            MAX-ACCESS read-only
            STATUS current
            DESCRIPTION
                "This object indicates the application scenario of the optical transceiver.
                 Options:
                 1. unknown(1)        - Unknown
                 2. olt(2)            - OLT
                 3. ont(3)            - ONT
                 4. onu(4)            - ONU
                 5. invalid(-1)       - Indicates that the query fails or no information is detected
                "
            ::= { hwEponOltXFPOpticsModuleInfoEntry 53 }

        hwEponOltXFPOpticsModuleXponEncapsulationType OBJECT-TYPE
            SYNTAX INTEGER {
                unknown(1),
                sff2x5(2),
                sff2x10(3),
                sfp(4),
                xfp(5),
                lxfp(6),
                bosaonboard(7),
                sfpplus(8),
                invalid(-1)
            }
            MAX-ACCESS read-only
            STATUS current
            DESCRIPTION
                "This object indicates the encapsulation information about the optical transceiver.
                 Options:
                 1. unknown(1)        - Unknown
                 2. sff2x5(2)         - SFF 2x5
                 3. sff2x10(3)        - SFF 2x10
                 4. sfp(4)            - SFP
                 5. xfp(5)            - XFP
                 6. lxfp(6)           - LXFP
                 7. bosaonboard(7)    - BOSA ON BOARD
                 8. sfpplus(8)        - SFP+
                 9. invalid(-1)       - Indicates that the query fails or no information is detected
                "
            ::= { hwEponOltXFPOpticsModuleInfoEntry 54 }

        hwEponOltXFPOpticsModuleXponTemperatureLevel OBJECT-TYPE
            SYNTAX INTEGER {
                unknown(1),
                commercial(2),
                industry(3),
                expandtemperature(4),
                invalid(-1)
            }
            MAX-ACCESS read-only
            STATUS current
            DESCRIPTION
                "This object indicates the application scenario of the optical transceiver.
                 Options:
                 1. unknown(1)              - Unknown
                 2. commercial(2)           - commercial
                 3. industry(3)             - industry
                 4. expandtemperature(4)    - expand temperature
                 5. invalid(-1)             - Indicates that the query fails or no information is detected
                "
            ::= { hwEponOltXFPOpticsModuleInfoEntry 55 }

        hwEponOltXFPOpticsModuleXponOPMprecision OBJECT-TYPE
            SYNTAX INTEGER {
                unknown(1),
                db3(2),
                db1(3),
                invalid(-1)
            }
            MAX-ACCESS read-only
            STATUS current
            DESCRIPTION
                "This object indicates the OPM precision.
                 Options:
                 1. unknown(1)        - Unknown
                 2. db3(2)            - 3db
                 3. db1(3)            - 1db
                 4. invalid(-1)       - Indicates that the query fails or no information is detected
                "
            ::= { hwEponOltXFPOpticsModuleInfoEntry 56 }

    --Table : HwEponDeviceOltControlInfoTable
        hwEponDeviceOltControlInfoTable OBJECT-TYPE
            SYNTAX     SEQUENCE OF HwEponDeviceOltControlInfoEntry
            MAX-ACCESS not-accessible
            STATUS     current
            DESCRIPTION
                "This table implements the control of the EPON port. The index of this table is ifIndex."
            ::= { hwXponDeviceControlObjects 31 }

        hwEponDeviceOltControlInfoEntry OBJECT-TYPE
            SYNTAX     HwEponDeviceOltControlInfoEntry
            MAX-ACCESS not-accessible
            STATUS     current
            DESCRIPTION
                "This table implements the control of the EPON port. The index of this entry is ifIndex."
            INDEX       { ifIndex }
            ::= { hwEponDeviceOltControlInfoTable 1 }

        HwEponDeviceOltControlInfoEntry ::=
            SEQUENCE {
                hwEponDeviceOltControlfarthest                 Integer32,
                hwEponDeviceOltControlAutofindOntEnable        INTEGER,
                hwEponDeviceOltControlDespt                    OCTET STRING,
                hwEponDeviceOltControlLaserSwitch              INTEGER,
                hwEponDeviceOltControlStatus                   INTEGER,
                hwEponDeviceOltControlUpStreamBandWidth        Integer32,
                hwEponDeviceOltControlDownStreamBandWidth      Integer32,
                hwEponDeviceOltControlOpticAlarmProfileName    OCTET STRING,
                hwEponDeviceOltLowTimeLapseSwitch              Integer32,
                hwEponDeviceOltEffectiveFlag                   Integer32,
                hwEponOltLowTimeLapseStatus                    Integer32,
                hwEponDeviceOltControlOntNum                   Integer32,
                hwEponDeviceOltControlVlanTagMode              INTEGER,
                hwEponDeviceOltLastUpTime                      DateAndTime,
                hwEponDeviceOltLastDownTime                    DateAndTime,
                hwEponDeviceOltLastDownCause                   INTEGER,
                hwEponDeviceOltControlLeftBandWidth            Integer32,
                hwEponDeviceOltControlAvailableBandWidth       Integer32,
                hwEponDeviceOltControlManualDetectRogueOnt     INTEGER,
                hwEponDeviceOltRogueOntExist                   INTEGER,
                hwEponDeviceOltLeftBandWidth10GUpstream        Integer32,
                hwEponDeviceOltAvailableBandWidth10GUpstream   Integer32,
                hwEponDeviceOltControlAlarmProfileName         OCTET STRING,
                hwEponDeviceOltControlWarningProfileName       OCTET STRING,
                hwEponDeviceOltControlEnergySavingFlag         INTEGER,
                hwEponDeviceOltControlManualCheckRogueOnt      INTEGER,
                hwEponDeviceOltControlPortReset                INTEGER
            }

        hwEponDeviceOltControlfarthest  OBJECT-TYPE
            SYNTAX     Integer32
            MAX-ACCESS   read-write
            STATUS      current
            DESCRIPTION
                "This object indicates the fiber distance between the OLT and the farthest ONT
                 EPON: 0-40 km
                 10 Gb/s EPON: 0-60 km
                 "
            ::= { hwEponDeviceOltControlInfoEntry 1 }

        hwEponDeviceOltControlAutofindOntEnable  OBJECT-TYPE
            SYNTAX     INTEGER {
                enable(1),
                disable(2),
                invalid(-1)
            }
            MAX-ACCESS   read-write
            STATUS      current
            DESCRIPTION
                "This object indicates the ONT auto find switch.
                 Options:
                 1. enable(1)      - Enable the ONT auto find switch
                 2. disable(2)     - Disable the ONT auto find switch
                 3. invalid(-1)    - Indicates that the query fails or no information is detected
                "
            ::= { hwEponDeviceOltControlInfoEntry 2 }

        hwEponDeviceOltControlDespt  OBJECT-TYPE
            SYNTAX     OCTET STRING (SIZE (0..80))
            MAX-ACCESS   read-write
            STATUS      current
            DESCRIPTION
                "This object indicates the description of the EPON port."
            ::= { hwEponDeviceOltControlInfoEntry 3}

        hwEponDeviceOltControlLaserSwitch  OBJECT-TYPE
            SYNTAX     INTEGER{
                on(1),
                off(2),
                invalid(-1)
            }
            MAX-ACCESS   read-write
            STATUS      current
            DESCRIPTION
                "This object indicates the laser switch of the EPON port.
                 Options:
                 1. on(1)         - Open the laser switch of the EPON port
                 2. off(2)        - Close the laser switch of the EPON port
                 3. invalid(-1)   - Indicates that the query fails or no information is detected
                "
            ::= { hwEponDeviceOltControlInfoEntry 4 }

        hwEponDeviceOltControlStatus  OBJECT-TYPE
            SYNTAX     INTEGER{
                up(1),
                down(2)
            }
            MAX-ACCESS   read-only
            STATUS      current
            DESCRIPTION
                "This object indicates the EPON port status in the OLT:
                 Options:
                 1. up(1)         - Indicates that the EPON port is normal
                 2. down(2)       - Indicates that the EPON port is fault
                "
            ::= { hwEponDeviceOltControlInfoEntry 5 }

        hwEponDeviceOltControlUpStreamBandWidth  OBJECT-TYPE
            SYNTAX     Integer32
            MAX-ACCESS   read-only
            STATUS      current
            DESCRIPTION
                "This object indicates the up-stream bandwidth of EPON port."
            ::= { hwEponDeviceOltControlInfoEntry 6}

        hwEponDeviceOltControlDownStreamBandWidth  OBJECT-TYPE
            SYNTAX     Integer32
            MAX-ACCESS   read-only
            STATUS      current
            DESCRIPTION
                "This object indicates the down-stream bandwidth of EPON port."
            ::= { hwEponDeviceOltControlInfoEntry 7}

        hwEponDeviceOltControlOpticAlarmProfileName  OBJECT-TYPE
            SYNTAX     OCTET STRING (SIZE (0..32))
            MAX-ACCESS   read-write
            STATUS      current
            DESCRIPTION
                "This object indicates the short delay switch status that is saved in the database of the OLT."
            ::= { hwEponDeviceOltControlInfoEntry 8}

        hwEponDeviceOltLowTimeLapseSwitch  OBJECT-TYPE
            SYNTAX     Integer32
            MAX-ACCESS   read-write
            STATUS      current
            DESCRIPTION
                "This object is used to query the short delay switch status that is saved in the database of the OLT."
            ::= { hwEponDeviceOltControlInfoEntry 9 }

        hwEponDeviceOltEffectiveFlag  OBJECT-TYPE
            SYNTAX     Integer32
            MAX-ACCESS   read-write
            STATUS      current
            DESCRIPTION
                "This object is the flag indicating whether the buffer function takes effect immediately."
            ::= { hwEponDeviceOltControlInfoEntry 10 }

        hwEponOltLowTimeLapseStatus  OBJECT-TYPE
            SYNTAX     Integer32
            MAX-ACCESS   read-only
            STATUS      current
            DESCRIPTION
                "This object indicates the status of the EPON low time switch."
            ::= { hwEponDeviceOltControlInfoEntry 11 }

        hwEponDeviceOltControlOntNum  OBJECT-TYPE
            SYNTAX     Integer32
            MAX-ACCESS   read-only
            STATUS      current
            DESCRIPTION
                "This object indictates the number of ONTs that are added to the port."
            ::= { hwEponDeviceOltControlInfoEntry 12 }

        hwEponDeviceOltControlVlanTagMode  OBJECT-TYPE
            SYNTAX     INTEGER {
                tagbasedont(1),
                tagbasedvlan(2),
                invalid(-1)
            }
            MAX-ACCESS   read-write
            STATUS      current
            DESCRIPTION
                "This object indicates the configuration function of the VLAN tag mode of the PON port.
                 Options:
                 1. tagbasedont(1)    - Tag-based-ont
                 2. tagbasedvlan(2)   - Tag-based-vlan
                 3. invalid(-1)       - Indicates that the query fails or no information is detected
                "
            ::= { hwEponDeviceOltControlInfoEntry 13 }

        hwEponDeviceOltLastUpTime OBJECT-TYPE
            SYNTAX DateAndTime
            MAX-ACCESS  read-only
            STATUS current
            DESCRIPTION
                "This object indicates the time when the port last goes online."
            ::= { hwEponDeviceOltControlInfoEntry 14 }

        hwEponDeviceOltLastDownTime OBJECT-TYPE
            SYNTAX DateAndTime
            MAX-ACCESS  read-only
            STATUS current
            DESCRIPTION
                "This object indicates the time when the port last goes offline."
            ::= { hwEponDeviceOltControlInfoEntry 15 }

        hwEponDeviceOltLastDownCause OBJECT-TYPE
            SYNTAX INTEGER{
                los(1),
                opticModuleAbsence(2),
                opticModuleFault(3),
                opticPortClosed(4),
                otherCause(-1)
            }
            MAX-ACCESS  read-only
            STATUS current
            DESCRIPTION
                "This object indicates the reason why the port last goes offline.
                 Options:
                 1. los(1)                - Loss of signal
                 2. opticModuleAbsence(2) - The optic module is absence
                 3. opticModuleFault(3)   - The optic module is fault
                 4. opticPortClosed(4)    - The optic port is closed
                 5. otherCause(-1)        - Other cause
                "
            ::= { hwEponDeviceOltControlInfoEntry 16 }

        hwEponDeviceOltControlLeftBandWidth OBJECT-TYPE
            SYNTAX  Integer32
            MAX-ACCESS  read-only
            STATUS  current
            DESCRIPTION
                "This object indicates the untapped bandwidth of 1G upstream ONT's port, unit Kbps."
            ::= { hwEponDeviceOltControlInfoEntry 17 }

        hwEponDeviceOltControlAvailableBandWidth OBJECT-TYPE
            SYNTAX  Integer32
            MAX-ACCESS  read-only
            STATUS  current
            DESCRIPTION
                "This object indicates the available bandwidth of 1G upstream ONT's port, unit Kbps."
            ::= { hwEponDeviceOltControlInfoEntry 18 }

        hwEponDeviceOltControlManualDetectRogueOnt OBJECT-TYPE
            SYNTAX  INTEGER {
                startup(1),
                invalid(-1)
            }
            MAX-ACCESS  read-write
            STATUS  current
            DESCRIPTION
                "This object indicates the switch of the rogue ONT manual detection.
                 Options:
                 1. startup(1)    - Starts up the switch of the rogue ONT manual detection
                 2. invalid(-1)   - Indicates that the query fails or no information is detected
                "
            ::= { hwEponDeviceOltControlInfoEntry 19 }

        hwEponDeviceOltRogueOntExist OBJECT-TYPE
            SYNTAX INTEGER{
                inexistent (0),
                existent (1)
            }
            MAX-ACCESS  read-only
            STATUS current
            DESCRIPTION
                "This object is used to query whether there are Illegal incursionary rogue ONTs under port.
                 Options:
                 1. inexistent(0)    - Indicates that there are not Illegal incursionary rogue ONTs under port
                 2. existent(1)      - Indicates that there are Illegal incursionary rogue ONTs under port
                "
            ::= { hwEponDeviceOltControlInfoEntry 20 }

        hwEponDeviceOltLeftBandWidth10GUpstream OBJECT-TYPE
            SYNTAX  Integer32
            MAX-ACCESS  read-only
            STATUS  current
            DESCRIPTION
                "This object indicates the untapped bandwidth of 10G upstream ONT's port, unit Kbps."
            ::= { hwEponDeviceOltControlInfoEntry 21 }

        hwEponDeviceOltAvailableBandWidth10GUpstream OBJECT-TYPE
            SYNTAX  Integer32
            MAX-ACCESS  read-only
            STATUS  current
            DESCRIPTION
                "This object indicates the available bandwidth of 10G upstream ONT's port, unit Kbps."
            ::= { hwEponDeviceOltControlInfoEntry 22 }
        hwEponDeviceOltControlAlarmProfileName  OBJECT-TYPE
            SYNTAX     OCTET STRING (SIZE (0..32))
            MAX-ACCESS   read-write
            STATUS      current
            DESCRIPTION
                "This object indicates the name of the alarm profile that is bound to the EPON port."
            ::= { hwEponDeviceOltControlInfoEntry 23}

        hwEponDeviceOltControlWarningProfileName  OBJECT-TYPE
            SYNTAX     OCTET STRING (SIZE (0..32))
            MAX-ACCESS   read-write
            STATUS      current
            DESCRIPTION
                "This object indicates the name of the warning profile that is bound to the EPON port."
            ::= { hwEponDeviceOltControlInfoEntry 24}

        hwEponDeviceOltControlEnergySavingFlag  OBJECT-TYPE
            SYNTAX     INTEGER {
                yes(1),
                no(2)
            }
            MAX-ACCESS   read-only
            STATUS      current
            DESCRIPTION
                "Energy saving state of the EPON port.
                 Options:
                 1. yes (1)  - The EPON port is in energy saving state
                 2. no (2)   - The EPON port is not in energy saving state
                "
            ::= { hwEponDeviceOltControlInfoEntry 25 }

        hwEponDeviceOltControlManualCheckRogueOnt OBJECT-TYPE
            SYNTAX  INTEGER {
                startup(1),
                invalid(-1)
            }
            MAX-ACCESS  read-write
            STATUS  current
            DESCRIPTION
                "This object indicates the switch of the rogue ONT manual check.
                 Options:
                 1. startup(1)    - Start up the switch of the rogue ONT manual checked
                 2. invalid(-1)   - Indicates that the query fails or no information is checked
                "
            ::= { hwEponDeviceOltControlInfoEntry 26 }

        hwEponDeviceOltControlPortReset OBJECT-TYPE
            SYNTAX  INTEGER {
                reset(1),
                invalid(-1)
            }
            MAX-ACCESS  read-write
            STATUS  current
            DESCRIPTION
                "This parameter is used to reset the port.
                 Options:
                 1. reset(1)      - Indicates that the port resets
                 2. invalid(-1)   - Indicates that the query fails or no information is checked
                "
            ::= { hwEponDeviceOltControlInfoEntry 27 }

   -- Table : hwEponOltOpticsModuleInfoTable
        hwEponOltOpticsModuleInfoTable OBJECT-TYPE
            SYNTAX     SEQUENCE OF HwEponOltOpticsModuleInfoEntry
            MAX-ACCESS not-accessible
            STATUS     current
            DESCRIPTION
                "Show the optics module information. The index of this table is ifIndex."
            ::= { hwXponDeviceControlObjects 32 }

        hwEponOltOpticsModuleInfoEntry OBJECT-TYPE
            SYNTAX     HwEponOltOpticsModuleInfoEntry
            MAX-ACCESS not-accessible
            STATUS     current
            DESCRIPTION
                "Show the optics module information. The index of this entry is ifIndex."
            INDEX       { ifIndex }
            ::= { hwEponOltOpticsModuleInfoTable 1 }

        HwEponOltOpticsModuleInfoEntry ::=
            SEQUENCE {
                hwEponOltOpticsModuleInfoIdentifier                  INTEGER,
                hwEponOltOpticsModuleInfoExtID                       INTEGER,
                hwEponOltOpticsModuleInfoConnector                   INTEGER,
                hwEponOltOpticsModuleInfoEncoding                    INTEGER,
                hwEponOltOpticsModuleInfoBrNominal                   Integer32,
                hwEponOltOpticsModuleInfoLength9Micronkm             Integer32,
                hwEponOltOpticsModuleInfoLength9Micron               Integer32,
                hwEponOltOpticsModuleInfoLength50Micron              Integer32,
                hwEponOltOpticsModuleInfoLength62Micron5             Integer32,
                hwEponOltOpticsModuleInfoLengthCopper                Integer32,
                hwEponOltOpticsModuleInfoVendorName                  OCTET STRING,
                hwEponOltOpticsModuleInfoVendorOUI                   OCTET STRING,
                hwEponOltOpticsModuleInfoVendorPN                    OCTET STRING,
                hwEponOltOpticsModuleInfoVendorRev                   OCTET STRING,
                hwEponOltOpticsModuleInfoWaveLength                  Integer32,
                hwEponOltOpticsModuleInfoCcBase                      Integer32,
                hwEponOltOpticsModuleInfoOptions                     Integer32,
                hwEponOltOpticsModuleInfoBrMax                       Integer32,
                hwEponOltOpticsModuleInfoBrMin                       Integer32,
                hwEponOltOpticsModuleInfoVendorSN                    OCTET STRING,
                hwEponOltOpticsModuleInfoDateCode                    OCTET STRING,
                hwEponOltOpticsModuleInfoDiagnosticMonitoringType    Integer32,
                hwEponOltOpticsModuleInfoEnhancedOptions             Integer32,
                hwEponOltOpticsModuleInfoSFF8472Compliance           INTEGER,
                hwEponOltOpticsModuleInfoCcExt                       Integer32,
                hwEponOltOpticsModuleInfoVendorSpecific              OCTET STRING,
                hwEponOltOpticsModuleXponType                        INTEGER,
                hwEponOltOpticsModuleXponSubType                     INTEGER,
                hwEponOltOpticsModuleXponUsedType                    INTEGER,
                hwEponOltOpticsModuleXponEncapsulationType           INTEGER
            }

        hwEponOltOpticsModuleInfoIdentifier OBJECT-TYPE
            SYNTAX INTEGER {
                unknown(1),
                gbic(2),
                solderedToMotherboard(3),
                sfp(4),
                invalid(-1)
            }
            MAX-ACCESS read-only
            STATUS current
            DESCRIPTION
                "This object indicates the type of serial transceiver.
                 Options:
                 1. unknown(1)                      - Unknown or unspecified
                 2. gbic(2)                         - GBIC
                 3. solderedToMotherboard(3)        - Module soldered to motherboard
                 4. sfp(4)                          - SFP or SFP Plus
                 5. invalid (-1)                    - Indicates that the query fails or no information is detected
                "
            ::= { hwEponOltOpticsModuleInfoEntry 1 }

        hwEponOltOpticsModuleInfoExtID OBJECT-TYPE
            SYNTAX INTEGER {
                notSpecifiedOrNotCompliant(1),
                moddef1(2),
                moddef2(3),
                moddef3(4),
                byTwowireOnly(5),
                moddef5(6),
                moddef6(7),
                moddef7(8),
                invalid(-1)
            }
            MAX-ACCESS read-only
            STATUS current
            DESCRIPTION
                "This object indicates the extended identifier of type of serial transceiver.
                 Options:
                 1. notSpecifiedOrNotCompliant(1)   - Not specified or not compliant with a defined MOD_DEF
                 2. moddef1(2)                      - GBIC is compliant with MOD_DEF 1
                 3. moddef2(3)                      - GBIC is compliant with MOD_DEF 2
                 4. moddef3(4)                      - GBIC is compliant with MOD_DEF 3
                 5. byTwowireOnly(5)                - GBIC/SFP function is defined by two-wire interface ID only
                 6. moddef5(6)                      - GBIC is compliant with MOD_DEF 5
                 7. moddef6(7)                      - GBIC is compliant with MOD_DEF 6
                 8. moddef7(8)                      - GBIC is compliant with MOD_DEF 7
                 9. invalid (-1)                    - Indicates that the query fails or no information is detected
                "
            ::= { hwEponOltOpticsModuleInfoEntry 2 }

        hwEponOltOpticsModuleInfoConnector OBJECT-TYPE
            SYNTAX INTEGER {
                unknown(1),
                sc(2),
                copperConnector1(3),
                copperConnector2(4),
                bnctnc(5),
                coaxialHeaders(6),
                fiberJack(7),
                lc(8),
                mtrj(9),
                mu(10),
                sg(11),
                opticalPigtail(12),
                hssdcII(13),
                copperPigtail(14),
                mpoParallelOptic(15),
                rj45(16),
                invalid(-1)
            }
            MAX-ACCESS read-only
            STATUS current
            DESCRIPTION
                "This object indicates the code for connector type.
                 Options:
                 1.  unknown(1)              - Unknown
                 2.  sc(2)                   - SC
                 3.  copperConnector1(3)     - Fibre Channel Style 1 copper connector
                 4.  copperConnector2(4)     - Fibre Channel Style 2 copper connector
                 5.  bnctnc(5)               - BNC/TNC
                 6.  coaxialHeaders(6)       - Fibre Channel coaxial headers
                 7.  fiberJack(7)            - FiberJack
                 8.  lc(8)                   - LC
                 9.  mtrj(9)                 - MT-RJ
                 10. mu(10)                  - MU
                 11. sg(11)                  - SG
                 12. opticalPigtail(12)      - Optical pigtail
                 13. hssdcII(13)             - HSSDC II
                 14. copperPigtail(14)       - Copper Pigtail
                 15. mpoParallelOptic(15)    - MPO Parallel Optic
                 16. rj45(16)                - RJ45
                 17. invalid(-1)             - Indicates that the query fails or no information is detected
                "
            ::= { hwEponOltOpticsModuleInfoEntry 3 }

        hwEponOltOpticsModuleInfoEncoding OBJECT-TYPE
            SYNTAX INTEGER {
                unspecified(1),
                encodingMethod8B10B(2),
                encodingMethod4B5B(3),
                nrz(4),
                manchester(5),
                sonetScrambled(6),
                encodingMethod64B66B(7),
                invalid(-1)
            }
            MAX-ACCESS read-only
            STATUS current
            DESCRIPTION
                "This object indicates the code for serial encoding algorithm.
                 Options:
                 1.  unspecified(1)            - Unspecified
                 2.  encodingMethod8B10B(2)    - 8B10B
                 3.  encodingMethod4B5B(3)     - 4B5B
                 4.  nrz(4)                    - NRZ
                 5.  manchester(5)             - Manchester
                 6.  sonetScrambled(6)         - SONET Scrambled
                 7.  encodingMethod64B66B(7)   - 64B66B
                 8.  invalid(-1)               - Indicates that the query fails or no information is detected
                "
            ::= { hwEponOltOpticsModuleInfoEntry 4 }

        hwEponOltOpticsModuleInfoBrNominal OBJECT-TYPE
            SYNTAX Integer32
            MAX-ACCESS read-only
            STATUS current
            DESCRIPTION
                "This object indicates the nominal bit rate, units of 100 MBits/sec."
            ::= { hwEponOltOpticsModuleInfoEntry 5 }

        hwEponOltOpticsModuleInfoLength9Micronkm OBJECT-TYPE
            SYNTAX Integer32
            MAX-ACCESS read-only
            STATUS current
            DESCRIPTION
                "This object indicates the link length supported for 9/125 micron fiber, units of 1000 m."
            ::= { hwEponOltOpticsModuleInfoEntry 6 }

        hwEponOltOpticsModuleInfoLength9Micron OBJECT-TYPE
            SYNTAX Integer32
            MAX-ACCESS read-only
            STATUS current
            DESCRIPTION
                "This object indicates the link length supported for 9/125 micron fiber, units of 100 m."
            ::= { hwEponOltOpticsModuleInfoEntry 7 }

        hwEponOltOpticsModuleInfoLength50Micron OBJECT-TYPE
            SYNTAX Integer32
            MAX-ACCESS read-only
            STATUS current
            DESCRIPTION
                "This object indicates the link length supported for 50/125 micron fiber, units of 10 m."
            ::= { hwEponOltOpticsModuleInfoEntry 8 }

        hwEponOltOpticsModuleInfoLength62Micron5 OBJECT-TYPE
            SYNTAX Integer32
            MAX-ACCESS read-only
            STATUS current
            DESCRIPTION
                "This object indicates the link length supported for 62.5/125 micron fiber, units of 10 m."
            ::= { hwEponOltOpticsModuleInfoEntry 9 }

        hwEponOltOpticsModuleInfoLengthCopper OBJECT-TYPE
            SYNTAX Integer32
            MAX-ACCESS read-only
            STATUS current
            DESCRIPTION
                "This object indicates the link length supported for copper, units of meters."
            ::= { hwEponOltOpticsModuleInfoEntry 10 }

        hwEponOltOpticsModuleInfoVendorName OBJECT-TYPE
            SYNTAX OCTET STRING (SIZE (0..17))
            MAX-ACCESS read-only
            STATUS current
            DESCRIPTION
                "This object indicates the SFP vendor name (ASCII)."
            ::= { hwEponOltOpticsModuleInfoEntry 11 }

        hwEponOltOpticsModuleInfoVendorOUI OBJECT-TYPE
            SYNTAX OCTET STRING (SIZE (0..9))
            MAX-ACCESS read-only
            STATUS current
            DESCRIPTION
                "This object indicates the SFP vendor IEEE company ID."
            ::= { hwEponOltOpticsModuleInfoEntry 12 }

        hwEponOltOpticsModuleInfoVendorPN OBJECT-TYPE
            SYNTAX OCTET STRING (SIZE (0..17))
            MAX-ACCESS read-only
            STATUS current
            DESCRIPTION
                "This object indicates the part number provided by SFP vendor (ASCII)."
            ::= { hwEponOltOpticsModuleInfoEntry 13 }

        hwEponOltOpticsModuleInfoVendorRev OBJECT-TYPE
            SYNTAX OCTET STRING (SIZE (0..5))
            MAX-ACCESS read-only
            STATUS current
            DESCRIPTION
                "This object indicates the revision level for part number provided by vendor (ASCII)."
            ::= { hwEponOltOpticsModuleInfoEntry 14 }

        hwEponOltOpticsModuleInfoWaveLength OBJECT-TYPE
            SYNTAX Integer32
            MAX-ACCESS read-only
            STATUS current
            DESCRIPTION
                "This object indicates the laser wavelength, units of nm."
            ::= { hwEponOltOpticsModuleInfoEntry 15 }

        hwEponOltOpticsModuleInfoCcBase OBJECT-TYPE
            SYNTAX Integer32
            MAX-ACCESS read-only
            STATUS current
            DESCRIPTION
                "This object indicates the check code for Base ID Fields."
            ::= { hwEponOltOpticsModuleInfoEntry 16 }

        hwEponOltOpticsModuleInfoOptions OBJECT-TYPE
            SYNTAX Integer32
            MAX-ACCESS read-only
            STATUS current
            DESCRIPTION
                "Indicates which optional transceiver signals are implemented.
                  bit                 Description of option
                   10                 Cooled laser transmitter
                   9                  Power Level 2 requirement
                   8                  Linear Receiver Output
                  7-6                 Reserved
                   5                  RATE_SELECT
                   4                  TX_DISABLE
                   3                  TX_FAULT
                   2                  LOS (signal inverted from standard definition)
                   1                  LOS (signal as defined in SFP MSA)
                   0                  Reserved
                "
            ::= { hwEponOltOpticsModuleInfoEntry 17 }

        hwEponOltOpticsModuleInfoBrMax OBJECT-TYPE
            SYNTAX Integer32
            MAX-ACCESS read-only
            STATUS current
            DESCRIPTION
                "This object indicates the upper bit rate margin, units of %."
            ::= { hwEponOltOpticsModuleInfoEntry 18 }

        hwEponOltOpticsModuleInfoBrMin OBJECT-TYPE
            SYNTAX Integer32
            MAX-ACCESS read-only
            STATUS current
            DESCRIPTION
                "This object indicates the lower bit rate margin, units of %."
            ::= { hwEponOltOpticsModuleInfoEntry 19 }

        hwEponOltOpticsModuleInfoVendorSN OBJECT-TYPE
            SYNTAX OCTET STRING (SIZE (0..17))
            MAX-ACCESS read-only
            STATUS current
            DESCRIPTION
                "This object indicates the serial number provided by vendor (ASCII)."
            ::= { hwEponOltOpticsModuleInfoEntry 20 }

        hwEponOltOpticsModuleInfoDateCode OBJECT-TYPE
            SYNTAX OCTET STRING (SIZE (0..9))
            MAX-ACCESS read-only
            STATUS current
            DESCRIPTION
                "This object indicates manufacturing date code of the vendor (ASCII)."
            ::= { hwEponOltOpticsModuleInfoEntry 21 }

        hwEponOltOpticsModuleInfoDiagnosticMonitoringType OBJECT-TYPE
            SYNTAX Integer32
            MAX-ACCESS read-only
            STATUS current
            DESCRIPTION
                "Indicates which type of diagnostic monitoring is implemented.
                 bit                 Description of Diagnostic Monitoring Type
                  7                  Reserved
                  6                  Digital diagnostic monitoring
                  5                  Internally Calibrated
                  4                  Externally Calibrated
                  3                  Received power measurement type:(0 = OMA, 1 = Average)
                  2                  Address change required
                  1-0                Reserved
                "
            ::= { hwEponOltOpticsModuleInfoEntry 22 }

        hwEponOltOpticsModuleInfoEnhancedOptions OBJECT-TYPE
            SYNTAX Integer32
            MAX-ACCESS read-only
            STATUS current
            DESCRIPTION
                "Indicates which optional enhanced features are implemented.
                 bit                 Description of Enhanced Options
                  7                  Alarm/warning flags
                  6                  TX_DISABLE control and monitoring
                  5                  TX_FAULT monitoring
                  4                  RX_LOS monitoring
                  3                  RATE_SELECT control and monitoring
                  2                  Application Select control
                  1                  Rate Select control
                  0                  Reserved
                "
            ::= { hwEponOltOpticsModuleInfoEntry 23 }

        hwEponOltOpticsModuleInfoSFF8472Compliance OBJECT-TYPE
            SYNTAX INTEGER {
                undefined(1),
                includesRev93SFF8472(2),
                includesRev95SFF8472(3),
                includesRev102SFF8472(4),
                includesRev104SFF8472(5),
                includesRev110SFF8472(6),
                invalid(-1)
            }
            MAX-ACCESS read-only
            STATUS current
            DESCRIPTION
                "Indicates which revision of SFF-8472 the transceiver complies
                 Options:
                 1. undefined(1)               - Not included or undefined
                 2. includesRev93SFF8472(2)    - Includes functionality described in Rev 9.3
                 3. includesRev95SFF8472(3)    - Includes functionality described in Rev 9.5
                 4. includesRev102SFF8472(4)   - Includes functionality described in Rev 10.2
                 5. includesRev104SFF8472(5)   - Includes functionality described in Rev 10.4
                 6. includesRev110SFF8472(6)   - Includes functionality described in Rev 11.0
                 7. invalid (-1)               - Indicates that the query fails or no information is detected
                "
            ::= { hwEponOltOpticsModuleInfoEntry 24 }

        hwEponOltOpticsModuleInfoCcExt OBJECT-TYPE
            SYNTAX Integer32
            MAX-ACCESS read-only
            STATUS current
            DESCRIPTION
                "This object indicates the check code for the Extended ID Fields."
            ::= { hwEponOltOpticsModuleInfoEntry 25 }

        hwEponOltOpticsModuleInfoVendorSpecific OBJECT-TYPE
            SYNTAX OCTET STRING (SIZE (0..33))
            MAX-ACCESS read-only
            STATUS current
            DESCRIPTION
                "This object indicates the vendor Specific EEPROM."
            ::= { hwEponOltOpticsModuleInfoEntry 26 }

        hwEponOltOpticsModuleXponType OBJECT-TYPE
            SYNTAX INTEGER {
                unknown(1),
                gpon(2),
                epon(3),
                epon10g(4),
                gpon10g(5),
                wdmpon(6),
                hybridpon(7),
                invalid(-1)
            }
            MAX-ACCESS  read-only
            STATUS current
            DESCRIPTION
                "This object indicates the type of the optical transceiver.
                 Options:
                 1. unknown(1)      - Unknown
                 2. gpon(2)         - GPON
                 3. epon(3)         - EPON
                 4. epon10g(4)      - 10G EPON
                 5. gpon10g(5)      - 10G GPON
                 6. wdmpon(6)       - WDM PON
                 7. hybridpon(7)    - Hybrid PON
                 8. invalid(-1)     - Indicates that the query fails or no information is detected
                "
            ::= { hwEponOltOpticsModuleInfoEntry 27 }

        hwEponOltOpticsModuleXponSubType OBJECT-TYPE
            SYNTAX INTEGER {
                unknown(1),
                classbplus(101),
                classcplus(102),
                classb(103),
                classcplusplus(104),
                px20(201),
                px20plus(202),
                px20plusplus(203),
                pr30(301),
                pr20(302),
                prx30(303),
                prx20(304),
		prx40(305),
                pr40(306),
                prx30e(307),
                prx40e(308),
                pr30plus(309),
                n2a(405),
                n2b(406),
                n1(407),
                e1(408),
                e2a(409),
                e2b(410),
                invalid(-1)
            }
            MAX-ACCESS  read-only
            STATUS current
            DESCRIPTION
                "This object indicates the sub type of the optical transceiver.
                 Options:
                 1. unknown(1)             - Unknown
                 2. classbplus(101)        - CLASS B+
                 3. classcplus(102)        - CLASS C+
                 4. classb(103)            - CLASS B
                 5. classcplusplus(104)    - CLASS C++
                 6. px20(201)              - PX20
                 7. px20plus(202)          - PX20+
                 8. px20plusplus(203)      - PX20++
                 9. pr30(301)              - PR30
                 10.pr20(302)              - PR20
                 11.prx30(303)             - PRX30
                 12.prx20(304)             - PRX20
                 13.prx40(305)             - PRX40
                 14.pr40(306)              - PR40
                 15.prx30e(307)            - PRX30-E
                 16.prx40e(308)            - PRX40-E
                 17.pr30plus(309)          - PR30+
                 18.n2a(405)               - N2a
                 19.n2b(406)               - N2b
                 20.n1(407)                - N1
                 21.e1(408)                - E1
                 22.e2a(409)               - E2a
                 23.e2b(410)               - E2b
                 24.invalid(-1)            - Indicates that the query fails or no information is detected
                "
            ::= { hwEponOltOpticsModuleInfoEntry 28 }

        hwEponOltOpticsModuleXponUsedType OBJECT-TYPE
            SYNTAX INTEGER {
                unknown(1),
                olt(2),
                ont(3),
                onu(4),
                invalid(-1)
            }
            MAX-ACCESS  read-only
            STATUS current
            DESCRIPTION
                "This object indicates the application scenario of the optical transceiver.
                 Options:
                 1. unknown(1)             - Unknown
                 2. olt(2)                 - OLT
                 3. ont(3)                 - ONT
                 4. onu(4)                 - ONU
                 5.invalid(-1)             - Indicates that the query fails or no information is detected
                "
            ::= { hwEponOltOpticsModuleInfoEntry 29 }

        hwEponOltOpticsModuleXponEncapsulationType OBJECT-TYPE
            SYNTAX INTEGER {
                unknown(1),
                sff2x5(2),
                sff2x10(3),
                sfp(4),
                xfp(5),
                lxfp(6),
                bosaonboard(7),
                invalid(-1)
            }
            MAX-ACCESS  read-only
            STATUS current
            DESCRIPTION
                "This object indicates the encapsulation information about the optical transceiver.
                 Options:
                 1. unknown(1)              - Unknown
                 2. sff2x5(2)               - SFF 2x5
                 3. sff2x10(3)              - SFF 2x10
                 4. sfp(4)                  - SFP
                 5. xfp(5)                  - XFP
                 6. lxfp(6)                 - LXFP
                 7. bosaonboard(7)          - BOSA ON BOARD
                 8.invalid(-1)              - Indicates that the query fails or no information is detected
                "
            ::= { hwEponOltOpticsModuleInfoEntry 30 }

-- Table : hwEponOltOpticsDdmInfoTable
        hwEponOltOpticsDdmInfoTable OBJECT-TYPE
            SYNTAX     SEQUENCE OF HwEponOltOpticsDdmInfoEntry
            MAX-ACCESS not-accessible
            STATUS     current
            DESCRIPTION
                "This table is used to query the diagnostic information about the optical transceiver of the EPON port.
                 The index of this table is ifIndex.
                "
            ::= { hwXponDeviceControlObjects 33 }

        hwEponOltOpticsDdmInfoEntry OBJECT-TYPE
            SYNTAX     HwEponOltOpticsDdmInfoEntry
            MAX-ACCESS not-accessible
            STATUS     current
            DESCRIPTION
                "
                 This table is used to query the diagnostic information about the optical transceiver of the EPON port.
                 The index of this entry is ifIndex.
                "
            INDEX       { ifIndex }
            ::= { hwEponOltOpticsDdmInfoTable 1 }

        HwEponOltOpticsDdmInfoEntry ::=
            SEQUENCE {
                hwEponOltOpticsDdmInfoTemperature     Integer32,
                hwEponOltOpticsDdmInfoSupplyVoltage   Integer32,
                hwEponOltOpticsDdmInfoTxBiasCurrent   Integer32,
                hwEponOltOpticsDdmInfoTxPower         Integer32,
                hwEponOltOpticsDdmInfoRxPower         Integer32
            }

        hwEponOltOpticsDdmInfoTemperature OBJECT-TYPE
            SYNTAX Integer32
            MAX-ACCESS read-only
            STATUS current
            DESCRIPTION
                "This object indicates the optics temperature, units of C(centigrade)."
            ::= { hwEponOltOpticsDdmInfoEntry 1 }

        hwEponOltOpticsDdmInfoSupplyVoltage OBJECT-TYPE
            SYNTAX Integer32
            MAX-ACCESS read-only
            STATUS current
            DESCRIPTION
                "This object indicates the supply voltage, units of 0.01V."
            ::= { hwEponOltOpticsDdmInfoEntry 2 }

        hwEponOltOpticsDdmInfoTxBiasCurrent OBJECT-TYPE
            SYNTAX Integer32
            MAX-ACCESS read-only
            STATUS current
            DESCRIPTION
                "This object indicates the optics current, units of mA."
            ::= { hwEponOltOpticsDdmInfoEntry 3 }

        hwEponOltOpticsDdmInfoTxPower OBJECT-TYPE
            SYNTAX Integer32
            MAX-ACCESS read-only
            STATUS current
            DESCRIPTION
                "This object indicates the optics send power, units of 0.01dBm."
            ::= { hwEponOltOpticsDdmInfoEntry 4 }

        hwEponOltOpticsDdmInfoRxPower OBJECT-TYPE
            SYNTAX Integer32
            MAX-ACCESS read-only
            STATUS current
            DESCRIPTION
                "This object indicates the optics receive power, units of 0.01dBm."
            ::= { hwEponOltOpticsDdmInfoEntry 5 }

-- Table:HwXponOntLoadSelectTable
        hwXponOntLoadSelectTable OBJECT-TYPE
            SYNTAX     SEQUENCE OF HwXponOntLoadSelectEntry
            MAX-ACCESS not-accessible
            STATUS     current
            DESCRIPTION
                "It is used to add ont to loading list and query the loading state for ONT.
                 The index of this table is a combination of ifIndex and hwXponDeviceOntIndex.
                "
            ::= { hwXponDeviceControlObjects 41 }

            hwXponOntLoadSelectEntry OBJECT-TYPE
            SYNTAX     HwXponOntLoadSelectEntry
            MAX-ACCESS not-accessible
            STATUS     current
            DESCRIPTION
                "It is used to add ont to loading list and query the loading state for ONT.
                 The index of this entry is a combination of ifIndex and hwXponDeviceOntIndex.
                "
            INDEX       { ifIndex, hwXponDeviceOntIndex }
            ::= { hwXponOntLoadSelectTable 1 }

        HwXponOntLoadSelectEntry ::=
            SEQUENCE {
                hwXponDeviceOntIndex                      Integer32,
                hwXponOntLoadSelectState                  INTEGER,
                hwXponOntLoadSelectProgress               Integer32,
                hwXponOntLoadSelectRowStatus              RowStatus,
                hwXponOntLoadSelectPriority               Integer32,
                hwXponOntLoadSelectActiveMode             INTEGER
            }

        hwXponDeviceOntIndex  OBJECT-TYPE
            SYNTAX     Integer32
            MAX-ACCESS   not-accessible
            STATUS      current
            DESCRIPTION
                "This object indicates the ONT ID, range: 0~255.
                 The value of 255 indicates that ONT ID is invalid or ignored in process of ont loading."
            ::= { hwXponOntLoadSelectEntry 1}

        hwXponOntLoadSelectState OBJECT-TYPE
            SYNTAX INTEGER {
                ready(1),
                loading(2),
                success(3),
                fail(4),
                invalid(-1)
            }
            MAX-ACCESS read-only
            STATUS current
            DESCRIPTION
                "This object indicates the loading state of the ONT.
                 Options:
                 1. ready(1)              - Indicates that the loading state of the ONT is ready
                 2. loading(2)            - Indicates that the loading state of the ONT is loading
                 3. success(3)            - Indicates that the loading state of the ONT is success
                 4. fail(4)               - Indicates that the loading state of the ONT is fail
                 5. invalid(-1)           - Indicates that the query fails or no information is detected
                "
            ::= { hwXponOntLoadSelectEntry 2 }

        hwXponOntLoadSelectProgress OBJECT-TYPE
            SYNTAX Integer32
            MAX-ACCESS read-only
            STATUS current
            DESCRIPTION
                "This object indicates the loading progress of the ONT"
            ::= { hwXponOntLoadSelectEntry 3 }

        hwXponOntLoadSelectRowStatus OBJECT-TYPE
            SYNTAX     RowStatus
            MAX-ACCESS    read-create
            STATUS current
            DESCRIPTION
                "This object is used to create a new row or to modify or delete an existing row in this table.
                 Options:
                 1. createAndGo(4) -create a new instance of a conceptual row
                 2. destroy(6)     -delete the instances associated with an existing conceptual row
                "
            ::= { hwXponOntLoadSelectEntry 4 }

        hwXponOntLoadSelectPriority OBJECT-TYPE
            SYNTAX Integer32
            MAX-ACCESS    read-write
            STATUS current
            DESCRIPTION
                "This object is used to set the priority of an ONT loading task.
                 A smaller value represents a higher priority.
                "
            ::= { hwXponOntLoadSelectEntry 5 }

        hwXponOntLoadSelectActiveMode OBJECT-TYPE
            SYNTAX INTEGER {
                nextstartup(1),
                immediate(2),
                graceful(3),
                invalid(-1)
            }
            MAX-ACCESS   read-write
            STATUS current
            DESCRIPTION
                "This object is used to configure the effect mode of an loaded ONT.
                 Options:
                 1. nextstartup(1)         - Indicates that the ONT takes effect after next startup
                 2. immediate(2)           - Indicates that the ONT takes effect immediately
                 3. graceful(3)            - Indicates that the ONT takes effect gracefully
                 4. invalid(-1)            - Indicates that the query fails or no information is detected
                "
            ::= { hwXponOntLoadSelectEntry 6 }

-- Table:HwXponOntLoadCtrlTable
        hwXponOntLoadCtrlTable OBJECT
            IDENTIFIER
            ::= { hwXponDeviceControlObjects 42}

        hwXponOntLoadFileType OBJECT-TYPE
            SYNTAX INTEGER{
                app(1),
                cfg(2),
                inValidFileType(255)
            }
            MAX-ACCESS read-write
            STATUS current
            DESCRIPTION
                "This object indicates the ONT file type.
                 Options:
                 1. app(1)                - Application load
                 2. cfg(2)                - Configuration load
                 3. inValidFileType(255)  - Indicates that the query fails or no information is detected
                "
            ::= { hwXponOntLoadCtrlTable 1 }

        hwXponOntLoadServerIpAddr OBJECT-TYPE
            SYNTAX     IpAddress
            MAX-ACCESS    read-write
            STATUS current
            DESCRIPTION
                "This object indicates the server IP address."
            ::= { hwXponOntLoadCtrlTable 2 }

        hwXponOntLoadProtocol OBJECT-TYPE
            SYNTAX     INTEGER {
                tftp(1),
                ftp(2),
                sftp(3),
                inValidProtocol(255)
            }
            MAX-ACCESS    read-write
            STATUS current
            DESCRIPTION
                "This object indicates the transfer protocol.
                 Options:
                 1. tftp(1)               - TFTP
                 2. ftp(2)                - FTP
                 3. sftp(3)               - SFTP
                 4. inValidProtocol(255)  - Indicates that the query fails or no information is detected
                "
            ::= { hwXponOntLoadCtrlTable 3 }

        hwXponOntLoadFileName OBJECT-TYPE
            SYNTAX OCTET STRING (SIZE (0..80))
            MAX-ACCESS    read-write
            STATUS current
            DESCRIPTION
                "This object indicates the file name."
            ::= { hwXponOntLoadCtrlTable 4 }

        hwXponOntLoadUserName OBJECT-TYPE
            SYNTAX OCTET STRING (SIZE (0..16))
            MAX-ACCESS    read-write
            STATUS current
            DESCRIPTION
                "This object indicates the user name."
            ::= { hwXponOntLoadCtrlTable 5 }

        hwXponOntLoadPassword OBJECT-TYPE
            SYNTAX OCTET STRING (SIZE (0..16))
            MAX-ACCESS    read-write
            STATUS current
            DESCRIPTION
                "This object indicates the password."
            ::= { hwXponOntLoadCtrlTable 6 }

        hwXponOntLoadAdminStatus OBJECT-TYPE
            SYNTAX  INTEGER{
                start(1),
                stop(2),
                invalid(-1)
            }
            MAX-ACCESS    read-write
            STATUS current
            DESCRIPTION
                "This object indicates the ONT loading flag.
                 Options:
                 1. start(1)               - Indicates that the loading of ONT is started
                 2. stop(2)                - Indicates that the loading of ONT is stopped
                 3. invalid(-1)            - Indicates that the query fails or no information is detected
                "
            ::= { hwXponOntLoadCtrlTable 7 }

        hwXponOntLoadXmlIndex OBJECT-TYPE
            SYNTAX Integer32
            MAX-ACCESS    read-write
            STATUS current
            DESCRIPTION
                "F/S/P of ONT loading xml file.
                 If the value of the ACCESS clause is 'write-only',
                 then the value of the MAX-ACCESS clause MUST be 'read-write',
                 and the DESCRIPTION clause SHALL note that reading this
                 object will result in implementation-specific results.
                "
            ::= { hwXponOntLoadCtrlTable 8 }

        hwXponOntLoadXmlOntObjectIndex OBJECT-TYPE
            SYNTAX     Integer32 (-1 | 0..255)
            MAX-ACCESS   read-write
            STATUS current
            DESCRIPTION
                "ONT ID of loading xml file.
                 If the value of the ACCESS clause is 'write-only',
                 then the value of the MAX-ACCESS clause MUST be 'read-write',
                 and the DESCRIPTION clause SHALL note that reading
                 this object will result in implementation-specific results.
                "
            ::= { hwXponOntLoadCtrlTable 9 }

        hwXponOntLoadImageActiveMode OBJECT-TYPE
            SYNTAX  INTEGER {
                nextstartup(1),
                immediate(2),
                graceful(3),
                invalid(-1)
            }
            MAX-ACCESS    read-write
            STATUS current
            DESCRIPTION
                "Active mode of ont loading.
                 Options:
                 1. nextstartup(1)         - Indicates that the ONT takes effect after next startup
                 2. immediate(2)           - Indicates that the ONT takes effect immediately
                 3. graceful(3)            - Indicates that the ONT takes effect gracefully
                 4. invalid(-1)            - Indicates that the query fails or no information is detected
                "
            ::= { hwXponOntLoadCtrlTable 10 }

        hwXponOntLoadXmlAES128Key OBJECT-TYPE
            SYNTAX OCTET STRING (SIZE (0..16))
            MAX-ACCESS    read-write
            STATUS current
            DESCRIPTION
                "This object indicates the AES-128 cryptographic key for the ont xml file.
                 This AES-128 key is 128bits(16 Bytes).
                "
            ::= { hwXponOntLoadCtrlTable 11 }

        hwXponOntLoadServerPort OBJECT-TYPE
            SYNTAX     Integer32 ( 0..65535)
            MAX-ACCESS   read-write
            STATUS current
            DESCRIPTION
                "This object indicates the port of server for ont loading.
                 The TFTP port default value is 69.
		 The FTP port default value is 21.
                 The SFTP port default value is 22.
                "
            ::= { hwXponOntLoadCtrlTable 12 }

-- hwGponDeviceOntConfigInfoTable
        hwGponDeviceOntConfigInfoTable OBJECT-TYPE
            SYNTAX     SEQUENCE OF HwGponDeviceOntConfigInfoEntry
            MAX-ACCESS not-accessible
            STATUS     current
            DESCRIPTION
                "This table is used to create, modify, delete or query an ONT.
                 The index of this table is a combination of ifIndex and hwGponDeviceOntIndex.
                "
            ::= { hwXponDeviceControlObjects 43 }

        hwGponDeviceOntConfigInfoEntry OBJECT-TYPE
            SYNTAX     HwGponDeviceOntConfigInfoEntry
            MAX-ACCESS not-accessible
            STATUS     current
            DESCRIPTION
                "This table is used to create, modify, delete or query an ONT.
                 The index of this entry is a combination of ifIndex and hwGponDeviceOntIndex.
                "
            INDEX       { ifIndex, hwGponDeviceOntIndex}
            ::= { hwGponDeviceOntConfigInfoTable 1 }

        HwGponDeviceOntConfigInfoEntry ::=
            SEQUENCE {
                hwGponDeviceOntIndex                            Integer32,
                hwGponDeviceOntAuthMethod                       INTEGER,
                hwGponDeviceOntSn                               OCTET STRING,
                hwGponDeviceOntPassword                         OCTET STRING,
                hwGponDeviceOntTimeOut                          Integer32,
                hwGponDeviceOntManagementMode                   INTEGER,
                hwGponDeviceOntLineProfName                     OCTET STRING,
                hwGponDeviceOntServiceProfName                  OCTET STRING,
                hwGponDeviceOntDespt                            OCTET STRING,
                hwGponDeviceOntEntryStatus                      RowStatus,
                hwGponDeviceOntProtectSide                      INTEGER,
                hwGponDeviceOntPGMemberRole                     INTEGER,
                hwGponDeviceOntLoid                             OCTET STRING,
                hwGponDeviceOntCheckcode                        OCTET STRING,
                hwGponDeviceOntReregisterAuthMode               INTEGER,
                hwGponDeviceOntInfoAuthEffectMode               INTEGER,
                hwGponDeviceOntNniType                          INTEGER,
                hwGponDeviceOntManualSwitchChannelIfindex       Integer32
            }

        hwGponDeviceOntIndex  OBJECT-TYPE
            SYNTAX     Integer32
            MAX-ACCESS   not-accessible
            STATUS      current
            DESCRIPTION
                "This object indicates the ONT ID, range: 0-127."
            ::= { hwGponDeviceOntConfigInfoEntry 1}

        hwGponDeviceOntAuthMethod OBJECT-TYPE
            SYNTAX      INTEGER {
                sn(1),
                snpassword(2),
                alwayson(3),
                onceon(4),
                loidalwayson (5),
                loidonceon (6),
                loidcheckcodealwayson (7),
                loidcheckcodeonceon (8),
                snorpassword(9),
                invalid(-1)
            }
            MAX-ACCESS  read-write
            STATUS      current
            DESCRIPTION
                "This object indicates the authentication mode for the ONT.
                 Options:
                 1. sn(1)                        - Serial Number
                 2. snpassword(2)                - SN and password
                 3. alwayson(3)                  - Password + always-on
                 4. onceon(4)                    - Password + once-on
                 5. loidalwayson (5)             - LOID + always-on
                 6. loidonceon (6)               - LOID + once-on
                 7. loidcheckcodealwayson (7)    - LOID + CHECKCODE + always-on
                 8. loidcheckcodeonceon (8)      - LOID + CHECKCODE + once-on
                 9. snorpassword(9)              - SN or password
                 10.invalid(-1)                  - Indicates that the query fails or no information is detected
                 If the hwGponDeviceOntAuthMethod leaf is not specified for creation of a table instance, the default authentication mode sn(1) is used.
                "
            ::= { hwGponDeviceOntConfigInfoEntry 2 }

        hwGponDeviceOntSn OBJECT-TYPE
            SYNTAX      OCTET STRING  (SIZE (8))
            MAX-ACCESS  read-write
            STATUS      current
            DESCRIPTION
                "This object indicates the configured ONT serial number."
            ::= { hwGponDeviceOntConfigInfoEntry 3 }

        hwGponDeviceOntPassword OBJECT-TYPE
            SYNTAX      OCTET STRING
            MAX-ACCESS  read-write
            STATUS      current
            DESCRIPTION
                "This object indicates the ONT password.
                 GPON password size (0..10)
                 XG-PON password size (0..36)
                "
            ::= { hwGponDeviceOntConfigInfoEntry 4 }

        hwGponDeviceOntTimeOut OBJECT-TYPE
            SYNTAX      Integer32
            MAX-ACCESS  read-write
            STATUS      current
            DESCRIPTION
                "This object indicates the registered working period of the ONT, ranging from 1 to 168 hours.
                 The value (-1) indicates that there is no-aging time."
            ::= { hwGponDeviceOntConfigInfoEntry 5 }

        hwGponDeviceOntManagementMode OBJECT-TYPE
            SYNTAX      INTEGER {
                omci(1),
                snmp(2),
                extendFrame(3),
                invalid(-1)
            }
            MAX-ACCESS  read-write
            STATUS      current
            DESCRIPTION
                "This object indicates the ONT management mode, including OMCI and SNMP.
                 Options:
                 1. omci(1)                - OMCI
                 2. snmp(2)                - SNMP
                 3. extendFrame(3)        - extendFrame
                 4. invalid(-1)            - Indicates that the query fails or no information is detected
                "
            DEFVAL { omci }
            ::= { hwGponDeviceOntConfigInfoEntry 6 }

        hwGponDeviceOntLineProfName OBJECT-TYPE
            SYNTAX      OCTET STRING (SIZE (0..32))
            MAX-ACCESS  read-write
            STATUS      current
            DESCRIPTION
                "This object indicates the name of the profile that is bound to the ONT."
            ::= { hwGponDeviceOntConfigInfoEntry 7 }

        hwGponDeviceOntServiceProfName OBJECT-TYPE
            SYNTAX      OCTET STRING (SIZE (0..32))
            MAX-ACCESS  read-write
            STATUS      current
            DESCRIPTION
                "This object indicates the name of the service profile that is bound to the ONT."
            ::= { hwGponDeviceOntConfigInfoEntry 8 }

        hwGponDeviceOntDespt OBJECT-TYPE
            SYNTAX      OCTET STRING (SIZE (0..128))
            MAX-ACCESS  read-write
            STATUS      current
            DESCRIPTION
                "This object indicates the description of the ONT."
            ::= { hwGponDeviceOntConfigInfoEntry 9 }

        hwGponDeviceOntEntryStatus OBJECT-TYPE
            SYNTAX      RowStatus
            MAX-ACCESS  read-create
            STATUS      current
            DESCRIPTION
                "This object is used to create a new row or to modify or delete an existing row in this table.
                 Options:
                 1. createAndGo(4) -create a new instance of a conceptual row
                 2. destroy(6)     -delete the instances associated with an existing conceptual row
                 3. active(1)      -when this leaf is queried, the value is fixed to active(1)
                "
            ::= { hwGponDeviceOntConfigInfoEntry 10 }

        hwGponDeviceOntProtectSide OBJECT-TYPE
            SYNTAX      INTEGER {
                protectside(1),
                work(2)
            }
            MAX-ACCESS  read-write
            STATUS      current
            DESCRIPTION
                "This object indicates whether the ONT is the ONT on the protection side.
                 Options:
                 1. protectside(1)         - Indicates that the ONT is the ONT on the protection side
                 2. work(2)                - Indicates that the ONT is the ONT on the work side
                "
            ::= { hwGponDeviceOntConfigInfoEntry 11 }

            hwGponDeviceOntPGMemberRole OBJECT-TYPE
            SYNTAX INTEGER {
                work (1),
                protect (2),
                unjoined (-1)
            }
            MAX-ACCESS read-only
            STATUS current
            DESCRIPTION
                "This object indicates the role of the ont in the protect group.
                 Options:
                 1. work(1)                    - Indicates that the role of the ONT is work
                 2. protect(2)                 - Indicates that the role of the ONT is protection
                 3. unjoined(-1)               - Indicates that the ONT is not added to the protect group
                "
            ::= { hwGponDeviceOntConfigInfoEntry 12 }

            hwGponDeviceOntLoid OBJECT-TYPE
            SYNTAX     OCTET STRING (SIZE (0..24))
            MAX-ACCESS read-write
            STATUS current
            DESCRIPTION
                "The object indicates the LOID of the ONT."
            ::= { hwGponDeviceOntConfigInfoEntry 13 }

            hwGponDeviceOntCheckcode OBJECT-TYPE
            SYNTAX     OCTET STRING (SIZE (0..12))
            MAX-ACCESS read-write
            STATUS current
            DESCRIPTION
                "The object indicates the checkcode of the ONT."
            ::= { hwGponDeviceOntConfigInfoEntry 14 }

            hwGponDeviceOntReregisterAuthMode OBJECT-TYPE
            SYNTAX INTEGER {
                sn (1),
                snPassword (2),
                invalid (-1)
            }
            MAX-ACCESS read-write
            STATUS current
            DESCRIPTION
                 "Indicate the type of the ont re-register type for once-on authentication mode, if the ont authentication mode is not once-on,
                  the value is invalid. if the ont authentication mode is once-on, the default is snPassword.
                  Options:
                  1. sn(1)           -Indicate the re-register type of the ont is sn authentication type
                  2. snPassword(2)  -Indicate the re-register type of the ont is snPassword authentication type
                  3. invalid(-1)     -Indicate the re-register type of the ont is invalid
                  "
            ::= { hwGponDeviceOntConfigInfoEntry 15 }

            hwGponDeviceOntInfoAuthEffectMode OBJECT-TYPE
            SYNTAX INTEGER {
                   immediate (1),
                   nextstartup (2),
                   invalid (-1)
            }
            MAX-ACCESS read-write
            STATUS current
            DESCRIPTION
                 "Indicates the effect taking mode after the ONT authentication mode is changed. The default effect taking mode is immediate.
                  Options:
                  1. immediate (1)    -Indicates that the change will take effect immediately.
                  2. nextstartup (2)  -Indicates that the change will take effect when the ONT goes online next time.
                  3. invalid (-1)     -Indicates that the effect taking mode is invalid.
            "
            ::= { hwGponDeviceOntConfigInfoEntry 16 }

            hwGponDeviceOntNniType OBJECT-TYPE
            SYNTAX INTEGER {
                rate2dot5G1dot25G (1),
                rate10G2dot5G (2),
                rate10G10G (3),
                auto (4),
                invalid (-1)
            }
            MAX-ACCESS read-write
            STATUS current
            DESCRIPTION
                "This object indicates the NNI type of the ONT.
                 Options:
                 1. rate2dot5G1dot25G (1) -Downstream rate 2.5Gbps, upstream rate 1.25Gbps.
                 2. rate10G2dot5G (2)     -Downstream rate 10Gbps, upstream rate 2.5Gbps.
                 3. rate10G10G (3)        -Downstream rate 10Gbps, upstream rate 10Gbps.
                 4. auto(4)               -Indicates the actual ont nni type is automatically selected.
                 5. invalid (-1)          -Indicates the invalid value.
                "
            ::= { hwGponDeviceOntConfigInfoEntry 17 }

            hwGponDeviceOntManualSwitchChannelIfindex OBJECT-TYPE
            SYNTAX Integer32
            MAX-ACCESS read-write
            STATUS current
            DESCRIPTION
                 "Indicates the destination channel's ifindex that the ont switch to.
                  Only the ont under a dynamic channel group support to switch channel.
                 "
            ::= { hwGponDeviceOntConfigInfoEntry 18 }


-- hwGponDeviceOntExtendConfigTable
        hwGponDeviceOntExtendConfigTable OBJECT-TYPE
            SYNTAX     SEQUENCE OF HwGponDeviceOntExtendConfigEntry
            MAX-ACCESS not-accessible
            STATUS     current
            DESCRIPTION
                "This is the ONT extend function configuration table.
                 The index of this table is a combination of ifIndex and hwGponDeviceOntIndex.
                "
            ::= { hwXponDeviceControlObjects 44 }

        hwGponDeviceOntExtendConfigEntry OBJECT-TYPE
            SYNTAX     HwGponDeviceOntExtendConfigEntry
            MAX-ACCESS not-accessible
            STATUS     current
            DESCRIPTION
                "This is the ONT extend function configuration table.
                 The index of this entry is a combination of ifIndex and hwGponDeviceOntIndex.
                "
            INDEX       { ifIndex, hwGponDeviceOntIndex}
            ::= { hwGponDeviceOntExtendConfigTable 1 }

        HwGponDeviceOntExtendConfigEntry ::=
            SEQUENCE {
                hwGponDeviceOntCfgAlarmProfileName              OCTET STRING,
                hwGponDeviceOntCfgSnmpProfileName               OCTET STRING,
                hwGponDeviceOntExtCfgOpticAlarmProfileName      OCTET STRING
            }

        hwGponDeviceOntCfgAlarmProfileName OBJECT-TYPE
            SYNTAX      OCTET STRING (SIZE (0..33))
            MAX-ACCESS  read-write
            STATUS      current
            DESCRIPTION
                "The name of the ONT alarm profile."
            ::= { hwGponDeviceOntExtendConfigEntry 1 }

        hwGponDeviceOntCfgSnmpProfileName OBJECT-TYPE
            SYNTAX      OCTET STRING (SIZE (0..32))
            MAX-ACCESS  read-write
            STATUS      current
            DESCRIPTION
                "The name of the ONT SNMP profile."
            ::= { hwGponDeviceOntExtendConfigEntry 2 }

        hwGponDeviceOntExtCfgOpticAlarmProfileName OBJECT-TYPE
            SYNTAX      OCTET STRING (SIZE (0..32))
            MAX-ACCESS  read-write
            STATUS      current
            DESCRIPTION
                "This object indicates the name of the optical alarm profile that is bound to the ONT."
            ::= { hwGponDeviceOntExtendConfigEntry 3 }

-- HwGponDeviceOntVersionInfoTable
        hwGponDeviceOntVersionInfoTable OBJECT-TYPE
            SYNTAX     SEQUENCE OF HwGponDeviceOntVersionInfoEntry
            MAX-ACCESS not-accessible
            STATUS     current
            DESCRIPTION
                "This is the ONT version information table.
                 The index of this table is a combination of ifIndex and hwGponDeviceOntIndex.
                "
            ::= { hwXponDeviceControlObjects 45 }

        hwGponDeviceOntVersionInfoEntry OBJECT-TYPE
            SYNTAX     HwGponDeviceOntVersionInfoEntry
            MAX-ACCESS not-accessible
            STATUS     current
            DESCRIPTION
                "This is the ONT version information table.
                 The index of this entry is a combination of ifIndex and hwGponDeviceOntIndex.
                "
            INDEX       { ifIndex, hwGponDeviceOntIndex}
            ::= { hwGponDeviceOntVersionInfoTable 1 }

        HwGponDeviceOntVersionInfoEntry ::=
            SEQUENCE {
                hwGponDeviceOntVersion              OCTET STRING,
                hwGponDeviceOntVendorId             Integer32,
                hwGponDeviceOntProductId            Integer32,
                hwGponDeviceOntEquipmentId          OCTET STRING,
                hwGponDeviceOntMainSoftVer          OCTET STRING,
                hwGponDeviceOntStandbySoftVer       OCTET STRING,
                hwGponDeviceOntSoftwareWorkMode     INTEGER,
                hwGponDeviceOntCustomizedInfo       OCTET STRING,
                hwGponDeviceOntEquipmentSn          OCTET STRING,
                hwGponDeviceOntMac                  MacAddress
            }

        hwGponDeviceOntVersion OBJECT-TYPE
            SYNTAX      OCTET STRING (SIZE (0..15))
            MAX-ACCESS  read-only
            STATUS      current
            DESCRIPTION
                "The ONT version number."
            ::= { hwGponDeviceOntVersionInfoEntry 1 }

        hwGponDeviceOntVendorId OBJECT-TYPE
            SYNTAX      Integer32
            MAX-ACCESS  read-only
            STATUS      current
            DESCRIPTION
                "This object indicates the ONT VendorID."
            ::= { hwGponDeviceOntVersionInfoEntry 2 }

        hwGponDeviceOntProductId OBJECT-TYPE
            SYNTAX      Integer32
            MAX-ACCESS  read-only
            STATUS      current
            DESCRIPTION
                "This object indicates the ONT productID."
            ::= { hwGponDeviceOntVersionInfoEntry 3 }

        hwGponDeviceOntEquipmentId OBJECT-TYPE
            SYNTAX      OCTET STRING (SIZE(0..20))
            MAX-ACCESS  read-only
            STATUS      current
            DESCRIPTION
                "This object indicates the ONT equipmentID."
            ::= { hwGponDeviceOntVersionInfoEntry 4 }

        hwGponDeviceOntMainSoftVer OBJECT-TYPE
            SYNTAX      OCTET STRING (SIZE(0..14))
            MAX-ACCESS  read-only
            STATUS      current
            DESCRIPTION
                "The active softerware version of the ONT."
            ::= { hwGponDeviceOntVersionInfoEntry 5 }

        hwGponDeviceOntStandbySoftVer OBJECT-TYPE
            SYNTAX      OCTET STRING (SIZE(0..14))
            MAX-ACCESS  read-only
            STATUS      current
            DESCRIPTION
                "The standby software version of the ONT."
            ::= { hwGponDeviceOntVersionInfoEntry 6 }

        hwGponDeviceOntSoftwareWorkMode OBJECT-TYPE
            SYNTAX  INTEGER {
               normal (1),
               survivalmode (2)
            }
            MAX-ACCESS read-only
            STATUS current
            DESCRIPTION
                "The object indicates the software working mode of the GPON ONT.
                 Options:
                 1. normal(1)             - Normal
                 2. survivalmode(2)       - Survival mode
                "
            ::= { hwGponDeviceOntVersionInfoEntry 7}

         hwGponDeviceOntCustomizedInfo  OBJECT-TYPE
            SYNTAX      OCTET STRING (SIZE(0..24))
            MAX-ACCESS  read-only
            STATUS      current
            DESCRIPTION
                "This object indicates the ONT customize information.
		"
            ::= { hwGponDeviceOntVersionInfoEntry 8 }

        hwGponDeviceOntEquipmentSn  OBJECT-TYPE
            SYNTAX   OCTET STRING (SIZE (0..25))
            MAX-ACCESS  read-only
            STATUS   current
            DESCRIPTION
                "This object indicates the ONT Equipment Sn."
            ::= { hwGponDeviceOntVersionInfoEntry 9 }

        hwGponDeviceOntMac  OBJECT-TYPE
            SYNTAX     MacAddress
            MAX-ACCESS  read-only
            STATUS   current
            DESCRIPTION
                "This object indicates the ONT MAC address."
            ::= { hwGponDeviceOntVersionInfoEntry 10 }

-- HwGponDeviceOntControlInfoTable
        hwGponDeviceOntControlInfoTable OBJECT-TYPE
            SYNTAX     SEQUENCE OF HwGponDeviceOntControlInfoEntry
            MAX-ACCESS not-accessible
            STATUS     current
            DESCRIPTION
                "This is the control table of the ONT.
                 The index of this table is a combination of ifIndex and hwGponDeviceOntIndex.
                "
            ::= { hwXponDeviceControlObjects 46 }

        hwGponDeviceOntControlInfoEntry OBJECT-TYPE
            SYNTAX     HwGponDeviceOntControlInfoEntry
            MAX-ACCESS not-accessible
            STATUS     current
            DESCRIPTION
                "This is the control table of the ONT.
                 The index of this entry is a combination of ifIndex and hwGponDeviceOntIndex.
                "
            INDEX       { ifIndex, hwGponDeviceOntIndex}
            ::= { hwGponDeviceOntControlInfoTable 1 }

        HwGponDeviceOntControlInfoEntry ::=
            SEQUENCE {
                hwGponDeviceOntControlActive                     INTEGER,
                hwGponDeviceOntControlReset                      INTEGER,
                hwGponDeviceOntControlReRegister                 INTEGER,
                hwGponDeviceOntControlReDiscovery                INTEGER,
                hwGponDeviceOntControlRunStatus                  INTEGER,
                hwGponDeviceOntControlConfigStatus               INTEGER,
                hwGponDeviceOntControlDiscoveryStatus            INTEGER,
                hwGponDeviceOntControlMatchStatus                INTEGER,
                hwGponDeviceOntControlDbaStatus                  INTEGER,
                hwGponDeviceOntControlRanging                    Integer32,
                hwGponDeviceOntControlMacCount                   Integer32,
                hwGponDeviceOntControlLastUpTime                 DateAndTime,
                hwGponDeviceOntControlLastDownTime               DateAndTime,
                hwGponDeviceOntControlLastDownCause              Integer32,
                hwGponDeviceOntControlLastDyingGaspTime          DateAndTime,
                hwGponDeviceOntControlIsolationState             INTEGER,
                hwGponDeviceOntControlBatteryCurStatus           INTEGER,
                hwGponDeviceOntControlTcontNumCombined           Integer32,
                hwGponDeviceOntControlLastRanging                Integer32,
                hwGponDeviceOntControlActualSn                   OCTET STRING

            }

        hwGponDeviceOntControlActive OBJECT-TYPE
            SYNTAX      INTEGER {
                activate(1),
                deactivate(2),
                invalid(-1)
            }
            MAX-ACCESS  read-write
            STATUS      current
            DESCRIPTION
                "This object is used to activate or deactivate an ONT.
                 Options:
                 1. activate(1)             - Activates an ONT
                 2. deactivate(2)           - Deactivate an ONT
                 3. invalid(-1)             - Indicates that the query fails or no information is detected
                "
            DEFVAL { activate }
            ::= { hwGponDeviceOntControlInfoEntry 1 }

        hwGponDeviceOntControlReset OBJECT-TYPE
            SYNTAX      INTEGER {
                reset(1),
                invalid(-1)
            }
            MAX-ACCESS  read-write
            STATUS      current
            DESCRIPTION
                "This object is used to reset an ONT.
                 Options:
                 1. reset(1)          - Reset an ONT
                 2. invalid(-1)       - Indicates that the query fails or no information is detected
                "
            ::= { hwGponDeviceOntControlInfoEntry 2 }

        hwGponDeviceOntControlReRegister OBJECT-TYPE
            SYNTAX      INTEGER {
                reRegister(1),
                invalid(-1)
            }
            MAX-ACCESS  read-write
            STATUS      current
            DESCRIPTION
                "This object is used to re-register an ONT.
                 Options:
                 1. reRegister(1)     - Re-register an ONT
                 2. invalid(-1)       - Indicates that the query fails or no information is detected
                "
            ::= { hwGponDeviceOntControlInfoEntry 3 }

        hwGponDeviceOntControlReDiscovery OBJECT-TYPE
            SYNTAX      INTEGER {
                rediscovery(1),
                invalid(-1)
            }
            MAX-ACCESS  read-write
            STATUS      current
            DESCRIPTION
                "This object is used to reset the discovery status of an ONT.
                 If the authentication mode is once-on(4), after performing the rediscovery operation,
                 the registered working period is re-timed.
                 Options:
                 1. rediscovery(1)     - Reset the discovery status of an ONT
                 2. invalid(-1)        - Indicates that the query fails or no information is detected
                "
            ::= { hwGponDeviceOntControlInfoEntry 4 }

        hwGponDeviceOntControlRunStatus OBJECT-TYPE
            SYNTAX       INTEGER {
                up(1),
                down(2),
                invalid(-1)
            }
            MAX-ACCESS  read-only
            STATUS      current
            DESCRIPTION
                "This object indicates the ONT running status.
                 Options:
                 1. up(1)          - Normal
                 2. down(2)        - Fault
                 3. invalid(-1)    - Indicates that the query fails or no information is detected
                "
            ::= { hwGponDeviceOntControlInfoEntry 15 }

        hwGponDeviceOntControlConfigStatus OBJECT-TYPE
            SYNTAX      INTEGER {
                initialization(1),
                normal(2),
                failed(3),
                noresume(4),
                config(5),
                invalid(-1)
            }
            MAX-ACCESS  read-only
            STATUS      current
            DESCRIPTION
                "This is the ONT configuration resume status. If it is failed(3),
                 the ONT is down and the service is interrupted. If the config status is noresume (4),
                 set the resume policy as resume for the system and re-register the ONT.
                 Options:
                 1. initialization(1)     - Indicates that the ONT configuration resume status is initialization
                 2. normal(2)             - Indicates that the ONT configuration resume status is normal
                 3. failed(3)             - Indicates that the ONT configuration resume status is failed
                 4. noresume(4)           - Indicates that the ONT configuration resume status is not resumed
                 5. config(5)             - Indicates that the ONT configuration resume status is configuration
                 6. invalid(-1)           - Indicates that the query fails or no information is detected
                "
            ::= { hwGponDeviceOntControlInfoEntry 16 }

        hwGponDeviceOntControlDiscoveryStatus OBJECT-TYPE
            SYNTAX      INTEGER {
                on(1),
                off(2),
                invalid(-1)
            }
            MAX-ACCESS  read-only
            STATUS      current
            DESCRIPTION
                "This object indicates the ONT discovery state.
                 Options:
                 1. on(1)               - Indicates that the ONT discovery state is on
                 2. off(2)              - Indicates that the ONT discovery state is off
                 3. invalid(-1)         - Indicates that the query fails or no information is detected
                "
            ::= { hwGponDeviceOntControlInfoEntry 17 }

        hwGponDeviceOntControlMatchStatus OBJECT-TYPE
            SYNTAX       INTEGER {
                initialization(1),
                match(2),
                mismatch(3),
                invalid(-1)
            }
            MAX-ACCESS   read-only
            STATUS       current
            DESCRIPTION
                "This object indicates the ONT match status.
                 Options:
                 1. initialization(1)        - Indicates that the ONT is initialization
                 2. match(2)                 - Indicates that the ONT is matched
                 3. mismatch(3)              - Indicates that the ONT is mismatched
                 4. invalid(-1)              - Indicates that the query fails or no information is detected
                "
            ::= { hwGponDeviceOntControlInfoEntry 18 }

        hwGponDeviceOntControlDbaStatus OBJECT-TYPE
            SYNTAX       INTEGER {
                nsr(1),
                sr(2),
                invalid(-1)
            }
            MAX-ACCESS  read-only
            STATUS      current
            DESCRIPTION
                "This object indicates the DBA report status.
                 Options:
                 1. nsr(1)        - NSR
                 2. sr(2)         - SR
                 3. invalid(-1)   - Indicates that the query fails or no information is detected
                "
            ::= { hwGponDeviceOntControlInfoEntry 19 }

        hwGponDeviceOntControlRanging OBJECT-TYPE
            SYNTAX      Integer32
            MAX-ACCESS  read-only
            STATUS      current
            DESCRIPTION
                "This object indicates the result of the ONT ranging.
                 Unit: m
                 Options:
                 1. invalid (-1)  - Indicates that the query fails or no information is detected.
                "
            ::= { hwGponDeviceOntControlInfoEntry 20 }

        hwGponDeviceOntControlMacCount OBJECT-TYPE
            SYNTAX      Integer32
            MAX-ACCESS  read-only
            STATUS      current
            DESCRIPTION

                "This object indicates the number of MAC addresses that are learned by the ONT."
            ::= { hwGponDeviceOntControlInfoEntry 21 }

        hwGponDeviceOntControlLastUpTime OBJECT-TYPE
            SYNTAX      DateAndTime
            MAX-ACCESS  read-only
            STATUS      current
            DESCRIPTION
                "This object indicates the time when the ONT last went online."
            ::= { hwGponDeviceOntControlInfoEntry 22 }

        hwGponDeviceOntControlLastDownTime OBJECT-TYPE
            SYNTAX      DateAndTime
            MAX-ACCESS  read-only
            STATUS      current
            DESCRIPTION
                "This object indicates the time when the ONT last went offline."
            ::= { hwGponDeviceOntControlInfoEntry 23 }

        hwGponDeviceOntControlLastDownCause OBJECT-TYPE
            SYNTAX       Integer32
            MAX-ACCESS   read-only
            STATUS       current
            DESCRIPTION
                "This object indicates the reason why the ONT last went offline.
                 The value (1) indicates that the reason is LOS(Loss of signal),
                 The value (2) indicates that the reason is LOSi(Loss of signal for ONUi) or LOBi (Loss of burst for ONUi),
                 The value (3) indicates that the reason is LOFI(Loss of frame of ONUi),
                 The value (4) indicates that the reason is SFI(Signal fail of ONUi),
                 The value (5) indicates that the reason is LOAI(Loss of acknowledge with ONUi),
                 The value (6) indicates that the reason is LOAMI(Loss of PLOAM for ONUi),
                 The value (7) indicates that the reason is deactive ONT fails,
                 The value (8) indicates that the reason is deactive ONT success,
                 The value (9) indicates that the reason is reset ONT,
                 The value (10) indicates that the reason is re-register ONT,
                 The value (11) indicates that the reason is pop up fail,
                 The value (13) indicates that the reason is dying-gasp,
                 The value (15) indicates that the reason is LOKI(Loss of key synch with ONUi),
                 The value (18) indicates that the reason is deactived ONT due to the ring,
                 The value (30) indicates that the reason is shut down ONT optical module,
                 The value (31) indicates that the reason is reset ONT by ONT command,
                 The value (32) indicates that the reason is reset ONT by ONT reset button,
                 The value (33) indicates that the reason is reset ONT by ONT software,
                 The value (34) indicates that the reason is deactived ONT due to broadcast attack,
                 The value (35) indicates that the reason is operator check fail,
                 The value (37) indicates that the reason is a rogue ONT detected by itself,
                 The value (-1) indicates that the query fails.
                 "
            ::= { hwGponDeviceOntControlInfoEntry 24 }

        hwGponDeviceOntControlLastDyingGaspTime OBJECT-TYPE
            SYNTAX      DateAndTime
            MAX-ACCESS  read-only
            STATUS      current
            DESCRIPTION
                "This object indicates the time when the ONT last went down due to Dying Gasp."
            ::= { hwGponDeviceOntControlInfoEntry 25 }

        hwGponDeviceOntControlIsolationState  OBJECT-TYPE
            SYNTAX  INTEGER {
                normal (0),
                isolated (1)
            }
            MAX-ACCESS  read-only
            STATUS  current
            DESCRIPTION
                "This object indicates the ONT isolation status.
                 Options:
                 1. normal(0)          - Indicates that the ONT is normal
                 2. isolated(1)        - Indicates that the ONT is isolated
                "
            ::= { hwGponDeviceOntControlInfoEntry 26 }

        hwGponDeviceOntControlBatteryCurStatus  OBJECT-TYPE
            SYNTAX  INTEGER{
                notSupport (0),
                charge (1),
                discharge (2),
                holding (3),
                supportButInvalid (4),
                unknownStatus (-1)
            }
            MAX-ACCESS  read-only
            STATUS  current
            DESCRIPTION
                "This object indicates the ONT battery status.
                 Options:
                 1. notSupport(0)         - Not support
                 2. charge(1)             - Charge state
                 3. discharge(2)          - Discharge state
                 4. holding(3)            - Holding state
                 5. supportButInvalid(4)  - Provisioned and present but cannot recharge
                 6. unknownStatus(-1)     - Indicates that the query fails or no information is detected
                "
            ::= { hwGponDeviceOntControlInfoEntry 27 }

    hwGponDeviceOntControlTcontNumCombined OBJECT-TYPE
       SYNTAX Integer32
       MAX-ACCESS read-only
       STATUS current
       DESCRIPTION
                "The number of the combined T-CONTs."
       ::= { hwGponDeviceOntControlInfoEntry 28 }

        hwGponDeviceOntControlLastRanging OBJECT-TYPE
            SYNTAX      Integer32
            MAX-ACCESS  read-only
            STATUS      current
            DESCRIPTION
                "This object indicates the result of the ONT last ranging.
                 Unit: m
                 Options:
                 1. invalid (-1)  - Indicates that the query fails or no information is detected.
                 "
            ::= { hwGponDeviceOntControlInfoEntry 29 }

	hwGponDeviceOntControlActualSn OBJECT-TYPE
	        SYNTAX OCTET STRING (SIZE (8))
	        MAX-ACCESS read-only
	        STATUS  current
	        DESCRIPTION
	            "The ONT's actual serial number."
	        ::= { hwGponDeviceOntControlInfoEntry 30 }

-- HwGponDeviceOntCfgCapabilityTable
        hwGponDeviceOntCfgCapabilityTable OBJECT-TYPE
            SYNTAX     SEQUENCE OF HwGponDeviceOntCfgCapabilityEntry
            MAX-ACCESS not-accessible
            STATUS     current
            DESCRIPTION
                "The ONT configuration capability table.
                 The index of this table is a combination of ifIndex and hwGponDeviceOntIndex.
                "
            ::= { hwXponDeviceControlObjects 47 }

        hwGponDeviceOntCfgCapabilityEntry OBJECT-TYPE
            SYNTAX     HwGponDeviceOntCfgCapabilityEntry
            MAX-ACCESS not-accessible
            STATUS     current
            DESCRIPTION
                "The ONT configuration capability table.
                 The index of this entry is a combination of ifIndex and hwGponDeviceOntIndex.
                "
            INDEX       { ifIndex, hwGponDeviceOntIndex }
            ::= { hwGponDeviceOntCfgCapabilityTable 1 }

        HwGponDeviceOntCfgCapabilityEntry ::=
            SEQUENCE {
                hwGponDeviceOntCfgCapManagementMode     INTEGER,
                hwGponDeviceOntCfgCapEthNum             Integer32,
                hwGponDeviceOntCfgCapPotsNum            Integer32,
                hwGponDeviceOntCfgCapIPSupport          INTEGER,
                hwGponDeviceOntCfgCapTdmPortType        INTEGER,
                hwGponDeviceOntCfgCapTdmServiceType     INTEGER,
                hwGponDeviceOntCfgCapTdmNum             Integer32,
                hwGponDeviceOntCfgCapMocaNum            Integer32,
                hwGponDeviceOntCfgCapCatvUniNum         Integer32,
                hwGponDeviceOntCfgCapGemNum             Integer32,
                hwGponDeviceOntCfgCapGemMappingMode     INTEGER,
                hwGponDeviceOntCfgCapTcontNum           Integer32,
                hwGponDeviceOntCfgCapFCType             INTEGER,
                hwGponDeviceOntCfgCapVdslPortNum        Integer32
            }

        hwGponDeviceOntCfgCapManagementMode OBJECT-TYPE
            SYNTAX      INTEGER {
                omci(1),
                snmp(2),
                extendFrame(3),
                invalid(-1)
            }
            MAX-ACCESS   read-only
            STATUS       current
            DESCRIPTION
                "This object indicates the ONT's management mode, including omci and snmp.
                 Options:
                 1. omci(1)            - OMCI
                 2. snmp(2)            - SNMP
                 3. extendFrame(3)     - Extend Frame
                 4. invalid(-1)        - Indicates that the query fails or no information is detected
                "
            ::= { hwGponDeviceOntCfgCapabilityEntry 1 }

        hwGponDeviceOntCfgCapEthNum OBJECT-TYPE
            SYNTAX       Integer32
            MAX-ACCESS   read-only
            STATUS       current
            DESCRIPTION
                "This object indicates the number of ethernet ports.
                 A special value of 0xFE (254) indicates the number of port is adaptive.
                 The value is -1 when the query fails or no information is detected."
            ::= { hwGponDeviceOntCfgCapabilityEntry 2 }

        hwGponDeviceOntCfgCapPotsNum OBJECT-TYPE
            SYNTAX       Integer32
            MAX-ACCESS   read-only
            STATUS       current
            DESCRIPTION
                "This object indicates the number of POTS ports.
                 A special value of 0xFE (254) indicates the number of port is adaptive
                 The value is -1 when the query fails or no information is detected."
            ::= { hwGponDeviceOntCfgCapabilityEntry 3 }

        hwGponDeviceOntCfgCapIPSupport OBJECT-TYPE
            SYNTAX       INTEGER{
                dhcp(1),
                static(2),
                unconfiguration(3),
                pppoe(4),
                invalid(-1)
            }
            MAX-ACCESS   read-only
            STATUS       current
            DESCRIPTION
                "This object indicates the IP address configuration mode.
                 Options:
                 1. dhcp(1)               - DHCP
                 2. static(2)             - Indicates that the IP address configuration mode is static
                 3. unconfiguration(3)    - Indicates that the IP address is not configuration
                 4. pppoe(4)              - Indicates that the IP address configuration mode is pppoe
                 5. invalid(-1)           - Indicates that the query fails or no information is detected
                "
            ::= { hwGponDeviceOntCfgCapabilityEntry 4 }

        hwGponDeviceOntCfgCapTdmPortType OBJECT-TYPE
            SYNTAX       INTEGER{
                t1(13),
                e1(14),
                invalid(-1)
            }
            MAX-ACCESS   read-only
            STATUS       current
            DESCRIPTION
                "This object indicates the TDM port type.
                 Options:
                 1. t1(13)             - T1
                 2. e1(14)             - E1
                 3. invalid(-1)        - Indicates that the query fails or no information is detected
                "
            ::= { hwGponDeviceOntCfgCapabilityEntry 5 }

        hwGponDeviceOntCfgCapTdmServiceType OBJECT-TYPE
            SYNTAX       INTEGER{
                tdmovergem(1),
                cesop(2),
                invalid(-1)
            }
            MAX-ACCESS   read-only
            STATUS       current
            DESCRIPTION
                "This object indicates the TDM service type.
                 Options:
                 1. tdmovergem(1)     - Tdm over gem
                 2. cesop(2)          - Cesop
                 3. invalid(-1)       - Indicates that the query fails or no information is detected
                "
            ::= { hwGponDeviceOntCfgCapabilityEntry 6 }

        hwGponDeviceOntCfgCapTdmNum OBJECT-TYPE
            SYNTAX       Integer32
            MAX-ACCESS   read-only
            STATUS       current
            DESCRIPTION
                "This object indicates the number of TDM ports.
                 The value is -1 when the query fails or no information is detected."
            ::= { hwGponDeviceOntCfgCapabilityEntry 7 }

        hwGponDeviceOntCfgCapMocaNum OBJECT-TYPE
            SYNTAX       Integer32
            MAX-ACCESS   read-only
            STATUS       current
            DESCRIPTION
                "This object indicates the number of MOCA ports.
                 The value is -1 when the query fails or no information is detected."
            ::= { hwGponDeviceOntCfgCapabilityEntry 8 }

        hwGponDeviceOntCfgCapCatvUniNum OBJECT-TYPE
            SYNTAX       Integer32
            MAX-ACCESS   read-only
            STATUS       current
            DESCRIPTION
                "This object indicates the number of CATV UNI ports.
                 A special value of 0xFE (254) indicates the number of port is adaptive
                 The value is -1 when the query fails or no information is detected."
            ::= { hwGponDeviceOntCfgCapabilityEntry 9 }

        hwGponDeviceOntCfgCapGemNum OBJECT-TYPE
            SYNTAX       Integer32
            MAX-ACCESS   read-only
            STATUS       current
            DESCRIPTION
                "This object indicates the number of GEM ports.
                 The value is -1 when the query fails or no information is detected."
            ::= { hwGponDeviceOntCfgCapabilityEntry 10 }

        hwGponDeviceOntCfgCapGemMappingMode OBJECT-TYPE
            SYNTAX       INTEGER{
                vlan(1),
                pri8021p(2),
                vlanpri(3),
                port(4),
                vlanport(5),
                portpri(6),
                vlanpriport(7),
                e1t1port(8),
                iptos(9),
                vlaniptos(10),
                invalid(-1)
            }
            MAX-ACCESS   read-only
            STATUS       current
            DESCRIPTION
                "This object indicates the mapping mode.
                 Options:
                 1. vlan(1)            - The mapping mode is vlan
                 2. pri8021p(2)        - The mapping mode is 802.1p
                 3. vlanpri(3)         - The mapping mode is vlan and 802.1p
                 4. port(4)            - The mapping mode is port
                 5. vlanport(5)        - The mapping mode is vlan and port
                 6. portpri(6)         - The mapping mode is port and 802.1p
                 7. vlanpriport(7)     - The mapping mode is vlan, port and 802.1p
                 8. e1t1port(8)        - The mapping mode is the port of e1 and t1
                 9. iptos(9)           - The mapping mode is iptos
                 10. vlaniptos(10)     - The mapping mode is vlan and iptos
                 11. invalid(-1)       - Indicates that the query fails or no information is detected
                "
            ::= { hwGponDeviceOntCfgCapabilityEntry 11 }

        hwGponDeviceOntCfgCapTcontNum OBJECT-TYPE
            SYNTAX       Integer32
            MAX-ACCESS   read-only
            STATUS       current
            DESCRIPTION
                "This object indicates the number of T-CONTs.
                 The value is -1 when the query fails or no information is detected."
            ::= { hwGponDeviceOntCfgCapabilityEntry 12 }

        hwGponDeviceOntCfgCapFCType OBJECT-TYPE
            SYNTAX       INTEGER{
                pq(1),
                gemportcar(2),
                flowcar(3),
                invalid(-1)
            }
            MAX-ACCESS   read-only
            STATUS       current
            DESCRIPTION
                "This object indicates the type of flow control.
                 Options:
                 1. pq(1)              - The type of flow control is PQ
                 2. gemportcar(2)      - The type of flow control is the gemportcar
                 3. flowcar(3)         - The type of flow control is the flowcar
                 4. invalid(-1)        - Indicates that the query fails or no information is detected
                "
            ::= { hwGponDeviceOntCfgCapabilityEntry 13 }

        hwGponDeviceOntCfgCapVdslPortNum OBJECT-TYPE
            SYNTAX       Integer32
            MAX-ACCESS   read-only
            STATUS       current
            DESCRIPTION
                "This object indicates the number of VDSL ports.
                 A special value of 0xFE (254) indicates the number of port is adaptive.
                 The value is -1 when the query fails or no information is detected."
            ::= { hwGponDeviceOntCfgCapabilityEntry 14 }

-- HwGponDeviceAutoFindOntInfoTable
        hwGponDeviceAutoFindOntInfoTable OBJECT-TYPE
            SYNTAX  SEQUENCE OF HwGponDeviceAutoFindOntInfoEntry
            MAX-ACCESS  not-accessible
            STATUS  current
            DESCRIPTION
                "This table is used to query the information about the auto-found ONTs in the system.
                 The index of this table is a combination of ifIndex and hwGponDeviceAutoFindOntInfoOntIndex.
                "
            ::= { hwXponDeviceControlObjects  48 }

        hwGponDeviceAutoFindOntInfoEntry OBJECT-TYPE
            SYNTAX  HwGponDeviceAutoFindOntInfoEntry
            MAX-ACCESS  not-accessible
            STATUS  current
            DESCRIPTION
                "This table is used to query the information about the auto-found ONTs in the system.
                 The index of this entry is a combination of ifIndex and hwGponDeviceAutoFindOntInfoOntIndex.
                "
            INDEX  { ifIndex, hwGponDeviceAutoFindOntInfoOntIndex }
            ::= { hwGponDeviceAutoFindOntInfoTable 1 }

        HwGponDeviceAutoFindOntInfoEntry ::=
            SEQUENCE {
                hwGponDeviceAutoFindOntInfoOntIndex              Integer32,
                hwGponDeviceAutoFindOntInfoSn                    OCTET STRING,
                hwGponDeviceAutoFindOntInfoPassword              OCTET STRING,
                hwGponDeviceAutoFindOntInfoOntVendorId           Integer32,
                hwGponDeviceAutoFindOntInfoOntVer                OCTET STRING,
                hwGponDeviceAutoFindOntInfoOntMainSoftVer        OCTET STRING,
                hwGponDeviceAutoFindOntInfoOntEquipmentId        OCTET STRING,
                hwGponDeviceAutoFindOntInfoOntAutoFindTime       DateAndTime,
                hwGponDeviceAutoFindOntInfoLoid                  OCTET STRING,
                hwGponDeviceAutoFindOntInfoCheckcode             OCTET STRING,
                hwGponDeviceAutoFindOntInfoCustomizedInfo        OCTET STRING,
                hwGponDeviceAutoFindOntInfoOntNniType            INTEGER,
                hwGponDeviceAutoFindOntInfoEquipmentSn           OCTET STRING,
                hwGponDeviceAutoFindOntInfoMac                   MacAddress
     }

        hwGponDeviceAutoFindOntInfoOntIndex OBJECT-TYPE
            SYNTAX      Integer32
            MAX-ACCESS  not-accessible
            STATUS      current
            DESCRIPTION
                "The index of the auto-found ONT."
            ::= { hwGponDeviceAutoFindOntInfoEntry 1 }

        hwGponDeviceAutoFindOntInfoSn OBJECT-TYPE
            SYNTAX     OCTET STRING  (SIZE (8))
            MAX-ACCESS  read-only
            STATUS     current
            DESCRIPTION
                "This object indicates the ONT serial number."
            ::= { hwGponDeviceAutoFindOntInfoEntry 2 }

        hwGponDeviceAutoFindOntInfoPassword OBJECT-TYPE
            SYNTAX     OCTET STRING
            MAX-ACCESS  read-only
            STATUS     current
            DESCRIPTION
                "This object indicates the ONT password.
                 GPON password size (0..10)
                 XG-PON password size (0..36)
                "
            ::= { hwGponDeviceAutoFindOntInfoEntry 3 }

        hwGponDeviceAutoFindOntInfoOntVendorId OBJECT-TYPE
            SYNTAX     Integer32
            MAX-ACCESS  read-only
            STATUS     current
            DESCRIPTION
                "This object indicates the ONT vendorid."
            ::= { hwGponDeviceAutoFindOntInfoEntry 4 }

        hwGponDeviceAutoFindOntInfoOntVer OBJECT-TYPE
            SYNTAX     OCTET STRING  (SIZE (16))
            MAX-ACCESS  read-only
            STATUS     current
            DESCRIPTION
                "This object indicates the ONT Version."
            ::= { hwGponDeviceAutoFindOntInfoEntry 5 }

        hwGponDeviceAutoFindOntInfoOntMainSoftVer OBJECT-TYPE
            SYNTAX     OCTET STRING  (SIZE (16))
            MAX-ACCESS  read-only
            STATUS     current
            DESCRIPTION
                "This object indicates the ONT MainSoftVer."
            ::= { hwGponDeviceAutoFindOntInfoEntry 6 }

        hwGponDeviceAutoFindOntInfoOntEquipmentId OBJECT-TYPE
            SYNTAX     OCTET STRING  (SIZE (20))
            MAX-ACCESS  read-only
            STATUS     current
            DESCRIPTION
                "This object indicates the ONT EquipmentId."
            ::= { hwGponDeviceAutoFindOntInfoEntry 7 }

        hwGponDeviceAutoFindOntInfoOntAutoFindTime OBJECT-TYPE
            SYNTAX     DateAndTime
            MAX-ACCESS  read-only
            STATUS     current
            DESCRIPTION
                "This object indicates the time for ONT's auto find."
            ::= { hwGponDeviceAutoFindOntInfoEntry 8 }

        hwGponDeviceAutoFindOntInfoLoid  OBJECT-TYPE
            SYNTAX   OCTET STRING (SIZE (0..24))
            MAX-ACCESS  read-only
            STATUS   current
            DESCRIPTION
                "This object indicates the ONT LOID."
            ::= { hwGponDeviceAutoFindOntInfoEntry 9 }

        hwGponDeviceAutoFindOntInfoCheckcode  OBJECT-TYPE
            SYNTAX   OCTET STRING (SIZE (0..12))
            MAX-ACCESS  read-only
            STATUS   current
            DESCRIPTION
                "This object indicates the ONT CHECKCODE"
            ::= { hwGponDeviceAutoFindOntInfoEntry 10 }

        hwGponDeviceAutoFindOntInfoCustomizedInfo  OBJECT-TYPE
            SYNTAX   OCTET STRING (SIZE (0..24))
            MAX-ACCESS  read-only
            STATUS   current
            DESCRIPTION
                "This object indicates the ONT customize information.
		"
            ::= { hwGponDeviceAutoFindOntInfoEntry 11 }

        hwGponDeviceAutoFindOntInfoOntNniType OBJECT-TYPE
            SYNTAX INTEGER {
                rate2dot5G1dot25G(1),
                rate10G2dot5G(2),
                rate10G10G(3),
                invalid(-1)
            }
            MAX-ACCESS read-only
            STATUS current
            DESCRIPTION
                "This object indicates the ONT actual rate type.
                 Options:
                 1. rate2dot5G1dot25G(1)      - Downstream rate 2.5Gbps, upstream rate 1.25Gbps
                 2. rate10G2dot5G(2)          - Downstream rate 10Gbps, upstream rate 2.5Gbps
                 3. rate10G10G(3)             - Downstream rate 10Gbps, upstream rate 10Gbps
                 4. invalid(-1)               - Indicates that the query fails or no information is detected
                "
            ::= { hwGponDeviceAutoFindOntInfoEntry 12 }

        hwGponDeviceAutoFindOntInfoEquipmentSn  OBJECT-TYPE
            SYNTAX   OCTET STRING (SIZE (0..25))
            MAX-ACCESS  read-only
            STATUS   current
            DESCRIPTION
                "This object indicates the ONT Equipment Sn."
            ::= { hwGponDeviceAutoFindOntInfoEntry 13 }

        hwGponDeviceAutoFindOntInfoMac  OBJECT-TYPE
            SYNTAX     MacAddress
            MAX-ACCESS  read-only
            STATUS   current
            DESCRIPTION
                "This object indicates the ONT MAC address."
            ::= { hwGponDeviceAutoFindOntInfoEntry 14 }

-- hwGponDeviceOntIpConfigInfoTable
        hwGponDeviceOntIpConfigInfoTable OBJECT-TYPE
            SYNTAX     SEQUENCE OF HwGponDeviceOntIpConfigInfoEntry
            MAX-ACCESS not-accessible
            STATUS     current
            DESCRIPTION
                "This is the ONT IP configuration table. This table is used to configure and query
                 the IP configuration mode and IP address of an ONT.
                 The index of this table is a combination of ifIndex, hwGponDeviceOntIndex and hwGponDeviceOntIpIndex.
                "
            ::= { hwXponDeviceControlObjects 49 }

        hwGponDeviceOntIpConfigInfoEntry OBJECT-TYPE
            SYNTAX     HwGponDeviceOntIpConfigInfoEntry
            MAX-ACCESS not-accessible
            STATUS     current
            DESCRIPTION
                "This is the ONT IP configuration table. This table is used to configure and query
                 the IP configuration mode and IP address of an ONT.
                 The index of this entry is a combination of ifIndex, hwGponDeviceOntIndex and hwGponDeviceOntIpIndex.
                "
            INDEX       { ifIndex, hwGponDeviceOntIndex, hwGponDeviceOntIpIndex}
            ::= { hwGponDeviceOntIpConfigInfoTable 1 }

        HwGponDeviceOntIpConfigInfoEntry ::=
            SEQUENCE {
                hwGponDeviceOntIpConfigMode                 INTEGER,
                hwGponDeviceOntIpAddress                    IpAddress,
                hwGponDeviceOntNetMask                      IpAddress,
                hwGponDeviceOntPhyAddress                   MacAddress,
                hwGponDeviceOntNetGateway                   IpAddress,
                hwGponDeviceOntMasterDNS                    IpAddress,
                hwGponDeviceOntSlaveDNS                     IpAddress,
                hwGponDeviceOntIpConfigVlan                 Integer32,
                hwGponDeviceOntIpConfigPriority             Integer32,
                hwGponDeviceOntIpIndex                      Integer32,
                hwGponDeviceOntIpconfigDscpDefaultPriority  Integer32,
                hwGponDeviceOntIpconfigDscpProfIndex        Integer32,
                hwGponDeviceOntIpconfigDhcpReset            INTEGER
            }

        hwGponDeviceOntIpConfigMode  OBJECT-TYPE
            SYNTAX     INTEGER{
                dhcp(1),
                static(2),
                unconfiguration(3),
                configurationFile(4),
                invalid(-1)
            }
            MAX-ACCESS   read-write
            STATUS      current
            DESCRIPTION
                "This object indicates the IP configuration mode.
                 Options:
                 1. dhcp(1)               - DHCP
                 2. static(2)             - Indicates that the IP configuration mode is static
                 3. unconfiguration(3)    - Indicates that the IP is not configuration
                 4. configurationFile(4)  - Indicates that the IP is configuration file
                 5. invalid(-1)           - Indicates that the query fails or no information is detected
                "
            ::= { hwGponDeviceOntIpConfigInfoEntry 1 }

        hwGponDeviceOntIpAddress  OBJECT-TYPE
            SYNTAX     IpAddress
            MAX-ACCESS   read-write
            STATUS      current
            DESCRIPTION
                "This object indicates the IP address."
            ::= { hwGponDeviceOntIpConfigInfoEntry 2 }

        hwGponDeviceOntNetMask  OBJECT-TYPE
            SYNTAX     IpAddress
            MAX-ACCESS   read-write
            STATUS      current
            DESCRIPTION
                "This object indicates the Subnet mask."
            ::= { hwGponDeviceOntIpConfigInfoEntry 3 }

        hwGponDeviceOntPhyAddress  OBJECT-TYPE
            SYNTAX       MacAddress
            MAX-ACCESS   read-only
            STATUS      current
            DESCRIPTION
                "This object indicates the ONT MAC address."
            ::= { hwGponDeviceOntIpConfigInfoEntry 4 }

        hwGponDeviceOntNetGateway  OBJECT-TYPE
            SYNTAX     IpAddress
            MAX-ACCESS   read-write
            STATUS      current
            DESCRIPTION
                "This object indicates the default network gateway."
            ::= { hwGponDeviceOntIpConfigInfoEntry 5 }

        hwGponDeviceOntMasterDNS  OBJECT-TYPE
            SYNTAX     IpAddress
            MAX-ACCESS   read-write
            STATUS      current
            DESCRIPTION
                "This object indicates the active DNS address."
            ::= { hwGponDeviceOntIpConfigInfoEntry 6 }

        hwGponDeviceOntSlaveDNS  OBJECT-TYPE
            SYNTAX     IpAddress
            MAX-ACCESS   read-write
            STATUS      current
            DESCRIPTION
                "This object indicates the slave DNS address."
            ::= { hwGponDeviceOntIpConfigInfoEntry 7 }

        hwGponDeviceOntIpConfigVlan  OBJECT-TYPE
            SYNTAX     Integer32
            MAX-ACCESS   read-write
            STATUS      current
            DESCRIPTION
                "This object indicates the management VLAN of ONT.
                range: 0-4095"
            ::= { hwGponDeviceOntIpConfigInfoEntry 8 }

        hwGponDeviceOntIpConfigPriority  OBJECT-TYPE
            SYNTAX     Integer32
            MAX-ACCESS   read-write
            STATUS      current
            DESCRIPTION
                "The management priority of ONT. range: 0-7, 0xfe: dscpMapping, -1: invalid value."
            DEFVAL { 0 }
            ::= { hwGponDeviceOntIpConfigInfoEntry 9 }

        hwGponDeviceOntIpIndex  OBJECT-TYPE
            SYNTAX     Integer32
            MAX-ACCESS   not-accessible
            STATUS      current
            DESCRIPTION
                "This object indicates the IP index of the ont IP host"
            ::= { hwGponDeviceOntIpConfigInfoEntry 10 }

        hwGponDeviceOntIpconfigDscpDefaultPriority OBJECT-TYPE
            SYNTAX      Integer32
            MAX-ACCESS  read-write
            STATUS      current
            DESCRIPTION
                "This object indicates the default priority for dscpMapping policy.
                 range: 0-7 "
            ::= { hwGponDeviceOntIpConfigInfoEntry 11 }

        hwGponDeviceOntIpconfigDscpProfIndex OBJECT-TYPE
            SYNTAX      Integer32
            MAX-ACCESS  read-write
            STATUS      current
            DESCRIPTION
                "This object indicates the dscp profile index of the ONT ip host."
            ::= { hwGponDeviceOntIpConfigInfoEntry 12 }

       hwGponDeviceOntIpconfigDhcpReset     OBJECT-TYPE
            SYNTAX      INTEGER
            {
               reset(1),
               invalid(-1)
            }
            MAX-ACCESS  read-write
            STATUS      current
            DESCRIPTION
                "This object is used for resetting the ip host in the DHCP mode.
                Options:
                 1. reset(1)            - DHCP reset in the DHCP mode
                 2. invalid(-1)         - invalid
                 "
            ::= { hwGponDeviceOntIpConfigInfoEntry 13 }

-- hwGponDeviceOntAlarmStateInfoTable
        hwGponDeviceOntAlarmStateInfoTable OBJECT-TYPE
            SYNTAX     SEQUENCE OF HwGponDeviceOntAlarmStateInfoEntry
            MAX-ACCESS not-accessible
            STATUS     current
            DESCRIPTION
                "The table is used to query the state of the ONT alarms.
                 The index of this table is a combination of ifIndex and hwGponDeviceOntIndex.
                "
            ::= { hwXponDeviceControlObjects 50 }

        hwGponDeviceOntAlarmStateInfoEntry OBJECT-TYPE
            SYNTAX     HwGponDeviceOntAlarmStateInfoEntry
            MAX-ACCESS not-accessible
            STATUS     current
            DESCRIPTION
                "The table is used to query the state of the ONT alarms.
                 The index of this entry is a combination of ifIndex and hwGponDeviceOntIndex.
                "
            INDEX       { ifIndex, hwGponDeviceOntIndex }
            ::= { hwGponDeviceOntAlarmStateInfoTable 1 }

        HwGponDeviceOntAlarmStateInfoEntry ::=
            SEQUENCE {
                hwGponDeviceOntAlarmSDi                Integer32,
                hwGponDeviceOntAlarmSFi                Integer32,
                hwGponDeviceOntAlarmDOWi               Integer32,
                hwGponDeviceOntAlarmLOSi               Integer32,
                hwGponDeviceOntObjAlarmStateRDIi       Integer32
            }

        hwGponDeviceOntAlarmSDi OBJECT-TYPE
            SYNTAX Integer32
            MAX-ACCESS read-only
            STATUS current
            DESCRIPTION
                "This object indicates the signal degrade (SDi) alarm.
                 1: no alarm is generated; 2: alarm is generated.
                "
            ::= { hwGponDeviceOntAlarmStateInfoEntry 1 }

        hwGponDeviceOntAlarmSFi OBJECT-TYPE
            SYNTAX Integer32
            MAX-ACCESS read-only
            STATUS current
            DESCRIPTION
                "This object indicates the signal fail (SFi) alarm.
                 1: no alarm is generated; 2: alarm is generated.
                "
            ::= { hwGponDeviceOntAlarmStateInfoEntry 2 }

        hwGponDeviceOntAlarmDOWi OBJECT-TYPE
            SYNTAX Integer32
            MAX-ACCESS read-only
            STATUS current
            DESCRIPTION
                "This object indicates the the ONU DOWi alarm.
                 1: no alarm is generated; 2: alarm is generated.
                "
            ::= { hwGponDeviceOntAlarmStateInfoEntry 3 }

        hwGponDeviceOntAlarmLOSi OBJECT-TYPE
            SYNTAX Integer32
            MAX-ACCESS read-only
            STATUS current
            DESCRIPTION
                "This object indicates the loss of frame (LOSi) alarm.
                 1: no alarm is generated; 2: alarm is generated.
                "
            ::= { hwGponDeviceOntAlarmStateInfoEntry 4 }

        hwGponDeviceOntObjAlarmStateRDIi  OBJECT-TYPE
            SYNTAX Integer32
            MAX-ACCESS read-only
            STATUS current
            DESCRIPTION
                "This object indicates the remote defect indication (RDIi) alarm
                 1: no alarm is generated; 2: alarm is generated.
                "
            ::= { hwGponDeviceOntAlarmStateInfoEntry 5 }

-- hwGponDeviceOntOpticalDdmInfoTable
        hwGponDeviceOntOpticalDdmInfoTable OBJECT-TYPE
            SYNTAX     SEQUENCE OF HwGponDeviceOntOpticalDdmInfoEntry
            MAX-ACCESS not-accessible
            STATUS     current
            DESCRIPTION
                "The table is used to query the information of the ONT Optical module.
                 The index of this table is a combination of ifIndex and hwGponDeviceOntIndex.
                "
            ::= { hwXponDeviceControlObjects 51 }

        hwGponDeviceOntOpticalDdmInfoEntry OBJECT-TYPE
            SYNTAX     HwGponDeviceOntOpticalDdmInfoEntry
            MAX-ACCESS not-accessible
            STATUS     current
            DESCRIPTION
                "The table is used to query the information of the ONT Optical module.
                 The index of this entry is a combination of ifIndex and hwGponDeviceOntIndex.
                "
            INDEX       { ifIndex, hwGponDeviceOntIndex }
            ::= { hwGponDeviceOntOpticalDdmInfoTable 1 }

        HwGponDeviceOntOpticalDdmInfoEntry ::=
            SEQUENCE {
                hwGponOntOpticalDdmTemperature                Integer32,
                hwGponOntOpticalDdmBiasCurrent                Integer32,
                hwGponOntOpticalDdmTxPower                    Integer32,
                hwGponOntOpticalDdmRxPower                    Integer32,
                hwGponOntOpticalDdmVoltage                    Integer32,
                hwGponOntOpticalDdmOltRxOntPower              Integer32,
                hwGponOntOpticalDdmAniCATVRxPower             Integer32
            }

        hwGponOntOpticalDdmTemperature OBJECT-TYPE
            SYNTAX Integer32
            MAX-ACCESS read-only
            STATUS current
            DESCRIPTION
                "The temperature of the optical module, unit C(centigrade)."
            ::= { hwGponDeviceOntOpticalDdmInfoEntry 1 }

        hwGponOntOpticalDdmBiasCurrent OBJECT-TYPE
            SYNTAX Integer32
            MAX-ACCESS read-only
            STATUS current
            DESCRIPTION
              "The Bias Current of the optical module, unit mA."
            ::= { hwGponDeviceOntOpticalDdmInfoEntry 2 }

        hwGponOntOpticalDdmTxPower OBJECT-TYPE
            SYNTAX Integer32
            MAX-ACCESS read-only
            STATUS current
            DESCRIPTION
                "The transmitting power of the optical module, unit 0.01dBm."
            ::= { hwGponDeviceOntOpticalDdmInfoEntry 3 }

        hwGponOntOpticalDdmRxPower OBJECT-TYPE
            SYNTAX Integer32
            MAX-ACCESS read-only
            STATUS current
            DESCRIPTION
                "The receiving power of the optical module, unit 0.01dBm."
            ::= { hwGponDeviceOntOpticalDdmInfoEntry 4 }

        hwGponOntOpticalDdmVoltage OBJECT-TYPE
            SYNTAX Integer32
            MAX-ACCESS read-only
            STATUS current
            DESCRIPTION
                "The power feed voltage of the optical module, unit mV."
            ::= { hwGponDeviceOntOpticalDdmInfoEntry 5 }

        hwGponOntOpticalDdmOltRxOntPower OBJECT-TYPE
            SYNTAX Integer32
            MAX-ACCESS read-only
            STATUS current
            DESCRIPTION
                "The ONT optical power received on the OLT, unit dBm.
                 The relationship between the actual value and the value get from this leaf node is as follows,
                 Actual value = ((Node value - 10000) / 100)
                "
            ::= { hwGponDeviceOntOpticalDdmInfoEntry 6 }

        hwGponOntOpticalDdmAniCATVRxPower OBJECT-TYPE
            SYNTAX Integer32
            MAX-ACCESS read-only
            STATUS current
            DESCRIPTION
                "Indicates the CATV receiving optical power of the optical module, unit 0.01dBm."
            ::= { hwGponDeviceOntOpticalDdmInfoEntry 7 }

-- hwGponDeviceOntRegisterInfoTable
        hwGponDeviceOntRegisterInfoTable OBJECT-TYPE
            SYNTAX  SEQUENCE OF HwGponDeviceOntRegisterInfoEntry
            MAX-ACCESS  not-accessible
            STATUS  current
            DESCRIPTION
                "This table is used to query the register information about the ONT,
                 including the ONT SN, register time and register result.
                 The index of this table is a combination of ifIndex and hwGponDeviceOntRegisterSerialNum.
                "
            ::= { hwXponDeviceControlObjects 52 }

        hwGponDeviceOntRegisterInfoEntry OBJECT-TYPE
            SYNTAX  HwGponDeviceOntRegisterInfoEntry
            MAX-ACCESS  not-accessible
            STATUS  current
            DESCRIPTION
                "This table is used to query the register information about the ONT,
                 including the ONT SN, register time and register result.
                 The index of this entry is a combination of ifIndex and hwGponDeviceOntRegisterSerialNum.
                "
            INDEX  { ifIndex, hwGponDeviceOntRegisterSerialNum }
            ::= { hwGponDeviceOntRegisterInfoTable 1 }

        HwGponDeviceOntRegisterInfoEntry ::=
            SEQUENCE {
                hwGponDeviceOntRegisterSerialNum              Integer32,
                hwGponDeviceOntRegisterSn                     OCTET STRING,
                hwGponDeviceOntRegisterResult                 INTEGER,
                hwGponDeviceOntRegisterTime                   DateAndTime,
                hwGponDeviceOntRegisterConflictedIfindex      Integer32,
                hwGponDeviceOntRegisterConflictedOntIndex     Integer32,
                hwGponDeviceOntRegisterOntPassword            OCTET STRING,
                hwGponDeviceOntRegisterOntVendorId            Integer32,
                hwGponDeviceOntRegisterOntVersion             OCTET STRING,
                hwGponDeviceOntRegisterOntMainSoftVersion     OCTET STRING,
                hwGponDeviceOntRegisterOntEquipmentId         OCTET STRING,
                hwGponDeviceOntRegisterOntLoid                OCTET STRING,
                hwGponDeviceOntRegisterOntCheckcode           OCTET STRING,
                hwGponDeviceOntRegisterOntNniType             INTEGER
            }

        hwGponDeviceOntRegisterSerialNum OBJECT-TYPE
            SYNTAX  Integer32
            MAX-ACCESS   not-accessible
            STATUS  current
            DESCRIPTION
                "This object indicates the register number."
            ::= { hwGponDeviceOntRegisterInfoEntry 1 }

        hwGponDeviceOntRegisterSn OBJECT-TYPE
            SYNTAX  OCTET STRING (SIZE (8))
            MAX-ACCESS  read-only
            STATUS  current
            DESCRIPTION
                "This object indicates the ONT serial number."
            ::= { hwGponDeviceOntRegisterInfoEntry 2 }

        hwGponDeviceOntRegisterResult OBJECT-TYPE
            SYNTAX  INTEGER {
                success(1),
                fail(2),
                snConflict(3),
                passwordConflict(4),
                loidConflict(5),
                passwordError(6),
                ccError(7),
                rangingOnuFail(8),
                unconfirmed(9),
                misMatch(10),
                loidError(11),
                invalid(-1)
            }
            MAX-ACCESS  read-only
            STATUS  current
            DESCRIPTION
                "This object indicates the register result.
                 Options:
                 1. success(1)                    - Indicates that the register result is success
                 2. fail(2)                       - Indicates that the register result is fail
                 3. snConflict(3)                 - Indicates that the SN conflict
                 4. passwordConflict(4)           - Indicates that the password conflict
                 5. loidConflict(5)               - Indicates that the LOID conflict
                 6. passwordError(6)              - Indicates that the password conflict
                 7. ccError(7)                    - Indicates that the CC error
                 8. rangingOnuFail(8)             - Indicates that the ranging ONU fail
                 9. unconfirmed(9)                - Indicates that the ONU is unconfirmed
                 10. misMatch(10)                 - Indicates that the ONU is mismatch
                 11. loidError(11)                - Indicates that the LOID error
                 12. invalid(-1)                  - Indicates that the query fails or no information is detected
                "
            ::= { hwGponDeviceOntRegisterInfoEntry 3 }

        hwGponDeviceOntRegisterTime OBJECT-TYPE
            SYNTAX  DateAndTime
            MAX-ACCESS  read-only
            STATUS  current
            DESCRIPTION
                "This object indicates the register time.
                 -1 is the invalid value."
            ::= { hwGponDeviceOntRegisterInfoEntry 4 }

        hwGponDeviceOntRegisterConflictedIfindex OBJECT-TYPE
            SYNTAX  Integer32
            MAX-ACCESS   read-only
            STATUS  current
            DESCRIPTION
                "This object indicates the ifIndex of the conflicted ONT.
                 -1 is the invalid value."
            ::= { hwGponDeviceOntRegisterInfoEntry 5 }

         hwGponDeviceOntRegisterConflictedOntIndex OBJECT-TYPE
            SYNTAX  Integer32
            MAX-ACCESS   read-only
            STATUS  current
            DESCRIPTION
                "This object indicates the index of the conflicted ONT.
                 -1 is the invalid value."
            ::= { hwGponDeviceOntRegisterInfoEntry 6 }

        hwGponDeviceOntRegisterOntPassword OBJECT-TYPE
            SYNTAX     OCTET STRING
            MAX-ACCESS  read-only
            STATUS     current
            DESCRIPTION
                "This object indicates the ONT password
                 GPON password size (0..10)
                 XG-PON password size (0..36)
                "
            ::= { hwGponDeviceOntRegisterInfoEntry 7 }

        hwGponDeviceOntRegisterOntVendorId OBJECT-TYPE
            SYNTAX     Integer32
            MAX-ACCESS  read-only
            STATUS     current
            DESCRIPTION
                "This object indicates the ONT vendor ID."
            ::= { hwGponDeviceOntRegisterInfoEntry 8 }

        hwGponDeviceOntRegisterOntVersion OBJECT-TYPE
            SYNTAX     OCTET STRING  (SIZE (16))
            MAX-ACCESS  read-only
            STATUS     current
            DESCRIPTION
                "This object indicates the ONT version."
            ::= { hwGponDeviceOntRegisterInfoEntry 9 }

        hwGponDeviceOntRegisterOntMainSoftVersion OBJECT-TYPE
            SYNTAX     OCTET STRING  (SIZE (16))
            MAX-ACCESS  read-only
            STATUS     current
            DESCRIPTION
                "This object indicates the ONT mainsoft version."
            ::= { hwGponDeviceOntRegisterInfoEntry 10 }

        hwGponDeviceOntRegisterOntEquipmentId OBJECT-TYPE
            SYNTAX     OCTET STRING  (SIZE (20))
            MAX-ACCESS  read-only
            STATUS     current
            DESCRIPTION
                "This object indicates the ONT equipment ID."
            ::= { hwGponDeviceOntRegisterInfoEntry 11 }

        hwGponDeviceOntRegisterOntLoid  OBJECT-TYPE
            SYNTAX   OCTET STRING (SIZE (0..24))
            MAX-ACCESS  read-only
            STATUS   current
            DESCRIPTION
                "This object indicates the ONT LOID."
            ::= { hwGponDeviceOntRegisterInfoEntry 12 }

        hwGponDeviceOntRegisterOntCheckcode  OBJECT-TYPE
            SYNTAX   OCTET STRING (SIZE (0..12))
            MAX-ACCESS  read-only
            STATUS   current
            DESCRIPTION
                "This object indicates the ONT CHECKCODE"
            ::= { hwGponDeviceOntRegisterInfoEntry 13 }

        hwGponDeviceOntRegisterOntNniType OBJECT-TYPE
            SYNTAX INTEGER {
                rate2dot5G1dot25G(1),
                rate10G2dot5G(2),
                rate10G10G(3),
                invalid(-1)
            }
            MAX-ACCESS read-only
            STATUS current
            DESCRIPTION
                "This object indicates the ONT actual rate type.
                 Options:
                 1. rate2dot5G1dot25G(1)      - Downstream rate 2.5Gbps, upstream rate 1.25Gbps
                 2. rate10G2dot5G(2)          - Downstream rate 10Gbps, upstream rate 2.5Gbps
                 3. rate10G10G(3)             - Downstream rate 10Gbps, upstream rate 10Gbps
                 4. invalid(-1)               - Indicates that the query fails or no information is detected
                "
            ::= { hwGponDeviceOntRegisterInfoEntry 14 }

-- hwEponDeviceOntConfigInfoTable
        hwEponDeviceOntConfigInfoTable OBJECT-TYPE
            SYNTAX     SEQUENCE OF HwEponDeviceOntConfigInfoEntry
            MAX-ACCESS not-accessible
            STATUS     current
            DESCRIPTION
                "This table is used to create, modify, delete or query an ONT.
                 The index of this table is a combination of ifIndex and hwEponDeviceOntIndex.
                "
            ::= { hwXponDeviceControlObjects 53 }

        hwEponDeviceOntConfigInfoEntry OBJECT-TYPE
            SYNTAX     HwEponDeviceOntConfigInfoEntry
            MAX-ACCESS not-accessible
            STATUS     current
            DESCRIPTION
                "This table is used to create, modify, delete or query an ONT.
                 The index of this entry is a combination of ifIndex and hwEponDeviceOntIndex.
                "
            INDEX       { ifIndex, hwEponDeviceOntIndex }
            ::= { hwEponDeviceOntConfigInfoTable 1 }

        HwEponDeviceOntConfigInfoEntry ::=
            SEQUENCE {
                hwEponDeviceOntIndex              Integer32,
                hwEponDeviceOntAuthMode           INTEGER,
                hwEponDeviceOntMacAddress         MacAddress,
                hwEponDeviceOntPassword           OCTET STRING,
                hwEponDeviceOntTimeout            Integer32,
                hwEponDeviceOntManagementMode     INTEGER,
                hwEponDeviceOntLineProfName       OCTET STRING,
                hwEponDeviceOntServiceProfName    OCTET STRING,
                hwEponDeviceOntDespt              OCTET STRING,
                hwEponDeviceOntEntryStatus        RowStatus,
                hwEponDeviceOntProtectSide        INTEGER,
                hwEponDeviceOntObjectLoid         OCTET STRING,
                hwEponDeviceOntObjectCheckcode    OCTET STRING,
                hwEponDeviceLineProfileServiceSlaProfileIndex  OCTET STRING,
                hwEponDeviceOntPGMemberRole       INTEGER,
                hwEponDeviceOntAuthEffectMode     INTEGER,
                hwEponDeviceOntNniType            INTEGER
            }

        hwEponDeviceOntIndex  OBJECT-TYPE
            SYNTAX     Integer32
            MAX-ACCESS   not-accessible
            STATUS      current
            DESCRIPTION
                "This object indicates the ONT ID, range: 0~254."
            ::= { hwEponDeviceOntConfigInfoEntry 1 }

        hwEponDeviceOntAuthMode OBJECT-TYPE
            SYNTAX      INTEGER {
                onceon(1),
                alwayson(2),
                mac(3),
                lOIDonceon(5),
                lOIDalwayson(6),
                lOIDCheckCodeOnceon(7),
                lOIDCheckCodeAlwayson(8),
                invalid(-1)
            }
            MAX-ACCESS  read-write
            STATUS      current
            DESCRIPTION
                "This object indicates the authentication mode for the ONT.
                 Options:
                 1. onceon(1)                    - The authentication mode is once on
                 2. alwayson(2)                  - The authentication mode is always on
                 3. mac(3)                       - The authentication mode is MAC
                 4. lOIDonceon(5)                - The authentication mode is LOID and once on
                 5. lOIDalwayson(6)              - The authentication mode is LOID and always on
                 6. lOIDCheckCodeOnceon(7)       - The authentication mode is LOID, checkcode and once on
                 7. lOIDCheckCodeAlwayson(8)     - The authentication mode is LOID, checkcode and once always on
                 8. invalid(-1)                  - Indicates that the query fails or no information is detected
                "
            ::= { hwEponDeviceOntConfigInfoEntry 2 }

        hwEponDeviceOntMacAddress OBJECT-TYPE
            SYNTAX      MacAddress
            MAX-ACCESS  read-write
            STATUS      current
            DESCRIPTION
                "This object indicates the ONT MAC."
            ::= { hwEponDeviceOntConfigInfoEntry 3 }

        hwEponDeviceOntPassword OBJECT-TYPE
            SYNTAX      OCTET STRING  (SIZE (0..32))
            MAX-ACCESS  read-write
            STATUS      current
            DESCRIPTION
                "This object indicates the ONT password."
            ::= { hwEponDeviceOntConfigInfoEntry 4 }

        hwEponDeviceOntTimeout OBJECT-TYPE
            SYNTAX      Integer32
            MAX-ACCESS  read-write
            STATUS      current
            DESCRIPTION
                "This object indicates the registered working period of the ONT, ranging from 1 to 168 hours.
                 The value (-1) indicates that there is no-aging time.
                "
            ::= { hwEponDeviceOntConfigInfoEntry 5 }

        hwEponDeviceOntManagementMode OBJECT-TYPE
            SYNTAX     INTEGER {
                oam(1),
                snmp(2),
                invalid(-1)
            }
            MAX-ACCESS  read-write
            STATUS      current
            DESCRIPTION
                "This object indicates the ONT management mode, including OAM and SNMP.
                 Options:
                 1. oam(1)            - OAM
                 2. snmp(2)           - SNMP
                 3. invalid(-1)       - Indicates that the query fails or no information is detected
                "
            ::= { hwEponDeviceOntConfigInfoEntry 6 }

        hwEponDeviceOntLineProfName OBJECT-TYPE
            SYNTAX      OCTET STRING (SIZE (0..32))
            MAX-ACCESS  read-write
            STATUS      current
            DESCRIPTION
                "This object indicates the name of the line profile that is bound to the ONT."
            ::= { hwEponDeviceOntConfigInfoEntry 7 }

        hwEponDeviceOntServiceProfName OBJECT-TYPE
            SYNTAX      OCTET STRING (SIZE (0..32))
            MAX-ACCESS  read-write
            STATUS      current
            DESCRIPTION
                "This object indicates the name of the service profile that is bound to the ONT."
            ::= { hwEponDeviceOntConfigInfoEntry 8 }

        hwEponDeviceOntDespt OBJECT-TYPE
            SYNTAX      OCTET STRING (SIZE (1..64))
            MAX-ACCESS  read-write
            STATUS      current
            DESCRIPTION
                "This object indicates the description of the ONT."
            ::= { hwEponDeviceOntConfigInfoEntry 9 }

        hwEponDeviceOntEntryStatus OBJECT-TYPE
            SYNTAX      RowStatus
            MAX-ACCESS  read-create
            STATUS      current
            DESCRIPTION
                "This object is used to create a new row or to modify or delete an existing row in this table.
                 Options:
                 1. createAndGo(4) -create a new instance of a conceptual row
                 2. destroy(6)     -delete the instances associated with an existing conceptual row
                "
            ::= { hwEponDeviceOntConfigInfoEntry 10 }

        hwEponDeviceOntProtectSide OBJECT-TYPE
            SYNTAX      INTEGER {
                protectside(1),
                work(2)
            }
            MAX-ACCESS  read-write
            STATUS      current
            DESCRIPTION
                "This object indicates whether the ONT is the ONT on the protection side.
                 Options:
                 1. protectside(1)         - Indicates that the ONT is the ONT on the protection side
                 2. work(2)                - Indicates that the ONT is the ONT on the work side
                "
            ::= { hwEponDeviceOntConfigInfoEntry 11 }

        hwEponDeviceOntObjectLoid OBJECT-TYPE
            SYNTAX      OCTET STRING   (SIZE (0..24))
            MAX-ACCESS  read-write
            STATUS      current
            DESCRIPTION
                "This object indicates the ONT LOID."
            ::= { hwEponDeviceOntConfigInfoEntry 12 }

        hwEponDeviceOntObjectCheckcode OBJECT-TYPE
            SYNTAX      OCTET STRING   (SIZE (0..12))
            MAX-ACCESS  read-write
            STATUS      current
            DESCRIPTION
                "This object indicates the ONT CHECKCODE."
            ::= { hwEponDeviceOntConfigInfoEntry 13 }

        hwEponDeviceLineProfileServiceSlaProfileIndex OBJECT-TYPE
            SYNTAX      OCTET STRING (SIZE (0..32))
            MAX-ACCESS  read-write
            STATUS      current
            DESCRIPTION
                "This object indicates the index of SLA profile"
            ::= { hwEponDeviceOntConfigInfoEntry 14 }

        hwEponDeviceOntPGMemberRole OBJECT-TYPE
            SYNTAX INTEGER {
                work (1),
                protect (2),
                unjoined (-1)
            }
            MAX-ACCESS read-only
            STATUS current
            DESCRIPTION
                "Indicate the role of the ont in the protect group,
                 Options:
                 1. work(1)                    - Indicates that the role of the ONT is work
                 2. protect(2)                 - Indicates that the role of the ONT is protection
                 3. unjoined(-1)               - Indicates that the ONT is not added to the protect group
                "
            ::= { hwEponDeviceOntConfigInfoEntry 15 }

            hwEponDeviceOntAuthEffectMode OBJECT-TYPE
            SYNTAX INTEGER {
                   immediate (1),
                   nextstartup (2),
                   invalid (-1)
            }
            MAX-ACCESS read-write
            STATUS current
            DESCRIPTION
                 "Indicates the effect taking mode after the ONT authentication mode is changed. The default effect taking mode is immediate.
                  Options:
                  1. immediate (1)    -Indicates that the change will take effect immediately.
                  2. nextstartup (2)  -Indicates that the change will take effect when the ONT goes online next time.
                  3. invalid (-1)     -Indicates that the effect taking mode is invalid.
                "
            ::= { hwEponDeviceOntConfigInfoEntry 16 }

        hwEponDeviceOntNniType OBJECT-TYPE
            SYNTAX INTEGER {
                rate1G1G(1),
                rate10G1G(2),
                rate10G10G(3),
                auto(4),
                rate10G2G(5),
                invalid(-1)
            }
            MAX-ACCESS read-write
            STATUS current
            DESCRIPTION
                "This object indicates the ONT rate type.
                 Options:
                 1. rate1G1G(1)               - Downstream rate 1Gbps, upstream rate 1Gbps
                 2. rate10G1G(2)              - Downstream rate 10Gbps, upstream rate 1Gbps
                 3. rate10G10G(3)             - Downstream rate 10Gbps, upstream rate 10Gbps
                 4. auto(4)                   - Indicates that the ONT NNI type is automatically selected
                 5. rate10G2G(5)              - Downstream rate 10Gbps, upstream rate 2Gbps
                 6. invalid(-1)               - Indicates that the query fails or no information is detected
                "
            ::= { hwEponDeviceOntConfigInfoEntry 17 }
-- hwEponDeviceOntExtendConfigTable
        hwEponDeviceOntExtendConfigTable OBJECT-TYPE
            SYNTAX     SEQUENCE OF HwEponDeviceOntExtendConfigEntry
            MAX-ACCESS not-accessible
            STATUS     current
            DESCRIPTION
                "This is the ONT extend function configuration table.
                 The index of this table is a combination of ifIndex and hwEponDeviceOntIndex.
                "
            ::= { hwXponDeviceControlObjects 54 }

        hwEponDeviceOntExtendConfigEntry OBJECT-TYPE
            SYNTAX     HwEponDeviceOntExtendConfigEntry
            MAX-ACCESS not-accessible
            STATUS     current
            DESCRIPTION
                "This is the ONT extend function configuration table.
                 The index of this entry is a combination of ifIndex and hwEponDeviceOntIndex.
                "
            INDEX       { ifIndex, hwEponDeviceOntIndex}
            ::= { hwEponDeviceOntExtendConfigTable 1 }

        HwEponDeviceOntExtendConfigEntry ::=
            SEQUENCE {
                hwEponDeviceOntCfgSnmpProfileName               OCTET STRING,
                hwEponDeviceOntCfgMulticastMode                 INTEGER,
                hwEponDeviceOntExtCfgOpticAlarmProfileName      OCTET STRING,
                hwEponDeviceOntExtCfgAlarmProfileName           OCTET STRING,
                hwEponDeviceOntExtCfgWarningProfileName         OCTET STRING
            }

        hwEponDeviceOntCfgSnmpProfileName OBJECT-TYPE
            SYNTAX      OCTET STRING (SIZE (0..32))
            MAX-ACCESS  read-write
            STATUS      current
            DESCRIPTION
                "This object indicates the name of the ONT SNMP profile."
            ::= { hwEponDeviceOntExtendConfigEntry 1 }

        hwEponDeviceOntCfgMulticastMode OBJECT-TYPE
            SYNTAX INTEGER {
                ctc(1),
                igmpsnooping(2),
                transparent(3),
                invalid(-1)
            }
            MAX-ACCESS read-write
            STATUS current
            DESCRIPTION
                "This object indicates the XPON service profile multicast mode.
                 Options:
                 1. ctc(1)             - Indicates that the XPON service profile multicast mode is CTC
                 2. igmpsnooping(2)    - Indicates that the XPON service profile multicast mode is igmp snooping
                 3. transparent(3)     - Indicates that the XPON service profile multicast mode is transparent
                 4. invalid(-1)        - Indicates that the query fails or no information is detected
                "
            ::= { hwEponDeviceOntExtendConfigEntry 2 }

        hwEponDeviceOntExtCfgOpticAlarmProfileName  OBJECT-TYPE
            SYNTAX     OCTET STRING (SIZE (0..32))
            MAX-ACCESS   read-write
            STATUS      current
            DESCRIPTION
                "This object indicates the name of the optical alarm profile that is bound to the ONT."
            ::= { hwEponDeviceOntExtendConfigEntry 3 }

        hwEponDeviceOntExtCfgAlarmProfileName  OBJECT-TYPE
            SYNTAX     OCTET STRING (SIZE (0..32))
            MAX-ACCESS   read-write
            STATUS      current
            DESCRIPTION
                "This object indicates the name of the alarm profile that is bound to the ONT PON port."
            ::= { hwEponDeviceOntExtendConfigEntry 4 }

        hwEponDeviceOntExtCfgWarningProfileName  OBJECT-TYPE
            SYNTAX     OCTET STRING (SIZE (0..32))
            MAX-ACCESS   read-write
            STATUS      current
            DESCRIPTION
                "This object indicates the name of the warning profile that is bound to the ONT PON port."
            ::= { hwEponDeviceOntExtendConfigEntry 5 }

-- hwEponDeviceOntVersionInfoTable
        hwEponDeviceOntVersionInfoTable OBJECT-TYPE
            SYNTAX     SEQUENCE OF HwEponDeviceOntVersionInfoEntry
            MAX-ACCESS not-accessible
            STATUS     current
            DESCRIPTION
                "This is the ONT version information table.
                 The index of this table is a combination of ifIndex and hwEponDeviceOntIndex.
                "
            ::= { hwXponDeviceControlObjects 55 }

        hwEponDeviceOntVersionInfoEntry OBJECT-TYPE
            SYNTAX     HwEponDeviceOntVersionInfoEntry
            MAX-ACCESS not-accessible
            STATUS     current
            DESCRIPTION
                "This is the ONT version information table.
                 The index of this entry is a combination of ifIndex and hwEponDeviceOntIndex.
                "
            INDEX       { ifIndex, hwEponDeviceOntIndex}
            ::= { hwEponDeviceOntVersionInfoTable 1 }

        HwEponDeviceOntVersionInfoEntry ::=
            SEQUENCE {
                hwEponDeviceOntVendorId                 Integer32,
                hwEponDeviceOntModel                    Integer32,
                hwEponDeviceOntOntIdentifier            OCTET STRING,
                hwEponDeviceOntHardwareVersion          OCTET STRING,
                hwEponDeviceOntSoftwareVersion          OCTET STRING,
                hwEponDeviceOntChipVendorID             OCTET STRING,
                hwEponDeviceOntChipModel                Integer32,
                hwEponDeviceOntChipVersion              Integer32,
                hwEponDeviceOntChipDesignDate           OCTET STRING,
                hwEponDeviceOntFirmwareVersion          Integer32,
                hwEponDeviceOntChipRevision             Integer32,
                hwEponDeviceOntSoftwareWorkMode         INTEGER,
                hwEponDeviceOntExtendedModel            OCTET STRING,
                hwEponDeviceOntOuiVersion               OCTET STRING,
                hwEponDeviceOntExtendedFirmwareVersion  Opaque,
                hwEponDeviceOntCustomizedInfo           OCTET STRING
            }

        hwEponDeviceOntVendorId OBJECT-TYPE
            SYNTAX      Integer32
            MAX-ACCESS  read-only
            STATUS      current
            DESCRIPTION
                "This object indicates the ONT VendorID."
            ::= { hwEponDeviceOntVersionInfoEntry 1 }

        hwEponDeviceOntModel OBJECT-TYPE
            SYNTAX      Integer32
            MAX-ACCESS  read-only
            STATUS      current
            DESCRIPTION
                "This object indicates the ONT model."
            ::= { hwEponDeviceOntVersionInfoEntry 2 }

        hwEponDeviceOntOntIdentifier OBJECT-TYPE
            SYNTAX      OCTET STRING (SIZE (8))
            MAX-ACCESS  read-only
            STATUS      current
            DESCRIPTION
                "This object indicates the ONT identifier."
            ::= { hwEponDeviceOntVersionInfoEntry 3 }

        hwEponDeviceOntHardwareVersion OBJECT-TYPE
            SYNTAX      OCTET STRING (SIZE (8))
            MAX-ACCESS  read-only
            STATUS      current
            DESCRIPTION
                "This object indicates the hardware version of the ONT."
            ::= { hwEponDeviceOntVersionInfoEntry 4 }

        hwEponDeviceOntSoftwareVersion OBJECT-TYPE
            SYNTAX      OCTET STRING (SIZE (16))
            MAX-ACCESS  read-only
            STATUS      current
            DESCRIPTION
                "This object indicates the software version of the ONT."
            ::= { hwEponDeviceOntVersionInfoEntry 5 }

        hwEponDeviceOntChipVendorID OBJECT-TYPE
            SYNTAX      OCTET STRING (SIZE (2))
            MAX-ACCESS  read-only
            STATUS      current
            DESCRIPTION
                "This object indicates the verder ID of the ONT's chip."
            ::= { hwEponDeviceOntVersionInfoEntry 6 }

        hwEponDeviceOntChipModel OBJECT-TYPE
            SYNTAX      Integer32
            MAX-ACCESS  read-only
            STATUS      current
            DESCRIPTION
                "This object indicates the model of the ONT's chip."
            ::= { hwEponDeviceOntVersionInfoEntry 7 }

        hwEponDeviceOntChipVersion OBJECT-TYPE
            SYNTAX      Integer32
            MAX-ACCESS  read-only
            STATUS      current
            DESCRIPTION
                "This object indicates the verion of the ONT's chip."
            ::= { hwEponDeviceOntVersionInfoEntry 8 }

        hwEponDeviceOntChipDesignDate OBJECT-TYPE
            SYNTAX      OCTET STRING (SIZE (3))
            MAX-ACCESS  read-only
            STATUS      current
            DESCRIPTION
                "This object indicates the design data of the ONT's chip."
            ::= { hwEponDeviceOntVersionInfoEntry 9 }

        hwEponDeviceOntFirmwareVersion OBJECT-TYPE
            SYNTAX      Integer32
            MAX-ACCESS  read-only
            STATUS      current
            DESCRIPTION
                "This object indicates the firmware version of the ONT's chip."
            ::= { hwEponDeviceOntVersionInfoEntry 10 }

        hwEponDeviceOntChipRevision OBJECT-TYPE
            SYNTAX      Integer32
            MAX-ACCESS  read-only
            STATUS      current
            DESCRIPTION
                "This object indicates the firmware reversion of the ONT's chip."
            ::= { hwEponDeviceOntVersionInfoEntry 11 }

        hwEponDeviceOntSoftwareWorkMode OBJECT-TYPE
            SYNTAX  INTEGER {
               normal (1),
               survivalmode (2)
            }
            MAX-ACCESS read-only
            STATUS current
            DESCRIPTION
                "The object indicates the software working mode of the EPON ONT.
                 Options:
                 1. normal(1)             - Normal
                 2. survivalmode(2)       - Survival mode
                "
            ::= { hwEponDeviceOntVersionInfoEntry 12}

        hwEponDeviceOntExtendedModel OBJECT-TYPE
            SYNTAX      OCTET STRING (SIZE (0..32))
            MAX-ACCESS read-only
            STATUS current
            DESCRIPTION
                "This object indicates the ONT extended model."
            ::= { hwEponDeviceOntVersionInfoEntry 13}

        hwEponDeviceOntOuiVersion OBJECT-TYPE
            SYNTAX      OCTET STRING (SIZE (0..32))
            MAX-ACCESS read-only
            STATUS current
            DESCRIPTION
                "This object indicates the highest version of ONT OUI."
            ::= { hwEponDeviceOntVersionInfoEntry 14}

        hwEponDeviceOntExtendedFirmwareVersion OBJECT-TYPE
            SYNTAX      Opaque (SIZE (0..128))
            MAX-ACCESS read-only
            STATUS current
            DESCRIPTION
                "This object indicates the extended firmware version of the ONT's chip."
            ::= { hwEponDeviceOntVersionInfoEntry 15}

        hwEponDeviceOntCustomizedInfo OBJECT-TYPE
            SYNTAX      OCTET STRING (SIZE (0..24))
            MAX-ACCESS read-only
            STATUS current
            DESCRIPTION
                "This object indicates the ONT customize information.
		"
            ::= { hwEponDeviceOntVersionInfoEntry 16}

-- HwEponDeviceOntCfgCapabilityTable
        hwEponDeviceOntCfgCapabilityTable OBJECT-TYPE
            SYNTAX     SEQUENCE OF HwEponDeviceOntCfgCapabilityEntry
            MAX-ACCESS not-accessible
            STATUS     current
            DESCRIPTION
                "The EPON ONT configuration capability table.
                 The index of this table is a combination of ifIndex and hwEponDeviceOntIndex.
                "
            ::= { hwXponDeviceControlObjects 56 }

        hwEponDeviceOntCfgCapabilityEntry OBJECT-TYPE
            SYNTAX     HwEponDeviceOntCfgCapabilityEntry
            MAX-ACCESS not-accessible
            STATUS     current
            DESCRIPTION
                "The EPON ONT configuration capability table.
                 The index of this entry is a combination of ifIndex and hwEponDeviceOntIndex.
                "
            INDEX       { ifIndex, hwEponDeviceOntIndex}
            ::= { hwEponDeviceOntCfgCapabilityTable 1 }

        HwEponDeviceOntCfgCapabilityEntry ::=
            SEQUENCE {
                hwEponDeviceOntCfgCapManageMode       INTEGER,
                hwEponDeviceOntCfgCapPotsNum          Integer32,
                hwEponDeviceOntCfgCapIPSupport        INTEGER,
                hwEponDeviceOntCfgCapTdmPortType      INTEGER,
                hwEponDeviceOntCfgCapTdmNum           Integer32,
                hwEponDeviceOntCfgCapEthNum           Integer32
            }

        hwEponDeviceOntCfgCapManageMode OBJECT-TYPE
            SYNTAX       INTEGER {
                oam(1),
                snmp(2),
                invalid(-1)
            }
            MAX-ACCESS   read-only
            STATUS       current
            DESCRIPTION
                "This object indicates the ONT's management mode, including oam and snmp.
                 Options:
                 1. oam(1)            - OAM
                 2. snmp(2)           - SNMP
                 3. invalid(-1)       - Indicates that the query fails or no information is detected
                "
            ::= { hwEponDeviceOntCfgCapabilityEntry 1 }

        hwEponDeviceOntCfgCapPotsNum     OBJECT-TYPE
            SYNTAX       Integer32
            MAX-ACCESS   read-only
            STATUS       current
            DESCRIPTION
                "This object indicates the number of POTS ports.
                 A special value of 0xFE (254) indicates the number
                 of port is adaptive."
            ::= { hwEponDeviceOntCfgCapabilityEntry 2 }

        hwEponDeviceOntCfgCapIPSupport OBJECT-TYPE
            SYNTAX       INTEGER{
                dhcp(1),
                static(2),
                unconfiguration(3),
                pppoe(4),
                invalid(-1)
            }
            MAX-ACCESS   read-only
            STATUS       current
            DESCRIPTION
                "This object indicates the IP config mode.
                 Options:
                 1. dhcp(1)               - DHCP
                 2. static(2)             - Indicates that the IP config mode is static
                 3. unconfiguration(3)    - Indicates that the IP is not configuration
                 4. pppoe(4)              - Indicates that the IP config mode is PPPoE
                 5. invalid (-1)          - Indicates that the query fails or no information is detected
                "
            ::= { hwEponDeviceOntCfgCapabilityEntry 3 }

        hwEponDeviceOntCfgCapTdmPortType OBJECT-TYPE
            SYNTAX       INTEGER{
                t1(13),
                e1(14),
                invalid(-1)
            }
            MAX-ACCESS   read-only
            STATUS       current
            DESCRIPTION
                "This object indicates the TDM port type.
                 Options:
                 1. t1(13)             - T1
                 2. e1(14)             - E1
                 3. invalid(-1)        - Indicates that the query fails or no information is detected
                "
            ::= { hwEponDeviceOntCfgCapabilityEntry 4 }

        hwEponDeviceOntCfgCapTdmNum OBJECT-TYPE
            SYNTAX       Integer32
            MAX-ACCESS   read-only
            STATUS       current
            DESCRIPTION
                "This object indicates the number of TDM ports."
            ::= { hwEponDeviceOntCfgCapabilityEntry 5 }

        hwEponDeviceOntCfgCapEthNum OBJECT-TYPE
            SYNTAX       Integer32
            MAX-ACCESS   read-only
            STATUS       current
            DESCRIPTION
                "This object indicates the number ethernet ports.
                 A special value of 0xFE (254) indicates the number
                 of port is adaptive."
            ::= { hwEponDeviceOntCfgCapabilityEntry 6 }

-- hwEponDeviceOntControlInfoTable
        hwEponDeviceOntControlInfoTable OBJECT-TYPE
            SYNTAX     SEQUENCE OF HwEponDeviceOntControlInfoEntry
            MAX-ACCESS not-accessible
            STATUS     current
            DESCRIPTION
                "This is the control table of the ONT.
                 The index of this table is a combination of ifIndex and hwEponDeviceOntIndex.
                "
            ::= { hwXponDeviceControlObjects 57 }

        hwEponDeviceOntControlInfoEntry OBJECT-TYPE
            SYNTAX     HwEponDeviceOntControlInfoEntry
            MAX-ACCESS not-accessible
            STATUS     current
            DESCRIPTION
                "This is the control table of the ONT.
                 The index of this entry is a combination of ifIndex and hwEponDeviceOntIndex.
                "
            INDEX       { ifIndex, hwEponDeviceOntIndex}
            ::= { hwEponDeviceOntControlInfoTable 1 }

        HwEponDeviceOntControlInfoEntry ::=
            SEQUENCE {
                hwEponDeviceOntActive                 INTEGER,
                hwEponDeviceOntReset                  INTEGER,
                hwEponDeviceOntReRegister             INTEGER,
                hwEponDeviceOntReDiscovery            INTEGER,
                hwEponDeviceOntPing                   Integer32,
                hwEponDeviceOntRunStatus              INTEGER,
                hwEponDeviceOntConfigStatus           INTEGER,
                hwEponDeviceOntDiscoveryState         INTEGER,
                hwEponDeviceOntMatchStatus            INTEGER,
                hwEponDeviceOntDistance               Integer32,
                hwEponDeviceOntRtt                    Integer32,
                hwEponDeviceOntUpStreamBW             Integer32,
                hwEponDeviceOntDownStreamBW           Integer32,
                hwEponDeviceOntLastUpTime             DateAndTime,
                hwEponDeviceOntLastDownTime           DateAndTime,
                hwEponDeviceOntLastDownCause          Integer32,
                hwEponDeviceOntLastDyingGaspTime      DateAndTime,
                hwEponDeviceOntIsolationStatus        INTEGER,
                hwEponDeviceOntActualNniType          INTEGER,
                hwEponDeviceOntLastActualNniType      INTEGER,
                hwEponDeviceOntLastDistance           Integer32
            }

        hwEponDeviceOntActive OBJECT-TYPE
            SYNTAX      INTEGER {
                activate(1),
                deactivate(2),
                invalid(-1)
            }
            MAX-ACCESS  read-write
            STATUS      current
            DESCRIPTION
                "This object is used to activate or deactivate an ONT.
                 Options:
                 1. activate(1)             - Activates an ONT
                 2. deactivate(2)           - Deactivates an ONT
                 3. invalid (-1)            - Indicates that the query fails or no information is detected
                "
            DEFVAL { activate }
            ::= { hwEponDeviceOntControlInfoEntry 1 }

        hwEponDeviceOntReset OBJECT-TYPE
            SYNTAX      INTEGER {
                reset(1),
                invalid(-1)
            }
            MAX-ACCESS  read-write
            STATUS      current
            DESCRIPTION
                "This object is used to reset an ONT.
                 Options:
                 1. reset(1)          - Reset an ONT
                 2. invalid(-1)       - Indicates that the query fails or no information is detected
                "
            ::= { hwEponDeviceOntControlInfoEntry 2 }

        hwEponDeviceOntReRegister OBJECT-TYPE
            SYNTAX      INTEGER {
                reRegister(1),
                invalid(-1)
            }
            MAX-ACCESS  read-write
            STATUS      current
            DESCRIPTION
                "This object is used to re-register an ONT.
                 Options:
                 1. reRegister(1)     - Re-register an ONT
                 2. invalid(-1)       - Indicates that the query fails or no information is detected
                "
            ::= { hwEponDeviceOntControlInfoEntry 3 }

        hwEponDeviceOntReDiscovery OBJECT-TYPE
            SYNTAX      INTEGER {
                rediscovery(1),
                invalid(-1)
            }
            MAX-ACCESS  read-write
            STATUS      current
            DESCRIPTION
                "This object is used to reset the discovery status of an ONT.
                 If the authentication mode is once-on(4), after performing the rediscovery operation,
                 the registered working period is re-timed.
                 Options:
                 1. rediscovery(1)     - Reset the discovery status of an ONT
                 2. invalid(-1)        - Indicates that the query fails or no information is detected
                "
            ::= { hwEponDeviceOntControlInfoEntry 4 }

        hwEponDeviceOntPing OBJECT-TYPE
            SYNTAX      Integer32
            MAX-ACCESS  read-only
            STATUS      current
            DESCRIPTION
                "This object indicates the ONT ping."
            ::= { hwEponDeviceOntControlInfoEntry 5 }

        hwEponDeviceOntRunStatus OBJECT-TYPE
            SYNTAX      INTEGER {
                up(1),
                down(2),
                invalid(-1)
            }
            MAX-ACCESS  read-only
            STATUS      current
            DESCRIPTION
                "This object indicates the ONT running status.
                 Options:
                 1. up(1)                       - Normal
                 2. down(2)                     - Fault
                 3. invalid(-1)                 - Indicates that the query fails or no information is detected
                "
            ::= { hwEponDeviceOntControlInfoEntry 15 }

        hwEponDeviceOntConfigStatus OBJECT-TYPE
            SYNTAX      INTEGER {
                initialization(1),
                normal(2),
                failed(3),
                noresume(4),
                config(5),
                invalid(-1)
            }
            MAX-ACCESS  read-only
            STATUS      current
            DESCRIPTION
                "This is the ONT configuration resume status. If it is failed(3),
                 the ONT is down and the service is interrupted.
                 If the config status is noresume (4), set the resume policy as
                 resume for the system and re-register the ONT.
                 Options:
                 1. initialization(1)     - Indicates that the ONT configuration resume status is initialization
                 2. normal(2)             - Indicates that the ONT configuration resume status is normal
                 3. failed(3)             - Indicates that the ONT configuration resume status is failed
                 4. noresume(4)           - Indicates that the ONT configuration resume status is not resumed
                 5. config(5)             - Indicates that the ONT configuration resume status is configuration
                 6. invalid(-1)           - Indicates that the query fails or no information is detected
                "
            ::= { hwEponDeviceOntControlInfoEntry 16 }

        hwEponDeviceOntDiscoveryState OBJECT-TYPE
            SYNTAX      INTEGER{
                on(1),
                off(2),
                invalid(-1)
            }
            MAX-ACCESS  read-only
            STATUS      current
            DESCRIPTION
                "This object indicates the ONT discovery state.
                 Options:
                 1. on(1)               - Indicates that the ONT discovery state is on
                 2. off(2)              - Indicates that the ONT discovery state is off
                 3. invalid(-1)         - Indicates that the query fails or no information is detected
                "
            ::= { hwEponDeviceOntControlInfoEntry 17 }

        hwEponDeviceOntMatchStatus OBJECT-TYPE
            SYNTAX       INTEGER {
                initialization(1),
                match(2),
                mismatch(3),
                invalid(-1)
            }
            MAX-ACCESS   read-only
            STATUS       current
            DESCRIPTION
                "This object indicates the ONT match status.
                 Options:
                 1. initialization(1)        - Indicates that the ONT is initialization
                 2. match(2)                 - Indicates that the ONT is matched
                 3. mismatch(3)              - Indicates that the ONT is mismatched
                 4. invalid(-1)              - Indicates that the query fails or no information is detected
                "
            ::= { hwEponDeviceOntControlInfoEntry 18 }

        hwEponDeviceOntDistance OBJECT-TYPE
            SYNTAX      Integer32
            MAX-ACCESS  read-only
            STATUS      current
            DESCRIPTION
                "This object indicates the result of the ONT ranging."
            ::= { hwEponDeviceOntControlInfoEntry 19 }

        hwEponDeviceOntRtt OBJECT-TYPE
            SYNTAX      Integer32
            MAX-ACCESS  read-only
            STATUS      current
            DESCRIPTION
                "This object indicates the result of the ONT ranging(RTT)."
            ::= { hwEponDeviceOntControlInfoEntry 20 }

        hwEponDeviceOntUpStreamBW OBJECT-TYPE
            SYNTAX      Integer32
            MAX-ACCESS  read-only
            STATUS      current
            DESCRIPTION
                "This object indicates the upstream bandwidth of the ONT."
            ::= { hwEponDeviceOntControlInfoEntry 21 }

        hwEponDeviceOntDownStreamBW OBJECT-TYPE
            SYNTAX      Integer32
            MAX-ACCESS  read-only
            STATUS      current
            DESCRIPTION
                "This object indicates the downstream bandwidth of the ONT."
            ::= { hwEponDeviceOntControlInfoEntry 22 }

        hwEponDeviceOntLastUpTime OBJECT-TYPE
            SYNTAX      DateAndTime
            MAX-ACCESS  read-only
            STATUS      current
            DESCRIPTION
                "This object indicates the time when the ONT last goes online."
            ::= { hwEponDeviceOntControlInfoEntry 23 }

        hwEponDeviceOntLastDownTime OBJECT-TYPE
            SYNTAX      DateAndTime
            MAX-ACCESS  read-only
            STATUS      current
            DESCRIPTION
                "This object indicates the time when the ONT last goes offline."
            ::= { hwEponDeviceOntControlInfoEntry 24 }

        hwEponDeviceOntLastDownCause OBJECT-TYPE
            SYNTAX       Integer32
            MAX-ACCESS   read-only
            STATUS       current
            DESCRIPTION
                "This object indicates the reason why the ONT last went offline.
                 The value (1) indicates that the reason is LOS(Loss of signal),
                 The value (2) indicates that the reason is LOSI(Loss of signal for ONUi),
                 The value (3) indicates that the reason is LOFI(Loss of frame of ONUi),
                 The value (4) indicates that the reason is SFI(Signal fail of ONUi),
                 The value (5) indicates that the reason is LOAI(Loss of acknowledge with ONUi),
                 The value (6) indicates that the reason is LOAMI(Loss of PLOAM for ONUi),
                 The value (7) indicates that the reason is deactive ONT fails,
                 The value (8) indicates that the reason is deactive ONT success,
                 The value (9) indicates that the reason is reset ONT,
                 The value (10) indicates that the reason is re-register ONT,
                 The value (11) indicates that the reason is pop up fail,
                 The value (12) indicates that the reason is authentication fail,
                 The value (13) indicates that the reason is dying-gasp,
                 The value (14) reserved,
                 The value (15) indicates that the reason is LOKI(Loss of key synch with ONUi),
                 The value (18) indicates that the reason is deactived ONT due to the ring,
                 The value (30) indicates that the reason is shut down ONT optical module,
                 The value (31) indicates that the reason is reset ONT by ONT command,
                 The value (32) indicates that the reason is reset ONT by ONT reset button,
                 The value (33) indicates that the reason is reset ONT by ONT software,
                 The value (34) indicates that the reason is deactived ONT due to broadcast attack,
                 The value (37) indicates that the reason is a rogue ONT detected by itself,
                 The value (-1) indicates that the query fails.
                 "
            ::= { hwEponDeviceOntControlInfoEntry 25 }

        hwEponDeviceOntLastDyingGaspTime OBJECT-TYPE
            SYNTAX      DateAndTime
            MAX-ACCESS  read-only
            STATUS      current
            DESCRIPTION
                "This object indicates the time when the ONT last goes down due to Dying Gasp."
            ::= { hwEponDeviceOntControlInfoEntry 26 }

        hwEponDeviceOntIsolationStatus OBJECT-TYPE
            SYNTAX      INTEGER {
                normal(0),
                isolated(1)
            }
            MAX-ACCESS  read-only
            STATUS      current
            DESCRIPTION
                "This object indicates the ONT isolation status.
                 Options:
                 1. normal(0)          - Indicates that the ONT is normal
                 2. isolated(1)        - Indicates that the ONT is isolated
                "
            ::= { hwEponDeviceOntControlInfoEntry 27 }

        hwEponDeviceOntActualNniType OBJECT-TYPE
            SYNTAX INTEGER {
                rate1G1G(1),
                rate10G1G(2),
                rate10G10G(3),
                rate10G2G(5),
                invalid(-1)
            }
            MAX-ACCESS read-only
            STATUS current
            DESCRIPTION
                "This object indicates the ONT actual rate type.
                 Options:
                 1. rate1G1G(1)               - Downstream rate 1Gbps, upstream rate 1Gbps
                 2. rate10G1G(2)              - Downstream rate 10Gbps, upstream rate 1Gbps
                 3. rate10G10G(3)             - Downstream rate 10Gbps, upstream rate 10Gbps
                 4. rate10G2G(5)              - Downstream rate 10Gbps, upstream rate 2Gbps
                 5. invalid(-1)               - Indicates that the query fails or no information is detected
                "
            ::= { hwEponDeviceOntControlInfoEntry 28 }

        hwEponDeviceOntLastActualNniType OBJECT-TYPE
            SYNTAX INTEGER {
                rate1G1G(1),
                rate10G1G(2),
                rate10G10G(3),
                rate10G2G(5),
                invalid(-1)
            }
            MAX-ACCESS read-only
            STATUS current
            DESCRIPTION
                "This object indicates the ONT last actual rate type.
                 Options:
                 1. rate1G1G(1)               - Downstream rate 1Gbps, upstream rate 1Gbps
                 2. rate10G1G(2)              - Downstream rate 10Gbps, upstream rate 1Gbps
                 3. rate10G10G(3)             - Downstream rate 10Gbps, upstream rate 10Gbps
                 4. rate10G2G(5)              - Downstream rate 10Gbps, upstream rate 2Gbps
                 5. invalid(-1)               - Indicates that the query fails or no information is detected
                "
            ::= { hwEponDeviceOntControlInfoEntry 29 }

        hwEponDeviceOntLastDistance OBJECT-TYPE
            SYNTAX      Integer32
            MAX-ACCESS  read-only
            STATUS      current
            DESCRIPTION
                "This object indicates the result of the ONT last ranging."
            ::= { hwEponDeviceOntControlInfoEntry 30 }

-- hwEponDeviceAutoFindOntInfoTable
        hwEponDeviceAutoFindOntInfoTable OBJECT-TYPE
            SYNTAX     SEQUENCE OF HwEponDeviceAutoFindOntInfoEntry
            MAX-ACCESS not-accessible
            STATUS     current
            DESCRIPTION
                "The table is used to query ONT(s) that are found automatically.
                 The index of this table is a combination of ifIndex and hwEponDeviceAutoFindOntInfoOntIndex.
                "
            ::= { hwXponDeviceControlObjects 58 }

        hwEponDeviceAutoFindOntInfoEntry OBJECT-TYPE
            SYNTAX     HwEponDeviceAutoFindOntInfoEntry
            MAX-ACCESS not-accessible
            STATUS     current
            DESCRIPTION
                "The table is used to query ONT(s) that are found automatically.
                 The index of this entry is a combination of ifIndex and hwEponDeviceAutoFindOntInfoOntIndex.
                "
            INDEX       { ifIndex, hwEponDeviceAutoFindOntInfoOntIndex }
            ::= { hwEponDeviceAutoFindOntInfoTable 1 }

        HwEponDeviceAutoFindOntInfoEntry ::=
            SEQUENCE {
                hwEponDeviceAutoFindOntInfoOntIndex             Integer32,
                hwEponDeviceAutoFindOntInfoMacAddress           MacAddress,
                hwEponDeviceAutoFindOntInfoPasswordValue        OCTET STRING,
                hwEponDeviceAutoFindOntInfoVendorId             Integer32,
                hwEponDeviceAutoFindOntInfoSoftwareVersion      OCTET STRING,
                hwEponDeviceAutoFindOntInfoHardwareVersion      OCTET STRING,
                hwEponDeviceAutoFindOntInfoAutoFindTime         DateAndTime,
                hwEponDeviceAutoFindOntInfoOntModel             Integer32,
                hwEponDeviceAutoFindOntInfoLoid                 OCTET STRING,
                hwEponDeviceAutoFindOntInfoCheckcode            OCTET STRING,
                hwEponDeviceAutoFindOntNniType                  INTEGER,
                hwEponDeviceAutoFindOntInfoOntExtendedModel     OCTET STRING,
                hwEponDeviceAutoFindOntInfoOuiVersion           OCTET STRING,
                hwEponDeviceAutoFindOntInfoCustomizedInfo       OCTET STRING
            }

        hwEponDeviceAutoFindOntInfoOntIndex  OBJECT-TYPE
            SYNTAX     Integer32
            MAX-ACCESS   not-accessible
            STATUS      current
            DESCRIPTION
                "This object indicates the auto find ONT index, range: 0~254."
            ::= { hwEponDeviceAutoFindOntInfoEntry 1 }

        hwEponDeviceAutoFindOntInfoMacAddress  OBJECT-TYPE
            SYNTAX     MacAddress
            MAX-ACCESS   read-only
            STATUS      current
            DESCRIPTION
                "This object indicates the MAC address of ONT."
            ::= { hwEponDeviceAutoFindOntInfoEntry 2 }

        hwEponDeviceAutoFindOntInfoPasswordValue OBJECT-TYPE
            SYNTAX     OCTET STRING   (SIZE (0..32))
            MAX-ACCESS   read-only
            STATUS      current
            DESCRIPTION
                "This object indicates the password of ONT."
            ::= { hwEponDeviceAutoFindOntInfoEntry 3 }

        hwEponDeviceAutoFindOntInfoVendorId OBJECT-TYPE
            SYNTAX     Integer32
            MAX-ACCESS   read-only
            STATUS      current
            DESCRIPTION
                "This object indicates the Vendor identifier of ONT."
            ::= { hwEponDeviceAutoFindOntInfoEntry 4 }

        hwEponDeviceAutoFindOntInfoSoftwareVersion OBJECT-TYPE
            SYNTAX     OCTET STRING   (SIZE (16))
            MAX-ACCESS   read-only
            STATUS      current
            DESCRIPTION
                "This object indicates the Software version of ONT."
            ::= { hwEponDeviceAutoFindOntInfoEntry 5 }

        hwEponDeviceAutoFindOntInfoHardwareVersion OBJECT-TYPE
            SYNTAX     OCTET STRING   (SIZE (8))
            MAX-ACCESS   read-only
            STATUS      current
            DESCRIPTION
                "This object indicates the hardware version of ONT."
            ::= { hwEponDeviceAutoFindOntInfoEntry 6 }

        hwEponDeviceAutoFindOntInfoAutoFindTime OBJECT-TYPE
            SYNTAX      DateAndTime
            MAX-ACCESS  read-only
            STATUS      current
            DESCRIPTION
                "This object indicates the time for ONT's auto find."
            ::= { hwEponDeviceAutoFindOntInfoEntry 7 }

        hwEponDeviceAutoFindOntInfoOntModel OBJECT-TYPE
            SYNTAX     Integer32
            MAX-ACCESS   read-only
            STATUS      current
            DESCRIPTION
                "This object indicates the Mode of ONT."
            ::= { hwEponDeviceAutoFindOntInfoEntry 8 }

        hwEponDeviceAutoFindOntInfoLoid OBJECT-TYPE
            SYNTAX     OCTET STRING    (SIZE (0..24))
            MAX-ACCESS   read-only
            STATUS      current
            DESCRIPTION
                "This object indicates the ONT LOID."
            ::= { hwEponDeviceAutoFindOntInfoEntry 9 }

        hwEponDeviceAutoFindOntInfoCheckcode OBJECT-TYPE
            SYNTAX     OCTET STRING    (SIZE (0..12))
            MAX-ACCESS   read-only
            STATUS      current
            DESCRIPTION
                "This object indicates the ONT CHECKCODE."
            ::= { hwEponDeviceAutoFindOntInfoEntry 10 }

        hwEponDeviceAutoFindOntNniType OBJECT-TYPE
            SYNTAX INTEGER {
                rate1G1G(1),
                rate10G1G(2),
                rate10G10G(3),
                rate10G2G(5),
                invalid(-1)
            }
            MAX-ACCESS read-only
            STATUS current
            DESCRIPTION
                "This object indicates the ONT actual rate type.
                 Options:
                 1. rate1G1G(1)               - Downstream rate 1Gbps, upstream rate 1Gbps
                 2. rate10G1G(2)              - Downstream rate 10Gbps, upstream rate 1Gbps
                 3. rate10G10G(3)             - Downstream rate 10Gbps, upstream rate 10Gbps
                 4. rate10G2G(5)              - Downstream rate 10Gbps, upstream rate 2Gbps
                 5. invalid(-1)               - Indicates that the query fails or no information is detected
                "
            ::= { hwEponDeviceAutoFindOntInfoEntry 11 }

        hwEponDeviceAutoFindOntInfoOntExtendedModel OBJECT-TYPE
            SYNTAX     OCTET STRING    (SIZE (1..32))
            MAX-ACCESS   read-only
            STATUS      current
            DESCRIPTION
                "This object indicates the ONT extended model."
            ::= { hwEponDeviceAutoFindOntInfoEntry 12 }

        hwEponDeviceAutoFindOntInfoOuiVersion OBJECT-TYPE
            SYNTAX     OCTET STRING    (SIZE (1..32))
            MAX-ACCESS   read-only
            STATUS      current
            DESCRIPTION
                "This object indicates the highest ONT OUI version"
            ::= { hwEponDeviceAutoFindOntInfoEntry 13 }

        hwEponDeviceAutoFindOntInfoCustomizedInfo OBJECT-TYPE
            SYNTAX     OCTET STRING    (SIZE (1..24))
            MAX-ACCESS   read-only
            STATUS      current
            DESCRIPTION
                "This object indicates the ONT customize information.
		"
            ::= { hwEponDeviceAutoFindOntInfoEntry 14 }

-- hwEponDeviceOntCapabilityInfoTable
        hwEponDeviceOntCapabilityInfoTable OBJECT-TYPE
            SYNTAX     SEQUENCE OF HwEponDeviceOntCapabilityInfoEntry
            MAX-ACCESS not-accessible
            STATUS     current
            DESCRIPTION
                "This table is used to query the ONT capability set.
                 The index of this table is a combination of ifIndex and hwEponDeviceOntIndex.
                "
            ::= { hwXponDeviceControlObjects 59 }

        hwEponDeviceOntCapabilityInfoEntry OBJECT-TYPE
            SYNTAX     HwEponDeviceOntCapabilityInfoEntry
            MAX-ACCESS not-accessible
            STATUS     current
            DESCRIPTION
                "This table is used to query the ONT capability set.
                 The index of this entry is a combination of ifIndex and hwEponDeviceOntIndex.
                "
            INDEX       { ifIndex, hwEponDeviceOntIndex }
            ::= { hwEponDeviceOntCapabilityInfoTable 1 }

        HwEponDeviceOntCapabilityInfoEntry ::=
            SEQUENCE {
                hwEponDeviceOntPOTSPortNum                       Integer32,
                hwEponDeviceOntFEPortsNum                        Integer32,
                hwEponDeviceOntGEPortsNum                        Integer32,
                hwEponDeviceOntTDMPortsNum                       Integer32,
                hwEponDeviceOntFECSupport                        Integer32,
                hwEponDeviceOntSupportbackupbattery              Integer32,
                hwEponDeviceOntUpQueueAllocationIncre            Integer32,
                hwEponDeviceOntUpQueueNum                        Integer32,
                hwEponDeviceOntUpQueueNumPerPort                 Integer32,
                hwEponDeviceOntDownQueueNum                      Integer32,
                hwEponDeviceOntDownQueueNumPerPort               Integer32,
                hwEponDeviceOntFePortList                        PortList,
                hwEponDeviceOntGePortList                        PortList,
                hwEponDeviceOntSupportMulticastQuickLeave        Integer32,
                hwEponDeviceOntDeviceType                        INTEGER,
                hwEponDeviceOntMultiLLID                         Integer32,
                hwEponDeviceOntProtectionType                    INTEGER,
                hwEponDeviceOntPonIFNum                          Integer32,
                hwEponDeviceOntSlotNum                           Integer32,
                hwEponDeviceOntADSL2plusNum                      Integer32,
                hwEponDeviceOntVDSL2Num                          Integer32,
                hwEponDeviceOntWLANNum                           Integer32,
                hwEponDeviceOntUSBNum                            Integer32,
                hwEponDeviceOntCATVNum                           Integer32,
                hwEponDeviceOntSupportIPv6Aware                  INTEGER,
                hwEponDeviceOntSupportPowerSupplyControl         INTEGER,
                hwEponDeviceOntSupportServiceSLA                 Integer32,
		hwEponDeviceOnt10GEPortsNum                      Integer32
            }

        hwEponDeviceOntPOTSPortNum  OBJECT-TYPE
            SYNTAX     Integer32
            MAX-ACCESS   read-only
            STATUS      current
            DESCRIPTION
                "This object indicates the number of POTS ports."
            ::= { hwEponDeviceOntCapabilityInfoEntry 1 }

        hwEponDeviceOntFEPortsNum  OBJECT-TYPE
            SYNTAX     Integer32
            MAX-ACCESS   read-only
            STATUS      current
            DESCRIPTION
                "This object indicates the number of FE ports."
            ::= { hwEponDeviceOntCapabilityInfoEntry 2 }

        hwEponDeviceOntGEPortsNum  OBJECT-TYPE
            SYNTAX     Integer32
            MAX-ACCESS   read-only
            STATUS      current
            DESCRIPTION
                "This object indicates the number of GE ports."
            ::= { hwEponDeviceOntCapabilityInfoEntry 3 }

        hwEponDeviceOntTDMPortsNum  OBJECT-TYPE
            SYNTAX     Integer32
            MAX-ACCESS   read-only
            STATUS      current
            DESCRIPTION
                "This object indicates the number of TDM ports."
            ::= { hwEponDeviceOntCapabilityInfoEntry 4 }

        hwEponDeviceOntFECSupport  OBJECT-TYPE
            SYNTAX     Integer32
            MAX-ACCESS   read-only
            STATUS      current
            DESCRIPTION
                "This object indicates whether the ONT supports the FEC.
                 The value (1) indicates that the ONT supports the FEC.
                 The value (2) indicates that the ONT not supports the FEC.
                 The value (-1) indicates that the query fails or no information is detected."
            ::= { hwEponDeviceOntCapabilityInfoEntry 5 }

        hwEponDeviceOntSupportbackupbattery  OBJECT-TYPE
            SYNTAX     Integer32
            MAX-ACCESS   read-only
            STATUS      current
            DESCRIPTION
                "This object indicates whether the ONT supports the standby battery."
            ::= { hwEponDeviceOntCapabilityInfoEntry 6 }

        hwEponDeviceOntUpQueueAllocationIncre  OBJECT-TYPE
            SYNTAX     Integer32
            MAX-ACCESS   read-only
            STATUS      current
            DESCRIPTION
                "This object indicates the increment of the allocated bandwidth of the upstream queue."
            ::= { hwEponDeviceOntCapabilityInfoEntry 7 }

        hwEponDeviceOntUpQueueNum  OBJECT-TYPE
            SYNTAX     Integer32
            MAX-ACCESS   read-only
            STATUS      current
            DESCRIPTION
                "This object indicates the number of upstream queues."
            ::= { hwEponDeviceOntCapabilityInfoEntry 8 }

        hwEponDeviceOntUpQueueNumPerPort  OBJECT-TYPE
            SYNTAX     Integer32
            MAX-ACCESS   read-only
            STATUS      current
            DESCRIPTION
                "This object indicates the maximum number of queues of the upsstream port."
            ::= { hwEponDeviceOntCapabilityInfoEntry 9 }

        hwEponDeviceOntDownQueueNum  OBJECT-TYPE
            SYNTAX     Integer32
            MAX-ACCESS   read-only
            STATUS      current
            DESCRIPTION
                "This object indicates the number of downstream queues."
            ::= { hwEponDeviceOntCapabilityInfoEntry 10}

        hwEponDeviceOntDownQueueNumPerPort  OBJECT-TYPE
            SYNTAX     Integer32
            MAX-ACCESS   read-only
            STATUS      current
            DESCRIPTION
                "This object indicates the maximum number of queues of the downstream port."
            ::= { hwEponDeviceOntCapabilityInfoEntry 11}

        hwEponDeviceOntFePortList  OBJECT-TYPE
            SYNTAX     PortList (SIZE (200))
            MAX-ACCESS   read-only
            STATUS      current
            DESCRIPTION
                "This object indicates the bitmap of the FE port."
            ::= { hwEponDeviceOntCapabilityInfoEntry 12}

        hwEponDeviceOntGePortList  OBJECT-TYPE
            SYNTAX     PortList (SIZE (200))
            MAX-ACCESS   read-only
            STATUS      current
            DESCRIPTION
                "This object indicates the bitmap of the GE port."
            ::= { hwEponDeviceOntCapabilityInfoEntry 13}

        hwEponDeviceOntSupportMulticastQuickLeave OBJECT-TYPE
            SYNTAX     Integer32
            MAX-ACCESS   read-only
            STATUS      current
            DESCRIPTION
                "This object indicates the multicast quick leave capability."
            ::= { hwEponDeviceOntCapabilityInfoEntry 14}

        hwEponDeviceOntDeviceType  OBJECT-TYPE
            SYNTAX     INTEGER{
                sfu(0),
                hgu(1),
                sbu(2),
                boxShapedMDU(3),
                smallCapacityCardTypeMDU(4),
                boxShapedCardTypeMDU(5),
                rackCardTypeMDU(6),
                cardTypeMDU(7),
                mtu(8),
                invalid(-1)
            }
            MAX-ACCESS   read-only
            STATUS      current
            DESCRIPTION
                "This object indicates the ONT device type.
                 Options:
                 1. sfu(0)                         - SFU
                 2. hgu(1)                         - HGU
                 3. sbu(2)                         - SBU
                 4. boxShapedMDU(3)                - Box shaped MDU
                 5. smallCapacityCardTypeMDU(4)    - Small capacity card type MDU
                 6. boxShapedCardTypeMDU(5)        - Box shaped card type MDU
                 7. rackCardTypeMDU(6)             - Rack card type MDU
                 8. cardTypeMDU(7)                 - Card type MDU
                 9. mtu(8)                         - MTU
                 10. invalid(-1)                   - Indicates that the query fails or no information is detected
                "
            ::= { hwEponDeviceOntCapabilityInfoEntry 15 }

        hwEponDeviceOntMultiLLID  OBJECT-TYPE
            SYNTAX     Integer32 (-1 | 0..255)
            MAX-ACCESS   read-only
            STATUS      current
            DESCRIPTION
                "This object indicates the ONT device multiLLID.
                 -1 indicates an invalid value.
                 A value from 1 to 255 indicates the number of supported LLIDs.
                 In CTC Technical Specification for EPON Equipment V2.1_200904,
                 0 indicates that multiple LLIDs are supported.
                 In CTC Technical Specification for EPON Equipment V2.1_200912,
                 0 indicates an invalid value.
                "
            ::= { hwEponDeviceOntCapabilityInfoEntry 16 }

        hwEponDeviceOntProtectionType  OBJECT-TYPE
            SYNTAX     INTEGER{
                unsupport(0),
                typecProtection(1),
                typedProtection(2),
                invalid(-1)
            }
            MAX-ACCESS   read-only
            STATUS      current
            DESCRIPTION
                "This object indicates the ONT protection type.
                 Options:
                 1. unsupport(0)                   - Do not support the ONT protection
                 2. typecProtection(1)            - Type C protection
                 3. typedProtection(2)            - Type D protection
                 4. invalid(-1)                    - Indicates that the query fails or no information is detected
                "
            ::= { hwEponDeviceOntCapabilityInfoEntry 17 }

        hwEponDeviceOntPonIFNum  OBJECT-TYPE
            SYNTAX     Integer32
            MAX-ACCESS   read-only
            STATUS      current
            DESCRIPTION
                "This object indicates the ONT device ponIF number."
            ::= { hwEponDeviceOntCapabilityInfoEntry 18 }

        hwEponDeviceOntSlotNum  OBJECT-TYPE
            SYNTAX     Integer32
            MAX-ACCESS   read-only
            STATUS      current
            DESCRIPTION
                "This object indicates the ONT device slot number."
            ::= { hwEponDeviceOntCapabilityInfoEntry 19 }

        hwEponDeviceOntADSL2plusNum  OBJECT-TYPE
            SYNTAX     Integer32
            MAX-ACCESS   read-only
            STATUS      current
            DESCRIPTION
                "This object indicates the ONT device ADSL2 + port number"
            ::= { hwEponDeviceOntCapabilityInfoEntry 20 }

        hwEponDeviceOntVDSL2Num  OBJECT-TYPE
            SYNTAX     Integer32
            MAX-ACCESS   read-only
            STATUS      current
            DESCRIPTION
                "This object indicates the ONT device VDSL2 port number."
            ::= { hwEponDeviceOntCapabilityInfoEntry 21 }

        hwEponDeviceOntWLANNum  OBJECT-TYPE
            SYNTAX     Integer32
            MAX-ACCESS   read-only
            STATUS      current
            DESCRIPTION
                "This object indicates the ONT device WLAN port number."
            ::= { hwEponDeviceOntCapabilityInfoEntry 22 }

        hwEponDeviceOntUSBNum  OBJECT-TYPE
            SYNTAX     Integer32
            MAX-ACCESS   read-only
            STATUS      current
            DESCRIPTION
                "This object indicates the ONT device USB port number."
            ::= { hwEponDeviceOntCapabilityInfoEntry 23 }

        hwEponDeviceOntCATVNum  OBJECT-TYPE
            SYNTAX     Integer32
            MAX-ACCESS   read-only
            STATUS      current
            DESCRIPTION
                "This object indicates the ONT device CATV port number."
            ::= { hwEponDeviceOntCapabilityInfoEntry 24 }

        hwEponDeviceOntSupportIPv6Aware OBJECT-TYPE
            SYNTAX     INTEGER {
                 unsupport(1),
                 support(2),
                 invalid(-1)
            }
            MAX-ACCESS   read-only
            STATUS      current
            DESCRIPTION
                 "This object indicates whether the ONT supports IPv6 aware.
                 Options:
                 1.unsupport(1)         - Indicates that the ONT does not support IPv6 aware.
                 2.support(2)           - Indicates that the ONT supports IPv6 aware.
                 3.invalid(-1)          - Indicates that the query fails or no information is detected.
                "
            ::= { hwEponDeviceOntCapabilityInfoEntry 25 }

        hwEponDeviceOntSupportPowerSupplyControl OBJECT-TYPE
            SYNTAX     INTEGER{
                 unsupport(1),
                 supportTx(2),
                 supportTxAndRx(3),
                 invalid(-1)
            }
            MAX-ACCESS   read-only
            STATUS      current
            DESCRIPTION
                 "This object indicates whether the ONT supports power supply control.
                 Options:
                 1. unsupport(1)        - Indicates that the ONT does not support power supply control.
                 2. supportTx(2)        - Indicates that the ONT only supports Tx power supply control.
                 3. supportTxAndRx(3)   - Indicates that the ONT supports both Tx power and Rx power supply control.
                 4. invalid(-1)         - Indicates that the query fails or no information is detected.
                "
            ::= { hwEponDeviceOntCapabilityInfoEntry 26 }

        hwEponDeviceOntSupportServiceSLA OBJECT-TYPE
            SYNTAX     Integer32( -1 | 1..8 )
            MAX-ACCESS   read-only
            STATUS      current
            DESCRIPTION
                 "This object indicates whether the ONT supports service SLA.
                 The value (1) indicates that the ONT does not support service SLA.
                 The value (2-8) indicates the number of the ONT supports service SLA.
                 The value (-1) indicates that the query fails or no information is detected.
                "
           ::= { hwEponDeviceOntCapabilityInfoEntry 27 }

	hwEponDeviceOnt10GEPortsNum  OBJECT-TYPE
            SYNTAX     Integer32
            MAX-ACCESS   read-only
            STATUS      current
            DESCRIPTION
                "This object indicates the number of 10GE ports."
            ::= { hwEponDeviceOntCapabilityInfoEntry 28 }

-- hwEponDeviceOntIpConfigInfoTable
        hwEponDeviceOntIpConfigInfoTable OBJECT-TYPE
            SYNTAX     SEQUENCE OF HwEponDeviceOntIpConfigInfoEntry
            MAX-ACCESS not-accessible
            STATUS     current
            DESCRIPTION
                "This is the ONT IP configuration table. This table is used to configure and query
                 the IP configuration mode and IP address of an ONT.
                 The index of this table is a combination of ifIndex and hwEponDeviceOntIndex.
                "
            ::= { hwXponDeviceControlObjects 60 }

        hwEponDeviceOntIpConfigInfoEntry OBJECT-TYPE
            SYNTAX     HwEponDeviceOntIpConfigInfoEntry
            MAX-ACCESS not-accessible
            STATUS     current
            DESCRIPTION
                "This is the ONT IP configuration table. This table is used to configure and query
                 the IP configuration mode and IP address of an ONT.
                 The index of this entry is a combination of ifIndex and hwEponDeviceOntIndex.
                "
            INDEX       { ifIndex, hwEponDeviceOntIndex }
            ::= { hwEponDeviceOntIpConfigInfoTable 1 }

        HwEponDeviceOntIpConfigInfoEntry ::=
            SEQUENCE {
                hwEponDeviceOntIpConfigVlan                 Integer32,
                hwEponDeviceOntIpAddress                    IpAddress,
                hwEponDeviceOntNetMask                      IpAddress,
                hwEponDeviceOntNetGateway                   IpAddress,
                hwEponDeviceOntIpConfigRowStatus            RowStatus,
                hwEponDeviceOntIpConfigPriority             Integer32
            }

        hwEponDeviceOntIpConfigVlan  OBJECT-TYPE
            SYNTAX       Integer32
            MAX-ACCESS   read-write
            STATUS      current
            DESCRIPTION
                "This object indicates the management VLAN."
            ::= { hwEponDeviceOntIpConfigInfoEntry 1 }

        hwEponDeviceOntIpAddress  OBJECT-TYPE
            SYNTAX     IpAddress
            MAX-ACCESS   read-write
            STATUS      current
            DESCRIPTION
                "This object indicates the IP address."
            ::= { hwEponDeviceOntIpConfigInfoEntry 2 }

        hwEponDeviceOntNetMask  OBJECT-TYPE
            SYNTAX     IpAddress
            MAX-ACCESS   read-write
            STATUS      current
            DESCRIPTION
                "This object indicates the subnet mask of the IP address."
            ::= { hwEponDeviceOntIpConfigInfoEntry 3 }

        hwEponDeviceOntNetGateway  OBJECT-TYPE
            SYNTAX     IpAddress
            MAX-ACCESS   read-write
            STATUS      current
            DESCRIPTION
                "This object indicates the default network gateway."
            ::= { hwEponDeviceOntIpConfigInfoEntry 4 }

        hwEponDeviceOntIpConfigRowStatus OBJECT-TYPE
            SYNTAX       RowStatus
            MAX-ACCESS   read-create
            STATUS      current
            DESCRIPTION
                "The hwEponDeviceOntIpConfigRowStatus is used to create a new row or to modify
                 or delete an existing row in this table.
                 Options:
                 1. createAndGo(4) -create a new instance of a conceptual row
                 2. destroy(6)     -delete the instances associated with an existing conceptual row
                "
            ::= { hwEponDeviceOntIpConfigInfoEntry 5 }

        hwEponDeviceOntIpConfigPriority  OBJECT-TYPE
            SYNTAX     Integer32
            MAX-ACCESS   read-write
            STATUS      current
            DESCRIPTION
                "This object indicates the management priority of MDU."
            DEFVAL { 0 }
            ::= { hwEponDeviceOntIpConfigInfoEntry 6 }

-- hwEponDeviceOntRegInfoTable
        hwEponDeviceOntRegInfoTable OBJECT-TYPE
            SYNTAX  SEQUENCE OF HwEponDeviceOntRegInfoEntry
            MAX-ACCESS  not-accessible
            STATUS  current
            DESCRIPTION
                "This table is used to query the register information about the ONT,
                 including the ONT MAC, register time and register result.
                 The index of this table is a combination of ifIndex and hwEponDeviceSerialNum.
                "
            ::= { hwXponDeviceControlObjects 61 }

        hwEponDeviceOntRegInfoEntry OBJECT-TYPE
            SYNTAX  HwEponDeviceOntRegInfoEntry
            MAX-ACCESS  not-accessible
            STATUS  current
            DESCRIPTION
                "This table is used to query the register information about the ONT,
                 including the ONT MAC, register time and register result.
                 The index of this entry is a combination of ifIndex and hwEponDeviceSerialNum.
                "
            INDEX  { ifIndex, hwEponDeviceSerialNum }
            ::= { hwEponDeviceOntRegInfoTable 1 }

        HwEponDeviceOntRegInfoEntry ::=
            SEQUENCE {
                hwEponDeviceSerialNum                    Integer32,
                hwEponDeviceRegOntMac                    OCTET STRING,
                hwEponDeviceRegOntResult                 INTEGER,
                hwEponDeviceRegOntTime                   DateAndTime,
                hwEponDeviceRegConflictedIfindex         Integer32,
                hwEponDeviceRegConflictedOntIndex        Integer32,
                hwEponDeviceRegOntPasswordValue          OCTET STRING,
                hwEponDeviceRegOntVendorId               Integer32,
                hwEponDeviceRegOntSoftwareVersion        OCTET STRING,
                hwEponDeviceRegOntHardwareVersion        OCTET STRING,
                hwEponDeviceRegOntModel                  Integer32,
                hwEponDeviceRegOntLoid                   OCTET STRING,
                hwEponDeviceRegOntCheckcode              OCTET STRING,
                hwEponDeviceRegOntRateType               INTEGER,
                hwEponDeviceRegOntExtendedModel          OCTET STRING,
                hwEponDeviceRegOntOuiVersion             OCTET STRING
            }

        hwEponDeviceSerialNum OBJECT-TYPE
            SYNTAX  Integer32
            MAX-ACCESS   not-accessible
            STATUS  current
            DESCRIPTION
                "This object indicates the register number."
            ::= { hwEponDeviceOntRegInfoEntry 1 }

        hwEponDeviceRegOntMac OBJECT-TYPE
            SYNTAX  OCTET STRING (SIZE (6))
            MAX-ACCESS  read-only
            STATUS  current
            DESCRIPTION
                "This object indicates the ONT MAC."
            ::= { hwEponDeviceOntRegInfoEntry 2 }

        hwEponDeviceRegOntResult OBJECT-TYPE
            SYNTAX  INTEGER {
                success(1),
                fail(2),
                macConflict(3),
                passwordConflict(4),
                loidConflict(5),
                passwordError(6),
                ccError(7),
                rangingOnuFail(8),
                unconfirmed(9),
                misMatch(10),
                loidError(11),
                invalid(-1)
            }
            MAX-ACCESS  read-only
            STATUS  current
            DESCRIPTION
                "This object indicates the register result.
                 Options:
                 1. success(1)                    - Indicates that the register result is success
                 2. fail(2)                       - Indicates that the register result is fail
                 3. macConflict(3)                - Indicates that the MAC conflict
                 4. passwordConflict(4)           - Indicates that the password conflict
                 5. loidConflict(5)               - Indicates that the LOID conflict
                 6. passwordError(6)              - Indicates that the password conflict
                 7. ccError(7)                    - Indicates that the CC error
                 8. rangingOnuFail(8)             - Indicates that the ranging ONU fail
                 9. unconfirmed(9)                - Indicates that the ONU is unconfirmed
                 10. misMatch(10)                 - Indicates that the ONU is mismatch
                 11. loidError(11)                - Indicates that the LOID error
                 12. invalid(-1)                  - Indicates that the query fails or no information is detected
                "
            ::= { hwEponDeviceOntRegInfoEntry 3 }

        hwEponDeviceRegOntTime OBJECT-TYPE
            SYNTAX  DateAndTime
            MAX-ACCESS  read-only
            STATUS  current
            DESCRIPTION
                "This object indicates the register time.
                 -1 is the invalid value."
            ::= { hwEponDeviceOntRegInfoEntry 4 }

        hwEponDeviceRegConflictedIfindex OBJECT-TYPE
            SYNTAX  Integer32
            MAX-ACCESS   read-only
            STATUS  current
            DESCRIPTION
                "This object indicates the ifIndex of the conflicted ONT.
                 -1 is the invalid value."
            ::= { hwEponDeviceOntRegInfoEntry 5 }

        hwEponDeviceRegConflictedOntIndex OBJECT-TYPE
            SYNTAX  Integer32
            MAX-ACCESS   read-only
            STATUS  current
            DESCRIPTION
                "This object indicates the index of the conflicted ONT.
                 -1 is the invalid value."
            ::= { hwEponDeviceOntRegInfoEntry 6 }

        hwEponDeviceRegOntPasswordValue    OBJECT-TYPE
            SYNTAX     OCTET STRING (SIZE (0..32))
            MAX-ACCESS  read-only
            STATUS     current
            DESCRIPTION
                "This object indicates the ONT password.
                 A valid value is reported only when hwEponDeviceRegOntResult is unconfirmed.
                 A null is reported in other scenarios.
                "
            ::= { hwEponDeviceOntRegInfoEntry 7 }

        hwEponDeviceRegOntVendorId        OBJECT-TYPE
            SYNTAX     Integer32
            MAX-ACCESS  read-only
            STATUS     current
            DESCRIPTION
                "This object indicates the ONT vendor ID.
                 A valid value is reported only when hwEponDeviceRegOntResult is unconfirmed.
                "
            ::= { hwEponDeviceOntRegInfoEntry 8 }

        hwEponDeviceRegOntSoftwareVersion  OBJECT-TYPE
            SYNTAX     OCTET STRING  (SIZE (16))
            MAX-ACCESS  read-only
            STATUS     current
            DESCRIPTION
                "This object indicates the Software version of ONT.
                 A valid value is reported only when hwEponDeviceRegOntResult is unconfirmed.
                 A null is reported in other scenarios.
                "
            ::= { hwEponDeviceOntRegInfoEntry 9 }

        hwEponDeviceRegOntHardwareVersion    OBJECT-TYPE
            SYNTAX     OCTET STRING  (SIZE (8))
            MAX-ACCESS  read-only
            STATUS     current
            DESCRIPTION
                "This object indicates the hardware version of ONT.
                 A valid value is reported only when hwEponDeviceRegOntResult is unconfirmed.
                 A null is reported in other scenarios.
                "
            ::= { hwEponDeviceOntRegInfoEntry 10 }

        hwEponDeviceRegOntModel         OBJECT-TYPE
            SYNTAX     Integer32
            MAX-ACCESS   read-only
            STATUS      current
            DESCRIPTION
                "This object indicates the Mode of ONT.
                 A valid value is reported only when hwEponDeviceRegOntResult is unconfirmed.
                "
            ::= { hwEponDeviceOntRegInfoEntry 11 }

        hwEponDeviceRegOntLoid             OBJECT-TYPE
            SYNTAX   OCTET STRING (SIZE (0..24))
            MAX-ACCESS  read-only
            STATUS   current
            DESCRIPTION
                "This object indicates the ONT LOID.
                 A valid value is reported only when hwEponDeviceRegOntResult is unconfirmed.
                 A null is reported in other scenarios.
                "
            ::= { hwEponDeviceOntRegInfoEntry 12 }

        hwEponDeviceRegOntCheckcode       OBJECT-TYPE
            SYNTAX   OCTET STRING (SIZE (0..12))
            MAX-ACCESS  read-only
            STATUS   current
            DESCRIPTION
                "This object indicates the ONT CHECKCODE.
                 A valid value is reported only when hwEponDeviceRegOntResult is unconfirmed.
                 A null is reported in other scenarios.
                "
            ::= { hwEponDeviceOntRegInfoEntry 13 }

        hwEponDeviceRegOntRateType         OBJECT-TYPE
            SYNTAX INTEGER {
                rate1G1G(1),
                rate10G1G(2),
                rate10G10G(3),
                rate10G2G(5),
                invalid(-1)
            }
            MAX-ACCESS read-only
            STATUS current
            DESCRIPTION
                "This object indicates the ONT actual rate type.
                 A valid value is reported only when hwEponDeviceRegOntResult is unconfirmed.
                 Options:
                 1. rate1G1G(1)               - Downstream rate 1Gbps, upstream rate 1Gbps
                 2. rate10G1G(2)              - Downstream rate 10Gbps, upstream rate 1Gbps
                 3. rate10G10G(3)             - Downstream rate 10Gbps, upstream rate 10Gbps
                 4. rate10G2G(5)              - Downstream rate 10Gbps, upstream rate 2Gbps
                 5. invalid(-1)               - Indicates that the query fails or no information is detected
                "
            ::= { hwEponDeviceOntRegInfoEntry 14 }

        hwEponDeviceRegOntExtendedModel   OBJECT-TYPE
            SYNTAX     OCTET STRING    (SIZE (0..32))
            MAX-ACCESS   read-only
            STATUS      current
            DESCRIPTION
                "This object indicates the ONT extended model.
                 A valid value is reported only when hwEponDeviceRegOntResult is unconfirmed.
                 A null is reported in other scenarios.
                "
            ::= { hwEponDeviceOntRegInfoEntry 15 }

        hwEponDeviceRegOntOuiVersion OBJECT-TYPE
            SYNTAX     OCTET STRING    (SIZE (0..32))
            MAX-ACCESS   read-only
            STATUS      current
            DESCRIPTION
                "This object indicates the highest ONT OUI version.
                 A valid value is reported only when hwEponDeviceRegOntResult is unconfirmed.
                 A null is reported in other scenarios.
                "
            ::= { hwEponDeviceOntRegInfoEntry 16 }

-- hwGponDeviceOntEthernetPortCfgTable
        hwGponDeviceOntEthernetPortCfgTable OBJECT-TYPE
            SYNTAX     SEQUENCE OF HwGponDeviceOntEthernetPortCfgEntry
            MAX-ACCESS not-accessible
            STATUS     current
            DESCRIPTION
                "This is the ONT ETH port table, This table is used to set or query the attribute
                 of the ONT ETH port, including duplex, transmission rate and native VLAN and others.
                 The index of this table is a combination of ifIndex, hwGponDeviceOntIndex
                 and hwGponDeviceOntEthernetPortId.
                 When the attribute of an ONT ETH port is queried on the NMS,
                 if the port is bound with hwGponDeviceOntEthernetOnlineState,
                 the running states of the port is queried.
                 If the port is not bound with hwGponDeviceOntEthernetOnlineState,
                 the configuration of the port is queried.
                 "
            ::= { hwXponDeviceControlObjects 62 }

        hwGponDeviceOntEthernetPortCfgEntry OBJECT-TYPE
            SYNTAX     HwGponDeviceOntEthernetPortCfgEntry
            MAX-ACCESS not-accessible
            STATUS     current
            DESCRIPTION
                "This is the ONT ETH port table, This table is used to set or query the attribute
                 of the ONT ETH port, including duplex, transmission rate and native VLAN and others.
                 The index of this entry is a combination of ifIndex, hwGponDeviceOntIndex
                 and hwGponDeviceOntEthernetPortId.
                 When the attribute of an ONT ETH port is queried on the NMS,
                 if the port is bound with hwGponDeviceOntEthernetOnlineState,
                 the running states of the port is queried.
                 If the port is not bound with hwGponDeviceOntEthernetOnlineState,
                 the configuration of the port is queried.

                 "
            INDEX       { ifIndex, hwGponDeviceOntIndex, hwGponDeviceOntEthernetPortId }
            ::= { hwGponDeviceOntEthernetPortCfgTable 1 }

        HwGponDeviceOntEthernetPortCfgEntry ::=
            SEQUENCE {
                hwGponDeviceOntEthernetPortId                          Integer32,
                hwGponDeviceOntEthernetNegotiate                       Integer32,
                hwGponDeviceOntEthernetDuplexMode                      INTEGER,
                hwGponDeviceOntEthernetSpeed                           INTEGER,
                hwGponDeviceOntEthernetOperateStatus                   INTEGER,
                hwGponDeviceOntEthernetFlowCtrlSwitch                  INTEGER,
                hwGponDeviceOntEthernetVlanDefault                     Integer32,
                hwGponDeviceOntEthernetVlanDefaultPriority             Integer32,
                hwGponDeviceOntEthernetActualPortType                  Integer32,
                hwGponDeviceOntEthernetOnlineState                     INTEGER,
                hwGponDeviceOntEthernetUpStreamCarTrafficTableId       Integer32,
                hwGponDeviceOntEthernetDownStreamCarTrafficTableId     Integer32,
                hwGponDeviceOntEthernetPortIgmpForwardMode             INTEGER,
                hwGponDeviceOntEthernetPortRingStatus                  INTEGER,
                hwGponDeviceOntEthernetUpStreamCarTrafficTableName     OCTET STRING,
                hwGponDeviceOntEthernetDownStreamCarTrafficTableName   OCTET STRING,
                hwGponDeviceOntEthernetRouteSwitch                     INTEGER,
                hwGponDeviceOntEthernetMode                            INTEGER,
                hwGponDeviceOntEthernetOpticalModuleStatus             INTEGER,
                hwGponDeviceOntEthernetOnlineDuration                  Gauge32
            }

        hwGponDeviceOntEthernetPortId OBJECT-TYPE
            SYNTAX     Integer32
            MAX-ACCESS    not-accessible
            STATUS      current
            DESCRIPTION
                "This object indicates the ONT ETH port ID."
            ::= { hwGponDeviceOntEthernetPortCfgEntry 1 }

        hwGponDeviceOntEthernetNegotiate OBJECT-TYPE
            SYNTAX     Integer32
            MAX-ACCESS    read-write
            STATUS      current
            DESCRIPTION
                "This object indicates the negotiation switch.
                 The value (1) indicates that the negotiation switch is on.
                 The value (2) indicates that the negotiation switch is off.
                 The value (-1) indicates that the query fails or no information is detected.
                 "
            ::= { hwGponDeviceOntEthernetPortCfgEntry 2 }

        hwGponDeviceOntEthernetDuplexMode OBJECT-TYPE
            SYNTAX     INTEGER {
                half (1),
                full (2),
                autoneg (3),
                autohalf(4),
                autofull(5),
                invalid (-1)
            }
            MAX-ACCESS    read-write
            STATUS      current
            DESCRIPTION
                "This object indicates the duplex type of the port.
                 Options:
                 1. half(1)                    - Forced half duplex
                 2. full(2)                    - Forced full duplex
                 3. autoneg(3)                 - Auto negotiation
                 4. autohalf(4)                - Auto half duplex
                 5. autofull(5)                - Auto full duplex
                 6. invalid(-1)                - Indicates that the query fails or no information is detected
                "
            ::= { hwGponDeviceOntEthernetPortCfgEntry 3 }

        hwGponDeviceOntEthernetSpeed OBJECT-TYPE
            SYNTAX     INTEGER {
                speed10M (1),
                speed100M (2),
                speed1000M (3),
                autoneg (4),
                autospeed10M(5),
                autospeed100M(6),
                autospeed1000M(7),
                speed10G(8),
                autospeed10G(9),
                speed2500M(10),
                autospeed2500M(11),
                invalid (-1)
            }
            MAX-ACCESS    read-write
            STATUS      current
            DESCRIPTION
                "This object indicates the transmission rate of the port.
                 Options:
                 1. speed10M(1)         - The forced transmission rate of the port is 10M
                 2. speed100M(2)        - The forced transmission rate of the port is 100M
                 3. speed1000M(3)       - The forced transmission rate of the port is 1000M
                 4. autoneg(4)          - The transmission rate of the port is auto negotiation
                 5. autospeed10M(5)     - The auto transmission rate of the port is 10M
                 6. autospeed100M(6)    - The auto transmission rate of the port is 100M
                 7. autospeed1000M(7)   - The auto transmission rate of the port is 1000M
                 8. speed10G(8)         - The forced transmission rate of the port is 10G
                 9. autospeed10G(9)     - The auto transmission rate of the port is 10G
                 10. speed2500M(10)     - The forced transmission rate of the port is 2500M
                 11. autospeed2500M(11) - The auto transmission rate of the port is 2500M
                 12. invalid(-1)        - Indicates that the query fails or no information is detected
               "
            ::= { hwGponDeviceOntEthernetPortCfgEntry 4 }

        hwGponDeviceOntEthernetOperateStatus OBJECT-TYPE
            SYNTAX     INTEGER {
                on(1),
                off(2),
                invalid(-1)
            }
            MAX-ACCESS    read-write
            STATUS      current
            DESCRIPTION
                "This object indicates the switch of the port.
                 Options:
                 1. on(1)               - Indicates that the switch of the port is on
                 2. off(2)              - Indicates that the switch of the port is off
                 3. invalid(-1)         - Indicates that the query fails or no information is detected
                "
            ::= { hwGponDeviceOntEthernetPortCfgEntry 5 }

        hwGponDeviceOntEthernetFlowCtrlSwitch OBJECT-TYPE
            SYNTAX     INTEGER {
                on(1),
                off(2),
                invalid(-1)
            }
            MAX-ACCESS    read-write
            STATUS      current
            DESCRIPTION
                "This object is used to set the flow control switch of ONT port.
                 Options:
                 1. on(1)               - Indicates that the flow control switch of ONT port is on
                 2. off(2)              - Indicates that the flow control switch of ONT port is off
                 3. invalid(-1)         - Indicates that the query fails or no information is detected
                "
            ::= { hwGponDeviceOntEthernetPortCfgEntry 6 }

        hwGponDeviceOntEthernetVlanDefault  OBJECT-TYPE
            SYNTAX     Integer32
            MAX-ACCESS    read-write
            STATUS      current
            DESCRIPTION
                "This object indicates the native VLAN of the port."
            ::= { hwGponDeviceOntEthernetPortCfgEntry 7 }

        hwGponDeviceOntEthernetVlanDefaultPriority OBJECT-TYPE
            SYNTAX     Integer32
            MAX-ACCESS    read-write
            STATUS      current
            DESCRIPTION
                "This object indicates the native VLAN priority of the port."
            ::= { hwGponDeviceOntEthernetPortCfgEntry 8 }

        hwGponDeviceOntEthernetActualPortType  OBJECT-TYPE
            SYNTAX     Integer32
            MAX-ACCESS    read-only
            STATUS      current
            DESCRIPTION
                "This object indicates the actual ETH port type of the ONT.
                 The value (13) indicates that the port type is t1,
                 The value (14) indicates that the port type is e1,
                 The value (24) indicates that the port type is fe,
                 The value (34) indicates that the port type is ge,
                 The value (46) indicates that the port type is moca,
                 The value (47) indicates that the port type is eth,
                 The value (50) indicates that the port type is iphost,
                 The value (-1) indicates that the query fails.
                "
            ::= { hwGponDeviceOntEthernetPortCfgEntry 21 }

        hwGponDeviceOntEthernetOnlineState OBJECT-TYPE
            SYNTAX     INTEGER {
                linkup(1),
                linkdown(2),
                invalid(-1)
            }
            MAX-ACCESS    read-only
            STATUS      current
            DESCRIPTION
                "This object indicates the status of ONT ETH port.
                 Options:
                 1. linkup(1)            - Indicates that the status of ONT ETH port is link up
                 2. linkdown(2)          - Indicates that the status of ONT ETH port is link down
                 3. invalid(-1)          - Indicates that the query fails or no information is detected
                "
            ::= { hwGponDeviceOntEthernetPortCfgEntry 22 }

        hwGponDeviceOntEthernetUpStreamCarTrafficTableId OBJECT-TYPE
            SYNTAX     Integer32
            MAX-ACCESS    read-write
            STATUS      current
            DESCRIPTION
                "This object indicates the ONT ethernet port upstream car profile id (1~1024, 0xfffe-unconcern)."
            ::= { hwGponDeviceOntEthernetPortCfgEntry 23 }

        hwGponDeviceOntEthernetDownStreamCarTrafficTableId OBJECT-TYPE
            SYNTAX     Integer32
            MAX-ACCESS    read-write
            STATUS      current
            DESCRIPTION
                "This object indicates the ONT ethernet port downstream car profile id (1~1024, 0xfffe-unconcern)."
            ::= { hwGponDeviceOntEthernetPortCfgEntry 24 }

        hwGponDeviceOntEthernetPortIgmpForwardMode OBJECT-TYPE
            SYNTAX    INTEGER{
                disable(1),
                enable(2),
                invalid (-1)
                }
            MAX-ACCESS  read-write
            STATUS      current
            DESCRIPTION
                "The object is used to enable or disable the switch of ONT port IGMP forward mode.
                Options:
                1. disable(1)     - Disable the switch of ONT port IGMP forward mode
                2. enable(2)      - Enable the switch of ONT port IGMP forward mode
                3. invalid(-1)    - Indicates that the query fails or no information is detected
                "
            ::= { hwGponDeviceOntEthernetPortCfgEntry 25 }

        hwGponDeviceOntEthernetPortRingStatus OBJECT-TYPE
            SYNTAX    INTEGER{
                loop(1),
                noloop(2),
                invalid (-1)
                }
            MAX-ACCESS  read-only
            STATUS      current
            DESCRIPTION
                "The object is used to enable or disable the switch of ONT port IGMP forward mode.
                Options:
                1. loop(1)        - Indicates that the ring status of ONT ETH port is loop
                2. noloop(2)      - Indicates that the ring status of ONT ETH port is no loop
                3. invalid(-1)    - Indicates that the query fails or no information is detected
                "
            ::= { hwGponDeviceOntEthernetPortCfgEntry 26 }

        hwGponDeviceOntEthernetUpStreamCarTrafficTableName OBJECT-TYPE
            SYNTAX     OCTET STRING  (SIZE (0..32))
            MAX-ACCESS    read-write
            STATUS      current
            DESCRIPTION
                "This object indicates the ONT ethernet port upstream car profile name."
            ::= { hwGponDeviceOntEthernetPortCfgEntry 27 }

        hwGponDeviceOntEthernetDownStreamCarTrafficTableName OBJECT-TYPE
            SYNTAX     OCTET STRING  (SIZE (0..32))
            MAX-ACCESS    read-write
            STATUS      current
            DESCRIPTION
                "This object indicates the ONT ethernet port downstream car profile name."
            ::= { hwGponDeviceOntEthernetPortCfgEntry 28 }

        hwGponDeviceOntEthernetRouteSwitch OBJECT-TYPE
            SYNTAX     INTEGER {
                enable(1),
                disable(2),
                invalid(-1)
            }
            MAX-ACCESS    read-only
            STATUS      current
            DESCRIPTION
                "This object indicates the actual route switch status of ONT ETH port.
                 Options:
                 1. enable(1)           - Indicates that the route switch status of ONT ETH port is enable
                 2. disable(2)          - Indicates that the route switch status of ONT ETH port is disable
                 3. invalid(-1)         - Indicates that the query fails or no information is detected
                "
            ::= { hwGponDeviceOntEthernetPortCfgEntry 29 }

        hwGponDeviceOntEthernetMode OBJECT-TYPE
	    SYNTAX     INTEGER {
	                  electric (1),
	                  optic (2),
	                  invalid (-1)
	                  }
	     MAX-ACCESS    read-only
	     STATUS      current
	     DESCRIPTION
	           "Indicates the optical module status of the ONT ethernet port.
	            Options:
	            1. electric(1)     - Indicates that the mode status of ONT ETH port is electric
	            2. optic(2)        - Indicates that the mode status of ONT ETH port is optic
	            3. invalid(-1)     - Indicates that the query fails or no information is detected
	           "
	  ::= { hwGponDeviceOntEthernetPortCfgEntry 30 }

       hwGponDeviceOntEthernetOpticalModuleStatus OBJECT-TYPE
           SYNTAX    INTEGER {
                  normal (1),
                  absence (2),
                  mismatch (3),
                  invalid (-1)
                  }
          MAX-ACCESS    read-only
          STATUS      current
          DESCRIPTION
           "The status of the ONT ethernet port.
            Options:
            1. normal(1)       - Indicates that the optical module status  of ONT ETH port is normal
            2. absence(2)      - Indicates that the optical module status  of ONT ETH port is absence
            3. mismatch(3)     - Indicates that the optical module status  of ONT ETH port is mismatch
            4. invalid(-1)     - Indicates that the query fails or no information is detected
           "
       ::= { hwGponDeviceOntEthernetPortCfgEntry 31 }

       hwGponDeviceOntEthernetOnlineDuration OBJECT-TYPE
            SYNTAX      Gauge32
            UNITS       "second"
            MAX-ACCESS  read-only
            STATUS      current
            DESCRIPTION
                "Indicates the online duration of the ONT ethernet port.
                 Unit: second
                "
            ::= { hwGponDeviceOntEthernetPortCfgEntry 32 }

-- Table hwGponDeviceOntCatvPortCfgTable
        hwGponDeviceOntCatvPortCfgTable OBJECT-TYPE
            SYNTAX     SEQUENCE OF HwGponDeviceOntCatvPortCfgEntry
            MAX-ACCESS not-accessible
            STATUS     current
            DESCRIPTION
                "This is the ONT CATV port table.
                 The index of this table is a combination of ifIndex, hwGponDeviceOntIndex
                 and hwGponDeviceOntCatvPortId.
                "
            ::= { hwXponDeviceControlObjects 63 }

        hwGponDeviceOntCatvPortCfgEntry OBJECT-TYPE
            SYNTAX     HwGponDeviceOntCatvPortCfgEntry
            MAX-ACCESS not-accessible
            STATUS     current
            DESCRIPTION
                "This is the ONT CATV port table.
                 The index of this entry is a combination of ifIndex, hwGponDeviceOntIndex
                 and hwGponDeviceOntCatvPortId.
                "
            INDEX       { ifIndex, hwGponDeviceOntIndex, hwGponDeviceOntCatvPortId }
            ::= { hwGponDeviceOntCatvPortCfgTable 1 }

        HwGponDeviceOntCatvPortCfgEntry ::=
            SEQUENCE {
                hwGponDeviceOntCatvPortId              Integer32,
                hwGponDeviceOntCatvOperateStatus       INTEGER,
                hwGponDeviceOntCatvOnlineStatus        Integer32,
                hwGponDeviceOntCatvFrequency           INTEGER,
                hwGponDeviceOntCatvTxPower             Integer32
            }

        hwGponDeviceOntCatvPortId OBJECT-TYPE
            SYNTAX     Integer32
            MAX-ACCESS    not-accessible
            STATUS      current
            DESCRIPTION
                "This object indicates the ONT CATV port ID."
            ::= { hwGponDeviceOntCatvPortCfgEntry 1 }

        hwGponDeviceOntCatvOperateStatus OBJECT-TYPE
            SYNTAX     INTEGER {
                on(1),
                off(2),
                invalid(-1)
            }
            MAX-ACCESS    read-write
            STATUS      current
            DESCRIPTION
                "This object indicates the laser switch of ONT CATV port.
                 Options:
                 1. on(1)               - Indicates that the laser switch of ONT CATV port is on
                 2. off(2)              - Indicates that the laser switch of ONT CATV port is off
                 3. invalid(-1)         - Indicates that the query fails or no information is detected
                "
            ::= { hwGponDeviceOntCatvPortCfgEntry 2 }

        hwGponDeviceOntCatvOnlineStatus OBJECT-TYPE
            SYNTAX     Integer32
            MAX-ACCESS    read-only
            STATUS      current
            DESCRIPTION
                "This object indicates the link status of ONT CATV port.
                 The value (1) indicates that the CATV port is online.
                 The value (2) indicates that the CATV port is offline.
                 The value (-1) indicates that the query fails or no information is detected."
            ::= { hwGponDeviceOntCatvPortCfgEntry 3 }

        hwGponDeviceOntCatvFrequency OBJECT-TYPE
            SYNTAX     INTEGER {
                allPass(1),
                highPass(2),
                lowPass(3),
                invalid(-1)
            }
            MAX-ACCESS    read-write
            STATUS      current
            DESCRIPTION
                "This object indicates the frequency of ONT CATV port.
                 Options:
                 1. allPass(1)         - Indicates that the frequency of ONT CATV port is all-pass
                 2. highPass(2)        - Indicates that the frequency of ONT CATV port is high-pass
                 3. lowPass(3)         - Indicates that the frequency of ONT CATV port is low-pass
                 4. invalid(-1)         - Indicates that the query fails or no information is detected
                "
            ::= { hwGponDeviceOntCatvPortCfgEntry 4 }

        hwGponDeviceOntCatvTxPower OBJECT-TYPE
            SYNTAX     Integer32
            UNITS      "0.001dBmV"
            MAX-ACCESS    read-only
            STATUS      current
            DESCRIPTION
                "This object indicates the Tx power of ONT CATV port.
                 Unit: 0.001dBmV
                 Options:
                 1. invalid(0x7FFFFFFF)      - Indicates that the query fails or no information is detected
                "
            ::= { hwGponDeviceOntCatvPortCfgEntry 5 }

-- Table hwGponDeviceOntMocaPortCfgTable
        hwGponDeviceOntMocaPortCfgTable OBJECT-TYPE
            SYNTAX     SEQUENCE OF HwGponDeviceOntMocaPortCfgEntry
            MAX-ACCESS not-accessible
            STATUS     current
            DESCRIPTION
                "This is the ONT MOCA port config table.
                 The index of this table is a combination of ifIndex, hwGponDeviceOntIndex
                 and hwGponDeviceOntMocaPortId.
                "
            ::= { hwXponDeviceControlObjects 64 }

        hwGponDeviceOntMocaPortCfgEntry OBJECT-TYPE
            SYNTAX     HwGponDeviceOntMocaPortCfgEntry
            MAX-ACCESS not-accessible
            STATUS     current
            DESCRIPTION
                "This is the ONT MOCA port config table.
                 The index of this entry is a combination of ifIndex, hwGponDeviceOntIndex
                 and hwGponDeviceOntMocaPortId.
                "
            INDEX       { ifIndex, hwGponDeviceOntIndex, hwGponDeviceOntMocaPortId }
            ::= { hwGponDeviceOntMocaPortCfgTable 1 }

        HwGponDeviceOntMocaPortCfgEntry ::=
            SEQUENCE {
                hwGponDeviceOntMocaPortId                 Integer32,
                hwGponDeviceOntMocaPortVlanDefault        Integer32,
                hwGponDeviceOntMocaPortVlanDefaultPri     Integer32
            }

        hwGponDeviceOntMocaPortId OBJECT-TYPE
            SYNTAX    Integer32
            MAX-ACCESS  not-accessible
            STATUS      current
            DESCRIPTION
                "This object indicates the ONT MOCA port ID."
            ::= { hwGponDeviceOntMocaPortCfgEntry 1 }

        hwGponDeviceOntMocaPortVlanDefault OBJECT-TYPE
            SYNTAX    Integer32
            MAX-ACCESS  read-write
            STATUS      current
            DESCRIPTION
                "This object indicates the native VLAN of the Moca port."
            ::= { hwGponDeviceOntMocaPortCfgEntry 2 }

        hwGponDeviceOntMocaPortVlanDefaultPri OBJECT-TYPE
            SYNTAX    Integer32
            MAX-ACCESS  read-write
            STATUS      current
            DESCRIPTION
                "This object indicates the native VLAN priority of the MOCA port.
                 The range is from 0 to 7, and the value (-1) is invalid."
            ::= { hwGponDeviceOntMocaPortCfgEntry 3 }

-- Table hwGponDeviceOntIpHostPortCfgTable
        hwGponDeviceOntIpHostPortCfgTable OBJECT-TYPE
            SYNTAX     SEQUENCE OF HwGponDeviceOntIpHostPortCfgEntry
            MAX-ACCESS not-accessible
            STATUS     current
            DESCRIPTION
                "This is the ONT IPHOST port config table.
                 The index of this table is a combination of ifIndex, hwGponDeviceOntIndex
                 and hwGponDeviceOntIpHostPortId.
                "
            ::= { hwXponDeviceControlObjects 65 }

        hwGponDeviceOntIpHostPortCfgEntry OBJECT-TYPE
            SYNTAX     HwGponDeviceOntIpHostPortCfgEntry
            MAX-ACCESS not-accessible
            STATUS     current
            DESCRIPTION
                "This is the ONT IPHOST port config table.
                 The index of this entry is a combination of ifIndex, hwGponDeviceOntIndex
                 and hwGponDeviceOntIpHostPortId.
                "
            INDEX       { ifIndex, hwGponDeviceOntIndex, hwGponDeviceOntIpHostPortId }
            ::= { hwGponDeviceOntIpHostPortCfgTable 1 }

        HwGponDeviceOntIpHostPortCfgEntry ::=
            SEQUENCE {
                hwGponDeviceOntIpHostPortId               Integer32,
                hwGponDeviceOntIpHostPortVlanDefault      Integer32,
                hwGponDeviceOntIpHostPortVlanDefaultPri   Integer32
            }

        hwGponDeviceOntIpHostPortId OBJECT-TYPE
            SYNTAX    Integer32
            MAX-ACCESS  not-accessible
            STATUS      current
            DESCRIPTION
                "This object indicates the ONT IPHOST port ID."
            ::= { hwGponDeviceOntIpHostPortCfgEntry 1 }

        hwGponDeviceOntIpHostPortVlanDefault OBJECT-TYPE
            SYNTAX    Integer32
            MAX-ACCESS  read-write
            STATUS      current
            DESCRIPTION
                "This object indicates the native VLAN of the IPHOST port."
            ::= { hwGponDeviceOntIpHostPortCfgEntry 2 }

        hwGponDeviceOntIpHostPortVlanDefaultPri OBJECT-TYPE
            SYNTAX    Integer32
            MAX-ACCESS  read-write
            STATUS      current
            DESCRIPTION
                "This object indicates the native VLAN priority of the IPHOST port.
                 The range is from 0 to 7, and the value (-1) is invalid."
            ::= { hwGponDeviceOntIpHostPortCfgEntry 3 }

-- Table hwEponDeviceOntEthernetPortCfgTable
        hwEponDeviceOntEthernetPortCfgTable OBJECT-TYPE
            SYNTAX     SEQUENCE OF HwEponDeviceOntEthernetPortCfgEntry
            MAX-ACCESS not-accessible
            STATUS     current
            DESCRIPTION
                "This is the ONT ETH port config table.
                 The index of this table is a combination of ifIndex, hwEponDeviceOntIndex
                 and hwEponDeviceOntEthernetPortId.
                "
            ::= { hwXponDeviceControlObjects 81 }

        hwEponDeviceOntEthernetPortCfgEntry OBJECT-TYPE
            SYNTAX     HwEponDeviceOntEthernetPortCfgEntry
            MAX-ACCESS not-accessible
            STATUS     current
            DESCRIPTION
                "This is the ONT ETH port config table.
                 The index of this entry is a combination of ifIndex, hwEponDeviceOntIndex
                 and hwEponDeviceOntEthernetPortId.
                "
            INDEX       { ifIndex, hwEponDeviceOntIndex, hwEponDeviceOntEthernetPortId }
            ::= { hwEponDeviceOntEthernetPortCfgTable 1 }

        HwEponDeviceOntEthernetPortCfgEntry ::=
            SEQUENCE {
                hwEponDeviceOntEthernetPortId                                Integer32,
                hwEponDeviceOntEthernetNegotiate                             INTEGER,
                hwEponDeviceOntEthernetDuplexMode                            INTEGER,
                hwEponDeviceOntEthernetSpeed                                 INTEGER,
                hwEponDeviceOntEthernetVlanDefault                           Integer32,
                hwEponDeviceOntEthernetOperateStatus                         INTEGER,
                hwEponDeviceOntEthernetFlowcontrolSwitch                     INTEGER,
                hwEponDeviceOntEthernetRingStatus                            INTEGER,
                hwEponDeviceOntEthernetOnlineState                           INTEGER,
                hwEponDeviceOntEthernetPortCfgUpStreamCarTrafficTableId      Integer32,
                hwEponDeviceOntEthernetPortCfgDownStreamCarTrafficTableId    Integer32,
                hwEponDeviceOntEthernetPortCfgUpStreamCarTrafficTableName    OCTET STRING,
                hwEponDeviceOntEthernetPortCfgDownStreamCarTrafficTableName  OCTET STRING
            }

        hwEponDeviceOntEthernetPortId  OBJECT-TYPE
            SYNTAX     Integer32
            MAX-ACCESS   not-accessible
            STATUS      current
            DESCRIPTION
                "This object indicates the ONT ETH port ID."
            ::= { hwEponDeviceOntEthernetPortCfgEntry 1 }

        hwEponDeviceOntEthernetNegotiate  OBJECT-TYPE
            SYNTAX     INTEGER {
                auto(1),
                neg(2),
                invalid(-1)
            }
            MAX-ACCESS   read-write
            STATUS      current
            DESCRIPTION
                "This object indicates the negotiation switch.
                 Options:
                 1. auto(1)             - Indicates that the negotiation switch is auto negotiation
                 2. neg(2)              - Indicates that the negotiation switch is negotiation
                 3. invalid(-1)         - Indicates that the query fails or no information is detected
                "
            ::= { hwEponDeviceOntEthernetPortCfgEntry 2 }

        hwEponDeviceOntEthernetDuplexMode  OBJECT-TYPE
            SYNTAX     INTEGER {
                half (1),
                full (2),
                autoneg (3),
                autohalf(4),
                autofull(5),
                invalid (-1)
            }
            MAX-ACCESS   read-write
            STATUS      current
            DESCRIPTION
                "This object indicates the duplex type of the port.
                 Options:
                 1. half(1)                    - Forced half duplex
                 2. full(2)                    - Forced full duplex
                 3. autoneg(3)                 - Auto negotiation
                 4. autohalf(4)                - Auto half duplex
                 5. autofull(5)                - Auto full duplex
                 6. invalid(-1)                - Indicates that the query fails or no information is detected
                "
            ::= { hwEponDeviceOntEthernetPortCfgEntry 3 }

        hwEponDeviceOntEthernetSpeed  OBJECT-TYPE
            SYNTAX     INTEGER {
                speed10M (10),
                speed100M (100),
                speed1000M (1000),
                autoneg (4),
                autospeed10M(5),
                autospeed100M(6),
                autospeed1000M(7),
                speed10G(8),
                autospeed10G(9),
                invalid (-1)
            }
            MAX-ACCESS   read-write
            STATUS      current
            DESCRIPTION
                "This object indicates the transmission rate of the port.
                 Options:
                 1. speed10M(10)        - The forced transmission rate of the port is 10M
                 2. speed100M(100)      - The forced transmission rate of the port is 100M
                 3. speed1000M(1000)    - The forced transmission rate of the port is 1000M
                 4. autoneg(4)          - The transmission rate of the port is auto negotiation
                 5. autospeed10M(5)     - The auto transmission rate of the port is 10M
                 6. autospeed100M(6)    - The auto transmission rate of the port is 100M
                 7. autospeed1000M(7)   - The auto transmission rate of the port is 1000M
                 8. speed10G(8)  - The forced transmission rate of the port is 10G
                 9. autospeed10G(9)     - The auto transmission rate of the port is 10G
                 10. invalid(-1)         - Indicates that the query fails or no information is detected
               "
            ::= { hwEponDeviceOntEthernetPortCfgEntry 4 }

        hwEponDeviceOntEthernetVlanDefault  OBJECT-TYPE
            SYNTAX     Integer32
            MAX-ACCESS   read-write
            STATUS      current
            DESCRIPTION
                "This object indicates the native VLAN of the port."
            ::= { hwEponDeviceOntEthernetPortCfgEntry 5 }

        hwEponDeviceOntEthernetOperateStatus  OBJECT-TYPE
            SYNTAX     INTEGER {
                on(1),
                off(2),
                invalid(-1)
            }
            MAX-ACCESS   read-write
            STATUS      current
            DESCRIPTION
                "This object indicates the switch of the port.
                 Options:
                 1. on(1)               - Indicates that the switch of the port is on
                 2. off(2)              - Indicates that the switch of the port is off
                 3. invalid(-1)         - Indicates that the query fails or no information is detected
                "
            ::= { hwEponDeviceOntEthernetPortCfgEntry 7 }

        hwEponDeviceOntEthernetFlowcontrolSwitch  OBJECT-TYPE
            SYNTAX     INTEGER {
                on(1),
                off(2),
                invalid(-1)
            }
            MAX-ACCESS   read-write
            STATUS      current
            DESCRIPTION
                "This object is used to set ONT port flow control switch.
                 Options:
                 1. on(1)               - Indicates that the switch of ONT port flow control is on
                 2. off(2)              - Indicates that the switch of ONT port flow control is off
                 3. invalid(-1)         - Indicates that the query fails or no information is detected
                "
            ::= { hwEponDeviceOntEthernetPortCfgEntry 8 }

        hwEponDeviceOntEthernetRingStatus  OBJECT-TYPE
            SYNTAX     INTEGER {
                forward(1),
                block(2),
                invalid(-1)
            }
            MAX-ACCESS   read-only
            STATUS      current
            DESCRIPTION
                "This object indicates the ring status of ONT ETH port.
                 Options:
                 1. forward(1)            - Indicates that the ring status of ONT ETH port is forward
                 2. block(2)              - Indicates that the ring status of ONT ETH port is block
                 3. invalid(-1)           - Indicates that the query fails or no information is detected
                "
            ::= { hwEponDeviceOntEthernetPortCfgEntry 10 }

        hwEponDeviceOntEthernetOnlineState  OBJECT-TYPE
            SYNTAX     INTEGER {
                linkup(1),
                linkdown(2),
                invalid(-1)
            }
            MAX-ACCESS   read-only
            STATUS      current
            DESCRIPTION
                "This object indicates the status of ONT ETH port.
                 Options:
                 1. linkup(1)            - Indicates that the status of ONT ETH port is link up
                 2. linkdown(2)          - Indicates that the status of ONT ETH port is link down
                 3. invalid(-1)          - Indicates that the query fails or no information is detected
                "
            ::= { hwEponDeviceOntEthernetPortCfgEntry 31 }

        hwEponDeviceOntEthernetPortCfgUpStreamCarTrafficTableId  OBJECT-TYPE
            SYNTAX     Integer32
            MAX-ACCESS   read-write
            STATUS      current
            DESCRIPTION
                "This object indicates the ONT port upstream car profile id (1~1024, 0xfffe-unconcern)."
            ::= { hwEponDeviceOntEthernetPortCfgEntry 32 }

        hwEponDeviceOntEthernetPortCfgDownStreamCarTrafficTableId  OBJECT-TYPE
            SYNTAX     Integer32
            MAX-ACCESS   read-write
            STATUS      current
            DESCRIPTION
                "This object indicates the ONT port downstream car profile id (1~1024, 0xfffe-unconcern)."
            ::= { hwEponDeviceOntEthernetPortCfgEntry 33 }

        hwEponDeviceOntEthernetPortCfgUpStreamCarTrafficTableName  OBJECT-TYPE
            SYNTAX     OCTET STRING  (SIZE (0..32))
            MAX-ACCESS   read-write
            STATUS      current
            DESCRIPTION
                "This object indicates the ONT port upstream car profile name."
            ::= { hwEponDeviceOntEthernetPortCfgEntry 34 }

        hwEponDeviceOntEthernetPortCfgDownStreamCarTrafficTableName  OBJECT-TYPE
            SYNTAX     OCTET STRING  (SIZE (0..32))
            MAX-ACCESS   read-write
            STATUS      current
            DESCRIPTION
                "This object indicates the ONT port downstream car profile name."
            ::= { hwEponDeviceOntEthernetPortCfgEntry 35 }

--Table  hwEponDeviceOntTDMPortCfgTable
        hwEponDeviceOntTDMPortCfgTable OBJECT-TYPE
            SYNTAX     SEQUENCE OF HwEponDeviceOntTDMPortCfgEntry
            MAX-ACCESS not-accessible
            STATUS     current
            DESCRIPTION
                "The ONT TDM port config table.
                 The index of this table is a combination of ifIndex, hwEponDeviceOntIndex
                 and hwEponDeviceOntTDMPortId.
                "
            ::= { hwXponDeviceControlObjects 82 }

        hwEponDeviceOntTDMPortCfgEntry OBJECT-TYPE
            SYNTAX     HwEponDeviceOntTDMPortCfgEntry
            MAX-ACCESS not-accessible
            STATUS     current
            DESCRIPTION
                "The ONT TDM port config table.
                 The index of this entry is a combination of ifIndex, hwEponDeviceOntIndex
                 and hwEponDeviceOntTDMPortId.
                "
            INDEX       { ifIndex, hwEponDeviceOntIndex, hwEponDeviceOntTDMPortId }
            ::= { hwEponDeviceOntTDMPortCfgTable 1 }

        HwEponDeviceOntTDMPortCfgEntry ::=
            SEQUENCE {
                hwEponDeviceOntTDMPortId                             Integer32,
                hwEponDeviceOntTDMPortOperateStatus                  INTEGER
            }

        hwEponDeviceOntTDMPortId  OBJECT-TYPE
            SYNTAX     Integer32
            MAX-ACCESS   not-accessible
            STATUS      current
            DESCRIPTION
                "This object indicates the ONT TDM port ID."
            ::= { hwEponDeviceOntTDMPortCfgEntry 1 }

        hwEponDeviceOntTDMPortOperateStatus  OBJECT-TYPE
            SYNTAX     INTEGER {
                on(1),
                off(2),
                invalid(-1)
            }
            MAX-ACCESS   read-write
            STATUS      current
            DESCRIPTION
                "This object indicates the switch of the port.
                 Options:
                 1. on(1)               - Indicates that the switch of the port is on
                 2. off(2)              - Indicates that the switch of the port is off
                 3. invalid(-1)         - Indicates that the query fails or no information is detected
                "
            ::= { hwEponDeviceOntTDMPortCfgEntry 2 }

-- Table hwEponDeviceOntPOTSPortCfgTable
        hwEponDeviceOntPOTSPortCfgTable OBJECT-TYPE
            SYNTAX     SEQUENCE OF HwEponDeviceOntPOTSPortCfgEntry
            MAX-ACCESS not-accessible
            STATUS     current
            DESCRIPTION
                "The ONT POTS port config table.
                 The index of this table is a combination of ifIndex, hwEponDeviceOntIndex
                 and hwEponDeviceOntPOTSPortId.
                "
            ::= { hwXponDeviceControlObjects 83 }

        hwEponDeviceOntPOTSPortCfgEntry OBJECT-TYPE
            SYNTAX     HwEponDeviceOntPOTSPortCfgEntry
            MAX-ACCESS not-accessible
            STATUS     current
            DESCRIPTION
                "The ONT POTS port config table.
                 The index of this entry is a combination of ifIndex, hwEponDeviceOntIndex
                 and hwEponDeviceOntPOTSPortId.
                "
            INDEX       { ifIndex, hwEponDeviceOntIndex, hwEponDeviceOntPOTSPortId }
            ::= { hwEponDeviceOntPOTSPortCfgTable 1 }

        HwEponDeviceOntPOTSPortCfgEntry ::=
            SEQUENCE {
                hwEponDeviceOntPOTSPortId                 Integer32,
                hwEponDeviceOntPOTSPortOperateStatus      INTEGER
            }

        hwEponDeviceOntPOTSPortId OBJECT-TYPE
            SYNTAX     Integer32
            MAX-ACCESS    not-accessible
            STATUS      current
            DESCRIPTION
                "This object indicates the ONT POTS port ID."
            ::= { hwEponDeviceOntPOTSPortCfgEntry 1 }

        hwEponDeviceOntPOTSPortOperateStatus OBJECT-TYPE
            SYNTAX     INTEGER {
                on(1),
                off(2),
                invalid(-1)
            }
            MAX-ACCESS    read-write
            STATUS      current
            DESCRIPTION
                "This object indicates the ONT POTS port switch.
                 Options:
                 1. on(1)               - Indicates that the switch of the ONT POTS port is on
                 2. off(2)              - Indicates that the switch of the ONT POTS port is off
                 3. invalid(-1)         - Indicates that the query fails or no information is detected
                "
            ::= { hwEponDeviceOntPOTSPortCfgEntry 2 }

-- Table hwGponDeviceOntTDMPortCfgTable
        hwGponDeviceOntTDMPortCfgTable OBJECT-TYPE
            SYNTAX     SEQUENCE OF HwGponDeviceOntTDMPortCfgEntry
            MAX-ACCESS not-accessible
            STATUS     current
            DESCRIPTION
                "The ONT TDM port config table.
                 The index of this table is a combination of ifIndex, hwGponDeviceOntIndex
                 and hwGponDeviceOntTDMPortId.
                "
            ::= { hwXponDeviceControlObjects 84 }

        hwGponDeviceOntTDMPortCfgEntry OBJECT-TYPE
            SYNTAX     HwGponDeviceOntTDMPortCfgEntry
            MAX-ACCESS not-accessible
            STATUS     current
            DESCRIPTION
                "The ONT TDM port config table.
                 The index of this entry is a combination of ifIndex, hwGponDeviceOntIndex
                 and hwGponDeviceOntTDMPortId.
                "
            INDEX       { ifIndex, hwGponDeviceOntIndex, hwGponDeviceOntTDMPortId }
            ::= { hwGponDeviceOntTDMPortCfgTable 1 }

        HwGponDeviceOntTDMPortCfgEntry ::=
            SEQUENCE {
                hwGponDeviceOntTDMPortId         Integer32,
                hwGponDeviceOntTDMPortState      INTEGER,
                hwGponDeviceOntTDMPortOperateStatus  INTEGER
            }

        hwGponDeviceOntTDMPortId OBJECT-TYPE
            SYNTAX     Integer32
            MAX-ACCESS    not-accessible
            STATUS      current
            DESCRIPTION
                "This object indicates the ONT TDM port ID."
            ::= { hwGponDeviceOntTDMPortCfgEntry 1 }

        hwGponDeviceOntTDMPortState OBJECT-TYPE
            SYNTAX     INTEGER {
                normal(1),
                los(2),
                ais(3),
                lof(4),
                invalid(-1)
            }
            MAX-ACCESS  read-only
            STATUS      current
            DESCRIPTION
                "This object indicates the ONT TDM port state.
                 Options:
                 1. normal (1)            - Indicates that the ONT TDM port state is normal
                 2. los (2)               - Indicates that the ONT TDM port state is LOS
                 3. ais(3)                - Indicates that the ONT TDM port state is AIS
                 4. lof(4)                - Indicates that the ONT TDM port state is LOF
                 5. invalid(-1)           - Indicates that the query fails or no information is detected
                "
            ::= { hwGponDeviceOntTDMPortCfgEntry 2 }

        hwGponDeviceOntTDMPortOperateStatus OBJECT-TYPE
            SYNTAX     INTEGER {
                enable(1),
                disable(2),
                invalid(-1)
            }
            MAX-ACCESS  read-write
            STATUS      current
            DESCRIPTION
                "ONT TDM port enable switch.
                 Options:
                 1. enable(1)   - Enable the ONT TDM port switch
                 2. disable(2)  - Disable the ONT TDM port switch
                 3. invalid(-1) - Indicates that the query fails or no information is detected
                "
            ::= { hwGponDeviceOntTDMPortCfgEntry 3 }

-- Table hwEponDeviceCtcRemoteOntPortVlanConfigTable
        hwEponDeviceCtcRemoteOntPortVlanConfigTable OBJECT-TYPE
            SYNTAX     SEQUENCE OF HwEponDeviceCtcRemoteOntPortVlanConfigEntry
            MAX-ACCESS not-accessible
            STATUS     current
            DESCRIPTION
                "The ont port's remote native vlan info table.
                 The index of this table is a combination of ifIndex, hwEponDeviceOntIndex,
                 hwEponDeviceOntPortType and hwEponDeviceOntPortId.
                "
            ::= { hwXponDeviceControlObjects 91 }

        hwEponDeviceCtcRemoteOntPortVlanConfigEntry OBJECT-TYPE
            SYNTAX     HwEponDeviceCtcRemoteOntPortVlanConfigEntry
            MAX-ACCESS not-accessible
            STATUS     current
            DESCRIPTION
                "The ont port's remote native vlan info table.
                 The index of this entry is a combination of ifIndex, hwEponDeviceOntIndex,
                 hwEponDeviceOntPortType and hwEponDeviceOntPortId.
                "
            INDEX       { ifIndex, hwEponDeviceOntIndex, hwEponDeviceOntPortType, hwEponDeviceOntPortId }
            ::= { hwEponDeviceCtcRemoteOntPortVlanConfigTable 1 }

        HwEponDeviceCtcRemoteOntPortVlanConfigEntry ::=
            SEQUENCE {
                hwEponDeviceOntPortType                           Integer32,
                hwEponDeviceOntPortId                             Integer32,
                hwEponDeviceCtcRemoteOntPortVlanMode              INTEGER,
                hwEponDeviceCtcRemoteOntPortDefaultTagTPID        Integer32,
                hwEponDeviceCtcRemoteOntPortDefaultTagCFI         Integer32,
                hwEponDeviceCtcRemoteOntPortDefaultTagPri         Integer32,
                hwEponDeviceCtcRemoteOntPortDefaultTagVID         Integer32
            }

        hwEponDeviceOntPortType  OBJECT-TYPE
            SYNTAX     Integer32
            MAX-ACCESS   not-accessible
            STATUS      current
            DESCRIPTION
                "This object indicates the ont port's type.
                 The value 24 indicates the FE port.
                 The value 34 indicates the GE port.
                 The value 47 indicates the ETH port.
                "
            ::= { hwEponDeviceCtcRemoteOntPortVlanConfigEntry 1 }

        hwEponDeviceOntPortId  OBJECT-TYPE
            SYNTAX      Integer32
            MAX-ACCESS   not-accessible
            STATUS      current
            DESCRIPTION
                "This object indicates the ont port ID."
            ::= { hwEponDeviceCtcRemoteOntPortVlanConfigEntry 2 }

        hwEponDeviceCtcRemoteOntPortVlanMode  OBJECT-TYPE
            SYNTAX     INTEGER {
                transparent(0),
                tag(1),
                translation(2),
                aggregation(3),
                trunk(4),
                invalid(-1)
            }
            MAX-ACCESS   read-only
            STATUS      current
            DESCRIPTION
                "This object indicates the vlan mode of ont's port.
                 Options:
                 1. transparent(0)     - Indicates that the vlan mode of ont's port is transparent
                 2. tag(1)             - Indicates that the vlan mode of ont's port is tag
                 3. translation(2)     - Indicates that the vlan mode of ont's port is translation
                 4. aggregation(3)     - Indicates that the vlan mode of ont's port is aggregation
                 5. trunk(4)           - Indicates that the vlan mode of ont's port is trunk
                 6. invalid(-1)        - Indicates that the query fails or no information is detected
                "
            ::= { hwEponDeviceCtcRemoteOntPortVlanConfigEntry 3 }

        hwEponDeviceCtcRemoteOntPortDefaultTagTPID  OBJECT-TYPE
            SYNTAX     Integer32
            MAX-ACCESS   read-only
            STATUS      current
            DESCRIPTION
                "This object indicates the ont port's native vlan TPID."
            ::= { hwEponDeviceCtcRemoteOntPortVlanConfigEntry 4 }

        hwEponDeviceCtcRemoteOntPortDefaultTagCFI  OBJECT-TYPE
            SYNTAX     Integer32
            MAX-ACCESS   read-only
            STATUS      current
            DESCRIPTION
                "This object indicates the ont port's native vlan CFI."
            ::= { hwEponDeviceCtcRemoteOntPortVlanConfigEntry 5 }

        hwEponDeviceCtcRemoteOntPortDefaultTagPri  OBJECT-TYPE
            SYNTAX     Integer32
            MAX-ACCESS   read-only
            STATUS      current
            DESCRIPTION
                "This object indicates the ont port's native vlan priority."
            ::= { hwEponDeviceCtcRemoteOntPortVlanConfigEntry 6 }

        hwEponDeviceCtcRemoteOntPortDefaultTagVID  OBJECT-TYPE
            SYNTAX     Integer32
            MAX-ACCESS   read-only
            STATUS      current
            DESCRIPTION
                "This object indicates the ont port's native VLAN ID."
            ::= { hwEponDeviceCtcRemoteOntPortVlanConfigEntry 7 }

-- Table  hwEponDeviceCtcRemoteOntPortVlanTranslationTable
        hwEponDeviceCtcRemoteOntPortVlanTranslationInfoTable OBJECT-TYPE
            SYNTAX     SEQUENCE OF HwEponDeviceCtcRemoteOntPortVlanTranslationInfoEntry
            MAX-ACCESS not-accessible
            STATUS     current
            DESCRIPTION
                "This table is used to display the configuration information about VLAN switching pair of the ONT port.
                 The index of this table is a combination of ifIndex, hwEponDeviceOntIndex,
                 hwEponDeviceOntPortType, hwEponDeviceOntPortId and hwEponDeviceOntPortVlanIndex.
                "
            ::= { hwXponDeviceControlObjects 92 }

        hwEponDeviceCtcRemoteOntPortVlanTranslationInfoEntry OBJECT-TYPE
            SYNTAX     HwEponDeviceCtcRemoteOntPortVlanTranslationInfoEntry
            MAX-ACCESS not-accessible
            STATUS     current
            DESCRIPTION
                "This table is used to display the configuration information about VLAN switching pair of the ONT port.
                 The index of this entry is a combination of ifIndex, hwEponDeviceOntIndex,
                 hwEponDeviceOntPortType, hwEponDeviceOntPortId and hwEponDeviceOntPortVlanIndex.
                "
            INDEX       { ifIndex, hwEponDeviceOntIndex, hwEponDeviceOntPortType, hwEponDeviceOntPortId, hwEponDeviceOntPortVlanIndex }
            ::= { hwEponDeviceCtcRemoteOntPortVlanTranslationInfoTable 1 }

        HwEponDeviceCtcRemoteOntPortVlanTranslationInfoEntry ::=
            SEQUENCE {
                hwEponDeviceOntPortVlanIndex                 Integer32,
                hwEponDeviceCtcOntPortCvlanTagTPID           Integer32,
                hwEponDeviceCtcOntPortCvlanTagCFI            Integer32,
                hwEponDeviceCtcOntPortCvlanTagPri            Integer32,
                hwEponDeviceCtcOntPortCvlanTagVID            Integer32,
                hwEponDeviceCtcOntPortSvlanTagTPID           Integer32,
                hwEponDeviceCtcOntPortSvlanTagCFI            Integer32,
                hwEponDeviceCtcOntPortSvlanTagPri            Integer32,
                hwEponDeviceCtcOntPortSvlanTagVID            Integer32
            }

        hwEponDeviceOntPortVlanIndex     OBJECT-TYPE
            SYNTAX     Integer32
            MAX-ACCESS   not-accessible
            STATUS      current
            DESCRIPTION
                "This object indicates the vlan index."
            ::= { hwEponDeviceCtcRemoteOntPortVlanTranslationInfoEntry 1 }

        hwEponDeviceCtcOntPortCvlanTagTPID  OBJECT-TYPE
            SYNTAX     Integer32
            MAX-ACCESS   read-only
            STATUS      current
            DESCRIPTION
                "This object indicates the ont port's vlan TPID."
            ::= { hwEponDeviceCtcRemoteOntPortVlanTranslationInfoEntry 2 }

        hwEponDeviceCtcOntPortCvlanTagCFI  OBJECT-TYPE
            SYNTAX     Integer32
            MAX-ACCESS   read-only
            STATUS      current
            DESCRIPTION
                "This object indicates the ont port's vlan CFI."
            ::= { hwEponDeviceCtcRemoteOntPortVlanTranslationInfoEntry 3 }

        hwEponDeviceCtcOntPortCvlanTagPri  OBJECT-TYPE
            SYNTAX     Integer32
            MAX-ACCESS   read-only
            STATUS      current
            DESCRIPTION
                "This object indicates the ont port's vlan priority."
            ::= { hwEponDeviceCtcRemoteOntPortVlanTranslationInfoEntry 4 }

        hwEponDeviceCtcOntPortCvlanTagVID  OBJECT-TYPE
            SYNTAX     Integer32
            MAX-ACCESS   read-only
            STATUS      current
            DESCRIPTION
                "This object indicates the ont port's VLAN ID."
            ::= { hwEponDeviceCtcRemoteOntPortVlanTranslationInfoEntry 5 }

        hwEponDeviceCtcOntPortSvlanTagTPID  OBJECT-TYPE
            SYNTAX     Integer32
            MAX-ACCESS   read-only
            STATUS      current
            DESCRIPTION
                "This object indicates the ont port's vlan TPID."
            ::= { hwEponDeviceCtcRemoteOntPortVlanTranslationInfoEntry 6 }

        hwEponDeviceCtcOntPortSvlanTagCFI  OBJECT-TYPE
            SYNTAX     Integer32
            MAX-ACCESS   read-only
            STATUS      current
            DESCRIPTION
                "This object indicates the ont port's vlan CFI."
            ::= { hwEponDeviceCtcRemoteOntPortVlanTranslationInfoEntry 7 }

        hwEponDeviceCtcOntPortSvlanTagPri  OBJECT-TYPE
            SYNTAX     Integer32
            MAX-ACCESS   read-only
            STATUS      current
            DESCRIPTION
                "This object indicates the ont port's vlan priority."
            ::= { hwEponDeviceCtcRemoteOntPortVlanTranslationInfoEntry 8 }

        hwEponDeviceCtcOntPortSvlanTagVID  OBJECT-TYPE
            SYNTAX     Integer32
            MAX-ACCESS   read-only
            STATUS      current
            DESCRIPTION
                "This object indicates the ont port's VLAN ID."
            ::= { hwEponDeviceCtcRemoteOntPortVlanTranslationInfoEntry 9 }

-- Table  hwEponDeviceCtcRemoteOntMultiCtrItemTable
        hwEponDeviceCtcRemoteOntMultiCtrItemTable OBJECT-TYPE
            SYNTAX     SEQUENCE OF HwEponDeviceCtcRemoteOntMultiCtrItemEntry
            MAX-ACCESS not-accessible
            STATUS     current
            DESCRIPTION
                "This table is used to display the ONT multicast control list.
                 The index of this table is a combination of ifIndex, hwEponDeviceOntIndex
                 and hwEponDeviceOntMultiCtrItemIndex.
                "
            ::= { hwXponDeviceControlObjects 93 }

        hwEponDeviceCtcRemoteOntMultiCtrItemEntry OBJECT-TYPE
            SYNTAX     HwEponDeviceCtcRemoteOntMultiCtrItemEntry
            MAX-ACCESS not-accessible
            STATUS     current
            DESCRIPTION
                "This table is used to display the ONT multicast control list.
                 The index of this entry is a combination of ifIndex, hwEponDeviceOntIndex
                 and hwEponDeviceOntMultiCtrItemIndex.
                "
            INDEX       { ifIndex, hwEponDeviceOntIndex, hwEponDeviceOntMultiCtrItemIndex }
            ::= { hwEponDeviceCtcRemoteOntMultiCtrItemTable 1 }

        HwEponDeviceCtcRemoteOntMultiCtrItemEntry ::=
            SEQUENCE {
                hwEponDeviceOntMultiCtrItemIndex                      Integer32,
                hwEponDeviceCtcOntMultiCtrlType                       INTEGER,
                hwEponDeviceCtcOntMultiCtrlUsrID                      Integer32,
                hwEponDeviceCtcOntMultiCtrlGDA                        OCTET STRING,
                hwEponDeviceCtcOntMultiCtrlVlanIDorSA                 OCTET STRING
            }

        hwEponDeviceOntMultiCtrItemIndex  OBJECT-TYPE
            SYNTAX     Integer32
            MAX-ACCESS   not-accessible
            STATUS      current
            DESCRIPTION
                "This object indicates the item's index."
            ::= { hwEponDeviceCtcRemoteOntMultiCtrItemEntry 1 }

        hwEponDeviceCtcOntMultiCtrlType  OBJECT-TYPE
            SYNTAX     INTEGER {
                gda(0),
                gdaVLAN(1),
                gdaSA(2),
                invalid(-1)
            }
            MAX-ACCESS   read-only
            STATUS      current
            DESCRIPTION
                "This object indicates the multicast contrl type.
                 Options:
                 1. gda(0)       - Based GDA MAC only
                 2. gdaVLAN(1)   - Based GDA MAC plus muliticast VLAN ID
                 3. gdaSA(2)     - Based GDA MAC plus SA MAC
                 4. invalid(-1)  - Indicates that the query fails or no information is detected
                "
            ::= { hwEponDeviceCtcRemoteOntMultiCtrItemEntry 2 }

        hwEponDeviceCtcOntMultiCtrlUsrID  OBJECT-TYPE
            SYNTAX     Integer32
            MAX-ACCESS   read-only
            STATUS      current
            DESCRIPTION
                "This object indicates the user ID of multicast."
            ::= { hwEponDeviceCtcRemoteOntMultiCtrItemEntry 3 }

        hwEponDeviceCtcOntMultiCtrlGDA  OBJECT-TYPE
            SYNTAX     OCTET STRING  (SIZE (6))
            MAX-ACCESS   read-only
            STATUS      current
            DESCRIPTION
                "This object indicates the GDA of multicast control."
            ::= { hwEponDeviceCtcRemoteOntMultiCtrItemEntry 4 }

        hwEponDeviceCtcOntMultiCtrlVlanIDorSA  OBJECT-TYPE
            SYNTAX     OCTET STRING  (SIZE (6))
            MAX-ACCESS   read-only
            STATUS      current
            DESCRIPTION
                "This object indicates the SA of multicast control."
            ::= { hwEponDeviceCtcRemoteOntMultiCtrItemEntry 5 }

-- hwXponDeviceControlObjects  end

-- hwXponDeviceProfileObjects  begin

--  Table hwXponDeviceDbaProfileInfoTable
        hwXponDeviceDbaProfileInfoTable OBJECT-TYPE
            SYNTAX     SEQUENCE OF HwXponDeviceDbaProfileInfoEntry
            MAX-ACCESS   not-accessible
            STATUS     current
            DESCRIPTION
                "This is the DBA profile table. This table is used to create a DBA profile,
                 and is used to modify or delete a DBA profile which is not bound.
                 The index of this table is hwXponDeviceDbaProfileInfoNameIndex.
                "
            ::= { hwXponDeviceProfileObjects  21 }

        hwXponDeviceDbaProfileInfoEntry OBJECT-TYPE
            SYNTAX     HwXponDeviceDbaProfileInfoEntry
            MAX-ACCESS not-accessible
            STATUS     current
            DESCRIPTION
                "This is the DBA profile table. This table is used to create a DBA profile,
                 and is used to modify or delete a DBA profile which is not bound.
                 The index of this entry is hwXponDeviceDbaProfileInfoNameIndex.
                "
            INDEX       { IMPLIED hwXponDeviceDbaProfileInfoNameIndex }
            ::= { hwXponDeviceDbaProfileInfoTable 1 }

        HwXponDeviceDbaProfileInfoEntry ::=
            SEQUENCE {
                hwXponDeviceDbaProfileInfoNameIndex         OCTET STRING,
                hwXponDeviceDbaProfileType                  Integer32,
                hwXponDeviceDbaProfileFixedRate             Integer32,
                hwXponDeviceDbaProfileAssuredRate           Integer32,
                hwXponDeviceDbaProfileMaxRate               Integer32,
                hwXponDeviceDbaProfileReferenceNum          Integer32,
                hwXponDeviceDbaProfileBandwithCompensate    INTEGER,
                hwXponDeviceDbaProfileEntryStatus           RowStatus,
                hwXponDeviceDbaProfileFixDelay              INTEGER,
                hwXponDeviceDbaProfileAdditionalBW          INTEGER,
                hwXponDeviceDbaProfilePriority              Integer32,
                hwXponDeviceDbaProfileWeight                Integer32,
                hwXponDeviceDbaProfileOperateResult         Integer32,
                hwXponDeviceDbaProfileAsynCommit            INTEGER
            }

        hwXponDeviceDbaProfileInfoNameIndex OBJECT-TYPE
            SYNTAX    OCTET STRING  (SIZE (1..33))
            MAX-ACCESS    not-accessible
            STATUS    current
            DESCRIPTION
                "This object indicates the DBA profile name."
            ::= { hwXponDeviceDbaProfileInfoEntry 1 }

        hwXponDeviceDbaProfileType OBJECT-TYPE
            SYNTAX  Integer32
            MAX-ACCESS    read-write
            STATUS    current
            DESCRIPTION
                "This object indicates the DBA profile type.
                 The value (1) indicates that the DBA profile type is Type 1.
                 The value (2) indicates that the DBA profile type is Type 2.
                 The value (3) indicates that the DBA profile type is Type 3.
                 The value (4) indicates that the DBA profile type is Type 4.
                 The value (5) indicates that the DBA profile type is Type 5.
                 The value (-1) indicates that the query fails or no information is detected."
            ::= { hwXponDeviceDbaProfileInfoEntry 2 }

        hwXponDeviceDbaProfileFixedRate OBJECT-TYPE
            SYNTAX  Integer32 (0 | 128..10000000)
            MAX-ACCESS    read-write
            STATUS    current
            DESCRIPTION
                "This object indicates the fixed bandwidth of the profile, unit Kbps.
                 The value (0) is invalid value.
                "
            ::= { hwXponDeviceDbaProfileInfoEntry 3 }

        hwXponDeviceDbaProfileAssuredRate OBJECT-TYPE
            SYNTAX  Integer32 (0 | 128..10000000)
            MAX-ACCESS    read-write
            STATUS    current
            DESCRIPTION
                "This object indicates the assured bandwidth of the profile, unit Kbps.
                 The value (0) is invalid value.
                "
            ::= { hwXponDeviceDbaProfileInfoEntry 4 }

        hwXponDeviceDbaProfileMaxRate OBJECT-TYPE
            SYNTAX  Integer32 (0 | 128..10000000)
            MAX-ACCESS    read-write
            STATUS    current
            DESCRIPTION
                "This object indicates the max bandwidth of the profile, unit Kbps.
                 The value (0) is invalid value.
                "
            ::= { hwXponDeviceDbaProfileInfoEntry 5 }

        hwXponDeviceDbaProfileReferenceNum  OBJECT-TYPE
            SYNTAX  Integer32
            MAX-ACCESS    read-only
            STATUS    current
            DESCRIPTION
                "This object indicates the binding times of the profile."
            ::= { hwXponDeviceDbaProfileInfoEntry 6 }

        hwXponDeviceDbaProfileBandwithCompensate   OBJECT-TYPE
            SYNTAX  INTEGER{
                enable(1),
                disable(2)
            }
            MAX-ACCESS    read-write
            STATUS    current
            DESCRIPTION
                "This object indicates the bandwidth compensation policy of the profile.
                 Options:
                 1. enable(1)      - Enable the bandwidth compensation policy of the profile
                 2. disable(2)     - Disable the bandwidth compensation policy of the profile
                "
            ::= { hwXponDeviceDbaProfileInfoEntry 7 }

        hwXponDeviceDbaProfileEntryStatus OBJECT-TYPE
            SYNTAX  RowStatus
            MAX-ACCESS  read-create
            STATUS    current
            DESCRIPTION
                "The hwXponDeviceDbaProfileEntryStatus is used to create a new row or to modify
                 or delete an existing row in this table.
                 Options:
                 1. createAndGo(4) -create a new instance of a conceptual row
                 2. destroy(6)     -delete the instances associated with an existing conceptual row
                "
            ::= { hwXponDeviceDbaProfileInfoEntry 8 }

        hwXponDeviceDbaProfileFixDelay   OBJECT-TYPE
            SYNTAX   INTEGER{
                       enable(1),
                       disable(2)
            }
            MAX-ACCESS    read-write
            STATUS    current
            DESCRIPTION
                "Fix delay switch of the profile.
                 Options:
                 1. enable(1)  -Fix delay switch of the profile is enable
                 2. disable(2) -Fix delay switch of the profile is disable
                "
            ::= { hwXponDeviceDbaProfileInfoEntry 9 }

        hwXponDeviceDbaProfileAdditionalBW   OBJECT-TYPE
            SYNTAX   INTEGER{
                       nonAssure(1),
                       bestEffort(2),
                       invalid(-1)
            }
            MAX-ACCESS    read-write
            STATUS    current
            DESCRIPTION
                "Additional bandwidth type of the profile.
                 Options:
                 1. nonAssure(1)  -Additional bandwidth type of the profile is non assure
                 2. bestEffort(2) -Additional bandwidth type of the profile is best effort
                 3. invalid(-1)    - Indicates that the query fails or no information is detected
                "
            ::= { hwXponDeviceDbaProfileInfoEntry 10 }

        hwXponDeviceDbaProfilePriority   OBJECT-TYPE
             SYNTAX Integer32
             MAX-ACCESS read-write
             STATUS current
             DESCRIPTION
                 "This object is used to set best effort bandwidth assignment priority.
                  Ranging from 0 to 7, 0 is the lowest priority.
                  The default value is 0.
                 "
            ::= { hwXponDeviceDbaProfileInfoEntry 11 }

        hwXponDeviceDbaProfileWeight   OBJECT-TYPE
             SYNTAX Integer32
             MAX-ACCESS read-write
             STATUS current
             DESCRIPTION
                 "This object is used to set best effort bandwidth assignment weight.
                  Ranging from 1 to 10000.
                  The default value is 128.
                 "
            ::= { hwXponDeviceDbaProfileInfoEntry 12 }

        hwXponDeviceDbaProfileOperateResult   OBJECT-TYPE
            SYNTAX   Integer32
            MAX-ACCESS    read-only
            STATUS    current
            DESCRIPTION
                "This object indicates the commit result of a DBA profile, the aging time of the result is 20s.
                 Options:
                 This node identifies the result of DBA profile commit:
                 	Value 0 indicates the commit result is successfully.
                 	Value 1~0xFFFFFFFF-2 indicates the commit result is fail and return error code.
                 	Value 0xFFFFFFFD  indicates that the commit does not complete
                 	Value 0xFFFFFFFE  indicates that no commit is being operated
                 	Value 0xFFFFFFFF  indicates invalid
                "
            ::= { hwXponDeviceDbaProfileInfoEntry 13 }

       	hwXponDeviceDbaProfileAsynCommit OBJECT-TYPE
            SYNTAX INTEGER {
                 asynMode(1),
                 invalid(-1)
            }
            MAX-ACCESS read-write
            STATUS current
            DESCRIPTION
              	"This object indicates the mode of commit of a DBA profile
                Options:
                1. asynMode (1)   - Indicates that the commit mode is asynchronous
                2. invalid(-1)	  - Invalid value
             	The device will perform sync mode without the mib node.
	    	"
            ::= { hwXponDeviceDbaProfileInfoEntry 14 }


--  Table hwXponDeviceOntSnmpProfileInfoTable
        hwXponDeviceOntSnmpProfileInfoTable OBJECT-TYPE
            SYNTAX SEQUENCE OF HwXponDeviceOntSnmpProfileInfoEntry
            MAX-ACCESS not-accessible
            STATUS current
            DESCRIPTION
                "This table is the SNMP parameter management profile of the ONT.
                 The index of this table is hwXponDeviceOntSnmpProfileInfoNameIndex.
                "
            ::= { hwXponDeviceProfileObjects 22 }

        hwXponDeviceOntSnmpProfileInfoEntry OBJECT-TYPE
            SYNTAX HwXponDeviceOntSnmpProfileInfoEntry
            MAX-ACCESS not-accessible
            STATUS current
            DESCRIPTION
                "This table is the SNMP parameter management profile of the ONT.
                 The index of this entry is hwXponDeviceOntSnmpProfileInfoNameIndex.
                "
            INDEX { IMPLIED hwXponDeviceOntSnmpProfileInfoNameIndex }
            ::= { hwXponDeviceOntSnmpProfileInfoTable 1 }

        HwXponDeviceOntSnmpProfileInfoEntry ::=
            SEQUENCE {
                hwXponDeviceOntSnmpProfileInfoNameIndex      OCTET STRING,
                hwXponDeviceOntSnmpProfileVersion            INTEGER,
                hwXponDeviceOntSnmpProfileReadCommunityName  OCTET STRING,
                hwXponDeviceOntSnmpProfileWriteCommunityName OCTET STRING,
                hwXponDeviceOntSnmpProfileTrapHostIP         IpAddress,
                hwXponDeviceOntSnmpProfileTrapHostSrcUDPPort Integer32,
                hwXponDeviceOntSnmpProfileSecurityName       OCTET STRING,
                hwXponDeviceOntSnmpProfileRowStatus              RowStatus,
                hwXponDeviceOntSnmpProfileUsmUsername            OCTET STRING,
                hwXponDeviceOntSnmpProfileAuthenticationMode     INTEGER,
                hwXponDeviceOntSnmpProfileAuthenticationPassword OCTET STRING,
                hwXponDeviceOntSnmpProfilePrivacyMode            INTEGER,
                hwXponDeviceOntSnmpProfilePrivacyPassword        OCTET STRING,
                hwXponDeviceOntSnmpProfileSecurityLevel          INTEGER
            }

        hwXponDeviceOntSnmpProfileInfoNameIndex OBJECT-TYPE
            SYNTAX OCTET STRING (SIZE (1..32))
            MAX-ACCESS not-accessible
            STATUS current
            DESCRIPTION
                "This object indicates the ONT SNMP profile name."
            ::= { hwXponDeviceOntSnmpProfileInfoEntry 1 }

        hwXponDeviceOntSnmpProfileVersion OBJECT-TYPE
            SYNTAX INTEGER{
                v1(1),
                v2c(2),
                v3(3)
            }
            MAX-ACCESS read-write
            STATUS current
            DESCRIPTION
                "This object indicates the SNMP version number.
                 Options:
                 1. v1(1)                - Indicates that the SNMP version is v1
                 2. v2c(2)               - Indicates that the SNMP version is v2c
                 3. v3(3)                - Indicates that the SNMP version is v3
                 The default value is v1(1).
                "
            DEFVAL { v1 }
            ::= { hwXponDeviceOntSnmpProfileInfoEntry 2 }

        hwXponDeviceOntSnmpProfileReadCommunityName OBJECT-TYPE
            SYNTAX OCTET STRING (SIZE (0..32))
            MAX-ACCESS read-write
            STATUS current
            DESCRIPTION
                "This object indicates the name of the read community."
            ::= { hwXponDeviceOntSnmpProfileInfoEntry 3 }

        hwXponDeviceOntSnmpProfileWriteCommunityName OBJECT-TYPE
            SYNTAX OCTET STRING (SIZE (0..32))
            MAX-ACCESS read-write
            STATUS current
            DESCRIPTION
                "This object indicates the name of the write community."
            ::= { hwXponDeviceOntSnmpProfileInfoEntry 4 }

        hwXponDeviceOntSnmpProfileTrapHostIP OBJECT-TYPE
            SYNTAX IpAddress
            MAX-ACCESS read-write
            STATUS current
            DESCRIPTION
                "This object indicates the target host address of sending trap msg."
            ::= { hwXponDeviceOntSnmpProfileInfoEntry 5 }

        hwXponDeviceOntSnmpProfileTrapHostSrcUDPPort OBJECT-TYPE
            SYNTAX Integer32
            MAX-ACCESS read-write
            STATUS current
            DESCRIPTION
                "This object indicates the ID of the host UDP source port from which the trap is sent."
            ::= { hwXponDeviceOntSnmpProfileInfoEntry 6 }

        hwXponDeviceOntSnmpProfileSecurityName OBJECT-TYPE
            SYNTAX OCTET STRING (SIZE (1..32))
            MAX-ACCESS read-write
            STATUS current
            DESCRIPTION
                "This object indicates the securityname of SNMP msg"
            ::= { hwXponDeviceOntSnmpProfileInfoEntry 7 }

        hwXponDeviceOntSnmpProfileRowStatus OBJECT-TYPE
            SYNTAX RowStatus
            MAX-ACCESS read-create
            STATUS current
            DESCRIPTION
                "The hwXponDeviceOntSnmpProfileRowStatus is used to create a new row
                 or to modify or delete an existing row in this table.
                 Options:
                 1. createAndGo(4) -create a new instance of a conceptual row
                 2. destroy(6)     -delete the instances associated with an existing conceptual row
                "
            ::= { hwXponDeviceOntSnmpProfileInfoEntry 8 }

        hwXponDeviceOntSnmpProfileUsmUsername OBJECT-TYPE
            SYNTAX OCTET STRING (SIZE (0..32))
            MAX-ACCESS read-write
            STATUS current
            DESCRIPTION
                "The name of the SNMPv3 user."
            ::= { hwXponDeviceOntSnmpProfileInfoEntry 9 }

        hwXponDeviceOntSnmpProfileAuthenticationMode OBJECT-TYPE
            SYNTAX INTEGER{
                none(1),
                hmacMd5(2),
                hmacSha(3),
                invalid(255)
            }
            MAX-ACCESS read-write
            STATUS current
            DESCRIPTION
                "This object indicates the user authentication mode.
                 When the version of the SNMP profile is v1 or v2c, the invalid value will be returned.
                 Options:
                 1. none(1)        - No authentication mode
                 2. hmacMd5(2)     - Hmac-md5 authentication mode
                 3. hmacSha(3)     - Hmac-sha authentication mode
                 4. invalid(255)   - Invalid value
                "
            ::= { hwXponDeviceOntSnmpProfileInfoEntry 10 }

        hwXponDeviceOntSnmpProfileAuthenticationPassword OBJECT-TYPE
            SYNTAX OCTET STRING (SIZE (0..0 | 8..64))
            MAX-ACCESS read-write
            STATUS current
            DESCRIPTION
                "The authentication password."
            ::= { hwXponDeviceOntSnmpProfileInfoEntry 11 }

        hwXponDeviceOntSnmpProfilePrivacyMode OBJECT-TYPE
            SYNTAX INTEGER{
                none(1),
                des56(2),
                tripleDes(3),
                aes128(4),
                aes192(20),
                aes256(21),
                invalid(255)
            }
            MAX-ACCESS read-write
            STATUS current
            DESCRIPTION
                "This object indicates the user encryption mode.
                 When the version of the SNMP profile is v1 or v2c, the invalid value will be returned.
                 Options:
                 1. none(1)        - No encryption mode
                 2. des56(2)       - 56-bit DES encryption mode
                 3. tripleDes(3)   - 3DES encryption mode
                 4. aes128(4)      - 128-bit AES encryption mode
                 5. aes192(20)      - 192-bit AES encryption mode
                 6. aes256(21)      - 256-bit AES encryption mode
                 7. invalid(255)   - Invalid value
                "
            ::= { hwXponDeviceOntSnmpProfileInfoEntry 12 }

        hwXponDeviceOntSnmpProfilePrivacyPassword OBJECT-TYPE
            SYNTAX OCTET STRING (SIZE (0..0 | 8..64))
            MAX-ACCESS read-write
            STATUS current
            DESCRIPTION
                "The encryption password."
            ::= { hwXponDeviceOntSnmpProfileInfoEntry 13 }

        hwXponDeviceOntSnmpProfileSecurityLevel OBJECT-TYPE
            SYNTAX INTEGER{
                privacy(1),
                authentication(2),
                noauthnopriv(3),
                invalid(255)
            }
            MAX-ACCESS read-write
            STATUS current
            DESCRIPTION
                "This object indicates the trap security level.
                 When the version of the SNMP profile is v1 or v2c, the invalid value will be returned.
                 Options:
                 1. privacy(1)         - Authenticate and encrypt the SNMPv3 trap packet
                 2. authentication(2)  - Authenticate but not encrypt the SNMPv3 trap packet
                 3. noauthnopriv(3)    - Not authenticate nor encrypt the SNMPv3 trap packet
                 4. invalid(255)       - Invalid value
                "
            ::= { hwXponDeviceOntSnmpProfileInfoEntry 14 }

-- Table hwXponDeviceOntPortClassTable
        hwXponDeviceOntPortClassTable OBJECT-TYPE
            SYNTAX  SEQUENCE OF HwXponDeviceOntPortClassEntry
            MAX-ACCESS  not-accessible
            STATUS  current
            DESCRIPTION
                "The configuration table of the XPON classification.
                 The index of this table is a combination of hwXponDeviceOntPortClassProfileIdIndex,
                 hwXponDeviceOntPortClassPrecedenceIndex and hwXponDeviceOntPortClassConditionIndex.
                "
            ::= { hwXponDeviceProfileObjects 23 }

        hwXponDeviceOntPortClassEntry OBJECT-TYPE
            SYNTAX  HwXponDeviceOntPortClassEntry
            MAX-ACCESS  not-accessible
            STATUS  current
            DESCRIPTION
                "The configuration table of the XPON classification.
                 The index of this entry is a combination of hwXponDeviceOntPortClassProfileIdIndex,
                 hwXponDeviceOntPortClassPrecedenceIndex and hwXponDeviceOntPortClassConditionIndex.
                "
            INDEX  { hwXponDeviceOntPortClassProfileIdIndex, hwXponDeviceOntPortClassPrecedenceIndex,
                     hwXponDeviceOntPortClassConditionIndex }
            ::= { hwXponDeviceOntPortClassTable 1 }

        HwXponDeviceOntPortClassEntry  ::=
            SEQUENCE {
                hwXponDeviceOntPortClassProfileIdIndex                 Integer32,
                hwXponDeviceOntPortClassPrecedenceIndex                Integer32,
                hwXponDeviceOntPortClassConditionIndex                 Integer32,
                hwXponDeviceOntPortClassProfileRefNum                  Integer32,
                hwXponDeviceOntPortClassProfileName                    OCTET STRING,
                hwXponDeviceOntPortClassProfileQueuemapped             Integer32,
                hwXponDeviceOntPortClassProfilePriMark                 Integer32,
                hwXponDeviceOntPortClassProfileFieldselect             Integer32,
                hwXponDeviceOntPortClassProfileOperator                Integer32,
                hwXponDeviceOntPortClassProfileMatchValue              OCTET STRING,
                hwXponDeviceOntPortClassProfileRowStatus               RowStatus
            }

        hwXponDeviceOntPortClassProfileIdIndex OBJECT-TYPE
            SYNTAX  Integer32
            MAX-ACCESS  not-accessible
            STATUS  current
            DESCRIPTION
                "This object indicates the profile index."
            ::= { hwXponDeviceOntPortClassEntry 1 }

        hwXponDeviceOntPortClassPrecedenceIndex OBJECT-TYPE
            SYNTAX  Integer32
            MAX-ACCESS not-accessible
            STATUS  current
            DESCRIPTION
                "This object indicates the precedence-rule"
            ::= { hwXponDeviceOntPortClassEntry 2 }

        hwXponDeviceOntPortClassConditionIndex OBJECT-TYPE
            SYNTAX  Integer32
            MAX-ACCESS  not-accessible
            STATUS  current
            DESCRIPTION
                "This object indicates the conditionindex-condition."
            ::= { hwXponDeviceOntPortClassEntry 3 }

        hwXponDeviceOntPortClassProfileRefNum OBJECT-TYPE
            SYNTAX  Integer32
            MAX-ACCESS read-only
            STATUS  current
            DESCRIPTION
                "This object indicates the profile binding times."
            ::= { hwXponDeviceOntPortClassEntry 4 }

        hwXponDeviceOntPortClassProfileName OBJECT-TYPE
            SYNTAX  OCTET STRING (SIZE (1..32))
            MAX-ACCESS  read-write
            STATUS  current
            DESCRIPTION
                "This object indicates the profile name."
            ::= { hwXponDeviceOntPortClassEntry 5 }

        hwXponDeviceOntPortClassProfileQueuemapped OBJECT-TYPE
            SYNTAX   Integer32
            MAX-ACCESS  read-write
            STATUS  current
            DESCRIPTION
                "This object indicates the mapping queue.
                The valid value range is 0~255.
		The value (-1) indicates that the query fails or no information is detected.
		"
            ::= { hwXponDeviceOntPortClassEntry 6 }

        hwXponDeviceOntPortClassProfilePriMark OBJECT-TYPE
            SYNTAX  Integer32
            MAX-ACCESS  read-write
            STATUS  current
            DESCRIPTION
                "This object indicates the priority mark.
                The valid value range is 0~7,255.
		The value (-1) indicates that the query fails or no information is detected.
		"
            ::= { hwXponDeviceOntPortClassEntry 7 }

        hwXponDeviceOntPortClassProfileFieldselect OBJECT-TYPE
            SYNTAX  Integer32
            MAX-ACCESS  read-write
            STATUS  current
            DESCRIPTION
                "This object indicates the field selected corresponding the condition.
                 The value (0) indicates that the field is classified by destination MAC.
                 The value (1) indicates that the field is classified by source MAC.
                 The value (2) indicates that the field is classified by ethernet user priority.
                 The value (3) indicates that the field is classified by VLAN ID.
                 The value (4) indicates that the field is classified by ETH type.
                 The value (5) indicates that the field is classified by destination IPv4 address.
                 The value (6) indicates that the field is classified by source IPv4 address.
                 The value (7) indicates that the field is classified by IP protocol type.
                 The value (8) indicates that the field is classified by IPv4 DSCP.
                 The value (9) indicates that the field is classified by IPv6 DSCP.
                 The value (10) indicates that the field is classified by source port of layer 4 protocol.
                 The value (11) indicates that the field is classified by destination port of layer 4 protocol.
                 The value (12) indicates that the field is classified by IP version.
                 The value (13) indicates that the field is classified by IPv6 flow label.
                 The value (14) indicates that the field is classified by destination IPv6 address.
                 The value (15) indicates that the field is classified by source IPv6 address.
                 The value (16) indicates that the field is classified by prefix of destination IPv6 address.
                 The value (17) indicates that the field is classified by prefix of source IPv6 address.
                 The value (18) indicates that the field is classified by IPv6 next header.
		 The value (-1) indicates that the query fails or no information is detected.
                "
            ::= { hwXponDeviceOntPortClassEntry 8 }

        hwXponDeviceOntPortClassProfileOperator OBJECT-TYPE
            SYNTAX  Integer32
            MAX-ACCESS  read-write
            STATUS  current
            DESCRIPTION
                "This object indicates the operator flag.
             	 The value (0) indicates that the operator flag is never match.
	 	 The value (1) indicates that the operator flag is equal.
		 The value (2) indicates that the operator flag is not equal.
		 The value (3) indicates that the operator flag is less than or equal.
		 The value (4) indicates that the operator flag is greater or equal.
		 The value (5) indicates that the operator flag is true if field exists.
	 	 The value (6) indicates that the operator flag is true if field not exist.
		 The value (7) indicates that the operator flag is always match.
		 The value (-1) indicates that the query fails or no information is detected
                "
            ::= { hwXponDeviceOntPortClassEntry 9 }

        hwXponDeviceOntPortClassProfileMatchValue OBJECT-TYPE
            SYNTAX  OCTET STRING (SIZE (1..64))
            MAX-ACCESS  read-write
            STATUS  current
            DESCRIPTION
                "This object indicates the match values."
            ::= { hwXponDeviceOntPortClassEntry 10 }

        hwXponDeviceOntPortClassProfileRowStatus OBJECT-TYPE
            SYNTAX  RowStatus
            MAX-ACCESS  read-create
            STATUS  current
            DESCRIPTION
                "The hwXponDeviceOntPortClassProfileRowStatus is used to create a new row
                 or to modify or delete an existing row in this table.
                 Options:
                 1. createAndGo(4) -create a new instance of a conceptual row
                 2. destroy(6)     -delete the instances associated with an existing conceptual row
                "
            ::= { hwXponDeviceOntPortClassEntry 11 }
-- ont classification table end

--  Table hwEponDeviceLineProfileInfoTable
        hwEponDeviceLineProfileInfoTable OBJECT-TYPE
            SYNTAX SEQUENCE OF HwEponDeviceLineProfileInfoEntry
            MAX-ACCESS not-accessible
            STATUS current
            DESCRIPTION
                "This is the EPON line profile table. This table is used to create a EPON line profile.
                 The index of this table is hwEponDeviceLineProfileInfoNameIndex.
                "
            ::= { hwXponDeviceProfileObjects 41 }

        hwEponDeviceLineProfileInfoEntry OBJECT-TYPE
            SYNTAX HwEponDeviceLineProfileInfoEntry
            MAX-ACCESS not-accessible
            STATUS current
            DESCRIPTION
                "This is the EPON line profile table. This table is used to create a EPON line profile.
                 The index of this entry is hwEponDeviceLineProfileInfoNameIndex.
                "
            INDEX { IMPLIED hwEponDeviceLineProfileInfoNameIndex }
            ::= { hwEponDeviceLineProfileInfoTable 1 }

        HwEponDeviceLineProfileInfoEntry ::=
            SEQUENCE {
                hwEponDeviceLineProfileInfoNameIndex            OCTET STRING,
                hwEponDeviceLineProfileBindNum                  Integer32,
                hwEponDeviceLineProfileFEC                      INTEGER,
                hwEponDeviceLineProfileCommit                   INTEGER,
                hwEponDeviceLineProfileRowStatus                RowStatus,
                hwEponDeviceLineProfileTr069ManagementIpIndex   Integer32
            }

        hwEponDeviceLineProfileInfoNameIndex OBJECT-TYPE
            SYNTAX OCTET STRING (SIZE (1..32))
            MAX-ACCESS not-accessible
            STATUS current
            DESCRIPTION
                "This object indicates the EPON line profile name index."
            ::= { hwEponDeviceLineProfileInfoEntry 1 }

        hwEponDeviceLineProfileBindNum OBJECT-TYPE
            SYNTAX Integer32
            MAX-ACCESS read-only
            STATUS current
            DESCRIPTION
                "This object indicates the number of ONT bound with EPON line profile."
            ::= { hwEponDeviceLineProfileInfoEntry 2 }

        hwEponDeviceLineProfileFEC OBJECT-TYPE
            SYNTAX INTEGER {
                enable(1),
                disable(2),
                invalid(-1)
            }
            MAX-ACCESS read-write
            STATUS current
            DESCRIPTION
                "This object indicates the EPON line profile FEC switch.
                 Options:
                 1. enable (1)      - Enable the EPON line profile FEC switch
                 2. disable (2)     - Disable the EPON line profile FEC switch
                 3. invalid (-1)    - Indicates that the query fails or no information is detected
                "
            ::= { hwEponDeviceLineProfileInfoEntry 3 }

        hwEponDeviceLineProfileCommit OBJECT-TYPE
            SYNTAX INTEGER {
                commitExecute(1),
                invalid(-1)
            }
            MAX-ACCESS read-write
            STATUS current
            DESCRIPTION
                "This object indicates the EPON line profile configuration commit.
                 Options:
                 1. commitExecute(1)      - Execute the EPON line profile configuration commit
                 2. invalid(-1)           - Indicates that the query fails or no information is detected
                "
            ::= { hwEponDeviceLineProfileInfoEntry 4 }

        hwEponDeviceLineProfileRowStatus OBJECT-TYPE
            SYNTAX RowStatus
            MAX-ACCESS read-create
            STATUS current
            DESCRIPTION
                "The hwEponDeviceLineProfileRowStatus is used to create a new row
                 or to modify or delete an existing row in this table.
                 Options:
                 1. createAndGo(4) -create a new instance of a conceptual row
                 2. destroy(6)     -delete the instances associated with an existing conceptual row
                "
            ::= { hwEponDeviceLineProfileInfoEntry 5 }

        hwEponDeviceLineProfileTr069ManagementIpIndex OBJECT-TYPE
            SYNTAX Integer32
            MAX-ACCESS read-write
            STATUS current
            DESCRIPTION
                "The index of IP host which used by TR069.
                "
            ::= { hwEponDeviceLineProfileInfoEntry 6 }

--  Table hwEponDeviceLineProfLlidCfgTable
        hwEponDeviceLineProfLlidCfgTable OBJECT-TYPE
            SYNTAX SEQUENCE OF HwEponDeviceLineProfLlidCfgEntry
            MAX-ACCESS not-accessible
            STATUS current
            DESCRIPTION
                "This is the XPON line profile LLID config table. This table is used to configure epon LLID.
                 The index of this table is a combination of hwEponLineProfLlidCfgLineProfNameIndex,
                 and hwEponLineProfLlidCfgLlidIndex.
                "
            ::= { hwXponDeviceProfileObjects 42 }

        hwEponDeviceLineProfLlidCfgEntry OBJECT-TYPE
            SYNTAX HwEponDeviceLineProfLlidCfgEntry
            MAX-ACCESS not-accessible
            STATUS current
            DESCRIPTION
                "This is the XPON line profile LLID config table. This table is used to configure epon LLID.
                 The index of this entry is a combination of hwEponLineProfLlidCfgLineProfNameIndex,
                 and hwEponLineProfLlidCfgLlidIndex.
                "
            INDEX { hwEponLineProfLlidCfgLineProfNameIndex ,
                    hwEponLineProfLlidCfgLlidIndex}
            ::= { hwEponDeviceLineProfLlidCfgTable 1 }

        HwEponDeviceLineProfLlidCfgEntry ::=
            SEQUENCE {
                hwEponLineProfLlidCfgLineProfNameIndex            OCTET STRING,
                hwEponLineProfLlidCfgLlidIndex                    Integer32,
                hwEponLineProfLlidCfgCarTrafficTableId            Integer32,
                hwEponLineProfLlidCfgDbaProfileName               OCTET STRING,
                hwEponLineProfLlidCfgEncryptMode                  INTEGER,
                hwEponLineProfLlidCfgQueueSetIndex1ReportBitMap   Integer32,
                hwEponLineProfLlidCfgQueueSetIndex1Threshold      OCTET STRING,
                hwEponLineProfLlidCfgQueueSetIndex2ReportBitMap   Integer32,
                hwEponLineProfLlidCfgQueueSetIndex2Threshold      OCTET STRING,
                hwEponLineProfLlidCfgQueueSetIndex3ReportBitMap   Integer32,
                hwEponLineProfLlidCfgQueueSetIndex3Threshold      OCTET STRING,
                hwEponLineProfLlidCfgRowStatus                    RowStatus,
                hwEponLineProfLlidCfgCarTrafficTableName          OCTET STRING
            }

        hwEponLineProfLlidCfgLineProfNameIndex OBJECT-TYPE
            SYNTAX OCTET STRING (SIZE (1..32))
            MAX-ACCESS not-accessible
            STATUS current
            DESCRIPTION
                "This object indicates the XPON line profile name index."
            ::= { hwEponDeviceLineProfLlidCfgEntry 1 }

        hwEponLineProfLlidCfgLlidIndex OBJECT-TYPE
            SYNTAX Integer32 (0..1023)
            MAX-ACCESS not-accessible
            STATUS current
            DESCRIPTION
                "This object indicates the XPON line profile LLID config Llid index."
            ::= { hwEponDeviceLineProfLlidCfgEntry 2 }

        hwEponLineProfLlidCfgCarTrafficTableId OBJECT-TYPE
            SYNTAX Integer32 (1..1024 | 65534)
            MAX-ACCESS read-write
            STATUS current
            DESCRIPTION
                "This object indicates the XPON line profile LLID config car profile index(1~1024, 0xfffe-unconcern)."
            ::= { hwEponDeviceLineProfLlidCfgEntry 3 }

        hwEponLineProfLlidCfgDbaProfileName OBJECT-TYPE
            SYNTAX OCTET STRING (SIZE (0..33))
            MAX-ACCESS read-write
            STATUS current
            DESCRIPTION
                "This object indicates the XPON line profile LLID config DBA profile name."
            ::= { hwEponDeviceLineProfLlidCfgEntry 4 }

        hwEponLineProfLlidCfgEncryptMode OBJECT-TYPE
            SYNTAX INTEGER {
                aes128(1),
                triplechurning(2),
                off(3)
            }
            MAX-ACCESS read-write
            STATUS current
            DESCRIPTION
                "This object indicates the XPON line profile LLID config gem encryp mode.
                 Options:
                 1. aes128(1)               - Indicates that the XPON line profile LLID config gem encrypt mode is aes128
                 2. triplechurning(2)       - Indicates that the XPON line profile LLID config gem encrypt mode is triple churning
                 3. off(3)                  - Indicates that the XPON line profile LLID config gem encrypt mode is off
                "
            DEFVAL { off }
            ::= { hwEponDeviceLineProfLlidCfgEntry 5 }

        hwEponLineProfLlidCfgQueueSetIndex1ReportBitMap OBJECT-TYPE
            SYNTAX Integer32
            MAX-ACCESS read-write
            STATUS current
            DESCRIPTION
                "This object indicates the XPON line profile LLID config queue-set-1 report bitmap."
            ::= { hwEponDeviceLineProfLlidCfgEntry 6 }

        hwEponLineProfLlidCfgQueueSetIndex1Threshold OBJECT-TYPE
            SYNTAX OCTET STRING (SIZE (16))
            MAX-ACCESS read-write
            STATUS current
            DESCRIPTION
                "This object indicates the XPON line profile LLID config queue-set-1 threshold value."
            ::= { hwEponDeviceLineProfLlidCfgEntry 7 }

        hwEponLineProfLlidCfgQueueSetIndex2ReportBitMap OBJECT-TYPE
            SYNTAX Integer32
            MAX-ACCESS read-write
            STATUS current
            DESCRIPTION
                "This object indicates the XPON line profile LLID config queue-set-2 report bitmap."
            ::= { hwEponDeviceLineProfLlidCfgEntry 8 }

        hwEponLineProfLlidCfgQueueSetIndex2Threshold OBJECT-TYPE
            SYNTAX OCTET STRING (SIZE (16))
            MAX-ACCESS read-write
            STATUS current
            DESCRIPTION
                "This object indicates the XPON line profile LLID config queue-set-2 threshold value."
            ::= { hwEponDeviceLineProfLlidCfgEntry 9 }

        hwEponLineProfLlidCfgQueueSetIndex3ReportBitMap OBJECT-TYPE
            SYNTAX Integer32
            MAX-ACCESS read-write
            STATUS current
            DESCRIPTION
                "This object indicates the XPON line profile LLID config queue-set-3 report bitmap."
            ::= { hwEponDeviceLineProfLlidCfgEntry 10 }

        hwEponLineProfLlidCfgQueueSetIndex3Threshold OBJECT-TYPE
            SYNTAX OCTET STRING (SIZE (16))
            MAX-ACCESS read-write
            STATUS current
            DESCRIPTION
                "This object indicates the XPON line profile LLID config queue-set-3 threshold value."
            ::= { hwEponDeviceLineProfLlidCfgEntry 11 }

        hwEponLineProfLlidCfgRowStatus OBJECT-TYPE
            SYNTAX RowStatus
            MAX-ACCESS read-create
            STATUS current
            DESCRIPTION
                "The hwEponLineProfLlidCfgRowStatus is used to create a new row
                 or to modify or delete an existing row in this table.
                 Options:
                 1. createAndGo(4) -create a new instance of a conceptual row
                 2. destroy(6)     -delete the instances associated with an existing conceptual row
                "
            ::= { hwEponDeviceLineProfLlidCfgEntry 12 }

        hwEponLineProfLlidCfgCarTrafficTableName OBJECT-TYPE
            SYNTAX OCTET STRING  (SIZE (0..32))
            MAX-ACCESS read-write
            STATUS current
            DESCRIPTION
                "This object indicates the XPON line profile LLID config car profile name."
            ::= { hwEponDeviceLineProfLlidCfgEntry 13 }

--  Table hwEponDeviceSrvProfileInfoTable
        hwEponDeviceSrvProfileInfoTable OBJECT-TYPE
            SYNTAX SEQUENCE OF HwEponDeviceSrvProfileInfoEntry
            MAX-ACCESS not-accessible
            STATUS current
            DESCRIPTION
                "This is the EPON service profile table.
                 The index of this table is hwEponDeviceSrvProfileInfoNameIndex.
                "
            ::= { hwXponDeviceProfileObjects 43 }

        hwEponDeviceSrvProfileInfoEntry OBJECT-TYPE
            SYNTAX HwEponDeviceSrvProfileInfoEntry
            MAX-ACCESS not-accessible
            STATUS current
            DESCRIPTION
                "This is the EPON service profile table.
                 The index of this entry is hwEponDeviceSrvProfileInfoNameIndex.
                "
            INDEX { IMPLIED hwEponDeviceSrvProfileInfoNameIndex }
            ::= { hwEponDeviceSrvProfileInfoTable 1 }

        HwEponDeviceSrvProfileInfoEntry ::=
            SEQUENCE {
                hwEponDeviceSrvProfileInfoNameIndex        OCTET STRING,
                hwEponDeviceSrvProfileBindNum              Integer32,
                hwEponDeviceSrvProfileCommit               INTEGER,
                hwEponDeviceSrvProfileRowStatus            RowStatus
            }

        hwEponDeviceSrvProfileInfoNameIndex OBJECT-TYPE
            SYNTAX OCTET STRING (SIZE (1..32))
            MAX-ACCESS not-accessible
            STATUS current
            DESCRIPTION
                "This object indicates the EPON line profile name index."
            ::= { hwEponDeviceSrvProfileInfoEntry 1 }

        hwEponDeviceSrvProfileBindNum OBJECT-TYPE
            SYNTAX Integer32
            MAX-ACCESS read-only
            STATUS current
            DESCRIPTION
                "This object indicates the number of ONT bound with EPON service profile."
            ::= { hwEponDeviceSrvProfileInfoEntry 2 }

        hwEponDeviceSrvProfileCommit OBJECT-TYPE
            SYNTAX INTEGER {
                commitExecute(1),
                invalid(-1)
            }
            MAX-ACCESS read-write
            STATUS current
            DESCRIPTION
                "This object indicates the EPON service profile configuration commit.
                 Options:
                 1. commitExecute(1)      - Execute the EPON service profile configuration commit
                 2. invalid(-1)           - Indicates that the query fails or no information is detected
                "
            ::= { hwEponDeviceSrvProfileInfoEntry 3 }

        hwEponDeviceSrvProfileRowStatus OBJECT-TYPE
            SYNTAX RowStatus
            MAX-ACCESS read-create
            STATUS current
            DESCRIPTION
                "The hwEponDeviceSrvProfileRowStatus is used to create a new row
                 or to modify or delete an existing row in this table.
                 Options:
                 1. createAndGo(4) -create a new instance of a conceptual row
                 2. destroy(6)     -delete the instances associated with an existing conceptual row
                "
            ::= { hwEponDeviceSrvProfileInfoEntry 4 }

--  Table hwEponDeviceSrvProfileOntCfgTable
        hwEponDeviceSrvProfileOntCfgTable OBJECT-TYPE
            SYNTAX SEQUENCE OF HwEponDeviceSrvProfileOntCfgEntry
            MAX-ACCESS not-accessible
            STATUS current
            DESCRIPTION
                "This is the EPON service profile ont config table.
                 The index of this table is hwEponDeviceSrvProfOntCfgSrvProfNameIndex.
                "
            ::= { hwXponDeviceProfileObjects 44 }

        hwEponDeviceSrvProfileOntCfgEntry OBJECT-TYPE
            SYNTAX HwEponDeviceSrvProfileOntCfgEntry
            MAX-ACCESS not-accessible
            STATUS current
            DESCRIPTION
                "This is the EPON service profile ont config table.
                 The index of this entry is hwEponDeviceSrvProfOntCfgSrvProfNameIndex.
                "
            INDEX { IMPLIED hwEponDeviceSrvProfOntCfgSrvProfNameIndex }
            ::= { hwEponDeviceSrvProfileOntCfgTable 1 }

        HwEponDeviceSrvProfileOntCfgEntry ::=
            SEQUENCE {
                hwEponDeviceSrvProfOntCfgSrvProfNameIndex        OCTET STRING,
                hwEponDeviceSrvProfilePotsNum                    Integer32,
                hwEponDeviceSrvProfileEthNum                     Integer32,
                hwEponDeviceSrvProfileTdmPortNum                 Integer32,
                hwEponDeviceSrvProfileTdmPortType                INTEGER,
                hwEponDeviceSrvProfileMulticastMode              INTEGER,
                hwEponDeviceSrvProfileMulticastQuickLeaveSwitch  INTEGER,
                hwEponDeviceSrvProfileRingCheckSwitch            INTEGER,
                hwEponDeviceSrvProfileRingCheckAutoShutdownSwitch INTEGER,
                hwEponDeviceSrvProfileMaxNumOfAdapPotsPort       Integer32,
                hwEponDeviceSrvProfileMaxNumOfAdapEthPort        Integer32
            }

        hwEponDeviceSrvProfOntCfgSrvProfNameIndex OBJECT-TYPE
            SYNTAX OCTET STRING (SIZE (1..32))
            MAX-ACCESS not-accessible
            STATUS current
            DESCRIPTION
                "This object indicates the EPON service profile name index."
            ::= { hwEponDeviceSrvProfileOntCfgEntry 1 }

        hwEponDeviceSrvProfilePotsNum OBJECT-TYPE
            SYNTAX Integer32
            MAX-ACCESS read-write
            STATUS current
            DESCRIPTION
                "This object indicates the XPON service profile pots port number.
                A special value of 0xFE (254) indicates the number
                of port is adaptive."
            ::= { hwEponDeviceSrvProfileOntCfgEntry 2 }

        hwEponDeviceSrvProfileEthNum OBJECT-TYPE
            SYNTAX Integer32
            MAX-ACCESS read-write
            STATUS current
            DESCRIPTION
                "This object indicates the XPON service profile eth port number.
                 A special value of 0xFE (254) indicates the number
                 of port is adaptive."
            ::= { hwEponDeviceSrvProfileOntCfgEntry 3 }

        hwEponDeviceSrvProfileTdmPortNum OBJECT-TYPE
            SYNTAX Integer32
            MAX-ACCESS read-write
            STATUS current
            DESCRIPTION
                "This object indicates the XPON service profile tdm port number."
            ::= { hwEponDeviceSrvProfileOntCfgEntry 4 }

        hwEponDeviceSrvProfileTdmPortType OBJECT-TYPE
            SYNTAX INTEGER {
                t1(13),
                e1(14),
                invalid(-1)
            }
            MAX-ACCESS read-write
            STATUS current
            DESCRIPTION
                "This object indicates the XPON service profile tdm port type.
                 Options:
                 1. t1(13)             - T1
                 2. e1(14)             - E1
                 3. invalid(-1)        - Indicates that the query fails or no information is detected
                "
            ::= { hwEponDeviceSrvProfileOntCfgEntry 5 }

        hwEponDeviceSrvProfileMulticastMode OBJECT-TYPE
            SYNTAX INTEGER {
                ctc(1),
                igmpsnooping(2),
                transparent(3),
                invalid(-1)
            }
            MAX-ACCESS read-write
            STATUS current
            DESCRIPTION
                "This object indicates the XPON service profile multicast mode.
                 Options:
                 1. ctc(1)             - Indicates that the XPON service profile multicast mode is CTC
                 2. igmpsnooping(2)    - Indicates that the XPON service profile multicast mode is igmp snooping
                 3. transparent(3)     - Indicates that the XPON service profile multicast mode is transparent
                 4. invalid(-1)        - Indicates that the query fails or no information is detected
                "
            ::= { hwEponDeviceSrvProfileOntCfgEntry 6 }

        hwEponDeviceSrvProfileMulticastQuickLeaveSwitch OBJECT-TYPE
            SYNTAX INTEGER {
                enable(1),
                disable(2),
                unconcern(254)
            }
            MAX-ACCESS read-write
            STATUS current
            DESCRIPTION
                "This object indicates the XPON service profile multicast quick leave switch.
                 Options:
                 1. enable(1)       - Enable the XPON service profile multicast quick leave switch
                 2. disable(2)      - Disable the XPON service profile multicast quick leave switch
                 3. unconcern(254)  - Indicates that the query fails or no information is detected
                "
            ::= { hwEponDeviceSrvProfileOntCfgEntry 7 }

        hwEponDeviceSrvProfileRingCheckSwitch OBJECT-TYPE
            SYNTAX INTEGER {
                enable(1),
                disable(2),
                unconcern(254)
            }
            MAX-ACCESS read-write
            STATUS current
            DESCRIPTION
                "This object indicates the XPON service profile ring check function switch.
                 Options:
                 1. enable(1)       - Enable the XPON service profile ring check function switch
                 2. disable(2)      - Disable the XPON service profile ring check function switch
                 3. unconcern(254)  - Indicates that the query fails or no information is detected
                "
            ::= { hwEponDeviceSrvProfileOntCfgEntry 8 }

        hwEponDeviceSrvProfileRingCheckAutoShutdownSwitch OBJECT-TYPE
            SYNTAX INTEGER {
                enable(1),
                disable(2),
                unconcern(254)
            }
            MAX-ACCESS read-write
            STATUS current
            DESCRIPTION
                "This object indicates the XPON service profile ring check auto shutdown function switch
                 Options:
                 1. enable(1)       - Indicates that the XPON service profile ring check auto shutdown switch enable.
                 2. disable(2)      - Indicates that the XPON service profile ring check auto shutdown switch disable.
                 3. unconcern(254)  - Indicates that the XPON service profile ring check auto shutdown switch unconcern.
                "
            ::= { hwEponDeviceSrvProfileOntCfgEntry 9 }

        hwEponDeviceSrvProfileMaxNumOfAdapPotsPort OBJECT-TYPE
            SYNTAX Integer32
            MAX-ACCESS read-write
            STATUS current
            DESCRIPTION
                "This object indicates the max number of adaptive pots ports.
                 Range: 1-32. 32 is default value."
            ::= { hwEponDeviceSrvProfileOntCfgEntry 10}

        hwEponDeviceSrvProfileMaxNumOfAdapEthPort OBJECT-TYPE
            SYNTAX Integer32
            MAX-ACCESS read-write
            STATUS current
            DESCRIPTION
                "This object indicates the max number of adaptive eth ports.
                 Range: 1-24. 8 is default value."
            ::= { hwEponDeviceSrvProfileOntCfgEntry 11}

--  Table hwEponDeviceSrvProfMulticastVlanCfgTable
        hwEponDeviceSrvProfMulticastVlanCfgTable OBJECT-TYPE
            SYNTAX SEQUENCE OF HwEponDeviceSrvProfMulticastVlanCfgEntry
            MAX-ACCESS not-accessible
            STATUS current
            DESCRIPTION
                "This is the EPON service profile multicast vlan config table.
                 The index of this table is a combination of hwEponDeviceSrvProfMulticastVlanCfgSrvProfNameIndex,
                 hwEponDeviceSrvProfMulticastVlanCfgOntPhyType, hwEponDeviceSrvProfMulticastVlanCfgOntPhyIndex
                 and hwEponDeviceSrvProfMulticastVlanCfgMulticastVlan.
                "
            ::= { hwXponDeviceProfileObjects 45 }

        hwEponDeviceSrvProfMulticastVlanCfgEntry OBJECT-TYPE
            SYNTAX HwEponDeviceSrvProfMulticastVlanCfgEntry
            MAX-ACCESS not-accessible
            STATUS current
            DESCRIPTION
                "This is the EPON service profile multicast vlan config table.
                 The index of this entry is a combination of hwEponDeviceSrvProfMulticastVlanCfgSrvProfNameIndex,
                 hwEponDeviceSrvProfMulticastVlanCfgOntPhyType, hwEponDeviceSrvProfMulticastVlanCfgOntPhyIndex
                 and hwEponDeviceSrvProfMulticastVlanCfgMulticastVlan.
                "
            INDEX { hwEponDeviceSrvProfMulticastVlanCfgSrvProfNameIndex, hwEponDeviceSrvProfMulticastVlanCfgOntPhyType,
                    hwEponDeviceSrvProfMulticastVlanCfgOntPhyIndex, hwEponDeviceSrvProfMulticastVlanCfgMulticastVlan}
            ::= { hwEponDeviceSrvProfMulticastVlanCfgTable 1 }

        HwEponDeviceSrvProfMulticastVlanCfgEntry ::=
            SEQUENCE {
                hwEponDeviceSrvProfMulticastVlanCfgSrvProfNameIndex             OCTET STRING,
                hwEponDeviceSrvProfMulticastVlanCfgOntPhyType                   INTEGER,
                hwEponDeviceSrvProfMulticastVlanCfgOntPhyIndex                  Integer32,
                hwEponDeviceSrvProfMulticastVlanCfgMulticastVlan                Integer32,
                hwEponDeviceSrvProfMulticastVlanCfgRowStatus                    RowStatus,
                hwEponDeviceSrvProfMulticastVlanCfgTranslatedVlan               Integer32
            }

        hwEponDeviceSrvProfMulticastVlanCfgSrvProfNameIndex OBJECT-TYPE
            SYNTAX OCTET STRING (SIZE(1..32))
            MAX-ACCESS not-accessible
            STATUS current
            DESCRIPTION
                "This object indicates the XPON service profile name index."
            ::= { hwEponDeviceSrvProfMulticastVlanCfgEntry 1 }

        hwEponDeviceSrvProfMulticastVlanCfgOntPhyType OBJECT-TYPE
            SYNTAX INTEGER {
                t1(13),
                e1(14),
                fe(24),
                ge(34),
                moca(46),
                eth(47),
                iphost(50)
            }
            MAX-ACCESS not-accessible
            STATUS current
            DESCRIPTION
                "This object indicates the port type of the ONT.
                 Options:
                 1. t1(13)             - T1
                 2. e1(14)             - E1
                 3. fe(24)             - FE
                 4. ge(34)             - GE
                 5. moca(46)           - MOCA
                 6. eth(47)            - ETH
                 7. iphost(50)         - IPHOST
                "
            ::= { hwEponDeviceSrvProfMulticastVlanCfgEntry 2 }

        hwEponDeviceSrvProfMulticastVlanCfgOntPhyIndex OBJECT-TYPE
            SYNTAX Integer32
            MAX-ACCESS not-accessible
            STATUS current
            DESCRIPTION
                "This object indicates the port index of the ONT"
            ::= { hwEponDeviceSrvProfMulticastVlanCfgEntry 3 }

        hwEponDeviceSrvProfMulticastVlanCfgMulticastVlan OBJECT-TYPE
            SYNTAX Integer32 (1..4093)
            MAX-ACCESS not-accessible
            STATUS current
            DESCRIPTION
                "This object indicates the EPON service profile multicast vlan."
            ::= { hwEponDeviceSrvProfMulticastVlanCfgEntry 4 }

        hwEponDeviceSrvProfMulticastVlanCfgRowStatus OBJECT-TYPE
            SYNTAX RowStatus
            MAX-ACCESS read-create
            STATUS current
            DESCRIPTION
                "The hwEponDeviceSrvProfMulticastVlanCfgRowStatus is used to create a new row
                 or to modify or delete an existing row in this table.
                 Options:
                 1. createAndGo(4) -create a new instance of a conceptual row
                 2. destroy(6)     -delete the instances associated with an existing conceptual row
                "
            ::= { hwEponDeviceSrvProfMulticastVlanCfgEntry 5 }

        hwEponDeviceSrvProfMulticastVlanCfgTranslatedVlan OBJECT-TYPE
            SYNTAX Integer32 (-1 | 1..4093)
            MAX-ACCESS read-write
            STATUS current
            DESCRIPTION
                "This object indicates the EPON service profile multicast translated VLAN."
            ::= { hwEponDeviceSrvProfMulticastVlanCfgEntry 6 }

--  Table hwEponDeviceSrvProfPortVlanCfgTable
        hwEponDeviceSrvProfPortVlanCfgTable OBJECT-TYPE
            SYNTAX SEQUENCE OF HwEponDeviceSrvProfPortVlanCfgEntry
            MAX-ACCESS not-accessible
            STATUS current
            DESCRIPTION
                "This is the EPON service profile port vlan config table.
                 The index of this table is a combination of hwEponDeviceSrvProfPortVlanCfgSrvProfNameIndex,
                 hwEponDeviceSrvProfPortVlanCfgOntPhyType, hwEponDeviceSrvProfPortVlanCfgOntPhyIndex
                 and hwEponDeviceSrvProfPortVlanCfgPortCVlan.
                "
            ::= { hwXponDeviceProfileObjects 46 }

        hwEponDeviceSrvProfPortVlanCfgEntry OBJECT-TYPE
            SYNTAX HwEponDeviceSrvProfPortVlanCfgEntry
            MAX-ACCESS not-accessible
            STATUS current
            DESCRIPTION
                "This is the EPON service profile port vlan config table.
                 The index of this entry is a combination of hwEponDeviceSrvProfPortVlanCfgSrvProfNameIndex,
                 hwEponDeviceSrvProfPortVlanCfgOntPhyType, hwEponDeviceSrvProfPortVlanCfgOntPhyIndex
                 and hwEponDeviceSrvProfPortVlanCfgPortCVlan.
                "
            INDEX { hwEponDeviceSrvProfPortVlanCfgSrvProfNameIndex, hwEponDeviceSrvProfPortVlanCfgOntPhyType,
                    hwEponDeviceSrvProfPortVlanCfgOntPhyIndex, hwEponDeviceSrvProfPortVlanCfgPortCVlan}
            ::= { hwEponDeviceSrvProfPortVlanCfgTable 1 }

        HwEponDeviceSrvProfPortVlanCfgEntry ::=
            SEQUENCE {
                hwEponDeviceSrvProfPortVlanCfgSrvProfNameIndex              OCTET STRING,
                hwEponDeviceSrvProfPortVlanCfgOntPhyType                    INTEGER,
                hwEponDeviceSrvProfPortVlanCfgOntPhyIndex                   Integer32,
                hwEponDeviceSrvProfPortVlanCfgPortVlanType                  INTEGER,
                hwEponDeviceSrvProfPortVlanCfgPortCVlan                     Integer32,
                hwEponDeviceSrvProfPortVlanCfgPortSVlan                     Integer32,
                hwEponDeviceSrvProfPortVlanCfgRowStatus                     RowStatus
            }

        hwEponDeviceSrvProfPortVlanCfgSrvProfNameIndex OBJECT-TYPE
            SYNTAX OCTET STRING (SIZE(1..32))
            MAX-ACCESS not-accessible
            STATUS current
            DESCRIPTION
                "This object indicates the XPON service profile name index."
            ::= { hwEponDeviceSrvProfPortVlanCfgEntry 1 }

        hwEponDeviceSrvProfPortVlanCfgOntPhyType OBJECT-TYPE
            SYNTAX INTEGER {
                t1(13),
                e1(14),
                fe(24),
                ge(34),
                moca(46),
                eth(47),
                iphost(50)
            }
            MAX-ACCESS not-accessible
            STATUS current
            DESCRIPTION
                "This object indicates the port type of the ONT.
                 Options:
                 1. t1(13)             - T1
                 2. e1(14)             - E1
                 3. fe(24)             - FE
                 4. ge(34)             - GE
                 5. moca(46)           - MOCA
                 6. eth(47)            - ETH
                 7. iphost(50)         - IPHOST
                "
            ::= { hwEponDeviceSrvProfPortVlanCfgEntry 2 }

        hwEponDeviceSrvProfPortVlanCfgOntPhyIndex OBJECT-TYPE
            SYNTAX Integer32
            MAX-ACCESS not-accessible
            STATUS current
            DESCRIPTION
                "This object indicates the port index of the ONT."
            ::= { hwEponDeviceSrvProfPortVlanCfgEntry 3 }

        hwEponDeviceSrvProfPortVlanCfgPortVlanType OBJECT-TYPE
            SYNTAX INTEGER {
                transparent(1),
                translation(2),
                invalid(-1)
            }
            MAX-ACCESS read-write
            STATUS current
            DESCRIPTION
                "This object indicates the XPON service profile port vlan type.
                 Options:
                 1. transparent(1)       - Indicates that the XPON service profile port vlan type is transparent
                 2. translation(2)       - Indicates that the XPON service profile port vlan type is translation
                 3. invalid(-1)          - Indicates that the query fails or no information is detected
                "
            ::= { hwEponDeviceSrvProfPortVlanCfgEntry 4 }

        hwEponDeviceSrvProfPortVlanCfgPortCVlan OBJECT-TYPE
            SYNTAX Integer32 (1..4094 | 65534)
            MAX-ACCESS not-accessible
            STATUS current
            DESCRIPTION
                "This object indicates the EPON service profile port customer vlan.
                 The value 65534 indicates that the vlan mode of ont's port is transparent.
                "
            ::= { hwEponDeviceSrvProfPortVlanCfgEntry 5 }

        hwEponDeviceSrvProfPortVlanCfgPortSVlan OBJECT-TYPE
            SYNTAX Integer32 (-1 | 1..4094)
            MAX-ACCESS read-write
            STATUS current
            DESCRIPTION
                "This object indicates the EPON service profile port service vlan.
                 The value(-1) is invalid value.
                "
            ::= { hwEponDeviceSrvProfPortVlanCfgEntry 6 }

        hwEponDeviceSrvProfPortVlanCfgRowStatus OBJECT-TYPE
            SYNTAX RowStatus
            MAX-ACCESS read-create
            STATUS current
            DESCRIPTION
                "The hwEponDeviceSrvProfPortVlanCfgRowStatus is used to create a new row
                 or to modify or delete an existing row in this table.
                 Options:
                 1. createAndGo(4) -create a new instance of a conceptual row
                 2. destroy(6)     -delete the instances associated with an existing conceptual row
                "
            ::= { hwEponDeviceSrvProfPortVlanCfgEntry 7 }

--  Table hwEponDeviceSrvProfOntPortCfgTable
        hwEponDeviceSrvProfOntPortCfgTable OBJECT-TYPE
            SYNTAX SEQUENCE OF HwEponDeviceSrvProfOntPortCfgEntry
            MAX-ACCESS not-accessible
            STATUS current
            DESCRIPTION
                "This is the EPON service profile ont port config table.
                 The index of this table is a combination of hwEponDeviceSrvProfOntPortCfgSrvProfNameIndex,
                 hwEponDeviceSrvProfOntPortCfgOntPhyType and hwEponDeviceSrvProfOntPortCfgOntPhyIndex.
                "
            ::= { hwXponDeviceProfileObjects 47 }

        hwEponDeviceSrvProfOntPortCfgEntry OBJECT-TYPE
            SYNTAX HwEponDeviceSrvProfOntPortCfgEntry
            MAX-ACCESS not-accessible
            STATUS current
            DESCRIPTION
                "This is the EPON service profile ont port config table.
                 The index of this entry is a combination of hwEponDeviceSrvProfOntPortCfgSrvProfNameIndex,
                 hwEponDeviceSrvProfOntPortCfgOntPhyType and hwEponDeviceSrvProfOntPortCfgOntPhyIndex.
                "
            INDEX { hwEponDeviceSrvProfOntPortCfgSrvProfNameIndex, hwEponDeviceSrvProfOntPortCfgOntPhyType,
                    hwEponDeviceSrvProfOntPortCfgOntPhyIndex}
            ::= { hwEponDeviceSrvProfOntPortCfgTable 1 }

        HwEponDeviceSrvProfOntPortCfgEntry ::=
            SEQUENCE {
                hwEponDeviceSrvProfOntPortCfgSrvProfNameIndex                   OCTET STRING,
                hwEponDeviceSrvProfOntPortCfgOntPhyType                         INTEGER,
                hwEponDeviceSrvProfOntPortCfgOntPhyIndex                        Integer32,
                hwEponDeviceSrvProfOntPortCfgUpStreamCarTrafficTableId          Integer32,
                hwEponDeviceSrvProfOntPortCfgDownStreamCarTrafficTableId        Integer32,
                hwEponDeviceSrvProfOntPortCfgMaxMacAddressNum                   Integer32,
                hwEponDeviceSrvProfOntPortCfgClassProfileIndex                  Integer32,
                hwEponDeviceSrvProfOntPortCfgMulticastStripSwitch               INTEGER,
                hwEponDeviceSrvProfOntPortCfgMaxGroupNum                        Integer32,
                hwEponDeviceSrvProfOntPortCfgUpStreamCarTrafficTableName        OCTET STRING,
                hwEponDeviceSrvProfOntPortCfgDownStreamCarTrafficTableName      OCTET STRING
             }

        hwEponDeviceSrvProfOntPortCfgSrvProfNameIndex OBJECT-TYPE
            SYNTAX OCTET STRING (SIZE(1..32))
            MAX-ACCESS not-accessible
            STATUS current
            DESCRIPTION
                "This object indicates the XPON service profile name index."
            ::= { hwEponDeviceSrvProfOntPortCfgEntry 1 }

        hwEponDeviceSrvProfOntPortCfgOntPhyType OBJECT-TYPE
            SYNTAX INTEGER {
                t1(13),
                e1(14),
                fe(24),
                ge(34),
                moca(46),
                eth(47),
                iphost(50)
            }
            MAX-ACCESS not-accessible
            STATUS current
            DESCRIPTION
                "This object indicates the port type of the ONT.
                 Options:
                 1. t1(13)             - T1
                 2. e1(14)             - E1
                 3. fe(24)             - FE
                 4. ge(34)             - GE
                 5. moca(46)           - MOCA
                 6. eth(47)            - ETH
                 7. iphost(50)         - IPHOST
                "
            ::= { hwEponDeviceSrvProfOntPortCfgEntry 2 }

        hwEponDeviceSrvProfOntPortCfgOntPhyIndex OBJECT-TYPE
            SYNTAX Integer32
            MAX-ACCESS not-accessible
            STATUS current
            DESCRIPTION
                "This object indicates the port index of the ONT."
            ::= { hwEponDeviceSrvProfOntPortCfgEntry 3 }

        hwEponDeviceSrvProfOntPortCfgUpStreamCarTrafficTableId OBJECT-TYPE
            SYNTAX Integer32
            MAX-ACCESS read-write
            STATUS current
            DESCRIPTION
                "This object indicates the XPON service profile ont port up-stream car profile id."
            ::= { hwEponDeviceSrvProfOntPortCfgEntry 4 }

        hwEponDeviceSrvProfOntPortCfgDownStreamCarTrafficTableId OBJECT-TYPE
            SYNTAX Integer32
            MAX-ACCESS read-write
            STATUS current
            DESCRIPTION
                "This object indicates the XPON service profile ont port down-stream car profile id."
            ::= { hwEponDeviceSrvProfOntPortCfgEntry 5 }

        hwEponDeviceSrvProfOntPortCfgMaxMacAddressNum OBJECT-TYPE
            SYNTAX Integer32
            MAX-ACCESS read-write
            STATUS current
            DESCRIPTION
                "This object indicates the XPON service profile ont port max mac-address number."
            ::= { hwEponDeviceSrvProfOntPortCfgEntry 6 }

        hwEponDeviceSrvProfOntPortCfgClassProfileIndex OBJECT-TYPE
            SYNTAX Integer32
            MAX-ACCESS read-write
            STATUS current
            DESCRIPTION
                "This object indicates the XPON service profile port config class profile index."
            ::= { hwEponDeviceSrvProfOntPortCfgEntry 7 }

        hwEponDeviceSrvProfOntPortCfgMulticastStripSwitch OBJECT-TYPE
            SYNTAX INTEGER {
                tag(1),
                untag(2),
                translation(3),
                invalid(-1)
            }
            MAX-ACCESS read-write
            STATUS current
            DESCRIPTION
                "This object indicates the XPON service profile multicast strip switch.
                 Options:
                 1. tag(1)              - Indicates that the XPON service profile multicast strip switch is tag
                 2. untag(2)            - Indicates that the XPON service profile multicast strip switch is untag
                 3. translation(3)      - Indicates that the XPON service profile multicast strip switch is translation
                 4. invalid(-1)         - Indicates that the query fails or no information is detected
                "
            ::= { hwEponDeviceSrvProfOntPortCfgEntry 8 }

        hwEponDeviceSrvProfOntPortCfgMaxGroupNum OBJECT-TYPE
            SYNTAX Integer32
            MAX-ACCESS read-write
            STATUS current
            DESCRIPTION
                "This object indicates the max multicast group num on port."
            ::= { hwEponDeviceSrvProfOntPortCfgEntry 9 }

        hwEponDeviceSrvProfOntPortCfgUpStreamCarTrafficTableName OBJECT-TYPE
            SYNTAX OCTET STRING  (SIZE (0..32))
            MAX-ACCESS read-write
            STATUS current
            DESCRIPTION
                "This object indicates the XPON service profile ont port up-stream car profile name."
            ::= { hwEponDeviceSrvProfOntPortCfgEntry 10 }

        hwEponDeviceSrvProfOntPortCfgDownStreamCarTrafficTableName OBJECT-TYPE
            SYNTAX OCTET STRING  (SIZE (0..32))
            MAX-ACCESS read-write
            STATUS current
            DESCRIPTION
                "This object indicates the XPON service profile ont port down-stream car profile name."
            ::= { hwEponDeviceSrvProfOntPortCfgEntry 11 }

--  Table hwGponDeviceLineProfileInfoTable
        hwGponDeviceLineProfileInfoTable OBJECT-TYPE
            SYNTAX SEQUENCE OF HwGponDeviceLineProfileInfoEntry
            MAX-ACCESS not-accessible
            STATUS current
            DESCRIPTION
                "This is the GPON line profile table. This table is used to create a GPON line profile.
                 The index of this table is hwGponDeviceLineProfileInfoNameIndex.
                "
            ::= { hwXponDeviceProfileObjects 61 }

        hwGponDeviceLineProfileInfoEntry OBJECT-TYPE
            SYNTAX HwGponDeviceLineProfileInfoEntry
            MAX-ACCESS not-accessible
            STATUS current
            DESCRIPTION
                "This is the GPON line profile table. This table is used to create a GPON line profile.
                 The index of this entry is hwGponDeviceLineProfileInfoNameIndex.
                "
            INDEX { IMPLIED hwGponDeviceLineProfileInfoNameIndex }
            ::= { hwGponDeviceLineProfileInfoTable 1 }

        HwGponDeviceLineProfileInfoEntry ::=
            SEQUENCE {
                hwGponDeviceLineProfileInfoNameIndex                    OCTET STRING,
                hwGponDeviceLineProfileBindNum                          Integer32,
                hwGponDeviceLineProfileUpFEC                            INTEGER,
                hwGponDeviceLineProfileMappingMode                      INTEGER,
                hwGponDeviceLineProfileQosMode                          INTEGER,
                hwGponDeviceLineProfileCommit                           INTEGER,
                hwGponDeviceLineProfileRowStatus                        RowStatus,
                hwGponDeviceLineProfileOMCCEncrypt                      INTEGER,
                hwGponDeviceLineProfileTr069ManagementSwitch            INTEGER,
                hwGponDeviceLineProfileCommitResult                     INTEGER,
                hwGponDeviceLineProfileTr069ManagementIpIndex           Integer32
            }
        hwGponDeviceLineProfileInfoNameIndex OBJECT-TYPE
            SYNTAX OCTET STRING (SIZE (1..32))
            MAX-ACCESS not-accessible
            STATUS current
            DESCRIPTION
                "This object indicates the GPON line profile name index."
            ::= { hwGponDeviceLineProfileInfoEntry 1 }

        hwGponDeviceLineProfileBindNum OBJECT-TYPE
            SYNTAX Integer32
            MAX-ACCESS read-only
            STATUS current
            DESCRIPTION
                "This object indicates the  number of ONT bound with GPON line profile."
            ::= { hwGponDeviceLineProfileInfoEntry 2 }

        hwGponDeviceLineProfileUpFEC OBJECT-TYPE
            SYNTAX INTEGER {
                enable(1),
                disable(2)
            }
            MAX-ACCESS read-write
            STATUS current
            DESCRIPTION
                "This object indicates the GPON line profile upstream FEC.
                 Options:
                 1. enable (1)      - Enable the GPON line profile upstream FEC
                 2. disable (2)     - Disable the GPON line profile upstream FEC
                "
            ::= { hwGponDeviceLineProfileInfoEntry 3 }

        hwGponDeviceLineProfileMappingMode OBJECT-TYPE
            SYNTAX INTEGER {
                vlan(1),
                pri8021p(2),
                vlanpri(3),
                port(4),
                vlanport(5),
                portpri(6),
                vlanpriport(7),
                e1t1(8),
                iptos(9),
                vlaniptos(10),
                invalid(-1)
            }
            MAX-ACCESS read-write
            STATUS current
            DESCRIPTION
                "This object indicates the GPON line profile mapping mode.
                 Options:
                 1. vlan(1)            - The GPON line profile mapping mode is vlan
                 2. pri8021p(2)        - The GPON line profile mapping mode is 802.1p
                 3. vlanpri(3)         - The GPON line profile mapping mode is vlan and 802.1p
                 4. port(4)            - The GPON line profile mapping mode is port
                 5. vlanport(5)        - The GPON line profile mapping mode is vlan and port
                 6. portpri(6)         - The GPON line profile mapping mode is port and 802.1p
                 7. vlanpriport(7)     - The GPON line profile mapping mode is vlan, port and 802.1p
                 8. e1t1(8)            - The GPON line profile mapping mode is the port of e1 and t1
                 9. iptos(9)           - The GPON line profile mapping mode is iptos
                 10. vlaniptos(10)     - The GPON line profile mapping mode is vlan and iptos
                 11. invalid(-1)       - Indicates that the query fails or no information is detected
                "
            ::= { hwGponDeviceLineProfileInfoEntry 4 }

        hwGponDeviceLineProfileQosMode OBJECT-TYPE
            SYNTAX INTEGER {
                pq(1),
                gemcar(2),
                flowcar(3)
            }
            MAX-ACCESS read-write
            STATUS current
            DESCRIPTION
                "This object indicates the GPON line profile QOS mode.
                 Options:
                 1. pq(1)              - The GPON line profile QOS mode is PQ
                 2. gemcar(2)          - The GPON line profile QOS mode is the gemcar
                 3. flowcar(3)         - The GPON line profile QOS mode is the flowcar
                "
            ::= { hwGponDeviceLineProfileInfoEntry 5 }

        hwGponDeviceLineProfileCommit OBJECT-TYPE
            SYNTAX INTEGER {
                commitExecute(1),
                clearResult(2),
                invalid(-1)
            }
            MAX-ACCESS read-write
            STATUS current
            DESCRIPTION
                "This object indicates the GPON Line Profile Configuration Commit.
                 Options:
                 1. commitExecute(1)      - Execute the GPON line profile configuration commit
                 2. clearResult(2)        - Clear the commit result
                 3. invalid(-1)           - Indicates that the query fails or no information is detected
                "
            ::= { hwGponDeviceLineProfileInfoEntry 6 }

        hwGponDeviceLineProfileRowStatus OBJECT-TYPE
            SYNTAX RowStatus
            MAX-ACCESS read-create
            STATUS current
            DESCRIPTION
                "The hwGponDeviceLineProfileRowStatus is used to create a new row
                 or to modify or delete an existing row in this table.
                 Options:
                 1. createAndGo(4) -create a new instance of a conceptual row
                 2. destroy(6)     -delete the instances associated with an existing conceptual row
                "
            ::= { hwGponDeviceLineProfileInfoEntry 7 }

        hwGponDeviceLineProfileOMCCEncrypt OBJECT-TYPE
            SYNTAX INTEGER {
                on(1),
                off(2)
            }
            MAX-ACCESS read-write
            STATUS current
            DESCRIPTION
                "This object indicates the GPON line profile OMCC downstream encrypt status.
                 Options:
                 1. on(1)               - Indicates that the GPON line profile OMCC downstream encrypt status is on
                 2. off(2)              - Indicates that the GPON line profile OMCC downstream encrypt status is off
                "
            ::= { hwGponDeviceLineProfileInfoEntry 8 }

        hwGponDeviceLineProfileTr069ManagementSwitch OBJECT-TYPE
            SYNTAX INTEGER {
                enable(1),
                disable(2)
            }
            MAX-ACCESS read-write
            STATUS current
            DESCRIPTION
                "This object indicates the GPON line profile tr069 management status.
                 Options:
                 1. enable(1)      - Enable the GPON line profile tr069 management status
                 2. disable(2)     - Disable the GPON line profile tr069 management status
                "
            ::= { hwGponDeviceLineProfileInfoEntry 9 }

        hwGponDeviceLineProfileCommitResult OBJECT-TYPE
            SYNTAX INTEGER {
                 success(1),
                 fail(2),
                 operating(3),
                 invalid(-1)
            }
            MAX-ACCESS read-only
            STATUS current
            DESCRIPTION
                "This object indicates the commit result of a GPON line profile, the aging time of the result is 20s.
                 Options:
                 1. success(1)   - Indicates that the commit result is success
                 2. fail(2)      - Indicates that the commit result is fail
                 3. operating(3) - Indicates that the commit does not complete
                 4. invalid(-1)  - Indicates that no commit is being operated
                "
            ::= { hwGponDeviceLineProfileInfoEntry 11 }

        hwGponDeviceLineProfileTr069ManagementIpIndex OBJECT-TYPE
            SYNTAX Integer32
            MAX-ACCESS read-write
            STATUS current
            DESCRIPTION
                "The index of IP host which used by TR069.
                "
            ::= { hwGponDeviceLineProfileInfoEntry 12 }
--  Table hwGponDeviceLineProfTcontCfgTable
        hwGponDeviceLineProfTcontCfgTable OBJECT-TYPE
            SYNTAX SEQUENCE OF HwGponDeviceLineProfTcontCfgEntry
            MAX-ACCESS not-accessible
            STATUS current
            DESCRIPTION
                "This is the XPON line profile tcont config table. This table is used to configure tcont.
                 The index of this table is a combination of hwGponDeviceLineProfTcontCfgLineProfNameIndex,
                 and hwGponDeviceLineProfTcontCfgTcontIndex.
                "
            ::= { hwXponDeviceProfileObjects 62 }

        hwGponDeviceLineProfTcontCfgEntry OBJECT-TYPE
            SYNTAX HwGponDeviceLineProfTcontCfgEntry
            MAX-ACCESS not-accessible
            STATUS current
            DESCRIPTION
                "This is the XPON line profile tcont config table. This table is used to configure tcont.
                 The index of this entry is a combination of hwGponDeviceLineProfTcontCfgLineProfNameIndex,
                 and hwGponDeviceLineProfTcontCfgTcontIndex.
                "
            INDEX { hwGponDeviceLineProfTcontCfgLineProfNameIndex, hwGponDeviceLineProfTcontCfgTcontIndex }
            ::= { hwGponDeviceLineProfTcontCfgTable 1 }

        HwGponDeviceLineProfTcontCfgEntry ::=
            SEQUENCE {
                hwGponDeviceLineProfTcontCfgLineProfNameIndex           OCTET STRING,
                hwGponDeviceLineProfTcontCfgTcontIndex                  Integer32,
                hwGponDeviceLineProfTcontCfgDbaProfileName              OCTET STRING,
                hwGponDeviceLineProfTcontCfgRowStatus                   RowStatus
            }

        hwGponDeviceLineProfTcontCfgLineProfNameIndex OBJECT-TYPE
            SYNTAX OCTET STRING (SIZE (1..32))
            MAX-ACCESS not-accessible
            STATUS current
            DESCRIPTION
                "This object indicates the XPON line profile name index."
            ::= { hwGponDeviceLineProfTcontCfgEntry 1 }

        hwGponDeviceLineProfTcontCfgTcontIndex OBJECT-TYPE
            SYNTAX Integer32 (0..127)
            MAX-ACCESS not-accessible
            STATUS current
            DESCRIPTION
                "This object indicates the XPON line profile tcont index."
            ::= { hwGponDeviceLineProfTcontCfgEntry 2 }

        hwGponDeviceLineProfTcontCfgDbaProfileName OBJECT-TYPE
            SYNTAX OCTET STRING (SIZE (0..33))
            MAX-ACCESS read-write
            STATUS current
            DESCRIPTION
                "This object indicates the XPON line profile tcont config DBA profile name."
            ::= { hwGponDeviceLineProfTcontCfgEntry 3 }

        hwGponDeviceLineProfTcontCfgRowStatus OBJECT-TYPE
            SYNTAX RowStatus
            MAX-ACCESS read-create
            STATUS current
            DESCRIPTION
                "The hwGponDeviceLineProfTcontCfgRowStatus is used to create a new row
                 or to modify or delete an existing row in this table.
                 Options:
                 1. createAndGo(4) -create a new instance of a conceptual row
                 2. destroy(6)     -delete the instances associated with an existing conceptual row
                "
            ::= { hwGponDeviceLineProfTcontCfgEntry 4 }

--  Table hwGponDeviceLineProfGemCfgTable
        hwGponDeviceLineProfGemCfgTable OBJECT-TYPE
            SYNTAX SEQUENCE OF HwGponDeviceLineProfGemCfgEntry
            MAX-ACCESS not-accessible
            STATUS current
            DESCRIPTION
                "This is the XPON line profile gem config table. This table is used to configure gem.
                 The index of this table is a combination of hwGponDeviceLineProfGemCfgLineProfNameIndex
                 and hwGponDeviceLineProfGemCfgGemIndex.
                "
            ::= { hwXponDeviceProfileObjects 63 }

        hwGponDeviceLineProfGemCfgEntry OBJECT-TYPE
            SYNTAX HwGponDeviceLineProfGemCfgEntry
            MAX-ACCESS not-accessible
            STATUS current
            DESCRIPTION
                "This is the XPON line profile gem config table. This table is used to configure gem.
                 The index of this entry is a combination of hwGponDeviceLineProfGemCfgLineProfNameIndex
                 and hwGponDeviceLineProfGemCfgGemIndex.
                "
            INDEX { hwGponDeviceLineProfGemCfgLineProfNameIndex , hwGponDeviceLineProfGemCfgGemIndex }
            ::= { hwGponDeviceLineProfGemCfgTable 1 }

        HwGponDeviceLineProfGemCfgEntry ::=
            SEQUENCE {
                hwGponDeviceLineProfGemCfgLineProfNameIndex         OCTET STRING,
                hwGponDeviceLineProfGemCfgGemIndex                  Integer32,
                hwGponDeviceLineProfGemCfgCarTrafficTableId         Integer32,
                hwGponDeviceLineProfGemCfgTcontIndex                Integer32,
                hwGponDeviceLineProfGemCfgServiceType               INTEGER,
                hwGponDeviceLineProfGemCfgEncryptMode               INTEGER,
                hwGponDeviceLineProfGemCfgCascadeMode               INTEGER,
                hwGponDeviceLineProfGemCfgUpPQIndex                 Integer32,
                hwGponDeviceLineProfGemCfgRowStatus                 RowStatus,
                hwGponDeviceLineProfGemCfgDownPQIndex               Integer32,
                hwGponDeviceLineProfGemCfgCarTrafficTableName       OCTET STRING
             }

        hwGponDeviceLineProfGemCfgLineProfNameIndex OBJECT-TYPE
            SYNTAX OCTET STRING (SIZE (1..32))
            MAX-ACCESS not-accessible
            STATUS current
            DESCRIPTION
                "This object indicates the XPON line profile name index."
            ::= { hwGponDeviceLineProfGemCfgEntry 1 }

        hwGponDeviceLineProfGemCfgGemIndex OBJECT-TYPE
            SYNTAX Integer32 (0..1023)
            MAX-ACCESS not-accessible
            STATUS current
            DESCRIPTION
                "This object indicates the XPON line profile gem config gem index."
            ::= { hwGponDeviceLineProfGemCfgEntry 2 }

        hwGponDeviceLineProfGemCfgCarTrafficTableId OBJECT-TYPE
            SYNTAX Integer32 (-1 | 1..1024)
            MAX-ACCESS read-write
            STATUS current
            DESCRIPTION
                "This object indicates the XPON line profile gem config car profile index."
            ::= { hwGponDeviceLineProfGemCfgEntry 3 }

        hwGponDeviceLineProfGemCfgTcontIndex OBJECT-TYPE
            SYNTAX Integer32 (-1 | 0..127)
            MAX-ACCESS read-write
            STATUS current
            DESCRIPTION
                "This object indicates the XPON line profile gem config bind tcont index."
            ::= { hwGponDeviceLineProfGemCfgEntry 4 }

        hwGponDeviceLineProfGemCfgServiceType OBJECT-TYPE
            SYNTAX INTEGER {
                eth(1),
                tdm(2)
            }
            MAX-ACCESS read-write
            STATUS current
            DESCRIPTION
                "This object indicates the XPON line profile gem config gem service type.
                 Options:
                 1. eth(1)         - ETH
                 2. tdm(2)         - TDM
                "
            ::= { hwGponDeviceLineProfGemCfgEntry 5 }

        hwGponDeviceLineProfGemCfgEncryptMode OBJECT-TYPE
            SYNTAX INTEGER {
                on(1),
                off(2)
            }
            MAX-ACCESS read-write
            STATUS current
            DESCRIPTION
                "This object indicates the XPON line profile gem config gem encrypt mode.
                 Options:
                 1. on(1)               - Indicates that the XPON line profile gem config gem encrypt mode is on
                 2. off(2)              - Indicates that the XPON line profile gem config gem encrypt mode is off
                "
            DEFVAL { off }
            ::= { hwGponDeviceLineProfGemCfgEntry 6 }

        hwGponDeviceLineProfGemCfgCascadeMode OBJECT-TYPE
            SYNTAX INTEGER {
                on(1),
                off(2)
                }
            MAX-ACCESS read-write
            STATUS current
            DESCRIPTION
                "This object indicates the XPON line profile gem config gem cascade switch.
                 Options:
                 1. on(1)               - Indicates that the XPON line profile gem config gem cascade switch is on
                 2. off(2)              - Indicates that the XPON line profile gem config gem cascade switch is off
                "
            ::= { hwGponDeviceLineProfGemCfgEntry 7 }

        hwGponDeviceLineProfGemCfgUpPQIndex OBJECT-TYPE
            SYNTAX Integer32 (-1 | 0..7)
            MAX-ACCESS read-write
            STATUS current
            DESCRIPTION
                "This object indicates the XPON line profile gem config up stream PQ index."
            ::= { hwGponDeviceLineProfGemCfgEntry 8 }

        hwGponDeviceLineProfGemCfgRowStatus OBJECT-TYPE
            SYNTAX RowStatus
            MAX-ACCESS read-create
            STATUS current
            DESCRIPTION
                "The hwGponDeviceLineProfGemCfgRowStatus is used to create a new row
                 or to modify or delete an existing row in this table.
                 Options:
                 1. createAndGo(4) -create a new instance of a conceptual row
                 2. destroy(6)     -delete the instances associated with an existing conceptual row
                "
            ::= { hwGponDeviceLineProfGemCfgEntry 9 }

        hwGponDeviceLineProfGemCfgDownPQIndex OBJECT-TYPE
            SYNTAX Integer32 (-1 | 0..7 | 254)
            MAX-ACCESS read-write
            STATUS current
            DESCRIPTION
                "This object indicates the XPON line profile gem config down stream PQ index.
                 0..7: Down Stream PQ index,
                 254 : Apaptive, Gemport Down Stream PQ is decided by ont.
                 -1  : Default Value.Gemport Down Stream PQ is decided by olt.
                "
            ::= { hwGponDeviceLineProfGemCfgEntry 10 }

        hwGponDeviceLineProfGemCfgCarTrafficTableName OBJECT-TYPE
            SYNTAX OCTET STRING  (SIZE (0..32))
            MAX-ACCESS read-write
            STATUS current
            DESCRIPTION
                "This object indicates the XPON line profile gem config car profile name."
            ::= { hwGponDeviceLineProfGemCfgEntry 11 }

--  Table hwGponDeviceLineProfMappingCfgTable
        hwGponDeviceLineProfMappingCfgTable OBJECT-TYPE
            SYNTAX SEQUENCE OF HwGponDeviceLineProfMappingCfgEntry
            MAX-ACCESS not-accessible
            STATUS current
            DESCRIPTION
                "This is the XPON line profile flow config table.
                 This table is used to configure gem mapping to service.
                 The index of this table is a combination of hwGponDeviceLineProfMappingCfgLineProfNameIndex,
                 hwGponDeviceLineProfMappingCfgGemIndex and hwGponDeviceLineProfMappingCfgMappingIndex.
                "
            ::= { hwXponDeviceProfileObjects 64 }

        hwGponDeviceLineProfMappingCfgEntry OBJECT-TYPE
            SYNTAX HwGponDeviceLineProfMappingCfgEntry
            MAX-ACCESS not-accessible
            STATUS current
            DESCRIPTION
                "This is the XPON line profile flow config table.
                 This table is used to configure gem mapping to service.
                 The index of this entry is a combination of hwGponDeviceLineProfMappingCfgLineProfNameIndex,
                 hwGponDeviceLineProfMappingCfgGemIndex and hwGponDeviceLineProfMappingCfgMappingIndex.
                "
            INDEX { hwGponDeviceLineProfMappingCfgLineProfNameIndex ,
                   hwGponDeviceLineProfMappingCfgGemIndex , hwGponDeviceLineProfMappingCfgMappingIndex }
            ::= { hwGponDeviceLineProfMappingCfgTable 1 }

        HwGponDeviceLineProfMappingCfgEntry ::=
            SEQUENCE {
                hwGponDeviceLineProfMappingCfgLineProfNameIndex         OCTET STRING,
                hwGponDeviceLineProfMappingCfgGemIndex                  Integer32,
                hwGponDeviceLineProfMappingCfgMappingIndex              Integer32,
                hwGponDeviceLineProfMappingCfgMappingMode               INTEGER,
                hwGponDeviceLineProfMappingCfgCarTrafficTableId         Integer32,
                hwGponDeviceLineProfMappingCfgOntPhyType                INTEGER,
                hwGponDeviceLineProfMappingCfgOntPhyIndex               Integer32,
                hwGponDeviceLineProfMappingCfgVlanId                    Integer32,
                hwGponDeviceLineProfMappingCfgVlanPriority              Integer32,
                hwGponDeviceLineProfMappingCfgRowStatus                 RowStatus,
                hwGponDeviceLineProfMappingTransparent                  INTEGER,
                hwGponDeviceLineProfMappingCfgCarTrafficTableName       OCTET STRING
            }

        hwGponDeviceLineProfMappingCfgLineProfNameIndex OBJECT-TYPE
            SYNTAX OCTET STRING (SIZE (1..32))
            MAX-ACCESS not-accessible
            STATUS current
            DESCRIPTION
                "This object indicates the XPON line profile name index."
            ::= { hwGponDeviceLineProfMappingCfgEntry 1 }

        hwGponDeviceLineProfMappingCfgGemIndex OBJECT-TYPE
            SYNTAX Integer32 (0..1023)
            MAX-ACCESS not-accessible
            STATUS current
            DESCRIPTION
                "This object indicates the XPON line profile mapping config gem index."
            ::= { hwGponDeviceLineProfMappingCfgEntry 2 }

        hwGponDeviceLineProfMappingCfgMappingIndex OBJECT-TYPE
            SYNTAX Integer32 (0..7)
            MAX-ACCESS not-accessible
            STATUS current
            DESCRIPTION
                "This object indicates the XPON line profile mapping config flow index."
            ::= { hwGponDeviceLineProfMappingCfgEntry 3 }

        hwGponDeviceLineProfMappingCfgMappingMode OBJECT-TYPE
            SYNTAX INTEGER {
                vlan(1),
                pri8021p(2),
                vlanpri(3),
                port(4),
                vlanport(5),
                portpri(6),
                vlanpriport(7),
                e1t1port(8),
                iptos(9),
                vlaniptos(10),
                invalid(-1)
            }
            MAX-ACCESS read-write
            STATUS current
            DESCRIPTION
                "This object indicates the XPON line profile mapping config mapping mode.
                 Options:
                 1. vlan(1)            - The XPON line profile mapping mode is vlan
                 2. pri8021p(2)        - The XPON line profile mapping mode is 802.1p
                 3. vlanpri(3)         - The XPON line profile mapping mode is vlan and 802.1p
                 4. port(4)            - The XPON line profile mapping mode is port
                 5. vlanport(5)        - The XPON line profile mapping mode is vlan and port
                 6. portpri(6)         - The XPON line profile mapping mode is port and 802.1p
                 7. vlanpriport(7)     - The XPON line profile mapping mode is vlan, port and 802.1p
                 8. e1t1port(8)        - The XPON line profile mapping mode is the port of e1 and t1
                 9. iptos(9)           - The XPON line profile mapping mode is iptos
                 10. vlaniptos(10)     - The XPON line profile mapping mode is vlan and iptos
                 11. invalid(-1)       - Indicates that the mapping port type is tdm-vcl
                "
            ::= { hwGponDeviceLineProfMappingCfgEntry 4 }

        hwGponDeviceLineProfMappingCfgCarTrafficTableId OBJECT-TYPE
            SYNTAX Integer32 (-1 | 1..1024)
            MAX-ACCESS read-write
            STATUS current
            DESCRIPTION
                "This object indicates the XPON line profile mapping config car profile index."
            ::= { hwGponDeviceLineProfMappingCfgEntry 5 }

        hwGponDeviceLineProfMappingCfgOntPhyType OBJECT-TYPE
            SYNTAX INTEGER {
                t1(13),
                e1(14),
                fe(24),
                ge(34),
                vdsl(37),
                moca(46),
                eth(47),
                iphost(50),
                ippath(61),
                tdmvcl(253),
                ethBundle(254),
                invalid(-1)
            }
            MAX-ACCESS read-write
            STATUS current
            DESCRIPTION
                "This object indicates the port type of the ONT.
                 Options:
                 1. t1(13)             - T1
                 2. e1(14)             - E1
                 3. fe(24)             - FE
                 4. ge(34)             - GE
                 5. vdsl(37)           - VDSL
                 6. moca(46)           - MOCA
                 7. eth(47)            - ETH
                 8. iphost(50)         - IPHOST
                 9. ippath(61)         - Ippath
                 10. tdmvcl(253)        - Tdmvcl
                 11. ethBundle(254)     - EthBundle
                 12. invalid(-1)       - Indicates that the query fails or no information is detected
                "
            ::= { hwGponDeviceLineProfMappingCfgEntry 6 }

        hwGponDeviceLineProfMappingCfgOntPhyIndex OBJECT-TYPE
            SYNTAX Integer32
            MAX-ACCESS read-write
            STATUS current
            DESCRIPTION
                "This object indicates the port index of the ONT,
                 or the bundle-groupid when it is the eth-bundle port type.
                "
            ::= { hwGponDeviceLineProfMappingCfgEntry 7 }

        hwGponDeviceLineProfMappingCfgVlanId OBJECT-TYPE
            SYNTAX Integer32 (-1|0..4095|65533)
            MAX-ACCESS read-write
            STATUS current
            DESCRIPTION
                "This object indicates the VLAN ID of the service. The value -1 indicates invalid VLAN ID, and 65533 indicates untag traffic stream."
            ::= { hwGponDeviceLineProfMappingCfgEntry 8 }

        hwGponDeviceLineProfMappingCfgVlanPriority OBJECT-TYPE
            SYNTAX Integer32 (-1|0..7)
            MAX-ACCESS read-write
            STATUS current
            DESCRIPTION
                "This object indicates the priority of the service."
            ::= { hwGponDeviceLineProfMappingCfgEntry 9 }

        hwGponDeviceLineProfMappingCfgRowStatus OBJECT-TYPE
            SYNTAX RowStatus
            MAX-ACCESS read-create
            STATUS current
            DESCRIPTION
                "The hwGponDeviceLineProfMappingCfgRowStatus is used to create a new row
                 or to modify or delete an existing row in this table.
                 Options:
                 1. createAndGo(4) -create a new instance of a conceptual row
                 2. destroy(6)     -delete the instances associated with an existing conceptual row
                "
            ::= { hwGponDeviceLineProfMappingCfgEntry 10 }

        hwGponDeviceLineProfMappingTransparent OBJECT-TYPE
            SYNTAX INTEGER {
                enable(1),
                disable(2),
                invalid(-1)
            }
            MAX-ACCESS read-write
            STATUS current
            DESCRIPTION
                "This object indicates the flow transparent switch of the ONT.
                 Options:
                 1. enable(1)      - Enable the flow transparent switch of the ONT
                 2. disable(2)     - Disable the flow transparent switch of the ONT
                 3. invalid(-1)    - Indicates that the query fails or no information is detected
                "
            ::= { hwGponDeviceLineProfMappingCfgEntry 11 }

        hwGponDeviceLineProfMappingCfgCarTrafficTableName OBJECT-TYPE
            SYNTAX OCTET STRING  (SIZE (0..32))
            MAX-ACCESS read-write
            STATUS current
            DESCRIPTION
                "This object indicates the XPON line profile mapping config car profile name."
            ::= { hwGponDeviceLineProfMappingCfgEntry 12 }

--  Table hwGponDeviceSrvProfileInfoTable
        hwGponDeviceSrvProfileInfoTable OBJECT-TYPE
            SYNTAX SEQUENCE OF HwGponDeviceSrvProfileInfoEntry
            MAX-ACCESS not-accessible
            STATUS current
            DESCRIPTION
                "This is the GPON service profile table.
                 The index of this table is hwGponDeviceSrvProfileInfoNameIndex.
                "
            ::= { hwXponDeviceProfileObjects 65 }

        hwGponDeviceSrvProfileInfoEntry OBJECT-TYPE
            SYNTAX HwGponDeviceSrvProfileInfoEntry
            MAX-ACCESS not-accessible
            STATUS current
            DESCRIPTION
                "This is the GPON service profile table.
                 The index of this entry is hwGponDeviceSrvProfileInfoNameIndex.
                "
            INDEX { IMPLIED hwGponDeviceSrvProfileInfoNameIndex }
            ::= { hwGponDeviceSrvProfileInfoTable 1 }

        HwGponDeviceSrvProfileInfoEntry ::=
            SEQUENCE {
                hwGponDeviceSrvProfileInfoNameIndex  OCTET STRING,
                hwGponDeviceSrvProfileBindNum        Integer32,
                hwGponDeviceSrvProfileCommit         INTEGER,
                hwGponDeviceSrvProfileRowStatus      RowStatus
            }

        hwGponDeviceSrvProfileInfoNameIndex OBJECT-TYPE
            SYNTAX OCTET STRING (SIZE (1..32))
            MAX-ACCESS not-accessible
            STATUS current
            DESCRIPTION
                "This object indicates the GPON service profile name index."
            ::= { hwGponDeviceSrvProfileInfoEntry 1 }

        hwGponDeviceSrvProfileBindNum OBJECT-TYPE
            SYNTAX Integer32
            MAX-ACCESS read-only
            STATUS current
            DESCRIPTION
                "This object indicates the  number of ONT bound with GPON service profile."
            ::= { hwGponDeviceSrvProfileInfoEntry 2 }

        hwGponDeviceSrvProfileCommit OBJECT-TYPE
            SYNTAX INTEGER {
                commitExecute(1),
                invalid(-1)
            }
            MAX-ACCESS read-write
            STATUS current
            DESCRIPTION
                "This object indicates the GPON service profile configuration commit.
                 Options:
                 1. commitExecute(1)      - Execute the GPON service profile configuration commit
                 2. invalid(-1)           - Indicates that the query fails or no information is detected
                "
            ::= { hwGponDeviceSrvProfileInfoEntry 3 }

        hwGponDeviceSrvProfileRowStatus OBJECT-TYPE
            SYNTAX RowStatus
            MAX-ACCESS read-create
            STATUS current
            DESCRIPTION
                "The hwGponDeviceSrvProfileRowStatus is used to create a new row
                 or to modify or delete an existing row in this table.
                 Options:
                 1. createAndGo(4) -create a new instance of a conceptual row
                 2. destroy(6)     -delete the instances associated with an existing conceptual row
                "
            ::= { hwGponDeviceSrvProfileInfoEntry 4 }

--  Table hwGponDeviceSrvProfileOntCfgTable
        hwGponDeviceSrvProfileOntCfgTable OBJECT-TYPE
            SYNTAX SEQUENCE OF HwGponDeviceSrvProfileOntCfgEntry
            MAX-ACCESS not-accessible
            STATUS current
            DESCRIPTION
                "This is GPON service profile ont config table.
                 The index of this table is hwGponDeviceSrvProfOntCfgSrvProfNameIndex.
                "
            ::= { hwXponDeviceProfileObjects 66 }

        hwGponDeviceSrvProfileOntCfgEntry OBJECT-TYPE
            SYNTAX HwGponDeviceSrvProfileOntCfgEntry
            MAX-ACCESS not-accessible
            STATUS current
            DESCRIPTION
                "This is GPON service profile ont config table.
                 The index of this entry is hwGponDeviceSrvProfOntCfgSrvProfNameIndex.
                "
            INDEX { IMPLIED hwGponDeviceSrvProfOntCfgSrvProfNameIndex }
            ::= { hwGponDeviceSrvProfileOntCfgTable 1 }

        HwGponDeviceSrvProfileOntCfgEntry ::=
            SEQUENCE {
                hwGponDeviceSrvProfOntCfgSrvProfNameIndex                   OCTET STRING,
                hwGponDeviceSrvProfilePotsNum                               Integer32,
                hwGponDeviceSrvProfileEthNum                                Integer32,
                hwGponDeviceSrvProfileTdmPortNum                            Integer32,
                hwGponDeviceSrvProfileTdmPortType                           INTEGER,
                hwGponDeviceSrvProfileTdmPortSrvType                        INTEGER,
                hwGponDeviceSrvProfileMocaNum                               Integer32,
                hwGponDeviceSrvProfileCatvNum                               Integer32,
                hwGponDeviceSrvProfileMacAddressSwitch                      INTEGER,
                hwGponDeviceSrvProfileTransparentSwitch                     INTEGER,
                hwGponDeviceSrvProfileMultiSrvTransmitMode                  INTEGER,
                hwGponDeviceSrvProfileMulticastVlan                         Integer32,
                hwGponDeviceSrvProfileMulticastMode                         INTEGER,
                hwGponDeviceSrvProfileUpIgmpTransmitMode                    INTEGER,
                hwGponDeviceSrvProfileUpIgmpMsgTranslationVlan              Integer32,
                hwGponDeviceSrvProfileUpIgmpMsgPriority                     Integer32,
                hwGponDeviceSrvProfileNativeVlanOption                      INTEGER,
                hwGponDeviceSrvProfileUpPqColorPolicy                       INTEGER,
                hwGponDeviceSrvProfileDownPqColorPolicy                     INTEGER,
                hwGponDeviceSrvProfileVdslPortNum                           Integer32,
                hwGponDeviceSrvProfileRingCheckSwitch                       INTEGER,
                hwGponDeviceSrvProfileRingCheckAutoShutdownSwitch           INTEGER,
                hwGponDeviceSrvProfileRingCheckDetectingFrequency           Integer32,
                hwGponDeviceSrvProfileRingCheckResumeInterval               Integer32,
                hwGponDeviceSrvProfileMaxNumOfAdapPotsPort                  Integer32,
                hwGponDeviceSrvProfileMaxNumOfAdapEthPort                   Integer32,
                hwGponDeviceSrvProfileMaxNumOfAdapVdslPort                  Integer32,
                hwGponDeviceSrvProfileMaxNumOfAdapCatvPort                  Integer32,
                hwGponDeviceSrvProfileWifiPortNum                           Integer32,
                hwGponDeviceSrvProfileMonitorLinkSwitch                     INTEGER,
                hwGponDeviceSrvProfileMTU                                   Integer32
            }

        hwGponDeviceSrvProfOntCfgSrvProfNameIndex OBJECT-TYPE
            SYNTAX OCTET STRING (SIZE (1..32))
            MAX-ACCESS not-accessible
            STATUS current
            DESCRIPTION
                "This object indicates the XPON service profile name index."
            ::= { hwGponDeviceSrvProfileOntCfgEntry 1 }

        hwGponDeviceSrvProfilePotsNum OBJECT-TYPE
            SYNTAX Integer32
            MAX-ACCESS read-write
            STATUS current
            DESCRIPTION
                "This object indicates the XPON service profile pots port number.
                 A special value of 0xFE (254) indicates the number of port is adaptive."
            ::= { hwGponDeviceSrvProfileOntCfgEntry 2 }

        hwGponDeviceSrvProfileEthNum OBJECT-TYPE
            SYNTAX Integer32
            MAX-ACCESS read-write
            STATUS current
            DESCRIPTION
                "This object indicates the XPON service profile eth port number.
                 A special value of 0xFE (254) indicates the number of port is adaptive."
            ::= { hwGponDeviceSrvProfileOntCfgEntry 3 }

        hwGponDeviceSrvProfileTdmPortNum OBJECT-TYPE
            SYNTAX Integer32
            MAX-ACCESS read-write
            STATUS current
            DESCRIPTION
                "This object indicates the XPON service profile tdm port number."
            ::= { hwGponDeviceSrvProfileOntCfgEntry 4 }

        hwGponDeviceSrvProfileTdmPortType OBJECT-TYPE
            SYNTAX INTEGER {
                t1(13),
                e1(14),
                invalid(-1)
            }
            MAX-ACCESS read-write
            STATUS current
            DESCRIPTION
                "This object indicates the XPON service profile tdm port type.
                 Options:
                 1. t1(13)             - T1
                 2. e1(14)             - E1
                 3. invalid(-1)        - Indicates that the query fails or no information is detected
                "
            ::= { hwGponDeviceSrvProfileOntCfgEntry 5 }

        hwGponDeviceSrvProfileTdmPortSrvType OBJECT-TYPE
            SYNTAX INTEGER {
                tdmovergem(1),
                cesop(2)
            }
            MAX-ACCESS read-write
            STATUS current
            DESCRIPTION
                "This object indicates the XPON service profile tdm port service type.
                 Options:
                 1. tdmovergem(1)     - Tdm over gem
                 2. cesop(2)          - Cesop
                "
            ::= { hwGponDeviceSrvProfileOntCfgEntry 6 }

        hwGponDeviceSrvProfileMocaNum OBJECT-TYPE
            SYNTAX Integer32
            MAX-ACCESS read-write
            STATUS current
            DESCRIPTION
                "This object indicates the XPON service profile MOCA port number."
            ::= { hwGponDeviceSrvProfileOntCfgEntry 7 }

        hwGponDeviceSrvProfileCatvNum OBJECT-TYPE
            SYNTAX Integer32
            MAX-ACCESS read-write
            STATUS current
            DESCRIPTION
                "This object indicates the XPON service profile catv port number.
                 A special value of 0xFE (254) indicates the number of port is adaptive."
            ::= { hwGponDeviceSrvProfileOntCfgEntry 8 }

        hwGponDeviceSrvProfileMacAddressSwitch OBJECT-TYPE
            SYNTAX INTEGER {
                enable(1),
                disable(2),
                invalid(-1)
            }
            MAX-ACCESS read-write
            STATUS current
            DESCRIPTION
                "This object indicates the XPON service profile mac address switch.
                 Options:
                 1. enable(1)      - Enable the XPON service profile mac address switch
                 2. disable(2)     - Disable the XPON service profile mac address switch
                 3. invalid(-1)    - Indicates that the query fails or no information is detected
                "
            ::= { hwGponDeviceSrvProfileOntCfgEntry 9 }

        hwGponDeviceSrvProfileTransparentSwitch OBJECT-TYPE
            SYNTAX INTEGER {
                enable(1),
                disable(2),
                invalid(-1)
            }
            MAX-ACCESS read-write
            STATUS current
            DESCRIPTION
                "This object indicates the XPON service profile transparent switch.
                 Options:
                 1. enable(1)      - Enable the XPON service profile transparent switch
                 2. disable(2)     - Disable the XPON service profile transparent switch
                 3. invalid(-1)    - Indicates that the query fails or no information is detected
                "
            ::= { hwGponDeviceSrvProfileOntCfgEntry 10 }

        hwGponDeviceSrvProfileMultiSrvTransmitMode OBJECT-TYPE
            SYNTAX INTEGER {
                tagtranslation(1),
                tagtransparent(2),
                untag(3),
                unconcern(254)
            }
            MAX-ACCESS read-write
            STATUS current
            DESCRIPTION
                "This object indicates the XPON service profile igmp transmit mode.
                 Options:
                 1. tagtranslation(1)    - Indicates that the XPON service profile igmp transmit mode is tag translation
                 2. tagtransparent(2)    - Indicates that the XPON service profile igmp transmit mode is tag transparent
                 3. untag(3)             - Indicates that the XPON service profile igmp transmit mode is untag
                 4. unconcern(254)       - Indicates that the query fails or no information is detected
                "
            ::= { hwGponDeviceSrvProfileOntCfgEntry 11 }

        hwGponDeviceSrvProfileMulticastVlan OBJECT-TYPE
            SYNTAX Integer32 (-1 | 1..4095 | 4096)
            MAX-ACCESS read-write
            STATUS current
            DESCRIPTION
                "This object indicates the XPON service profile multicast vlan.
                 value 4096 indicates IGMP-user-VLAN is used for multicast vlan."
            ::= { hwGponDeviceSrvProfileOntCfgEntry 12 }

        hwGponDeviceSrvProfileMulticastMode OBJECT-TYPE
            SYNTAX INTEGER {
                oltcontrol(1),
                igmpsnooping(2),
                unconcern(254)
            }
            MAX-ACCESS read-write
            STATUS current
            DESCRIPTION
                "This object indicates the XPON service profile multicast mode.
                 Options:
                 1. oltcontrol(1)      - Indicates that the XPON service profile multicast mode is olt controled
                 2. igmpsnooping(2)    - Indicates that the XPON service profile multicast mode is igmp snooping
                 3. unconcern(254)     - Indicates that the XPON service profile multicast mode is not concerned
                "
            ::= { hwGponDeviceSrvProfileOntCfgEntry 13 }

        hwGponDeviceSrvProfileUpIgmpTransmitMode OBJECT-TYPE
            SYNTAX INTEGER {
                transparent(1),
                translation(2),
                default(3),
                unconcern(254),
                invalid(-1)
            }
            MAX-ACCESS read-write
            STATUS current
            DESCRIPTION
                "This object indicates the XPON service profile upstream igmp packets forward mode.
                 Options:
                 1. transparent(1)    - Indicates that the XPON service profile upstream igmp packets forward mode is transparent
                 2. translation(2)    - Indicates that the XPON service profile upstream igmp packets forward mode is translation
                 3. default(3)        - Indicates that the XPON service profile upstream igmp packets forward mode is default
                 4. unconcern(254)    - Indicates that the XPON service profile upstream igmp packets forward mode is not concerned
                 5. invalid(-1)       - Indicates that the query fails or no information is detected
                "
            ::= { hwGponDeviceSrvProfileOntCfgEntry 14 }

        hwGponDeviceSrvProfileUpIgmpMsgTranslationVlan OBJECT-TYPE
            SYNTAX Integer32 (-1|0..4095)
            MAX-ACCESS read-write
            STATUS current
            DESCRIPTION
                "XPON service profile upstream igmp packets will be translate to the translation vlan,
                 if upstream igmp packets forward mode is translation(2).
                "
            ::= { hwGponDeviceSrvProfileOntCfgEntry 15 }

        hwGponDeviceSrvProfileUpIgmpMsgPriority OBJECT-TYPE
            SYNTAX Integer32 (-1|0..7)
            MAX-ACCESS read-write
            STATUS current
            DESCRIPTION
                "When xpon service profile upstream igmp packets were added a vlan or
                 translated to the translation vlan, priority was set.
                "
            ::= { hwGponDeviceSrvProfileOntCfgEntry 16 }

        hwGponDeviceSrvProfileNativeVlanOption OBJECT-TYPE
            SYNTAX INTEGER {
                concern(1),
                unconcern(2)
            }
            MAX-ACCESS read-write
            STATUS current
            DESCRIPTION
                "This object indicates the XPON service profile native VLAN.
                 Options:
                 1. concern(1)    - Concern the XPON service profile native VLAN
                 2. unconcern(2)  - Unconcern the XPON service profile native VLAN
                "
            ::= { hwGponDeviceSrvProfileOntCfgEntry 17 }

        hwGponDeviceSrvProfileUpPqColorPolicy OBJECT-TYPE
            SYNTAX INTEGER {
                noMarking(0),
                dei(2),
                invalid(-1)
            }
            MAX-ACCESS read-write
            STATUS current
            DESCRIPTION
                "This object indicates the GPON service profile upstream priority-queue color policy.
                 Options:
                 1. noMarking(0)        - Indicates that the upstream priority-queue color policy is no marking
                 2. dei(2)               - Indicates that the upstream priority-queue color policy is DEI
                 3. invalid(-1)          - Indicates that the upstream priority-queue color policy is invalid
                "
            ::= { hwGponDeviceSrvProfileOntCfgEntry 18 }

        hwGponDeviceSrvProfileDownPqColorPolicy OBJECT-TYPE
            SYNTAX INTEGER {
                noMarking(0),
                dei(2),
                invalid(-1)
            }
            MAX-ACCESS read-write
            STATUS current
            DESCRIPTION
                "This object indicates the GPON service profile downstream priority-queue color policy.
                 Options:
                 1. noMarking(0)        - Indicates that the downstream priority-queue color policy is no marking
                 2. dei(2)               - Indicates that the downstream priority-queue color policy is DEI
                 3. invalid(-1)          - Indicates that the downstream priority-queue color policy is invalid
                "
            ::= { hwGponDeviceSrvProfileOntCfgEntry 19 }

        hwGponDeviceSrvProfileVdslPortNum OBJECT-TYPE
            SYNTAX Integer32
            MAX-ACCESS read-write
            STATUS current
            DESCRIPTION
                "This object indicates the XPON service profile VDSL port number.
                 A special value of 0xFE (254) indicates the number of port is adaptive."
            ::= { hwGponDeviceSrvProfileOntCfgEntry 20 }

        hwGponDeviceSrvProfileRingCheckSwitch OBJECT-TYPE
            SYNTAX INTEGER {
                enable(1),
                disable(2),
                invalid(-1)
            }
            MAX-ACCESS read-write
            STATUS current
            DESCRIPTION
                "This object indicates the XPON service profile mac address switch.
                 Options:
                 1. enable(1)      - Enable the XPON service profile ring check switch
                 2. disable(2)     - Disable the XPON service profile ring check switch
                 3. invalid(-1)    - Indicates that the query fails or no information is detected
                "
            ::= { hwGponDeviceSrvProfileOntCfgEntry 21 }

        hwGponDeviceSrvProfileRingCheckAutoShutdownSwitch OBJECT-TYPE
            SYNTAX INTEGER {
                enable(1),
                disable(2),
                invalid(-1)
            }
            MAX-ACCESS read-write
            STATUS current
            DESCRIPTION
                "This object indicates the XPON service profile mac address switch.
                 Options:
                 1. enable(1)      - Enable the XPON service profile ring check auto shutdown switch
                 2. disable(2)     - Disable the XPON service profile ring check auto shutdown switch
                 3. invalid(-1)    - Indicates that the query fails or no information is detected
                "
            ::= { hwGponDeviceSrvProfileOntCfgEntry 22 }

        hwGponDeviceSrvProfileRingCheckDetectingFrequency OBJECT-TYPE
            SYNTAX Integer32 (1..20)
            MAX-ACCESS read-write
            STATUS current
            DESCRIPTION
                "This object indicates the XPON service profile ring check detecting frequency."
            ::= { hwGponDeviceSrvProfileOntCfgEntry 23}

        hwGponDeviceSrvProfileRingCheckResumeInterval OBJECT-TYPE
            SYNTAX Integer32 (60..3600)
            MAX-ACCESS read-write
            STATUS current
            DESCRIPTION
                "This object indicates the XPON service profile ring check resume frequency."
            ::= { hwGponDeviceSrvProfileOntCfgEntry 24}

        hwGponDeviceSrvProfileMaxNumOfAdapPotsPort OBJECT-TYPE
            SYNTAX Integer32
            MAX-ACCESS read-write
            STATUS current
            DESCRIPTION
                "This object indicates the max number of adaptive pots ports.
                 Range: 1-32. 32 is default value."
            ::= { hwGponDeviceSrvProfileOntCfgEntry 25}

        hwGponDeviceSrvProfileMaxNumOfAdapEthPort OBJECT-TYPE
            SYNTAX Integer32
            MAX-ACCESS read-write
            STATUS current
            DESCRIPTION
                "This object indicates the max number of adaptive eth ports.
                 Range: 1-24. 8 is default value."
            ::= { hwGponDeviceSrvProfileOntCfgEntry 26}

        hwGponDeviceSrvProfileMaxNumOfAdapVdslPort OBJECT-TYPE
            SYNTAX Integer32
            MAX-ACCESS read-write
            STATUS current
            DESCRIPTION
                "This object indicates the max number of adaptive vdsl ports.
                 Range: 1-8. 8 is default value."
            ::= { hwGponDeviceSrvProfileOntCfgEntry 27}

        hwGponDeviceSrvProfileMaxNumOfAdapCatvPort OBJECT-TYPE
            SYNTAX Integer32
            MAX-ACCESS read-write
            STATUS current
            DESCRIPTION
                "This object indicates the max number of adaptive catv ports.
                 Range: 1-8. 8 is default value."
            ::= { hwGponDeviceSrvProfileOntCfgEntry 28}

        hwGponDeviceSrvProfileWifiPortNum OBJECT-TYPE
            SYNTAX Integer32
            MAX-ACCESS read-write
            STATUS current
            DESCRIPTION
                "This object indicates the XPON service profile WiFi port number.
                 Range: 0-4. 0 is default value."
            ::= { hwGponDeviceSrvProfileOntCfgEntry 29}

	    hwGponDeviceSrvProfileMonitorLinkSwitch OBJECT-TYPE
            SYNTAX INTEGER {
                enable(1),
                disable(2),
                unconcern(254)
            }
            MAX-ACCESS read-write
            STATUS current
            DESCRIPTION
                "The switch of the ONT Monitor Link function.
                 Options:
                 1. enable(1)    -Enable the the ONT Monitor Link function
                 2. disable(2)   -Disable the the ONT Monitor Link function
                 3. unconcern (254) -The ONT Monitor Link function is unconcern and depends on ONT Configuration.The default value is unconcern.
			    "
            ::= { hwGponDeviceSrvProfileOntCfgEntry 30 }

        hwGponDeviceSrvProfileMTU OBJECT-TYPE
            SYNTAX Integer32 (-1|0|1519..9280)
            UNITS  "byte"
            MAX-ACCESS read-write
            STATUS current
            DESCRIPTION
                "This object indicates the ONT MTU value. Unit:byte.
                 The value (0) indicates that the MTU value is decided by ONT.
                 The value (-1) indicates that the query fails or no information is detected.
                 The default value is unconcern(0).
                "
            ::= { hwGponDeviceSrvProfileOntCfgEntry 31}

--  Table hwGponDeviceSrvProfOntPortCfgTable
        hwGponDeviceSrvProfOntPortCfgTable OBJECT-TYPE
            SYNTAX SEQUENCE OF HwGponDeviceSrvProfOntPortCfgEntry
            MAX-ACCESS not-accessible
            STATUS current
            DESCRIPTION
                "This is the GPON service profile ont port config table.
                 The index of this table is a combination of hwGponDeviceSrvProfOntPortCfgSrvProfNameIndex,
                 hwGponDeviceSrvProfOntPortCfgOntPhyType and hwGponDeviceSrvProfOntPortCfgOntPhyIndex.
                "
            ::= { hwXponDeviceProfileObjects 67 }

        hwGponDeviceSrvProfOntPortCfgEntry OBJECT-TYPE
            SYNTAX HwGponDeviceSrvProfOntPortCfgEntry
            MAX-ACCESS not-accessible
            STATUS current
            DESCRIPTION
                "This is the GPON service profile ont port config table.
                 The index of this entry is a combination of hwGponDeviceSrvProfOntPortCfgSrvProfNameIndex,
                 hwGponDeviceSrvProfOntPortCfgOntPhyType and hwGponDeviceSrvProfOntPortCfgOntPhyIndex.
                "
            INDEX { hwGponDeviceSrvProfOntPortCfgSrvProfNameIndex,
                    hwGponDeviceSrvProfOntPortCfgOntPhyType , hwGponDeviceSrvProfOntPortCfgOntPhyIndex }
            ::= { hwGponDeviceSrvProfOntPortCfgTable 1 }

        HwGponDeviceSrvProfOntPortCfgEntry ::=
            SEQUENCE {
                hwGponDeviceSrvProfOntPortCfgSrvProfNameIndex                   OCTET STRING,
                hwGponDeviceSrvProfOntPortCfgOntPhyType                         INTEGER,
                hwGponDeviceSrvProfOntPortCfgOntPhyIndex                        Integer32,
                hwGponDeviceSrvProfOntPortCfgTDMPortCodeMode                    INTEGER,
                hwGponDeviceSrvProfOntPortCfgPortQinQMode                       INTEGER,
                hwGponDeviceSrvProfOntPortCfgPortPriorityPolicy                 INTEGER,
                hwGponDeviceSrvProfOntPortCfgUpStreamCarTrafficTableId          Integer32,
                hwGponDeviceSrvProfOntPortCfgDownStreamCarTrafficTableId        Integer32,
                hwGponDeviceSrvProfOntPortCfgDscpProfIndex                      Integer32,
                hwGponDeviceSrvProfOntPortCfgUpIgmpTransmitMode                 INTEGER,
                hwGponDeviceSrvProfOntPortCfgUpIgmpMsgTranslationVlan           Integer32,
                hwGponDeviceSrvProfOntPortCfgUpIgmpMsgPriority                  Integer32,
                hwGponDeviceSrvProfOntPortCfgMaxMacAddressNum                   Gauge32,
                hwGponDeviceSrvProfOntPortCfgTDMPortTxClockMode                 INTEGER,
                hwGponDeviceSrvProfOntPortCfgDownstreamMode                     INTEGER,
                hwGponDeviceSrvProfOntPortCfgUpStreamCarTrafficTableName        OCTET STRING,
                hwGponDeviceSrvProfOntPortCfgDownStreamCarTrafficTableName      OCTET STRING,
                hwGponDeviceSrvProfOntPortCfgClassProfileIndex                  Integer32,
                hwGponDeviceSrvProfOntPortCfgUnknownUnicastRate                 Integer32,
                hwGponDeviceSrvProfOntPortCfgBroadcastRate                      Integer32,
                hwGponDeviceSrvProfOntPortCfgUnknownMulticastRate               Integer32,
                hwGponDeviceSrvProfOntPortCfgL2IsolateSwitch                    INTEGER
            }

        hwGponDeviceSrvProfOntPortCfgSrvProfNameIndex OBJECT-TYPE
            SYNTAX OCTET STRING (SIZE (1..32))
            MAX-ACCESS not-accessible
            STATUS current
            DESCRIPTION
                "XPON service profile name index."
            ::= { hwGponDeviceSrvProfOntPortCfgEntry 1 }

        hwGponDeviceSrvProfOntPortCfgOntPhyType OBJECT-TYPE
            SYNTAX INTEGER {
                t1(13),
                e1(14),
                fe(24),
                ge(34),
                vdsl(37),
                moca(46),
                eth(47),
                iphost(50)
            }
            MAX-ACCESS not-accessible
            STATUS current
            DESCRIPTION
                "This object indicates the port type of the ONT.
                 Options:
                 1. t1(13)             - T1
                 2. e1(14)             - E1
                 3. fe(24)             - FE
                 4. ge(34)             - GE
                 5. vdsl(37)           - VDSL
                 6. moca(46)           - MOCA
                 7. eth(47)            - ETH
                 8. iphost(50)         - IPHOST
                "
            ::= { hwGponDeviceSrvProfOntPortCfgEntry 2 }

        hwGponDeviceSrvProfOntPortCfgOntPhyIndex OBJECT-TYPE
            SYNTAX Integer32
            MAX-ACCESS not-accessible
            STATUS current
            DESCRIPTION
                "This object indicates the port index of the ONT."
            ::= { hwGponDeviceSrvProfOntPortCfgEntry 3 }

        hwGponDeviceSrvProfOntPortCfgTDMPortCodeMode OBJECT-TYPE
            SYNTAX INTEGER {
                ami(1),
                hdb3(2),
                b8zs(3),
                invalid(-1)
            }
            MAX-ACCESS read-write
            STATUS current
            DESCRIPTION
                "This object indicates the XPON service profile tdm port coding mode.
                 Options:
                 1. ami(1)            - AMI
                 2. hdb3(2)           - HDB3
                 3. b8zs(3)           - B8ZS
                 4. invalid(-1)       - Indicates that the query fails or no information is detected
                "
            ::= { hwGponDeviceSrvProfOntPortCfgEntry 4 }

        hwGponDeviceSrvProfOntPortCfgPortQinQMode OBJECT-TYPE
            SYNTAX INTEGER {
                disable(1),
                enable(2),
                unconcern(254),
                invalid(-1)
            }
            MAX-ACCESS read-write
            STATUS current
            DESCRIPTION
                "This object indicates the QinQ mode.
                 Options:
                 1. disable(1)      - Disable the QinQ mode
                 2. enable(2)       - Enable the QinQ mode
                 3. unconcern(254)  - The QinQ mode is not concerned
                 4. invalid(-1)     - Indicates that the query fails or no information is detected
                "
            ::= { hwGponDeviceSrvProfOntPortCfgEntry 5 }

        hwGponDeviceSrvProfOntPortCfgPortPriorityPolicy OBJECT-TYPE
            SYNTAX    INTEGER {
                assigned(1),
                copycos(2),
                unconcern(254),
                invalid(-1)
            }
            MAX-ACCESS  read-write
            STATUS      current
            DESCRIPTION
                "This object indicates the priority policy.
                 Options:
                 1. assigned(1)      - The priority policy is assigned
                 2. copycos(2)       - The priority policy is copy CoS
                 3. unconcern(254)   - The priority policy is not concerned
                 4. invalid(-1)      - Indicates that the query fails or no information is detected
                "
            ::= { hwGponDeviceSrvProfOntPortCfgEntry 6 }

        hwGponDeviceSrvProfOntPortCfgUpStreamCarTrafficTableId OBJECT-TYPE
            SYNTAX    Integer32
            MAX-ACCESS  read-write
            STATUS      current
            DESCRIPTION
                "The upstream car profile index of the ONT port."
            ::= { hwGponDeviceSrvProfOntPortCfgEntry 7 }

        hwGponDeviceSrvProfOntPortCfgDownStreamCarTrafficTableId OBJECT-TYPE
            SYNTAX    Integer32
            MAX-ACCESS  read-write
            STATUS      current
            DESCRIPTION
                "The downstream car profile index of the ONT port."
            ::= { hwGponDeviceSrvProfOntPortCfgEntry 8 }

        hwGponDeviceSrvProfOntPortCfgDscpProfIndex OBJECT-TYPE
            SYNTAX      Integer32
            MAX-ACCESS  read-write
            STATUS      current
            DESCRIPTION
                "The dscp profile index of the ONT port."
            ::= { hwGponDeviceSrvProfOntPortCfgEntry 9 }

        hwGponDeviceSrvProfOntPortCfgUpIgmpTransmitMode OBJECT-TYPE
            SYNTAX INTEGER {
                transparent(1),
                translation(2),
                default(3),
                disable(254),
                invalid(-1)
                }
            MAX-ACCESS read-write
            STATUS current
            DESCRIPTION
                "This object indicates the upstream igmp packets transmit mode profile of GPON ONT port.
                 Options:
                 1. transparent(1)    - Indicates that the GPON ONT port upstream igmp packets transmit mode profile is transparent
                 2. translation(2)    - Indicates that the GPON ONT port upstream igmp packets transmit mode profile is translation
                 3. default(3)        - Indicates that the GPON ONT port upstream igmp packets transmit mode profile is default
                 4. disable(254)      - Indicates that the GPON ONT port upstream igmp packets transmit mode profile configured will be cancelled
                 5. invalid(-1)       - Indicates that the query fails or no information is detected
                "
           ::= { hwGponDeviceSrvProfOntPortCfgEntry 10 }

       hwGponDeviceSrvProfOntPortCfgUpIgmpMsgTranslationVlan OBJECT-TYPE
           SYNTAX Integer32 (-1|0..4095)
           MAX-ACCESS read-write
           STATUS current
           DESCRIPTION
               "The GPON ONT port upstream igmp packets will be translate to the translation vlan,
                if GPON ONT port upstream igmp packets forward mode is translation(2) or default(3).
               "
           ::= { hwGponDeviceSrvProfOntPortCfgEntry 11 }

       hwGponDeviceSrvProfOntPortCfgUpIgmpMsgPriority OBJECT-TYPE
           SYNTAX Integer32 (-1|0..7)
           MAX-ACCESS read-write
           STATUS current
           DESCRIPTION
                "When GPON ONT port upstream igmp packets were added a vlan or
                 translated to the translation vlan, priority was set.
                "
           ::= { hwGponDeviceSrvProfOntPortCfgEntry 12 }

       hwGponDeviceSrvProfOntPortCfgMaxMacAddressNum  OBJECT-TYPE
           SYNTAX Gauge32 (0..255 | 4294967295)
           MAX-ACCESS read-write
           STATUS current
           DESCRIPTION
               "This object indicates the maximum number of MAC addresses that can be learned on each ONT port.
                The number of MAC addresses learned on an ONT port should not greater than this number.
                range:0~255. 4294967295 is invalid value. 0 is default value, means unlimited.
               "
           ::= { hwGponDeviceSrvProfOntPortCfgEntry 13 }

       hwGponDeviceSrvProfOntPortCfgTDMPortTxClockMode  OBJECT-TYPE
           SYNTAX    INTEGER{
                  adapt(1),
                  system(2),
                  invalid(-1)
                 }
       MAX-ACCESS  read-write
       STATUS      current
       DESCRIPTION
               "This object indicates the tx-clock mode of ONT TDM port.
                Options:
                1. adapt(1)  - Indicates that the tx-clock mode of the ONT TDM port is adapt
                2. system(2) - Indicates that the tx-clock mode of the ONT TDM port is system
                3. invalid(-1) - Indicates that the query fails or no information is detected
               "
           ::= { hwGponDeviceSrvProfOntPortCfgEntry 14 }

       hwGponDeviceSrvProfOntPortCfgDownstreamMode OBJECT-TYPE
           SYNTAX INTEGER {
                    noOperation(1),
                    operationAndDiscardMismatch(2),
                    operationAndForwardMismatch(3),
                    invalid(-1)
                    }
           MAX-ACCESS read-write
           STATUS current
           DESCRIPTION
                "This object indicates the downstream mode of GPON ONT port.
                 Options:
                 1. noOperation(1)                 - Indicates not to process the VLAN tag of the downstram packets
                 2. operationAndDiscardMismatch(2) - Indicates to process the VLAN tag of the downstream packets and discard the packets with mismatched VLAN tag
                 3. operationAndForwardMismatch(3) - Indicates to process the VLAN tag of the downstream packets and forward the packets with mismatched VLAN tag
                 4. invalid(-1)                    - Indicates that the query fails or no information is detected
                "
           ::= { hwGponDeviceSrvProfOntPortCfgEntry 15 }

        hwGponDeviceSrvProfOntPortCfgUpStreamCarTrafficTableName OBJECT-TYPE
            SYNTAX    OCTET STRING  (SIZE (0..32))
            MAX-ACCESS  read-write
            STATUS      current
            DESCRIPTION
                "The upstream car profile name of the ONT port."
            ::= { hwGponDeviceSrvProfOntPortCfgEntry 16 }

        hwGponDeviceSrvProfOntPortCfgDownStreamCarTrafficTableName OBJECT-TYPE
            SYNTAX    OCTET STRING  (SIZE (0..32))
            MAX-ACCESS  read-write
            STATUS      current
            DESCRIPTION
                "The downstream car profile name of the ONT port."
            ::= { hwGponDeviceSrvProfOntPortCfgEntry 17 }

        hwGponDeviceSrvProfOntPortCfgClassProfileIndex OBJECT-TYPE
            SYNTAX    Integer32
            MAX-ACCESS  read-write
            STATUS      current
            DESCRIPTION
                "Indicates the index of the traffic classification profile configured on the ONT port.
                 The valid value range is 1~256.
                 The value (65534) indicates that the traffic classification profile is not bound to the port.
                 The value (-1) indicates that the query fails or no information is detected.
                "
            ::= { hwGponDeviceSrvProfOntPortCfgEntry 18 }

        hwGponDeviceSrvProfOntPortCfgUnknownUnicastRate OBJECT-TYPE
            SYNTAX Integer32
            MAX-ACCESS read-write
            STATUS current
            DESCRIPTION
                "This object indicates the unknown unicast traffic suppression on the ONT port.
                 The value (0~10000000) indicates the unknown unicast traffic maximum rate on the ONT port.
                 The value (-3) indicates that the unknown unicast traffic rate on the ONT port is unlimited.
                 The value (-2) indicates that the unknown unicast traffic suppression on the ONT port is not configured.
                 The value (-1) indicates that the query fails or no information is detected.
                 "
            ::= { hwGponDeviceSrvProfOntPortCfgEntry 19 }

        hwGponDeviceSrvProfOntPortCfgBroadcastRate OBJECT-TYPE
            SYNTAX Integer32
            MAX-ACCESS read-write
            STATUS current
            DESCRIPTION
                "This object indicates the broadcast traffic suppression on the ONT port.
                 The value (0~10000000) indicates the broadcast traffic maximum rate on the ONT port.
                 The value (-3) indicates that the broadcast traffic rate on the ONT port is unlimited.
                 The value (-2) indicates that the broadcast traffic suppression on the ONT port is not configured.
                 The value (-1) indicates that the query fails or no information is detected.
                 "
            ::= { hwGponDeviceSrvProfOntPortCfgEntry 20 }

        hwGponDeviceSrvProfOntPortCfgUnknownMulticastRate OBJECT-TYPE
            SYNTAX Integer32
            MAX-ACCESS read-write
            STATUS current
            DESCRIPTION
                "This object indicates the unknown multicast traffic suppression on the ONT port.
                 The value (0~10000000) indicates the multicast unicast traffic maximum rate on the ONT port.
                 The value (-3) indicates that the multicast unicast traffic rate on the ONT port is unlimited.
                 The value (-2) indicates that the multicast unicast traffic suppression on the ONT port is not configured.
                 The value (-1) indicates that the query fails or no information is detected.
                 "
            ::= { hwGponDeviceSrvProfOntPortCfgEntry 21 }

        hwGponDeviceSrvProfOntPortCfgL2IsolateSwitch OBJECT-TYPE
            SYNTAX    INTEGER
            {
                enable(1),
                disable(2),
                unconcern(254),
			    invalid(-1)
            }
            MAX-ACCESS  read-write
            STATUS      current
            DESCRIPTION
                "This object is used to configure Layer 2 isolation for a GPON ONT port.
				 The default value is unconcern(254).
                 Options:
                 1. enable(1)       - Indicates that the switch is enabled
                 2. disable(2)      - Indicates that the switch is disabled
				 3. unconcern(254)  - Indicates that the switch is unconcern
				 4. invalid(-1)     - Indicates that the query fails or no information is detected
                "
            ::= { hwGponDeviceSrvProfOntPortCfgEntry 22 }

--  Table hwGponDeviceSrvProfPortVlanCfgTable
        hwGponDeviceSrvProfPortVlanCfgTable OBJECT-TYPE
            SYNTAX SEQUENCE OF HwGponDeviceSrvProfPortVlanCfgEntry
            MAX-ACCESS not-accessible
            STATUS current
            DESCRIPTION
                "This is the GPON service profile port vlan config table.
                 The index of this table is a combination of hwGponDeviceSrvProfPortVlanCfgSrvProfNameIndex,
                 hwGponDeviceSrvProfPortVlanCfgOntPhyType, hwGponDeviceSrvProfPortVlanCfgOntPhyIndex,
                 hwGponDeviceSrvProfPortVlanCfgPortCVlan, hwGponDeviceSrvProfPortVlanCfgPortVlanCPri
                 and hwGponDeviceSrvProfPortVlanCfgEtherType.
                "
            ::= { hwXponDeviceProfileObjects 68 }

        hwGponDeviceSrvProfPortVlanCfgEntry OBJECT-TYPE
            SYNTAX HwGponDeviceSrvProfPortVlanCfgEntry
            MAX-ACCESS not-accessible
            STATUS current
            DESCRIPTION
                "This is the GPON service profile port vlan config table.
                 The index of this entry is a combination of hwGponDeviceSrvProfPortVlanCfgSrvProfNameIndex,
                 hwGponDeviceSrvProfPortVlanCfgOntPhyType, hwGponDeviceSrvProfPortVlanCfgOntPhyIndex,
                 hwGponDeviceSrvProfPortVlanCfgPortCVlan, hwGponDeviceSrvProfPortVlanCfgPortVlanCPri
                 and hwGponDeviceSrvProfPortVlanCfgEtherType.
                "
            INDEX { hwGponDeviceSrvProfPortVlanCfgSrvProfNameIndex, hwGponDeviceSrvProfPortVlanCfgOntPhyType,
                    hwGponDeviceSrvProfPortVlanCfgOntPhyIndex, hwGponDeviceSrvProfPortVlanCfgPortCVlan,
                    hwGponDeviceSrvProfPortVlanCfgPortVlanCPri, hwGponDeviceSrvProfPortVlanCfgEtherType}
            ::= { hwGponDeviceSrvProfPortVlanCfgTable 1 }

        HwGponDeviceSrvProfPortVlanCfgEntry ::=
            SEQUENCE {
                hwGponDeviceSrvProfPortVlanCfgSrvProfNameIndex              OCTET STRING,
                hwGponDeviceSrvProfPortVlanCfgOntPhyType                    INTEGER,
                hwGponDeviceSrvProfPortVlanCfgOntPhyIndex                   Integer32,
                hwGponDeviceSrvProfPortVlanCfgPortCVlan                     Integer32,
                hwGponDeviceSrvProfPortVlanCfgRowStatus                     RowStatus,
                hwGponDeviceSrvProfPortVlanCfgPortVlanType                  INTEGER,
                hwGponDeviceSrvProfPortVlanCfgPortVlanSPri                  Integer32,
                hwGponDeviceSrvProfPortVlanCfgPortSVlan                     Integer32,
                hwGponDeviceSrvProfPortVlanCfgPortVlanCPri                  Integer32,
                hwGponDeviceSrvProfPortVlanCfgEtherType                     Integer32,
                hwGponDeviceSrvProfPortVlanCfgPortVlanSPriPolicy            INTEGER,
                hwGponDeviceSrvProfPortVlanCfgDscpDefaultPriority           Integer32,
                hwGponDeviceSrvProfPortVlanCfgPortVlanTlsSwitch             INTEGER
             }

        hwGponDeviceSrvProfPortVlanCfgSrvProfNameIndex OBJECT-TYPE
            SYNTAX OCTET STRING (SIZE (1..32))
            MAX-ACCESS not-accessible
            STATUS current
            DESCRIPTION
                "This object indicates the XPON service profile name index."
            ::= { hwGponDeviceSrvProfPortVlanCfgEntry 1 }

        hwGponDeviceSrvProfPortVlanCfgOntPhyType OBJECT-TYPE
            SYNTAX INTEGER {
                t1(13),
                e1(14),
                fe(24),
                ge(34),
                vdsl(37),
                wifi(40),
                moca(46),
                eth(47),
                iphost(50)
            }
            MAX-ACCESS not-accessible
            STATUS current
            DESCRIPTION
                "This object indicates the port type of the ONT.
                 Options:
                 1. t1(13)             - T1
                 2. e1(14)             - E1
                 3. fe(24)             - FE
                 4. ge(34)             - GE
                 5. vdsl(37)           - VDSL
                 6. wifi(40)           - WiFi
                 7. moca(46)           - MOCA
                 8. eth(47)            - ETH
                 9. iphost(50)         - IPHOST
                "
            ::= { hwGponDeviceSrvProfPortVlanCfgEntry 2 }

        hwGponDeviceSrvProfPortVlanCfgOntPhyIndex OBJECT-TYPE
            SYNTAX Integer32
            MAX-ACCESS not-accessible
            STATUS current
            DESCRIPTION
                "This object indicates the port index of the ONT."
            ::= { hwGponDeviceSrvProfPortVlanCfgEntry 3 }

        hwGponDeviceSrvProfPortVlanCfgPortCVlan OBJECT-TYPE
            SYNTAX Integer32
            MAX-ACCESS not-accessible
            STATUS current
            DESCRIPTION
                "This object indicates the user-side VLAN of port on the GPON service profile.
                 Options:
                 1.user-vlan(0~4095)     - Indicates the VLAN for user-side packets of an ONT port
                 2.transparent(65534)    - Indicates the transparent transmission mode for packet forwarding. In this mode, packets are not processed and VLAN tags remain the same
                 3.untagged(65533)       - Indicates that user-side packets before VLAN translation do not carry VLAN tags
                 4.other-all(65532)      - Indicates that user-side packets before VLAN translation are ones that cannot be matched by specified VLAN or untagged VLAN
                 5.invalid(-1)           - Indicates that there is no VLAN translation, or this port is not in VLAN translation mode, for example, user-side packets is in priority translation mode, not concerned VLAN ID.
                "
            ::= { hwGponDeviceSrvProfPortVlanCfgEntry 4 }

        hwGponDeviceSrvProfPortVlanCfgRowStatus OBJECT-TYPE
            SYNTAX RowStatus
            MAX-ACCESS read-create
            STATUS current
            DESCRIPTION
                "The hwGponDeviceSrvProfPortVlanCfgRowStatus is used to create a new row
                 or to modify or delete an existing row in this table.
                 Options:
                 1. createAndGo(4) -create a new instance of a conceptual row
                 2. destroy(6)     -delete the instances associated with an existing conceptual row
                "
            ::= { hwGponDeviceSrvProfPortVlanCfgEntry 5 }

        hwGponDeviceSrvProfPortVlanCfgPortVlanType OBJECT-TYPE
            SYNTAX INTEGER {
                transparent(1),
                translation(2),
                qinq(3),
                invalid(-1)
            }
            MAX-ACCESS read-write
            STATUS current
            DESCRIPTION
                "This object indicates the XPON service profile port vlan type.
                 Options:
                 1. transparent(1)    - Indicates that the XPON service profile port vlan type is transparent
                 2. translation(2)    - Indicates that the XPON service profile port vlan type is translation
                 3. qinq(3)           - Indicates that the XPON service profile port vlan type is qinq
                 4. invalid(-1)       - Indicates that the query fails or no information is detected
                "
            ::= { hwGponDeviceSrvProfPortVlanCfgEntry 6 }

        hwGponDeviceSrvProfPortVlanCfgPortVlanSPri OBJECT-TYPE
            SYNTAX Integer32 (-1|0..7)
            MAX-ACCESS read-write
            STATUS current
            DESCRIPTION
                "This object indicates the GPON service profile port translation or qinq s-priority"
            ::= { hwGponDeviceSrvProfPortVlanCfgEntry 7 }

        hwGponDeviceSrvProfPortVlanCfgPortSVlan OBJECT-TYPE
            SYNTAX Integer32 (-1 | 0..4095)
            MAX-ACCESS read-write
            STATUS current
            DESCRIPTION
                "This object indicates the GPON service profile port service vlan."
            ::= { hwGponDeviceSrvProfPortVlanCfgEntry 8 }

        hwGponDeviceSrvProfPortVlanCfgPortVlanCPri OBJECT-TYPE
            SYNTAX Integer32
            MAX-ACCESS not-accessible
            STATUS current
            DESCRIPTION
                "This object indicates the GPON service profile port translation or qinq c-priority."
            ::= { hwGponDeviceSrvProfPortVlanCfgEntry 9 }

        hwGponDeviceSrvProfPortVlanCfgEtherType OBJECT-TYPE
            SYNTAX Integer32
            MAX-ACCESS read-write
            STATUS current
            DESCRIPTION
                "This object indicates the XPON service profile customer service encapsulation type.
                 Options:
                 1. ipv4-ipoe(1)  - Indicates that the XPON service profile customer service encapsulation type is ipv4 ipoe
                 2. pppoe(2)      - Indicates that the XPON service profile customer service encapsulation type is pppoe
                 3. ipv6-ipoe(4)  - Indicates that the XPON service profile customer service encapsulation type is ipv6 ipoe
                 4. invalid(-1)   - Indicates that the query fails or no information is detected
                 5. 0x600-0xffff  - Indicates that the XPON service profile customer service encapsulation type is user-defined
                "
            ::= { hwGponDeviceSrvProfPortVlanCfgEntry 10 }

        hwGponDeviceSrvProfPortVlanCfgPortVlanSPriPolicy OBJECT-TYPE
            SYNTAX INTEGER {
                invalid(-1),
                specify(1),
                userCos(2),
                dscpMapping(3)
            }
            MAX-ACCESS read-write
            STATUS current
            DESCRIPTION
                "This object indicates the s-vlan priority policy.
                 Options:
                 1. specify(1)      - Indicates that the s-vlan priority policy is specified
                 2. userCos(2)     - Indicates that the s-vlan priority policy is userCos
                 3. dscpMapping(3) - Indicates that the s-vlan priority policy is dscpMapping
                 4. invalid(-1)     - Indicates that the query fails or no information is detected
                "
            ::= { hwGponDeviceSrvProfPortVlanCfgEntry 11 }

        hwGponDeviceSrvProfPortVlanCfgDscpDefaultPriority OBJECT-TYPE
            SYNTAX      Integer32
            MAX-ACCESS  read-write
            STATUS      current
            DESCRIPTION
                "This object indicates the default priority for dscpMapping policy."
            ::= { hwGponDeviceSrvProfPortVlanCfgEntry 12 }

        hwGponDeviceSrvProfPortVlanCfgPortVlanTlsSwitch OBJECT-TYPE
            SYNTAX INTEGER {
                off(1),
                on(2),
                invalid(-1)
            }
            MAX-ACCESS read-write
            STATUS current
            DESCRIPTION
                "The switch used to config the attribute of vlan translation.
                 Options:
                 1. off(1)              - Indicates that the attribute of vlan translation is off
                 2. on(2)               - Indicates that the attribute of vlan translation is on
                 3. invalid(-1)         - Indicates that the query fails or no information is detected
                "
            ::= { hwGponDeviceSrvProfPortVlanCfgEntry 13 }

--  Table HwGponDeviceAlarmProfileInfoTable
        hwGponDeviceAlarmProfileInfoTable OBJECT-TYPE
            SYNTAX     SEQUENCE OF HwGponDeviceAlarmProfileInfoEntry
            MAX-ACCESS not-accessible
            STATUS     current
            DESCRIPTION
                "This is the GPON alarm profile table.
                 The index of this table is hwGponDeviceAlarmProfileInfoNameIndex.
                "
            ::= { hwXponDeviceProfileObjects 69 }

        hwGponDeviceAlarmProfileInfoEntry OBJECT-TYPE
            SYNTAX     HwGponDeviceAlarmProfileInfoEntry
            MAX-ACCESS not-accessible
            STATUS     current
            DESCRIPTION
                "This is the GPON alarm profile table.
                 The index of this entry is hwGponDeviceAlarmProfileInfoNameIndex.
                "
            INDEX       { IMPLIED hwGponDeviceAlarmProfileInfoNameIndex }
            ::= { hwGponDeviceAlarmProfileInfoTable 1 }

        HwGponDeviceAlarmProfileInfoEntry ::=
            SEQUENCE {
                hwGponDeviceAlarmProfileInfoNameIndex                             OCTET STRING,
                hwGponDeviceAlarmProfileBindNum                                   Integer32,
                hwGponDeviceAlarmProfileLostPacketsThreshold                      Integer32,
                hwGponDeviceAlarmProfileMisinsertedPacketsThreshold               Integer32,
                hwGponDeviceAlarmProfileImpairedBlocksThreshold                   Integer32,
                hwGponDeviceAlarmProfileFCSErrorsThreshold                        Integer32,
                hwGponDeviceAlarmProfileExcessiveCollisionCounterThreshold        Integer32,
                hwGponDeviceAlarmProfileLateCollisionCounterThreshold             Integer32,
                hwGponDeviceAlarmProfileFrameTooLongsThreshold                    Integer32,
                hwGponDeviceAlarmProfileBufferOverflowsonReceiveThreshold         Integer32,
                hwGponDeviceAlarmProfileBufferOverflowsonTransmitThreshold        Integer32,
                hwGponDeviceAlarmProfileSingleCollisionFrameCounterThreshold      Integer32,
                hwGponDeviceAlarmProfileMultipleCollisionsFrameCounterThreshold   Integer32,
                hwGponDeviceAlarmProfileSQECounterThreshold                       Integer32,
                hwGponDeviceAlarmProfileDeferredTransmissionCounterThreshold      Integer32,
                hwGponDeviceAlarmProfileInternalmactransmiterrorcounterThreshold  Integer32,
                hwGponDeviceAlarmProfileCarrierSenseErrorCounterThreshold         Integer32,
                hwGponDeviceAlarmProfileAlignmentErrorCounterThreshold            Integer32,
                hwGponDeviceAlarmProfileInternalMACReceiveErrorCounterThreshold   Integer32,
                hwGponDeviceAlarmProfilePPPoEFilteredFrameCounterThreshold        Integer32,
                hwGponDeviceAlarmProfileDelayExceededDiscardThreshold             Integer32,
                hwGponDeviceAlarmProfileMTUExceededDiscardThreshold               Integer32,
                hwGponDeviceAlarmProfileReceivedAndDiscardedThreshold             Integer32,
                hwGponDeviceAlarmProfileCESErrorSecondsThreshold                  Integer32,
                hwGponDeviceAlarmProfileCESSeverelyErrorSecondsThreshold          Integer32,
                hwGponDeviceAlarmProfileCESBurstyErrorSecondsThreshold            Integer32,
                hwGponDeviceAlarmProfileCESUnavailableSecondsThreshold            Integer32,
                hwGponDeviceAlarmProfileCESControlledSlipSecondsThreshold         Integer32,
                hwGponDeviceAlarmProfileDropEventsThreshold                       Integer32,
                hwGponDeviceAlarmProfileUndersizepacketsThreshold                 Integer32,
                hwGponDeviceAlarmProfileFragmentsThreshold                        Integer32,
                hwGponDeviceAlarmProfileJabbersThreshold                          Integer32,
                hwGponDeviceAlarmProfileFailedSignalOfOnuThreshold                Integer32,
                hwGponDeviceAlarmProfileDegradedSignalOfOnuThreshold              Integer32,
                hwGponDeviceAlarmProfileFECUncorrectCodeWordsThreshold            Gauge32,
                hwGponDeviceAlarmProfileFECCorrectCodeWordsThreshold              Gauge32,
                hwGponDeviceAlarmProfileUpstreamPQDiscardedBytesThreshold         Integer32,
                hwGponDeviceAlarmProfileDownstreamPQDiscardedBytesThreshold       Integer32,
                hwGponDeviceAlarmProfileRowStatus                                 RowStatus,
                hwGponDeviceAlarmProfileEncryptionKeyErrorsOfOnuThreshold         Integer32,
                hwGponDeviceAlarmProfileXgemKeyErrorsOfOnuThreshold               Integer32,
                hwGponDeviceAlarmProfileXgemHecErrorCountOfOnuThreshold           Integer32
            }

        hwGponDeviceAlarmProfileInfoNameIndex OBJECT-TYPE
            SYNTAX     OCTET STRING (SIZE (1..33))
            MAX-ACCESS    not-accessible
            STATUS      current
            DESCRIPTION
                "This object indicates the alarm profile name."
            ::= { hwGponDeviceAlarmProfileInfoEntry 1 }

        hwGponDeviceAlarmProfileBindNum OBJECT-TYPE
            SYNTAX     Integer32
            MAX-ACCESS    read-only
            STATUS      current
            DESCRIPTION
                "This object indicates the binding times of the profile."
            ::= { hwGponDeviceAlarmProfileInfoEntry 2 }

        hwGponDeviceAlarmProfileLostPacketsThreshold OBJECT-TYPE
            SYNTAX     Integer32
            MAX-ACCESS    read-write
            STATUS      current
            DESCRIPTION
                "This object indicates the loss of frames threshold of GEM port."
            ::= { hwGponDeviceAlarmProfileInfoEntry 3 }

        hwGponDeviceAlarmProfileMisinsertedPacketsThreshold OBJECT-TYPE
            SYNTAX     Integer32
            MAX-ACCESS    read-write
            STATUS      current
            DESCRIPTION
                "This object indicates the mis-inserted frames threshold of GEM port."
            ::= { hwGponDeviceAlarmProfileInfoEntry 4 }

        hwGponDeviceAlarmProfileImpairedBlocksThreshold OBJECT-TYPE
            SYNTAX     Integer32
            MAX-ACCESS    read-write
            STATUS      current
            DESCRIPTION
                "This object indicates the impaired blocks alarm threshold of GEM port."
            ::= { hwGponDeviceAlarmProfileInfoEntry 5 }

        hwGponDeviceAlarmProfileFCSErrorsThreshold OBJECT-TYPE
            SYNTAX     Integer32
            MAX-ACCESS    read-write
            STATUS      current
            DESCRIPTION
                "This object indicates the Ethernet FCS errors alarm threshold."
            ::= { hwGponDeviceAlarmProfileInfoEntry 6 }

        hwGponDeviceAlarmProfileExcessiveCollisionCounterThreshold OBJECT-TYPE
            SYNTAX     Integer32
            MAX-ACCESS    read-write
            STATUS      current
            DESCRIPTION
                "This object indicates the ethernet excessive collision count alarm threshold."
            ::= { hwGponDeviceAlarmProfileInfoEntry 7 }

        hwGponDeviceAlarmProfileLateCollisionCounterThreshold OBJECT-TYPE
            SYNTAX     Integer32
            MAX-ACCESS    read-write
            STATUS      current
            DESCRIPTION
                "This object indicates the ethernet late collision count alarm threshold within 512 bit-times."
            ::= { hwGponDeviceAlarmProfileInfoEntry 8 }

        hwGponDeviceAlarmProfileFrameTooLongsThreshold OBJECT-TYPE
            SYNTAX     Integer32
            MAX-ACCESS    read-write
            STATUS      current
            DESCRIPTION
                "This object indicates the too long Ethernet frames alarm threshold."
            ::= { hwGponDeviceAlarmProfileInfoEntry 9 }

        hwGponDeviceAlarmProfileBufferOverflowsonReceiveThreshold OBJECT-TYPE
            SYNTAX     Integer32
            MAX-ACCESS    read-write
            STATUS      current
            DESCRIPTION
                "This object indicates the Ethernet buffer received overflows alarm threshold."
            ::= { hwGponDeviceAlarmProfileInfoEntry 10 }

        hwGponDeviceAlarmProfileBufferOverflowsonTransmitThreshold OBJECT-TYPE
            SYNTAX     Integer32
            MAX-ACCESS    read-write
            STATUS      current
            DESCRIPTION
                "This object indicates the alarm threshold of transmit buffer overflows."
            ::= { hwGponDeviceAlarmProfileInfoEntry 11 }

        hwGponDeviceAlarmProfileSingleCollisionFrameCounterThreshold OBJECT-TYPE
            SYNTAX     Integer32
            MAX-ACCESS    read-write
            STATUS      current
            DESCRIPTION
                "This object indicates alarm threshold of the Ethernet single collision frame count."
            ::= { hwGponDeviceAlarmProfileInfoEntry 12 }

        hwGponDeviceAlarmProfileMultipleCollisionsFrameCounterThreshold OBJECT-TYPE
            SYNTAX     Integer32
            MAX-ACCESS    read-write
            STATUS      current
            DESCRIPTION
                "This object indicates the alarm threshold of Ethernet multiple collisions frame count."
            ::= { hwGponDeviceAlarmProfileInfoEntry 13 }

        hwGponDeviceAlarmProfileSQECounterThreshold OBJECT-TYPE
            SYNTAX     Integer32
            MAX-ACCESS    read-write
            STATUS      current
            DESCRIPTION
                "This object indicates the alarm threshold of Ethernet SQE test error messages count."
            ::= { hwGponDeviceAlarmProfileInfoEntry 14 }

        hwGponDeviceAlarmProfileDeferredTransmissionCounterThreshold OBJECT-TYPE
            SYNTAX     Integer32
            MAX-ACCESS    read-write
            STATUS      current
            DESCRIPTION
                "This object indicates the alarm threshold of the deferred frames count."
            ::= { hwGponDeviceAlarmProfileInfoEntry 15 }

        hwGponDeviceAlarmProfileInternalmactransmiterrorcounterThreshold OBJECT-TYPE
            SYNTAX     Integer32
            MAX-ACCESS    read-write
            STATUS      current
            DESCRIPTION
                "This object indicates the alarm threshold of transmit errors at the MAC sub-layer."
            ::= { hwGponDeviceAlarmProfileInfoEntry 16 }

        hwGponDeviceAlarmProfileCarrierSenseErrorCounterThreshold OBJECT-TYPE
            SYNTAX     Integer32
            MAX-ACCESS    read-write
            STATUS      current
            DESCRIPTION
                "This object indicates the alarm threshold of carrier sense errors."
            ::= { hwGponDeviceAlarmProfileInfoEntry 17 }

        hwGponDeviceAlarmProfileAlignmentErrorCounterThreshold OBJECT-TYPE
            SYNTAX     Integer32
            MAX-ACCESS    read-write
            STATUS      current
            DESCRIPTION
                "This object indicates the alarm threshold of frame alignment errors."
            ::= { hwGponDeviceAlarmProfileInfoEntry 18 }

        hwGponDeviceAlarmProfileInternalMACReceiveErrorCounterThreshold OBJECT-TYPE
            SYNTAX     Integer32
            MAX-ACCESS    read-write
            STATUS      current
            DESCRIPTION
                "This object indicates the alarm threshold of receive errors at the MAC sub-layer."
            ::= { hwGponDeviceAlarmProfileInfoEntry 19 }

        hwGponDeviceAlarmProfilePPPoEFilteredFrameCounterThreshold OBJECT-TYPE
            SYNTAX     Integer32
            MAX-ACCESS    read-write
            STATUS      current
            DESCRIPTION
                "This object indicates the alarm threshold of filtered PPPoE frames."
            ::= { hwGponDeviceAlarmProfileInfoEntry 20 }

        hwGponDeviceAlarmProfileDelayExceededDiscardThreshold OBJECT-TYPE
            SYNTAX     Integer32
            MAX-ACCESS read-write
            STATUS  current
            DESCRIPTION
                "This object indicates the alarm threshold of frames discarded due to timeout."
            ::= { hwGponDeviceAlarmProfileInfoEntry 21 }

        hwGponDeviceAlarmProfileMTUExceededDiscardThreshold OBJECT-TYPE
            SYNTAX     Integer32
            MAX-ACCESS read-write
            STATUS  current
            DESCRIPTION
                "This object indicates the alarm threshold of frames dropped due to excessive MTU."
            ::= { hwGponDeviceAlarmProfileInfoEntry 22 }

        hwGponDeviceAlarmProfileReceivedAndDiscardedThreshold OBJECT-TYPE
            SYNTAX     Integer32
            MAX-ACCESS read-write
            STATUS  current
            DESCRIPTION
                "This object indicates the alarm threshold of received error frames."
            ::= { hwGponDeviceAlarmProfileInfoEntry 23 }

        hwGponDeviceAlarmProfileCESErrorSecondsThreshold OBJECT-TYPE
            SYNTAX     Integer32
            MAX-ACCESS    read-write
            STATUS      current
            DESCRIPTION
                "This object indicates the alarm threshold of CES errored seconds."
            ::= { hwGponDeviceAlarmProfileInfoEntry 26 }

        hwGponDeviceAlarmProfileCESSeverelyErrorSecondsThreshold OBJECT-TYPE
            SYNTAX     Integer32
            MAX-ACCESS    read-write
            STATUS      current
            DESCRIPTION
                "This object indicates the alarm threshold of CES severely errored seconds."
            ::= { hwGponDeviceAlarmProfileInfoEntry 27 }

        hwGponDeviceAlarmProfileCESBurstyErrorSecondsThreshold OBJECT-TYPE
            SYNTAX     Integer32
            MAX-ACCESS    read-write
            STATUS      current
            DESCRIPTION
                "This object indicates the alarm threshold of CES bursty errored seconds."
            ::= { hwGponDeviceAlarmProfileInfoEntry 28 }

        hwGponDeviceAlarmProfileCESUnavailableSecondsThreshold OBJECT-TYPE
            SYNTAX     Integer32
            MAX-ACCESS    read-write
            STATUS      current
            DESCRIPTION
                "This object indicates the alarm threshold of CES unavailable seconds."
            ::= { hwGponDeviceAlarmProfileInfoEntry 29 }

        hwGponDeviceAlarmProfileCESControlledSlipSecondsThreshold OBJECT-TYPE
            SYNTAX     Integer32
            MAX-ACCESS    read-write
            STATUS      current
            DESCRIPTION
                "This object indicates the alarm threshold of CES controlled slip seconds."
            ::= { hwGponDeviceAlarmProfileInfoEntry 30 }

        hwGponDeviceAlarmProfileDropEventsThreshold OBJECT-TYPE
            SYNTAX     Integer32
            MAX-ACCESS    read-write
            STATUS      current
            DESCRIPTION
                "This object indicates the alarm threshold of discarded packets."
            ::= { hwGponDeviceAlarmProfileInfoEntry 31 }

        hwGponDeviceAlarmProfileUndersizepacketsThreshold OBJECT-TYPE
            SYNTAX     Integer32
            MAX-ACCESS    read-write
            STATUS      current
            DESCRIPTION
                "This object indicates the alarm threshold of undersized packets."
            ::= { hwGponDeviceAlarmProfileInfoEntry 32 }

        hwGponDeviceAlarmProfileFragmentsThreshold OBJECT-TYPE
            SYNTAX     Integer32
            MAX-ACCESS    read-write
            STATUS      current
            DESCRIPTION
                "This object indicates the alarm threshold of fragments."
            ::= { hwGponDeviceAlarmProfileInfoEntry 33 }

        hwGponDeviceAlarmProfileJabbersThreshold OBJECT-TYPE
            SYNTAX     Integer32
            MAX-ACCESS    read-write
            STATUS      current
            DESCRIPTION
                "This object indicates the alarm threshold of jabbers."
            ::= { hwGponDeviceAlarmProfileInfoEntry 34 }

        hwGponDeviceAlarmProfileFailedSignalOfOnuThreshold OBJECT-TYPE
            SYNTAX     Integer32
            MAX-ACCESS    read-write
            STATUS      current
            DESCRIPTION
                "This object indicates the threshold of ONT signal failures(Format:1e-x).,range:3~8
                 for example: if the value of the leaf is 3,the actual value is 0.001,
                 if the value of the leaf is 8,the actual value is 0.00000001
                "
            ::= { hwGponDeviceAlarmProfileInfoEntry 35 }

        hwGponDeviceAlarmProfileDegradedSignalOfOnuThreshold OBJECT-TYPE
            SYNTAX     Integer32
            MAX-ACCESS    read-write
            STATUS      current
            DESCRIPTION
                "This object indicates the threshold of ONT degraded signals(Format:1e-x),range:4~9
                 for example: if the value of the leaf is 4,the actual value is 0.0001,
                 if the value of the leaf is 9,the actual value is 0.000000001.
                "
            ::= { hwGponDeviceAlarmProfileInfoEntry 36 }

        hwGponDeviceAlarmProfileFECUncorrectCodeWordsThreshold OBJECT-TYPE
            SYNTAX     Gauge32 (0..1101600000 | 4294967295)
            MAX-ACCESS    read-write
            STATUS      current
            DESCRIPTION
                "This object indicates the threshold of the code words that were not corrected by
                 the FEC function, range:0~1101600000. 4294967295 is invalid value.
                "
            ::= { hwGponDeviceAlarmProfileInfoEntry 37 }

        hwGponDeviceAlarmProfileFECCorrectCodeWordsThreshold OBJECT-TYPE
            SYNTAX     Gauge32 (0..1101600000 | 4294967295)
            MAX-ACCESS    read-write
            STATUS      current
            DESCRIPTION
                "This object indicates the threshold of the code words that were corrected by the
                 FEC function, range:0~1101600000. 4294967295 is invalid value.
                "
            ::= { hwGponDeviceAlarmProfileInfoEntry 38 }

        hwGponDeviceAlarmProfileUpstreamPQDiscardedBytesThreshold OBJECT-TYPE
            SYNTAX     Integer32
            MAX-ACCESS    read-write
            STATUS      current
            DESCRIPTION
                "Upstream PQ discarded byte alarm threshold, range:0~65535. If this parameter is set to an invalid value 0, the PQ alarm statistics function is disabled."
            ::= { hwGponDeviceAlarmProfileInfoEntry 39 }

        hwGponDeviceAlarmProfileDownstreamPQDiscardedBytesThreshold OBJECT-TYPE
            SYNTAX     Integer32
            MAX-ACCESS    read-write
            STATUS      current
            DESCRIPTION
                "Downstream PQ discarded byte alarm threshold, range:0~65535. If this parameter is set to an invalid value 0, the PQ alarm statistics function is disabled."
            ::= { hwGponDeviceAlarmProfileInfoEntry 40 }

        hwGponDeviceAlarmProfileRowStatus OBJECT-TYPE
            SYNTAX     RowStatus
            MAX-ACCESS    read-create
            STATUS      current
            DESCRIPTION
                "The hwGponDeviceAlarmProfileRowStatus is used to create a new row
                 or to modify or delete an existing row in this table.
                 Options:
                 1. createAndGo(4) -create a new instance of a conceptual row
                 2. destroy(6)     -delete the instances associated with an existing conceptual row
                "
            ::= { hwGponDeviceAlarmProfileInfoEntry 50 }

        hwGponDeviceAlarmProfileEncryptionKeyErrorsOfOnuThreshold OBJECT-TYPE
            SYNTAX     Integer32
            MAX-ACCESS    read-write
            STATUS      current
            DESCRIPTION
                "Encryption key errors Of Onu Threshold, range:0~100.
                "
            ::= { hwGponDeviceAlarmProfileInfoEntry 51 }

        hwGponDeviceAlarmProfileXgemKeyErrorsOfOnuThreshold OBJECT-TYPE
            SYNTAX     Integer32
            MAX-ACCESS    read-write
            STATUS      current
            DESCRIPTION
                "XGEM key errors Of Onu Threshold, range:0~100.
                "
            ::= { hwGponDeviceAlarmProfileInfoEntry 52 }

        hwGponDeviceAlarmProfileXgemHecErrorCountOfOnuThreshold OBJECT-TYPE
            SYNTAX     Integer32
            MAX-ACCESS    read-write
            STATUS      current
            DESCRIPTION
                "XGEM HEC error count Of Onu Threshold,range:0~100.
                "
            ::= { hwGponDeviceAlarmProfileInfoEntry 53 }
-- hwXponDeviceProfileObjects  end

-- hwXponDeviceStatisticObjects  begin

-- Table: hwGponOltEthernetStatisticTable
        hwGponOltEthernetStatisticTable OBJECT-TYPE
            SYNTAX     SEQUENCE OF HwGponOltEthernetStatisticEntry
            MAX-ACCESS not-accessible
            STATUS     current
            DESCRIPTION
                "The GPON port ether statistics table. The index of this table is ifIndex."
            ::= { hwXponDeviceStatisticObjects 21 }

        hwGponOltEthernetStatisticEntry OBJECT-TYPE
            SYNTAX     HwGponOltEthernetStatisticEntry
            MAX-ACCESS not-accessible
            STATUS     current
            DESCRIPTION
                "The GPON port ether statistics table. The index of this entry is ifIndex."
            INDEX       { ifIndex }
            ::= { hwGponOltEthernetStatisticTable 1 }

        HwGponOltEthernetStatisticEntry ::=
            SEQUENCE {
                hwGponOltEthernetStatisticReceivedPakts                  Counter64,
                hwGponOltEthernetStatisticSendPakts                      Counter64,
                hwGponOltEthernetStatisticDropPakts                      Counter64,
                hwGponOltEthernetStatisticReceivedTotalPakts             Counter64,
                hwGponOltEthernetStatisticReceivedBroadcastPakts         Counter64,
                hwGponOltEthernetStatisticReceivedMulticastPakts         Counter64,
                hwGponOltEthernetStatisticReceivedUnicastPakts           Counter64,
                hwGponOltEthernetStatisticReceivedLen64Bytes             Counter64,
                hwGponOltEthernetStatisticReceivedLen65To127Bytes        Counter64,
                hwGponOltEthernetStatisticReceivedLen128To255Bytes       Counter64,
                hwGponOltEthernetStatisticReceivedLen256To511Bytes       Counter64,
                hwGponOltEthernetStatisticReceivedLen512To1023Bytes      Counter64,
                hwGponOltEthernetStatisticReceivedLen1024To1518Bytes     Counter64,
                hwGponOltEthernetStatisticReceivedLenMore1518Bytes       Counter64,
                hwGponOltEthernetStatisticReceivedBytes                  Counter64,
                hwGponOltEthernetStatisticReceivedTooLongPakts           Counter64,
                hwGponOltEthernetStatisticReceivedTooShortPakts          Counter64,
                hwGponOltEthernetStatisticReceivedCRCErrPakts            Counter64,
                hwGponOltEthernetStatisticSendTotalPakts                 Counter64,
                hwGponOltEthernetStatisticSendBroadcastPakts             Counter64,
                hwGponOltEthernetStatisticSendMulticastPakts             Counter64,
                hwGponOltEthernetStatisticSendUnicastPakts               Counter64,
                hwGponOltEthernetStatisticSendLen64Bytes                 Counter64,
                hwGponOltEthernetStatisticSendLen65To127Bytes            Counter64,
                hwGponOltEthernetStatisticSendLen128To255Bytes           Counter64,
                hwGponOltEthernetStatisticSendLen256To511Bytes           Counter64,
                hwGponOltEthernetStatisticSendLen512To1023Bytes          Counter64,
                hwGponOltEthernetStatisticSendLen1024To1518Bytes         Counter64,
                hwGponOltEthernetStatisticSendLenMore1518Bytes           Counter64,
                hwGponOltEthernetStatisticSendBytes                      Counter64,
                hwGponOltEthernetStatisticSendMulticastBytes             Counter64,
                hwGponOltEtherStatisticSendBufferOverflowDropPakts       Counter64,
                hwGponOltEthernetStatisticSendGreenOctets                Counter64,
                hwGponOltEthernetStatisticSendGreenPakts                 Counter64,
                hwGponOltEthernetStatisticGreenDropPakts                 Counter64,
                hwGponOltEthernetStatisticSendYellowOctets               Counter64,
                hwGponOltEthernetStatisticSendYellowPakts                Counter64,
                hwGponOltEthernetStatisticYellowDropPakts                Counter64,
                hwGponOltEthernetStatisticClear                          INTEGER
            }

        hwGponOltEthernetStatisticReceivedPakts  OBJECT-TYPE
            SYNTAX     Counter64
            MAX-ACCESS   read-only
            STATUS      current
            DESCRIPTION
                "This object indicates the received frames."
            ::= { hwGponOltEthernetStatisticEntry 1 }

        hwGponOltEthernetStatisticSendPakts  OBJECT-TYPE
            SYNTAX     Counter64
            MAX-ACCESS   read-only
            STATUS      current
            DESCRIPTION
                "This object indicates the sent frames."
            ::= { hwGponOltEthernetStatisticEntry 2 }

        hwGponOltEthernetStatisticDropPakts  OBJECT-TYPE
            SYNTAX     Counter64
            MAX-ACCESS   read-only
            STATUS      current
            DESCRIPTION
                "This object indicates the number of Ethernet frames, including oversized frames,
                 undersized frames, and CRC failures.
                "
            ::= { hwGponOltEthernetStatisticEntry 3 }

        hwGponOltEthernetStatisticReceivedTotalPakts  OBJECT-TYPE
            SYNTAX     Counter64
            MAX-ACCESS   read-only
            STATUS      current
            DESCRIPTION
                "This object indicates the received GEM frames."
            ::= { hwGponOltEthernetStatisticEntry 4 }

        hwGponOltEthernetStatisticReceivedBroadcastPakts  OBJECT-TYPE
            SYNTAX     Counter64
            MAX-ACCESS   read-only
            STATUS      current
            DESCRIPTION
                "This object indicates the received broadcast frames."
            ::= { hwGponOltEthernetStatisticEntry 5 }

        hwGponOltEthernetStatisticReceivedMulticastPakts  OBJECT-TYPE
            SYNTAX     Counter64
            MAX-ACCESS   read-only
            STATUS      current
            DESCRIPTION
                "This object indicates the received multicast frames."
            ::= { hwGponOltEthernetStatisticEntry 6 }

        hwGponOltEthernetStatisticReceivedUnicastPakts  OBJECT-TYPE
            SYNTAX     Counter64
            MAX-ACCESS   read-only
            STATUS      current
            DESCRIPTION
                "This object indicates the received unicast frames."
            ::= { hwGponOltEthernetStatisticEntry 7 }

        hwGponOltEthernetStatisticReceivedLen64Bytes    OBJECT-TYPE
            SYNTAX     Counter64
            MAX-ACCESS   read-only
            STATUS      current
            DESCRIPTION
                "This object indicates the received 64-octet frames."
            ::= { hwGponOltEthernetStatisticEntry 8 }

        hwGponOltEthernetStatisticReceivedLen65To127Bytes    OBJECT-TYPE
            SYNTAX     Counter64
            MAX-ACCESS   read-only
            STATUS      current
            DESCRIPTION
                "This object indicates the received 65~127-octet frames."
            ::= { hwGponOltEthernetStatisticEntry 9 }

        hwGponOltEthernetStatisticReceivedLen128To255Bytes    OBJECT-TYPE
            SYNTAX     Counter64
            MAX-ACCESS   read-only
            STATUS      current
            DESCRIPTION
                "This object indicates the received 128~255-octet frames."
            ::= { hwGponOltEthernetStatisticEntry 10 }

        hwGponOltEthernetStatisticReceivedLen256To511Bytes    OBJECT-TYPE
            SYNTAX     Counter64
            MAX-ACCESS   read-only
            STATUS      current
            DESCRIPTION
                "This object indicates the received 256~511-octet frames."
            ::= { hwGponOltEthernetStatisticEntry 11 }

        hwGponOltEthernetStatisticReceivedLen512To1023Bytes    OBJECT-TYPE
            SYNTAX     Counter64
            MAX-ACCESS   read-only
            STATUS      current
            DESCRIPTION
                "This object indicates the received 512~1023-octet frames."
            ::= { hwGponOltEthernetStatisticEntry 12 }

        hwGponOltEthernetStatisticReceivedLen1024To1518Bytes    OBJECT-TYPE
            SYNTAX     Counter64
            MAX-ACCESS   read-only
            STATUS      current
            DESCRIPTION
                "This object indicates the received 1024~1518-octet frames."
            ::= { hwGponOltEthernetStatisticEntry 13 }

        hwGponOltEthernetStatisticReceivedLenMore1518Bytes    OBJECT-TYPE
            SYNTAX     Counter64
            MAX-ACCESS   read-only
            STATUS      current
            DESCRIPTION
                "This object indicates the received over 1518-octet frames."
            ::= { hwGponOltEthernetStatisticEntry 14 }

        hwGponOltEthernetStatisticReceivedBytes    OBJECT-TYPE
            SYNTAX     Counter64
            MAX-ACCESS   read-only
            STATUS      current
            DESCRIPTION
                "This object indicates the received octets."
            ::= { hwGponOltEthernetStatisticEntry 15 }

        hwGponOltEthernetStatisticReceivedTooLongPakts    OBJECT-TYPE
            SYNTAX     Counter64
            MAX-ACCESS   read-only
            STATUS      current
            DESCRIPTION
                "This object indicates the received oversize frames."
            ::= { hwGponOltEthernetStatisticEntry 16 }

        hwGponOltEthernetStatisticReceivedTooShortPakts    OBJECT-TYPE
            SYNTAX     Counter64
            MAX-ACCESS   read-only
            STATUS      current
            DESCRIPTION
                "This object indicates the received undersize frames."
            ::= { hwGponOltEthernetStatisticEntry 17 }

        hwGponOltEthernetStatisticReceivedCRCErrPakts    OBJECT-TYPE
            SYNTAX     Counter64
            MAX-ACCESS   read-only
            STATUS      current
            DESCRIPTION
                "This object indicates the received error frames."
            ::= { hwGponOltEthernetStatisticEntry 18 }

        hwGponOltEthernetStatisticSendTotalPakts    OBJECT-TYPE
            SYNTAX     Counter64
            MAX-ACCESS   read-only
            STATUS      current
            DESCRIPTION
                "This object indicates the send GEM frames."
            ::= { hwGponOltEthernetStatisticEntry 19 }

        hwGponOltEthernetStatisticSendBroadcastPakts    OBJECT-TYPE
            SYNTAX     Counter64
            MAX-ACCESS   read-only
            STATUS      current
            DESCRIPTION
                "This object indicates the send broadcast frames."
            ::= { hwGponOltEthernetStatisticEntry 20 }

        hwGponOltEthernetStatisticSendMulticastPakts    OBJECT-TYPE
            SYNTAX     Counter64
            MAX-ACCESS   read-only
            STATUS      current
            DESCRIPTION
                "This object indicates the send multicast frames."
            ::= { hwGponOltEthernetStatisticEntry 21 }

        hwGponOltEthernetStatisticSendUnicastPakts    OBJECT-TYPE
            SYNTAX     Counter64
            MAX-ACCESS   read-only
            STATUS      current
            DESCRIPTION
                "This object indicates the send unicast frames."
            ::= { hwGponOltEthernetStatisticEntry 22 }

        hwGponOltEthernetStatisticSendLen64Bytes    OBJECT-TYPE
            SYNTAX     Counter64
            MAX-ACCESS   read-only
            STATUS      current
            DESCRIPTION
                "This object indicates the sent 64-octet frames."
            ::= { hwGponOltEthernetStatisticEntry 23 }

        hwGponOltEthernetStatisticSendLen65To127Bytes    OBJECT-TYPE
            SYNTAX     Counter64
            MAX-ACCESS   read-only
            STATUS      current
            DESCRIPTION
                "This object indicates the sent 65~127-octet frames."
            ::= { hwGponOltEthernetStatisticEntry 24 }

        hwGponOltEthernetStatisticSendLen128To255Bytes    OBJECT-TYPE
            SYNTAX     Counter64
            MAX-ACCESS   read-only
            STATUS      current
            DESCRIPTION
                "This object indicates the sent 128~255-octet frames."
            ::= { hwGponOltEthernetStatisticEntry 25 }

        hwGponOltEthernetStatisticSendLen256To511Bytes    OBJECT-TYPE
            SYNTAX     Counter64
            MAX-ACCESS   read-only
            STATUS      current
            DESCRIPTION
                "This object indicates the sent 256~511-octet frames."
            ::= { hwGponOltEthernetStatisticEntry 26 }

        hwGponOltEthernetStatisticSendLen512To1023Bytes    OBJECT-TYPE
            SYNTAX     Counter64
            MAX-ACCESS   read-only
            STATUS      current
            DESCRIPTION
                "This object indicates the sent 512~1023-octet frames."
            ::= { hwGponOltEthernetStatisticEntry 27 }

        hwGponOltEthernetStatisticSendLen1024To1518Bytes    OBJECT-TYPE
            SYNTAX     Counter64
            MAX-ACCESS   read-only
            STATUS      current
            DESCRIPTION
                "This object indicates the sent 1024~1518-octet frames."
            ::= { hwGponOltEthernetStatisticEntry 28 }

        hwGponOltEthernetStatisticSendLenMore1518Bytes    OBJECT-TYPE
            SYNTAX     Counter64
            MAX-ACCESS   read-only
            STATUS      current
            DESCRIPTION
                "This object indicates the sent over 1518-octet frames."
            ::= { hwGponOltEthernetStatisticEntry 29 }

        hwGponOltEthernetStatisticSendBytes    OBJECT-TYPE
            SYNTAX     Counter64
            MAX-ACCESS   read-only
            STATUS      current
            DESCRIPTION
                "This object indicates the sent octets."
            ::= { hwGponOltEthernetStatisticEntry 30 }

        hwGponOltEthernetStatisticSendMulticastBytes    OBJECT-TYPE
            SYNTAX     Counter64
            MAX-ACCESS   read-only
            STATUS      current
            DESCRIPTION
                "This object indicates the sent multicast bytes."
            ::= { hwGponOltEthernetStatisticEntry 31 }

        hwGponOltEtherStatisticSendBufferOverflowDropPakts    OBJECT-TYPE
            SYNTAX     Counter64
            MAX-ACCESS   read-only
            STATUS      current
            DESCRIPTION
                "This object indicates the sent overflow drop frames."
            ::= { hwGponOltEthernetStatisticEntry 32 }

        hwGponOltEthernetStatisticSendGreenOctets    OBJECT-TYPE
            SYNTAX     Counter64
            MAX-ACCESS   read-only
            STATUS      current
            DESCRIPTION
                "This object indicates the sent green frames."
            ::= { hwGponOltEthernetStatisticEntry 33 }

        hwGponOltEthernetStatisticSendGreenPakts    OBJECT-TYPE
            SYNTAX     Counter64
            MAX-ACCESS   read-only
            STATUS      current
            DESCRIPTION
                "This object indicates the sent green frames."
            ::= { hwGponOltEthernetStatisticEntry 34 }

        hwGponOltEthernetStatisticGreenDropPakts    OBJECT-TYPE
            SYNTAX     Counter64
            MAX-ACCESS   read-only
            STATUS      current
            DESCRIPTION
                "This object indicates the discarded green packets due to congestion."
            ::= { hwGponOltEthernetStatisticEntry 35 }

        hwGponOltEthernetStatisticSendYellowOctets    	OBJECT-TYPE
            SYNTAX     Counter64
            MAX-ACCESS   read-only
            STATUS      current
            DESCRIPTION
                "This object indicates the sent yellow octets."
            ::= { hwGponOltEthernetStatisticEntry 36 }

        hwGponOltEthernetStatisticSendYellowPakts    OBJECT-TYPE
            SYNTAX     Counter64
            MAX-ACCESS   read-only
            STATUS      current
            DESCRIPTION
                "This object indicates the sent yellow frames."
            ::= { hwGponOltEthernetStatisticEntry 37}

        hwGponOltEthernetStatisticYellowDropPakts    OBJECT-TYPE
            SYNTAX     Counter64
            MAX-ACCESS   read-only
            STATUS      current
            DESCRIPTION
                "This object indicates the discarded yellow packets due to congestion."
            ::= { hwGponOltEthernetStatisticEntry 38 }

        hwGponOltEthernetStatisticClear    OBJECT-TYPE
            SYNTAX     INTEGER{
                clear(1),
                invalid(-1)
            }
            MAX-ACCESS   read-write
            STATUS      current
            DESCRIPTION
                "This object is used to clear the statistics.
                 Options:
                 1. clear(1)                    - Indicates that clear the statistics
                 2. invalid(-1)                 - Indicates that the query fails or no information is detected
                "
       ::= { hwGponOltEthernetStatisticEntry 50 }

-- Table: hwGponOltGemStatisticTable
        hwGponOltGemStatisticTable OBJECT-TYPE
            SYNTAX     SEQUENCE OF HwGponOltGemStatisticEntry
            MAX-ACCESS not-accessible
            STATUS     current
            DESCRIPTION
                "The GPON port GEM frame statistics table.
                 The index of this table is ifIndex.
                "
            ::= { hwXponDeviceStatisticObjects 22 }

        hwGponOltGemStatisticEntry OBJECT-TYPE
            SYNTAX     HwGponOltGemStatisticEntry
            MAX-ACCESS not-accessible
            STATUS     current
            DESCRIPTION
                "The GPON port GEM frame statistics table.
                 The index of this entry is ifIndex.
                "
            INDEX       { ifIndex }
            ::= { hwGponOltGemStatisticTable 1 }

        HwGponOltGemStatisticEntry ::=
            SEQUENCE {
                hwGponOltGemStatisticReceivedFrames       Counter64,
                hwGponOltGemStatisticReceivedOMCIPackts   Counter64,
                hwGponOltGemStatisticReceivedPLOAMPackts  Counter64,
                hwGponOltGemStatisticReceivedIdlePackts   Counter64,
                hwGponOltGemStatisticSendFrames           Counter64,
                hwGponOltGemStatisticSendOMCIPackts       Counter64,
                hwGponOltGemStatisticSendPLOAMPackts      Counter64,
                hwGponOltGemStatisticSendIdlePackts       Counter64,
                hwGponOltGemStatisticClear                INTEGER
            }

        hwGponOltGemStatisticReceivedFrames  OBJECT-TYPE
            SYNTAX     Counter64
            MAX-ACCESS   read-only
            STATUS      current
            DESCRIPTION
                "This object indicates the received GEM frames."
            ::= { hwGponOltGemStatisticEntry 1 }

        hwGponOltGemStatisticReceivedOMCIPackts  OBJECT-TYPE
            SYNTAX     Counter64
            MAX-ACCESS   read-only
            STATUS      current
            DESCRIPTION
                "This object indicates the recived OMCI frames."
            ::= { hwGponOltGemStatisticEntry 2 }

        hwGponOltGemStatisticReceivedPLOAMPackts  OBJECT-TYPE
            SYNTAX     Counter64
            MAX-ACCESS   read-only
            STATUS      current
            DESCRIPTION
                "This object indicates the recived PLOAM frames."
            ::= { hwGponOltGemStatisticEntry 3 }

        hwGponOltGemStatisticReceivedIdlePackts  OBJECT-TYPE
            SYNTAX     Counter64
            MAX-ACCESS   read-only
            STATUS      current
            DESCRIPTION
                "This object indicates the recived IDLE frames."
            ::= { hwGponOltGemStatisticEntry 4 }

        hwGponOltGemStatisticSendFrames  OBJECT-TYPE
            SYNTAX     Counter64
            MAX-ACCESS   read-only
            STATUS      current
            DESCRIPTION
                "This object indicates the sent GEM frames."
            ::= { hwGponOltGemStatisticEntry 5 }

        hwGponOltGemStatisticSendOMCIPackts  OBJECT-TYPE
            SYNTAX     Counter64
            MAX-ACCESS   read-only
            STATUS      current
            DESCRIPTION
                "This object indicates the sent OMCI frames."
            ::= { hwGponOltGemStatisticEntry 6 }

        hwGponOltGemStatisticSendPLOAMPackts  OBJECT-TYPE
            SYNTAX     Counter64
            MAX-ACCESS   read-only
            STATUS      current
            DESCRIPTION
                "This object indicates the sent PLOAM frames."
            ::= { hwGponOltGemStatisticEntry 7 }

        hwGponOltGemStatisticSendIdlePackts    OBJECT-TYPE
            SYNTAX     Counter64
            MAX-ACCESS   read-only
            STATUS      current
            DESCRIPTION
                "This object indicates the sent IDLE frames."
            ::= { hwGponOltGemStatisticEntry 8 }

        hwGponOltGemStatisticClear    OBJECT-TYPE
            SYNTAX     INTEGER{
                clear(1),
                invalid(-1)
            }
            MAX-ACCESS   read-write
            STATUS      current
            DESCRIPTION
                "This object is used to clear the statistics.
                 Options:
                 1. clear(1)                    - Indicates that clear the statistics
                 2. invalid(-1)                 - Indicates that the query fails or no information is detected
                "
            ::= { hwGponOltGemStatisticEntry 30 }

-- Table: hwGponOntStatisticTable
        hwGponOntStatisticTable OBJECT-TYPE
            SYNTAX     SEQUENCE OF HwGponOntStatisticEntry
            MAX-ACCESS not-accessible
            STATUS     current
            DESCRIPTION
                "The ONT statistics table. This table is used in xpon profile mode.
                 The index of this table is a combination of ifIndex and hwGponDeviceOntIndex.
                "
            ::= { hwXponDeviceStatisticObjects 23 }

        hwGponOntStatisticEntry OBJECT-TYPE
            SYNTAX     HwGponOntStatisticEntry
            MAX-ACCESS not-accessible
            STATUS     current
            DESCRIPTION
                "The ONT statistics table. This table is used in xpon profile mode.
                 The index of this entry is a combination of ifIndex and hwGponDeviceOntIndex.
                "
            INDEX       { ifIndex, hwGponDeviceOntIndex }
            ::= { hwGponOntStatisticTable 1 }

        HwGponOntStatisticEntry ::=
            SEQUENCE {
                hwGponOntStatisticUpPackts             Counter64,
                hwGponOntStatisticDownPackts           Counter64,
                hwGponOntStatisticUpBytes              Counter64,
                hwGponOntStatisticDownBytes            Counter64,
                hwGponOntStatisticUpDropPackts         Counter64,
                hwGponOntStatisticDownDropPackts       Counter64,
                hwGponOntStatisticClear                INTEGER
            }

        hwGponOntStatisticUpPackts  OBJECT-TYPE
            SYNTAX     Counter64
            MAX-ACCESS   read-only
            STATUS      current
            DESCRIPTION
                "This object indicates the upstream frames."
            ::= { hwGponOntStatisticEntry 1 }

        hwGponOntStatisticDownPackts  OBJECT-TYPE
            SYNTAX     Counter64
            MAX-ACCESS   read-only
            STATUS      current
            DESCRIPTION
                "This object indicates the downstream frames."
            ::= { hwGponOntStatisticEntry 2 }

        hwGponOntStatisticUpBytes  OBJECT-TYPE
            SYNTAX     Counter64
            MAX-ACCESS   read-only
            STATUS      current
            DESCRIPTION
                "This object indicates the upstream bytes."
            ::= { hwGponOntStatisticEntry 3 }

        hwGponOntStatisticDownBytes  OBJECT-TYPE
            SYNTAX     Counter64
            MAX-ACCESS   read-only
            STATUS      current
            DESCRIPTION
                "This object indicates the downstream bytes."
            ::= { hwGponOntStatisticEntry 4 }

        hwGponOntStatisticUpDropPackts   OBJECT-TYPE
            SYNTAX     Counter64
            MAX-ACCESS   read-only
            STATUS      current
            DESCRIPTION
                "This object indicates the number of upstream discarded frames."
            ::= { hwGponOntStatisticEntry 5 }

        hwGponOntStatisticDownDropPackts  OBJECT-TYPE
            SYNTAX     Counter64
            MAX-ACCESS   read-only
            STATUS      current
            DESCRIPTION
                "This object indicates the number of downstream discarded frames."
            ::= { hwGponOntStatisticEntry 6 }

        hwGponOntStatisticClear  OBJECT-TYPE
            SYNTAX     INTEGER{
                clear(1),
                invalid(-1)
            }
            MAX-ACCESS   read-write
            STATUS      current
            DESCRIPTION
                "This object is used to clear the statistics.
                 Options:
                 1. clear(1)                    - Indicates that clear the statistics
                 2. invalid(-1)                 - Indicates that the query fails or no information is detected
                "
            ::= { hwGponOntStatisticEntry 20 }

    -- Table: hwGponOltGemIndexStatisticTable
        hwGponOltGemIndexStatisticTable OBJECT-TYPE
            SYNTAX     SEQUENCE OF HwGponOltGemIndexStatisticEntry
            MAX-ACCESS not-accessible
            STATUS     current
            DESCRIPTION
                "The GEM Port statistics table.
                 The index of this table is a combination of ifIndex,
                 hwGponDeviceOntIndex and hwGponDeviceGemIndexObjectIndex.
                "
            ::= { hwXponDeviceStatisticObjects 24 }

        hwGponOltGemIndexStatisticEntry OBJECT-TYPE
            SYNTAX     HwGponOltGemIndexStatisticEntry
            MAX-ACCESS not-accessible
            STATUS     current
            DESCRIPTION
                "The GEM Port statistics table.
                 The index of this entry is a combination of ifIndex,
                 hwGponDeviceOntIndex and hwGponDeviceGemIndexObjectIndex.
                "
            INDEX       { ifIndex, hwGponDeviceOntIndex, hwGponDeviceGemIndexObjectIndex }
            ::= { hwGponOltGemIndexStatisticTable 1 }

        HwGponOltGemIndexStatisticEntry ::=
            SEQUENCE {
                hwGponDeviceGemIndexObjectIndex                Integer32,
                hwGponOltGemIndexStatisticUpFrames             Counter64,
                hwGponOltGemIndexStatisticDownFrames           Counter64,
                hwGponOltGemIndexStatisticUpBytes              Counter64,
                hwGponOltGemIndexStatisticDownBytes            Counter64,
                hwGponOltGemIndexStatisticUpDropFrames         Counter64,
                hwGponOltGemIndexStatisticDownDropFrames       Counter64,
                hwGponOltGemIndexStatisticClear                INTEGER
            }

        hwGponDeviceGemIndexObjectIndex OBJECT-TYPE
            SYNTAX Integer32
            MAX-ACCESS not-accessible
            STATUS current
            DESCRIPTION
                "This object indicates the GEM Index."
            ::= { hwGponOltGemIndexStatisticEntry 1 }

        hwGponOltGemIndexStatisticUpFrames  OBJECT-TYPE
            SYNTAX     Counter64
            MAX-ACCESS   read-only
            STATUS      current
            DESCRIPTION
                "This object indicates the upstream frames."
            ::= { hwGponOltGemIndexStatisticEntry 2 }

        hwGponOltGemIndexStatisticDownFrames  OBJECT-TYPE
            SYNTAX     Counter64
            MAX-ACCESS   read-only
            STATUS      current
            DESCRIPTION
                "This object indicates the downstream frames."
            ::= { hwGponOltGemIndexStatisticEntry 3 }

        hwGponOltGemIndexStatisticUpBytes  OBJECT-TYPE
            SYNTAX     Counter64
            MAX-ACCESS   read-only
            STATUS      current
            DESCRIPTION
                "This object indicates the upstream bytes."
            ::= { hwGponOltGemIndexStatisticEntry 4 }

        hwGponOltGemIndexStatisticDownBytes  OBJECT-TYPE
            SYNTAX     Counter64
            MAX-ACCESS   read-only
            STATUS      current
            DESCRIPTION
                "This object indicates the downstream bytes."
            ::= { hwGponOltGemIndexStatisticEntry 5 }

        hwGponOltGemIndexStatisticUpDropFrames   OBJECT-TYPE
            SYNTAX     Counter64
            MAX-ACCESS   read-only
            STATUS      current
            DESCRIPTION
                "This object indicates the number of upstream discarded frames."
            ::= { hwGponOltGemIndexStatisticEntry 6 }

        hwGponOltGemIndexStatisticDownDropFrames  OBJECT-TYPE
            SYNTAX     Counter64
            MAX-ACCESS   read-only
            STATUS      current
            DESCRIPTION
                "This object indicates the number of downstream discarded frames."
            ::= { hwGponOltGemIndexStatisticEntry 7 }

        hwGponOltGemIndexStatisticClear  OBJECT-TYPE
            SYNTAX     INTEGER{
                clear(1),
                invalid(-1)
            }
            MAX-ACCESS   read-write
            STATUS      current
            DESCRIPTION
                "This object is used to clear the statistics.
                 Options:
                 1. clear(1)                    - Indicates that clear the statistics
                 2. invalid(-1)                 - Indicates that the query fails or no information is detected
                "
            ::= { hwGponOltGemIndexStatisticEntry 20 }

-- Table: HwGponOntEthernetStatisticTable
        hwGponOntEthernetStatisticTable OBJECT-TYPE
            SYNTAX  SEQUENCE OF HwGponOntEthernetStatisticEntry
            MAX-ACCESS not-accessible
            STATUS current
            DESCRIPTION
                "The ONT ETH port statistics table.
                 The index of this table is a combination of ifIndex,
                 hwGponDeviceOntIndex and hwGponDeviceOntEthernetPortId.
                "
            ::= { hwXponDeviceStatisticObjects 25 }

        hwGponOntEthernetStatisticEntry OBJECT-TYPE
            SYNTAX HwGponOntEthernetStatisticEntry
            MAX-ACCESS not-accessible
            STATUS current
            DESCRIPTION
                "The ONT ETH port statistics table.
                 The index of this entry is a combination of ifIndex,
                 hwGponDeviceOntIndex and hwGponDeviceOntEthernetPortId.
                "
            INDEX { ifIndex, hwGponDeviceOntIndex, hwGponDeviceOntEthernetPortId }
            ::= { hwGponOntEthernetStatisticTable 1 }

        HwGponOntEthernetStatisticEntry ::=
            SEQUENCE {
                hwGponOntEthernetStatisticDataSource                    OBJECT IDENTIFIER,
                hwGponOntEthernetStatisticRecvDropEvents                Counter64,
                hwGponOntEthernetStatisticRecvOctets                    Counter64,
                hwGponOntEthernetStatisticRecvPkts                      Counter64,
                hwGponOntEthernetStatisticRecvBroadcastPkts             Counter64,
                hwGponOntEthernetStatisticRecvMulticastPkts             Counter64,
                hwGponOntEthernetStatisticRecvCRCAlignErrors            Counter64,
                hwGponOntEthernetStatisticRecvUndersizePkts             Counter64,
                hwGponOntEthernetStatisticMTUExceededDiscardFrames      Counter64,
                hwGponOntEthernetStatisticRecvFragments                 Counter64,
                hwGponOntEthernetStatisticRecvJabbers                   Counter64,
                hwGponOntEthernetStatisticCollisions                    Counter64,
                hwGponOntEthernetStatisticRecvPkts64Octets              Counter64,
                hwGponOntEthernetStatisticRecvPkts65to127Octets         Counter64,
                hwGponOntEthernetStatisticRecvPkts128to255Octets        Counter64,
                hwGponOntEthernetStatisticRecvPkts256to511Octets        Counter64,
                hwGponOntEthernetStatisticRecvPkts512to1023Octets       Counter64,
                hwGponOntEthernetStatisticRecvPkts1024to1518Octets      Counter64,
                hwGponOntEthernetStatisticRecvFCSErrors                 Counter64,
                hwGponOntEthernetStatisticSendExcessiveCollision        Counter64,
                hwGponOntEthernetStatisticSendLateCollision             Counter64,
                hwGponOntEthernetStatisticRecvFrameTooLongs             Counter64,
                hwGponOntEthernetStatisticRecvBufferOverflowson         Counter64,
                hwGponOntEthernetStatisticSendBufferOverflowson         Counter64,
                hwGponOntEthernetStatisticSendSingleCollisionFrame      Counter64,
                hwGponOntEthernetStatisticSendMultipleCollisionsFrame   Counter64,
                hwGponOntEthernetStatisticSendSQETestError              Counter64,
                hwGponOntEthernetStatisticDeferredTransmission          Counter64,
                hwGponOntEthernetStatisticInternalmacTransmitError      Counter64,
                hwGponOntEthernetStatisticSendCarrierSenseError         Counter64,
                hwGponOntEthernetStatisticRecvAlignmentError            Counter64,
                hwGponOntEthernetStatisticInternalMACReceiveError       Counter64,
                hwGponOntEthernetStatisticRecvPPPoEFilteredFrame        Counter64,
                hwGponOntEthernetStatisticSendForwardedFrame            Counter64,
                hwGponOntEthernetStatisticDelayExceededDiscard          Counter64,
                hwGponOntEthernetStatisticRecvUnicastPkts               Counter64,
                hwGponOntEthernetStatisticSendUnicastPkts               Counter64,
                hwGponOntEthernetStatisticSendBroadcastPkts             Counter64,
                hwGponOntEthernetStatisticSendMulticastPkts             Counter64,
                hwGponOntEthernetStatisticRecvPauseFlowCtrlFrame        Counter64,
                hwGponOntEthernetStatisticSendPauseFlowCtrlFrame        Counter64,
                hwGponOntEthernetStatisticRecvGoodPktsOctets            Counter64,
                hwGponOntEthernetStatisticSendGoodPktsOctets            Counter64,
                hwGponOntEthernetStatisticRecvBadPktsOctets             Counter64,
                hwGponOntEthernetStatisticSendBadPktsOctets             Counter64,
                hwGponOntEthernetStatisticSendOctets                    Counter64,
                hwGponOntEthernetStatisticForwardDropEvents             Counter64,
                hwGponOntEthernetStatisticSendPkts64Octets              Counter64,
                hwGponOntEthernetStatisticSendPkts65to127Octets         Counter64,
                hwGponOntEthernetStatisticSendPkts128to255Octets        Counter64,
                hwGponOntEthernetStatisticSendPkts256to511Octets        Counter64,
                hwGponOntEthernetStatisticSendPkts512to1023Octets       Counter64,
                hwGponOntEthernetStatisticSendPkts1024to1518Octets      Counter64,
                hwGponOntEthernetStatisticSendPktsOversize              Counter64,
                hwGponOntEthernetStatisticRecvPkts1519toOversizeOctets  Counter64,
                hwGponOntEthernetStatisticClear                         INTEGER,
                hwGponOntEthernetStatisticStateChangeTimes              Integer32,
                hwGponOntEthernetStatisticDuration                      Gauge32
            }

        hwGponOntEthernetStatisticDataSource OBJECT-TYPE
            SYNTAX OBJECT IDENTIFIER
            MAX-ACCESS read-only
            STATUS current
            DESCRIPTION
                "This object indicates the ONT ETH statistics data source."
            ::= { hwGponOntEthernetStatisticEntry 1 }

        hwGponOntEthernetStatisticRecvDropEvents OBJECT-TYPE
            SYNTAX Counter64
            MAX-ACCESS read-only
            STATUS current
            DESCRIPTION
                "This object indicates the number of received and discarded frames."
            ::= { hwGponOntEthernetStatisticEntry 2 }

        hwGponOntEthernetStatisticRecvOctets OBJECT-TYPE
            SYNTAX Counter64
            MAX-ACCESS read-only
            STATUS current
            DESCRIPTION
                "This object indicates the received bytes."
            ::= { hwGponOntEthernetStatisticEntry 3 }

        hwGponOntEthernetStatisticRecvPkts OBJECT-TYPE
            SYNTAX Counter64
            MAX-ACCESS read-only
            STATUS current
            DESCRIPTION
                "This object indicates the received frames."
            ::= { hwGponOntEthernetStatisticEntry 4 }

        hwGponOntEthernetStatisticRecvBroadcastPkts OBJECT-TYPE
            SYNTAX Counter64
            MAX-ACCESS read-only
            STATUS current
            DESCRIPTION
                "This object indicates the received broadcast frames."
            ::= { hwGponOntEthernetStatisticEntry 5 }

        hwGponOntEthernetStatisticRecvMulticastPkts OBJECT-TYPE
            SYNTAX Counter64
            MAX-ACCESS read-only
            STATUS current
            DESCRIPTION
                "This object indicates the received multicast frames."
            ::= { hwGponOntEthernetStatisticEntry 6 }

        hwGponOntEthernetStatisticRecvCRCAlignErrors OBJECT-TYPE
            SYNTAX Counter64
            MAX-ACCESS read-only
            STATUS current
            DESCRIPTION
                "This object indicates the received CRC error frames."
            ::= { hwGponOntEthernetStatisticEntry 7 }

        hwGponOntEthernetStatisticRecvUndersizePkts OBJECT-TYPE
            SYNTAX Counter64
            MAX-ACCESS read-only
            STATUS current
            DESCRIPTION
                "This object indicates the received undersize frames."
            ::= { hwGponOntEthernetStatisticEntry 8 }

        hwGponOntEthernetStatisticMTUExceededDiscardFrames OBJECT-TYPE
            SYNTAX Counter64
            MAX-ACCESS read-only
            STATUS current
            DESCRIPTION
                "This object indicates the send MTU exceeded discard frames."
            ::= { hwGponOntEthernetStatisticEntry 9 }

        hwGponOntEthernetStatisticRecvFragments OBJECT-TYPE
            SYNTAX Counter64
            MAX-ACCESS read-only
            STATUS current
            DESCRIPTION
                "This object indicates the number of received fragments."
            ::= { hwGponOntEthernetStatisticEntry 10 }

        hwGponOntEthernetStatisticRecvJabbers OBJECT-TYPE
            SYNTAX Counter64
            MAX-ACCESS read-only
            STATUS current
            DESCRIPTION
                "This object indicates the received Jabber error frames."
            ::= { hwGponOntEthernetStatisticEntry 11 }

        hwGponOntEthernetStatisticCollisions OBJECT-TYPE
            SYNTAX Counter64
            MAX-ACCESS read-only
            STATUS current
            DESCRIPTION
                "This object indicates the count of collisions."
            ::= { hwGponOntEthernetStatisticEntry 12 }

        hwGponOntEthernetStatisticRecvPkts64Octets OBJECT-TYPE
            SYNTAX Counter64
            MAX-ACCESS read-only
            STATUS current
            DESCRIPTION
                "This object indicates the received 64-octet frames"
            ::= { hwGponOntEthernetStatisticEntry 13 }

        hwGponOntEthernetStatisticRecvPkts65to127Octets OBJECT-TYPE
            SYNTAX Counter64
            MAX-ACCESS read-only
            STATUS current
            DESCRIPTION
                "This object indicates the received 65~127-octet frames"
            ::= { hwGponOntEthernetStatisticEntry 14 }

        hwGponOntEthernetStatisticRecvPkts128to255Octets OBJECT-TYPE
            SYNTAX Counter64
            MAX-ACCESS read-only
            STATUS current
            DESCRIPTION
                "This object indicates the received 128~255-octet frames"
            ::= { hwGponOntEthernetStatisticEntry 15 }

        hwGponOntEthernetStatisticRecvPkts256to511Octets OBJECT-TYPE
            SYNTAX Counter64
            MAX-ACCESS read-only
            STATUS current
            DESCRIPTION
                "This object indicates the received 256~511-octet frames."
            ::= { hwGponOntEthernetStatisticEntry 16 }

        hwGponOntEthernetStatisticRecvPkts512to1023Octets OBJECT-TYPE
            SYNTAX Counter64
            MAX-ACCESS read-only
            STATUS current
            DESCRIPTION
                "This object indicates the received 512~1023-octet frames."
            ::= { hwGponOntEthernetStatisticEntry 17 }

        hwGponOntEthernetStatisticRecvPkts1024to1518Octets OBJECT-TYPE
            SYNTAX Counter64
            MAX-ACCESS read-only
            STATUS current
            DESCRIPTION
                "This object indicates the received 1024~1518-octet frames."
            ::= { hwGponOntEthernetStatisticEntry 18 }

        hwGponOntEthernetStatisticRecvFCSErrors  OBJECT-TYPE
            SYNTAX Counter64
            MAX-ACCESS read-only
            STATUS current
            DESCRIPTION
                "This object indicates the received FCS error frames."
            ::= { hwGponOntEthernetStatisticEntry 19 }

        hwGponOntEthernetStatisticSendExcessiveCollision  OBJECT-TYPE
            SYNTAX Counter64
            MAX-ACCESS read-only
            STATUS current
            DESCRIPTION
                "This object indicates the sent excessive collision frames."
            ::= { hwGponOntEthernetStatisticEntry 20 }

        hwGponOntEthernetStatisticSendLateCollision  OBJECT-TYPE
            SYNTAX Counter64
            MAX-ACCESS read-only
            STATUS current
            DESCRIPTION
                "This object indicates the sent late collision frames."
            ::= { hwGponOntEthernetStatisticEntry 21 }

        hwGponOntEthernetStatisticRecvFrameTooLongs  OBJECT-TYPE
            SYNTAX Counter64
            MAX-ACCESS read-only
            STATUS current
            DESCRIPTION
                "This object indicates the received oversize frames."
            ::= { hwGponOntEthernetStatisticEntry 22 }

        hwGponOntEthernetStatisticRecvBufferOverflowson  OBJECT-TYPE
            SYNTAX Counter64
            MAX-ACCESS read-only
            STATUS current
            DESCRIPTION
                "This object indicates the number of received buffer overflows."
            ::= { hwGponOntEthernetStatisticEntry 23 }

        hwGponOntEthernetStatisticSendBufferOverflowson  OBJECT-TYPE
            SYNTAX Counter64
            MAX-ACCESS read-only
            STATUS current
            DESCRIPTION
                "This object indicates the number of sent buffer overflows."
            ::= { hwGponOntEthernetStatisticEntry 24 }

        hwGponOntEthernetStatisticSendSingleCollisionFrame  OBJECT-TYPE
            SYNTAX Counter64
            MAX-ACCESS read-only
            STATUS current
            DESCRIPTION
                "This object indicates the number of deferred sent frames due to single collision."
            ::= { hwGponOntEthernetStatisticEntry 25 }

        hwGponOntEthernetStatisticSendMultipleCollisionsFrame  OBJECT-TYPE
            SYNTAX Counter64
            MAX-ACCESS read-only
            STATUS current
            DESCRIPTION
                "This object indicates the number of deferred sent frames due to multiple collisions."
            ::= { hwGponOntEthernetStatisticEntry 26 }

        hwGponOntEthernetStatisticSendSQETestError  OBJECT-TYPE
            SYNTAX Counter64
            MAX-ACCESS read-only
            STATUS current
            DESCRIPTION
                "This object indicates the number of SQE test error messages."
            ::= { hwGponOntEthernetStatisticEntry 27 }

        hwGponOntEthernetStatisticDeferredTransmission  OBJECT-TYPE
            SYNTAX Counter64
            MAX-ACCESS read-only
            STATUS current
            DESCRIPTION
                "This object indicates the sent deferred frames."
            ::= { hwGponOntEthernetStatisticEntry 28 }

        hwGponOntEthernetStatisticInternalmacTransmitError  OBJECT-TYPE
            SYNTAX Counter64
            MAX-ACCESS read-only
            STATUS current
            DESCRIPTION
                "This object indicates the sent error frames at the MAC sub-layer."
            ::= { hwGponOntEthernetStatisticEntry 29 }

        hwGponOntEthernetStatisticSendCarrierSenseError  OBJECT-TYPE
            SYNTAX Counter64
            MAX-ACCESS read-only
            STATUS current
            DESCRIPTION
                "This object indicates the sent carrier sense errors."
            ::= { hwGponOntEthernetStatisticEntry 30 }

        hwGponOntEthernetStatisticRecvAlignmentError  OBJECT-TYPE
            SYNTAX Counter64
            MAX-ACCESS read-only
            STATUS current
            DESCRIPTION
                "This object indicates the received alignment error frames."
            ::= { hwGponOntEthernetStatisticEntry 31 }

        hwGponOntEthernetStatisticInternalMACReceiveError  OBJECT-TYPE
            SYNTAX Counter64
            MAX-ACCESS read-only
            STATUS current
            DESCRIPTION
                "This object indicates the received error frames at the MAC sub-layer."
            ::= { hwGponOntEthernetStatisticEntry 32 }

        hwGponOntEthernetStatisticRecvPPPoEFilteredFrame  OBJECT-TYPE
            SYNTAX Counter64
            MAX-ACCESS read-only
            STATUS current
            DESCRIPTION
                "This object indicates the received PPPoE filtered frames."
            ::= { hwGponOntEthernetStatisticEntry 33 }

        hwGponOntEthernetStatisticSendForwardedFrame  OBJECT-TYPE
            SYNTAX Counter64
            MAX-ACCESS read-only
            STATUS current
            DESCRIPTION
                "This object indicates the send frames."
            ::= { hwGponOntEthernetStatisticEntry 34 }

        hwGponOntEthernetStatisticDelayExceededDiscard  OBJECT-TYPE
            SYNTAX Counter64
            MAX-ACCESS read-only
            STATUS current
            DESCRIPTION
                "This object indicates the discarded frames due to delay."
            ::= { hwGponOntEthernetStatisticEntry 35 }

        hwGponOntEthernetStatisticRecvUnicastPkts  OBJECT-TYPE
            SYNTAX Counter64
            MAX-ACCESS read-only
            STATUS current
            DESCRIPTION
                "This object indicates the received unicast frames."
            ::= { hwGponOntEthernetStatisticEntry 36 }

        hwGponOntEthernetStatisticSendUnicastPkts  OBJECT-TYPE
            SYNTAX Counter64
            MAX-ACCESS read-only
            STATUS current
            DESCRIPTION
                "This object indicates the sent unicast frames."
            ::= { hwGponOntEthernetStatisticEntry 37 }

        hwGponOntEthernetStatisticSendBroadcastPkts  OBJECT-TYPE
            SYNTAX Counter64
            MAX-ACCESS read-only
            STATUS current
            DESCRIPTION
                "This object indicates the sent broadcast frames."
            ::= { hwGponOntEthernetStatisticEntry 38 }

        hwGponOntEthernetStatisticSendMulticastPkts  OBJECT-TYPE
            SYNTAX Counter64
            MAX-ACCESS read-only
            STATUS current
            DESCRIPTION
                "This object indicates the sent multicast frames."
            ::= { hwGponOntEthernetStatisticEntry 39 }

        hwGponOntEthernetStatisticRecvPauseFlowCtrlFrame  OBJECT-TYPE
            SYNTAX Counter64
            MAX-ACCESS read-only
            STATUS current
            DESCRIPTION
                "This object indicates the received pause flow control frames."
            ::= { hwGponOntEthernetStatisticEntry 40 }

        hwGponOntEthernetStatisticSendPauseFlowCtrlFrame  OBJECT-TYPE
            SYNTAX Counter64
            MAX-ACCESS read-only
            STATUS current
            DESCRIPTION
                "This object indicates the sent pause flow control frames."
            ::= { hwGponOntEthernetStatisticEntry 41 }

        hwGponOntEthernetStatisticRecvGoodPktsOctets  OBJECT-TYPE
            SYNTAX Counter64
            MAX-ACCESS read-only
            STATUS current
            DESCRIPTION
                "This object indicates the received right octets."
            ::= { hwGponOntEthernetStatisticEntry 42 }

        hwGponOntEthernetStatisticSendGoodPktsOctets  OBJECT-TYPE
            SYNTAX Counter64
            MAX-ACCESS read-only
            STATUS current
            DESCRIPTION
                "This object indicates the sent good frames octets."
            ::= { hwGponOntEthernetStatisticEntry 43 }

        hwGponOntEthernetStatisticRecvBadPktsOctets  OBJECT-TYPE
            SYNTAX Counter64
            MAX-ACCESS read-only
            STATUS current
            DESCRIPTION
                "This object indicates the received error octets."
            ::= { hwGponOntEthernetStatisticEntry 44 }

        hwGponOntEthernetStatisticSendBadPktsOctets  OBJECT-TYPE
            SYNTAX Counter64
            MAX-ACCESS read-only
            STATUS current
            DESCRIPTION
                "This object indicates the sent error octets."
            ::= { hwGponOntEthernetStatisticEntry 45 }


        hwGponOntEthernetStatisticSendOctets  OBJECT-TYPE
            SYNTAX Counter64
            MAX-ACCESS read-only
            STATUS current
            DESCRIPTION
                "This object indicates the sent error octets."
            ::= { hwGponOntEthernetStatisticEntry 46 }

         hwGponOntEthernetStatisticForwardDropEvents  OBJECT-TYPE
            SYNTAX Counter64
            MAX-ACCESS read-only
            STATUS current
            DESCRIPTION
                "This object indicates the sent drop events."
            ::= { hwGponOntEthernetStatisticEntry 47 }

         hwGponOntEthernetStatisticSendPkts64Octets  OBJECT-TYPE
            SYNTAX Counter64
            MAX-ACCESS read-only
            STATUS current
            DESCRIPTION
                "This object indicates the sent 64-octet frames."
            ::= { hwGponOntEthernetStatisticEntry 48 }

         hwGponOntEthernetStatisticSendPkts65to127Octets  OBJECT-TYPE
            SYNTAX Counter64
            MAX-ACCESS read-only
            STATUS current
            DESCRIPTION
                "This object indicates the sent 65~127-octet frames."
            ::= { hwGponOntEthernetStatisticEntry 49 }

        hwGponOntEthernetStatisticSendPkts128to255Octets  OBJECT-TYPE
            SYNTAX Counter64
            MAX-ACCESS read-only
            STATUS current
            DESCRIPTION
                "This object indicates the sent 128~255-octet frames."
            ::= { hwGponOntEthernetStatisticEntry 50}

         hwGponOntEthernetStatisticSendPkts256to511Octets   OBJECT-TYPE
            SYNTAX Counter64
            MAX-ACCESS read-only
            STATUS current
            DESCRIPTION
                "This object indicates the sent 256~511-octet frames."
            ::= { hwGponOntEthernetStatisticEntry 51 }

      hwGponOntEthernetStatisticSendPkts512to1023Octets   OBJECT-TYPE
            SYNTAX Counter64
            MAX-ACCESS read-only
            STATUS current
            DESCRIPTION
                "This object indicates the sent 512~1023-octet frames."
            ::= { hwGponOntEthernetStatisticEntry 52 }

      hwGponOntEthernetStatisticSendPkts1024to1518Octets   OBJECT-TYPE
            SYNTAX Counter64
            MAX-ACCESS read-only
            STATUS current
            DESCRIPTION
                "This object indicates the sent 1024~1518-octet frames."
            ::= { hwGponOntEthernetStatisticEntry 53 }

       hwGponOntEthernetStatisticSendPktsOversize    OBJECT-TYPE
            SYNTAX Counter64
            MAX-ACCESS read-only
            STATUS current
            DESCRIPTION
                "This object indicates the sent oversize frames."
            ::= { hwGponOntEthernetStatisticEntry 54 }

       hwGponOntEthernetStatisticRecvPkts1519toOversizeOctets    OBJECT-TYPE
            SYNTAX Counter64
            MAX-ACCESS read-only
            STATUS current
            DESCRIPTION
                "This object indicates the received 1519~oversize-octet frames."
            ::= { hwGponOntEthernetStatisticEntry 55 }

       hwGponOntEthernetStatisticClear  OBJECT-TYPE
            SYNTAX INTEGER{
                clear(1),
                invalid(-1)
            }
            MAX-ACCESS read-write
            STATUS current
            DESCRIPTION
                "This object is used to clear the statistics.
                 Options:
                 1. clear(1)                    - Indicates that clear the statistics
                 2. invalid(-1)                 - Indicates that the query fails or no information is detected
                "
            ::= { hwGponOntEthernetStatisticEntry 60 }

        hwGponOntEthernetStatisticStateChangeTimes  OBJECT-TYPE
            SYNTAX Integer32
            MAX-ACCESS read-only
            STATUS current
            DESCRIPTION
                "This object indicates the ONT ethernet port state changed times."
            ::= { hwGponOntEthernetStatisticEntry 61 }

       hwGponOntEthernetStatisticDuration  OBJECT-TYPE
            SYNTAX      Gauge32
            UNITS       "second"
            MAX-ACCESS  read-only
            STATUS      current
            DESCRIPTION
                "Indicates the statistic duration of the GPON ONT ethernet port.
                 Unit: second
                "
            ::= { hwGponOntEthernetStatisticEntry 62 }

-- Table: hwGponOntGemIndexStatisticTable
        hwGponOntGemIndexStatisticTable OBJECT-TYPE
            SYNTAX  SEQUENCE OF HwGponOntGemIndexStatisticEntry
            MAX-ACCESS not-accessible
            STATUS current
            DESCRIPTION
                "The ONT GEM Port statistics table.
                 The index of this table is a combination of ifIndex,
                 hwGponDeviceOntIndex and hwGponDeviceGemIndexObjectIndex.
                "
            ::= { hwXponDeviceStatisticObjects 26 }

        hwGponOntGemIndexStatisticEntry OBJECT-TYPE
            SYNTAX HwGponOntGemIndexStatisticEntry
            MAX-ACCESS not-accessible
            STATUS current
            DESCRIPTION
                "The ONT GEM Port statistics table.
                 The index of this entry is a combination of ifIndex,
                 hwGponDeviceOntIndex and hwGponDeviceGemIndexObjectIndex.
                "
            INDEX { ifIndex, hwGponDeviceOntIndex, hwGponDeviceGemIndexObjectIndex }
            ::= { hwGponOntGemIndexStatisticTable 1 }

        HwGponOntGemIndexStatisticEntry ::=
            SEQUENCE {
                hwGponOntGemIndexStatisticRecvLostFrames         Counter64,
                hwGponOntGemIndexStatisticMisinsertedFrames      Counter64,
                hwGponOntGemIndexStatisticRecvFrames             Counter64,
                hwGponOntGemIndexStatisticRecvBlocks             Counter64,
                hwGponOntGemIndexStatisticSendBlocks             Counter64,
                hwGponOntGemIndexStatisticImpairedBlocks         Counter64,
                hwGponOntGemIndexStatisticTransmittedGemFrames   Counter64,
                hwGponOntGemIndexStatisticClear                  INTEGER
            }

        hwGponOntGemIndexStatisticRecvLostFrames OBJECT-TYPE
            SYNTAX Counter64
            MAX-ACCESS read-only
            STATUS current
            DESCRIPTION
                "This object indicates the loss of frames."
            ::= { hwGponOntGemIndexStatisticEntry 1 }

        hwGponOntGemIndexStatisticMisinsertedFrames OBJECT-TYPE
            SYNTAX Counter64
            MAX-ACCESS read-only
            STATUS current
            DESCRIPTION
                "This object indicates the misinserted frames."
            ::= { hwGponOntGemIndexStatisticEntry 2 }

        hwGponOntGemIndexStatisticRecvFrames OBJECT-TYPE
            SYNTAX Counter64
            MAX-ACCESS read-only
            STATUS current
            DESCRIPTION
                "This object indicates the received frames."
            ::= { hwGponOntGemIndexStatisticEntry 3 }

        hwGponOntGemIndexStatisticRecvBlocks OBJECT-TYPE
            SYNTAX Counter64
            MAX-ACCESS read-only
            STATUS current
            DESCRIPTION
                "This object indicates the received blocks."
            ::= { hwGponOntGemIndexStatisticEntry 4 }

        hwGponOntGemIndexStatisticSendBlocks OBJECT-TYPE
            SYNTAX Counter64
            MAX-ACCESS read-only
            STATUS current
            DESCRIPTION
                "This object indicates the sent blocks."
            ::= { hwGponOntGemIndexStatisticEntry 5 }

        hwGponOntGemIndexStatisticImpairedBlocks OBJECT-TYPE
            SYNTAX Counter64
            MAX-ACCESS read-only
            STATUS current
            DESCRIPTION
                "This object indicates the number of received impaired data blocks."
            ::= { hwGponOntGemIndexStatisticEntry 6 }

        hwGponOntGemIndexStatisticTransmittedGemFrames OBJECT-TYPE
            SYNTAX Counter64
            MAX-ACCESS read-only
            STATUS current
            DESCRIPTION
               "This object indicates the number of transmitted GEM frames."
               ::= { hwGponOntGemIndexStatisticEntry 7 }

        hwGponOntGemIndexStatisticClear OBJECT-TYPE
            SYNTAX INTEGER{
                clear(1),
                invalid(-1)
            }
            MAX-ACCESS read-write
            STATUS current
            DESCRIPTION
                "This object is used to clear the statistics.
                 Options:
                 1. clear(1)                    - Indicates that clear the statistics
                 2. invalid(-1)                 - Indicates that the query fails or no information is detected
                "
            ::= { hwGponOntGemIndexStatisticEntry 20 }

-- Table: hwGponOntTrafficFlowStatisticTable
        hwGponOntTrafficFlowStatisticTable OBJECT-TYPE
            SYNTAX  SEQUENCE OF HwGponOntTrafficFlowStatisticEntry
            MAX-ACCESS not-accessible
            STATUS current
            DESCRIPTION
                "The ONT traffic stream statistics table.
                 The index of this table is a combination of ifIndex and hwGponDeviceOntIndex.
                "
            ::= { hwXponDeviceStatisticObjects 27 }

        hwGponOntTrafficFlowStatisticEntry OBJECT-TYPE
            SYNTAX HwGponOntTrafficFlowStatisticEntry
            MAX-ACCESS not-accessible
            STATUS current
            DESCRIPTION
                "The ONT traffic stream statistics table.
                 The index of this entry is a combination of ifIndex and hwGponDeviceOntIndex.
                "
            INDEX { ifIndex, hwGponDeviceOntIndex }
            ::= { hwGponOntTrafficFlowStatisticTable 1 }

        HwGponOntTrafficFlowStatisticEntry ::=
            SEQUENCE {
                hwGponOntTrafficFlowStatisticLofiAlarmStatsCnt              Counter64,
                hwGponOntTrafficFlowStatisticUpFramesScapeErrCnt            Counter64,
                hwGponOntTrafficFlowStatisticUpFrameBipErrCnt               Counter64,
                hwGponOntTrafficFlowStatisticDnFramesBipErrCnt              Counter64,
                hwGponOntTrafficFlowStatisticUpFecDecodCorrectCnt           Counter64,
                hwGponOntTrafficFlowStatisticUpFecDecodUnCorrectCnt         Counter64,
                hwGponOntTrafficFlowStatisticUpHecCheckErrCnt               Counter64,
                hwGponOntTrafficFlowStatisticDowiAlarmCnt                   Counter64,
                hwGponOntTrafficFlowStatisticUpFecCodeDecodCorrectCnt       Counter64,
                hwGponOntTrafficFlowStatisticUpFecCodeCnt                   Counter64,
                hwGponOntTrafficFlowStatisticUpFcsErrorCnt                  Counter64,
                hwGponOntTrafficFlowStatisticUpFrameBitErrorRatio           Counter64,
                hwGponOntTrafficFlowStatisticUpEthFrameErrorRatio           Counter64,
                hwGponOntTrafficFlowStatisticUpGemFrameErrorRatio           Counter64,
                hwGponOntTrafficFlowStatisticClear                          INTEGER
            }

        hwGponOntTrafficFlowStatisticLofiAlarmStatsCnt OBJECT-TYPE
            SYNTAX Counter64
            MAX-ACCESS read-only
            STATUS current
            DESCRIPTION
                "This object indicates the number of the ONT LOFI alarms."
            ::= { hwGponOntTrafficFlowStatisticEntry 1 }

        hwGponOntTrafficFlowStatisticUpFramesScapeErrCnt OBJECT-TYPE
            SYNTAX Counter64
            MAX-ACCESS read-only
            STATUS current
            DESCRIPTION
                "This object indicates the number of ONT upstream scape error frames."
            ::= { hwGponOntTrafficFlowStatisticEntry 2 }

        hwGponOntTrafficFlowStatisticUpFrameBipErrCnt OBJECT-TYPE
            SYNTAX Counter64
            MAX-ACCESS read-only
            STATUS current
            DESCRIPTION
                "This object indicates the number of ONT upstream frames with BIP errors."
            ::= { hwGponOntTrafficFlowStatisticEntry 3 }

        hwGponOntTrafficFlowStatisticDnFramesBipErrCnt OBJECT-TYPE
            SYNTAX Counter64
            MAX-ACCESS read-only
            STATUS current
            DESCRIPTION
                "This object indicates the number of ONT downstream frames with BIP errors."
            ::= { hwGponOntTrafficFlowStatisticEntry 4 }

        hwGponOntTrafficFlowStatisticUpFecDecodCorrectCnt OBJECT-TYPE
            SYNTAX Counter64
            MAX-ACCESS read-only
            STATUS current
            DESCRIPTION
                "This object indicates the number of upstream FEC decoding corrected blocks."
            ::= { hwGponOntTrafficFlowStatisticEntry 5 }

        hwGponOntTrafficFlowStatisticUpFecDecodUnCorrectCnt OBJECT-TYPE
            SYNTAX Counter64
            MAX-ACCESS read-only
            STATUS current
            DESCRIPTION
                "This object indicates the number of upstream FEC decoding uncorrected blocks."
            ::= { hwGponOntTrafficFlowStatisticEntry 6 }

        hwGponOntTrafficFlowStatisticUpHecCheckErrCnt OBJECT-TYPE
            SYNTAX Counter64
            MAX-ACCESS read-only
            STATUS current
            DESCRIPTION
                "This object indicates the number of upstream HEC errors."
            ::= { hwGponOntTrafficFlowStatisticEntry 7 }

        hwGponOntTrafficFlowStatisticDowiAlarmCnt OBJECT-TYPE
            SYNTAX Counter64
            MAX-ACCESS read-only
            STATUS current
            DESCRIPTION
                "The count of ONU DOWi(Drift of Window) Alarm."
            ::= { hwGponOntTrafficFlowStatisticEntry 8 }

        hwGponOntTrafficFlowStatisticUpFecCodeDecodCorrectCnt OBJECT-TYPE
               SYNTAX Counter64
               MAX-ACCESS read-only
               STATUS current
               DESCRIPTION
                   "This object indicates the number of upstream FEC code decoding corrected blocks."
               ::= { hwGponOntTrafficFlowStatisticEntry 9 }

        hwGponOntTrafficFlowStatisticUpFecCodeCnt OBJECT-TYPE
               SYNTAX Counter64
               MAX-ACCESS read-only
               STATUS current
               DESCRIPTION
                   "This object indicates the number of upstream FEC code blocks."
               ::= { hwGponOntTrafficFlowStatisticEntry 10 }

        hwGponOntTrafficFlowStatisticUpFcsErrorCnt OBJECT-TYPE
               SYNTAX Counter64
               MAX-ACCESS read-only
               STATUS current
               DESCRIPTION
                   "This object indicates the number of upstream FCS code errors in current 15 minutes.
                    The value (-1) indicates that the query fails or no information is detected."
               ::= { hwGponOntTrafficFlowStatisticEntry 11 }

        hwGponOntTrafficFlowStatisticUpFrameBitErrorRatio OBJECT-TYPE
               SYNTAX Counter64
               MAX-ACCESS read-only
               STATUS current
               DESCRIPTION
                   "This object indicates upstream frame bit error ratio in current 15 minutes.
                    The value of this object indicates the exponente of the exponential expression of the upstream frame bit error ratio.
                    For example, if the upstream frame bit error ratio is calculated to be (0.0012), the exponential expression is 1.2E-3.
                    The multiplicando (1.2) is ignored, and the value of this object is (3).
                    The value (-1) indicates that the query fails or no information is detected.
                    The value (0xFFFFFFE) indicates that the bit error ratio is (0).
                    The value (0) indicates that the bit error ratio is (1)."
               ::= { hwGponOntTrafficFlowStatisticEntry 12 }

        hwGponOntTrafficFlowStatisticUpEthFrameErrorRatio OBJECT-TYPE
               SYNTAX Counter64
               MAX-ACCESS read-only
               STATUS current
               DESCRIPTION
                   "This object indicates upstream ETH frame error ratio in current 15 minutes.
                    The value of this object indicates the exponente of the exponential expression of the upstream ETH frame error ratio.
                    For example, if the upstream ETH frame bit error ratio is calculated to be (0.0012), the exponential expression is 1.2E-3.
                    The multiplicando (1.2) is ignored, and the value of this object is (3).
                    The value (-1) indicates that the query fails or no information is detected.
                    The value (0xFFFFFFE) indicates that the bit error ratio is (0).
                    The value (0) indicates that the bit error ratio is (1)."
               ::= { hwGponOntTrafficFlowStatisticEntry 13 }

        hwGponOntTrafficFlowStatisticUpGemFrameErrorRatio OBJECT-TYPE
               SYNTAX Counter64
               MAX-ACCESS read-only
               STATUS current
               DESCRIPTION
                   "This object indicates upstream GEM frame error ratio in current 15 minutes.
                    The value of this object indicates the exponente of the exponential expression of the upstream GEM frame error ratio.
                    For example, if the upstream GEM frame bit error ratio is calculated to be (0.0012), the exponential expression is 1.2E-3.
                    The multiplicando (1.2) is ignored, and the value of this object is (3).
                    The value (-1) indicates that the query fails or no information is detected.
                    The value (0xFFFFFFE) indicates that the bit error ratio is (0).
                    The value (0) indicates that the bit error ratio is (1)."
               ::= { hwGponOntTrafficFlowStatisticEntry 14 }

        hwGponOntTrafficFlowStatisticClear OBJECT-TYPE
            SYNTAX INTEGER{
                clear(1),
                invalid(-1)
            }
            MAX-ACCESS read-write
            STATUS current
            DESCRIPTION
                "This object is used to clear the statistics.
                 Options:
                 1. clear(1)                    - Indicates that clear the statistics
                 2. invalid(-1)                 - Indicates that the query fails or no information is detected
                "
            ::= { hwGponOntTrafficFlowStatisticEntry 20 }

-- Table : HwEponOltEthernetStatisticTable
        hwEponOltEthernetStatisticTable OBJECT-TYPE
            SYNTAX     SEQUENCE OF HwEponOltEthernetStatisticEntry
            MAX-ACCESS not-accessible
            STATUS     current
            DESCRIPTION
                "The OLT ETH statisitcs table. The index of this table is ifIndex."
            ::= {  hwXponDeviceStatisticObjects 41 }

        hwEponOltEthernetStatisticEntry OBJECT-TYPE
            SYNTAX     HwEponOltEthernetStatisticEntry
            MAX-ACCESS not-accessible
            STATUS     current
            DESCRIPTION
                "The OLT ETH statisitcs table. The index of this entry is ifIndex."
            INDEX       { ifIndex  }
            ::= { hwEponOltEthernetStatisticTable 1 }

        HwEponOltEthernetStatisticEntry ::=
            SEQUENCE {
                hwEponOltEthernetStatisticRcvFrames                       Counter64,
                hwEponOltEthernetStatisticRcvBoardcastFrames              Counter64,
                hwEponOltEthernetStatisticRcvMulticastFrames              Counter64,
                hwEponOltEthernetStatisticRcvUnicastFrames                Counter64,
                hwEponOltEthernetStatisticRcv64OctetFrames                Counter64,
                hwEponOltEthernetStatisticRcv65to127OctetFrames           Counter64,
                hwEponOltEthernetStatisticRcv128to255OctetFrames          Counter64,
                hwEponOltEthernetStatisticRcv256to511OctetFrames          Counter64,
                hwEponOltEthernetStatisticRcv512to1023OctetFrames         Counter64,
                hwEponOltEthernetStatisticRcv1024to1518OctetFrames        Counter64,
                hwEponOltEthernetStatisticRcvOver1518OctetFrames          Counter64,
                hwEponOltEthernetStatisticRcvOctets                       Counter64,
                hwEponOltEthernetStatisticRcvOversizeFrames               Counter64,
                hwEponOltEthernetStatisticRcvUndersizeFrames              Counter64,
                hwEponOltEthernetStatisticRcvCrcErrorFrames               Counter64,
                hwEponOltEthernetStatisticRcvDiscardFrames                Counter64,
                hwEponOltEthernetStatisticSendFrames                      Counter64,
                hwEponOltEthernetStatisticSendBoardcastFrames             Counter64,
                hwEponOltEthernetStatisticSendMulticastFrames             Counter64,
                hwEponOltEthernetStatisticSendUnicastFrames               Counter64,
                hwEponOltEthernetStatisticSend64OctetFrames               Counter64,
                hwEponOltEthernetStatisticSend65to127OctetFrames          Counter64,
                hwEponOltEthernetStatisticSend128to255OctetFrames         Counter64,
                hwEponOltEthernetStatisticSend256to511OctetFrames         Counter64,
                hwEponOltEthernetStatisticSend512to1023OctetFrames        Counter64,
                hwEponOltEthernetStatisticSend1024to1518OctetFrames       Counter64,
                hwEponOltEthernetStatisticSendOver1518OctetFrames         Counter64,
                hwEponOltEthernetStatisticSendOctets                      Counter64,
                hwEponOltEthernetStatisticClear                           INTEGER,
                hwEponOltEthernetStatisticRcvErrorFrames                  Counter64,
                hwEponOltEthernetStatisticRcvFragments                    Counter64,
                hwEponOltEthernetStatisticRcvJabbers                      Counter64,
                hwEponOltEthernetStatisticRcvDropEvents                   Counter64,
                hwEponOltEthernetStatisticSendDropEvents                  Counter64,
                hwEponOltEthernetStatisticSendDiscardFrames               Counter64,
                hwEponOltEthernetStatisticSendErrorFrames                 Counter64,
                hwEponOltEthernetStatisticSendCrcErrorFrames              Counter64,
                hwEponOltEthernetStatisticSendUndersizeFrames             Counter64,
                hwEponOltEthernetStatisticSendOversizeFrames              Counter64,
                hwEponOltEthernetStatisticSendFragments                   Counter64,
                hwEponOltEthernetStatisticSendJabbers                     Counter64
            }

        hwEponOltEthernetStatisticRcvFrames  OBJECT-TYPE
            SYNTAX     Counter64
            MAX-ACCESS   read-only
            STATUS      current
            DESCRIPTION
                "This object indicates the received frames."
            ::= { hwEponOltEthernetStatisticEntry 1 }

        hwEponOltEthernetStatisticRcvBoardcastFrames  OBJECT-TYPE
            SYNTAX     Counter64
            MAX-ACCESS   read-only
            STATUS      current
            DESCRIPTION
                "This object indicates the received broadcast frames."
            ::= { hwEponOltEthernetStatisticEntry 2 }

        hwEponOltEthernetStatisticRcvMulticastFrames  OBJECT-TYPE
            SYNTAX     Counter64
            MAX-ACCESS   read-only
            STATUS      current
            DESCRIPTION
                "This object indicates the received multicast frames."
            ::= { hwEponOltEthernetStatisticEntry 3 }

        hwEponOltEthernetStatisticRcvUnicastFrames  OBJECT-TYPE
            SYNTAX     Counter64
            MAX-ACCESS   read-only
            STATUS      current
            DESCRIPTION
                "This object indicates the received unicast frames."
            ::= { hwEponOltEthernetStatisticEntry 4 }

        hwEponOltEthernetStatisticRcv64OctetFrames  OBJECT-TYPE
            SYNTAX     Counter64
            MAX-ACCESS   read-only
            STATUS      current
            DESCRIPTION
                "This object indicates the received 64-octet frames."
            ::= { hwEponOltEthernetStatisticEntry 5 }

        hwEponOltEthernetStatisticRcv65to127OctetFrames  OBJECT-TYPE
            SYNTAX     Counter64
            MAX-ACCESS   read-only
            STATUS      current
            DESCRIPTION
                "This object indicates the received 65~127-octet frames."
            ::= { hwEponOltEthernetStatisticEntry 6 }

        hwEponOltEthernetStatisticRcv128to255OctetFrames  OBJECT-TYPE
            SYNTAX     Counter64
            MAX-ACCESS   read-only
            STATUS      current
            DESCRIPTION
                "This object indicates the received 128~255-octet frames."
            ::= { hwEponOltEthernetStatisticEntry 7 }

        hwEponOltEthernetStatisticRcv256to511OctetFrames  OBJECT-TYPE
            SYNTAX     Counter64
            MAX-ACCESS   read-only
            STATUS      current
            DESCRIPTION
                "This object indicates the received 256~511-octet frames."
            ::= { hwEponOltEthernetStatisticEntry 8 }

        hwEponOltEthernetStatisticRcv512to1023OctetFrames  OBJECT-TYPE
            SYNTAX     Counter64
            MAX-ACCESS   read-only
            STATUS      current
            DESCRIPTION
                "This object indicates the received 512~1023-octet frames."
            ::= { hwEponOltEthernetStatisticEntry 9 }

            hwEponOltEthernetStatisticRcv1024to1518OctetFrames  OBJECT-TYPE
        SYNTAX     Counter64
            MAX-ACCESS   read-only
            STATUS      current
            DESCRIPTION
                "This object indicates the received 1024~1518-octet frames."
            ::= { hwEponOltEthernetStatisticEntry 10 }

        hwEponOltEthernetStatisticRcvOver1518OctetFrames  OBJECT-TYPE
            SYNTAX     Counter64
            MAX-ACCESS   read-only
            STATUS      current
            DESCRIPTION
                "This object indicates the received over 1518-octet frames."
            ::= { hwEponOltEthernetStatisticEntry 11 }

        hwEponOltEthernetStatisticRcvOctets  OBJECT-TYPE
            SYNTAX     Counter64
            MAX-ACCESS   read-only
            STATUS      current
            DESCRIPTION
                "This object indicates the received octets."
            ::= { hwEponOltEthernetStatisticEntry 12 }

        hwEponOltEthernetStatisticRcvOversizeFrames  OBJECT-TYPE
            SYNTAX     Counter64
            MAX-ACCESS   read-only
            STATUS      current
            DESCRIPTION
                "This object indicates the received oversize frames."
            ::= { hwEponOltEthernetStatisticEntry 13 }

        hwEponOltEthernetStatisticRcvUndersizeFrames  OBJECT-TYPE
            SYNTAX     Counter64
            MAX-ACCESS   read-only
            STATUS      current
            DESCRIPTION
                "This object indicates the received undersize frames."
            ::= { hwEponOltEthernetStatisticEntry 14 }

        hwEponOltEthernetStatisticRcvCrcErrorFrames  OBJECT-TYPE
            SYNTAX     Counter64
            MAX-ACCESS   read-only
            STATUS      current
            DESCRIPTION
                "This object indicates the received CRC error frames."
            ::= { hwEponOltEthernetStatisticEntry 15 }

        hwEponOltEthernetStatisticRcvDiscardFrames  OBJECT-TYPE
            SYNTAX     Counter64
            MAX-ACCESS   read-only
            STATUS      current
            DESCRIPTION
                "This object indicates the received discarded frames."
            ::= { hwEponOltEthernetStatisticEntry 16 }

        hwEponOltEthernetStatisticSendFrames  OBJECT-TYPE
            SYNTAX     Counter64
            MAX-ACCESS   read-only
            STATUS      current
            DESCRIPTION
                "This object indicates the sent frames."
            ::= { hwEponOltEthernetStatisticEntry 17 }

        hwEponOltEthernetStatisticSendBoardcastFrames  OBJECT-TYPE
            SYNTAX     Counter64
            MAX-ACCESS   read-only
            STATUS      current
            DESCRIPTION
                "This object indicates the sent broadcast frames."
            ::= { hwEponOltEthernetStatisticEntry 18 }

        hwEponOltEthernetStatisticSendMulticastFrames  OBJECT-TYPE
            SYNTAX     Counter64
            MAX-ACCESS   read-only
            STATUS      current
            DESCRIPTION
                "This object indicates the sent multicast frames."
            ::= { hwEponOltEthernetStatisticEntry 19 }

        hwEponOltEthernetStatisticSendUnicastFrames  OBJECT-TYPE
            SYNTAX     Counter64
            MAX-ACCESS   read-only
            STATUS      current
            DESCRIPTION
                "This object indicates the sent unicast frames."
            ::= { hwEponOltEthernetStatisticEntry 20 }

        hwEponOltEthernetStatisticSend64OctetFrames  OBJECT-TYPE
            SYNTAX     Counter64
            MAX-ACCESS   read-only
            STATUS      current
            DESCRIPTION
                "This object indicates the sent 64-octet frames."
            ::= { hwEponOltEthernetStatisticEntry 21 }

        hwEponOltEthernetStatisticSend65to127OctetFrames  OBJECT-TYPE
            SYNTAX     Counter64
            MAX-ACCESS   read-only
            STATUS      current
            DESCRIPTION
                "This object indicates the sent 65~127-octet frames."
            ::= { hwEponOltEthernetStatisticEntry 22 }

        hwEponOltEthernetStatisticSend128to255OctetFrames  OBJECT-TYPE
            SYNTAX     Counter64
            MAX-ACCESS   read-only
            STATUS      current
            DESCRIPTION
                "This object indicates the sent 128~255-octet frames."
            ::= { hwEponOltEthernetStatisticEntry 23 }

        hwEponOltEthernetStatisticSend256to511OctetFrames  OBJECT-TYPE
            SYNTAX     Counter64
            MAX-ACCESS   read-only
            STATUS      current
            DESCRIPTION
                "This object indicates the sent 256~511-octet frames."
            ::= { hwEponOltEthernetStatisticEntry 24 }

        hwEponOltEthernetStatisticSend512to1023OctetFrames  OBJECT-TYPE
            SYNTAX     Counter64
            MAX-ACCESS   read-only
            STATUS      current
            DESCRIPTION
                "This object indicates the sent 512~1023-octet frames."
            ::= { hwEponOltEthernetStatisticEntry 25 }

        hwEponOltEthernetStatisticSend1024to1518OctetFrames  OBJECT-TYPE
            SYNTAX     Counter64
            MAX-ACCESS   read-only
            STATUS      current
            DESCRIPTION
                "This object indicates the sent 1024~1518-octet frames."
            ::= { hwEponOltEthernetStatisticEntry 26 }

        hwEponOltEthernetStatisticSendOver1518OctetFrames  OBJECT-TYPE
            SYNTAX     Counter64
            MAX-ACCESS   read-only
            STATUS      current
            DESCRIPTION
                "This object indicates the sent over 1518-octet frames."
            ::= { hwEponOltEthernetStatisticEntry 27 }

        hwEponOltEthernetStatisticSendOctets   OBJECT-TYPE
            SYNTAX     Counter64
            MAX-ACCESS   read-only
            STATUS      current
            DESCRIPTION
                "This object indicates the sent octets."
            ::= { hwEponOltEthernetStatisticEntry 28 }

        hwEponOltEthernetStatisticClear   OBJECT-TYPE
            SYNTAX     INTEGER{
                clear(1),
                invalid(-1)
            }
            MAX-ACCESS   read-write
            STATUS      current
            DESCRIPTION
                "This object is used to clear the statistics.
                 Options:
                 1. clear(1)                    - Indicates that clear the statistics
                 2. invalid(-1)                 - Indicates that the query fails or no information is detected
                "
            ::= { hwEponOltEthernetStatisticEntry 50 }

        hwEponOltEthernetStatisticRcvErrorFrames OBJECT-TYPE
            SYNTAX     Counter64
            MAX-ACCESS   read-only
            STATUS      current
            DESCRIPTION
                "This object indicates the received error frames."
            ::= { hwEponOltEthernetStatisticEntry 51 }

        hwEponOltEthernetStatisticRcvFragments OBJECT-TYPE
            SYNTAX     Counter64
            MAX-ACCESS   read-only
            STATUS      current
            DESCRIPTION
                "This object indicates the received fragments."
            ::= { hwEponOltEthernetStatisticEntry 52 }

        hwEponOltEthernetStatisticRcvJabbers OBJECT-TYPE
            SYNTAX     Counter64
            MAX-ACCESS   read-only
            STATUS      current
            DESCRIPTION
                "This object indicates the received jabbers."
            ::= { hwEponOltEthernetStatisticEntry 53 }

        hwEponOltEthernetStatisticRcvDropEvents OBJECT-TYPE
            SYNTAX     Counter64
            MAX-ACCESS   read-only
            STATUS      current
            DESCRIPTION
                "This object indicates the received drop events."
            ::= { hwEponOltEthernetStatisticEntry 54 }

        hwEponOltEthernetStatisticSendDropEvents OBJECT-TYPE
            SYNTAX     Counter64
            MAX-ACCESS   read-only
            STATUS      current
            DESCRIPTION
                "This object indicates the send drop events."
            ::= { hwEponOltEthernetStatisticEntry 55 }

        hwEponOltEthernetStatisticSendDiscardFrames OBJECT-TYPE
            SYNTAX     Counter64
            MAX-ACCESS   read-only
            STATUS      current
            DESCRIPTION
                "This object indicates the send discard frames."
            ::= { hwEponOltEthernetStatisticEntry 56 }

        hwEponOltEthernetStatisticSendErrorFrames OBJECT-TYPE
            SYNTAX     Counter64
            MAX-ACCESS   read-only
            STATUS      current
            DESCRIPTION
                "This object indicates the send error frames."
            ::= { hwEponOltEthernetStatisticEntry 57 }

        hwEponOltEthernetStatisticSendCrcErrorFrames OBJECT-TYPE
            SYNTAX     Counter64
            MAX-ACCESS   read-only
            STATUS      current
            DESCRIPTION
                "This object indicates the send CRC error frames."
            ::= { hwEponOltEthernetStatisticEntry 58 }

        hwEponOltEthernetStatisticSendUndersizeFrames OBJECT-TYPE
            SYNTAX     Counter64
            MAX-ACCESS   read-only
            STATUS      current
            DESCRIPTION
                "This object indicates the send undersize frames."
            ::= { hwEponOltEthernetStatisticEntry 59 }

        hwEponOltEthernetStatisticSendOversizeFrames OBJECT-TYPE
            SYNTAX     Counter64
            MAX-ACCESS   read-only
            STATUS      current
            DESCRIPTION
                "This object indicates the send oversize frames."
            ::= { hwEponOltEthernetStatisticEntry 60 }

        hwEponOltEthernetStatisticSendFragments OBJECT-TYPE
            SYNTAX     Counter64
            MAX-ACCESS   read-only
            STATUS      current
            DESCRIPTION
                "This object indicates the send fragments."
            ::= { hwEponOltEthernetStatisticEntry 61 }

        hwEponOltEthernetStatisticSendJabbers OBJECT-TYPE
            SYNTAX     Counter64
            MAX-ACCESS   read-only
            STATUS      current
            DESCRIPTION
                "This object indicates the send jabbers."
            ::= { hwEponOltEthernetStatisticEntry 62 }

-- Table :  HwEponOltLlidStatisticTable
        hwEponOltLlidStatisticTable OBJECT-TYPE
            SYNTAX     SEQUENCE OF HwEponOltLlidStatisticEntry
            MAX-ACCESS not-accessible
            STATUS     current
            DESCRIPTION
                "The OLT LLID statistics table.
                 The index of this table is a combination of ifIndex,
                 hwEponDeviceOntIndex and hwEponDeviceOntLlid.
                "
            ::= {  hwXponDeviceStatisticObjects 42 }

        hwEponOltLlidStatisticEntry OBJECT-TYPE
            SYNTAX     HwEponOltLlidStatisticEntry
            MAX-ACCESS not-accessible
            STATUS     current
            DESCRIPTION
                "The OLT LLID statistics table.
                 The index of this entry is a combination of ifIndex,
                 hwEponDeviceOntIndex and hwEponDeviceOntLlid.
                "
            INDEX       { ifIndex, hwEponDeviceOntIndex, hwEponDeviceOntLlid }
            ::= { hwEponOltLlidStatisticTable 1 }

        HwEponOltLlidStatisticEntry ::=
            SEQUENCE {
                hwEponDeviceOntLlid                                 Integer32,
                hwEponOltLlidStatisticRecvDataFrames                Counter64,
                hwEponOltLlidStatisticRecvDataBytes                 Counter64,
                hwEponOltLlidStatisticRecvUnicastFrames             Counter64,
                hwEponOltLlidStatisticRecvMulticastFrames           Counter64,
                hwEponOltLlidStatisticRecvBoardcastFrames           Counter64,
                hwEponOltLlidStatisticRecvRightFrames               Counter64,
                hwEponOltLlidStatisticRecvRightBytes                Counter64,
                hwEponOltLlidStatisticRecvErrorFrames               Counter64,
                hwEponOltLlidStatisticRecvErrorBytes                Counter64,
                hwEponOltLlidStatisticRecv64ByteFrames              Counter64,
                hwEponOltLlidStatisticRecv65to127ByteFrames         Counter64,
                hwEponOltLlidStatisticRecv128to255ByteFrames        Counter64,
                hwEponOltLlidStatisticRecv256to511ByteFrames        Counter64,
                hwEponOltLlidStatisticRecv512to1023ByteFrames       Counter64,
                hwEponOltLlidStatisticRecv1024to1518ByteFrames      Counter64,
                hwEponOltLlidStatisticRecvOver1518ByteFrames        Counter64,
                hwEponOltLlidStatisticRecvUndersizeFrames           Counter64,
                hwEponOltLlidStatisticRecvOversizeFrames            Counter64,
                hwEponOltLlidStatisticRecvFcsErrorFrames            Counter64,
                hwEponOltLlidStatisticTransDataFrames               Counter64,
                hwEponOltLlidStatisticTransDataBytes                Counter64,
                hwEponOltLlidStatisticTransUnicastFrames            Counter64,
                hwEponOltLlidStatisticTransMulticastFrames          Counter64,
                hwEponOltLlidStatisticTransBoardcastFrames          Counter64,
                hwEponOltLlidStatisticTrans64ByteFrames             Counter64,
                hwEponOltLlidStatisticTrans65to127ByteFrames        Counter64,
                hwEponOltLlidStatisticTrans128to255ByteFrames       Counter64,
                hwEponOltLlidStatisticTrans256to511ByteFrames       Counter64,
                hwEponOltLlidStatisticTrans512to1023ByteFrames      Counter64,
                hwEponOltLlidStatisticTrans1024to1518ByteFrames     Counter64,
                hwEponOltLlidStatisticTransOver1518ByteFrames       Counter64,
                hwEponOltLlidStatisticTransFcsErrorFrames           Counter64,
                hwEponOltLlidStatisticRecvLineCodeErrorFrames       Counter64,
                hwEponOltLlidStatisticClear                         INTEGER,
                hwEponOltLlidStatisticRecvCrcErrorFrames            Counter64,
                hwEponOltLlidStatisticRecvFragments                 Counter64,
                hwEponOltLlidStatisticRecvJabbers                   Counter64,
                hwEponOltLlidStatisticRecvDiscardFrames             Counter64,
                hwEponOltLlidStatisticRecvDropEvents                Counter64,
                hwEponOltLlidStatisticTransDropEvents               Counter64,
                hwEponOltLlidStatisticTransDiscardFrames            Counter64,
                hwEponOltLlidStatisticTransErrorFrames              Counter64,
                hwEponOltLlidStatisticTransCrcErrorFrames           Counter64,
                hwEponOltLlidStatisticTransUndersizeFrames          Counter64,
                hwEponOltLlidStatisticTransOversizeFrames           Counter64,
                hwEponOltLlidStatisticTransFragments                Counter64,
                hwEponOltLlidStatisticTransJabbers                  Counter64
            }

        hwEponDeviceOntLlid  OBJECT-TYPE
            SYNTAX     Integer32
            MAX-ACCESS   not-accessible
            STATUS      current
            DESCRIPTION
                "This object indicates the ONT LLID."
            ::= { hwEponOltLlidStatisticEntry 1 }

        hwEponOltLlidStatisticRecvDataFrames  OBJECT-TYPE
            SYNTAX     Counter64
            MAX-ACCESS   read-only
            STATUS      current
            DESCRIPTION
                "This object indicates the received data frames."
            ::= { hwEponOltLlidStatisticEntry 2 }

        hwEponOltLlidStatisticRecvDataBytes  OBJECT-TYPE
            SYNTAX     Counter64
            MAX-ACCESS   read-only
            STATUS      current
            DESCRIPTION
                "This object indicates the received data octets."
            ::= { hwEponOltLlidStatisticEntry 3 }

        hwEponOltLlidStatisticRecvUnicastFrames  OBJECT-TYPE
            SYNTAX     Counter64
            MAX-ACCESS   read-only
            STATUS      current
            DESCRIPTION
                "This object indicates the received unicast frames."
            ::= { hwEponOltLlidStatisticEntry 4 }

        hwEponOltLlidStatisticRecvMulticastFrames  OBJECT-TYPE
            SYNTAX     Counter64
            MAX-ACCESS   read-only
            STATUS      current
            DESCRIPTION
                "This object indicates the received multicast frames."
            ::= { hwEponOltLlidStatisticEntry 5 }

        hwEponOltLlidStatisticRecvBoardcastFrames  OBJECT-TYPE
            SYNTAX     Counter64
            MAX-ACCESS   read-only
            STATUS      current
            DESCRIPTION
                "This object indicates the received broadcast frames."
            ::= { hwEponOltLlidStatisticEntry 6 }

        hwEponOltLlidStatisticRecvRightFrames  OBJECT-TYPE
            SYNTAX     Counter64
            MAX-ACCESS   read-only
            STATUS      current
            DESCRIPTION
                "This object indicates the received right frames."
            ::= { hwEponOltLlidStatisticEntry 7 }

        hwEponOltLlidStatisticRecvRightBytes  OBJECT-TYPE
            SYNTAX     Counter64
            MAX-ACCESS   read-only
            STATUS      current
            DESCRIPTION
                "This object indicates the received right octets."
            ::= { hwEponOltLlidStatisticEntry 8 }

        hwEponOltLlidStatisticRecvErrorFrames  OBJECT-TYPE
            SYNTAX     Counter64
            MAX-ACCESS   read-only
            STATUS      current
            DESCRIPTION
                "This object indicates the received error frames."
            ::= { hwEponOltLlidStatisticEntry 9 }

        hwEponOltLlidStatisticRecvErrorBytes  OBJECT-TYPE
            SYNTAX     Counter64
            MAX-ACCESS   read-only
            STATUS      current
            DESCRIPTION
                "This object indicates the received error octets."
            ::= { hwEponOltLlidStatisticEntry 10 }

        hwEponOltLlidStatisticRecv64ByteFrames  OBJECT-TYPE
            SYNTAX     Counter64
            MAX-ACCESS   read-only
            STATUS      current
            DESCRIPTION
                "This object indicates the received 64-octet frames."
            ::= { hwEponOltLlidStatisticEntry 11 }

        hwEponOltLlidStatisticRecv65to127ByteFrames  OBJECT-TYPE
            SYNTAX     Counter64
            MAX-ACCESS   read-only
            STATUS      current
            DESCRIPTION
                "This object indicates the received 65~127-octet frames."
            ::= { hwEponOltLlidStatisticEntry 12 }

        hwEponOltLlidStatisticRecv128to255ByteFrames  OBJECT-TYPE
            SYNTAX     Counter64
            MAX-ACCESS   read-only
            STATUS      current
            DESCRIPTION
                "This object indicates the received 128~255-octet frames."
            ::= { hwEponOltLlidStatisticEntry 13 }

        hwEponOltLlidStatisticRecv256to511ByteFrames  OBJECT-TYPE
            SYNTAX     Counter64
            MAX-ACCESS   read-only
            STATUS      current
            DESCRIPTION
                "This object indicates the received 256~511-octet frames."
            ::= { hwEponOltLlidStatisticEntry 14 }

        hwEponOltLlidStatisticRecv512to1023ByteFrames  OBJECT-TYPE
            SYNTAX     Counter64
            MAX-ACCESS   read-only
            STATUS      current
            DESCRIPTION
                "This object indicates the received 512~1023-octet frames."
            ::= { hwEponOltLlidStatisticEntry 15 }

        hwEponOltLlidStatisticRecv1024to1518ByteFrames  OBJECT-TYPE
            SYNTAX     Counter64
            MAX-ACCESS   read-only
            STATUS      current
            DESCRIPTION
                "This object indicates the received 1024~1518-octet frames."
            ::= { hwEponOltLlidStatisticEntry 16 }

        hwEponOltLlidStatisticRecvOver1518ByteFrames  OBJECT-TYPE
            SYNTAX     Counter64
            MAX-ACCESS   read-only
            STATUS      current
            DESCRIPTION
                "This object indicates the received over 1518-octet frames."
            ::= { hwEponOltLlidStatisticEntry 17 }

        hwEponOltLlidStatisticRecvUndersizeFrames  OBJECT-TYPE
            SYNTAX     Counter64
            MAX-ACCESS   read-only
            STATUS      current
            DESCRIPTION
                "This object indicates the received undersize frames."
            ::= { hwEponOltLlidStatisticEntry 18 }

        hwEponOltLlidStatisticRecvOversizeFrames  OBJECT-TYPE
            SYNTAX     Counter64
            MAX-ACCESS   read-only
            STATUS      current
            DESCRIPTION
                "This object indicates the received oversize frames."
            ::= { hwEponOltLlidStatisticEntry 19 }

        hwEponOltLlidStatisticRecvFcsErrorFrames  OBJECT-TYPE
            SYNTAX     Counter64
            MAX-ACCESS   read-only
            STATUS      current
            DESCRIPTION
                "This object indicates the received FCS error frames."
            ::= { hwEponOltLlidStatisticEntry 20 }

        hwEponOltLlidStatisticTransDataFrames  OBJECT-TYPE
            SYNTAX     Counter64
            MAX-ACCESS   read-only
            STATUS      current
            DESCRIPTION
                "This object indicates the sent data frames."
            ::= { hwEponOltLlidStatisticEntry 21 }

        hwEponOltLlidStatisticTransDataBytes  OBJECT-TYPE
            SYNTAX     Counter64
            MAX-ACCESS   read-only
            STATUS      current
            DESCRIPTION
                "This object indicates the sent data octets."
            ::= { hwEponOltLlidStatisticEntry 22 }

        hwEponOltLlidStatisticTransUnicastFrames  OBJECT-TYPE
            SYNTAX     Counter64
            MAX-ACCESS   read-only
            STATUS      current
            DESCRIPTION
                "This object indicates the sent unicast frames."
            ::= { hwEponOltLlidStatisticEntry 23 }

        hwEponOltLlidStatisticTransMulticastFrames  OBJECT-TYPE
            SYNTAX     Counter64
            MAX-ACCESS   read-only
            STATUS      current
            DESCRIPTION
                "This object indicates the sent multicast frames."
            ::= { hwEponOltLlidStatisticEntry 24 }

        hwEponOltLlidStatisticTransBoardcastFrames  OBJECT-TYPE
            SYNTAX     Counter64
            MAX-ACCESS   read-only
            STATUS      current
            DESCRIPTION
                "This object indicates the sent broadcast frames."
            ::= { hwEponOltLlidStatisticEntry 25 }

        hwEponOltLlidStatisticTrans64ByteFrames  OBJECT-TYPE
            SYNTAX     Counter64
            MAX-ACCESS   read-only
            STATUS      current
            DESCRIPTION
                "This object indicates the sent 64-octet frames."
            ::= { hwEponOltLlidStatisticEntry 26 }

        hwEponOltLlidStatisticTrans65to127ByteFrames  OBJECT-TYPE
            SYNTAX     Counter64
            MAX-ACCESS   read-only
            STATUS      current
            DESCRIPTION
                "This object indicates the sent 65~127-octet frames."
            ::= { hwEponOltLlidStatisticEntry 27 }

        hwEponOltLlidStatisticTrans128to255ByteFrames  OBJECT-TYPE
            SYNTAX     Counter64
            MAX-ACCESS   read-only
            STATUS      current
            DESCRIPTION
                "This object indicates the sent 128~255-octet frames."
            ::= { hwEponOltLlidStatisticEntry 28 }

        hwEponOltLlidStatisticTrans256to511ByteFrames  OBJECT-TYPE
            SYNTAX     Counter64
            MAX-ACCESS   read-only
            STATUS      current
            DESCRIPTION
                "This object indicates the sent 256~511-octet frames."
            ::= { hwEponOltLlidStatisticEntry 29 }

        hwEponOltLlidStatisticTrans512to1023ByteFrames  OBJECT-TYPE
            SYNTAX     Counter64
            MAX-ACCESS   read-only
            STATUS      current
            DESCRIPTION
                "This object indicates the sent 512~1023-octet frames."
            ::= { hwEponOltLlidStatisticEntry 30 }

        hwEponOltLlidStatisticTrans1024to1518ByteFrames  OBJECT-TYPE
            SYNTAX     Counter64
            MAX-ACCESS   read-only
            STATUS      current
            DESCRIPTION
                "This object indicates the sent 1024~1518-octet frames."
            ::= { hwEponOltLlidStatisticEntry 31 }

        hwEponOltLlidStatisticTransOver1518ByteFrames  OBJECT-TYPE
            SYNTAX     Counter64
            MAX-ACCESS   read-only
            STATUS      current
            DESCRIPTION
                "This object indicates the sent over 1518-octet frames."
            ::= { hwEponOltLlidStatisticEntry 32 }

        hwEponOltLlidStatisticTransFcsErrorFrames  OBJECT-TYPE
            SYNTAX     Counter64
            MAX-ACCESS   read-only
            STATUS      current
            DESCRIPTION
                "This object indicates the sent FCS error frames."
            ::= { hwEponOltLlidStatisticEntry 33 }

        hwEponOltLlidStatisticRecvLineCodeErrorFrames  OBJECT-TYPE
            SYNTAX     Counter64
            MAX-ACCESS   read-only
            STATUS      current
            DESCRIPTION
                "Received line code error frames."
            ::= { hwEponOltLlidStatisticEntry 34 }

        hwEponOltLlidStatisticClear    OBJECT-TYPE
            SYNTAX     INTEGER{
                clear(1),
                invalid(-1)
            }
            MAX-ACCESS   read-write
            STATUS      current
            DESCRIPTION
                "This object is used to clear the statistics.
                 Options:
                 1. clear(1)                    - Indicates that clear the statistics
                 2. invalid(-1)                 - Indicates that the query fails or no information is detected
                "
            ::= { hwEponOltLlidStatisticEntry 50 }

        hwEponOltLlidStatisticRecvCrcErrorFrames  OBJECT-TYPE
            SYNTAX     Counter64
            MAX-ACCESS   read-only
            STATUS      current
            DESCRIPTION
                "This object indicates the recieved CRC error frames."
            ::= { hwEponOltLlidStatisticEntry 51 }

        hwEponOltLlidStatisticRecvFragments  OBJECT-TYPE
            SYNTAX     Counter64
            MAX-ACCESS   read-only
            STATUS      current
            DESCRIPTION
                "This object indicates the recieved fragments."
            ::= { hwEponOltLlidStatisticEntry 52 }

        hwEponOltLlidStatisticRecvJabbers  OBJECT-TYPE
            SYNTAX     Counter64
            MAX-ACCESS   read-only
            STATUS      current
            DESCRIPTION
                "This object indicates the recieved jabbers."
            ::= { hwEponOltLlidStatisticEntry 53 }

        hwEponOltLlidStatisticRecvDiscardFrames  OBJECT-TYPE
            SYNTAX     Counter64
            MAX-ACCESS   read-only
            STATUS      current
            DESCRIPTION
                "This object indicates the recieved discarded frames."
            ::= { hwEponOltLlidStatisticEntry 54 }

        hwEponOltLlidStatisticRecvDropEvents  OBJECT-TYPE
            SYNTAX     Counter64
            MAX-ACCESS   read-only
            STATUS      current
            DESCRIPTION
                "This object indicates the recieved drop events."
            ::= { hwEponOltLlidStatisticEntry 55 }

        hwEponOltLlidStatisticTransDropEvents  OBJECT-TYPE
            SYNTAX     Counter64
            MAX-ACCESS   read-only
            STATUS      current
            DESCRIPTION
                "This object indicates the sent drop events."
            ::= { hwEponOltLlidStatisticEntry 56 }

        hwEponOltLlidStatisticTransDiscardFrames  OBJECT-TYPE
            SYNTAX     Counter64
            MAX-ACCESS   read-only
            STATUS      current
            DESCRIPTION
                "This object indicates the sent discarded frames."
            ::= { hwEponOltLlidStatisticEntry 57 }

        hwEponOltLlidStatisticTransErrorFrames  OBJECT-TYPE
            SYNTAX     Counter64
            MAX-ACCESS   read-only
            STATUS      current
            DESCRIPTION
                "This object indicates the sent error frames."
            ::= { hwEponOltLlidStatisticEntry 58 }

        hwEponOltLlidStatisticTransCrcErrorFrames  OBJECT-TYPE
            SYNTAX     Counter64
            MAX-ACCESS   read-only
            STATUS      current
            DESCRIPTION
                "This object indicates the sent CRC error frames."
            ::= { hwEponOltLlidStatisticEntry 59 }

        hwEponOltLlidStatisticTransUndersizeFrames  OBJECT-TYPE
            SYNTAX     Counter64
            MAX-ACCESS   read-only
            STATUS      current
            DESCRIPTION
                "This object indicates the sent undersize frames."
            ::= { hwEponOltLlidStatisticEntry 60 }

        hwEponOltLlidStatisticTransOversizeFrames  OBJECT-TYPE
            SYNTAX     Counter64
            MAX-ACCESS   read-only
            STATUS      current
            DESCRIPTION
                "This object indicates the sent oversize frames."
            ::= { hwEponOltLlidStatisticEntry 61 }

        hwEponOltLlidStatisticTransFragments  OBJECT-TYPE
            SYNTAX     Counter64
            MAX-ACCESS   read-only
            STATUS      current
            DESCRIPTION
                "This object indicates the sent fragments."
            ::= { hwEponOltLlidStatisticEntry 62 }

        hwEponOltLlidStatisticTransJabbers  OBJECT-TYPE
            SYNTAX     Counter64
            MAX-ACCESS   read-only
            STATUS      current
            DESCRIPTION
                "This object indicates the sent jabbers."
            ::= { hwEponOltLlidStatisticEntry 63 }

-- Table : hwEponOntEthernetPortStatisticTable
        hwEponOntEthernetPortStatisticTable OBJECT-TYPE
            SYNTAX     SEQUENCE OF HwEponOntEthernetPortStatisticEntry
            MAX-ACCESS not-accessible
            STATUS     current
            DESCRIPTION
                "The ONT ETH port statistics table.
                 The index of this table is a combination of ifIndex,
                 hwEponDeviceOntIndex and hwEponDeviceOntEthernetPortId.
                "
            ::= {  hwXponDeviceStatisticObjects 43 }

        hwEponOntEthernetPortStatisticEntry OBJECT-TYPE
            SYNTAX     HwEponOntEthernetPortStatisticEntry
            MAX-ACCESS not-accessible
            STATUS     current
            DESCRIPTION
                "The ONT ETH port statistics table.
                 The index of this entry is a combination of ifIndex,
                 hwEponDeviceOntIndex and hwEponDeviceOntEthernetPortId.
                "
            INDEX       { ifIndex, hwEponDeviceOntIndex, hwEponDeviceOntEthernetPortId}
            ::= { hwEponOntEthernetPortStatisticTable 1 }

        HwEponOntEthernetPortStatisticEntry ::=
            SEQUENCE {
                hwEponOntEthernetPortStatisticRecvFrames                      Counter64,
                hwEponOntEthernetPortStatisticRecvMulticastFrames             Counter64,
                hwEponOntEthernetPortStatisticRecvBroadcastFrames             Counter64,
                hwEponOntEthernetPortStatisticRecv64OctetFrames               Counter64,
                hwEponOntEthernetPortStatisticRecv65to127OctetFrames          Counter64,
                hwEponOntEthernetPortStatisticRecv128to255OctetFrames         Counter64,
                hwEponOntEthernetPortStatisticRecv256to511OctetFrames         Counter64,
                hwEponOntEthernetPortStatisticRecv512to1023OctetFrames        Counter64,
                hwEponOntEthernetPortStatisticRecv1024to1518OctetFrames       Counter64,
                hwEponOntEthernetPortStatisticRecvUndersizeFrames             Counter64,
                hwEponOntEthernetPortStatisticRecvTooLongFrames               Counter64,
                hwEponOntEthernetPortStatisticRecvFragments                   Counter64,
                hwEponOntEthernetPortStatisticRecvJabberErrorFrames           Counter64,
                hwEponOntEthernetPortStatisticRecvFCSErrorFrames              Counter64,
                hwEponOntEthernetPortStatisticRecvDropFrames                  Counter64,
                hwEponOntEthernetPortStatisticRecvAlignmentErrorFrames        Counter64,
                hwEponOntEthernetPortStatisticInternalMACRecvErrorFrames      Counter64,
                hwEponOntEthernetPortStatisticRecvPPPoEFilteredFrames         Counter64,
                hwEponOntEthernetPortStatisticRecvBufferOverflows             Counter64,
                hwEponOntEthernetPortStatisticRecvOctets                      Counter64,
                hwEponOntEthernetPortStatisticTransFrames                     Counter64,
                hwEponOntEthernetPortStatisticTransDeferredFrames             Counter64,
                hwEponOntEthernetPortStatisticTransMTUExceededDiscardFrames   Counter64,
                hwEponOntEthernetPortStatisticTransCarrierSenseErrorFrames    Counter64,
                hwEponOntEthernetPortStatisticTransSQETestErrorFrames         Counter64,
                hwEponOntEthernetPortStatisticTransSingleCollisionFrames      Counter64,
                hwEponOntEthernetPortStatisticTransMultipleCollisionsFrames   Counter64,
                hwEponOntEthernetPortStatisticTransExcessiveCollisionFrames   Counter64,
                hwEponOntEthernetPortStatisticTransLateCollisionFrames        Counter64,
                hwEponOntEthernetPortStatisticInternalmacTransErrorFrames     Counter64,
                hwEponOntEthernetPortStatisticTransBufferOverflows            Counter64,
                hwEponOntEthernetPortStatisticTransOctets                     Counter64,
                hwEponOntEthernetPortStatisticStateChange                     Integer32,
                hwEponOntEthernetPortStatisticTransUnicastFrames              Counter64,
                hwEponOntEthernetPortStatisticTransBroadcastFrames            Counter64,
                hwEponOntEthernetPortStatisticTransMulticastFrames            Counter64,
                hwEponOntEthernetPortStatisticRecv1519toOversizeOctetFrames   Counter64,
                hwEponOntEthernetPortStatisticRecvUnicastFrames               Counter64,
                hwEponOntEthernetPortStatisticTrans64OctetFrames              Counter64,
                hwEponOntEthernetPortStatisticTrans65to127OctetFrames         Counter64,
                hwEponOntEthernetPortStatisticTrans128to255OctetFrames        Counter64,
                hwEponOntEthernetPortStatisticTrans256to511OctetFrames        Counter64,
                hwEponOntEthernetPortStatisticTrans512to1023OctetFrames       Counter64,
                hwEponOntEthernetPortStatisticTrans1024to1518OctetFrames      Counter64,
                hwEponOntEthernetPortStatisticTransOver1518OctetFrames        Counter64,
                hwEponOntEthernetPortStatisticClear                           INTEGER,
                hwEponOntEthernetPortStatisticRecvErrorFrames                 Counter64,
                hwEponOntEthernetPortStatisticRecvCrcErrorFrames              Counter64,
                hwEponOntEthernetPortStatisticRecvDropEvents                  Counter64,
                hwEponOntEthernetPortStatisticTransDropEvents                 Counter64,
                hwEponOntEthernetPortStatisticTransDiscardFrames              Counter64,
                hwEponOntEthernetPortStatisticTransErrorFrames                Counter64,
                hwEponOntEthernetPortStatisticTransCrcErrorFrames             Counter64,
                hwEponOntEthernetPortStatisticTransUndersizeFrames            Counter64,
                hwEponOntEthernetPortStatisticTransOversizeFrames             Counter64,
                hwEponOntEthernetPortStatisticTransFragments                  Counter64,
                hwEponOntEthernetPortStatisticTransJabbers                    Counter64
            }

        hwEponOntEthernetPortStatisticRecvFrames OBJECT-TYPE
            SYNTAX     Counter64
            MAX-ACCESS   read-only
            STATUS      current
            DESCRIPTION
                "This object indicates the received frames."
            ::= { hwEponOntEthernetPortStatisticEntry 1}

        hwEponOntEthernetPortStatisticRecvMulticastFrames  OBJECT-TYPE
            SYNTAX     Counter64
            MAX-ACCESS   read-only
            STATUS      current
            DESCRIPTION
                "This object indicates the received multicast frames."
            ::= { hwEponOntEthernetPortStatisticEntry 2}

        hwEponOntEthernetPortStatisticRecvBroadcastFrames OBJECT-TYPE
            SYNTAX     Counter64
            MAX-ACCESS   read-only
            STATUS      current
            DESCRIPTION
                "This object indicates the received boardcast frames."
            ::= { hwEponOntEthernetPortStatisticEntry 3}

        hwEponOntEthernetPortStatisticRecv64OctetFrames  OBJECT-TYPE
            SYNTAX     Counter64
            MAX-ACCESS   read-only
            STATUS      current
            DESCRIPTION
                "This object indicates the received 64-octet frames."
            ::= { hwEponOntEthernetPortStatisticEntry 4}

        hwEponOntEthernetPortStatisticRecv65to127OctetFrames OBJECT-TYPE
            SYNTAX     Counter64
            MAX-ACCESS   read-only
            STATUS      current
            DESCRIPTION
                "This object indicates the received 65~127-octet frames."
            ::= { hwEponOntEthernetPortStatisticEntry 5}

        hwEponOntEthernetPortStatisticRecv128to255OctetFrames OBJECT-TYPE
            SYNTAX     Counter64
            MAX-ACCESS   read-only
            STATUS      current
            DESCRIPTION
                "This object indicates the received 128~255-octet frames."
            ::= { hwEponOntEthernetPortStatisticEntry 6}

        hwEponOntEthernetPortStatisticRecv256to511OctetFrames OBJECT-TYPE
            SYNTAX     Counter64
            MAX-ACCESS   read-only
            STATUS      current
            DESCRIPTION
                "This object indicates the received 256~511-octet frames."
            ::= { hwEponOntEthernetPortStatisticEntry 7}

        hwEponOntEthernetPortStatisticRecv512to1023OctetFrames OBJECT-TYPE
            SYNTAX     Counter64
            MAX-ACCESS   read-only
            STATUS      current
            DESCRIPTION
                "This object indicates the received 512~1023-octet frames."
            ::= { hwEponOntEthernetPortStatisticEntry 8}

        hwEponOntEthernetPortStatisticRecv1024to1518OctetFrames OBJECT-TYPE
            SYNTAX     Counter64
            MAX-ACCESS   read-only
            STATUS      current
            DESCRIPTION
                "This object indicates the received 1024~1518-octet frames."
            ::= { hwEponOntEthernetPortStatisticEntry 9}

        hwEponOntEthernetPortStatisticRecvUndersizeFrames OBJECT-TYPE
            SYNTAX     Counter64
            MAX-ACCESS   read-only
            STATUS      current
            DESCRIPTION
                "This object indicates the received undersize frames."
            ::= { hwEponOntEthernetPortStatisticEntry 10}

        hwEponOntEthernetPortStatisticRecvTooLongFrames OBJECT-TYPE
            SYNTAX     Counter64
            MAX-ACCESS   read-only
            STATUS      current
            DESCRIPTION
                "This object indicates the received oversize frames."
            ::= { hwEponOntEthernetPortStatisticEntry 11}

        hwEponOntEthernetPortStatisticRecvFragments OBJECT-TYPE
            SYNTAX     Counter64
            MAX-ACCESS   read-only
            STATUS      current
            DESCRIPTION
                "This object indicates the received fragments."
            ::= { hwEponOntEthernetPortStatisticEntry 12}

        hwEponOntEthernetPortStatisticRecvJabberErrorFrames OBJECT-TYPE
            SYNTAX     Counter64
            MAX-ACCESS   read-only
            STATUS      current
            DESCRIPTION
                "This object indicates the received jabbers error frames."
            ::= { hwEponOntEthernetPortStatisticEntry 13}

        hwEponOntEthernetPortStatisticRecvFCSErrorFrames OBJECT-TYPE
            SYNTAX     Counter64
            MAX-ACCESS   read-only
            STATUS      current
            DESCRIPTION
                "This object indicates the received FCS error frames."
            ::= { hwEponOntEthernetPortStatisticEntry 14}

        hwEponOntEthernetPortStatisticRecvDropFrames OBJECT-TYPE
            SYNTAX     Counter64
            MAX-ACCESS   read-only
            STATUS      current
            DESCRIPTION
                "This object indicates the received discarded frames."
            ::= { hwEponOntEthernetPortStatisticEntry 15}

        hwEponOntEthernetPortStatisticRecvAlignmentErrorFrames  OBJECT-TYPE
            SYNTAX     Counter64
            MAX-ACCESS   read-only
            STATUS      current
            DESCRIPTION
                "This object indicates the received alignment error frames."
            ::= { hwEponOntEthernetPortStatisticEntry 16}

        hwEponOntEthernetPortStatisticInternalMACRecvErrorFrames OBJECT-TYPE
            SYNTAX     Counter64
            MAX-ACCESS   read-only
            STATUS      current
            DESCRIPTION
                "This object indicates the received error frames at the MAC sub-layer."
            ::= { hwEponOntEthernetPortStatisticEntry 17}

        hwEponOntEthernetPortStatisticRecvPPPoEFilteredFrames OBJECT-TYPE
            SYNTAX     Counter64
            MAX-ACCESS   read-only
            STATUS      current
            DESCRIPTION
                "This object indicates the received PPPoE filtered frames."
            ::= { hwEponOntEthernetPortStatisticEntry 18}

        hwEponOntEthernetPortStatisticRecvBufferOverflows OBJECT-TYPE
            SYNTAX     Counter64
            MAX-ACCESS   read-only
            STATUS      current
            DESCRIPTION
                "This object indicates the received buffer overflows."
            ::= { hwEponOntEthernetPortStatisticEntry 19}

        hwEponOntEthernetPortStatisticRecvOctets  OBJECT-TYPE
            SYNTAX     Counter64
            MAX-ACCESS   read-only
            STATUS      current
            DESCRIPTION
                "This object indicates the received octets."
            ::= { hwEponOntEthernetPortStatisticEntry 20}

        hwEponOntEthernetPortStatisticTransFrames OBJECT-TYPE
            SYNTAX     Counter64
            MAX-ACCESS   read-only
            STATUS      current
            DESCRIPTION
                "This object indicates the sent frames."
            ::= { hwEponOntEthernetPortStatisticEntry 21}

        hwEponOntEthernetPortStatisticTransDeferredFrames OBJECT-TYPE
            SYNTAX     Counter64
            MAX-ACCESS   read-only
            STATUS      current
            DESCRIPTION
                "This object indicates the sent deferred frames."
            ::= { hwEponOntEthernetPortStatisticEntry 22}

        hwEponOntEthernetPortStatisticTransMTUExceededDiscardFrames OBJECT-TYPE
            SYNTAX     Counter64
            MAX-ACCESS   read-only
            STATUS      current
            DESCRIPTION
                "This object indicates the sent MTU exceeded discard frames."
            ::= { hwEponOntEthernetPortStatisticEntry 23}

        hwEponOntEthernetPortStatisticTransCarrierSenseErrorFrames OBJECT-TYPE
            SYNTAX     Counter64
            MAX-ACCESS   read-only
            STATUS      current
            DESCRIPTION
                "This object indicates the sent carrier sense errors."
            ::= { hwEponOntEthernetPortStatisticEntry 24}

        hwEponOntEthernetPortStatisticTransSQETestErrorFrames OBJECT-TYPE
            SYNTAX     Counter64
            MAX-ACCESS   read-only
            STATUS      current
            DESCRIPTION
                "This object indicates the sent SQE test errors."
            ::= { hwEponOntEthernetPortStatisticEntry 25}

        hwEponOntEthernetPortStatisticTransSingleCollisionFrames OBJECT-TYPE
            SYNTAX     Counter64
            MAX-ACCESS   read-only
            STATUS      current
            DESCRIPTION
                "This object indicates the sent single collision frames."
            ::= { hwEponOntEthernetPortStatisticEntry 26}

        hwEponOntEthernetPortStatisticTransMultipleCollisionsFrames OBJECT-TYPE
            SYNTAX     Counter64
            MAX-ACCESS   read-only
            STATUS      current
            DESCRIPTION
                "This object indicates the sent multiple collision frames."
            ::= { hwEponOntEthernetPortStatisticEntry 27}

        hwEponOntEthernetPortStatisticTransExcessiveCollisionFrames OBJECT-TYPE
            SYNTAX     Counter64
            MAX-ACCESS   read-only
            STATUS      current
            DESCRIPTION
                "This object indicates the sent excessive collision frames."
            ::= { hwEponOntEthernetPortStatisticEntry 28}

        hwEponOntEthernetPortStatisticTransLateCollisionFrames OBJECT-TYPE
            SYNTAX     Counter64
            MAX-ACCESS   read-only
            STATUS      current
            DESCRIPTION
                "This object indicates the sent late collisions."
            ::= { hwEponOntEthernetPortStatisticEntry 29}

        hwEponOntEthernetPortStatisticInternalmacTransErrorFrames OBJECT-TYPE
            SYNTAX     Counter64
            MAX-ACCESS   read-only
            STATUS      current
            DESCRIPTION
                "This object indicates the sent error frames at the MAC sub-layer."
            ::= { hwEponOntEthernetPortStatisticEntry 30}

        hwEponOntEthernetPortStatisticTransBufferOverflows OBJECT-TYPE
            SYNTAX     Counter64
            MAX-ACCESS   read-only
            STATUS      current
            DESCRIPTION
                "This object indicates the sent buffer overflows."
            ::= { hwEponOntEthernetPortStatisticEntry 31}

        hwEponOntEthernetPortStatisticTransOctets OBJECT-TYPE
            SYNTAX     Counter64
            MAX-ACCESS   read-only
            STATUS      current
            DESCRIPTION
                "This object indicates the sent octets."
            ::= { hwEponOntEthernetPortStatisticEntry 32}

        hwEponOntEthernetPortStatisticStateChange OBJECT-TYPE
            SYNTAX     Integer32
            MAX-ACCESS   read-only
            STATUS      current
            DESCRIPTION
                "This object indicates the state changed times."
            ::= { hwEponOntEthernetPortStatisticEntry 33}
        hwEponOntEthernetPortStatisticTransUnicastFrames OBJECT-TYPE
            SYNTAX     Counter64
            MAX-ACCESS   read-only
            STATUS      current
            DESCRIPTION
                "This object indicates the sent unicast frames."
            ::= { hwEponOntEthernetPortStatisticEntry 34}

        hwEponOntEthernetPortStatisticTransBroadcastFrames OBJECT-TYPE
            SYNTAX     Counter64
            MAX-ACCESS   read-only
            STATUS      current
            DESCRIPTION
                "This object indicates the sent broadcast frames."
            ::= { hwEponOntEthernetPortStatisticEntry 35}

        hwEponOntEthernetPortStatisticTransMulticastFrames OBJECT-TYPE
            SYNTAX     Counter64
            MAX-ACCESS   read-only
            STATUS      current
            DESCRIPTION
                "This object indicates the sent multicast frames."
            ::= { hwEponOntEthernetPortStatisticEntry 36}

        hwEponOntEthernetPortStatisticRecv1519toOversizeOctetFrames OBJECT-TYPE
            SYNTAX     Counter64
            MAX-ACCESS   read-only
            STATUS      current
            DESCRIPTION
                "This object indicates the received 1519~oversize-octet frames."
            ::= { hwEponOntEthernetPortStatisticEntry 37}

        hwEponOntEthernetPortStatisticRecvUnicastFrames OBJECT-TYPE
            SYNTAX     Counter64
            MAX-ACCESS   read-only
            STATUS      current
            DESCRIPTION
                "This object indicates the received unicast frames."
            ::= { hwEponOntEthernetPortStatisticEntry 38}

        hwEponOntEthernetPortStatisticTrans64OctetFrames OBJECT-TYPE
            SYNTAX     Counter64
            MAX-ACCESS   read-only
            STATUS      current
            DESCRIPTION
                "This object indicates the sent 64-octet frames."
            ::= { hwEponOntEthernetPortStatisticEntry 39}

        hwEponOntEthernetPortStatisticTrans65to127OctetFrames OBJECT-TYPE
            SYNTAX     Counter64
            MAX-ACCESS   read-only
            STATUS      current
            DESCRIPTION
                "This object indicates the sent 65~127-octet frames."
            ::= { hwEponOntEthernetPortStatisticEntry 40}

        hwEponOntEthernetPortStatisticTrans128to255OctetFrames OBJECT-TYPE
            SYNTAX     Counter64
            MAX-ACCESS   read-only
            STATUS      current
            DESCRIPTION
                "This object indicates the sent 128~255-octet frames."
            ::= { hwEponOntEthernetPortStatisticEntry 41}

        hwEponOntEthernetPortStatisticTrans256to511OctetFrames OBJECT-TYPE
            SYNTAX     Counter64
            MAX-ACCESS   read-only
            STATUS      current
            DESCRIPTION
                "This object indicates the sent 256~511-octet frames."
            ::= { hwEponOntEthernetPortStatisticEntry 42}

        hwEponOntEthernetPortStatisticTrans512to1023OctetFrames OBJECT-TYPE
            SYNTAX     Counter64
            MAX-ACCESS   read-only
            STATUS      current
            DESCRIPTION
                "This object indicates the sent 512~1023-octet frames."
            ::= { hwEponOntEthernetPortStatisticEntry 43}

        hwEponOntEthernetPortStatisticTrans1024to1518OctetFrames OBJECT-TYPE
            SYNTAX     Counter64
            MAX-ACCESS   read-only
            STATUS      current
            DESCRIPTION
                "This object indicates the sent 1024~1518-octet frames."
            ::= { hwEponOntEthernetPortStatisticEntry 44}

        hwEponOntEthernetPortStatisticTransOver1518OctetFrames OBJECT-TYPE
            SYNTAX     Counter64
            MAX-ACCESS   read-only
            STATUS      current
            DESCRIPTION
                "This object indicates the sent over 1518-octet frames."
            ::= { hwEponOntEthernetPortStatisticEntry 45}
        hwEponOntEthernetPortStatisticClear OBJECT-TYPE
            SYNTAX     INTEGER{
                clear(1),
                invalid(-1)
            }
            MAX-ACCESS   read-write
            STATUS      current
            DESCRIPTION
                "This object is used to clear the statistics.
                 Options:
                 1. clear(1)                    - Indicates that clear the statistics
                 2. invalid(-1)                 - Indicates that the query fails or no information is detected
                "
            ::= { hwEponOntEthernetPortStatisticEntry 50}

        hwEponOntEthernetPortStatisticRecvErrorFrames OBJECT-TYPE
            SYNTAX     Counter64
            MAX-ACCESS   read-only
            STATUS      current
            DESCRIPTION
                "This object indicates the received error frames."
            ::= { hwEponOntEthernetPortStatisticEntry 51}

        hwEponOntEthernetPortStatisticRecvCrcErrorFrames OBJECT-TYPE
            SYNTAX     Counter64
            MAX-ACCESS   read-only
            STATUS      current
            DESCRIPTION
                "This object indicates the received CRC error frames."
            ::= { hwEponOntEthernetPortStatisticEntry 52}

        hwEponOntEthernetPortStatisticRecvDropEvents OBJECT-TYPE
            SYNTAX     Counter64
            MAX-ACCESS   read-only
            STATUS      current
            DESCRIPTION
                "This object indicates the received drop events."
            ::= { hwEponOntEthernetPortStatisticEntry 53}

        hwEponOntEthernetPortStatisticTransDropEvents OBJECT-TYPE
            SYNTAX     Counter64
            MAX-ACCESS   read-only
            STATUS      current
            DESCRIPTION
                "This object indicates the sent drop events."
            ::= { hwEponOntEthernetPortStatisticEntry 54}

        hwEponOntEthernetPortStatisticTransDiscardFrames OBJECT-TYPE
            SYNTAX     Counter64
            MAX-ACCESS   read-only
            STATUS      current
            DESCRIPTION
                "This object indicates the sent discarded frames."
            ::= { hwEponOntEthernetPortStatisticEntry 55}

        hwEponOntEthernetPortStatisticTransErrorFrames OBJECT-TYPE
            SYNTAX     Counter64
            MAX-ACCESS   read-only
            STATUS      current
            DESCRIPTION
                "This object indicates the sent error frames."
            ::= { hwEponOntEthernetPortStatisticEntry 56}

        hwEponOntEthernetPortStatisticTransCrcErrorFrames OBJECT-TYPE
            SYNTAX     Counter64
            MAX-ACCESS   read-only
            STATUS      current
            DESCRIPTION
                "This object indicates the sent CRC error frames."
            ::= { hwEponOntEthernetPortStatisticEntry 57}

        hwEponOntEthernetPortStatisticTransUndersizeFrames OBJECT-TYPE
            SYNTAX     Counter64
            MAX-ACCESS   read-only
            STATUS      current
            DESCRIPTION
                "This object indicates the sent undersize frames."
            ::= { hwEponOntEthernetPortStatisticEntry 58}

        hwEponOntEthernetPortStatisticTransOversizeFrames OBJECT-TYPE
            SYNTAX     Counter64
            MAX-ACCESS   read-only
            STATUS      current
            DESCRIPTION
                "This object indicates the sent oversize frames."
            ::= { hwEponOntEthernetPortStatisticEntry 59}

        hwEponOntEthernetPortStatisticTransFragments OBJECT-TYPE
            SYNTAX     Counter64
            MAX-ACCESS   read-only
            STATUS      current
            DESCRIPTION
                "This object indicates the sent fragments."
            ::= { hwEponOntEthernetPortStatisticEntry 60}

        hwEponOntEthernetPortStatisticTransJabbers OBJECT-TYPE
            SYNTAX     Counter64
            MAX-ACCESS   read-only
            STATUS      current
            DESCRIPTION
                "This object indicates the sent jabbers."
            ::= { hwEponOntEthernetPortStatisticEntry 61}

--Table: hwEponOntCPUStatisticTable
        hwEponOntCPUStatisticTable OBJECT-TYPE
            SYNTAX     SEQUENCE OF HwEponOntCPUStatisticEntry
            MAX-ACCESS not-accessible
            STATUS     current
            DESCRIPTION
                "The ONT CPU statistics table.
                 The index of this table is a combination of ifIndex, and hwEponDeviceOntIndex.
                "
            ::= { hwXponDeviceStatisticObjects 44 }

        hwEponOntCPUStatisticEntry OBJECT-TYPE
            SYNTAX     HwEponOntCPUStatisticEntry
            MAX-ACCESS not-accessible
            STATUS     current
            DESCRIPTION
                "The ONT CPU statistics table.
                 The index of this entry is a combination of ifIndex, and hwEponDeviceOntIndex.
                "
            INDEX       { ifIndex, hwEponDeviceOntIndex}
            ::= { hwEponOntCPUStatisticTable 1 }

        HwEponOntCPUStatisticEntry ::=
            SEQUENCE {
                hwEponOntCPUStatisticIGMP            Counter64,
                hwEponOntCPUStatisticARP             Counter64,
                hwEponOntCPUStatisticDHCP            Counter64,
                hwEponOntCPUStatisticPPPOE           Counter64,
                hwEponOntCPUStatisticVOIP            Counter64,
                hwEponOntCPUStatisticDBPU            Counter64,
                hwEponOntCPUStatisticOTHER           Counter64,
                hwEponOntCPUStatisticClear           INTEGER
            }

        hwEponOntCPUStatisticIGMP  OBJECT-TYPE
            SYNTAX     Counter64
            MAX-ACCESS   read-only
            STATUS      current
            DESCRIPTION
                "This object indicates the IGMP frames transmitted through the CPU."
            ::= { hwEponOntCPUStatisticEntry 1 }

        hwEponOntCPUStatisticARP  OBJECT-TYPE
            SYNTAX     Counter64
            MAX-ACCESS   read-only
            STATUS      current
            DESCRIPTION
                "This object indicates the ARP frames transmitted through the CPU."
            ::= { hwEponOntCPUStatisticEntry 2 }

        hwEponOntCPUStatisticDHCP  OBJECT-TYPE
            SYNTAX     Counter64
            MAX-ACCESS   read-only
            STATUS      current
            DESCRIPTION
                "This object indicates the DHCP frames transmitted through the CPU."
            ::= { hwEponOntCPUStatisticEntry 3 }

        hwEponOntCPUStatisticPPPOE  OBJECT-TYPE
            SYNTAX     Counter64
            MAX-ACCESS   read-only
            STATUS      current
            DESCRIPTION
                "This object indicates the PPPOE frames transmitted through the CPU."
            ::= { hwEponOntCPUStatisticEntry 4 }

        hwEponOntCPUStatisticVOIP  OBJECT-TYPE
            SYNTAX     Counter64
            MAX-ACCESS   read-only
            STATUS      current
            DESCRIPTION
                "This object indicates the VOIP frames transmitted through the CPU."
            ::= { hwEponOntCPUStatisticEntry 5 }

        hwEponOntCPUStatisticDBPU  OBJECT-TYPE
            SYNTAX     Counter64
            MAX-ACCESS   read-only
            STATUS      current
            DESCRIPTION
                "This object indicates the BPDU frames transmitted through the CPU."
            ::= { hwEponOntCPUStatisticEntry 6 }

        hwEponOntCPUStatisticOTHER  OBJECT-TYPE
            SYNTAX     Counter64
            MAX-ACCESS   read-only
            STATUS      current
            DESCRIPTION
                "This object indicates the other frames transmitted through the CPU."
            ::= { hwEponOntCPUStatisticEntry 7 }

        hwEponOntCPUStatisticClear  OBJECT-TYPE
            SYNTAX     INTEGER{
                clear(1),
                invalid(-1)
            }
            MAX-ACCESS   read-write
            STATUS      current
            DESCRIPTION
                "This object is used to clear the statistics.
                 Options:
                 1. clear(1)                    - Indicates that clear the statistics
                 2. invalid(-1)                 - Indicates that the query fails or no information is detected
                "
            ::= { hwEponOntCPUStatisticEntry 20 }
-- hwXponDeviceStatisticObjects  end


-- Table hwGponDeviceOntSnmpStaticRouteConfigTable
        hwGponDeviceOntSnmpStaticRouteConfigTable OBJECT-TYPE
            SYNTAX     SEQUENCE OF HwGponDeviceOntSnmpStaticRouteConfigEntry
            MAX-ACCESS not-accessible
            STATUS     current
            DESCRIPTION
                "This is the ONT SNMP static route configuration table.
                 This table is used to configure and query the SNMP route configuration of an ONT.
                 The index of this table is a combination of ifIndex,
                 hwXponDeviceOntIndex and hwGponOntObjectSnmpStaticRouteIndex.
                "
            ::= { hwXponDeviceControlObjects 100 }

        hwGponDeviceOntSnmpStaticRouteConfigEntry OBJECT-TYPE
            SYNTAX     HwGponDeviceOntSnmpStaticRouteConfigEntry
            MAX-ACCESS not-accessible
            STATUS     current
            DESCRIPTION
                "This is the ONT SNMP static route configuration table.
                 This table is used to configure and query the SNMP route configuration of an ONT.
                 The index of this entry is a combination of ifIndex,
                 hwXponDeviceOntIndex and hwGponOntObjectSnmpStaticRouteIndex.
                "
            INDEX       { ifIndex, hwXponDeviceOntIndex, hwGponOntObjectSnmpStaticRouteIndex }
            ::= { hwGponDeviceOntSnmpStaticRouteConfigTable 1 }

        HwGponDeviceOntSnmpStaticRouteConfigEntry ::=
            SEQUENCE {
                hwGponOntObjectSnmpStaticRouteIndex                  Integer32,
                hwGponOntObjectSnmpStaticRouteIpAddress              IpAddress,
                hwGponOntObjectSnmpStaticRouteNetMask                IpAddress,
                hwGponOntObjectSnmpStaticRouteNextHop                IpAddress,
                hwGponOntObjectSnmpStaticRouteRowStatus              RowStatus,
                hwGponOntObjectSnmpStaticRouteOutputPort             Integer32
            }

        hwGponOntObjectSnmpStaticRouteIndex  OBJECT-TYPE
            SYNTAX     Integer32
            MAX-ACCESS   not-accessible
            STATUS      current
            DESCRIPTION
                "This object indicates the ONT SNMP static route table index."
            ::= { hwGponDeviceOntSnmpStaticRouteConfigEntry 1 }

        hwGponOntObjectSnmpStaticRouteIpAddress  OBJECT-TYPE
            SYNTAX     IpAddress
            MAX-ACCESS   read-write
            STATUS      current
            DESCRIPTION
                "This object indicates the IP address."
            ::= { hwGponDeviceOntSnmpStaticRouteConfigEntry 2 }

        hwGponOntObjectSnmpStaticRouteNetMask  OBJECT-TYPE
            SYNTAX     IpAddress
            MAX-ACCESS   read-write
            STATUS      current
            DESCRIPTION
                "This object indicates the subnet mask of the IP address."
            ::= { hwGponDeviceOntSnmpStaticRouteConfigEntry 3 }

        hwGponOntObjectSnmpStaticRouteNextHop  OBJECT-TYPE
            SYNTAX     IpAddress
            MAX-ACCESS   read-write
            STATUS      current
            DESCRIPTION
                "This object indicates the next hop IP address."
            ::= { hwGponDeviceOntSnmpStaticRouteConfigEntry 4 }

        hwGponOntObjectSnmpStaticRouteRowStatus OBJECT-TYPE
            SYNTAX       RowStatus
            MAX-ACCESS   read-create
            STATUS      current
            DESCRIPTION
                "The hwGponOntObjectSnmpStaticRouteRowStatus is used to create a new row
                 or to modify or delete an existing row in this table.
                 Options:
                 1. createAndGo(4) -create a new instance of a conceptual row
                 2. destroy(6)     -delete the instances associated with an existing conceptual row
                "
            ::= { hwGponDeviceOntSnmpStaticRouteConfigEntry 5 }

        hwGponOntObjectSnmpStaticRouteOutputPort OBJECT-TYPE
            SYNTAX       Integer32(-1 | 0..254)
            MAX-ACCESS   read-write
            STATUS      current
            DESCRIPTION
                "This object indicates the output portid.
                "
            ::= { hwGponDeviceOntSnmpStaticRouteConfigEntry 6 }

-- Table hwGponDeviceOntRegisterExInfoTable
        hwGponDeviceOntRegisterExInfoTable OBJECT-TYPE
            SYNTAX     SEQUENCE OF HwGponDeviceOntRegisterExInfoEntry
            MAX-ACCESS not-accessible
            STATUS     current
            DESCRIPTION
                "This table is used to save the ont's register info, less than 10 times.
                 The index of this table is a combination of ifIndex,
                 hwGponDeviceOntIndex and hwGponDeviceOntRegisterInfoIndex.
                "
            ::= { hwXponDeviceControlObjects 101 }

        hwGponDeviceOntRegisterExInfoEntry OBJECT-TYPE
            SYNTAX     HwGponDeviceOntRegisterExInfoEntry
            MAX-ACCESS not-accessible
            STATUS     current
            DESCRIPTION
                "This table is used to save the ont's register info, less than 10 times.
                 The index of this entry is a combination of ifIndex,
                 hwGponDeviceOntIndex and hwGponDeviceOntRegisterInfoIndex.
                "
            INDEX       { ifIndex, hwGponDeviceOntIndex, hwGponDeviceOntRegisterInfoIndex }
            ::= { hwGponDeviceOntRegisterExInfoTable 1 }

        HwGponDeviceOntRegisterExInfoEntry ::=
            SEQUENCE {
                hwGponDeviceOntRegisterInfoIndex                     Integer32,
                hwGponDeviceOntRegisterInfoAuthMethod                Integer32,
                hwGponDeviceOntRegisterInfoSN                        OCTET STRING,
                hwGponDeviceOntRegisterInfoPassword                  OCTET STRING,
                hwGponDeviceOntRegisterInfoType                      OCTET STRING,
                hwGponDeviceOntRegisterInfoUpTime                    OCTET STRING,
                hwGponDeviceOntRegisterInfoDownTime                  OCTET STRING,
                hwGponDeviceOntRegisterInfoDownCause                 INTEGER,
                hwGponDeviceOntRegisterInfoLoid                      OCTET STRING,
                hwGponDeviceOntRegisterInfoCheckcode                 OCTET STRING
            }

        hwGponDeviceOntRegisterInfoIndex  OBJECT-TYPE
            SYNTAX      Integer32
            MAX-ACCESS  read-only
            STATUS      current
            DESCRIPTION
                "This object indicates the ONT register information index."
            ::= { hwGponDeviceOntRegisterExInfoEntry 1 }

        hwGponDeviceOntRegisterInfoAuthMethod  OBJECT-TYPE
            SYNTAX      Integer32
            MAX-ACCESS  read-only
            STATUS      current
            DESCRIPTION
                "This object indicates the authentication mode for the ONT.
                 The value (1) indicates that the mode is SN or MAC.
                 The value (2) indicates that the mode is the combination of SN and PASSWORD or combination of MAC and PASSWORD.
                 The value (3) indicates that the mode is PASSWORD and the type is always on.
                 The value (4) indicates that the mode is PASSWORD and the type is once on.
                 The value (5) indicates that the mode is LOID and the type is always on.
                 The value (6) indicates that the mode is LOID and the type is once on.
                 The value (7) indicates that the mode is the combination of LOID and CHECKCODE ,and the type is always on.
                 The value (8) indicates that the mode is the combination of LOID and CHECKCODE ,and the type is once on.
                 The value (-1) indicates that the query fails or no information is detected."
            ::= { hwGponDeviceOntRegisterExInfoEntry 2 }

        hwGponDeviceOntRegisterInfoSN  OBJECT-TYPE
            SYNTAX      OCTET STRING (SIZE (16))
            MAX-ACCESS  read-only
            STATUS      current
            DESCRIPTION
                "This object indicates the ONT serial number."
            ::= { hwGponDeviceOntRegisterExInfoEntry 3 }

        hwGponDeviceOntRegisterInfoPassword  OBJECT-TYPE
            SYNTAX      OCTET STRING
            MAX-ACCESS  read-only
            STATUS      current
            DESCRIPTION
                "This object indicates the ONT password
                 GPON password size (0..10)
                 XG-PON password size (0..36)
                "
            ::= { hwGponDeviceOntRegisterExInfoEntry 4 }

        hwGponDeviceOntRegisterInfoType OBJECT-TYPE
            SYNTAX       OCTET STRING (SIZE (0..20))
            MAX-ACCESS   read-only
            STATUS       current
            DESCRIPTION
                "This object indicates the ONT type"
            ::= { hwGponDeviceOntRegisterExInfoEntry 5 }

        hwGponDeviceOntRegisterInfoUpTime  OBJECT-TYPE
            SYNTAX      OCTET STRING (SIZE (0..30))
            MAX-ACCESS  read-only
            STATUS      current
            DESCRIPTION
                "This object indicates the time when the ONT went online."
            ::= { hwGponDeviceOntRegisterExInfoEntry 6 }

        hwGponDeviceOntRegisterInfoDownTime  OBJECT-TYPE
            SYNTAX      OCTET STRING (SIZE (0..30))
            MAX-ACCESS  read-only
            STATUS      current
            DESCRIPTION
                "This object indicates the time when the ONT went offline."
            ::= { hwGponDeviceOntRegisterExInfoEntry 7 }

        hwGponDeviceOntRegisterInfoDownCause  OBJECT-TYPE
            SYNTAX INTEGER{
                ontdeleted(0),
                linkeddown(1),
                losi(2),
                lofi(3),
                sfi(4),
                loai(5),
                loami(6),
                disablefail(7),
                deactivated(8),
                reset(9),
                reregister(10),
                popupfail(11),
                authfail(12),
                powerdown(13),
                reserved(14),
                loki(15),
                ringDeactivated(18),
	        turnOffOptic(30),
                cmdReboot(31),
                ontResetkeyReboot(32),
                ontSoftwareReset(33),
                broadcastAttackDeactivated(34),
                operatorCheckFail(35),
		ontOltIncompatible(36),
                rogueOntselfDetected(37),
                autoIsolateReset(38),
                autoIsolateDeact(39),
		ontNotInWhiteList(40),
                noerror(255),
                invalid(-1)
            }
            MAX-ACCESS  read-only
            STATUS      current
            DESCRIPTION
                "This object indicates the reason why the ONT went offline.
                 Options:
                 1. ontdeleted(0)                     - The cause of ONT's down is that the ont is deleted
                 2. linkeddown(1)                     - The cause of ONT's down is that the ont is disconnected
                 3. losi(2)                           - The cause of ONT's down is LOSi(Loss of signal for ONUi) or LOBi (Loss of burst for ONUi)
                 4. lofi(3)                           - The cause of ONT's down is that the ont is lofi(OLT can not receive
                                                        expected optical frame from ONT)
                 5. sfi(4)                            - The cause of ONT's down is that the ont is sfi(Signal fail of ONUi)
                 6. loai(5)                           - The cause of ONT's down is that the ont is loai(Loss of acknowledge with ONUi)
                 7. loami(6)                          - The cause of ONT's down is that the ont is loami(Loss of PLOAM for ONUi)
                 8. disablefail(7)                    - The cause of ONT's down is that the ont fails to be deactivated
                 9. deactivated(8)                    - The cause of ONT's down is that the ont is deactivated
                 10. reset(9)                         - The cause of ONT's down is that the ont is reseted
                 11. reregister(10)                   - The cause of ONT's down is that the ont is registered again
                 12. popupfail(11)                    - The cause of ONT's down is that the ont popup test fails
                 13. authfail(12)                     - The cause of ONT's down is that the ont authentication fails
                 14. powerdown(13)                    - The cause of ONT's down is that the ont is powered off
                 15. reserved(14)                     - Reserved
                 16. loki(15)                         - The cause of ONT's down is that the ont is loki(Loss of key synch with ONUi)
                 17. ringDeactivated(18)              - The cause of ONT's down is that the ont is deactivated due to the ring
		 18. turnOffOptic(30)                 - The cause of ONT's down is that the ont optical module is shut down
                 19. cmdReboot(31)                    - The cause of ONT's down is that the ont is reset by ont command
                 20. ontResetkeyReboot(32)            - The cause of ONT's down is that the ont is reset by ont reset button
                 21. ontSoftwareReset(33)             - The cause of ONT's down is that the ont is reset by ont software
                 22. broadcastAttackDeactivated(34)   - The cause of ONT's down is that the ont is deactivated due to broadcast attack
                 23. operatorCheckFail(35)            - The cause of ONT's down is that operator check fail
                 24. ontOltIncompatible(36)           - The cause of ONT's down is that the ont is incompatible with the OLT
                 25. rogueOntselfDetected(37)         - The cause of ONT's down is that the rogue ont detected by itself
		 26. autoIsolateReset(38)             - The cause of ONT's down is that the ont resets to prevent rogue ont attacks
                 27. autoIsolateDeact(39)             - The cause of ONT's down is that the ont is deactivated to prevent rogue ont attacks
		 28. ontNotInWhiteList(40)	      - The cause of ONT's down is that the ont is not in the white list
		 29. noerror(255)                     - The cause of ONT's down is that the ont is noerror
                 30. invalid(-1)                      - Indicates that the query fails or no information is detected
                 "
            ::= { hwGponDeviceOntRegisterExInfoEntry 8 }

        hwGponDeviceOntRegisterInfoLoid  OBJECT-TYPE
            SYNTAX   OCTET STRING (SIZE (0..24))
            MAX-ACCESS  read-only
            STATUS   current
            DESCRIPTION
                "This object indicates the ONT LOID."
            ::= { hwGponDeviceOntRegisterExInfoEntry 9 }

        hwGponDeviceOntRegisterInfoCheckcode  OBJECT-TYPE
            SYNTAX   OCTET STRING (SIZE (0..12))
            MAX-ACCESS  read-only
            STATUS   current
            DESCRIPTION
                "This object indicates the ONT CHECKCODE."
            ::= { hwGponDeviceOntRegisterExInfoEntry 10 }

-- Table hwEponDeviceOntSnmpStaticRouteTable
        hwEponDeviceOntSnmpStaticRouteTable OBJECT-TYPE
            SYNTAX     SEQUENCE OF HwEponDeviceOntSnmpStaticRouteEntry
            MAX-ACCESS not-accessible
            STATUS     current
            DESCRIPTION
                "This is the ONT SNMP static route configuration table.
                 This table is used to configure and query the SNMP route configuration of an ONT.
                 The index of this table is a combination of ifIndex,
                 hwXponDeviceOntIndex and hwEponOntSnmpStaticRouteIndex.
                "
            ::= { hwXponDeviceControlObjects 102 }

        hwEponDeviceOntSnmpStaticRouteEntry OBJECT-TYPE
            SYNTAX     HwEponDeviceOntSnmpStaticRouteEntry
            MAX-ACCESS not-accessible
            STATUS     current
            DESCRIPTION
                "This is the ONT SNMP static route configuration table.
                 This table is used to configure and query the SNMP route configuration of an ONT.
                 The index of this entry is a combination of ifIndex,
                 hwXponDeviceOntIndex and hwEponOntSnmpStaticRouteIndex.
                "
            INDEX       { ifIndex, hwXponDeviceOntIndex, hwEponOntSnmpStaticRouteIndex }
            ::= { hwEponDeviceOntSnmpStaticRouteTable 1 }

        HwEponDeviceOntSnmpStaticRouteEntry ::=
            SEQUENCE {
                hwEponOntSnmpStaticRouteIndex                        Integer32,
                hwEponOntSnmpStaticRouteIpAddress                    IpAddress,
                hwEponOntSnmpStaticRouteNetMask                      IpAddress,
                hwEponOntSnmpStaticRouteNextHop                      IpAddress,
                hwEponOntSnmpStaticRouteRowStatus                    RowStatus
            }

       hwEponOntSnmpStaticRouteIndex  OBJECT-TYPE
           SYNTAX       Integer32
           MAX-ACCESS   not-accessible
           STATUS       current
           DESCRIPTION
                "This object indicates the ONT SNMP static route table index."
           ::= { hwEponDeviceOntSnmpStaticRouteEntry 1 }

        hwEponOntSnmpStaticRouteIpAddress  OBJECT-TYPE
           SYNTAX     IpAddress
           MAX-ACCESS   read-write
           STATUS      current
           DESCRIPTION
                "This object indicates the IP address."
           ::= { hwEponDeviceOntSnmpStaticRouteEntry 2 }

        hwEponOntSnmpStaticRouteNetMask  OBJECT-TYPE
           SYNTAX     IpAddress
           MAX-ACCESS   read-write
           STATUS      current
           DESCRIPTION
                "This object indicates the subnet mask of the IP address."
           ::= { hwEponDeviceOntSnmpStaticRouteEntry 3 }

        hwEponOntSnmpStaticRouteNextHop  OBJECT-TYPE
           SYNTAX     IpAddress
           MAX-ACCESS   read-write
           STATUS      current
           DESCRIPTION
                "This object indicates the next hop IP address."
           ::= { hwEponDeviceOntSnmpStaticRouteEntry 4 }

        hwEponOntSnmpStaticRouteRowStatus OBJECT-TYPE
           SYNTAX       RowStatus
           MAX-ACCESS   read-create
           STATUS      current
           DESCRIPTION
                "The hwEponOntSnmpStaticRouteRowStatus is used to create a new row
                 or to modify or delete an existing row in this table.
                 Options:
                 1. createAndGo(4) -create a new instance of a conceptual row
                 2. destroy(6)     -delete the instances associated with an existing conceptual row
                "
           ::= { hwEponDeviceOntSnmpStaticRouteEntry 5 }

-- Table hwEponDeviceOntRegisterExInfoTable
        hwEponDeviceOntRegisterExInfoTable OBJECT-TYPE
            SYNTAX     SEQUENCE OF HwEponDeviceOntRegisterExInfoEntry
            MAX-ACCESS not-accessible
            STATUS     current
            DESCRIPTION
                "This table is used to save the ONT's register info, less than 10 times.
                 The index of this table is a combination of ifIndex,
                 hwXponDeviceOntIndex and hwEponDeviceOntRegisterInfoIndex.
                "
            ::= { hwXponDeviceControlObjects 103 }

        hwEponDeviceOntRegisterExInfoEntry OBJECT-TYPE
            SYNTAX     HwEponDeviceOntRegisterExInfoEntry
            MAX-ACCESS not-accessible
            STATUS     current
            DESCRIPTION
                "This table is used to save the ONT's register info, less than 10 times.
                 The index of this entry is a combination of ifIndex,
                 hwXponDeviceOntIndex and hwEponDeviceOntRegisterInfoIndex.
                "
            INDEX       { ifIndex, hwXponDeviceOntIndex, hwEponDeviceOntRegisterInfoIndex }
            ::= { hwEponDeviceOntRegisterExInfoTable 1 }

        HwEponDeviceOntRegisterExInfoEntry ::=
            SEQUENCE {
                hwEponDeviceOntRegisterInfoIndex                     Integer32,
                hwEponDeviceOntRegisterInfoAuthMethod                INTEGER,
                hwEponDeviceOntRegisterInfoMac                       OCTET STRING,
                hwEponDeviceOntRegisterInfoPassword                  OCTET STRING,
                hwEponDeviceOntRegisterInfoType                      OCTET STRING,
                hwEponDeviceOntRegisterInfoUpTime                    OCTET STRING,
                hwEponDeviceOntRegisterInfoDownTime                  OCTET STRING,
                hwEponDeviceOntRegisterInfoDownCause                 INTEGER,
                hwEponDeviceOntRegisterInfoLoid                      OCTET STRING,
                hwEponDeviceOntRegisterInfoCheckcode                 OCTET STRING
            }

        hwEponDeviceOntRegisterInfoIndex  OBJECT-TYPE
            SYNTAX      Integer32
            MAX-ACCESS  read-only
            STATUS      current
            DESCRIPTION
                "This object indicates the ONT register information index."
            ::= { hwEponDeviceOntRegisterExInfoEntry 1 }

        hwEponDeviceOntRegisterInfoAuthMethod  OBJECT-TYPE
            SYNTAX      INTEGER {
                mac(1),
                macpassword(2),
                alwayson(3),
                onceon(4),
                lOIDonceon(5),
                lOIDalwayson(6),
                lOIDCheckCodeOnceon(7),
                lOIDCheckCodeAlwayson(8),
                invalid(-1)
            }
            MAX-ACCESS  read-only
            STATUS      current
            DESCRIPTION
                "This object indicates the authentication mode for the ONT.
                 Options:
                 1. mac(1)                      - The authentication mode is MAC
                 2. macpassword(2)              - The authentication mode is MAC and password
                 3. alwayson(3)                 - The authentication mode is always on
                 4. onceon(4)                   - The authentication mode is once on
                 5. lOIDonceon(5)               - The authentication mode is LOID and once on
                 6. lOIDalwayson(6)             - The authentication mode is LOID and always on
                 7. lOIDCheckCodeOnceon(7)      - The authentication mode is LOID, checkcode and once on
                 8. lOIDCheckCodeAlwayson(8)    - The authentication mode is LOID, checkcode and once always on
                 9. invalid(-1)                 - Indicates that the query fails or no information is detected
                "
            ::= { hwEponDeviceOntRegisterExInfoEntry 2 }

        hwEponDeviceOntRegisterInfoMac  OBJECT-TYPE
            SYNTAX      OCTET STRING (SIZE (16))
            MAX-ACCESS  read-only
            STATUS      current
            DESCRIPTION
                "This object indicates the ONT MAC address."
            ::= { hwEponDeviceOntRegisterExInfoEntry 3 }

        hwEponDeviceOntRegisterInfoPassword  OBJECT-TYPE
            SYNTAX      OCTET STRING (SIZE (0..32))
            MAX-ACCESS  read-only
            STATUS      current
            DESCRIPTION
                "This object indicates the ONT password."
            ::= { hwEponDeviceOntRegisterExInfoEntry 4 }

        hwEponDeviceOntRegisterInfoType OBJECT-TYPE
            SYNTAX       OCTET STRING (SIZE (0..20))
            MAX-ACCESS   read-only
            STATUS       current
            DESCRIPTION
                "This object indicates the ONT type."
            ::= { hwEponDeviceOntRegisterExInfoEntry 5 }

        hwEponDeviceOntRegisterInfoUpTime  OBJECT-TYPE
            SYNTAX      OCTET STRING (SIZE (0..30))
            MAX-ACCESS  read-only
            STATUS      current
            DESCRIPTION
                "This object indicates the time when the ONT goes online."
            ::= { hwEponDeviceOntRegisterExInfoEntry 6 }

        hwEponDeviceOntRegisterInfoDownTime  OBJECT-TYPE
            SYNTAX      OCTET STRING (SIZE (0..30))
            MAX-ACCESS  read-only
            STATUS      current
            DESCRIPTION
                "This object indicates the time when the ONT goes offline."
            ::= { hwEponDeviceOntRegisterExInfoEntry 7 }

        hwEponDeviceOntRegisterInfoDownCause  OBJECT-TYPE
            SYNTAX INTEGER{
                ontdeleted(0),
                linkeddown(1),
                losi(2),
                lofi(3),
                sfi(4),
                loai(5),
                loami(6),
                disablefail(7),
                deactivated(8),
                reset(9),
                reregister(10),
                popupfail(11),
                authfail(12),
                powerdown(13),
                reserved(14),
                loki(15),
                ringDeactivated(18),
                broadcastAttackDeactivated(34),
                noerror(255),
                invalid(-1),
                rogueOntselfDetected(37),
                antirogueontautoisolatereset(38),
                antirogueontautoisolatedeactive(39)
            }
            MAX-ACCESS  read-only
            STATUS      current
            DESCRIPTION
                "This object indicates the reason why the ONT goes offline.
                 Options:
                 1. ontdeleted(0)                     - The cause of ONT's down is that the ont is deleted
                 2. linkeddown(1)                     - The cause of ONT's down is that the ont is disconnected
                 3. losi(2)                           - The cause of ONT's down is that the ont is losi(OLT can not receive
                                                        expected optical signals from ONT)
                 4. lofi(3)                           - The cause of ONT's down is that the ont is lofi(OLT can not receive
                                                        expected optical frame from ONT)
                 5. sfi(4)                            - The cause of ONT's down is that the ont is sfi(Signal fail of ONUi)
                 6. loai(5)                           - The cause of ONT's down is that the ont is loai(Loss of acknowledge with ONUi)
                 7. loami(6)                          - The cause of ONT's down is that the ont is loami(Loss of PLOAM for ONUi)
                 8. disablefail(7)                    - The cause of ONT's down is that the ont fails to be deactivated
                 9. deactivated(8)                    - The cause of ONT's down is that the ont is deactivated
                 10. reset(9)                         - The cause of ONT's down is that the ont is reseted
                 11. reregister(10)                   - The cause of ONT's down is that the ont is registered again
                 12. popupfail(11)                    - The cause of ONT's down is that the ont popup test fails
                 13. authfail(12)                     - The cause of ONT's down is that the ont authentication fails
                 14. powerdown(13)                    - The cause of ONT's down is that the ont is powered off
                 15. reserved(14)                     - Reserved
                 16. loki(15)                         - The cause of ONT's down is that the ont is loki(Loss of key synch with ONUi)
                 17. ringDeactivated(18)              - The cause of ONT's down is that the ont is deactivated due to the ring
                 18. broadcastAttackDeactivated(34)   - The cause of ONT's down is that the ont is deactivated due to broadcast attack
                 19. noerror(255)                     - The cause of ONT's down is that the ont is noerror
                 20. invalid(-1)                      - Indicates that the query fails or no information is detected
                 21. rogueOntselfDetected(37)         - The cause of ONT's down is that the rogue ont detected by itself
                 22. antirogueontautoisolatereset(38) - The cause of ONT's down is to prevent rogue ONT attacks by reset ONT
                 23. antirogueontautoisolatedeactive(39) - The cause of ONT's down is to prevent rogue ONT attacks by deactive ONT
                 "
            ::= { hwEponDeviceOntRegisterExInfoEntry 8 }

        hwEponDeviceOntRegisterInfoLoid  OBJECT-TYPE
            SYNTAX      OCTET STRING (SIZE (0..24))
            MAX-ACCESS  read-only
            STATUS      current
            DESCRIPTION
                "This object indicates the ONT LOID."
            ::= { hwEponDeviceOntRegisterExInfoEntry 9 }

        hwEponDeviceOntRegisterInfoCheckcode  OBJECT-TYPE
            SYNTAX      OCTET STRING (SIZE (0..12))
            MAX-ACCESS  read-only
            STATUS      current
            DESCRIPTION
                "This object indicates the ONT CHECKCODE"
            ::= { hwEponDeviceOntRegisterExInfoEntry 10 }

  -- Table hwEponDeviceOntOpticsDdmInfoTable
        hwEponDeviceOntOpticsDdmInfoTable OBJECT-TYPE
            SYNTAX     SEQUENCE OF HwEponDeviceOntOpticsDdmInfoEntry
            MAX-ACCESS not-accessible
            STATUS     current
            DESCRIPTION
                "This table is used to query the information about the optical transceiver of the ONT.
                 The index of this table is a combination of ifIndex and hwXponDeviceOntIndex.
                "
            ::= { hwXponDeviceControlObjects 104 }

        hwEponDeviceOntOpticsDdmInfoEntry OBJECT-TYPE
            SYNTAX     HwEponDeviceOntOpticsDdmInfoEntry
            MAX-ACCESS not-accessible
            STATUS     current
            DESCRIPTION
                "This table is used to query the information about the optical transceiver of the ONT.
                 The index of this entry is a combination of ifIndex and hwXponDeviceOntIndex.
                "
            INDEX       { ifIndex, hwXponDeviceOntIndex }
            ::= { hwEponDeviceOntOpticsDdmInfoTable 1 }

        HwEponDeviceOntOpticsDdmInfoEntry ::=
            SEQUENCE {
                hwEponOntOpticalDdmOltRxOntPower              Integer32,
                hwEponOntOpticalDdmTemperature                Integer32,
                hwEponOntOpticalDdmBiasCurrent                Integer32,
                hwEponOntOpticalDdmTxPower                    Integer32,
                hwEponOntOpticalDdmRxPower                    Integer32,
                hwEponOntOpticalDdmVoltage                    Integer32,
                hwEponOntOpticalDdmOltTxPower                 Integer32
            }

        hwEponOntOpticalDdmOltRxOntPower     OBJECT-TYPE
            SYNTAX      Integer32
            MAX-ACCESS  read-only
            STATUS      current
            DESCRIPTION
                "The ONT optical power received on the OLT, unit dBm.
                 The relationship between the actual value and the value get from this leaf node is as follows,
                 Actual value = ((Node value - 10000) / 100)
                "
            ::= { hwEponDeviceOntOpticsDdmInfoEntry 1 }

        hwEponOntOpticalDdmTemperature     OBJECT-TYPE
            SYNTAX      Integer32
            MAX-ACCESS  read-only
            STATUS      current
            DESCRIPTION
                "This object indicates the temperature of the optical module."
            ::= { hwEponDeviceOntOpticsDdmInfoEntry 2 }

        hwEponOntOpticalDdmBiasCurrent     OBJECT-TYPE
            SYNTAX      Integer32
            MAX-ACCESS  read-only
            STATUS      current
            DESCRIPTION
                "This object indicates the Bias Current of the optical module."
            ::= { hwEponDeviceOntOpticsDdmInfoEntry 3 }

        hwEponOntOpticalDdmTxPower     OBJECT-TYPE
            SYNTAX      Integer32
            MAX-ACCESS  read-only
            STATUS      current
            DESCRIPTION
                "This object indicates the transmitting power of the optical module."
            ::= { hwEponDeviceOntOpticsDdmInfoEntry 4 }

        hwEponOntOpticalDdmRxPower     OBJECT-TYPE
            SYNTAX      Integer32
            MAX-ACCESS  read-only
            STATUS      current
            DESCRIPTION
                "This object indicates the receiving power of the optical module."
            ::= { hwEponDeviceOntOpticsDdmInfoEntry 5 }

        hwEponOntOpticalDdmVoltage     OBJECT-TYPE
            SYNTAX      Integer32
            MAX-ACCESS  read-only
            STATUS      current
            DESCRIPTION
                "This object indicates the Power feed voltage of the optical module."
            ::= { hwEponDeviceOntOpticsDdmInfoEntry 6 }

        hwEponOntOpticalDdmOltTxPower     OBJECT-TYPE
            SYNTAX      Integer32
            MAX-ACCESS  read-only
            STATUS      current
            DESCRIPTION
                "This object indicates the transmitting power of the ont peer optical module."
            ::= { hwEponDeviceOntOpticsDdmInfoEntry 7 }

--  Table hwXponDeviceOpticsDdmAlarmProfileInfoTable
        hwXponDeviceOpticsDdmAlarmProfileInfoTable OBJECT-TYPE
            SYNTAX SEQUENCE OF HwXponDeviceOpticsDdmAlarmProfileInfoEntry
            MAX-ACCESS not-accessible
            STATUS current
            DESCRIPTION
                "This is the XPON optical alarm profile infomation table.
                 The index of this table is hwXponDeviceOpticsModuleAlarmProfileInfoNameIndex.
                "
            ::= { hwXponDeviceProfileObjects 70 }

        hwXponDeviceOpticsDdmAlarmProfileInfoEntry OBJECT-TYPE
            SYNTAX HwXponDeviceOpticsDdmAlarmProfileInfoEntry
            MAX-ACCESS not-accessible
            STATUS current
            DESCRIPTION
                "This is the XPON optical alarm profile infomation table.
                 The index of this entry is hwXponDeviceOpticsModuleAlarmProfileInfoNameIndex.
                "
            INDEX { IMPLIED hwXponDeviceOpticsModuleAlarmProfileInfoNameIndex}
            ::= { hwXponDeviceOpticsDdmAlarmProfileInfoTable 1 }

        HwXponDeviceOpticsDdmAlarmProfileInfoEntry ::=
            SEQUENCE {
                hwXponDeviceOpticsModuleAlarmProfileInfoNameIndex                   OCTET STRING,
                hwXponDeviceOpticsDdmAlarmProfileBindNum                            Integer32,
                hwXponDeviceOpticsDdmAlarmProfileInfoRowStatus                      RowStatus,
                hwXponDeviceOpticsDdmAlarmProfileTxOpticAlarmUpper                  Integer32,
                hwXponDeviceOpticsDdmAlarmProfileTxOpticAlarmLower                  Integer32,
                hwXponDeviceOpticsDdmAlarmProfileTxOpticWarnUpper                   Integer32,
                hwXponDeviceOpticsDdmAlarmProfileTxOpticWarnLower                   Integer32,
                hwXponDeviceOpticsDdmAlarmProfileRxOpticAlarmUpper                  Integer32,
                hwXponDeviceOpticsDdmAlarmProfileRxOpticAlarmLower                  Integer32,
                hwXponDeviceOpticsDdmAlarmProfileRxOpticWarnUpper                   Integer32,
                hwXponDeviceOpticsDdmAlarmProfileRxOpticWarnLower                   Integer32,
                hwXponDeviceOpticsDdmAlarmProfileBiasCurrentAlarmUpper              Integer32,
                hwXponDeviceOpticsDdmAlarmProfileBiasCurrentAlarmLower              Integer32,
                hwXponDeviceOpticsDdmAlarmProfileBiasCurrentWarnUpper               Integer32,
                hwXponDeviceOpticsDdmAlarmProfileBiasCurrentWarnLower               Integer32,
                hwXponDeviceOpticsDdmAlarmProfileSupplyVoltageAlarmUpper            Integer32,
                hwXponDeviceOpticsDdmAlarmProfileSupplyVoltageAlarmLower            Integer32,
                hwXponDeviceOpticsDdmAlarmProfileSupplyVoltageWarnUpper             Integer32,
                hwXponDeviceOpticsDdmAlarmProfileSupplyVoltageWarnLower             Integer32,
                hwXponDeviceOpticsDdmAlarmProfileTemperatureAlarmUpper              Integer32,
                hwXponDeviceOpticsDdmAlarmProfileTemperatureAlarmLower              Integer32,
                hwXponDeviceOpticsDdmAlarmProfileTemperatureWarnUpper               Integer32,
                hwXponDeviceOpticsDdmAlarmProfileTemperatureWarnLower               Integer32,
                hwXponDeviceOpticsDdmAlarmProfile10GTxOpticAlarmUpper               Integer32,
                hwXponDeviceOpticsDdmAlarmProfile10GTxOpticAlarmLower               Integer32,
                hwXponDeviceOpticsDdmAlarmProfile10GTxOpticWarnUpper                Integer32,
                hwXponDeviceOpticsDdmAlarmProfile10GTxOpticWarnLower                Integer32,
                hwXponDeviceOpticsDdmAlarmProfile10GBiasCurrentAlarmUpper           Integer32,
                hwXponDeviceOpticsDdmAlarmProfile10GBiasCurrentAlarmLower           Integer32,
                hwXponDeviceOpticsDdmAlarmProfile10GBiasCurrentWarnUpper            Integer32,
                hwXponDeviceOpticsDdmAlarmProfile10GBiasCurrentWarnLower            Integer32,
                hwXponDeviceOpticsDdmAlarmProfileOntCatvRxOpticAlarmUpper           Integer32,
                hwXponDeviceOpticsDdmAlarmProfileOntCatvRxOpticAlarmLower           Integer32
            }

        hwXponDeviceOpticsModuleAlarmProfileInfoNameIndex OBJECT-TYPE
            SYNTAX OCTET STRING (SIZE(1..32))
            MAX-ACCESS not-accessible
            STATUS current
            DESCRIPTION
                "This object indicates the XPON optical alarm profile name index."
            ::= { hwXponDeviceOpticsDdmAlarmProfileInfoEntry 1 }

        hwXponDeviceOpticsDdmAlarmProfileBindNum OBJECT-TYPE
            SYNTAX Integer32
            MAX-ACCESS read-only
            STATUS current
            DESCRIPTION
                "This object indicates the XPON optical alarm profile binding times."
            ::= { hwXponDeviceOpticsDdmAlarmProfileInfoEntry 2 }

        hwXponDeviceOpticsDdmAlarmProfileInfoRowStatus OBJECT-TYPE
            SYNTAX RowStatus
            MAX-ACCESS read-create
            STATUS current
            DESCRIPTION
                "The hwXponDeviceOpticsDdmAlarmProfileInfoRowStatus is used to create a new row
                 or to modify or delete an existing row in this table.
                 Options:
                 1. createAndGo(4) -create a new instance of a conceptual row
                 2. destroy(6)     -delete the instances associated with an existing conceptual row
                "
            ::= { hwXponDeviceOpticsDdmAlarmProfileInfoEntry 3 }

        hwXponDeviceOpticsDdmAlarmProfileTxOpticAlarmUpper OBJECT-TYPE
            SYNTAX Integer32
            MAX-ACCESS read-write
            STATUS current
            DESCRIPTION
                "This object indicates the upper alarm threshold of the transmit optical power."
            ::= { hwXponDeviceOpticsDdmAlarmProfileInfoEntry 4 }

        hwXponDeviceOpticsDdmAlarmProfileTxOpticAlarmLower OBJECT-TYPE
            SYNTAX Integer32
            MAX-ACCESS read-write
            STATUS current
            DESCRIPTION
                "This object indicates the lower alarm threshold of the transmit optical power."
            ::= { hwXponDeviceOpticsDdmAlarmProfileInfoEntry 5 }

        hwXponDeviceOpticsDdmAlarmProfileTxOpticWarnUpper OBJECT-TYPE
            SYNTAX Integer32
            MAX-ACCESS read-write
            STATUS current
            DESCRIPTION
                "This object indicates the upper warning threshold of the transmit optical power."
            ::= { hwXponDeviceOpticsDdmAlarmProfileInfoEntry 6 }

        hwXponDeviceOpticsDdmAlarmProfileTxOpticWarnLower OBJECT-TYPE
            SYNTAX Integer32
            MAX-ACCESS read-write
            STATUS current
            DESCRIPTION
                "This object indicates the lower warning threshold of the transmit optical power."
            ::= { hwXponDeviceOpticsDdmAlarmProfileInfoEntry 7 }

        hwXponDeviceOpticsDdmAlarmProfileRxOpticAlarmUpper OBJECT-TYPE
            SYNTAX Integer32
            MAX-ACCESS read-write
            STATUS current
            DESCRIPTION
                "This object indicates the upper alarm threshold of the receive optical power."
            ::= { hwXponDeviceOpticsDdmAlarmProfileInfoEntry 8 }

        hwXponDeviceOpticsDdmAlarmProfileRxOpticAlarmLower OBJECT-TYPE
            SYNTAX Integer32
            MAX-ACCESS read-write
            STATUS current
            DESCRIPTION
                "This object indicates the lower alarm threshold of the receive optical power."
            ::= { hwXponDeviceOpticsDdmAlarmProfileInfoEntry 9 }

        hwXponDeviceOpticsDdmAlarmProfileRxOpticWarnUpper OBJECT-TYPE
            SYNTAX Integer32
            MAX-ACCESS read-write
            STATUS current
            DESCRIPTION
                "This object indicates the upper warning threshold of the receive optical power."
            ::= { hwXponDeviceOpticsDdmAlarmProfileInfoEntry 10 }

        hwXponDeviceOpticsDdmAlarmProfileRxOpticWarnLower OBJECT-TYPE
            SYNTAX Integer32
            MAX-ACCESS read-write
            STATUS current
            DESCRIPTION
                "This object indicates the lower warning threshold of the receive optical power."
            ::= { hwXponDeviceOpticsDdmAlarmProfileInfoEntry 11 }

        hwXponDeviceOpticsDdmAlarmProfileBiasCurrentAlarmUpper OBJECT-TYPE
            SYNTAX Integer32
            MAX-ACCESS read-write
            STATUS current
            DESCRIPTION
                "This object indicates the upper alarm threshold of the bias current."
            ::= { hwXponDeviceOpticsDdmAlarmProfileInfoEntry 12 }

        hwXponDeviceOpticsDdmAlarmProfileBiasCurrentAlarmLower OBJECT-TYPE
            SYNTAX Integer32
            MAX-ACCESS read-write
            STATUS current
            DESCRIPTION
                "This object indicates the lower alarm threshold of the bias current."
            ::= { hwXponDeviceOpticsDdmAlarmProfileInfoEntry 13 }

        hwXponDeviceOpticsDdmAlarmProfileBiasCurrentWarnUpper OBJECT-TYPE
            SYNTAX Integer32
            MAX-ACCESS read-write
            STATUS current
            DESCRIPTION
                "This object indicates the upper warning threshold of the bias current."
            ::= { hwXponDeviceOpticsDdmAlarmProfileInfoEntry 14 }

        hwXponDeviceOpticsDdmAlarmProfileBiasCurrentWarnLower OBJECT-TYPE
            SYNTAX Integer32
            MAX-ACCESS read-write
            STATUS current
            DESCRIPTION
                "This object indicates the lower warning threshold of the bias current."
            ::= { hwXponDeviceOpticsDdmAlarmProfileInfoEntry 15 }

        hwXponDeviceOpticsDdmAlarmProfileSupplyVoltageAlarmUpper OBJECT-TYPE
            SYNTAX Integer32
            MAX-ACCESS read-write
            STATUS current
            DESCRIPTION
                "This object indicates the upper alarm threshold of the voltage."
            ::= { hwXponDeviceOpticsDdmAlarmProfileInfoEntry 16 }

        hwXponDeviceOpticsDdmAlarmProfileSupplyVoltageAlarmLower OBJECT-TYPE
            SYNTAX Integer32
            MAX-ACCESS read-write
            STATUS current
            DESCRIPTION
                "This object indicates the lower alarm threshold of the voltage."
            ::= { hwXponDeviceOpticsDdmAlarmProfileInfoEntry 17 }

        hwXponDeviceOpticsDdmAlarmProfileSupplyVoltageWarnUpper OBJECT-TYPE
            SYNTAX Integer32
            MAX-ACCESS read-write
            STATUS current
            DESCRIPTION
                "This object indicates the upper warning threshold of the voltage."
            ::= { hwXponDeviceOpticsDdmAlarmProfileInfoEntry 18 }

        hwXponDeviceOpticsDdmAlarmProfileSupplyVoltageWarnLower OBJECT-TYPE
            SYNTAX Integer32
            MAX-ACCESS read-write
            STATUS current
            DESCRIPTION
                "This object indicates the lower warning threshold of the voltage."
            ::= { hwXponDeviceOpticsDdmAlarmProfileInfoEntry 19 }

        hwXponDeviceOpticsDdmAlarmProfileTemperatureAlarmUpper OBJECT-TYPE
            SYNTAX Integer32
            MAX-ACCESS read-write
            STATUS current
            DESCRIPTION
                "This object indicates the upper alarm threshold of the temperature of the optical transceiver."
            ::= { hwXponDeviceOpticsDdmAlarmProfileInfoEntry 20 }

        hwXponDeviceOpticsDdmAlarmProfileTemperatureAlarmLower OBJECT-TYPE
            SYNTAX Integer32
            MAX-ACCESS read-write
            STATUS current
            DESCRIPTION
                "This object indicates the lower alarm threshold of the temperature of the optical transceiver."
            ::= { hwXponDeviceOpticsDdmAlarmProfileInfoEntry 21 }

        hwXponDeviceOpticsDdmAlarmProfileTemperatureWarnUpper OBJECT-TYPE
            SYNTAX Integer32
            MAX-ACCESS read-write
            STATUS current
            DESCRIPTION
                "This object indicates the upper warning threshold of the temperature of the optical transceiver."
            ::= { hwXponDeviceOpticsDdmAlarmProfileInfoEntry 22 }

        hwXponDeviceOpticsDdmAlarmProfileTemperatureWarnLower OBJECT-TYPE
            SYNTAX Integer32
            MAX-ACCESS read-write
            STATUS current
            DESCRIPTION
                "This object indicates the lower warning threshold of the temperature of the optical transceiver."
            ::= { hwXponDeviceOpticsDdmAlarmProfileInfoEntry 23 }

        hwXponDeviceOpticsDdmAlarmProfile10GTxOpticAlarmUpper OBJECT-TYPE
            SYNTAX Integer32
            MAX-ACCESS read-write
            STATUS current
            DESCRIPTION
                "This object indicates the upper alarm threshold of the 10G transmit optical power."
            ::= { hwXponDeviceOpticsDdmAlarmProfileInfoEntry 24 }

        hwXponDeviceOpticsDdmAlarmProfile10GTxOpticAlarmLower OBJECT-TYPE
            SYNTAX Integer32
            MAX-ACCESS read-write
            STATUS current
            DESCRIPTION
                "This object indicates the lower alarm threshold of the 10G transmit optical power."
            ::= { hwXponDeviceOpticsDdmAlarmProfileInfoEntry 25 }

        hwXponDeviceOpticsDdmAlarmProfile10GTxOpticWarnUpper OBJECT-TYPE
            SYNTAX Integer32
            MAX-ACCESS read-write
            STATUS current
            DESCRIPTION
                "This object indicates the upper warning threshold of the 10G transmit optical power."
            ::= { hwXponDeviceOpticsDdmAlarmProfileInfoEntry 26 }

        hwXponDeviceOpticsDdmAlarmProfile10GTxOpticWarnLower OBJECT-TYPE
            SYNTAX Integer32
            MAX-ACCESS read-write
            STATUS current
            DESCRIPTION
                "This object indicates the lower warning threshold of the 10G transmit optical power."
            ::= { hwXponDeviceOpticsDdmAlarmProfileInfoEntry 27 }

        hwXponDeviceOpticsDdmAlarmProfile10GBiasCurrentAlarmUpper OBJECT-TYPE
            SYNTAX Integer32
            MAX-ACCESS read-write
            STATUS current
            DESCRIPTION
                "This object indicates the upper alarm threshold of the 10G bias current."
            ::= { hwXponDeviceOpticsDdmAlarmProfileInfoEntry 28 }

        hwXponDeviceOpticsDdmAlarmProfile10GBiasCurrentAlarmLower OBJECT-TYPE
            SYNTAX Integer32
            MAX-ACCESS read-write
            STATUS current
            DESCRIPTION
                "This object indicates the lower alarm threshold of the 10G bias current."
            ::= { hwXponDeviceOpticsDdmAlarmProfileInfoEntry 29 }

        hwXponDeviceOpticsDdmAlarmProfile10GBiasCurrentWarnUpper OBJECT-TYPE
            SYNTAX Integer32
            MAX-ACCESS read-write
            STATUS current
            DESCRIPTION
                "This object indicates the upper warning threshold of the 10G bias current."
            ::= { hwXponDeviceOpticsDdmAlarmProfileInfoEntry 30 }

        hwXponDeviceOpticsDdmAlarmProfile10GBiasCurrentWarnLower OBJECT-TYPE
            SYNTAX Integer32
            MAX-ACCESS read-write
            STATUS current
            DESCRIPTION
                "This object indicates the lower warning threshold of the 10G bias current."
            ::= { hwXponDeviceOpticsDdmAlarmProfileInfoEntry 31 }

        hwXponDeviceOpticsDdmAlarmProfileOntCatvRxOpticAlarmUpper OBJECT-TYPE
            SYNTAX Integer32
            MAX-ACCESS read-write
            STATUS current
            DESCRIPTION
                "This object indicates the upper alarm threshold of the ONT CATV receive optical power."
            ::= { hwXponDeviceOpticsDdmAlarmProfileInfoEntry 32 }

        hwXponDeviceOpticsDdmAlarmProfileOntCatvRxOpticAlarmLower OBJECT-TYPE
            SYNTAX Integer32
            MAX-ACCESS read-write
            STATUS current
            DESCRIPTION
                "This object indicates the lower alarm threshold of the ONT CATV receive optical power."
            ::= { hwXponDeviceOpticsDdmAlarmProfileInfoEntry 33 }

--table hwXponDeviceLineProfEthPortBundleCfgTable
        hwXponDeviceLineProfEthPortBundleCfgTable OBJECT-TYPE
            SYNTAX SEQUENCE OF HwXponDeviceLineProfEthPortBundleCfgEntry
            MAX-ACCESS not-accessible
            STATUS current
            DESCRIPTION
                "This is the XPON line profile PORT-BUNDLE config table.
                 The index of this table is a combination of hwXponDeviceLineProfEthPortBundleCfgLineProfNameIndex,
                 and hwXponDeviceLineProfEthPortBundleCfgGroupIndex.
                "
            ::= { hwXponDeviceProfileObjects 71 }

        hwXponDeviceLineProfEthPortBundleCfgEntry OBJECT-TYPE
            SYNTAX HwXponDeviceLineProfEthPortBundleCfgEntry
            MAX-ACCESS not-accessible
            STATUS current
            DESCRIPTION
                "This is the XPON line profile PORT-BUNDLE config table.
                 The index of this entry is a combination of hwXponDeviceLineProfEthPortBundleCfgLineProfNameIndex,
                 and hwXponDeviceLineProfEthPortBundleCfgGroupIndex.
                "
            INDEX { hwXponDeviceLineProfEthPortBundleCfgLineProfNameIndex,
                    hwXponDeviceLineProfEthPortBundleCfgGroupIndex}
            ::= { hwXponDeviceLineProfEthPortBundleCfgTable 1 }

        HwXponDeviceLineProfEthPortBundleCfgEntry ::=
            SEQUENCE {
                hwXponDeviceLineProfEthPortBundleCfgLineProfNameIndex      OCTET STRING,
                hwXponDeviceLineProfEthPortBundleCfgGroupIndex             Integer32,
                hwXponDeviceLineProfEthPortBundleCfgPortBitMap             Integer32,
                hwXponDeviceLineProfEthPortBundleCfgRowStatus              RowStatus
            }

        hwXponDeviceLineProfEthPortBundleCfgLineProfNameIndex OBJECT-TYPE
            SYNTAX OCTET STRING (SIZE (1..32))
            MAX-ACCESS not-accessible
            STATUS current
            DESCRIPTION
                "This object indicates the XPON line profile name index."
            ::= { hwXponDeviceLineProfEthPortBundleCfgEntry 1 }

        hwXponDeviceLineProfEthPortBundleCfgGroupIndex OBJECT-TYPE
            SYNTAX Integer32 (1..8)
            MAX-ACCESS not-accessible
            STATUS current
            DESCRIPTION
                "This object indicates the XPON line profile PORT-BUNDLE config bundle gproup index."
            ::= { hwXponDeviceLineProfEthPortBundleCfgEntry 2 }

        hwXponDeviceLineProfEthPortBundleCfgPortBitMap OBJECT-TYPE
            SYNTAX Integer32
            MAX-ACCESS read-write
            STATUS current
            DESCRIPTION
                "This object indicates the XPON line profile PORT-BUNDLE config bundle port bitmap,
                 support 32 ports, and the lowest bit indicates the port 1.
                "
            ::= { hwXponDeviceLineProfEthPortBundleCfgEntry 3 }

        hwXponDeviceLineProfEthPortBundleCfgRowStatus OBJECT-TYPE
            SYNTAX RowStatus
            MAX-ACCESS read-create
            STATUS current
            DESCRIPTION
                "The hwXponDeviceLineProfEthPortBundleCfgRowStatus is used to create a new row
                 or to modify or delete an existing row in this table.
                 Options:
                 1. createAndGo(4) -create a new instance of a conceptual row
                 2. destroy(6)     -delete the instances associated with an existing conceptual row
                "
            ::= { hwXponDeviceLineProfEthPortBundleCfgEntry 4 }

--  Table hwXponDeviceSLAProfileInfoTable
        hwXponDeviceSLAProfileInfoTable OBJECT-TYPE
            SYNTAX SEQUENCE OF HwXponDeviceSLAProfileInfoEntry
            MAX-ACCESS not-accessible
            STATUS current
            DESCRIPTION
                "This is the XPON SLA profile infomation table.
                 The index of this table is hwXponDeviceSLAProfileInfoNameIndex.
                "
            ::= { hwXponDeviceProfileObjects 72 }

        hwXponDeviceSLAProfileInfoEntry OBJECT-TYPE
            SYNTAX HwXponDeviceSLAProfileInfoEntry
            MAX-ACCESS not-accessible
            STATUS current
            DESCRIPTION
                "This is the XPON SLA profile infomation table.
                 The index of this entry is hwXponDeviceSLAProfileInfoNameIndex.
                "
            INDEX { IMPLIED hwXponDeviceSLAProfileInfoNameIndex}
            ::= { hwXponDeviceSLAProfileInfoTable 1 }

        HwXponDeviceSLAProfileInfoEntry ::=
            SEQUENCE {
                hwXponDeviceSLAProfileInfoNameIndex         OCTET STRING,
                hwXponDeviceSLAProfileCycleLength           Integer32,
                hwXponDeviceSLAProfileServiceNum            Integer32,
                hwXponDeviceSLAProfileFixedPacketSize1      Integer32,
                hwXponDeviceSLAProfileFixedBandwidth1       Integer32,
                hwXponDeviceSLAProfileAssuredBandwidth1     Integer32,
                hwXponDeviceSLAProfileBestEffortBandwidth1  Integer32,
                hwXponDeviceSLAProfileWrrWeight1            Integer32,
                hwXponDeviceSLAProfileFixedPacketSize2      Integer32,
                hwXponDeviceSLAProfileFixedBandwidth2       Integer32,
                hwXponDeviceSLAProfileAssuredBandwidth2     Integer32,
                hwXponDeviceSLAProfileBestEffortBandwidth2  Integer32,
                hwXponDeviceSLAProfileWrrWeight2            Integer32,
                hwXponDeviceSLAProfileFixedPacketSize3      Integer32,
                hwXponDeviceSLAProfileFixedBandwidth3       Integer32,
                hwXponDeviceSLAProfileAssuredBandwidth3     Integer32,
                hwXponDeviceSLAProfileBestEffortBandwidth3  Integer32,
                hwXponDeviceSLAProfileWrrWeight3            Integer32,
                hwXponDeviceSLAProfileFixedPacketSize4      Integer32,
                hwXponDeviceSLAProfileFixedBandwidth4       Integer32,
                hwXponDeviceSLAProfileAssuredBandwidth4     Integer32,
                hwXponDeviceSLAProfileBestEffortBandwidth4  Integer32,
                hwXponDeviceSLAProfileWrrWeight4            Integer32,
                hwXponDeviceSLAProfileFixedPacketSize5      Integer32,
                hwXponDeviceSLAProfileFixedBandwidth5       Integer32,
                hwXponDeviceSLAProfileAssuredBandwidth5     Integer32,
                hwXponDeviceSLAProfileBestEffortBandwidth5  Integer32,
                hwXponDeviceSLAProfileWrrWeight5            Integer32,
                hwXponDeviceSLAProfileFixedPacketSize6      Integer32,
                hwXponDeviceSLAProfileFixedBandwidth6       Integer32,
                hwXponDeviceSLAProfileAssuredBandwidth6     Integer32,
                hwXponDeviceSLAProfileBestEffortBandwidth6  Integer32,
                hwXponDeviceSLAProfileWrrWeight6            Integer32,
                hwXponDeviceSLAProfileFixedPacketSize7      Integer32,
                hwXponDeviceSLAProfileFixedBandwidth7       Integer32,
                hwXponDeviceSLAProfileAssuredBandwidth7     Integer32,
                hwXponDeviceSLAProfileBestEffortBandwidth7  Integer32,
                hwXponDeviceSLAProfileWrrWeight7            Integer32,
                hwXponDeviceSLAProfileFixedPacketSize8      Integer32,
                hwXponDeviceSLAProfileFixedBandwidth8       Integer32,
                hwXponDeviceSLAProfileAssuredBandwidth8     Integer32,
                hwXponDeviceSLAProfileBestEffortBandwidth8  Integer32,
                hwXponDeviceSLAProfileWrrWeight8            Integer32,
                hwXponDeviceSLAProfileEntryStatus           RowStatus

            }

        hwXponDeviceSLAProfileInfoNameIndex OBJECT-TYPE
            SYNTAX OCTET STRING (SIZE(1..32))
            MAX-ACCESS not-accessible
            STATUS current
            DESCRIPTION
                "This object indicates the name of the SLA profile."
            ::= { hwXponDeviceSLAProfileInfoEntry 1 }

        hwXponDeviceSLAProfileCycleLength OBJECT-TYPE
            SYNTAX Integer32 (200..16777215)
            MAX-ACCESS read-write
            STATUS current
            DESCRIPTION
                "This object indicates the cycle length."
                ::= { hwXponDeviceSLAProfileInfoEntry 2 }

        hwXponDeviceSLAProfileServiceNum OBJECT-TYPE
            SYNTAX Integer32 (1..8)
            MAX-ACCESS read-write
            STATUS current
            DESCRIPTION
                "This object indicates the service number."
            ::= { hwXponDeviceSLAProfileInfoEntry 3 }

        hwXponDeviceSLAProfileFixedPacketSize1 OBJECT-TYPE
            SYNTAX Integer32 (-1 | 0 | 64..2000)
            MAX-ACCESS read-write
            STATUS current
            DESCRIPTION
                "This object indicates the fixed packet size of service 1.
                 The value(0) indicates that there is no restriction of packet size.
                 The value(-1) is invalid value.
                "
            ::= { hwXponDeviceSLAProfileInfoEntry 4 }

        hwXponDeviceSLAProfileFixedBandwidth1 OBJECT-TYPE
            SYNTAX Integer32 (-1 | 0..999936)
            MAX-ACCESS read-write
            STATUS current
            DESCRIPTION
                "This object indicates the fixed bandwidth of service 1.
                 The value(-1) is invalid value.
                "
            ::= { hwXponDeviceSLAProfileInfoEntry 5 }

        hwXponDeviceSLAProfileAssuredBandwidth1 OBJECT-TYPE
            SYNTAX Integer32 (-1 | 0..999936)
            MAX-ACCESS read-write
            STATUS current
            DESCRIPTION
                "This object indicates the assure bandwidth of service 1.
                 The value(-1) is invalid value.
                "
            ::= { hwXponDeviceSLAProfileInfoEntry 6 }

        hwXponDeviceSLAProfileBestEffortBandwidth1 OBJECT-TYPE
            SYNTAX Integer32 (-1 | 0..999936)
            MAX-ACCESS read-write
            STATUS current
            DESCRIPTION
                "This object indicates the best effort bandwidth of service 1.
                 The value(-1) is invalid value.
                "
            ::= { hwXponDeviceSLAProfileInfoEntry 7 }

        hwXponDeviceSLAProfileWrrWeight1 OBJECT-TYPE
            SYNTAX Integer32 (-1 | 0..100)
            MAX-ACCESS read-write
            STATUS current
            DESCRIPTION
                "This object indicates the WRR weight of Service 1.
                 The value(-1) is invalid value.
                "
            ::= { hwXponDeviceSLAProfileInfoEntry 8 }

        hwXponDeviceSLAProfileFixedPacketSize2 OBJECT-TYPE
            SYNTAX Integer32 (-1 | 0 | 64..2000)
            MAX-ACCESS read-write
            STATUS current
            DESCRIPTION
                "This object indicates the fixed packet size of service 2.
                 The value(0) indicates that there is no restriction of packet size.
                 The value(-1) is invalid value.
                "
            ::= { hwXponDeviceSLAProfileInfoEntry 9 }

        hwXponDeviceSLAProfileFixedBandwidth2 OBJECT-TYPE
            SYNTAX Integer32 (-1 | 0..999936)
            MAX-ACCESS read-write
            STATUS current
            DESCRIPTION
                "This object indicates the fixed bandwidth of service 2.
                 The value(-1) is invalid value.
                "
            ::= { hwXponDeviceSLAProfileInfoEntry 10 }

        hwXponDeviceSLAProfileAssuredBandwidth2 OBJECT-TYPE
            SYNTAX Integer32 (-1 | 0..999936)
            MAX-ACCESS read-write
            STATUS current
            DESCRIPTION
                "This object indicates the assure bandwidth of service 2.
                 The value(-1) is invalid value.
                "
            ::= { hwXponDeviceSLAProfileInfoEntry 11 }

        hwXponDeviceSLAProfileBestEffortBandwidth2 OBJECT-TYPE
            SYNTAX Integer32 (-1 | 0..999936)
            MAX-ACCESS read-write
            STATUS current
            DESCRIPTION
                "This object indicates the best effort bandwidth of service 2.
                 The value(-1) is invalid value.
                "
            ::= { hwXponDeviceSLAProfileInfoEntry 12 }

        hwXponDeviceSLAProfileWrrWeight2 OBJECT-TYPE
            SYNTAX Integer32 (-1 | 0..100)
            MAX-ACCESS read-write
            STATUS current
            DESCRIPTION
                "This object indicates the WRR weight of service 2.
                 The value(-1) is invalid value.
                "
            ::= { hwXponDeviceSLAProfileInfoEntry 13 }

        hwXponDeviceSLAProfileFixedPacketSize3 OBJECT-TYPE
            SYNTAX Integer32 (-1 | 0 | 64..2000)
            MAX-ACCESS read-write
            STATUS current
            DESCRIPTION
                "This object indicates the fixed packet size of service 3.
                 The value(0) indicates that there is no restriction of packet size.
                 The value(-1) is invalid value.
                "
            ::= { hwXponDeviceSLAProfileInfoEntry 14 }

        hwXponDeviceSLAProfileFixedBandwidth3 OBJECT-TYPE
            SYNTAX Integer32 (-1 | 0..999936)
            MAX-ACCESS read-write
            STATUS current
            DESCRIPTION
                "This object indicates the fixed bandwidth of service 3.
                 The value(-1) is invalid value.
                "
            ::= { hwXponDeviceSLAProfileInfoEntry 15 }

        hwXponDeviceSLAProfileAssuredBandwidth3 OBJECT-TYPE
            SYNTAX Integer32 (-1 | 0..999936)
            MAX-ACCESS read-write
            STATUS current
            DESCRIPTION
                "This object indicates the assure bandwidth of service 3.
                 The value(-1) is invalid value.
                "
            ::= { hwXponDeviceSLAProfileInfoEntry 16 }

        hwXponDeviceSLAProfileBestEffortBandwidth3 OBJECT-TYPE
            SYNTAX Integer32 (-1 | 0..999936)
            MAX-ACCESS read-write
            STATUS current
            DESCRIPTION
                "This object indicates the best effort bandwidth of Service 3.
                 The value(-1) is invalid value.
                "
            ::= { hwXponDeviceSLAProfileInfoEntry 17 }

        hwXponDeviceSLAProfileWrrWeight3 OBJECT-TYPE
            SYNTAX Integer32 (-1 | 0..100)
            MAX-ACCESS read-write
            STATUS current
            DESCRIPTION
                "This object indicates the WRR weight of service 3.
                 The value(-1) is invalid value.
                "
            ::= { hwXponDeviceSLAProfileInfoEntry 18 }

        hwXponDeviceSLAProfileFixedPacketSize4 OBJECT-TYPE
            SYNTAX Integer32 (-1 | 0 | 64..2000)
            MAX-ACCESS read-write
            STATUS current
            DESCRIPTION
                "This object indicates the fixed packet size of service 4.
                 The value(0) indicates that there is no restriction of packet size.
                 The value(-1) is invalid value.
                "
            ::= { hwXponDeviceSLAProfileInfoEntry 19 }

        hwXponDeviceSLAProfileFixedBandwidth4 OBJECT-TYPE
            SYNTAX Integer32 (-1 | 0..999936)
            MAX-ACCESS read-write
            STATUS current
            DESCRIPTION
                "This object indicates the fixed bandwidth of service 4.
                 The value(-1) is invalid value.
                "
            ::= { hwXponDeviceSLAProfileInfoEntry 20 }

        hwXponDeviceSLAProfileAssuredBandwidth4 OBJECT-TYPE
            SYNTAX Integer32 (-1 | 0..999936)
            MAX-ACCESS read-write
            STATUS current
            DESCRIPTION
                "This object indicates the assure bandwidth of service 4.
                 The value(-1) is invalid value.
                "
            ::= { hwXponDeviceSLAProfileInfoEntry 21 }

        hwXponDeviceSLAProfileBestEffortBandwidth4 OBJECT-TYPE
            SYNTAX Integer32 (-1 | 0..999936)
            MAX-ACCESS read-write
            STATUS current
            DESCRIPTION
                "This object indicates the best effort bandwidth of service 4.
                 The value(-1) is invalid value.
                "
            ::= { hwXponDeviceSLAProfileInfoEntry 22 }

        hwXponDeviceSLAProfileWrrWeight4 OBJECT-TYPE
            SYNTAX Integer32 (-1 | 0..100)
            MAX-ACCESS read-write
            STATUS current
            DESCRIPTION
                "This object indicates the WRR weight of service 4.
                 The value(-1) is invalid value.
                "
            ::= { hwXponDeviceSLAProfileInfoEntry 23 }

        hwXponDeviceSLAProfileFixedPacketSize5 OBJECT-TYPE
            SYNTAX Integer32 (-1 | 0 | 64..2000)
            MAX-ACCESS read-write
            STATUS current
            DESCRIPTION
                "This object indicates the fixed packet size of service 5.
                 The value(0) indicates that there is no restriction of packet size.
                 The value(-1) is invalid value.
                "
            ::= { hwXponDeviceSLAProfileInfoEntry 24 }

        hwXponDeviceSLAProfileFixedBandwidth5 OBJECT-TYPE
            SYNTAX Integer32 (-1 | 0..999936)
            MAX-ACCESS read-write
            STATUS current
            DESCRIPTION
                "This object indicates the Fixed Bandwidth of service 5.
                 The value(-1) is invalid value.
                "
            ::= { hwXponDeviceSLAProfileInfoEntry 25 }

        hwXponDeviceSLAProfileAssuredBandwidth5 OBJECT-TYPE
            SYNTAX Integer32 (-1 | 0..999936)
            MAX-ACCESS read-write
            STATUS current
            DESCRIPTION
                "This object indicates the assure bandwidth of service 5.
                 The value(-1) is invalid value.
                "
            ::= { hwXponDeviceSLAProfileInfoEntry 26 }

        hwXponDeviceSLAProfileBestEffortBandwidth5 OBJECT-TYPE
            SYNTAX Integer32 (-1 | 0..999936)
            MAX-ACCESS read-write
            STATUS current
            DESCRIPTION
                "This object indicates the best effort bandwidth of service 5.
                 The value(-1) is invalid value.
                "
            ::= { hwXponDeviceSLAProfileInfoEntry 27 }

        hwXponDeviceSLAProfileWrrWeight5 OBJECT-TYPE
            SYNTAX Integer32 (-1 | 0..100)
            MAX-ACCESS read-write
            STATUS current
            DESCRIPTION
                "This object indicates the WRR weight of service 5.
                 The value(-1) is invalid value.
                "
            ::= { hwXponDeviceSLAProfileInfoEntry 28 }

        hwXponDeviceSLAProfileFixedPacketSize6 OBJECT-TYPE
            SYNTAX Integer32 (-1 | 0 | 64..2000)
            MAX-ACCESS read-write
            STATUS current
            DESCRIPTION
                "This object indicates the fixed packet size of service 6.
                 The value(0) indicates that there is no restriction of packet size.
                 The value(-1) is invalid value.
                "
            ::= { hwXponDeviceSLAProfileInfoEntry 29 }

        hwXponDeviceSLAProfileFixedBandwidth6 OBJECT-TYPE
            SYNTAX Integer32 (-1 | 0..999936)
            MAX-ACCESS read-write
            STATUS current
            DESCRIPTION
                "This object indicates the fixed bandwidth of service 6.
                 The value(-1) is invalid value.
                "
            ::= { hwXponDeviceSLAProfileInfoEntry 30 }

        hwXponDeviceSLAProfileAssuredBandwidth6 OBJECT-TYPE
            SYNTAX Integer32 (-1 | 0..999936)
            MAX-ACCESS read-write
            STATUS current
            DESCRIPTION
                "This object indicates the assure bandwidth of service 6.
                 The value(-1) is invalid value.
                "
            ::= { hwXponDeviceSLAProfileInfoEntry 31 }

        hwXponDeviceSLAProfileBestEffortBandwidth6 OBJECT-TYPE
            SYNTAX Integer32 (-1 | 0..999936)
            MAX-ACCESS read-write
            STATUS current
            DESCRIPTION
                "This object indicates the best effort bandwidth of service 6.
                 The value(-1) is invalid value.
                "
            ::= { hwXponDeviceSLAProfileInfoEntry 32 }

        hwXponDeviceSLAProfileWrrWeight6 OBJECT-TYPE
            SYNTAX Integer32 (-1 | 0..100)
            MAX-ACCESS read-write
            STATUS current
            DESCRIPTION
                "This object indicates the WRR weight of service 6.
                 The value(-1) is invalid value.
                "
            ::= { hwXponDeviceSLAProfileInfoEntry 33 }

        hwXponDeviceSLAProfileFixedPacketSize7 OBJECT-TYPE
            SYNTAX Integer32 (-1 | 0 | 64..2000)
            MAX-ACCESS read-write
            STATUS current
            DESCRIPTION
                "This object indicates the fixed packet size of service 7.
                 The value(0) indicates that there is no restriction of packet size.
                 The value(-1) is invalid value.
                "
            ::= { hwXponDeviceSLAProfileInfoEntry 34 }

        hwXponDeviceSLAProfileFixedBandwidth7 OBJECT-TYPE
            SYNTAX Integer32 (-1 | 0..999936)
            MAX-ACCESS read-write
            STATUS current
            DESCRIPTION
                "This object indicates the fixed bandwidth of service 7.
                 The value(-1) is invalid value.
                "
            ::= { hwXponDeviceSLAProfileInfoEntry 35 }

        hwXponDeviceSLAProfileAssuredBandwidth7 OBJECT-TYPE
            SYNTAX Integer32 (-1 | 0..999936)
            MAX-ACCESS read-write
            STATUS current
            DESCRIPTION
                "This object indicates the assure bandwidth of service 7.
                 The value(-1) is invalid value.
                "
            ::= { hwXponDeviceSLAProfileInfoEntry 36 }

        hwXponDeviceSLAProfileBestEffortBandwidth7 OBJECT-TYPE
            SYNTAX Integer32 (-1 | 0..999936)
            MAX-ACCESS read-write
            STATUS current
            DESCRIPTION
                "This object indicates the best effort bandwidth of service 7.
                 The value(-1) is invalid value.
                "
            ::= { hwXponDeviceSLAProfileInfoEntry 37 }

        hwXponDeviceSLAProfileWrrWeight7 OBJECT-TYPE
            SYNTAX Integer32 (-1 | 0..100)
            MAX-ACCESS read-write
            STATUS current
            DESCRIPTION
                "This object indicates the WRR weight of service 7.
                 The value(-1) is invalid value.
                "
            ::= { hwXponDeviceSLAProfileInfoEntry 38 }

        hwXponDeviceSLAProfileFixedPacketSize8 OBJECT-TYPE
            SYNTAX Integer32 (-1 | 0 | 64..2000)
            MAX-ACCESS read-write
            STATUS current
            DESCRIPTION
                "This object indicates the fixed packet size of service 8.
                 The value(0) indicates that there is no restriction of packet size.
                 The value(-1) is invalid value.
                "
            ::= { hwXponDeviceSLAProfileInfoEntry 39 }

        hwXponDeviceSLAProfileFixedBandwidth8 OBJECT-TYPE
            SYNTAX Integer32 (-1 | 0..999936)
            MAX-ACCESS read-write
            STATUS current
            DESCRIPTION
                "This object indicates the fixed bandwidth of service 8.
                 The value(-1) is invalid value.
                "
            ::= { hwXponDeviceSLAProfileInfoEntry 40 }

        hwXponDeviceSLAProfileAssuredBandwidth8 OBJECT-TYPE
            SYNTAX Integer32 (-1 | 0..999936)
            MAX-ACCESS read-write
            STATUS current
            DESCRIPTION
                "This object indicates the assure bandwidth of service 8.
                 The value(-1) is invalid value.
                "
            ::= { hwXponDeviceSLAProfileInfoEntry 41 }

        hwXponDeviceSLAProfileBestEffortBandwidth8 OBJECT-TYPE
            SYNTAX Integer32 (-1 | 0..999936)
            MAX-ACCESS read-write
            STATUS current
            DESCRIPTION
                "This object indicates the best effort bandwidth of service 8.
                 The value(-1) is invalid value.
                "
            ::= { hwXponDeviceSLAProfileInfoEntry 42 }

        hwXponDeviceSLAProfileWrrWeight8 OBJECT-TYPE
            SYNTAX Integer32 (-1 | 0..100)
            MAX-ACCESS read-write
            STATUS current
            DESCRIPTION
                "This object indicates the WRR weight of service 8.
                 The value(-1) is invalid value.
                "
            ::= { hwXponDeviceSLAProfileInfoEntry 43 }

        hwXponDeviceSLAProfileEntryStatus OBJECT-TYPE
            SYNTAX RowStatus
            MAX-ACCESS read-create
            STATUS current
            DESCRIPTION
                "The hwXponDeviceSLAProfileEntryStatus is used to create a new row
                 or to modify or delete an existing row in this table.
                 Options:
                 1. createAndGo(4) -create a new instance of a conceptual row
                 2. destroy(6)     -delete the instances associated with an existing conceptual row
                "
            ::= { hwXponDeviceSLAProfileInfoEntry 44 }
-- hwXponDeviceSLAProfileInfoTable  end

--  Table hwGponDeviceSrvProfileOntUpIgmpMsgCfgTable
        hwGponDeviceSrvProfileOntUpIgmpMsgCfgTable OBJECT-TYPE
            SYNTAX SEQUENCE OF HwGponDeviceSrvProfileOntUpIgmpMsgCfgEntry
            MAX-ACCESS not-accessible
            STATUS current
            DESCRIPTION
                "This table is used to set and query the user-VLAN-based IGMP packet forwarding mode of ONT.
                 The indexes of this table are hwGponDeviceSrvProfileOntIgmpCfgNameIndex and hwGponDeviceSrvProfileOntUpIgmpMsgUserVlan.
                "
            ::= { hwXponDeviceProfileObjects 73 }

        hwGponDeviceSrvProfileOntUpIgmpMsgCfgEntry OBJECT-TYPE
            SYNTAX HwGponDeviceSrvProfileOntUpIgmpMsgCfgEntry
            MAX-ACCESS not-accessible
            STATUS current
            DESCRIPTION
                "This table is used to set and query the user-VLAN-based IGMP packet forwarding mode of ONT.
                 The indexes of this entry are hwGponDeviceSrvProfileOntIgmpCfgNameIndex and hwGponDeviceSrvProfileOntUpIgmpMsgUserVlan.
                "
            INDEX { hwGponDeviceSrvProfileOntIgmpCfgNameIndex, hwGponDeviceSrvProfileOntUpIgmpMsgUserVlan}
            ::= { hwGponDeviceSrvProfileOntUpIgmpMsgCfgTable 1 }

        HwGponDeviceSrvProfileOntUpIgmpMsgCfgEntry ::=
            SEQUENCE {
                hwGponDeviceSrvProfileOntIgmpCfgNameIndex               OCTET STRING,
                hwGponDeviceSrvProfileOntUpIgmpMsgUserVlan              Integer32,
                hwGponDeviceSrvProfileOntUpIgmpTransmitMode             INTEGER,
                hwGponDeviceSrvProfileOntUpIgmpMsgTranslationVlan       Integer32,
                hwGponDeviceSrvProfileOntUpIgmpMsgPriority              Integer32,
                hwGponDeviceSrvProfileOntUpIgmpMsgCfgRowStatus          RowStatus
            }

        hwGponDeviceSrvProfileOntIgmpCfgNameIndex OBJECT-TYPE
            SYNTAX OCTET STRING (SIZE (1..32))
            MAX-ACCESS not-accessible
            STATUS current
            DESCRIPTION
                "This object indicates the XPON service profile name index."
            ::= { hwGponDeviceSrvProfileOntUpIgmpMsgCfgEntry 1 }

        hwGponDeviceSrvProfileOntUpIgmpMsgUserVlan OBJECT-TYPE
            SYNTAX Integer32
            MAX-ACCESS not-accessible
            STATUS current
            DESCRIPTION
                "This object indicates the user VLAN of upstream IGMP packets.
                 0..4095 indicates the user VLAN."
            ::= { hwGponDeviceSrvProfileOntUpIgmpMsgCfgEntry 2 }

        hwGponDeviceSrvProfileOntUpIgmpTransmitMode OBJECT-TYPE
            SYNTAX INTEGER {
                transparent(1),
                translation(2),
                default(3),
                invalid(-1)
            }
            MAX-ACCESS read-write
            STATUS current
            DESCRIPTION
                "This object indicates the IGMP packet forwarding mode.
                 Only the value transparent(1) is supported currently.
                 Options:
                 1. transparent(1)    - Indicates that the IGMP upstream packets forward mode is transparent
                 2. translation(2)    - Indicates that the IGMP upstream packets forward mode is translation
                 3. default(3)        - Indicates that the IGMP upstream packets forward mode is add VLAN tag
                 4. invalid(-1)       - Indicates that the query fails or no information is detected.
                "
            ::= { hwGponDeviceSrvProfileOntUpIgmpMsgCfgEntry 3 }

        hwGponDeviceSrvProfileOntUpIgmpMsgTranslationVlan OBJECT-TYPE
            SYNTAX Integer32 (-1|0..4095)
            MAX-ACCESS read-write
            STATUS current
            DESCRIPTION
                "This object indicates the ont upstream IGMP packets will be translate to the translation vlan.
                "
            ::= { hwGponDeviceSrvProfileOntUpIgmpMsgCfgEntry 4 }

        hwGponDeviceSrvProfileOntUpIgmpMsgPriority OBJECT-TYPE
            SYNTAX Integer32 (-1|0..7)
            MAX-ACCESS read-write
            STATUS current
            DESCRIPTION
                "When upstream IGMP packets were added a vlan or translated to the translation vlan, priority was set.
                "
            ::= { hwGponDeviceSrvProfileOntUpIgmpMsgCfgEntry 5 }

        hwGponDeviceSrvProfileOntUpIgmpMsgCfgRowStatus OBJECT-TYPE
            SYNTAX     RowStatus
            MAX-ACCESS    read-create
            STATUS      current
            DESCRIPTION
                "Row status. This object is used to differentiate the
                 creation, modification and deletion operations for an object.
                 Options:
                 1. createAndGo(4) -create a new instance of a conceptual row
                 2. destroy(6)     -delete the instances associated with an existing conceptual row
                "
            ::= { hwGponDeviceSrvProfileOntUpIgmpMsgCfgEntry 6 }

-- Table hwGponDeviceLineProfGemBundleCfgTable
        hwGponDeviceLineProfGemBundleCfgTable OBJECT-TYPE
            SYNTAX  SEQUENCE OF HwGponDeviceLineProfGemBundleCfgEntry
            MAX-ACCESS not-accessible
            STATUS current
            DESCRIPTION
                "This is the XPON line profile GEM port bundle configure table.
                 The indexes of this table are hwGponDeviceLineProfGemBundleLineProfNameIndex
                 and hwGponDeviceLineProfGemBundleCfgMaster.
                "
            ::= { hwXponDeviceProfileObjects 74 }

        hwGponDeviceLineProfGemBundleCfgEntry OBJECT-TYPE
            SYNTAX HwGponDeviceLineProfGemBundleCfgEntry
            MAX-ACCESS not-accessible
            STATUS current
            DESCRIPTION
                "This is the XPON line profile GEM port bundle config table.
                 The indexes of this entry are hwGponDeviceLineProfGemBundleLineProfNameIndex
                 and hwGponDeviceLineProfGemBundleCfgMaster.
                "
            INDEX { hwGponDeviceLineProfGemBundleLineProfNameIndex, hwGponDeviceLineProfGemBundleCfgMaster }
            ::= { hwGponDeviceLineProfGemBundleCfgTable 1 }

        HwGponDeviceLineProfGemBundleCfgEntry ::=
            SEQUENCE {
                hwGponDeviceLineProfGemBundleLineProfNameIndex OCTET STRING,
                hwGponDeviceLineProfGemBundleCfgMaster         Integer32,
                hwGponDeviceLineProfGemBundleCfgSlaveList      OCTET STRING
            }

        hwGponDeviceLineProfGemBundleLineProfNameIndex OBJECT-TYPE
            SYNTAX OCTET STRING (SIZE (1..32))
            MAX-ACCESS not-accessible
            STATUS current
            DESCRIPTION
                "This object indicates the XPON line profile name index."
            ::= { hwGponDeviceLineProfGemBundleCfgEntry 1 }

        hwGponDeviceLineProfGemBundleCfgMaster OBJECT-TYPE
            SYNTAX Integer32 (0..1023)
            MAX-ACCESS not-accessible
            STATUS current
            DESCRIPTION
                "Indicates the master GEM index of bundle."
            ::= { hwGponDeviceLineProfGemBundleCfgEntry 2 }

        hwGponDeviceLineProfGemBundleCfgSlaveList OBJECT-TYPE
            SYNTAX OCTET STRING  (SIZE (0..255))
            MAX-ACCESS read-write
            STATUS current
            DESCRIPTION
                "Indicates the slave GEM ports of bundle.
                 The value of slave GEM ports of bundle:
                 number(1byte)             :Indicates the number of slave GEM ports . The maximum number is 7.
                 gemportid(2byte * number) :Indicates a slave GEM port ID.
		        "
            ::= { hwGponDeviceLineProfGemBundleCfgEntry 3 }

-- Table hwXponDeviceOltDualparentTable
        hwXponDeviceOltDualparentTable OBJECT-TYPE
            SYNTAX     SEQUENCE OF HwXponDeviceOltDualparentEntry
            MAX-ACCESS not-accessible
            STATUS     current
            DESCRIPTION
                "This table is the type B dual-homing configuration table.
                 The index of this table is ifIndex.
                "
            ::= { hwXponDeviceControlObjects 120 }

        hwXponDeviceOltDualparentEntry OBJECT-TYPE
            SYNTAX     HwXponDeviceOltDualparentEntry
            MAX-ACCESS not-accessible
            STATUS     current
            DESCRIPTION
                "This table is the type B dual-homing configuration table.
                 The index of this entry is ifIndex.
                "
            INDEX       { ifIndex }
            ::= { hwXponDeviceOltDualparentTable 1 }

        HwXponDeviceOltDualparentEntry ::=
            SEQUENCE {
                hwXponDeviceOltDualparentJoin          INTEGER,
                hwXponDeviceOltDualparentFreeze        INTEGER,
                hwXponDeviceOltDualparentForceSwitch   INTEGER,
                hwXponDeviceOltDualparentWorkState     INTEGER,
                hwXponDeviceOltDualparentDetectTimeLen Integer32,
                hwXponDeviceOltDualparentDesc          OCTET STRING
            }

         hwXponDeviceOltDualparentJoin     OBJECT-TYPE
            SYNTAX    INTEGER {
                joinwork(1),
                joinprotect(2),
                undojoin(3),
                invalid(-1)
            }
            MAX-ACCESS  read-write
            STATUS      current
            DESCRIPTION
                "This object indicates whether to add a port to the protection group.
                 Options:
                 1.joinwork(1)     - Add the port as a working port to the protection group
                 2.joinprotect(2)  - Add the port as a protection port to the protection group
                 3.undojoin(3)     - Delete the memer port of the protection group
                 4.invalid(-1)     - Indicates that the query fails or no information is detected
                "
            ::= { hwXponDeviceOltDualparentEntry 1 }

        hwXponDeviceOltDualparentFreeze     OBJECT-TYPE
            SYNTAX      INTEGER {
                freeze(1),
                undofreeze(2),
                invalid(-1)
            }
            MAX-ACCESS  read-write
            STATUS      current
            DESCRIPTION
                "This object indicates whether the protection group is in the frozen state.
                 Options:
                 1. freeze(1)          - Freeze the protection group
                 2. undofreeze(2)      - Undo the frozen state of the protection group
                 3. invalid(-1)        - Indicates that the query fails or no information is detected
                "
            ::= { hwXponDeviceOltDualparentEntry 2 }

            hwXponDeviceOltDualparentForceSwitch  OBJECT-TYPE
            SYNTAX      INTEGER {
                force(1),
                undoforce(2),
                invalid(-1)
            }
            MAX-ACCESS  read-write
            STATUS      current
            DESCRIPTION
                "This object indicates whether the port is in the forced working mode.
                 Options:
                 1. force(1)          - The port is in the forced working mode
                 2. undoforce(2)      - The port is not in the forced working mode
                 3. invalid(-1)       - Indicates that the query fails or no information is detected
                "
            ::= { hwXponDeviceOltDualparentEntry 3 }

        hwXponDeviceOltDualparentWorkState     OBJECT-TYPE
            SYNTAX      INTEGER {
                active(1),
                standby(2),
                fault(3),
                detect(4),
                invalid(-1)
            }
            MAX-ACCESS  read-write
            STATUS      current
            DESCRIPTION
                "This object is used to set or show the port protect status.
                 Options:
                 1. active(1)      - The port protect status is active
                 2. standby(2)     - The port protect status is standby
                 3. fault(3)       - The port protect status is fault
                 4. detect(4)      - The port protect status is detective
                 5. invalid(-1)    - Indicates that the query fails or no information is detected
                "
            ::= { hwXponDeviceOltDualparentEntry 4 }

        hwXponDeviceOltDualparentDetectTimeLen      OBJECT-TYPE
            SYNTAX      Integer32
            MAX-ACCESS  read-only
            STATUS      current
            DESCRIPTION
                "This object indicates the duration of the protection group member in the detect state."
            ::= { hwXponDeviceOltDualparentEntry 5 }

        hwXponDeviceOltDualparentDesc OBJECT-TYPE
            SYNTAX OCTET STRING (SIZE(1..32))
            MAX-ACCESS read-write
            STATUS current
            DESCRIPTION
                "This object indicates the description of the member port of the protection group."
            ::= { hwXponDeviceOltDualparentEntry 6 }

-- hwXponDynamicMacQuery
        HwXponDynamicMacQueryPara ::= TEXTUAL-CONVENTION
            STATUS       current
            DESCRIPTION
                "Reserved parameter."
            SYNTAX  Integer32

        HwXponDynamicMacQueryType ::= TEXTUAL-CONVENTION
            STATUS       current
            DESCRIPTION
                "The value is quering index; if no index, th value is -1. For example, if the value
                 is XponOntPortInSpecVlan(1), the value of ifIndex, hwXponDynamicMacVlanId, hwXponDynamicMacIndex,
                 hwXponDynamicMacQueryPara0, hwXponDynamicMacQueryPara1, hwXponDynamicMacQueryPara2 is valid,
                 and the value of hwXponDynamicMacQueryPara3 is invalid, -1.
                 Options:
                 1. xponOntPortInSpecVlan(1)  - The ONT port is in the specified vlan
                 2. xponOntInSpecPort(2)  - The specified ONT port
                 3. xponOntInSpecOnt(3)  - The specified ONT
                 4. xponOntInSpecWlan(4)      - The WLAN of specified ONT
                "
            SYNTAX       INTEGER {
                -- learnt mac(s) of XPON ONT port in the specified vlan;
                -- hwXponDynamicMacQueryPara0 : ONT ID
                -- hwXponDynamicMacQueryPara1 : ONT Port type
                -- hwXponDynamicMacQueryPara2 : ONT Port ID
                xponOntPortInSpecVlan(1),

                -- learnt mac(s) of XPON ONT in the specified port;
                -- hwXponDynamicMacQueryPara0 : ONT ID
                -- hwXponDynamicMacQueryPara1 : ONT Port type
                -- hwXponDynamicMacQueryPara2 : ONT Port ID
                xponOntInSpecPort(2),

                -- learnt mac(s) of the specified XPON ONT;
                -- hwXponDynamicMacQueryPara0 : ONT ID
                -- hwXponDynamicMacQueryPara1 : invalid
                -- hwXponDynamicMacQueryPara2 : invalid
                xponInSpecOnt(3),

                -- learnt mac(s) of the WLAN of specified ONT;
                -- hwXponDynamicMacQueryPara0 : ONT ID
                -- hwXponDynamicMacQueryPara1 : invalid
                -- hwXponDynamicMacQueryPara2 : invalid
                xponOntInSpecWlan(4)
            }

        hwXponDynamicMacQueryTable OBJECT-TYPE
            SYNTAX SEQUENCE OF HwXponDynamicMacQueryEntry
            MAX-ACCESS not-accessible
            STATUS current
            DESCRIPTION
                "This table is used to query dynamic MAC address.
                 The index of this table is a combination of ifIndex, hwXponDynamicMacVlanId,
                 hwXponDynamicMacIndex, hwXponDynamicMacQueryType, hwXponDynamicMacQueryPara0,
                 hwXponDynamicMacQueryPara1, hwXponDynamicMacQueryPara2 and hwXponDynamicMacQueryPara3.
                "
            ::= { hwXponDeviceControlObjects 130 }

        hwXponDynamicMacQueryEntry OBJECT-TYPE
            SYNTAX HwXponDynamicMacQueryEntry
            MAX-ACCESS not-accessible
            STATUS current
            DESCRIPTION
                "This table is used to query dynamic MAC address.
                 The index of this entry is a combination of ifIndex, hwXponDynamicMacVlanId,
                 hwXponDynamicMacIndex, hwXponDynamicMacQueryType, hwXponDynamicMacQueryPara0,
                 hwXponDynamicMacQueryPara1, hwXponDynamicMacQueryPara2 and hwXponDynamicMacQueryPara3.
                "
            INDEX { ifIndex, hwXponDynamicMacVlanId, hwXponDynamicMacIndex,
                    hwXponDynamicMacQueryType, hwXponDynamicMacQueryPara0,
                    hwXponDynamicMacQueryPara1, hwXponDynamicMacQueryPara2,
                    hwXponDynamicMacQueryPara3
            }
            ::= { hwXponDynamicMacQueryTable 1 }

        HwXponDynamicMacQueryEntry ::=
            SEQUENCE {
                hwXponDynamicMacVlanId      Integer32,
                hwXponDynamicMacIndex       Integer32,
                hwXponDynamicMacQueryType   HwXponDynamicMacQueryType,
                hwXponDynamicMacQueryPara0  HwXponDynamicMacQueryPara,
                hwXponDynamicMacQueryPara1  HwXponDynamicMacQueryPara,
                hwXponDynamicMacQueryPara2  HwXponDynamicMacQueryPara,
                hwXponDynamicMacQueryPara3  HwXponDynamicMacQueryPara,
                hwXponDynamicMacAddr        OCTET STRING
            }

        hwXponDynamicMacVlanId   OBJECT-TYPE
            SYNTAX Integer32(-1 | 1..4094)
            MAX-ACCESS not-accessible
            STATUS current
            DESCRIPTION
                "This object indicates the VLAN of dynamic MAC address.
                 The value(-1) is invalid value."
            ::= { hwXponDynamicMacQueryEntry 1 }

        hwXponDynamicMacIndex   OBJECT-TYPE
            SYNTAX Integer32
            MAX-ACCESS not-accessible
            STATUS current
            DESCRIPTION
                "This object indicates the dynamic MAC address index."
            ::= { hwXponDynamicMacQueryEntry 2 }

        hwXponDynamicMacQueryType   OBJECT-TYPE
            SYNTAX HwXponDynamicMacQueryType
            MAX-ACCESS not-accessible
            STATUS current
            DESCRIPTION
                "This object indicates the query type.
                 Options:
                 1. xponOntPortInSpecVlan(1)  - The ONT port is in the specified vlan
                 2. xponOntInSpecPort(2)      - The specified ONT port
                 3. xponOntInSpecOnt(3)       - The specified ONT
                 4. xponOntInSpecWlan(4)      - The WLAN of specified ONT
                "
            ::= { hwXponDynamicMacQueryEntry 3 }

        hwXponDynamicMacQueryPara0   OBJECT-TYPE
            SYNTAX HwXponDynamicMacQueryPara
            MAX-ACCESS not-accessible
            STATUS current
            DESCRIPTION
                "This object indicates the ONT ID, range: 0~254."
            ::= { hwXponDynamicMacQueryEntry 4 }

        hwXponDynamicMacQueryPara1   OBJECT-TYPE
            SYNTAX HwXponDynamicMacQueryPara
            MAX-ACCESS not-accessible
            STATUS current
            DESCRIPTION
                "This object indicates the type of the ONT port."
            ::= { hwXponDynamicMacQueryEntry 5 }

        hwXponDynamicMacQueryPara2   OBJECT-TYPE
            SYNTAX HwXponDynamicMacQueryPara
            MAX-ACCESS not-accessible
            STATUS current
            DESCRIPTION
                "This object indicates the port ID of the ONT."
            ::= { hwXponDynamicMacQueryEntry 6 }

        hwXponDynamicMacQueryPara3   OBJECT-TYPE
            SYNTAX HwXponDynamicMacQueryPara
            MAX-ACCESS not-accessible
            STATUS current
            DESCRIPTION
                "This object indicates the Fourth reserved Parameter of HwXponDynamicMacQueryEntry."
            ::= { hwXponDynamicMacQueryEntry 7 }

        hwXponDynamicMacAddr   OBJECT-TYPE
            SYNTAX OCTET STRING (SIZE (0..1280))
            MAX-ACCESS read-only
            STATUS current
            DESCRIPTION
                "MAC address.
                 When hwXponDynamicMacQueryType is 1 ,the MAC addresses which can include 5 MAC addresses at most, and its format is (XX.XX.XX.XX.XX.XX).
                 When hwXponDynamicMacQueryType is 2, 3 or 4, the query result contains MAC address entries with a length of 0-1280 bytes.
                 A maximum of 128 MAC addresses can be queried, each entry containing 10 bytes.
                 The queried entry is in a format of port type (1 byte)+port ID (1 byte)+VLAN ID (2 bytes)+MAC address (6 bytes),
                 where the blank field can be represented by 0, for example, 3401400000E0FC000001.
                 Range: 0-1280
                "
            ::= { hwXponDynamicMacQueryEntry 8 }

-- Table hwEponOntLineQualityStatisticTable
        hwEponOntLineQualityStatisticTable OBJECT-TYPE
            SYNTAX  SEQUENCE OF HwEponOntLineQualityStatisticEntry
            MAX-ACCESS not-accessible
            STATUS current
            DESCRIPTION
                "This table is used to query or clear the statistics for the EPON line quality.
                 The index of this table is a combination of ifIndex and hwEponDeviceOntIndex.
                "
            ::= { hwXponDeviceStatisticObjects 46 }

        hwEponOntLineQualityStatisticEntry OBJECT-TYPE
            SYNTAX HwEponOntLineQualityStatisticEntry
            MAX-ACCESS not-accessible
            STATUS current
            DESCRIPTION
                "This table is used to query or clear the statistics for the EPON line quality.
                 The index of this entry is a combination of ifIndex and hwEponDeviceOntIndex.
                "
            INDEX { ifIndex, hwEponDeviceOntIndex }
            ::= { hwEponOntLineQualityStatisticTable 1 }

        HwEponOntLineQualityStatisticEntry ::=
            SEQUENCE {
                hwEponOntLineQualityStatisticFCSError                 Counter64,
                hwEponOntLineQualityStatisticLineCodeError            Counter64,
                hwEponOntLineQualityStatisticFrameLengthInrangeError  Counter64,
                hwEponOntLineQualityStatisticLLIDMismatchError        Counter64,
                hwEponOntLineQualityStatisticclear                    INTEGER
            }

        hwEponOntLineQualityStatisticFCSError OBJECT-TYPE
            SYNTAX Counter64
            MAX-ACCESS read-only
            STATUS current
            DESCRIPTION
                "This object indicates the number of queried FCS error frames."
            ::= { hwEponOntLineQualityStatisticEntry 1 }

        hwEponOntLineQualityStatisticLineCodeError OBJECT-TYPE
            SYNTAX Counter64
            MAX-ACCESS read-only
            STATUS current
            DESCRIPTION
                "This object indicates the number of queried line coding error frames."
            ::= { hwEponOntLineQualityStatisticEntry 2 }

        hwEponOntLineQualityStatisticFrameLengthInrangeError OBJECT-TYPE
            SYNTAX Counter64
            MAX-ACCESS read-only
            STATUS current
            DESCRIPTION
                "This object indicates the number of error frames whose frames lengths are not within a valid range."
            ::= { hwEponOntLineQualityStatisticEntry 3 }

        hwEponOntLineQualityStatisticLLIDMismatchError OBJECT-TYPE
            SYNTAX Counter64
            MAX-ACCESS read-only
            STATUS current
            DESCRIPTION
                "This object indicates the number of queried error frames whose LLIDs are mismatched."
            ::= { hwEponOntLineQualityStatisticEntry 4 }

        hwEponOntLineQualityStatisticclear OBJECT-TYPE
            SYNTAX INTEGER{
                clear(1),
                invalid(-1)
            }
            MAX-ACCESS read-write
            STATUS current
            DESCRIPTION
                "This object is used to clear the statistics.
                 Options:
                 1. clear(1)                    - Indicates that clear the statistics
                 2. invalid(-1)                 - Indicates that the query fails or no information is detected
                "
            ::= { hwEponOntLineQualityStatisticEntry 5 }

-- Table hwGponDeviceGemLoopackTable
        hwGponDeviceGemLoopbackTable OBJECT-TYPE
            SYNTAX     SEQUENCE OF HwGponDeviceGemLoopbackEntry
            MAX-ACCESS not-accessible
            STATUS     current
            DESCRIPTION
                "This is the GEM port loopback table.
                 This table is used to configure and query the GEM port loopack.
                 The index of this table is a combination of ifIndex,
                 hwGponDeviceOntIndex and hwGponDeviceGemIndexObjectIndex.
                "
            ::= { hwXponDeviceLoopbackObjects 1 }

        hwGponDeviceGemLoopbackEntry OBJECT-TYPE
            SYNTAX     HwGponDeviceGemLoopbackEntry
            MAX-ACCESS not-accessible
            STATUS     current
            DESCRIPTION
                "This is the GEM port loopback table.
                 This table is used to configure and query the GEM port loopack.
                 The index of this entry is a combination of ifIndex,
                 hwGponDeviceOntIndex and hwGponDeviceGemIndexObjectIndex.
                "
            INDEX       { ifIndex, hwGponDeviceOntIndex, hwGponDeviceGemIndexObjectIndex }
            ::= { hwGponDeviceGemLoopbackTable 1 }

        HwGponDeviceGemLoopbackEntry ::=
            SEQUENCE {
                hwGponGemOltLoopbackType                        INTEGER,
                hwGponGemOntLoopbackType                        INTEGER
            }

        hwGponGemOltLoopbackType   OBJECT-TYPE
            SYNTAX     INTEGER{
                noloopback(1),
                oltremoteinnerloopback(2),
                invalid(-1)
            }
            MAX-ACCESS read-write
            STATUS     current
            DESCRIPTION
                "This object indicates the type of OLT GEM port loopback.
                 Options:
                 1. noloopback(1)               - No Loopback
                 2. oltremoteinnerloopback(2)   - From OLT GEM port to OLT NNI
                 3. invalid(-1)                 - Indicates that the query fails or no information is detected
                "
            DEFVAL { noloopback }
            ::= { hwGponDeviceGemLoopbackEntry 1 }

        hwGponGemOntLoopbackType   OBJECT-TYPE
            SYNTAX     INTEGER{
                noloopback(1),
                ontremoteinnerloopback(2),
                invalid(-1)
            }
            MAX-ACCESS read-write
            STATUS     current
            DESCRIPTION
                "This object indicates the type of ONT GEM port loopback.
                 Options:
                 1. noloopback(1)               - No Loopback
                 2. ontremoteinnerloopback(2)   - From ONT GEM port to OLT NNI
                 3. invalid(-1)                 - Indicates that the query fails or no information is detected
                "
            ::= { hwGponDeviceGemLoopbackEntry 2 }
-- end Table1 hwGponDeviceGemLoopackTable

-- Table2 hwXponDeviceOntUniLoopbackTable
        hwXponDeviceOntUniLoopbackTable OBJECT-TYPE
            SYNTAX     SEQUENCE OF HwXponDeviceOntUniLoopbackEntry
            MAX-ACCESS not-accessible
            STATUS     current
            DESCRIPTION
                "This is the ONT UNI loopback table.
                 This table is used to configure and query the ONT UNI loopack.
                 The index of this table is a combination of ifIndex, hwXponDeviceOntIndex,
                 hwXponOntUniPhyType and hwXponOntUniPhyIndex.
                 "
            ::= { hwXponDeviceLoopbackObjects 2 }

        hwXponDeviceOntUniLoopbackEntry OBJECT-TYPE
            SYNTAX     HwXponDeviceOntUniLoopbackEntry
            MAX-ACCESS not-accessible
            STATUS     current
            DESCRIPTION
                "This is the ONT UNI loopback table.
                 This table is used to configure and query the ONT UNI loopack.
                 The index of this entry is a combination of ifIndex, hwXponDeviceOntIndex,
                 hwXponOntUniPhyType and hwXponOntUniPhyIndex.
                "
            INDEX       { ifIndex, hwXponDeviceOntIndex, hwXponOntUniPhyType, hwXponOntUniPhyIndex }
            ::= { hwXponDeviceOntUniLoopbackTable 1 }

        HwXponDeviceOntUniLoopbackEntry ::=
            SEQUENCE {
                hwXponOntUniPhyType                             INTEGER,
                hwXponOntUniPhyIndex                            Integer32,
                hwXponOntUniLoopbackType                        INTEGER
            }

        hwXponOntUniPhyType   OBJECT-TYPE
            SYNTAX     INTEGER {
                t1(13),
                e1(14),
                fe(24),
                ge(34),
                vdsl(37),
                moca(46),
                eth(47),
                iphost(50)
            }
            MAX-ACCESS not-accessible
            STATUS     current
            DESCRIPTION
                "This object indicates the physical type of ONT UNI.
                 Options:
                 1. t1(13)             - T1
                 2. e1(14)             - E1
                 3. fe(24)             - FE
                 4. ge(34)             - GE
                 5. vdsl(37)           - VDSL
                 6. moca(46)           - MOCA
                 7. eth(47)            - ETH
                 8. iphost(50)         - IPHOST
                "
            ::= { hwXponDeviceOntUniLoopbackEntry 1 }

        hwXponOntUniPhyIndex   OBJECT-TYPE
            SYNTAX     Integer32
            MAX-ACCESS not-accessible
            STATUS     current
            DESCRIPTION
                "This object indicates the physical Index of ONT UNI.
                "
            ::= { hwXponDeviceOntUniLoopbackEntry 2 }

        hwXponOntUniLoopbackType   OBJECT-TYPE
            SYNTAX     INTEGER{
                noloopback(1),
                remoteinnerloopback(2),
                remoteouterloopback(4),
                invalid(-1)
            }
            MAX-ACCESS read-write
            STATUS     current
            DESCRIPTION
                "This object indicates the type of ONT UNI loopback.
                 Options:
                 1. noloopback(1)               - No Loopback
                 2. remoteinnerloopback(2)      - From ONT UNI to OLT NNI
                 3. remoteouterloopback(4)      - From ONT NNI to OLT UNI
                 4. invalid(-1)                 - Indicates that the query fails or no information is detected
                "
            ::= { hwXponDeviceOntUniLoopbackEntry 3 }
-- end Table2 hwXponDeviceOntUniLoopbackTable

-- Table3 hwXponDeviceOltLoopbackTable
        hwXponDeviceOltLoopbackTable OBJECT-TYPE
            SYNTAX     SEQUENCE OF HwXponDeviceOltLoopbackEntry
            MAX-ACCESS not-accessible
            STATUS     current
            DESCRIPTION
                "This is the OLT loopback table.
                 This table is used to configure and query the loopack based on OLT.
                 The index of this table is ifIndex.
                "
            ::= { hwXponDeviceLoopbackObjects 3 }

        hwXponDeviceOltLoopbackEntry OBJECT-TYPE
            SYNTAX     HwXponDeviceOltLoopbackEntry
            MAX-ACCESS not-accessible
            STATUS     current
            DESCRIPTION
                "This is the OLT loopback table.
                 This table is used to configure and query the loopack based on OLT.
                 The index of this entry is ifIndex.
                "
            INDEX       { ifIndex }
            ::= { hwXponDeviceOltLoopbackTable 1 }

        HwXponDeviceOltLoopbackEntry ::=
            SEQUENCE {
                hwXponOltInnerLoopback                        INTEGER,
                hwXponOltOuterLoopback                        INTEGER
            }

        hwXponOltInnerLoopback   OBJECT-TYPE
            SYNTAX     INTEGER{
                disable(1),
                enable(2),
                invalid(-1)
            }
            MAX-ACCESS read-write
            STATUS     current
            DESCRIPTION
                "This object indicates the switch of OLT PON interface inner loopback.
                 inner loopback: From OLT interface to NNI.
                 Options:
                 1. disable(1)      - Disable the switch of OLT PON interface inner loopback
                 2. enable(2)       - Enable the switch of OLT PON interface inner loopback
                 3. invalid(-1)     - Indicates that the query fails or no information is detected
                "
            DEFVAL { disable }
            ::= { hwXponDeviceOltLoopbackEntry 1 }

        hwXponOltOuterLoopback   OBJECT-TYPE
            SYNTAX     INTEGER{
                disable(1),
                enable(2),
                invalid(-1)
            }
            MAX-ACCESS read-write
            STATUS     current
            DESCRIPTION
                "This object indicates the switch of OLT PON interface outer loopback.
                 outer-loopback: From OLT interface to ONT UNI.
                 Options:
                 1. disable(1)      - Disable the switch of OLT PON interface outer loopback
                 2. enable(2)       - Enable the switch of OLT PON interface outer loopback
                 3. invalid(-1)     - Indicates that the query fails or no information is detected
                "
            DEFVAL { disable }
            ::= { hwXponDeviceOltLoopbackEntry 2 }
-- end Table3 hwXponDeviceOltLoopbackTable

-- Table4 hwXponDeviceOntExtLoopbackTable
        hwXponDeviceOntExtLoopbackTable OBJECT-TYPE
            SYNTAX     SEQUENCE OF HwXponDeviceOntExtLoopbackEntry
            MAX-ACCESS not-accessible
            STATUS     current
            DESCRIPTION
                "This is the ONT extend loopback table.
                 This table is used to configure and query the loopack based on the whole ONT.
                 The index of this table is a combination of ifIndex and hwXponDeviceOntIndex.
                "
            ::= { hwXponDeviceLoopbackObjects 4 }

        hwXponDeviceOntExtLoopbackEntry OBJECT-TYPE
            SYNTAX     HwXponDeviceOntExtLoopbackEntry
            MAX-ACCESS not-accessible
            STATUS     current
            DESCRIPTION
                "This is the ONT extend loopback table.
                 This table is used to configure and query the loopack based on the whole ONT.
                 The index of this entry is a combination of ifIndex and hwXponDeviceOntIndex.
                "
            INDEX       { ifIndex, hwXponDeviceOntIndex }
            ::= { hwXponDeviceOntExtLoopbackTable 1 }

        HwXponDeviceOntExtLoopbackEntry ::=
            SEQUENCE {
                hwXponOntNniInnerLoopback                       INTEGER,
                hwXponOntTdmLocalInnerLoopback                  INTEGER,
                hwXponOntTdmLocalOuterLoopback                  INTEGER
            }

        hwXponOntNniInnerLoopback   OBJECT-TYPE
            SYNTAX     INTEGER{
                disable(1),
                enable(2),
                unknown(-1)
            }
            MAX-ACCESS read-write
            STATUS     current
            DESCRIPTION
                "This object indicates the switch of ONT NNI inner loopback.
                 inner loopback: From ONT NNI to OLT.
                 Options:
                 1. disable(1)      - Disable the switch of ONT NNI inner loopback
                 2. enable(2)       - Enable the switch of ONT NNI inner loopback
                 3. unknown(-1)     - Indicates that the query fails or no information is detected
                "
            DEFVAL { disable }
            ::= { hwXponDeviceOntExtLoopbackEntry 1 }

        hwXponOntTdmLocalInnerLoopback   OBJECT-TYPE
            SYNTAX     INTEGER{
                disable(1),
                enable(2),
                unknown(-1)
            }
            MAX-ACCESS read-write
            STATUS     current
            DESCRIPTION
                "This object indicates the switch of ONT TDM local inner loopback.
                 Local inner loopback: From ONT to ONT UNI.
                 Options:
                 1. disable(1)      - Disable the switch of ONT TDM local inner loopback
                 2. enable(2)       - Enable the switch of ONT TDM local inner loopback
                 3. unknown(-1)     - Indicates that the query fails or no information is detected
                "
            DEFVAL { disable }
            ::= { hwXponDeviceOntExtLoopbackEntry 2 }

        hwXponOntTdmLocalOuterLoopback   OBJECT-TYPE
            SYNTAX     INTEGER{
                disable(1),
                enable(2),
                unknown(-1)
            }
            MAX-ACCESS read-write
            STATUS     current
            DESCRIPTION
                "This object indicates the Switch of ONT TDM local outer loopback.
                 Local outer loopback: From ONT to OLT.
                 Options:
                 1. disable(1)      - Disable the switch of ONT TDM local outer loopback
                 2. enable(2)       - Enable the switch of ONT TDM local outer loopback
                 3. unknown(-1)     - Indicates that the query fails or no information is detected
                "
            DEFVAL { disable }
            ::= { hwXponDeviceOntExtLoopbackEntry 3 }
-- end Table4 hwXponDeviceOntExtLoopbackTable


-- Table1 hwGponDeviceGemLineTestTable
        hwGponDeviceGemLineTestTable OBJECT-TYPE
            SYNTAX     SEQUENCE OF HwGponDeviceGemLineTestEntry
            MAX-ACCESS not-accessible
            STATUS     current
            DESCRIPTION
                "This is the GEM port line test table.
                 This table is used to do line testing from OLT to ONT GEM port.
                 The index of this table is a combination of ifIndex,
                 hwGponDeviceOntIndex and hwGponDeviceGemIndexObjectIndex.
                "
            ::= { hwXponDeviceLineTestObjects 1 }

        hwGponDeviceGemLineTestEntry OBJECT-TYPE
            SYNTAX     HwGponDeviceGemLineTestEntry
            MAX-ACCESS not-accessible
            STATUS     current
            DESCRIPTION
                "This is the GEM port line test table.
                 This table is used to do line testing from OLT to ONT GEM port.
                 The index of this entry is a combination of ifIndex,
                 hwGponDeviceOntIndex and hwGponDeviceGemIndexObjectIndex.
                "
            INDEX       { ifIndex, hwGponDeviceOntIndex, hwGponDeviceGemIndexObjectIndex }
        ::= { hwGponDeviceGemLineTestTable 1 }

        HwGponDeviceGemLineTestEntry ::=
            SEQUENCE {
                hwGponGemLineTestFrameLength                Integer32,
                hwGponGemLineTestFramesTxNum                Integer32,
                hwGponGemLineTestFramesRxNum                Integer32
            }

        hwGponGemLineTestFrameLength   OBJECT-TYPE
            SYNTAX     Integer32
            MAX-ACCESS read-write
            STATUS     current
            DESCRIPTION
                "This object indicates the frame length of GEM port line test. Range: 64-1518.
                 If the value of the ACCESS clause is 'write-only',
                 then the value of the MAX-ACCESS clause MUST be 'read-write',
                 and the DESCRIPTION clause SHALL note that reading
                 this object will result in implementation-specific results.
                "
            DEFVAL { 64 }
            ::= { hwGponDeviceGemLineTestEntry 1 }

        hwGponGemLineTestFramesTxNum   OBJECT-TYPE
            SYNTAX     Integer32
            MAX-ACCESS read-write
            STATUS     current
            DESCRIPTION
                "This object indicates the number of GEM port line test frames sending. Range: 5-100.
                If the value of the ACCESS clause is 'write-only',
                then the value of the MAX-ACCESS clause MUST be 'read-write',
                and the DESCRIPTION clause SHALL note that reading
                this object will result in implementation-specific results.
               "
            DEFVAL { 5 }
            ::= { hwGponDeviceGemLineTestEntry 2 }

        hwGponGemLineTestFramesRxNum   OBJECT-TYPE
            SYNTAX     Integer32
            MAX-ACCESS read-only
            STATUS     current
            DESCRIPTION
                "This object indicates the number of GEM port line test frames receiving. Range: 0-100."
            ::= { hwGponDeviceGemLineTestEntry 3 }
-- end Table1 hwGponDeviceGemLineTestTable

-- Table2 hwXponDeviceOntUniLineTestTable
        hwXponDeviceOntUniLineTestTable OBJECT-TYPE
            SYNTAX     SEQUENCE OF HwXponDeviceOntUniLineTestEntry
            MAX-ACCESS not-accessible
            STATUS     current
            DESCRIPTION
                "This is the ONT UNI line test table. This table is used to do line testing from OLT to ONT UNI.
                 The index of this table is a combination of ifIndex, hwXponDeviceOntIndex,
                 hwXponOntUniPhyType and hwXponOntUniPhyIndex.
                "
            ::= { hwXponDeviceLineTestObjects 2 }

        hwXponDeviceOntUniLineTestEntry OBJECT-TYPE
            SYNTAX     HwXponDeviceOntUniLineTestEntry
            MAX-ACCESS not-accessible
            STATUS     current
            DESCRIPTION
                "This is the ONT UNI line test table. This table is used to do line testing from OLT to ONT UNI.
                 The index of this entry is a combination of ifIndex, hwXponDeviceOntIndex,
                 hwXponOntUniPhyType and hwXponOntUniPhyIndex.
                "
            INDEX       { ifIndex, hwXponDeviceOntIndex, hwXponOntUniPhyType, hwXponOntUniPhyIndex }
            ::= { hwXponDeviceOntUniLineTestTable 1 }

        HwXponDeviceOntUniLineTestEntry ::=
            SEQUENCE {
                hwXponOntUniLineTestFrameLength                Integer32,
                hwXponOntUniLineTestFramesTxNum                Integer32,
                hwXponOntUniLineTestSrvFlowIndex               Integer32,
                hwXponOntUniLineTestFramesRxNum                Integer32
            }

       hwXponOntUniLineTestFrameLength   OBJECT-TYPE
            SYNTAX     Integer32
            MAX-ACCESS read-write
            STATUS     current
            DESCRIPTION
                "This object indicates the frame length of ONT UNI line test. Range: 64-1518.
                 If the value of the ACCESS clause is 'write-only',
                 then the value of the MAX-ACCESS clause MUST be 'read-write',
                 and the DESCRIPTION clause SHALL note that reading
                 this object will result in implementation-specific results.
               "
            DEFVAL { 64 }
            ::= { hwXponDeviceOntUniLineTestEntry 1 }

        hwXponOntUniLineTestFramesTxNum   OBJECT-TYPE
            SYNTAX     Integer32
            MAX-ACCESS read-write
            STATUS     current
            DESCRIPTION
                "This object indicates the number of ONT UNI line test frames sending. Range: 5-100.
                 If the value of the ACCESS clause is 'write-only',
                 then the value of the MAX-ACCESS clause MUST be 'read-write',
                 and the DESCRIPTION clause SHALL note that reading
                 this object will result in implementation-specific results.
                "
            DEFVAL { 5 }
            ::= { hwXponDeviceOntUniLineTestEntry 2 }

        hwXponOntUniLineTestSrvFlowIndex   OBJECT-TYPE
            SYNTAX     Integer32
            MAX-ACCESS read-write
            STATUS     current
            DESCRIPTION
                "This object indicates the service-port index of ONT UNI line test flow. Range: 1-32768.
                 If the value of the ACCESS clause is 'write-only',
                 then the value of the MAX-ACCESS clause MUST be 'read-write',
                 and the DESCRIPTION clause SHALL note that reading
                 this object will result in implementation-specific results.
                "
            ::= { hwXponDeviceOntUniLineTestEntry 3 }

        hwXponOntUniLineTestFramesRxNum   OBJECT-TYPE
            SYNTAX     Integer32
            MAX-ACCESS read-only
            STATUS     current
            DESCRIPTION
                "This object indicates the number of ONT UNI line test frames receiving. Range: 0-100."
            ::= { hwXponDeviceOntUniLineTestEntry 4 }
-- end Table2 hwXponDeviceOntUniLineTestTable

-- Table3 hwXponDeviceOntNniLineTestTable
        hwXponDeviceOntNniLineTestTable OBJECT-TYPE
            SYNTAX     SEQUENCE OF HwXponDeviceOntNniLineTestEntry
            MAX-ACCESS not-accessible
            STATUS     current
            DESCRIPTION
                "This is the ONT NNI line test table.
                 This table is used to do line testing from OLT to ONT NNI.
                 The index of this table is a combination of ifIndex and hwXponDeviceOntIndex.
                "
            ::= { hwXponDeviceLineTestObjects 3 }

        hwXponDeviceOntNniLineTestEntry OBJECT-TYPE
            SYNTAX     HwXponDeviceOntNniLineTestEntry
            MAX-ACCESS not-accessible
            STATUS     current
            DESCRIPTION
                "This is the ONT NNI line test table.
                 This table is used to do line testing from OLT to ONT NNI.
                 The index of this entry is a combination of ifIndex and hwXponDeviceOntIndex.
                "
            INDEX       { ifIndex, hwXponDeviceOntIndex }
            ::= { hwXponDeviceOntNniLineTestTable 1 }

        HwXponDeviceOntNniLineTestEntry ::=
            SEQUENCE {
                hwXponOntNniLineTestFrameLength                Integer32,
                hwXponOntNniLineTestFramesTxNum                Integer32,
                hwXponOntNniLineTestFramesRxNum                Integer32
            }

        hwXponOntNniLineTestFrameLength   OBJECT-TYPE
            SYNTAX     Integer32
            MAX-ACCESS read-write
            STATUS     current
            DESCRIPTION
                "This object indicates the frame length of ONT NNI line test. Range: 64-1518.
                 If the value of the ACCESS clause is 'write-only',
                 then the value of the MAX-ACCESS clause MUST be 'read-write',
                 and the DESCRIPTION clause SHALL note that reading
                 this object will result in implementation-specific results.
                "
            DEFVAL { 64 }
            ::= { hwXponDeviceOntNniLineTestEntry 1 }

        hwXponOntNniLineTestFramesTxNum   OBJECT-TYPE
            SYNTAX     Integer32
            MAX-ACCESS read-write
            STATUS     current
            DESCRIPTION
                "This object indicates the number of ONT NNI line test frames sending. Range: 5-100.
                 If the value of the ACCESS clause is 'write-only',
                 then the value of the MAX-ACCESS clause MUST be 'read-write',
                 and the DESCRIPTION clause SHALL note that reading
                 this object will result in implementation-specific results.
                "
            DEFVAL { 5 }
            ::= { hwXponDeviceOntNniLineTestEntry 2 }

        hwXponOntNniLineTestFramesRxNum   OBJECT-TYPE
            SYNTAX     Integer32
            MAX-ACCESS read-only
            STATUS     current
            DESCRIPTION
                "This object indicates the number of ONT NNI line test frames receiving. Range: 0-100."
        ::= { hwXponDeviceOntNniLineTestEntry 3 }
-- end Table3 hwGponDeviceOntUniLineTestTable

--Table hwGponTDMPortStatisticTable <add by w00113729 2009-03-23>
        hwGponTDMPortStatisticTable OBJECT-TYPE
            SYNTAX      SEQUENCE OF HwGponTDMPortStatisticEntry
            MAX-ACCESS  not-accessible
            STATUS      current
            DESCRIPTION
                "This is the E1 perform monitor statistic table.
                 The index of this table is a combination of ifIndex, hwGponTDMPortStatisticOntIndex,
                 hwGponTDMPortStatisticOntPhyType and hwGponTDMPortStatisticOntPhyIndex.
                "
            ::= { hwXponDeviceStatisticObjects 45 }

        hwGponTDMPortStatisticEntry OBJECT-TYPE
            SYNTAX      HwGponTDMPortStatisticEntry
            MAX-ACCESS  not-accessible
            STATUS      current
            DESCRIPTION
                "This is the E1 perform monitor statistic table.
                 The index of this entry is a combination of ifIndex, hwGponTDMPortStatisticOntIndex,
                 hwGponTDMPortStatisticOntPhyType and hwGponTDMPortStatisticOntPhyIndex.
                "
            INDEX { ifIndex, hwGponTDMPortStatisticOntIndex, hwGponTDMPortStatisticOntPhyType,
                    hwGponTDMPortStatisticOntPhyIndex }
            ::= { hwGponTDMPortStatisticTable 1 }

        HwGponTDMPortStatisticEntry ::=
            SEQUENCE {
                hwGponTDMPortStatisticOntIndex    Integer32,
                hwGponTDMPortStatisticOntPhyType  Integer32,
                hwGponTDMPortStatisticOntPhyIndex Integer32,
                hwGponTDMPortStatisticDataES      Gauge32,
                hwGponTDMPortStatisticDataSES     Gauge32,
                hwGponTDMPortStatisticDataUAS     Gauge32,
                hwGponTDMPortStatisticDataEFS     Gauge32,
                hwGponTDMPortStatisticClear       INTEGER
            }

        hwGponTDMPortStatisticOntIndex OBJECT-TYPE
            SYNTAX      Integer32
            MAX-ACCESS  not-accessible
            STATUS      current
            DESCRIPTION
                "This object indicates the ONT index."
            ::={ hwGponTDMPortStatisticEntry 1 }

        hwGponTDMPortStatisticOntPhyType OBJECT-TYPE
            SYNTAX      Integer32
            MAX-ACCESS  not-accessible
            STATUS      current
            DESCRIPTION
                "This object indicates the port type of the ONT."
            ::={ hwGponTDMPortStatisticEntry 2 }

        hwGponTDMPortStatisticOntPhyIndex OBJECT-TYPE
            SYNTAX      Integer32
            MAX-ACCESS  not-accessible
            STATUS      current
            DESCRIPTION
                "This object indicates the port index of the ONT."
            ::={ hwGponTDMPortStatisticEntry 3 }

        hwGponTDMPortStatisticDataES OBJECT-TYPE
            SYNTAX      Gauge32
            MAX-ACCESS  read-only
            STATUS      current
            DESCRIPTION
                "This object indicates the statistic of the errored seconds."
            ::={ hwGponTDMPortStatisticEntry 4 }

        hwGponTDMPortStatisticDataSES OBJECT-TYPE
            SYNTAX      Gauge32
            MAX-ACCESS  read-only
            STATUS      current
            DESCRIPTION
                "This object indicates the statistic of the serverly erroeds."
            ::={ hwGponTDMPortStatisticEntry 5 }

        hwGponTDMPortStatisticDataUAS OBJECT-TYPE
            SYNTAX      Gauge32
            MAX-ACCESS  read-only
            STATUS      current
            DESCRIPTION
                "This object indicates the statistic of the unavailable seconds."
            ::={ hwGponTDMPortStatisticEntry 6 }

        hwGponTDMPortStatisticDataEFS OBJECT-TYPE
            SYNTAX      Gauge32
            MAX-ACCESS  read-only
            STATUS      current
            DESCRIPTION
                "This object indicates the statistic of the error free Seconds."
            ::={ hwGponTDMPortStatisticEntry 7 }
        hwGponTDMPortStatisticClear  OBJECT-TYPE
            SYNTAX INTEGER{
                clear(1),
                invalid(-1)
            }
            MAX-ACCESS read-write
            STATUS current
            DESCRIPTION
                "This object is used to clear the statistics.
                 Options:
                 1. clear(1)                     - Indicates that clear the statistics
                 2. invalid(-1)                 - Indicates that the query fails or no information is detected
                "
            ::= { hwGponTDMPortStatisticEntry 20 }

-- Table : HwEponOltChannelEthernetStatisticTable
        hwEponOltChannelEthernetStatisticTable OBJECT-TYPE
            SYNTAX     SEQUENCE OF HwEponOltChannelEthernetStatisticEntry
            MAX-ACCESS not-accessible
            STATUS     current
            DESCRIPTION
                "The OLT channel ETH statisitcs table.
                 The index of this table is a combination of ifIndex and hwEponOltChannelId."
            ::= {  hwXponDeviceStatisticObjects 47 }

        hwEponOltChannelEthernetStatisticEntry OBJECT-TYPE
            SYNTAX     HwEponOltChannelEthernetStatisticEntry
            MAX-ACCESS not-accessible
            STATUS     current
            DESCRIPTION
                "The OLT channel ETH statisitcs table.
                 The index of this entry is a combination of ifIndex and hwEponOltChannelId."
            INDEX       { ifIndex, hwEponOltChannelId }
            ::= { hwEponOltChannelEthernetStatisticTable 1 }

        HwEponOltChannelEthernetStatisticEntry ::=
            SEQUENCE {
                hwEponOltChannelId                                               INTEGER,
                hwEponOltChannelEthernetStatisticRcvOctets                       Counter64,
                hwEponOltChannelEthernetStatisticRcvFrames                       Counter64,
                hwEponOltChannelEthernetStatisticRcvBroadcastFrames              Counter64,
                hwEponOltChannelEthernetStatisticRcvMulticastFrames              Counter64,
                hwEponOltChannelEthernetStatisticRcvUnicastFrames                Counter64,
                hwEponOltChannelEthernetStatisticRcvOversizeFrames               Counter64,
                hwEponOltChannelEthernetStatisticRcvUndersizeFrames              Counter64,
                hwEponOltChannelEthernetStatisticRcvCrcErrorFrames               Counter64,
                hwEponOltChannelEthernetStatisticRcvLlidErrorFrames              Counter64,
                hwEponOltChannelEthernetStatisticRcvUngrantedFrames              Counter64,
                hwEponOltChannelEthernetStatisticSendOctets                      Counter64,
                hwEponOltChannelEthernetStatisticSendFrames                      Counter64,
                hwEponOltChannelEthernetStatisticSendBroadcastFrames             Counter64,
                hwEponOltChannelEthernetStatisticSendMulticastFrames             Counter64,
                hwEponOltChannelEthernetStatisticSendUnicastFrames               Counter64
            }
        hwEponOltChannelId   OBJECT-TYPE
            SYNTAX     INTEGER{
                oneGbitChannel(1),
                tenGbitChannel(2),
                twoGbitChannel(3),
                invalid(-1)
            }
            MAX-ACCESS   not-accessible
            STATUS      current
            DESCRIPTION
                "This object indicates the channel number.
                 Options:
                 1. oneGbitChannel(1)           - Indicates that the channel number is 1G
                 2. tenGbitChannel(2)           - Indicates that the channel number is 10G
                 3. twoGbitChannel(3)           - Indicates that the channel number is 2G
                 4. invalid(-1)                 - Indicates that the query fails or no information is detected
                "
            ::= { hwEponOltChannelEthernetStatisticEntry 1 }

        hwEponOltChannelEthernetStatisticRcvOctets  OBJECT-TYPE
            SYNTAX     Counter64
            MAX-ACCESS   read-only
            STATUS      current
            DESCRIPTION
                "This object indicates the received octets."
            ::= { hwEponOltChannelEthernetStatisticEntry 2 }

        hwEponOltChannelEthernetStatisticRcvFrames  OBJECT-TYPE
            SYNTAX     Counter64
            MAX-ACCESS   read-only
            STATUS      current
            DESCRIPTION
                "This object indicates the received frames."
            ::= { hwEponOltChannelEthernetStatisticEntry 3 }

        hwEponOltChannelEthernetStatisticRcvBroadcastFrames  OBJECT-TYPE
            SYNTAX     Counter64
            MAX-ACCESS   read-only
            STATUS      current
            DESCRIPTION
                "This object indicates the received broadcast frames."
            ::= { hwEponOltChannelEthernetStatisticEntry 4 }

        hwEponOltChannelEthernetStatisticRcvMulticastFrames  OBJECT-TYPE
            SYNTAX     Counter64
            MAX-ACCESS   read-only
            STATUS      current
            DESCRIPTION
                "This object indicates the received multicast frames."
            ::= { hwEponOltChannelEthernetStatisticEntry 5 }

        hwEponOltChannelEthernetStatisticRcvUnicastFrames  OBJECT-TYPE
            SYNTAX     Counter64
            MAX-ACCESS   read-only
            STATUS      current
            DESCRIPTION
                "This object indicates the received unicast frames."
            ::= { hwEponOltChannelEthernetStatisticEntry 6 }

        hwEponOltChannelEthernetStatisticRcvOversizeFrames  OBJECT-TYPE
            SYNTAX     Counter64
            MAX-ACCESS   read-only
            STATUS      current
            DESCRIPTION
                "This object indicates the received oversize frames."
            ::= { hwEponOltChannelEthernetStatisticEntry 7 }

        hwEponOltChannelEthernetStatisticRcvUndersizeFrames  OBJECT-TYPE
            SYNTAX     Counter64
            MAX-ACCESS   read-only
            STATUS      current
            DESCRIPTION
                "This object indicates the received undersize frames."
            ::= { hwEponOltChannelEthernetStatisticEntry 8 }

        hwEponOltChannelEthernetStatisticRcvCrcErrorFrames  OBJECT-TYPE
            SYNTAX     Counter64
            MAX-ACCESS   read-only
            STATUS      current
            DESCRIPTION
                "This object indicates the received CRC error frames."
            ::= { hwEponOltChannelEthernetStatisticEntry 9 }

        hwEponOltChannelEthernetStatisticRcvLlidErrorFrames  OBJECT-TYPE
            SYNTAX     Counter64
            MAX-ACCESS   read-only
            STATUS      current
            DESCRIPTION
                "This object indicates the received LLID error frames."
            ::= { hwEponOltChannelEthernetStatisticEntry 10 }

        hwEponOltChannelEthernetStatisticRcvUngrantedFrames  OBJECT-TYPE
            SYNTAX     Counter64
            MAX-ACCESS   read-only
            STATUS      current
            DESCRIPTION
                "This object indicates the received ungranted frames."
            ::= { hwEponOltChannelEthernetStatisticEntry 11 }

        hwEponOltChannelEthernetStatisticSendOctets   OBJECT-TYPE
            SYNTAX     Counter64
            MAX-ACCESS   read-only
            STATUS      current
            DESCRIPTION
                "This object indicates the sent octets."
            ::= { hwEponOltChannelEthernetStatisticEntry 12 }

        hwEponOltChannelEthernetStatisticSendFrames  OBJECT-TYPE
            SYNTAX     Counter64
            MAX-ACCESS   read-only
            STATUS      current
            DESCRIPTION
                "This object indicates the sent frames."
            ::= { hwEponOltChannelEthernetStatisticEntry 13 }

        hwEponOltChannelEthernetStatisticSendBroadcastFrames  OBJECT-TYPE
            SYNTAX     Counter64
            MAX-ACCESS   read-only
            STATUS      current
            DESCRIPTION
                "This object indicates the sent broadcast frames."
            ::= { hwEponOltChannelEthernetStatisticEntry 14 }

        hwEponOltChannelEthernetStatisticSendMulticastFrames  OBJECT-TYPE
            SYNTAX     Counter64
            MAX-ACCESS   read-only
            STATUS      current
            DESCRIPTION
                "This object indicates the sent multicast frames."
            ::= { hwEponOltChannelEthernetStatisticEntry 15 }

        hwEponOltChannelEthernetStatisticSendUnicastFrames  OBJECT-TYPE
            SYNTAX     Counter64
            MAX-ACCESS   read-only
            STATUS      current
            DESCRIPTION
                "This object indicates the sent unicast frames."
            ::= { hwEponOltChannelEthernetStatisticEntry 16 }

--Table hwGponDeviceUnboundGemPortQueryTable
        hwGponDeviceUnboundGemPortQueryTable OBJECT-TYPE
            SYNTAX      SEQUENCE OF HwGponDeviceUnboundGemPortQueryEntry
            MAX-ACCESS  not-accessible
            STATUS      current
            DESCRIPTION
                "This is the unbound GEM port query table in the profile mode.
                 The index of this table is a combination of ifIndex and hwGponDeviceUnboundGemPortId.
                "
            ::= { hwXponDeviceControlObjects 140 }

        hwGponDeviceUnboundGemPortQueryEntry OBJECT-TYPE
            SYNTAX    HwGponDeviceUnboundGemPortQueryEntry
            MAX-ACCESS  not-accessible
            STATUS      current
            DESCRIPTION
                "This is the unbound GEM port query table in the profile mode.
                 The index of this entry is a combination of ifIndex and hwGponDeviceUnboundGemPortId.
                "
            INDEX   { ifIndex, hwGponDeviceUnboundGemPortId }
            ::= { hwGponDeviceUnboundGemPortQueryTable 1 }

        HwGponDeviceUnboundGemPortQueryEntry ::=
            SEQUENCE {
                hwGponDeviceUnboundGemPortId                       Integer32,
                hwGponDeviceUnboundGemPortServiceType              INTEGER,
                hwGponDeviceUnboundGemPortEncrypt                  INTEGER,
                hwGponDeviceUnboundGemPortCascade                  INTEGER,
                hwGponDeviceUnboundGemPortDescription              OCTET STRING,
                hwGponDeviceUnboundGemPortEntryStatus              RowStatus
            }

        hwGponDeviceUnboundGemPortId  OBJECT-TYPE
            SYNTAX   Integer32
            MAX-ACCESS  not-accessible
            STATUS      current
            DESCRIPTION
                "This object indicates the unbound GEM port ID."
            ::= { hwGponDeviceUnboundGemPortQueryEntry 1 }

        hwGponDeviceUnboundGemPortServiceType  OBJECT-TYPE
            SYNTAX  INTEGER{
                tdm(1),
                omci(2),
                eth(3),
                invalid(-1)
            }
            MAX-ACCESS    read-only
            STATUS    current
            DESCRIPTION
                "This object indicates the carried service type of the unbound GEM port.
                 Options:
                 1. tdm(1)               - TDM
                 2. omci(2)              - OMCI
                 3. eth(3)               - ETH
                 4. invalid(-1)          - Indicates that the query fails or no information is detected
                "
            ::= { hwGponDeviceUnboundGemPortQueryEntry 2 }

        hwGponDeviceUnboundGemPortEncrypt   OBJECT-TYPE
            SYNTAX  INTEGER{
                on(1),
                off(2),
                invalid(-1)
            }
            MAX-ACCESS    read-only
            STATUS    current
            DESCRIPTION
                "This object indicates the downstream encryption switch of the unbound GEM port.
                 Options:
                 1. on(1)                       - Indicates that the downstream encryption switch of the unbound GEM port is on
                 2. off(2)                      - Indicates that the downstream encryption switch of the unbound GEM port is off
                 3. invalid(-1)                 - Indicates that the query fails or no information is detected
                "
            ::= { hwGponDeviceUnboundGemPortQueryEntry 3 }

        hwGponDeviceUnboundGemPortCascade   OBJECT-TYPE
            SYNTAX  INTEGER{
                on(1),
                off(2),
                invalid(-1)
            }
            MAX-ACCESS    read-only
            STATUS    current
            DESCRIPTION
                "This object indicates the subtending attribute of the unbound GEM port.
                 Options:
                 1. on(1)                       - Indicates that the subtending attribute of the unbound GEM port is on
                 2. off(2)                      - Indicates that the subtending attribute of the unbound GEM port is off
                 3. invalid(-1)                 - Indicates that the query fails or no information is detected
                "
            ::= { hwGponDeviceUnboundGemPortQueryEntry 4 }

        hwGponDeviceUnboundGemPortDescription OBJECT-TYPE
            SYNTAX    OCTET STRING (SIZE (1..64))
            MAX-ACCESS  read-only
            STATUS      current
            DESCRIPTION
                "This object indicates the unbound GEM port description."
            ::= { hwGponDeviceUnboundGemPortQueryEntry 5 }

        hwGponDeviceUnboundGemPortEntryStatus OBJECT-TYPE
            SYNTAX   RowStatus
            MAX-ACCESS  read-create
            STATUS      current
            DESCRIPTION
                "The hwGponDeviceUnboundGemPortEntryStatus is used to create a new row
                 or to modify or delete an existing row in this table.
                 Options:
                 1. createAndGo(4) -create a new instance of a conceptual row
                 2. destroy(6)     -delete the instances associated with an existing conceptual row
                "
            ::= { hwGponDeviceUnboundGemPortQueryEntry 6 }

--Table hwGponDeviceOntGemPortBindTable <add by z00130281 2009-04-16>
        hwGponDeviceOntGemPortBindTable OBJECT-TYPE
            SYNTAX     SEQUENCE OF HwGponDeviceOntGemPortBindEntry
            MAX-ACCESS not-accessible
            STATUS     current
            DESCRIPTION
                "This is ONT GEM port configuration table. This table is used to
                 configure the mapping relation between the T-CONT and GEM port of an ONT.
                 The index of this table is a combination of ifIndex and hwGponDeviceOntGemPortBindGemPortId.
                "
            ::= { hwXponDeviceControlObjects 141 }

        hwGponDeviceOntGemPortBindEntry OBJECT-TYPE
            SYNTAX     HwGponDeviceOntGemPortBindEntry
            MAX-ACCESS not-accessible
            STATUS     current
            DESCRIPTION
                "This is ONT GEM port configuration table. This table is used to
                 configure the mapping relation between the T-CONT and GEM port of an ONT.
                 The index of this entry is a combination of ifIndex and hwGponDeviceOntGemPortBindGemPortId.
                "
            INDEX       { ifIndex, hwGponDeviceOntGemPortBindGemPortId }
            ::= { hwGponDeviceOntGemPortBindTable 1 }

        HwGponDeviceOntGemPortBindEntry ::=
            SEQUENCE {
                hwGponDeviceOntGemPortBindGemPortId          Integer32,
                hwGponDeviceOntGemPortBindOntId              Integer32,
                hwGponDeviceOntGemPortBindTcontId            Integer32,
                hwGponDeviceOntGemPortBindUpPQIndex          Integer32,
                hwGponDeviceOntGemPortBindTrafficTableId     Integer32,
                hwGponDeviceOntGemPortBindEntryStatus        RowStatus,
                hwGponDeviceOntGemPortBindDownPQIndex        Integer32,
                hwGponDeviceOntGemPortBindTrafficTableName   OCTET STRING
            }

        hwGponDeviceOntGemPortBindGemPortId OBJECT-TYPE
            SYNTAX   Integer32
            MAX-ACCESS  not-accessible
            STATUS      current
            DESCRIPTION
                "This object indicates the ONT GEM Port ID."
            ::= { hwGponDeviceOntGemPortBindEntry 1 }

        hwGponDeviceOntGemPortBindOntId OBJECT-TYPE
            SYNTAX   Integer32
            MAX-ACCESS  read-write
            STATUS      current
            DESCRIPTION
                "This object indicates the ONT ID.
                 If the value of the ACCESS clause is 'write-only',
                 then the value of the MAX-ACCESS clause MUST be 'read-write',
                 and the DESCRIPTION clause SHALL note that reading
                 this object will result in implementation-specific results.
                "
            ::= { hwGponDeviceOntGemPortBindEntry 2 }

        hwGponDeviceOntGemPortBindTcontId OBJECT-TYPE
            SYNTAX   Integer32 (0..127)
            MAX-ACCESS  read-write
            STATUS      current
            DESCRIPTION
                "This object indicates the T-CONT ID.
                 If the value of the ACCESS clause is 'write-only',
                 then the value of the MAX-ACCESS clause MUST be 'read-write',
                 and the DESCRIPTION clause SHALL note that reading
                 this object will result in implementation-specific results.
                "
            ::= { hwGponDeviceOntGemPortBindEntry 3 }

        hwGponDeviceOntGemPortBindUpPQIndex OBJECT-TYPE
            SYNTAX   Integer32 (0..7)
            MAX-ACCESS   read-write
            STATUS       current
            DESCRIPTION
                "This object indicates the up stream priority-queue index.
                 If the value of the ACCESS clause is 'write-only',
                 then the value of the MAX-ACCESS clause MUST be 'read-write',
                 and the DESCRIPTION clause SHALL note that reading
                 this object will result in implementation-specific results.
                "
            ::= { hwGponDeviceOntGemPortBindEntry 4 }

        hwGponDeviceOntGemPortBindTrafficTableId OBJECT-TYPE
            SYNTAX   Integer32 (1..1024)
            MAX-ACCESS  read-write
            STATUS      current
            DESCRIPTION
                "This object indicates the traffic table id of the GEM port.
                 If the value of the ACCESS clause is 'write-only',
                 then the value of the MAX-ACCESS clause MUST be 'read-write',
                 and the DESCRIPTION clause SHALL note that reading
                 this object will result in implementation-specific results.
                "
            ::= { hwGponDeviceOntGemPortBindEntry 5 }

        hwGponDeviceOntGemPortBindEntryStatus OBJECT-TYPE
            SYNTAX   RowStatus
            MAX-ACCESS  read-create
            STATUS      current
            DESCRIPTION
                "The hwGponDeviceOntGemPortBindEntryStatus is used to create a new row
                 or to modify or delete an existing row in this table.
                 Options:
                 1. createAndGo(4) -create a new instance of a conceptual row
                 2. destroy(6)     -delete the instances associated with an existing conceptual row
                "
            ::= { hwGponDeviceOntGemPortBindEntry 6 }

        hwGponDeviceOntGemPortBindDownPQIndex OBJECT-TYPE
            SYNTAX Integer32 (-1 | 0..7 | 254)
            MAX-ACCESS   read-write
            STATUS       current
            DESCRIPTION
                "This object indicates the down stream priority-queue index.
                 0..7: Down Stream PQ index.
                 254 : Apaptive, Gemport Down Stream PQ is decided by ont.
                  -1  : Default Value.Gemport Down Stream PQ is decided by olt.
                "
            ::= { hwGponDeviceOntGemPortBindEntry 7 }

        hwGponDeviceOntGemPortBindTrafficTableName OBJECT-TYPE
            SYNTAX   OCTET STRING  (SIZE (0..32))
            MAX-ACCESS   read-write
            STATUS       current
            DESCRIPTION
                "This object indicates the traffic table name of the GEM port."
            ::= { hwGponDeviceOntGemPortBindEntry 8 }

--Table hwGponDeviceLineProfTcontRefTable <add by x00134267 2009-08-03>
        hwGponDeviceLineProfTcontRefTable OBJECT-TYPE
            SYNTAX     SEQUENCE OF HwGponDeviceLineProfTcontRefEntry
            MAX-ACCESS not-accessible
            STATUS     current
            DESCRIPTION
                "This is TCONTS configuration table in gpon mode.
                 This table is used to configure these TCONTS which are not binded dba-profile.
                 The index of this table is a combination of ifIndex,
                 hwGponDeviceOntIndex and hwGponDeviceLineProfTcontRefIndex.
                "
            ::= { hwXponDeviceControlObjects 142 }

        hwGponDeviceLineProfTcontRefEntry OBJECT-TYPE
            SYNTAX     HwGponDeviceLineProfTcontRefEntry
            MAX-ACCESS not-accessible
            STATUS     current
            DESCRIPTION
                "This is TCONTS configuration table in gpon mode.
                 This table is used to configure these TCONTS which are not binded dba-profile.
                 The index of this entry is a combination of ifIndex,
                 hwGponDeviceOntIndex and hwGponDeviceLineProfTcontRefIndex.
                "
            INDEX       { ifIndex, hwGponDeviceOntIndex, hwGponDeviceLineProfTcontRefIndex }
            ::= { hwGponDeviceLineProfTcontRefTable 1 }

        HwGponDeviceLineProfTcontRefEntry ::=
            SEQUENCE {
                hwGponDeviceLineProfTcontRefIndex                  Integer32,
                hwGponDeviceLineProfTcontName                      OCTET STRING,
                hwGponDeviceLineProfAllocId                        Integer32,
                hwGponDeviceLineProfTcontRefEntryStatus            RowStatus
            }

        hwGponDeviceLineProfTcontRefIndex OBJECT-TYPE
            SYNTAX   Integer32
            MAX-ACCESS  not-accessible
            STATUS      current
            DESCRIPTION
                "This object indicates the TCONT Index."
            ::= { hwGponDeviceLineProfTcontRefEntry 1 }

        hwGponDeviceLineProfTcontName OBJECT-TYPE
            SYNTAX   OCTET STRING (SIZE (1..33))
            MAX-ACCESS  read-write
            STATUS      current
            DESCRIPTION
                "This object indicates the dba-profile name."
            ::= { hwGponDeviceLineProfTcontRefEntry 2 }

        hwGponDeviceLineProfAllocId OBJECT-TYPE
            SYNTAX   Integer32
            MAX-ACCESS   read-only
            STATUS       current
            DESCRIPTION
                "This object indicates the alloc ID."
            ::= { hwGponDeviceLineProfTcontRefEntry 3 }

        hwGponDeviceLineProfTcontRefEntryStatus OBJECT-TYPE
            SYNTAX   RowStatus
            MAX-ACCESS  read-create
            STATUS      current
            DESCRIPTION
                "The hwGponDeviceLineProfTcontRefEntryStatus is used to create a new row
                 or to modify or delete an existing row in this table.
                 Options:
                 1. createAndGo(4) -create a new instance of a conceptual row
                 2. destroy(6)     -delete the instances associated with an existing conceptual row
                "
            ::= { hwGponDeviceLineProfTcontRefEntry 4 }

--table hwXponDeviceRogueOntTable
        hwXponDeviceRogueOntTable OBJECT-TYPE
            SYNTAX SEQUENCE OF HwXponDeviceRogueOntEntry
            MAX-ACCESS not-accessible
            STATUS current
            DESCRIPTION
                "This is the rogue ONT list table. The index of this table is ifIndex."
            ::= { hwXponDeviceControlObjects 143 }

        hwXponDeviceRogueOntEntry OBJECT-TYPE
            SYNTAX HwXponDeviceRogueOntEntry
            MAX-ACCESS not-accessible
            STATUS current
            DESCRIPTION
                "This is the rogue ONT list table. The index of this entry is ifIndex."
            INDEX { ifIndex }
            ::= { hwXponDeviceRogueOntTable 1 }

        HwXponDeviceRogueOntEntry ::=
            SEQUENCE {
                hwXponDeviceRogueOnt                        OntList
            }

        hwXponDeviceRogueOnt  OBJECT-TYPE
            SYNTAX     OntList
            MAX-ACCESS   read-only
            STATUS      current
            DESCRIPTION
                "This object indicates the rogue ont list."
            ::= { hwXponDeviceRogueOntEntry 1 }
-- hwXponDeviceRogueOntTable  end

-- hwEponDeviceOntLlidTable
      hwEponDeviceOntLlidTable OBJECT-TYPE
          SYNTAX     SEQUENCE OF HwEponDeviceOntLlidEntry
          MAX-ACCESS not-accessible
          STATUS     current
          DESCRIPTION
                   "This is the ONT LLID related configuration table.
                    The index of this table is a combination of ifIndex, hwEponDeviceOntIndex and hwEponDeviceOntLlidIndex."
          ::= { hwXponDeviceControlObjects 144 }

      hwEponDeviceOntLlidEntry OBJECT-TYPE
          SYNTAX     HwEponDeviceOntLlidEntry
          MAX-ACCESS not-accessible
          STATUS     current
          DESCRIPTION
                   "This is the ONT LLID related configuration table.
                    The index of this entry is a combination of ifIndex, hwEponDeviceOntIndex and hwEponDeviceOntLlidIndex."
          INDEX       { ifIndex, hwEponDeviceOntIndex, hwEponDeviceOntLlidIndex}
          ::= { hwEponDeviceOntLlidTable 1 }

       HwEponDeviceOntLlidEntry ::=
          SEQUENCE {
                    hwEponDeviceOntLlidIndex                    Integer32,
                    hwEponDeviceOntLlidValue                    Integer32,
                    hwEponDeviceOntLlidDbaProfileName           OCTET STRING,
                    hwEponDeviceOntLlidCarTrafficTableId        Integer32,
                    hwEponDeviceOntLlidCarTrafficTableName      OCTET STRING
                   }

       hwEponDeviceOntLlidIndex OBJECT-TYPE
           SYNTAX      Integer32 (0..1023)
           MAX-ACCESS  not-accessible
           STATUS      current
           DESCRIPTION
                   "This object indicates the EPON line profile LLID config Llid index."
           ::= { hwEponDeviceOntLlidEntry 1 }

      hwEponDeviceOntLlidValue OBJECT-TYPE
           SYNTAX      Integer32 (-1 | 0..65535)
           MAX-ACCESS  read-only
           STATUS      current
           DESCRIPTION
                   "This object indicates the value of Logical Link Identifier."
           ::= { hwEponDeviceOntLlidEntry 2 }

       hwEponDeviceOntLlidDbaProfileName OBJECT-TYPE
           SYNTAX      OCTET STRING (SIZE (0..33))
           MAX-ACCESS  read-write
           STATUS      current
           DESCRIPTION
                   "This object indicates the name of the DBA profile."
           ::= { hwEponDeviceOntLlidEntry 3 }

       hwEponDeviceOntLlidCarTrafficTableId OBJECT-TYPE
           SYNTAX      Integer32 (1..1024 | 65534)
           MAX-ACCESS  read-write
           STATUS      current
           DESCRIPTION
                   "This object indicates the ONT Llid car profile id (1~1024, 0xfffe-unconcern)."
           ::= { hwEponDeviceOntLlidEntry 4 }

       hwEponDeviceOntLlidCarTrafficTableName OBJECT-TYPE
           SYNTAX      OCTET STRING  (SIZE (0..32))
           MAX-ACCESS  read-write
           STATUS      current
           DESCRIPTION
                   "This object indicates the ONT Llid car profile name."
           ::= { hwEponDeviceOntLlidEntry 5 }
-- hwEponDeviceOntLlidTable end

-- hwEponDeviceOntPortVlanTable
      hwEponDeviceOntPortVlanTable OBJECT-TYPE
          SYNTAX     SEQUENCE OF HwEponDeviceOntPortVlanEntry
          MAX-ACCESS not-accessible
          STATUS     current
          DESCRIPTION
                   "This is the ONT port vlan configuration table.
                    The index of this table is a combination of ifIndex, hwEponOntPortVlanCfgOntPhyType, hwEponDeviceOntIndex,
                    hwEponOntPortVlanCfgOntPhyIndex and hwEponOntPortVlanCfgCVlan."
          ::= { hwXponDeviceControlObjects 145 }

      hwEponDeviceOntPortVlanEntry OBJECT-TYPE
          SYNTAX     HwEponDeviceOntPortVlanEntry
          MAX-ACCESS not-accessible
          STATUS     current
          DESCRIPTION
                   "This is the ONT port vlan configuration table.
                    The index of this entry is a combination of ifIndex, hwEponOntPortVlanCfgOntPhyType, hwEponDeviceOntIndex,
                    hwEponOntPortVlanCfgOntPhyIndex and hwEponOntPortVlanCfgCVlan."
          INDEX       { ifIndex, hwEponDeviceOntIndex, hwEponOntPortVlanCfgOntPhyType,
                        hwEponOntPortVlanCfgOntPhyIndex, hwEponOntPortVlanCfgCVlan }
          ::= { hwEponDeviceOntPortVlanTable 1 }

       HwEponDeviceOntPortVlanEntry ::=
          SEQUENCE {
                    hwEponOntPortVlanCfgOntPhyType            INTEGER,
                    hwEponOntPortVlanCfgOntPhyIndex           Integer32,
                    hwEponOntPortVlanCfgCVlan                 Integer32,
                    hwEponOntPortVlanCfgSVlan                 Integer32,
                    hwEponOntPortVlanCfgType                  INTEGER,
                    hwEponOntPortVlanCfgRowstatus             RowStatus
                   }

       hwEponOntPortVlanCfgOntPhyType OBJECT-TYPE
           SYNTAX      INTEGER
               {
                 t1(13),
                 e1(14),
                 fe(24),
                 ge(34),
                 moca(46),
                 eth(47),
                 iphost(50)
                }
           MAX-ACCESS  not-accessible
           STATUS      current
           DESCRIPTION
                   "This object indicates the port type of the ONT.
                    Options:
                    1. t1(13)             - T1
                    2. e1(14)             - E1
                    3. fe(24)             - FE
                    4. ge(34)             - GE
                    5. moca(46)           - MOCA
                    6. eth(47)            - ETH
                    7. iphost(50)         - IPHOST
                   "
           ::= { hwEponDeviceOntPortVlanEntry 1 }
       hwEponOntPortVlanCfgOntPhyIndex OBJECT-TYPE
           SYNTAX      Integer32
           MAX-ACCESS  not-accessible
           STATUS      current
           DESCRIPTION
                   "This object indicates the port index of the ONT."
           ::= { hwEponDeviceOntPortVlanEntry 2 }
       hwEponOntPortVlanCfgCVlan OBJECT-TYPE
           SYNTAX      Integer32 (1..4094 | 65534)
           MAX-ACCESS  not-accessible
           STATUS      current
           DESCRIPTION
                   "This object indicates the epon ont port customer vlan. When the vlan mode is transparent, should input 65534 (0xfffe)."
           ::= { hwEponDeviceOntPortVlanEntry 3 }

      hwEponOntPortVlanCfgSVlan OBJECT-TYPE
           SYNTAX      Integer32 (-1 | 1..4094)
           MAX-ACCESS  read-write
           STATUS      current
           DESCRIPTION
                   "This object indicates the epon ont port service vlan."
           ::= { hwEponDeviceOntPortVlanEntry 4 }

      hwEponOntPortVlanCfgType OBJECT-TYPE
           SYNTAX      INTEGER
               {
                transparent(1),
                translation(2),
                invalid(-1)
               }
           MAX-ACCESS  read-write
           STATUS      current
           DESCRIPTION
                   "This object indicates the xpon service profile port vlan type.
                    Options:
                    1. transparent(1)       - Indicates that the XPON service profile port vlan type is transparent
                    2. translation(2)       - Indicates that the XPON service profile port vlan type is translation
                    3. invalid(-1)          - Indicates that the XPON service profile port vlan type is invalid
                   "
           ::= { hwEponDeviceOntPortVlanEntry 5 }

      hwEponOntPortVlanCfgRowstatus OBJECT-TYPE
           SYNTAX RowStatus
           MAX-ACCESS read-create
           STATUS current
           DESCRIPTION
               "Row status. This object is used to differentiate the
                creation, modification and deletion operations for an object.
                Options:
                 1. createAndGo(4) -create a new instance of a conceptual row
                 2. destroy(6)     -delete the instances associated with an existing conceptual row
               "
           ::= { hwEponDeviceOntPortVlanEntry 6 }

-- hwEponDeviceOntPortVlanTable end

-- hwEponDeviceAlarmProfileInfoTable
      hwEponDeviceAlarmProfileInfoTable OBJECT-TYPE
          SYNTAX     SEQUENCE OF HwEponDeviceAlarmProfileInfoEntry
          MAX-ACCESS not-accessible
          STATUS     current
          DESCRIPTION
                   "This table is used to create, delete, modify or query the EPON alarm profile.
          The index of this table is hwEponDeviceAlarmProfileInfoNameIndex."
          ::= { hwXponDeviceControlObjects 146 }

      hwEponDeviceAlarmProfileInfoEntry OBJECT-TYPE
          SYNTAX     HwEponDeviceAlarmProfileInfoEntry
          MAX-ACCESS not-accessible
          STATUS     current
          DESCRIPTION
                   "This table is used to create, delete, modify or query the EPON alarm profile.
          The index of this entry is hwEponDeviceAlarmProfileInfoNameIndex."
          INDEX       { IMPLIED hwEponDeviceAlarmProfileInfoNameIndex}
          ::= { hwEponDeviceAlarmProfileInfoTable 1 }

      HwEponDeviceAlarmProfileInfoEntry ::=
          SEQUENCE {
                    hwEponDeviceAlarmProfileInfoNameIndex                           OCTET STRING,
                    hwEponDeviceAlarmProfileBindNum                                 Gauge32,
                    hwEponDeviceAlarmProfileTxDropEventsThreshold                   Gauge32,
                    hwEponDeviceAlarmProfileTxDropEventsRestoreThreshold            Gauge32,
                    hwEponDeviceAlarmProfileRxDropEventsThreshold                   Gauge32,
                    hwEponDeviceAlarmProfileRxDropEventsRestoreThreshold            Gauge32,
                    hwEponDeviceAlarmProfileTxCRCErrorFramesThreshold               Gauge32,
                    hwEponDeviceAlarmProfileTxCRCErrorFramesRestoreThreshold        Gauge32,
                    hwEponDeviceAlarmProfileRxCRCErrorFramesThreshold               Gauge32,
                    hwEponDeviceAlarmProfileRxCRCErrorFramesRestoreThreshold        Gauge32,
                    hwEponDeviceAlarmProfileTxUndersizeFramesThreshold              Gauge32,
                    hwEponDeviceAlarmProfileTxUndersizeFramesRestoreThreshold       Gauge32,
                    hwEponDeviceAlarmProfileRxUndersizeFramesThreshold              Gauge32,
                    hwEponDeviceAlarmProfileRxUndersizeFramesRestoreThreshold       Gauge32,
                    hwEponDeviceAlarmProfileTxOversizeFramesThreshold               Gauge32,
                    hwEponDeviceAlarmProfileTxOversizeFramesRestoreThreshold        Gauge32,
                    hwEponDeviceAlarmProfileRxOversizeFramesThreshold               Gauge32,
                    hwEponDeviceAlarmProfileRxOversizeFramesRestoreThreshold        Gauge32,
                    hwEponDeviceAlarmProfileTxFragmentsThreshold                    Gauge32,
                    hwEponDeviceAlarmProfileTxFragmentsRestoreThreshold             Gauge32,
                    hwEponDeviceAlarmProfileRxFragmentsThreshold                    Gauge32,
                    hwEponDeviceAlarmProfileRxFragmentsRestoreThreshold             Gauge32,
                    hwEponDeviceAlarmProfileTxJabbersThreshold                      Gauge32,
                    hwEponDeviceAlarmProfileTxJabbersRestoreThreshold               Gauge32,
                    hwEponDeviceAlarmProfileRxJabbersThreshold                      Gauge32,
                    hwEponDeviceAlarmProfileRxJabbersRestoreThreshold               Gauge32,
                    hwEponDeviceAlarmProfileTxDiscardsThreshold                     Gauge32,
                    hwEponDeviceAlarmProfileTxDiscardsRestoreThreshold              Gauge32,
                    hwEponDeviceAlarmProfileRxDiscardsThreshold                     Gauge32,
                    hwEponDeviceAlarmProfileRxDiscardsRestoreThreshold              Gauge32,
                    hwEponDeviceAlarmProfileTxErrorsThreshold                       Gauge32,
                    hwEponDeviceAlarmProfileTxErrorsRestoreThreshold                Gauge32,
                    hwEponDeviceAlarmProfileRxErrorsThreshold                       Gauge32,
                    hwEponDeviceAlarmProfileRxErrorsRestoreThreshold                Gauge32,
                    hwEponDeviceAlarmProfileRowStatus                               RowStatus
                   }

      hwEponDeviceAlarmProfileInfoNameIndex OBJECT-TYPE
            SYNTAX OCTET STRING (SIZE (1..32))
            MAX-ACCESS not-accessible
            STATUS current
            DESCRIPTION
                "This object indicates the name of EPON alarm profile."
            ::= { hwEponDeviceAlarmProfileInfoEntry 1 }

      hwEponDeviceAlarmProfileBindNum OBJECT-TYPE
            SYNTAX     Gauge32
            MAX-ACCESS   read-only
            STATUS current
            DESCRIPTION
                "This object indicates the bind number of EPON alarm profile."
            ::= { hwEponDeviceAlarmProfileInfoEntry 2 }

      hwEponDeviceAlarmProfileTxDropEventsThreshold OBJECT-TYPE
            SYNTAX     Gauge32
            MAX-ACCESS   read-write
            STATUS current
            DESCRIPTION
                "This object indicates the down stream drop events threshold of EPON alarm profile."
            ::= { hwEponDeviceAlarmProfileInfoEntry 3 }

      hwEponDeviceAlarmProfileTxDropEventsRestoreThreshold OBJECT-TYPE
            SYNTAX     Gauge32
            MAX-ACCESS   read-write
            STATUS current
            DESCRIPTION
                "This object indicates the down stream drop events restore threshold of EPON alarm profile."
            ::= { hwEponDeviceAlarmProfileInfoEntry 4 }

      hwEponDeviceAlarmProfileRxDropEventsThreshold OBJECT-TYPE
            SYNTAX     Gauge32
            MAX-ACCESS   read-write
            STATUS current
            DESCRIPTION
                "This object indicates the up stream drop events threshold of EPON alarm profile."
            ::= { hwEponDeviceAlarmProfileInfoEntry 5 }

      hwEponDeviceAlarmProfileRxDropEventsRestoreThreshold OBJECT-TYPE
            SYNTAX     Gauge32
            MAX-ACCESS   read-write
            STATUS current
            DESCRIPTION
                "This object indicates the up stream drop events restore threshold of EPON alarm profile."
            ::= { hwEponDeviceAlarmProfileInfoEntry 6 }

      hwEponDeviceAlarmProfileTxCRCErrorFramesThreshold OBJECT-TYPE
            SYNTAX     Gauge32
            MAX-ACCESS   read-write
            STATUS current
            DESCRIPTION
                "This object indicates the down stream CRC error frames threshold of EPON alarm profile."
            ::= { hwEponDeviceAlarmProfileInfoEntry 7 }

      hwEponDeviceAlarmProfileTxCRCErrorFramesRestoreThreshold OBJECT-TYPE
            SYNTAX     Gauge32
            MAX-ACCESS   read-write
            STATUS current
            DESCRIPTION
                "This object indicates the down stream CRC error frames restore threshold of EPON alarm profile."
            ::= { hwEponDeviceAlarmProfileInfoEntry 8 }

      hwEponDeviceAlarmProfileRxCRCErrorFramesThreshold OBJECT-TYPE
            SYNTAX     Gauge32
            MAX-ACCESS   read-write
            STATUS current
            DESCRIPTION
                "This object indicates the up stream CRC error frames threshold of EPON alarm profile."
            ::= { hwEponDeviceAlarmProfileInfoEntry 9 }

      hwEponDeviceAlarmProfileRxCRCErrorFramesRestoreThreshold OBJECT-TYPE
            SYNTAX     Gauge32
            MAX-ACCESS   read-write
            STATUS current
            DESCRIPTION
                "This object indicates the up stream CRC error frames restore threshold of EPON alarm profile."
            ::= { hwEponDeviceAlarmProfileInfoEntry 10 }

      hwEponDeviceAlarmProfileTxUndersizeFramesThreshold OBJECT-TYPE
            SYNTAX     Gauge32
            MAX-ACCESS   read-write
            STATUS current
            DESCRIPTION
                "This object indicates the down stream under size frames threshold of EPON alarm profile."
            ::= { hwEponDeviceAlarmProfileInfoEntry 11 }

      hwEponDeviceAlarmProfileTxUndersizeFramesRestoreThreshold OBJECT-TYPE
            SYNTAX     Gauge32
            MAX-ACCESS   read-write
            STATUS current
            DESCRIPTION
                "This object indicates the down stream under size frames restore threshold of EPON alarm profile."
            ::= { hwEponDeviceAlarmProfileInfoEntry 12 }

      hwEponDeviceAlarmProfileRxUndersizeFramesThreshold OBJECT-TYPE
            SYNTAX     Gauge32
            MAX-ACCESS   read-write
            STATUS current
            DESCRIPTION
                "This object indicates the up stream under size frames threshold of EPON alarm profile."
            ::= { hwEponDeviceAlarmProfileInfoEntry 13 }

      hwEponDeviceAlarmProfileRxUndersizeFramesRestoreThreshold OBJECT-TYPE
            SYNTAX     Gauge32
            MAX-ACCESS   read-write
            STATUS current
            DESCRIPTION
                "This object indicates the up stream under size frames restore threshold of EPON alarm profile."
            ::= { hwEponDeviceAlarmProfileInfoEntry 14 }

      hwEponDeviceAlarmProfileTxOversizeFramesThreshold OBJECT-TYPE
            SYNTAX     Gauge32
            MAX-ACCESS   read-write
            STATUS current
            DESCRIPTION
                "This object indicates the down stream over size frames threshold of EPON alarm profile."
            ::= { hwEponDeviceAlarmProfileInfoEntry 15 }

      hwEponDeviceAlarmProfileTxOversizeFramesRestoreThreshold OBJECT-TYPE
            SYNTAX     Gauge32
            MAX-ACCESS   read-write
            STATUS current
            DESCRIPTION
                "This object indicates the down stream over size frames restore threshold of EPON alarm profile."
            ::= { hwEponDeviceAlarmProfileInfoEntry 16 }

      hwEponDeviceAlarmProfileRxOversizeFramesThreshold OBJECT-TYPE
            SYNTAX     Gauge32
            MAX-ACCESS   read-write
            STATUS current
            DESCRIPTION
                "This object indicates the up stream over size frames threshold of EPON alarm profile."
            ::= { hwEponDeviceAlarmProfileInfoEntry 17 }

      hwEponDeviceAlarmProfileRxOversizeFramesRestoreThreshold OBJECT-TYPE
            SYNTAX     Gauge32
            MAX-ACCESS   read-write
            STATUS current
            DESCRIPTION
                "This object indicates the up stream over size frames restore threshold of EPON alarm profile."
            ::= { hwEponDeviceAlarmProfileInfoEntry 18 }


      hwEponDeviceAlarmProfileTxFragmentsThreshold OBJECT-TYPE
            SYNTAX     Gauge32
            MAX-ACCESS   read-write
            STATUS current
            DESCRIPTION
                "This object indicates the down stream fragments threshold of EPON alarm profile."
            ::= { hwEponDeviceAlarmProfileInfoEntry 19 }

      hwEponDeviceAlarmProfileTxFragmentsRestoreThreshold OBJECT-TYPE
            SYNTAX     Gauge32
            MAX-ACCESS   read-write
            STATUS current
            DESCRIPTION
                "This object indicates the down stream fragments restore threshold of EPON alarm profile."
            ::= { hwEponDeviceAlarmProfileInfoEntry 20 }

      hwEponDeviceAlarmProfileRxFragmentsThreshold OBJECT-TYPE
            SYNTAX     Gauge32
            MAX-ACCESS   read-write
            STATUS current
            DESCRIPTION
                "This object indicates the up stream fragments threshold of EPON alarm profile."
            ::= { hwEponDeviceAlarmProfileInfoEntry 21 }

      hwEponDeviceAlarmProfileRxFragmentsRestoreThreshold OBJECT-TYPE
            SYNTAX     Gauge32
            MAX-ACCESS   read-write
            STATUS current
            DESCRIPTION
                "This object indicates the up stream fragments restore threshold of EPON alarm profile."
            ::= { hwEponDeviceAlarmProfileInfoEntry 22 }

      hwEponDeviceAlarmProfileTxJabbersThreshold OBJECT-TYPE
            SYNTAX     Gauge32
            MAX-ACCESS   read-write
            STATUS current
            DESCRIPTION
                "This object indicates the down stream jabbers threshold of EPON alarm profile."
            ::= { hwEponDeviceAlarmProfileInfoEntry 23 }

      hwEponDeviceAlarmProfileTxJabbersRestoreThreshold OBJECT-TYPE
            SYNTAX     Gauge32
            MAX-ACCESS   read-write
            STATUS current
            DESCRIPTION
                "This object indicates the down stream jabbers restore threshold of EPON alarm profile."
            ::= { hwEponDeviceAlarmProfileInfoEntry 24 }

      hwEponDeviceAlarmProfileRxJabbersThreshold OBJECT-TYPE
            SYNTAX     Gauge32
            MAX-ACCESS   read-write
            STATUS current
            DESCRIPTION
                "This object indicates the up stream jabbers threshold of EPON alarm profile."
            ::= { hwEponDeviceAlarmProfileInfoEntry 25 }

      hwEponDeviceAlarmProfileRxJabbersRestoreThreshold OBJECT-TYPE
            SYNTAX     Gauge32
            MAX-ACCESS   read-write
            STATUS current
            DESCRIPTION
                "This object indicates the up stream jabbers restore threshold of EPON alarm profile."
            ::= { hwEponDeviceAlarmProfileInfoEntry 26 }

      hwEponDeviceAlarmProfileTxDiscardsThreshold OBJECT-TYPE
            SYNTAX     Gauge32
            MAX-ACCESS   read-write
            STATUS current
            DESCRIPTION
                "This object indicates the down stream discards threshold of EPON alarm profile."
            ::= { hwEponDeviceAlarmProfileInfoEntry 27 }

      hwEponDeviceAlarmProfileTxDiscardsRestoreThreshold OBJECT-TYPE
            SYNTAX     Gauge32
            MAX-ACCESS   read-write
            STATUS current
            DESCRIPTION
                "This object indicates the down stream discards restore threshold of EPON alarm profile."
            ::= { hwEponDeviceAlarmProfileInfoEntry 28 }

      hwEponDeviceAlarmProfileRxDiscardsThreshold OBJECT-TYPE
            SYNTAX     Gauge32
            MAX-ACCESS   read-write
            STATUS current
            DESCRIPTION
                "This object indicates the up stream discards threshold of EPON alarm profile."
            ::= { hwEponDeviceAlarmProfileInfoEntry 29 }

      hwEponDeviceAlarmProfileRxDiscardsRestoreThreshold OBJECT-TYPE
            SYNTAX     Gauge32
            MAX-ACCESS   read-write
            STATUS current
            DESCRIPTION
                "This object indicates the up stream discards restore threshold of EPON alarm profile."
            ::= { hwEponDeviceAlarmProfileInfoEntry 30 }

      hwEponDeviceAlarmProfileTxErrorsThreshold OBJECT-TYPE
            SYNTAX     Gauge32
            MAX-ACCESS   read-write
            STATUS current
            DESCRIPTION
                "This object indicates the down stream errors threshold of EPON alarm profile."
            ::= { hwEponDeviceAlarmProfileInfoEntry 31 }

      hwEponDeviceAlarmProfileTxErrorsRestoreThreshold OBJECT-TYPE
            SYNTAX     Gauge32
            MAX-ACCESS   read-write
            STATUS current
            DESCRIPTION
                "This object indicates the down stream errors restore threshold of EPON alarm profile."
            ::= { hwEponDeviceAlarmProfileInfoEntry 32 }

      hwEponDeviceAlarmProfileRxErrorsThreshold OBJECT-TYPE
            SYNTAX     Gauge32
            MAX-ACCESS   read-write
            STATUS current
            DESCRIPTION
                "This object indicates the up stream errors threshold of EPON alarm profile."
            ::= { hwEponDeviceAlarmProfileInfoEntry 33 }

      hwEponDeviceAlarmProfileRxErrorsRestoreThreshold OBJECT-TYPE
            SYNTAX     Gauge32
            MAX-ACCESS   read-write
            STATUS current
            DESCRIPTION
                "This object indicates the up stream errors restore threshold of EPON alarm profile."
            ::= { hwEponDeviceAlarmProfileInfoEntry 34 }

      hwEponDeviceAlarmProfileRowStatus OBJECT-TYPE
            SYNTAX     RowStatus
            MAX-ACCESS    read-create
            STATUS current
            DESCRIPTION
                "This object is used to create a new row or to modify or delete an existing row in this table.
                 Options:
                 1. createAndGo(4) -create a new instance of a conceptual row
                 2. destroy(6)     -delete the instances associated with an existing conceptual row
                "
            ::= { hwEponDeviceAlarmProfileInfoEntry 35 }


-- hwEponDeviceAlarmProfileInfoTable end

-- Table hwGponDeviceOntPortVlanTable
      hwGponDeviceOntPortVlanTable OBJECT-TYPE
          SYNTAX     SEQUENCE OF HwGponDeviceOntPortVlanEntry
          MAX-ACCESS not-accessible
          STATUS     current
          DESCRIPTION
                   "This table is used to create, delete, modify or query GPON ONT's distributed port vlan.
                    The index of this table is ifIndex, hwGponDeviceOntIndex, hwGponDeviceOntPortVlanPhyType,
                    hwGponDeviceOntPortVlanPhyIndex, hwGponDeviceOntPortVlanCVlan, hwGponDeviceOntPortVlanCPri, hwGponDeviceOntPortVlanEtherType."
          ::= { hwXponDeviceControlObjects 147 }

      hwGponDeviceOntPortVlanEntry OBJECT-TYPE
          SYNTAX     HwGponDeviceOntPortVlanEntry
          MAX-ACCESS not-accessible
          STATUS     current
          DESCRIPTION
                   "This table is used to create, delete, modify or query GPON ONT's distributed port vlan.
                    The index of this entry is ifIndex, hwGponDeviceOntIndex, hwGponDeviceOntPortVlanPhyType,
                    hwGponDeviceOntPortVlanPhyIndex, hwGponDeviceOntPortVlanCVlan, hwGponDeviceOntPortVlanCPri, hwGponDeviceOntPortVlanEtherType."
          INDEX       { ifIndex, hwGponDeviceOntIndex, hwGponDeviceOntPortVlanPhyType, hwGponDeviceOntPortVlanPhyIndex,
                        hwGponDeviceOntPortVlanCVlan, hwGponDeviceOntPortVlanCPri, hwGponDeviceOntPortVlanEtherType}
          ::= { hwGponDeviceOntPortVlanTable 1 }

     HwGponDeviceOntPortVlanEntry ::=
            SEQUENCE {
                hwGponDeviceOntPortVlanPhyType                              INTEGER,
                hwGponDeviceOntPortVlanPhyIndex                             Integer32,
                hwGponDeviceOntPortVlanCVlan                                Integer32,
                hwGponDeviceOntPortVlanCPri                                 Integer32,
                hwGponDeviceOntPortVlanEtherType                            Integer32,
                hwGponDeviceOntPortVlanCfgType                              INTEGER,
                hwGponDeviceOntPortVlanSVlan                                Integer32,
                hwGponDeviceOntPortVlanSPri                                 Integer32,
                hwGponDeviceOntPortVlanSPriPolicy                           INTEGER,
                hwGponDeviceOntPortVlanDscpDefaultPri                       Integer32,
                hwGponDeviceOntPortVlanRowStatus                            RowStatus
             }

      hwGponDeviceOntPortVlanPhyType OBJECT-TYPE
            SYNTAX INTEGER {
                t1(13),
                e1(14),
                fe(24),
                ge(34),
                vdsl(37),
                wifi(40),
                moca(46),
                eth(47),
                iphost(50)
            }
            MAX-ACCESS not-accessible
            STATUS current
            DESCRIPTION
                "This object indicates the port type of the ONT.
                 Options:
                 1. t1(13)             - T1
                 2. e1(14)             - E1
                 3. fe(24)             - FE
                 4. ge(34)             - GE
                 5. vdsl(37)           - VDSL
                 6. wifi(40)           - WiFi
                 7. moca(46)           - MOCA
                 8. eth(47)            - ETH
                 9. iphost(50)         - IPHOST
                "
            ::= { hwGponDeviceOntPortVlanEntry 1 }

     hwGponDeviceOntPortVlanPhyIndex OBJECT-TYPE
            SYNTAX Integer32
            MAX-ACCESS not-accessible
            STATUS current
            DESCRIPTION
                "This object indicates the port index of the ONT."
            ::= { hwGponDeviceOntPortVlanEntry 2 }

     hwGponDeviceOntPortVlanCVlan OBJECT-TYPE
            SYNTAX Integer32
            MAX-ACCESS not-accessible
            STATUS current
            DESCRIPTION
                "This object indicates the port customer vlan distributed configured on GPON ONT. When the vlan mode is transparent, the custom vlan should be 65534 (0xfffe).
                 When the vlan type is q-in-q and user vlan attribute is untagged, custom vlan should be 0xfffd(65533).
                "
            ::= { hwGponDeviceOntPortVlanEntry 3 }

     hwGponDeviceOntPortVlanCPri OBJECT-TYPE
            SYNTAX Integer32
            MAX-ACCESS not-accessible
            STATUS current
            DESCRIPTION
                "This object indicates the port translation or qinq c-priority distributed configured on GPON ONT."
            ::= { hwGponDeviceOntPortVlanEntry 4 }

     hwGponDeviceOntPortVlanEtherType OBJECT-TYPE
            SYNTAX Integer32
            MAX-ACCESS not-accessible
            STATUS current
            DESCRIPTION
                "This object indicates customer service encapsulation type distributed configured on GPON ONT.
                 Options:
                 1. ipv4-ipoe(1)  - Indicates that the customer service encapsulation type is ipv4 ipoe
                 2. pppoe(2)      - Indicates that the customer service encapsulation type is pppoe
                 3. ipv6-ipoe(4)  - Indicates that the customer service encapsulation type is ipv6 ipoe
                 4. invalid(-1)   - Indicates that don't specify the customer service encapsulation type
                 5. 0x600-0xffff  - Indicates that the customer service encapsulation type is user-defined
                "
            ::= { hwGponDeviceOntPortVlanEntry 5 }

     hwGponDeviceOntPortVlanCfgType OBJECT-TYPE
            SYNTAX INTEGER {
                transparent(1),
                translation(2),
                qinq(3),
                invalid(-1)
            }
            MAX-ACCESS read-write
            STATUS current
            DESCRIPTION
                "This object indicates the port vlan type distributed configured on GPON ONT.
                 Options:
                 1. transparent(1)    - Indicates that the port vlan type distributed configured on GPON ONT is transparent
                 2. translation(2)    - Indicates that the port vlan type distributed configured on GPON ONT is translation distributed configured on GPON ONT
                 3. qinq(3)           - Indicates that the port vlan type distributed configured on GPON ONT is qinq
                 4. invalid(-1)       - Indicates that the query fails or no information is detected
                "
            ::= { hwGponDeviceOntPortVlanEntry 6 }

     hwGponDeviceOntPortVlanSVlan OBJECT-TYPE
            SYNTAX Integer32 (-1 | 0..4095)
            MAX-ACCESS read-write
            STATUS current
            DESCRIPTION
                "This object indicates the port service vlan distributed configured on GPON ONT."
            ::= { hwGponDeviceOntPortVlanEntry 7 }

     hwGponDeviceOntPortVlanSPri OBJECT-TYPE
            SYNTAX Integer32 (-1|0..7)
            MAX-ACCESS read-write
            STATUS current
            DESCRIPTION
                "This object indicates the port translation or qinq s-priority distributed configured on GPON ONT."
            ::= { hwGponDeviceOntPortVlanEntry 8 }

     hwGponDeviceOntPortVlanSPriPolicy OBJECT-TYPE
            SYNTAX INTEGER {
                specify(1),
                userCos(2),
                dscpMapping(3),
                invalid(-1)
            }
            MAX-ACCESS read-write
            STATUS current
            DESCRIPTION
                "This object indicates the s-vlan priority policy distributed configured on GPON ONT.
                 Options:
                 1. specify(1)      - Indicates that the s-vlan priority policy is specified
                 2. userCos(2)     - Indicates that the s-vlan priority policy is userCos
                 3. dscpMapping(3) - Indicates that the s-vlan priority policy is dscpMapping
                 4. invalid(-1)     - Indicates that the query fails or no information is detected
                "
            ::= { hwGponDeviceOntPortVlanEntry 9 }

     hwGponDeviceOntPortVlanDscpDefaultPri OBJECT-TYPE
            SYNTAX      Integer32
            MAX-ACCESS  read-write
            STATUS      current
            DESCRIPTION
                "This object indicates the default priority for dscpMapping policy."
            ::= { hwGponDeviceOntPortVlanEntry 10 }

     hwGponDeviceOntPortVlanRowStatus OBJECT-TYPE
            SYNTAX RowStatus
            MAX-ACCESS read-create
            STATUS current
            DESCRIPTION
                "The hwGponDeviceOntPortVlanRowStatus is used to create a new row
                 or to modify or delete an existing row in this table.
                 Options:
                 1. createAndGo(4) -create a new instance of a conceptual row
                 2. destroy(6)     -delete the instances associated with an existing conceptual row
                "
            ::= { hwGponDeviceOntPortVlanEntry 11 }
-- hwGponDeviceOntPortVlanTable end

--  Table hwGponDeviceLineProfMulticastGemCfgTable
        hwGponDeviceLineProfMulticastGemCfgTable OBJECT-TYPE
            SYNTAX SEQUENCE OF HwGponDeviceLineProfMulticastGemCfgEntry
            MAX-ACCESS not-accessible
            STATUS current
            DESCRIPTION
                "This is the XPON line profile multicast gemport config table.
                 The index of this table is  hwGponDeviceLineProfileInfoNameIndex.
                "
            ::= { hwXponDeviceProfileObjects 148 }

        hwGponDeviceLineProfMulticastGemCfgEntry OBJECT-TYPE
            SYNTAX HwGponDeviceLineProfMulticastGemCfgEntry
            MAX-ACCESS not-accessible
            STATUS current
            DESCRIPTION
                "This is the XPON line profile multicast gemport config table.
                 The index of this entry is  hwGponDeviceLineProfileInfoNameIndex.
                "
            INDEX { IMPLIED hwGponDeviceLineProfileInfoNameIndex }
            ::= { hwGponDeviceLineProfMulticastGemCfgTable 1 }

        HwGponDeviceLineProfMulticastGemCfgEntry ::=
            SEQUENCE {
                hwGponDeviceLineProfMulticastGemCfgTcontIndex           Integer32,
                hwGponDeviceLineProfMulticastGemCfgOntPhyType           INTEGER,
                hwGponDeviceLineProfMulticastGemCfgOntPhyIndex          Integer32
            }

        hwGponDeviceLineProfMulticastGemCfgTcontIndex OBJECT-TYPE
            SYNTAX Integer32
            MAX-ACCESS read-write
            STATUS current
            DESCRIPTION
                "This object indicates the XPON line profile T-CONT index.
                The issued value (-1) of T-CONT index indicates that the multicast gemport is not specified to any tcont."
            ::= { hwGponDeviceLineProfMulticastGemCfgEntry 1 }

        hwGponDeviceLineProfMulticastGemCfgOntPhyType OBJECT-TYPE
            SYNTAX INTEGER {
                eth(47),
                ethBundle(254),
                invalid(-1)
            }
            MAX-ACCESS read-write
            STATUS current
            DESCRIPTION
                "This object indicates the port type of the ONT.
                 Options:
                 1. eth(47)            - ETH
                 2. ethBundle(254)     - EthBundle
                 3. invalid(-1)        - Indicates that the query fails or no information is detected
                "
            ::= { hwGponDeviceLineProfMulticastGemCfgEntry 2 }

        hwGponDeviceLineProfMulticastGemCfgOntPhyIndex OBJECT-TYPE
            SYNTAX Integer32
            MAX-ACCESS read-write
            STATUS current
            DESCRIPTION
                "This object indicates the port index of the ONT,
                 or the bundle-groupid when it is the eth-bundle port type.
                "
            ::= { hwGponDeviceLineProfMulticastGemCfgEntry 3 }

-- hwGponDeviceLineProfMulticastGemCfgTable end
    END
