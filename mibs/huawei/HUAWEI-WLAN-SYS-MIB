--
-- HUAWEI-WLAN-SYS-MIB.my
-- MIB generated by MG-SOFT Visual MIB Builder Version 4.0 Build 341
-- Tuesday, February 19, 2013 at 16:55:09
--

--  HUAWEI-WLAN-SYS-MIB.my
-- MIB generated by MG-SOFT Visual MIB Builder Version 4.0 Build 341
-- Thursday, March 08, 2012 at 16:18:52
--
--  HUAWEI-WLAN-SYS-MIB.mib
-- MIB generated by MG-SOFT Visual MIB Builder Version 4.0 Build 341
-- Thursday, November 24, 2011 at 22:43:06
--
--  ============================================================================
-- Copyright (C) 2014 by  HUAWEI TECHNOLOGIES. All rights reserved.
-- Description:  The mib is used for config the ac in global view.
-- Reference:HUAWEI-WLAN-MIB
-- Version: V1.06
--
-- ============================================================================

	HUAWEI-WLAN-SYS-MIB DEFINITIONS ::= BEGIN

		IMPORTS
			hwWlan
				FROM HUAWEI-WLAN-MIB
			OBJECT-GROUP, MODULE-COMPLIANCE
				FROM SNMPv2-CONF
			IpAddress, Integer32, Unsigned32, OBJECT-TYPE, MODULE-IDENTITY
				FROM SNMPv2-SMI;


--    Revision history
-- 1.3.6.1.4.1.2011.6.139.1
-- November 10, 2010 at 00:00 GMT
-- June 08, 2010 at 00:00 GMT
-- July 06, 2010 at 00:00 GMT
-- September 10, 2010 at 00:00 GMT
-- September 15, 2010 at 00:00 GMT
-- September 27, 2010 at 00:00 GMT
-- November 01, 2010 at 00:00 GMT
-- 1.3.6.1.4.1.2011.6.139.1
-- November 10, 2010 at 00:00 GMT
-- November 01, 2010 at 00:00 GMT
-- September 27, 2010 at 00:00 GMT
-- September 15, 2010 at 00:00 GMT
-- September 10, 2010 at 00:00 GMT
-- July 06, 2010 at 00:00 GMT
-- June 08, 2010 at 00:00 GMT
		-- 1.3.6.1.4.1.2011.6.139.1
		hwWlanSysManagement MODULE-IDENTITY
			LAST-UPDATED "201410231600Z"		-- Oct 23, 2014 at 16:00 GMT
			ORGANIZATION
				"Huawei Technologies Co.,Ltd."
			CONTACT-INFO
            "Huawei Industrial Base
				   Bantian, Longgang
				   Shenzhen 518129
				   People's Republic of China
				   Website: http://www.huawei.com
				   Email: support@huawei.com "

			DESCRIPTION
				"add table of hwWlanStaIpv6Switch,and notes for sta ipv6 service."
       	    REVISION "201410231600Z"		-- Oct 23, 2014 at 16:00 GMT

            DESCRIPTION
				"add table of hwWlanInterAcManagement,and notes for inter-ac dtls."
       	    REVISION "201403211600Z"		-- March 21, 2014 at 16:00 GMT

            DESCRIPTION
				"add node of hwWlanAcSourceIPv4Address for table hwWlanAcSourceInterface."
       	    REVISION "201312200958Z"		-- Dec 20, 2013 at 09:58 GMT

			DESCRIPTION
				"The MIB module defines the ap update operation."
       	    REVISION "201311121016Z"		-- Nov 12, 2013 at 10:16 GMT

			DESCRIPTION
				"add node of 80M for table hwWlanConfigChannel"
			REVISION "201311121016Z"		-- Nov 12, 2013 at 10:16 GMT

			DESCRIPTION
				"add node of 80M for table hwWlanConfigChannel"

			REVISION "201310231722Z"		-- October 23, 2013 at 17:22 GMT
			DESCRIPTION
				"
				V1.07, Add for v2r5.
				"

			REVISION "201305230000Z"		-- May 23, 2013 at 00:00 GMT
			DESCRIPTION
				"
				V1.06, Add for wifi location and spectrum analysis.
				"

			REVISION "201011010000Z"		-- November 01, 2010 at 00:00 GMT
			DESCRIPTION
				"
				V1.05, Add hwWlanAcProtectIpAddress for IP address of the backup AC,
					   Add hwWlanAcProtectPriority for Dual-link hot backup priorities,
					   Add hwWlanAcProtectSwitch for Dual-link hot backup switch.
				"

			REVISION "201009270000Z"		-- September 27, 2010 at 00:00 GMT
			DESCRIPTION
				"
				V1.04, Add hwWlanCapwapConfig for supportting configuration of CAPWAP parameter.
				       Add hwWlanCapwapKeepAliveInterval for supportting configuration of CAPWAP keep-alive interval, in seconds.
				       Add hwWlanCapwapKeepAliveTimes for supportting configuration of CAPWAP keep-alive times.
				       hwWlanCarrierId add a enum 'other'.
				       Add batch query function.
				       Add hwWlanAcCapwapControlPacketPriority for ac's priority value of CAPWAP control packet.
				       Add hwWlanApCapwapControlPacketPriority for ap's priority value of CAPWAP control packet.
				"

			REVISION "201009150000Z"		-- September 15, 2010 at 00:00 GMT
			DESCRIPTION
				"
				V1.03, Add hwWlanBatchQuery for the supporting batch query.
				"

			REVISION "201009100000Z"		-- September 10, 2010 at 00:00 GMT
			DESCRIPTION
				"
				V1.02, Add hwWlanAcSourceInterface for the supporting configuration of wlan ac source interface.
				"

			REVISION "201007060000Z"		-- July 06, 2010 at 00:00 GMT
			DESCRIPTION
				"
				V1.01, Add trap restrain.
				"

			REVISION "201006080000Z"		-- June 08, 2010 at 00:00 GMT
			DESCRIPTION
				"
				V1.00, Inital version.
				"
			::= { hwWlan 1 }



--
-- Node definitions
--

--  Node definitions
--
-- 1.3.6.1.4.1.2011.6.139.1.1
		-- 1.3.6.1.4.1.2011.6.139.1.1
		hwWlanTrapRestrain OBJECT IDENTIFIER ::= { hwWlanSysManagement 1 }


--  1.3.6.1.4.1.2011.6.139.1.1.1
		-- 1.3.6.1.4.1.2011.6.139.1.1.1
		hwWlanTrapRestrainAll OBJECT-TYPE
			SYNTAX INTEGER
				{
				enable(1),
				disable(2)
				}
			MAX-ACCESS read-write
			STATUS current
			DESCRIPTION
				"All wlan trap restrain switch. If this switch is enabled, all the traps on ac will not be sent."
			::= { hwWlanTrapRestrain 1 }


--  1.3.6.1.4.1.2011.6.139.1.1.2
		-- 1.3.6.1.4.1.2011.6.139.1.1.2
		hwWlanTrapSeverityRestrain OBJECT IDENTIFIER ::= { hwWlanTrapRestrain 2 }


--  1.3.6.1.4.1.2011.6.139.1.1.2.1
		-- 1.3.6.1.4.1.2011.6.139.1.1.2.1
		hwWlanTrapSeverityRestrainSeverity OBJECT-TYPE
			SYNTAX INTEGER
				{
				critical(1),
				major(2),
				minor(3),
				warning(4),
				none(5)
				}
			MAX-ACCESS read-write
			STATUS current
			DESCRIPTION
				"Wlan trap restrain by severity.
				critical: means the trap whose severity is not higner than critical will not be sent.
				major: means the trap whose severity is not higner than major will not be sent.
				minor: means the trap whose severity is not higner than minor will not be sent.
				warning: means the trap whose severity is not higner than warning will not be sent.
				none: means all the severities of traps can be sent."
			::= { hwWlanTrapSeverityRestrain 1 }


--  1.3.6.1.4.1.2011.6.139.1.1.3
		-- 1.3.6.1.4.1.2011.6.139.1.1.3
		hwWlanApRegionTrapRestrain OBJECT IDENTIFIER ::= { hwWlanTrapRestrain 3 }


--  1.3.6.1.4.1.2011.6.139.1.1.3.1
		-- 1.3.6.1.4.1.2011.6.139.1.1.3.1
		hwWlanApRegionTrapRestrainRegionIndexMask OBJECT-TYPE
			SYNTAX OCTET STRING
			MAX-ACCESS read-write
			STATUS current
			DESCRIPTION
				"Wlan trap restrain by ap region.
				Every bit is used to describe the region's trap will be restrained or not.
				0 means not restrain, and 1 means restrain.
				Each Byte describes 8 regions are restrained or not.
				The value of this node is hexadecimal integer block.
				For example, the first Byte describes region 0~7 is restrained or not,
				and the second Byte describes region 8~15 is restrained or not.
				Such as, if only region 0,4,5,6,7,9 is restrain, the binary number is 11110001 and 00000010,
				the hexadecimal number is 0xF1 and 0x2, so the first Byte of this node is 0xF1,
				and the second Byte is 0x2."
			::= { hwWlanApRegionTrapRestrain 1 }


--  1.3.6.1.4.1.2011.6.139.1.1.4
		-- 1.3.6.1.4.1.2011.6.139.1.1.4
		hwWlanApTrapRestrain OBJECT IDENTIFIER ::= { hwWlanTrapRestrain 4 }


--  1.3.6.1.4.1.2011.6.139.1.1.4.1
		-- 1.3.6.1.4.1.2011.6.139.1.1.4.1
		hwWlanApTrapRestrainApIndexMask OBJECT-TYPE
			SYNTAX OCTET STRING
			MAX-ACCESS read-write
			STATUS current
			DESCRIPTION
				"Wlan trap restrain by ap.
				Every bit is used to describe the ap's trap will be restrained or not.
				0 means not restrain, and 1 means restrain.
				Each Byte describes 8 aps are restrained or not.
				The value of this node is hexadecimal integer block.
				For example, the first Byte describes ap 0~7 is restrained or not,
				and the second Byte describes ap 8~15 is restrained or not.
				Such as, if only ap 0,4,5,6,7,9 is restrain, the binary number is 11110001 and 00000010,
				the hexadecimal number is 0xF1 and 0x2, so the first Byte of this node is 0xF1,
				and the second Byte is 0x2."
			::= { hwWlanApTrapRestrain 1 }


--  1.3.6.1.4.1.2011.6.139.1.2
		-- 1.3.6.1.4.1.2011.6.139.1.2
		hwWlanSysPara OBJECT IDENTIFIER ::= { hwWlanSysManagement 2 }


--   China mobile
-- China telecom
-- China unicom
-- Other company
-- 1.3.6.1.4.1.2011.6.139.1.2.1
		-- 1.3.6.1.4.1.2011.6.139.1.2.1
		hwWlanCarrierId OBJECT-TYPE
			SYNTAX INTEGER
				{
				cmcc(1),
				ctc(2),
				cuc(3),
				other(65535)
				}
			MAX-ACCESS read-write
			STATUS current
			DESCRIPTION
				"The carrier identification.
				cmcc means 'China mobile communications corporation' ,
				ctc means 'China telecom company' ,
				cuc means 'China unicom company',
				other means 'Other company',
				"
			::= { hwWlanSysPara 1 }


--  1.3.6.1.4.1.2011.6.139.1.2.2
		-- 1.3.6.1.4.1.2011.6.139.1.2.2
		hwWlanAcId OBJECT-TYPE
			SYNTAX Integer32
			MAX-ACCESS read-write
			STATUS current
			DESCRIPTION
				"The ac identification.
				The carrier must set ac id and carrier id before use.
				In this case, APs can check each other whether blong to a same AC.
				"
			::= { hwWlanSysPara 2 }


--   ess mode
-- ap mode
-- 1.3.6.1.4.1.2011.6.139.1.2.3
		-- 1.3.6.1.4.1.2011.6.139.1.2.3
		hwWlanForwardMode OBJECT-TYPE
			SYNTAX INTEGER
				{
				ess(1),
				ap(2)
				}
			MAX-ACCESS read-write
			STATUS current
			DESCRIPTION
				"AC forward mode.It can be set
				ess(1): ess mode
				ap(2): ap mode
				"
			::= { hwWlanSysPara 3 }


--   1.3.6.1.4.1.2011.6.139.1.2.4
-- 1.3.6.1.4.1.2011.6.139.1.2.4
		-- 1.3.6.1.4.1.2011.6.139.1.2.4
		hwWlanAcNEnumber OBJECT-TYPE
			SYNTAX OCTET STRING
			MAX-ACCESS read-write
			STATUS current
			DESCRIPTION
				"Description."
			::= { hwWlanSysPara 4 }


--   1.3.6.1.4.1.2011.6.139.1.2.5
-- 1.3.6.1.4.1.2011.6.139.1.2.5
		-- 1.3.6.1.4.1.2011.6.139.1.2.5
		hwWlanAcAccessMaxApNumber OBJECT-TYPE
			SYNTAX Integer32
			MAX-ACCESS read-only
			STATUS current
			DESCRIPTION
				"Description."
			::= { hwWlanSysPara 5 }


--  1.3.6.1.4.1.2011.6.139.1.2.6
		-- 1.3.6.1.4.1.2011.6.139.1.2.6
		hwAcCountryCode OBJECT-TYPE
			SYNTAX OCTET STRING
			MAX-ACCESS read-write
			STATUS current
			DESCRIPTION
				"Description."
			::= { hwWlanSysPara 6 }


--  1.3.6.1.4.1.2011.6.139.1.2.8
		-- 1.3.6.1.4.1.2011.6.139.1.2.8
		hwWlanApUsername OBJECT-TYPE
			SYNTAX OCTET STRING (SIZE (4..31))
			MAX-ACCESS read-write
			STATUS current
			DESCRIPTION
				"Description: When set, need to together with password, and the username length is 4 to 31 characters."
			::= { hwWlanSysPara 8 }


--  1.3.6.1.4.1.2011.6.139.1.2.9
		-- 1.3.6.1.4.1.2011.6.139.1.2.9
		hwWlanApPassword OBJECT-TYPE
			SYNTAX OCTET STRING (SIZE (8..32))
			MAX-ACCESS read-write
			STATUS current
			DESCRIPTION
				"Description: When set, need to together with username, and the password length is 8 to 32 characters which must contain at least one capital letter,
				one lowcase letter and one number."
			::= { hwWlanSysPara 9 }


--  1.3.6.1.4.1.2011.6.139.1.2.10
		-- 1.3.6.1.4.1.2011.6.139.1.2.10
		hwWlanUsernamePasswordApId OBJECT-TYPE
			SYNTAX Integer32
			MAX-ACCESS read-write
			STATUS current
			DESCRIPTION
				"Description: The node is useful only when get the username or password and must be set first and read with username or password.
				When get the username or password without the node ,it means get the gloable configuration from AC, otherwise, it means
				get the specified AP' username or password from AP. For when change the username or password,and not commit, the AC's
				configuration is diffrent with AP' real configuration.
				When specified the AP ID , and the AP is not in the normal state, return the username or password from AC's gloable configuration."
			::= { hwWlanSysPara 10 }


		-- 1.3.6.1.4.1.2011.6.139.1.2.11
		hwWlanApLldpSwitch OBJECT-TYPE
			SYNTAX INTEGER
				{
				disable(1),
				enable(2)
				}
			MAX-ACCESS read-write
			STATUS current
			DESCRIPTION
				"Description: Global AP LLDP switch."
			::= { hwWlanSysPara 11 }


		-- 1.3.6.1.4.1.2011.6.139.1.2.12
		hwWlanAcAccessMaxStaNumber OBJECT-TYPE
			SYNTAX Integer32
			MAX-ACCESS read-only
			STATUS current
			DESCRIPTION
				"Description."
			::= { hwWlanSysPara 12 }


		-- 1.3.6.1.4.1.2011.6.139.1.2.13
		hwWlanAcDtlsSwitch OBJECT-TYPE
			SYNTAX INTEGER
				{
				enable(1),
				disable(2)
				}
			MAX-ACCESS read-write
			STATUS current
			DESCRIPTION
				"Description."
			::= { hwWlanSysPara 13 }


		-- 1.3.6.1.4.1.2011.6.139.1.2.14
		hwWlanAcDtlsPsk OBJECT-TYPE
			SYNTAX OCTET STRING (SIZE (1..32))
			MAX-ACCESS read-write
			STATUS current
			DESCRIPTION
				"Description."
			::= { hwWlanSysPara 14 }

		-- 1.3.6.1.4.1.2011.6.139.1.2.15
		hwWlanApLogManualBackupApId  OBJECT-TYPE
			SYNTAX Integer32
			MAX-ACCESS read-write
			STATUS current
			DESCRIPTION
				"Description."
			::= { hwWlanSysPara 15 }
		-- 1.3.6.1.4.1.2011.6.139.1.2.16
		hwWlanAcDtlsDefaultPskSwitch OBJECT-TYPE
			SYNTAX INTEGER
				{
				enable(1),
				disable(2)
				}
			MAX-ACCESS read-write
			STATUS current
			DESCRIPTION
				"Description."
			::= { hwWlanSysPara 16 }

		-- 1.3.6.1.4.1.2011.6.139.1.2.17
		hwWlanWorkMode OBJECT-TYPE
			SYNTAX INTEGER
				{
				ac(1),
				ap(2)
				}
			MAX-ACCESS read-only
			STATUS current
			DESCRIPTION
				"Description."
			::= { hwWlanSysPara 17 }

		hwWlanIpv6Enable OBJECT-TYPE
			SYNTAX INTEGER
				{
				disable(1),
				enable(2)
				}
			MAX-ACCESS read-write
			STATUS current
			DESCRIPTION
				"Description."
			::= { hwWlanSysPara 18 }


		-- 1.3.6.1.4.1.2011.6.139.1.2.19
		hwWlanInterAcDtlsEncrpyt OBJECT-TYPE
			SYNTAX INTEGER
				{
				disable(1),
				enable(2)
				}
			MAX-ACCESS read-write
			STATUS current
			DESCRIPTION
				"Description."
			::= { hwWlanSysPara 19 }


		-- 1.3.6.1.4.1.2011.6.139.1.2.20
		hwWlanInterAcDtlsPsk OBJECT-TYPE
			SYNTAX OCTET STRING (SIZE (1..32))
			MAX-ACCESS read-write
			STATUS current
			DESCRIPTION
				"Description."
			::= { hwWlanSysPara 20 }


		-- 1.3.6.1.4.1.2011.6.139.1.2.21
		hwWlanStaIpv6Switch OBJECT-TYPE
			SYNTAX INTEGER
				{
				disable(1),
				enable(2)
				}
			MAX-ACCESS read-write
			STATUS current
			DESCRIPTION
				"Whether to process IPv6 services of STAs."
			DEFVAL { 2 }
			::= { hwWlanSysPara 21 }
--   1.3.6.1.4.1.2011.6.139.1.3
-- 1.3.6.1.4.1.2011.6.139.1.3
		-- 1.3.6.1.4.1.2011.6.139.1.3
		hwWlanAcSourceInterface OBJECT IDENTIFIER ::= { hwWlanSysManagement 3 }


--  1.3.6.1.4.1.2011.6.139.1.3.1
		-- 1.3.6.1.4.1.2011.6.139.1.3.1
		hwWlanAcSourceInterfaceValue OBJECT-TYPE
			SYNTAX Integer32
			MAX-ACCESS read-write
			STATUS current
			DESCRIPTION
				"the value of wlan ac source interface.
				"
			::= { hwWlanAcSourceInterface 1 }


--   default setting
-- vlanif interface
-- loopback interface
-- 1.3.6.1.4.1.2011.6.139.1.3.2
-- 1.3.6.1.4.1.2011.6.139.1.3.2
		-- 1.3.6.1.4.1.2011.6.139.1.3.2
		hwWlanAcSourceInterfaceMethod OBJECT-TYPE
			SYNTAX INTEGER
				{
				default(1),
				vlanif(2),
				loopback(3),
				ipaddress(4)
				}
			MAX-ACCESS read-write
			STATUS current
			DESCRIPTION
				"operation method of wlan ac source interface.It can be set
				default(1): use default setting
				vlanif(2): use vlanif interface
				loopback(3): use loopback interface
				ipaddress(4):user ip address
				"
			::= { hwWlanAcSourceInterface 2 }


		-- 1.3.6.1.4.1.2011.6.139.1.3.3
		hwWlanAcSourceIPv4Address OBJECT-TYPE
			SYNTAX IpAddress
			MAX-ACCESS read-write
			STATUS current
			DESCRIPTION
				"Description."
			::= { hwWlanAcSourceInterface 3 }

--   1.3.6.1.4.1.2011.6.139.1.4
-- 1.3.6.1.4.1.2011.6.139.1.4
		-- 1.3.6.1.4.1.2011.6.139.1.4
		hwWlanBatchQuery OBJECT IDENTIFIER ::= { hwWlanSysManagement 4 }


--  1.3.6.1.4.1.2011.6.139.1.4.1
		-- 1.3.6.1.4.1.2011.6.139.1.4.1
		hwWlanBatchQueryType OBJECT-TYPE
			SYNTAX INTEGER
				{
				apProfName(1),
				apWhiteListMac(2),
				apWhiteListSn(3),
				apBlackListMac(4),
				apBlackListSn(5),
				apRegionId(6),
				apRegionIdModeName(7),
				apId(8),
				apIdState(9),
				apIdStateRegionName(10),
				unauthApIdMac(11),
				radioProfName(12),
				radioBalanceGroupName(13),
				uncontrolApIdBssidAuthApId(14),
				essNameSsid(15),
				wmmProfName(16),
				trafficProfName(17),
				secProfName(18),
				authMacStateType(19),
				clear(65535)
				}
			MAX-ACCESS read-write
			STATUS current
			DESCRIPTION
				"Data type of Batch query. For example, apProfName(1) can be used to get ap-profile-name list.
				The batch query support two modes, the number mode and the ID list mode, binding the node hwWlanBatchRequestNum and
				hwWlanBatchStartCount means use the number mode, binding the node hwWlanBatchRequestIdList, hwWlanBatchRequestIdSize
				hwWlanBatchRequestIdNum means use the ID list mode.
				"
			::= { hwWlanBatchQuery 1 }


--  1.3.6.1.4.1.2011.6.139.1.4.2
		-- 1.3.6.1.4.1.2011.6.139.1.4.2
		hwWlanBatchRequestNum OBJECT-TYPE
			SYNTAX Integer32
			MAX-ACCESS read-write
			STATUS current
			DESCRIPTION
				"The request number of the batch query, it used in number mode. This node must be set in company with
				the node hwWlanBatchStartCount. For example, there are 6 ap-profiles(0 1 3 5 6 9) in the AC, Set hwWlanBatchQuery
				to apProfName(1), set hwWlanBatchRequestNum to 3, and set hwWlanBatchStartCount to 2, then get the node
				hwWlanBatchValueList and hwWlanBatchReturnNum, that means start from the 2nd ap-profile, get 3 ap-profile-names,
				the result in hwWlanBatchValueList are ap-profile(3 5 6 9).
				"
			::= { hwWlanBatchQuery 2 }


--  1.3.6.1.4.1.2011.6.139.1.4.3
		-- 1.3.6.1.4.1.2011.6.139.1.4.3
		hwWlanBatchStartCount OBJECT-TYPE
			SYNTAX Integer32
			MAX-ACCESS read-write
			STATUS current
			DESCRIPTION
				"The start count of the batch query, it used in number mode. This node must be set in company with
				the node hwWlanBatchRequestNum. For example, there are 6 ap-profiles(0 1 3 5 6 9) in the AC, Set hwWlanBatchQuery
				to apProfName(1), set hwWlanBatchRequestNum to 3, and set hwWlanBatchStartCount to 2, then get the node
				hwWlanBatchValueList and hwWlanBatchReturnNum, that means start from the 2nd ap-profile, get 3 ap-profile-names,
				the result in hwWlanBatchValueList are ap-profile(3 5 6 9)."
			::= { hwWlanBatchQuery 3 }


--  1.3.6.1.4.1.2011.6.139.1.4.4
		-- 1.3.6.1.4.1.2011.6.139.1.4.4
		hwWlanBatchRequestIdList OBJECT-TYPE
			SYNTAX OCTET STRING (SIZE (0..2048))
			MAX-ACCESS read-write
			STATUS current
			DESCRIPTION
				"The ID list of the data type, It used in ID list mode. This node must be set in company with
				the node hwWlanBatchRequestIdSize and hwWlanBatchRequestIdNum. For example, Ther are 6 apid(0 1 3 4 5 6) int the AC,
				set hwWlanBatchQuery to apIdStateRegionName(10), set hwWlanBatchRequestIdList to #0x00 0x01 0x00 0x02 0x00 0x03 (ap1 ap2 ap3),
				set	hwWlanBatchRequestIdSize to 2(bytes), and set hwWlanBatchRequestIdNum to 3, then get the node hwWlanBatchValueList
				and hwWlanBatchReturnNum. The result in hwWlanBatchValueList are apids(1 2 3)"
			::= { hwWlanBatchQuery 4 }


--  1.3.6.1.4.1.2011.6.139.1.4.5
		-- 1.3.6.1.4.1.2011.6.139.1.4.5
		hwWlanBatchRequestIdSize OBJECT-TYPE
			SYNTAX Integer32
			MAX-ACCESS read-write
			STATUS current
			DESCRIPTION
				"The length of a batch query ID element, it used in ID list mode. This node must be set in company with
				the node hwWlanBatchRequestIdList and hwWlanBatchRequestIdNum. For example, Ther are 6 apid(0 1 3 4 5 6) int the AC,
				set hwWlanBatchQuery to apIdStateRegionName(10), set hwWlanBatchRequestIdList to #0x00 0x01 0x00 0x02 0x00 0x03 (ap1 ap2 ap3),
				set	hwWlanBatchRequestIdSize to 2(bytes), and set hwWlanBatchRequestIdNum to 3, then get the node hwWlanBatchValueList
				and hwWlanBatchReturnNum. The result in hwWlanBatchValueList are apids(1 2 3)"
			::= { hwWlanBatchQuery 5 }


--  1.3.6.1.4.1.2011.6.139.1.4.6
		-- 1.3.6.1.4.1.2011.6.139.1.4.6
		hwWlanBatchRequestIdNum OBJECT-TYPE
			SYNTAX Integer32
			MAX-ACCESS read-write
			STATUS current
			DESCRIPTION
				"The number of batch query by id, it used in ID list mode. This node must be set in company with
				the node hwWlanBatchRequestIdList and hwWlanBatchRequestIdSize. For example, Ther are 6 apid(0 1 3 4 5 6) int the AC,
				set hwWlanBatchQuery to apIdStateRegionName(10), set hwWlanBatchRequestIdList to #0x00 0x01 0x00 0x02 0x00 0x03 (ap1 ap2 ap3),
				set	hwWlanBatchRequestIdSize to 2(bytes), and set hwWlanBatchRequestIdNum to 3, then get the node hwWlanBatchValueList
				and hwWlanBatchReturnNum. The result in hwWlanBatchValueList are apids(1 2 3)"
			::= { hwWlanBatchQuery 6 }


--  1.3.6.1.4.1.2011.6.139.1.4.7
		-- 1.3.6.1.4.1.2011.6.139.1.4.7
		hwWlanBatchValueList OBJECT-TYPE
			SYNTAX OCTET STRING (SIZE (0..6144))
			MAX-ACCESS read-only
			STATUS current
			DESCRIPTION
				"The returned value list. If the value ended by a string, each value is divided by '?', otherwise , each value
				will have a fixed length. This node must be get in company with the node hwWlanBatchReturnNum."
			::= { hwWlanBatchQuery 7 }


--  1.3.6.1.4.1.2011.6.139.1.4.8
		-- 1.3.6.1.4.1.2011.6.139.1.4.8
		hwWlanBatchReturnNum OBJECT-TYPE
			SYNTAX Integer32
			MAX-ACCESS read-only
			STATUS current
			DESCRIPTION
				"The number of successful query. This node must be get in company with the node hwWlanBatchValueList."
			::= { hwWlanBatchQuery 8 }


--  1.3.6.1.4.1.2011.6.139.1.4.9
		-- 1.3.6.1.4.1.2011.6.139.1.4.9
		hwWlanBatchTotalNum OBJECT-TYPE
			SYNTAX Integer32
			MAX-ACCESS read-only
			STATUS current
			DESCRIPTION
				"Total number of current batch query. For example, There are 10 ap-Profiles in the AC,
				the value of this node will be 10."
			::= { hwWlanBatchQuery 9 }


--  1.3.6.1.4.1.2011.6.139.1.5
		-- 1.3.6.1.4.1.2011.6.139.1.5
		hwWlanCapwapConfig OBJECT IDENTIFIER ::= { hwWlanSysManagement 5 }


--  1.3.6.1.4.1.2011.6.139.1.5.1
		-- 1.3.6.1.4.1.2011.6.139.1.5.1
		hwWlanCapwapKeepAliveInterval OBJECT-TYPE
			SYNTAX Integer32
			MAX-ACCESS read-write
			STATUS current
			DESCRIPTION
				"
				The interval of maintain freshness of the CAPWAP channel, in seconds.
				"
			::= { hwWlanCapwapConfig 1 }


--  1.3.6.1.4.1.2011.6.139.1.5.2
		-- 1.3.6.1.4.1.2011.6.139.1.5.2
		hwWlanCapwapKeepAliveTimes OBJECT-TYPE
			SYNTAX Integer32
			MAX-ACCESS read-write
			STATUS current
			DESCRIPTION
				"
				The times of maintain freshness of the CAPWAP channel before it timeout.
				"
			::= { hwWlanCapwapConfig 2 }


--  1.3.6.1.4.1.2011.6.139.1.5.3
		-- 1.3.6.1.4.1.2011.6.139.1.5.3
		hwWlanCapwapControlPriorityACToAP OBJECT-TYPE
			SYNTAX Integer32
			MAX-ACCESS read-write
			STATUS current
			DESCRIPTION
				"
				the ac's priority value of CAPWAP control packet,includ cos and tos,
				ranging between 0 and 7.
				"
			::= { hwWlanCapwapConfig 3 }


--  1.3.6.1.4.1.2011.6.139.1.5.4
		-- 1.3.6.1.4.1.2011.6.139.1.5.4
		hwWlanCapwapControlPriorityAPToAC OBJECT-TYPE
			SYNTAX Integer32
			MAX-ACCESS read-write
			STATUS current
			DESCRIPTION
				"
				the ap's priority value of CAPWAP control packet,includ tos,
				ranging between 0 and 7.
				"
			::= { hwWlanCapwapConfig 4 }


--  1.3.6.1.4.1.2011.6.139.1.6
		-- 1.3.6.1.4.1.2011.6.139.1.6
		hwWlanAcProtect OBJECT IDENTIFIER ::= { hwWlanSysManagement 6 }


--  1.3.6.1.4.1.2011.6.139.1.6.1
		-- 1.3.6.1.4.1.2011.6.139.1.6.1
		hwWlanAcProtectIpAddress OBJECT-TYPE
			SYNTAX IpAddress
			MAX-ACCESS read-write
			STATUS current
			DESCRIPTION
				"IP address of the backup AC."
			::= { hwWlanAcProtect 1 }


--  1.3.6.1.4.1.2011.6.139.1.6.2
		-- 1.3.6.1.4.1.2011.6.139.1.6.2
		hwWlanAcProtectPriority OBJECT-TYPE
			SYNTAX Unsigned32 (0..7)
			MAX-ACCESS read-write
			STATUS current
			DESCRIPTION
				"Dual-link hot backup priorities."
			::= { hwWlanAcProtect 2 }


--  1.3.6.1.4.1.2011.6.139.1.6.3
		-- 1.3.6.1.4.1.2011.6.139.1.6.3
		hwWlanAcProtectSwitch OBJECT-TYPE
			SYNTAX INTEGER
				{
				enable(1),
				disable(2)
				}
			MAX-ACCESS read-write
			STATUS current
			DESCRIPTION
				"Dual-link hot backup switch."
			::= { hwWlanAcProtect 3 }


--   1.3.6.1.4.1.2011.6.139.1.6.4
-- 1.3.6.1.4.1.2011.6.139.1.6.4
		-- 1.3.6.1.4.1.2011.6.139.1.6.4
		hwWlanAcProtectRestoreSwitch OBJECT-TYPE
			SYNTAX INTEGER
				{
				enable(1),
				disable(2)
				}
			MAX-ACCESS read-write
			STATUS current
			DESCRIPTION
				"Description."
			::= { hwWlanAcProtect 4 }


--  1.3.6.1.4.1.2011.6.139.1.6.5
		-- 1.3.6.1.4.1.2011.6.139.1.6.5
		hwUndoWlanAcProtectIpAddress OBJECT-TYPE
			SYNTAX Integer32
			MAX-ACCESS read-write
			STATUS current
			DESCRIPTION
				"Description."
			::= { hwWlanAcProtect 5 }


--  1.3.6.1.4.1.2011.6.139.1.6.6
		-- 1.3.6.1.4.1.2011.6.139.1.6.6
		hwUndoWlanAcProtectPriority OBJECT-TYPE
			SYNTAX Integer32
			MAX-ACCESS read-write
			STATUS current
			DESCRIPTION
				"Description."
			::= { hwWlanAcProtect 6 }


		-- 1.3.6.1.4.1.2011.6.139.1.6.7
		hwWlanAcProtectIpv6Address OBJECT-TYPE
			SYNTAX OCTET STRING (SIZE (0..46))
			MAX-ACCESS read-write
			STATUS current
			DESCRIPTION
				"Description."
			::= { hwWlanAcProtect 7 }

--  1.3.6.1.4.1.2011.6.139.1.7
		-- 1.3.6.1.4.1.2011.6.139.1.7
		hwWlanConfigChannel OBJECT IDENTIFIER ::= { hwWlanSysManagement 7 }


--   1.3.6.1.4.1.2011.6.139.1.7.1
-- 1.3.6.1.4.1.2011.6.139.1.7.1
		-- 1.3.6.1.4.1.2011.6.139.1.7.1
		hwWlan24G20MconfigChannel OBJECT-TYPE
			SYNTAX OCTET STRING
			MAX-ACCESS read-only
			STATUS current
			DESCRIPTION
				"Description."
			::= { hwWlanConfigChannel 1 }


--   1.3.6.1.4.1.2011.6.139.1.7.2
-- 1.3.6.1.4.1.2011.6.139.1.7.2
		-- 1.3.6.1.4.1.2011.6.139.1.7.2
		hwWlan24G40MPlusConfigChannel OBJECT-TYPE
			SYNTAX OCTET STRING
			MAX-ACCESS read-only
			STATUS current
			DESCRIPTION
				"Description."
			::= { hwWlanConfigChannel 2 }


--   1.3.6.1.4.1.2011.6.139.1.7.3
-- 1.3.6.1.4.1.2011.6.139.1.7.3
		-- 1.3.6.1.4.1.2011.6.139.1.7.3
		hwWlan24G40MMinusConfigChannel OBJECT-TYPE
			SYNTAX OCTET STRING
			MAX-ACCESS read-only
			STATUS current
			DESCRIPTION
				"Description."
			::= { hwWlanConfigChannel 3 }


--   1.3.6.1.4.1.2011.6.139.1.7.4
-- 1.3.6.1.4.1.2011.6.139.1.7.4
		-- 1.3.6.1.4.1.2011.6.139.1.7.4
		hwWlan5G20MConfigChannel OBJECT-TYPE
			SYNTAX OCTET STRING
			MAX-ACCESS read-only
			STATUS current
			DESCRIPTION
				"Description."
			::= { hwWlanConfigChannel 4 }


--   1.3.6.1.4.1.2011.6.139.1.7.5
-- 1.3.6.1.4.1.2011.6.139.1.7.5
		-- 1.3.6.1.4.1.2011.6.139.1.7.5
		hwWlan5G40MPlusConfigChannel OBJECT-TYPE
			SYNTAX OCTET STRING
			MAX-ACCESS read-only
			STATUS current
			DESCRIPTION
				"Description."
			::= { hwWlanConfigChannel 5 }


--   1.3.6.1.4.1.2011.6.139.1.7.6
-- 1.3.6.1.4.1.2011.6.139.1.7.6
		-- 1.3.6.1.4.1.2011.6.139.1.7.6
		hwWlan5G40MMinusConfigChannel OBJECT-TYPE
			SYNTAX OCTET STRING
			MAX-ACCESS read-only
			STATUS current
			DESCRIPTION
				"Description."
			::= { hwWlanConfigChannel 6 }


		-- 1.3.6.1.4.1.2011.6.139.1.7.7
		hwWlanConfigChannelApId OBJECT-TYPE
			SYNTAX Integer32
			MAX-ACCESS read-write
			STATUS current
			DESCRIPTION
				"Ap index, is used to identify AP uniquely.Query the configurable channel of the ap must contain apid otherwise query are global configurable channel."
			::= { hwWlanConfigChannel 7 }

		-- 1.3.6.1.4.1.2011.6.139.1.7.8
		hwWlan24G80MConfigChannel OBJECT-TYPE
			SYNTAX OCTET STRING
			MAX-ACCESS read-only
			STATUS current
			DESCRIPTION
				"Description."
			::= { hwWlanConfigChannel 8 }

		-- 1.3.6.1.4.1.2011.6.139.1.7.9
		hwWlan5G80MConfigChannel OBJECT-TYPE
			SYNTAX OCTET STRING
			MAX-ACCESS read-only
			STATUS current
			DESCRIPTION
				"Description."
			::= { hwWlanConfigChannel 9 }


		-- 1.3.6.1.4.1.2011.6.139.1.8
		hwWlanStaLoadbalance OBJECT IDENTIFIER ::= { hwWlanSysManagement 8 }


		-- 1.3.6.1.4.1.2011.6.139.1.8.1
		hwWlanStaLoadbalanceEnable OBJECT-TYPE
			SYNTAX Integer32
			MAX-ACCESS read-write
			STATUS current
			DESCRIPTION
				"Description."
			::= { hwWlanStaLoadbalance 1 }


		-- 1.3.6.1.4.1.2011.6.139.1.8.2
		hwWlanStaLoadbalanceMode OBJECT-TYPE
			SYNTAX Integer32
			MAX-ACCESS read-write
			STATUS current
			DESCRIPTION
				"Description."
			::= { hwWlanStaLoadbalance 2 }


		-- 1.3.6.1.4.1.2011.6.139.1.8.3
		hwWlanStaLoadbalanceSessionGap OBJECT-TYPE
			SYNTAX Integer32
			MAX-ACCESS read-write
			STATUS current
			DESCRIPTION
				"Description."
			::= { hwWlanStaLoadbalance 3 }


		-- 1.3.6.1.4.1.2011.6.139.1.8.4
		hwWlanStaLoadbalanceTrafficGap OBJECT-TYPE
			SYNTAX Integer32
			MAX-ACCESS read-write
			STATUS current
			DESCRIPTION
				"Description."
			::= { hwWlanStaLoadbalance 4 }


		-- 1.3.6.1.4.1.2011.6.139.1.8.5
		hwWlanStaLoadbalanceAssociateThreshold OBJECT-TYPE
			SYNTAX Integer32
			MAX-ACCESS read-write
			STATUS current
			DESCRIPTION
				"Description."
			::= { hwWlanStaLoadbalance 5 }


		-- 1.3.6.1.4.1.2011.6.139.1.9
		hwWlanHsbConfig OBJECT IDENTIFIER ::= { hwWlanSysManagement 9 }


		-- 1.3.6.1.4.1.2011.6.139.1.9.1
		hwWlanHsbServiceType OBJECT-TYPE
			SYNTAX INTEGER
				{
				disable(1),
				hsbGroup(2),
				hsbService(3)
				}
			MAX-ACCESS read-write
			STATUS current
			DESCRIPTION
				"The hsb service type can be one of the three values: 1, 2, 3 (1: disable(1) 2: hsbGroup(2) 3: hsbService(3)).
				The default value of this node is 1."
			::= { hwWlanHsbConfig 1 }


		-- 1.3.6.1.4.1.2011.6.139.1.9.2
		hwWlanHsbGroupId OBJECT-TYPE
			SYNTAX Unsigned32
			MAX-ACCESS read-write
			STATUS current
			DESCRIPTION
				"The id of the hsb group used. When hsb service type is disabled, the value of this node is 0xFFFFFFFF."
			::= { hwWlanHsbConfig 2 }


		-- 1.3.6.1.4.1.2011.6.139.1.9.3
		hwWlanHsbTunnelId OBJECT-TYPE
			SYNTAX Unsigned32
			MAX-ACCESS read-write
			STATUS current
			DESCRIPTION
				"The id of the hsb tunnel used. When hsb service type is disabled, the value of this node is 0xFFFFFFFF."
			::= { hwWlanHsbConfig 3 }


		-- 1.3.6.1.4.1.2011.6.139.1.10
		hwWlanLocation OBJECT IDENTIFIER ::= { hwWlanSysManagement 10 }


		-- 1.3.6.1.4.1.2011.6.139.1.10.1
		hwWlanLocationServerIP OBJECT-TYPE
			SYNTAX IpAddress
			MAX-ACCESS read-write
			STATUS current
			DESCRIPTION
				"Description."
			::= { hwWlanLocation 1 }


		-- 1.3.6.1.4.1.2011.6.139.1.10.2
		hwWlanLocationServerPort OBJECT-TYPE
			SYNTAX Integer32
			MAX-ACCESS read-write
			STATUS current
			DESCRIPTION
				"Description."
			::= { hwWlanLocation 2 }


		-- 1.3.6.1.4.1.2011.6.139.1.10.3
		hwWlanLocationSourceIP OBJECT-TYPE
			SYNTAX IpAddress
			MAX-ACCESS read-write
			STATUS current
			DESCRIPTION
				"Description."
			::= { hwWlanLocation 3 }


		-- 1.3.6.1.4.1.2011.6.139.1.10.4
		hwWlanLocationApReportToAC OBJECT-TYPE
			SYNTAX Integer32
			MAX-ACCESS read-write
			STATUS current
			DESCRIPTION
				"Description."
			::= { hwWlanLocation 4 }
		hwWlanLocationApReportToServerIp OBJECT-TYPE
			SYNTAX IpAddress
			MAX-ACCESS read-write
			STATUS current
			DESCRIPTION
				"Description."
			::= { hwWlanLocation 5 }
		-- 1.3.6.1.4.1.2011.6.139.1.10.6
		hwWlanLocationApReportToUdpPort OBJECT-TYPE
			SYNTAX Integer32
			MAX-ACCESS read-write
			STATUS current
			DESCRIPTION
				"Description."
			::= { hwWlanLocation 6 }

		-- 1.3.6.1.4.1.2011.6.139.1.10.7
		hwWlanLocationApReportToIpv6Addr OBJECT-TYPE
			SYNTAX OCTET STRING (SIZE (0..46))
			MAX-ACCESS read-write
			STATUS current
			DESCRIPTION
				"Description."
			::= { hwWlanLocation 7 }

		-- 1.3.6.1.4.1.2011.6.139.1.10.8
		hwWlanLocationAcReportToIpv6Addr OBJECT-TYPE
			SYNTAX OCTET STRING (SIZE (0..46))
			MAX-ACCESS read-write
			STATUS current
			DESCRIPTION
				"Description."
			::= { hwWlanLocation 8 }

		-- 1.3.6.1.4.1.2011.6.139.1.11
		hwWlanSpectrumAnalysis OBJECT IDENTIFIER ::= { hwWlanSysManagement 11 }


		-- 1.3.6.1.4.1.2011.6.139.1.11.1
		hwWlanSpectrumAnalysisServerIP OBJECT-TYPE
			SYNTAX IpAddress
			MAX-ACCESS read-write
			STATUS current
			DESCRIPTION
				"Description."
			::= { hwWlanSpectrumAnalysis 1 }


		-- 1.3.6.1.4.1.2011.6.139.1.11.2
		hwWlanSpectrumAnalysisServerPort OBJECT-TYPE
			SYNTAX Integer32
			MAX-ACCESS read-write
			STATUS current
			DESCRIPTION
				"Description."
			::= { hwWlanSpectrumAnalysis 2 }


		-- 1.3.6.1.4.1.2011.6.139.1.11.3
		hwWlanNonWifiDeviceAgeTime OBJECT-TYPE
			SYNTAX Integer32
			MAX-ACCESS read-write
			STATUS current
			DESCRIPTION
				"Description."
			::= { hwWlanSpectrumAnalysis 3 }


		-- 1.3.6.1.4.1.2011.6.139.1.11.4
		hwWlanSpectrogramServerIP OBJECT-TYPE
			SYNTAX IpAddress
			MAX-ACCESS read-write
			STATUS current
			DESCRIPTION
				"Description."
			::= { hwWlanSpectrumAnalysis 4 }
		-- 1.3.6.1.4.1.2011.6.139.1.11.5
		hwWlanSpectrogramServerPort OBJECT-TYPE
			SYNTAX Integer32
			MAX-ACCESS read-write
			STATUS current
			DESCRIPTION
				"Description."
			::= { hwWlanSpectrumAnalysis 5 }

		-- 1.3.6.1.4.1.2011.6.139.1.11.6
		hwWlanSpectrumAnalysisServerIPv6Addr OBJECT-TYPE
			SYNTAX OCTET STRING (SIZE (0..46))
			MAX-ACCESS read-write
			STATUS current
			DESCRIPTION
				"Description."
			::= { hwWlanSpectrumAnalysis 6 }

		-- 1.3.6.1.4.1.2011.6.139.1.11.7
		hwWlanSpectrogramServerIPv6Addr OBJECT-TYPE
			SYNTAX OCTET STRING (SIZE (0..46))
			MAX-ACCESS read-write
			STATUS current
			DESCRIPTION
				"Description."
			::= { hwWlanSpectrumAnalysis 7 }

		-- 1.3.6.1.4.1.2011.6.139.1.12
		hwWlanSysManagementObjects OBJECT IDENTIFIER ::= { hwWlanSysManagement 12 }


		-- 1.3.6.1.4.1.2011.6.139.1.12.1
		hwWlanLBSConfig OBJECT IDENTIFIER ::= { hwWlanSysManagementObjects 1 }


		-- 1.3.6.1.4.1.2011.6.139.1.12.1.1
		hwWlanLBSAeServerPort OBJECT-TYPE
			SYNTAX Integer32
			MAX-ACCESS read-write
			STATUS current
			DESCRIPTION
				"Description."
			::= { hwWlanLBSConfig 1 }


		-- 1.3.6.1.4.1.2011.6.139.1.12.1.2
		hwWlanLBSAeApReportMode OBJECT-TYPE
			SYNTAX INTEGER
				{
				off(1),
				toAc(2),
				toServer(3)
				}
			MAX-ACCESS read-write
			STATUS current
			DESCRIPTION
				"Description."
			::= { hwWlanLBSConfig 2 }


		-- 1.3.6.1.4.1.2011.6.139.1.12.1.3
		hwWlanLBSAeApReportPort OBJECT-TYPE
			SYNTAX Integer32
			MAX-ACCESS read-write
			STATUS current
			DESCRIPTION
				"Description."
			::= { hwWlanLBSConfig 3 }


		-- 1.3.6.1.4.1.2011.6.139.1.12.1.4
		hwWlanLBSEkServerIp OBJECT-TYPE
			SYNTAX IpAddress
			MAX-ACCESS read-write
			STATUS current
			DESCRIPTION
				"Description."
			::= { hwWlanLBSConfig 4 }


		-- 1.3.6.1.4.1.2011.6.139.1.12.1.5
		hwWlanLBSEkServerPort OBJECT-TYPE
			SYNTAX Integer32
			MAX-ACCESS read-write
			STATUS current
			DESCRIPTION
				"Description."
			::= { hwWlanLBSConfig 5 }


		-- 1.3.6.1.4.1.2011.6.139.1.12.1.6
		hwWlanLBSEkApReportMode OBJECT-TYPE
			SYNTAX INTEGER
				{
				off(1),
				toAc(2),
				toServer(3)
				}
			MAX-ACCESS read-write
			STATUS current
			DESCRIPTION
				"Description."
			::= { hwWlanLBSConfig 6 }


		-- 1.3.6.1.4.1.2011.6.139.1.12.1.7
		hwWlanLBSEkApReportIp OBJECT-TYPE
			SYNTAX IpAddress
			MAX-ACCESS read-write
			STATUS current
			DESCRIPTION
				"Description."
			::= { hwWlanLBSConfig 7 }


		-- 1.3.6.1.4.1.2011.6.139.1.12.1.8
		hwWlanLBSEkApReportPort OBJECT-TYPE
			SYNTAX Integer32
			MAX-ACCESS read-write
			STATUS current
			DESCRIPTION
				"Description."
			::= { hwWlanLBSConfig 8 }


		-- 1.3.6.1.4.1.2011.6.139.1.12.1.9
		hwWlanLBSSourceIp OBJECT-TYPE
			SYNTAX IpAddress
			MAX-ACCESS read-write
			STATUS current
			DESCRIPTION
				"Description."
			::= { hwWlanLBSConfig 9 }

		-- 1.3.6.1.4.1.2011.6.139.1.12.1.10
		hwWlanLBSAeCompoundTime OBJECT-TYPE
			SYNTAX Integer32
			MAX-ACCESS read-write
			STATUS current
			DESCRIPTION
				"Compound Time of AeroScout Tag Message"
			::= { hwWlanLBSConfig 10 }

		-- 1.3.6.1.4.1.2011.6.139.1.12.1.11
		hwWlanLBSEkServerIpv6Addr OBJECT-TYPE
			SYNTAX OCTET STRING (SIZE (0..46))
			MAX-ACCESS read-write
			STATUS current
			DESCRIPTION
				"Description."
			::= { hwWlanLBSConfig 11 }

		-- 1.3.6.1.4.1.2011.6.139.1.12.1.12
		hwWlanLBSEkApReportIpv6Addr OBJECT-TYPE
			SYNTAX OCTET STRING (SIZE (0..46))
			MAX-ACCESS read-write
			STATUS current
			DESCRIPTION
				"Description."
			::= { hwWlanLBSConfig 12 }

		-- 1.3.6.1.4.1.2011.6.139.1.12.1.13
		hwWlanLBSSourceIpv6Addr OBJECT-TYPE
			SYNTAX OCTET STRING (SIZE (0..46))
			MAX-ACCESS read-write
			STATUS current
			DESCRIPTION
				"Description."
			::= { hwWlanLBSConfig 13 }

--  1.3.6.1.4.1.2011.6.139.1.13
		-- 1.3.6.1.4.1.2011.6.139.1.13
		hwInterAcManagement OBJECT IDENTIFIER ::= { hwWlanSysManagement 13 }


--  1.3.6.1.4.1.2011.6.139.1.13.1
		-- 1.3.6.1.4.1.2011.6.139.1.13.1
		hwMasterControllerSwitch OBJECT-TYPE
			SYNTAX INTEGER
				{
				disable(1),
				enable(2)
				}
			MAX-ACCESS read-write
			STATUS current
			DESCRIPTION
				"Description."
			::= { hwInterAcManagement 1 }


--  1.3.6.1.4.1.2011.6.139.1.13.2
		-- 1.3.6.1.4.1.2011.6.139.1.13.2
		hwConnectMasterControllerSwitch OBJECT-TYPE
			SYNTAX INTEGER
			    {
                                                                       disconnect(1),
                                                                       connect(2)
			    }
			MAX-ACCESS read-write
			STATUS current
			DESCRIPTION
				"Description."
			::= { hwInterAcManagement 2 }


--  1.3.6.1.4.1.2011.6.139.1.13.3
		-- 1.3.6.1.4.1.2011.6.139.1.13.3
		hwConnectMasterControllerIPv4Address OBJECT-TYPE
			SYNTAX IpAddress
			MAX-ACCESS read-write
			STATUS current
			DESCRIPTION
				"Description."
			::= { hwInterAcManagement 3 }


--  1.3.6.1.4.1.2011.6.139.1.13.4
		-- 1.3.6.1.4.1.2011.6.139.1.13.4
		hwConnectMasterControllerIPv6Address OBJECT-TYPE
			SYNTAX OCTET STRING
			MAX-ACCESS read-write
			STATUS current
			DESCRIPTION
				"Description."
			::= { hwInterAcManagement 4 }

		hwWlanSysManagementConformance OBJECT IDENTIFIER ::= { hwWlanSysManagement 14 }

		-- 1.3.6.1.4.1.2011.6.139.1.13.1
		hwWlanSysManagementCompliances OBJECT IDENTIFIER ::= { hwWlanSysManagementConformance 1 }


		-- 1.3.6.1.4.1.2011.6.139.1.13.1.1
		hwWlanSysManagementCompliance MODULE-COMPLIANCE
			STATUS current
			DESCRIPTION
				"Description."
			MODULE -- this module
				MANDATORY-GROUPS { hwWlanTrapRestrainGroup, hwWlanSysParaGroup, hwWlanAcSourceInterfaceGroup, hwWlanBatchQueryGroup, hwWlanCapwapConfigGroup,
					hwWlanAcProtectGroup, hwWlanConfigChannelGroup, hwWlanStaLoadbalanceGroup, hwWlanHsbConfigGroup, hwWlanLocationGroup,
					hwWlanSpectrumAnalysisGroup, hwWlanLBSConfigGroup, hwInterAcManagementGroup }
			::= { hwWlanSysManagementCompliances 1 }


		-- 1.3.6.1.4.1.2011.6.139.1.13.2
		hwWlanSysManagementObjectGroups OBJECT IDENTIFIER ::= { hwWlanSysManagementConformance 2 }


		-- 1.3.6.1.4.1.2011.6.139.1.13.2.1
		hwWlanTrapRestrainGroup OBJECT-GROUP
			OBJECTS { hwWlanTrapRestrainAll, hwWlanTrapSeverityRestrainSeverity, hwWlanApRegionTrapRestrainRegionIndexMask, hwWlanApTrapRestrainApIndexMask }
			STATUS current
			DESCRIPTION
				"Description."
			::= { hwWlanSysManagementObjectGroups 1 }


		-- 1.3.6.1.4.1.2011.6.139.1.13.2.2
		hwWlanSysParaGroup OBJECT-GROUP
			OBJECTS { hwWlanCarrierId, hwWlanAcId, hwWlanForwardMode, hwWlanAcNEnumber, hwWlanAcAccessMaxApNumber,
				hwAcCountryCode, hwWlanApUsername, hwWlanApPassword, hwWlanUsernamePasswordApId, hwWlanApLldpSwitch,
				hwWlanAcAccessMaxStaNumber, hwWlanAcDtlsSwitch, hwWlanAcDtlsPsk, hwWlanApLogManualBackupApId, hwWlanAcDtlsDefaultPskSwitch,
				hwWlanWorkMode, hwWlanIpv6Enable, hwWlanInterAcDtlsEncrpyt, hwWlanInterAcDtlsPsk, hwWlanStaIpv6Switch }
			STATUS current
			DESCRIPTION
				"Description."
			::= { hwWlanSysManagementObjectGroups 2 }


		-- 1.3.6.1.4.1.2011.6.139.1.13.2.3
		hwWlanAcSourceInterfaceGroup OBJECT-GROUP
			OBJECTS { hwWlanAcSourceInterfaceValue, hwWlanAcSourceInterfaceMethod, hwWlanAcSourceIPv4Address}
			STATUS current
			DESCRIPTION
				"Description."
			::= { hwWlanSysManagementObjectGroups 3 }


		-- 1.3.6.1.4.1.2011.6.139.1.13.2.4
		hwWlanBatchQueryGroup OBJECT-GROUP
			OBJECTS { hwWlanBatchQueryType, hwWlanBatchRequestNum, hwWlanBatchStartCount, hwWlanBatchRequestIdList, hwWlanBatchRequestIdSize,
				hwWlanBatchRequestIdNum, hwWlanBatchValueList, hwWlanBatchReturnNum, hwWlanBatchTotalNum }
			STATUS current
			DESCRIPTION
				"Description."
			::= { hwWlanSysManagementObjectGroups 4 }


		-- 1.3.6.1.4.1.2011.6.139.1.13.2.5
		hwWlanCapwapConfigGroup OBJECT-GROUP
			OBJECTS { hwWlanCapwapKeepAliveInterval, hwWlanCapwapKeepAliveTimes, hwWlanCapwapControlPriorityACToAP, hwWlanCapwapControlPriorityAPToAC }
			STATUS current
			DESCRIPTION
				"Description."
			::= { hwWlanSysManagementObjectGroups 5 }


		-- 1.3.6.1.4.1.2011.6.139.1.13.2.6
		hwWlanAcProtectGroup OBJECT-GROUP
			OBJECTS { hwWlanAcProtectIpAddress, hwWlanAcProtectPriority, hwWlanAcProtectSwitch, hwWlanAcProtectRestoreSwitch, hwUndoWlanAcProtectIpAddress,
				hwUndoWlanAcProtectPriority,hwWlanAcProtectIpv6Address }
			STATUS current
			DESCRIPTION
				"Description."
			::= { hwWlanSysManagementObjectGroups 6 }


		-- 1.3.6.1.4.1.2011.6.139.1.13.2.7
		hwWlanConfigChannelGroup OBJECT-GROUP
			OBJECTS { hwWlan24G20MconfigChannel, hwWlan24G40MPlusConfigChannel, hwWlan24G40MMinusConfigChannel, hwWlan5G20MConfigChannel, hwWlan5G40MPlusConfigChannel,
				hwWlan5G40MMinusConfigChannel, hwWlanConfigChannelApId, hwWlan24G80MConfigChannel, hwWlan5G80MConfigChannel }
			STATUS current
			DESCRIPTION
				"Description."
			::= { hwWlanSysManagementObjectGroups 7 }


		-- 1.3.6.1.4.1.2011.6.139.1.13.2.8
		hwWlanStaLoadbalanceGroup OBJECT-GROUP
			OBJECTS { hwWlanStaLoadbalanceEnable, hwWlanStaLoadbalanceMode, hwWlanStaLoadbalanceSessionGap, hwWlanStaLoadbalanceTrafficGap, hwWlanStaLoadbalanceAssociateThreshold
				 }
			STATUS current
			DESCRIPTION
				"Description."
			::= { hwWlanSysManagementObjectGroups 8 }


		-- 1.3.6.1.4.1.2011.6.139.1.13.2.9
		hwWlanHsbConfigGroup OBJECT-GROUP
			OBJECTS { hwWlanHsbServiceType, hwWlanHsbGroupId, hwWlanHsbTunnelId }
			STATUS current
			DESCRIPTION
				"Description."
			::= { hwWlanSysManagementObjectGroups 9 }


		-- 1.3.6.1.4.1.2011.6.139.1.13.2.10
		hwWlanLocationGroup OBJECT-GROUP
			OBJECTS { hwWlanLocationServerIP, hwWlanLocationServerPort, hwWlanLocationSourceIP, hwWlanLocationApReportToAC, hwWlanLocationApReportToServerIp,
			          hwWlanLocationApReportToUdpPort, hwWlanLocationApReportToIpv6Addr, hwWlanLocationAcReportToIpv6Addr }
			STATUS current
			DESCRIPTION
				"Description."
			::= { hwWlanSysManagementObjectGroups 10 }


		-- 1.3.6.1.4.1.2011.6.139.1.13.2.11
		hwWlanSpectrumAnalysisGroup OBJECT-GROUP
			OBJECTS { hwWlanSpectrumAnalysisServerIP, hwWlanSpectrumAnalysisServerPort, hwWlanNonWifiDeviceAgeTime, hwWlanSpectrogramServerIP, hwWlanSpectrogramServerPort,
			hwWlanSpectrumAnalysisServerIPv6Addr, hwWlanSpectrogramServerIPv6Addr }
			STATUS current
			DESCRIPTION
				"Description."
			::= { hwWlanSysManagementObjectGroups 11 }


		-- 1.3.6.1.4.1.2011.6.139.1.13.2.12
		hwWlanLBSConfigGroup OBJECT-GROUP
			OBJECTS { hwWlanLBSAeServerPort, hwWlanLBSAeApReportMode, hwWlanLBSAeApReportPort, hwWlanLBSEkServerIp, hwWlanLBSEkServerPort,
				hwWlanLBSEkApReportMode, hwWlanLBSEkApReportIp, hwWlanLBSEkApReportPort, hwWlanLBSSourceIp, hwWlanLBSAeCompoundTime,
				hwWlanLBSEkServerIpv6Addr, hwWlanLBSEkApReportIpv6Addr, hwWlanLBSSourceIpv6Addr }
			STATUS current
			DESCRIPTION
				"Description."
			::= { hwWlanSysManagementObjectGroups 12 }


--  1.3.6.1.4.1.2011.6.139.1.16.2.13
		-- 1.3.6.1.4.1.2011.6.139.1.16.2.13
		hwInterAcManagementGroup OBJECT-GROUP
			OBJECTS { hwMasterControllerSwitch, hwConnectMasterControllerSwitch, hwConnectMasterControllerIPv4Address, hwConnectMasterControllerIPv6Address }
			STATUS current
			DESCRIPTION
				"Description."
			::= { hwWlanSysManagementObjectGroups 13 }

	END

--
-- HUAWEI-WLAN-SYS-MIB.my
--
