-- ============================================================================
-- Copyright (C) 2010 by  HUAWEI TECHNOLOGIES. All rights reserved.
-- Description:The mib is used for defining huawei's IPDSLAM PVCPPPOA MIB objects.
-- Reference:  RFC2320 RFC2225
-- Version:    V1.04
-- ============================================================================
HUAWEI-IPDSLAM-PVCPPPOA-MIB DEFINITIONS ::= BEGIN

IMPORTS
	OBJECT-TYPE, MODULE-IDENTITY
	        FROM SNMPv2-SMI
	huaweiUtility
	        FROM HUAWEI-MIB
	TruthValue
	        FROM SNMPv2-TC;


hwIpDslamPvcPPPoA MODULE-IDENTITY
	LAST-UPDATED "201111280000Z"
	ORGANIZATION "Huawei Technologies Co.,Ltd."
	CONTACT-INFO
	             "Huawei Industrial Base
	              Bantian, Longgang
	              Shenzhen 518129
	              People's Republic of China
	              Website: http://www.huawei.com
	              Email: support@huawei.com
	             "
	DESCRIPTION
		     "The mib is used for defining huawei's IPDSLAM PVCPPPOA MIB objects."

        --  Revision history
        REVISION     "201111240000Z"
	DESCRIPTION  "V1.04, added hwIpDslamPPPoAAgingMode."

        REVISION     "201008240000Z"
	DESCRIPTION  "V1.03, modified the description of hwIpDslamPPPoAMacMode, hwIpDslamPPPoAUserId."

	REVISION     "201003160000Z"
	DESCRIPTION  "V1.02, modified the description of hwIpDslamPPPoASwitch, hwIpDslamPPPoAMacMode and hwIpDslamPPPoAMRUSwitch."

	REVISION     "201001090900Z"
	DESCRIPTION  "V1.01, modified the description and fix the compiling error."

	REVISION     "200407050000Z"
	DESCRIPTION  "V1.00, initial version."

        ::= { huaweiUtility 44 }


-- System Management Parameter
hwIpDslamPPPoASwitch OBJECT-TYPE
	      SYNTAX      TruthValue
	      MAX-ACCESS  read-write
	      STATUS      current
	      DESCRIPTION
	         "
	         Indicates the global enable switch of PPPoA to PPPoE conversion.
	         DEFVAL 	  {false}
	         "
	      ::= { hwIpDslamPvcPPPoA 1 }

hwIpDslamPPPoAMacMode OBJECT-TYPE
	      SYNTAX INTEGER
		      {
		       multi-mac(1),
		       single-mac(2)
	 	      }
	      MAX-ACCESS  read-write
	      STATUS      current
	      DESCRIPTION
	         "
	         Indicates the mode for allocating the source MAC addresses during the conversion from PPPoA to PPPoE.
	         Options:
	         1. multi-mac(1)    -indicates the mode is multi-mac
	         2. single-mac(2)   -indicates the mode is single-mac
	         DEFVAL 	  {multi-mac}
	         "
	      ::= { hwIpDslamPvcPPPoA 2 }

hwIpDslamPPPoAUserId OBJECT-TYPE
	      SYNTAX INTEGER
		      {
		       host-uniq(1),
		       relay-session-id(2)
	 	      }
	      MAX-ACCESS  read-write
	      STATUS      current
	      DESCRIPTION
	         "
	         The selection of user identifier in PPPoE of PPPoA2E.
	         Options:
	         1. host-uniq(1)        -one of the fields of PPP packet, it indicates that PPP choose host-uniq to take user identify information
	         2. relay-session-id(2) -one of the fields of PPP packet, it indicates that PPP choose relay-session-id to take user identify information
	         DEFVAL 	  {host-uniq}
	         "
	      ::= { hwIpDslamPvcPPPoA 3 }

hwIpDslamPPPoAMRUSwitch OBJECT-TYPE
	      SYNTAX      TruthValue
	      MAX-ACCESS  read-write
	      STATUS      current
	      DESCRIPTION
	         "
	         Sets the MRU negotiation in PPPoA to PPPoE conversion.
	         DEFVAL 	  {false}
	         "
	      ::= { hwIpDslamPvcPPPoA 4 }

hwIpDslamPPPoAAgingMode OBJECT-TYPE
	      SYNTAX INTEGER
		      {
		       lcpecho(1),
		       lcpandservice(2)
	 	      }
	      MAX-ACCESS  read-write
	      STATUS      current
	      DESCRIPTION
	         "
	         Indicates the aging mode for the conversion from PPPoA to PPPoE.
	         Options:
	         1. lcpecho(1)    -indicates the aging mode is lcp echo.
	         2. lcpandservice(2)   -indicates the aging mode is lcp and service.
	         DEFVAL 	  {lcpandservice}
	         "
	      ::= { hwIpDslamPvcPPPoA 5 }

END
