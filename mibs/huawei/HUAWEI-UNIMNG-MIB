-- =================================================================
-- Copyright (C) 2019 by  HUAWEI TECHNOLOGIES. All rights reserved
--
-- Description: HUAWEI UNIMNG MIB, this mib will maintain information of Unified
--              Management Framework for datacomm product.
-- Reference:
-- Version:     V1.21
-- History:
--
--  V1.00 20140303 initial version
--  V1.01 20140710 add new trap node "hwTplmCmdExecuteSuccessfulNotify"
--  V1.02 20140818 modify node description LSWCCB-6116 LSWCCB-6553 LSWCCB-6908
--  V1.03 20140911 add new trap node
--  V1.04 20141023 modify as entity trap
--  V1.05 20141029 modify node description LSWCCB-8222
--  V1.06 20141118 Modify node description LSWV2R7-9213
--  V1.07 20150109 Add a new trap node LSWCCB-9570
--  V1.08 20150709 Add a new node
--  V1.09 20151019 Add a new table S21084
--  V1.10 20160114 Add a new node
--  V1.11 20160202 modify node description LSWCCB-13623
--  V1.14 20161118 Add the AS interface up/down time node S76661
--  V1.15 20170330 Add a new trap node "hwAsSlotOnlineFailNotify"
--  V1.16 20170330 modify node "hwTplmPortGroupIndex"
--  V1.17 20170725 Add a new trap node "hwUniMbrAsServiceAbnormal"
--  V1.18 20180203 modify by DTS2018020300441
--  V1.19 20181108 modify by DTS2018110802691
--  V1.20 20190524 Add a new table
-- =================================================================

	HUAWEI-UNIMNG-MIB DEFINITIONS ::= BEGIN

		IMPORTS
			hwDatacomm
				FROM HUAWEI-MIB
			OBJECT-GROUP, MODULE-COMPLIANCE, NOTIFICATION-GROUP
				FROM SNMPv2-CONF
			IpAddress, Integer32, Gauge32, Counter32, Counter64,
			OBJECT-TYPE, MODULE-IDENTITY, NOTIFICATION-TYPE
				FROM SNMPv2-SMI
			MacAddress, RowStatus, AutonomousType, DisplayString, TEXTUAL-CONVENTION
				FROM SNMPv2-TC;


--  February 02, 2016 at 14:07 GMT
		-- 1.3.6.1.4.1.2011.5.25.327
		hwUnimngMIB MODULE-IDENTITY
			LAST-UPDATED "201908201338Z"		-- 05/24, 2019 at 11:02 GMT
			ORGANIZATION
				"Huawei Technologies Co.,Ltd."
			CONTACT-INFO
				"Huawei Industrial Base
				Bantian, Longgang
				Shenzhen 518129
				People's Republic of China
				Website: http://www.huawei.com
				Email: support@huawei.com"
			DESCRIPTION
				"This MIB contains private managed object definitions for Unified Man
				agement Framework."

			REVISION "201908201338Z"		-- 08/20, 2019 at 11:02 GMT
			DESCRIPTION
				"Delete BITS in IMPORTS from SNMPv2-SMI"

			REVISION "201905241338Z"		-- 05/24, 2019 at 11:02 GMT
			DESCRIPTION
				"Add hwAuthenUserTable"

			REVISION "201811081338Z"		-- 11/08, 2018 at 15:02 GMT
			DESCRIPTION
				"Change hwMbrMngFabricPortId value max to 256"

			REVISION "201802031338Z"		-- 02/03, 2018 at 13:38 GMT
			DESCRIPTION
				"Change word successfully to successful"

			REVISION "201707251338Z"		-- 07/25, 2017 at 13:38 GMT
			DESCRIPTION
				"Add node hwUniMbrAsTrapInfo hwUniMbrAsServiceAbnormal"

			REVISION "201705231338Z"		-- 05/23, 2017 at 13:38 GMT
			DESCRIPTION
				"Modify node node hwTplmPortGroupIndex"

			REVISION "201703301338Z"		-- 03/30, 2017 at 13:38 GMT
			DESCRIPTION
				"Add a new trap node hwAsSlotOnlineFailNotify"

			REVISION "201611181338Z"		-- 11/18, 2016 at 13:38 GMT
			DESCRIPTION
				"Add the AS interface up/down time node S76661"

			REVISION "201609191338Z"		-- September 19, 2016 at 13:38 GMT
			DESCRIPTION
				"Add new node hwMbrMngFabricPortModeFlag"

            REVISION "201608271338Z"		-- August 27, 2016 at 13:38 GMT
			DESCRIPTION
				"Add new node hwAsMode"

            REVISION "201602021407Z"		-- February 02, 2016 at 14:07 GMT
			DESCRIPTION
				"modify node description LSWCCB-13623 "

			REVISION "201601141407Z"		-- January 14, 2016 at 14:07 GMT
			DESCRIPTION
				"Add new node hwAsSlotModel "

			REVISION "201510191407Z"		-- July 09, 2015 at 14:07 GMT
			DESCRIPTION
				"Add new table hwUnAuthenUserTable "

			REVISION "201507091407Z"		-- July 09, 2015 at 14:07 GMT
			DESCRIPTION
				"Add new node hwAsVpnInstance "

			REVISION "201501091407Z"		-- January 09, 2015 at 14:07 GMT
			DESCRIPTION
				"Add new trap node hwTplmDirectCmdRecoverFail LSWCCB-9570"
			REVISION "201411181530Z"		-- November 18, 2014 at 15:30 GMT
			DESCRIPTION
				"Modify node description LSWV2R7-9213 at 2014-11-18"
			REVISION "201410291657Z"		-- October 29, 2014 at 16:57 GMT
			DESCRIPTION
				"Modify node description LSWCCB-8222 at 2014-10-29"
			REVISION "201410231530Z"		-- October 23, 2014 at 15:30 GMT
			DESCRIPTION
				"Modify as entity trap at 2014-10-23"
			REVISION "201409111530Z"		-- September 11, 2014 at 15:30 GMT
			DESCRIPTION
				"Add new trap node at 2014-9-11"
			REVISION "201408191530Z"		-- August 19, 2014 at 15:30 GMT
			DESCRIPTION
				"Modify node description LSWCCB-6116 LSWCCB-6553 LSWCCB-6908 at 2014-8-19"
			REVISION "201407101250Z"		-- July 10, 2014 at 12:50 GMT
			DESCRIPTION
				"Add trap node hwTplmCmdExecuteSuccessfulNotify at 2014-7-10"
			REVISION "201403032000Z"		-- March 03, 2014 at 20:00 GMT
			DESCRIPTION
				"Create mib."
			::= { hwDatacomm 327 }



--
-- Textual conventions
--

		AlarmStatus ::= TEXTUAL-CONVENTION
			STATUS current
			DESCRIPTION
				"Represents the possible values of alarm status.
				When no bits of this attribute are set, then none of the
				status conditions described below are present. When the
				value of under repair is set, the resource is currently
				being repaired.

				When the value of critical is set, one or more critical
				alarms are active against the resource. When the value of
				major is set, one or more major alarms are active against
				the resource. When the value of minor is set, one or more
				minor alarms are active against the resource. When the
				value of warning is set, one or more warning alarms are
				active against the resource. When the value of
				indeterminate is set, one or more  alarms of indeterminate
				severity are active against the resource.

				When the value of alarm outstanding is set, one or more
				alarms is active against the resource. The fault may or may
				not be disabling. "
			REFERENCE
				"ITU Recommendation X.731, 'Information Technology - Open
				Systems Interconnection - System Management: State
				Management Function', 1992"
			SYNTAX BITS
				{
				notSupported(0),
				underRepair(1),
				critical(2),
				major(3),
				minor(4),
				alarmOutstanding(5),
				warning(6),
				indeterminate(7)
				}


--
-- Node definitions
--

		-- 1.3.6.1.4.1.2011.5.25.327.1
		hwUnimngObjects OBJECT IDENTIFIER ::= { hwUnimngMIB 1 }


		-- 1.3.6.1.4.1.2011.5.25.327.1.1
		hwUniMngEnable OBJECT-TYPE
			SYNTAX INTEGER
				{
				enabled(1),
				disabled(2)
				}
			MAX-ACCESS read-write
			STATUS current
			DESCRIPTION
				"Unimng enable status."
			::= { hwUnimngObjects 1 }


		-- 1.3.6.1.4.1.2011.5.25.327.2
		hwAsmngObjects OBJECT IDENTIFIER ::= { hwUnimngMIB 2 }


		-- 1.3.6.1.4.1.2011.5.25.327.2.1
		hwAsTable OBJECT-TYPE
			SYNTAX SEQUENCE OF HwAsEntry
			MAX-ACCESS not-accessible
			STATUS current
			DESCRIPTION
				"AS table entry. "
			::= { hwAsmngObjects 1 }


		-- 1.3.6.1.4.1.2011.5.25.327.2.1.1
		hwAsEntry OBJECT-TYPE
			SYNTAX HwAsEntry
			MAX-ACCESS not-accessible
			STATUS current
			DESCRIPTION
				"The entry of AS table."
			INDEX { hwAsIndex }
			::= { hwAsTable 1 }


		HwAsEntry ::=
			SEQUENCE {
				hwAsIndex
					Integer32,
				hwAsHardwareVersion
					OCTET STRING,
				hwAsIpAddress
					IpAddress,
				hwAsIpNetMask
					IpAddress,
				hwAsAccessUser
					Integer32,
				hwAsMac
					MacAddress,
				hwAsSn
					OCTET STRING,
				hwAsSysName
					OCTET STRING,
				hwAsRunState
					INTEGER,
				hwAsSoftwareVersion
					OCTET STRING,
				hwAsModel
					OCTET STRING,
				hwAsDns
					IpAddress,
				hwAsOnlineTime
					OCTET STRING,
				hwAsCpuUseage
					Integer32,
				hwAsMemoryUseage
					Integer32,
				hwAsSysMac
					MacAddress,
				hwAsStackEnable
					INTEGER,
				hwAsGatewayIp
					IpAddress,
				hwAsVpnInstance
					OCTET STRING,
				hwAsMode
					INTEGER,
				hwAsRowstatus
					RowStatus
			 }

		-- 1.3.6.1.4.1.2011.5.25.327.2.1.1.1
		hwAsIndex OBJECT-TYPE
			SYNTAX Integer32 (1..256)
			MAX-ACCESS read-only
			STATUS current
			DESCRIPTION
				"AS index."
			::= { hwAsEntry 1 }


		-- 1.3.6.1.4.1.2011.5.25.327.2.1.1.2
		hwAsHardwareVersion OBJECT-TYPE
			SYNTAX OCTET STRING (SIZE (0..64))
			MAX-ACCESS read-create
			STATUS current
			DESCRIPTION
				"The hardware version of AS."
			::= { hwAsEntry 2 }


		-- 1.3.6.1.4.1.2011.5.25.327.2.1.1.3
		hwAsIpAddress OBJECT-TYPE
			SYNTAX IpAddress
			MAX-ACCESS read-create
			STATUS current
			DESCRIPTION
				"The ip address of AS."
			::= { hwAsEntry 3 }


		-- 1.3.6.1.4.1.2011.5.25.327.2.1.1.4
		hwAsIpNetMask OBJECT-TYPE
			SYNTAX IpAddress
			MAX-ACCESS read-create
			STATUS current
			DESCRIPTION
				"The ip net mask of AS."
			::= { hwAsEntry 4 }


		-- 1.3.6.1.4.1.2011.5.25.327.2.1.1.5
		hwAsAccessUser OBJECT-TYPE
			SYNTAX Integer32
			MAX-ACCESS read-create
			STATUS current
			DESCRIPTION
				"The access user number of AS."
			::= { hwAsEntry 5 }


		-- 1.3.6.1.4.1.2011.5.25.327.2.1.1.6
		hwAsMac OBJECT-TYPE
			SYNTAX MacAddress
			MAX-ACCESS read-create
			STATUS current
			DESCRIPTION
				"The MAC address of AS."
			::= { hwAsEntry 6 }


		-- 1.3.6.1.4.1.2011.5.25.327.2.1.1.7
		hwAsSn OBJECT-TYPE
			SYNTAX OCTET STRING
			MAX-ACCESS read-create
			STATUS current
			DESCRIPTION
				"The SN of AS."
			::= { hwAsEntry 7 }


		-- 1.3.6.1.4.1.2011.5.25.327.2.1.1.8
		hwAsSysName OBJECT-TYPE
			SYNTAX OCTET STRING (SIZE (1..31))
			MAX-ACCESS read-create
			STATUS current
			DESCRIPTION
				"The Name of AS."
			::= { hwAsEntry 8 }


		-- 1.3.6.1.4.1.2011.5.25.327.2.1.1.9
		hwAsRunState OBJECT-TYPE
			SYNTAX INTEGER
				{
				idle(1),
				versionMismatch(2),
				fault(3),
				normal(4)
				}
			MAX-ACCESS read-create
			STATUS current
			DESCRIPTION
				"The run state of AS."
			::= { hwAsEntry 9 }


		-- 1.3.6.1.4.1.2011.5.25.327.2.1.1.10
		hwAsSoftwareVersion OBJECT-TYPE
			SYNTAX OCTET STRING (SIZE (0..64))
			MAX-ACCESS read-create
			STATUS current
			DESCRIPTION
				"The software version of AS."
			::= { hwAsEntry 10 }


		-- 1.3.6.1.4.1.2011.5.25.327.2.1.1.11
		hwAsModel OBJECT-TYPE
			SYNTAX OCTET STRING (SIZE (1..23))
			MAX-ACCESS read-create
			STATUS current
			DESCRIPTION
				"The model of AS. "
			::= { hwAsEntry 11 }


		-- 1.3.6.1.4.1.2011.5.25.327.2.1.1.12
		hwAsDns OBJECT-TYPE
			SYNTAX IpAddress
			MAX-ACCESS read-create
			STATUS current
			DESCRIPTION
				"The DNS of AS."
			::= { hwAsEntry 12 }


		-- 1.3.6.1.4.1.2011.5.25.327.2.1.1.13
		hwAsOnlineTime OBJECT-TYPE
			SYNTAX OCTET STRING
			MAX-ACCESS read-create
			STATUS current
			DESCRIPTION
				"The online time of AS."
			::= { hwAsEntry 13 }


		-- 1.3.6.1.4.1.2011.5.25.327.2.1.1.14
		hwAsCpuUseage OBJECT-TYPE
			SYNTAX Integer32
			MAX-ACCESS read-create
			STATUS current
			DESCRIPTION
				"The cpu usage of AS."
			::= { hwAsEntry 14 }


		-- 1.3.6.1.4.1.2011.5.25.327.2.1.1.15
		hwAsMemoryUseage OBJECT-TYPE
			SYNTAX Integer32
			MAX-ACCESS read-create
			STATUS current
			DESCRIPTION
				"The memory usage of AS."
			::= { hwAsEntry 15 }


		-- 1.3.6.1.4.1.2011.5.25.327.2.1.1.16
		hwAsSysMac OBJECT-TYPE
			SYNTAX MacAddress
			MAX-ACCESS read-create
			STATUS current
			DESCRIPTION
				"The system MAC address of AS."
			::= { hwAsEntry 16 }


		-- 1.3.6.1.4.1.2011.5.25.327.2.1.1.17
		hwAsStackEnable OBJECT-TYPE
			SYNTAX INTEGER
				{
				enabled(1),
				disabled(2)
				}
			MAX-ACCESS read-create
			STATUS current
			DESCRIPTION
				"Whether AS is stack enable or disable."
			::= { hwAsEntry 17 }


		-- 1.3.6.1.4.1.2011.5.25.327.2.1.1.18
		hwAsGatewayIp OBJECT-TYPE
			SYNTAX IpAddress
			MAX-ACCESS read-create
			STATUS current
			DESCRIPTION
				"The gateway's IP address of AS."
			::= { hwAsEntry 18 }

		-- 1.3.6.1.4.1.2011.5.25.327.2.1.1.19
		hwAsVpnInstance OBJECT-TYPE
			SYNTAX OCTET STRING
			MAX-ACCESS read-only
			STATUS current
			DESCRIPTION
				"The VPN instance of AS."
			::= { hwAsEntry 19 }

		-- 1.3.6.1.4.1.2011.5.25.327.2.1.1.20
		hwAsMode OBJECT-TYPE
			SYNTAX INTEGER
				{
				centralized(1),
				independent(2)
				}
			MAX-ACCESS read-only
			STATUS current
			DESCRIPTION
				"The mode of AS."
			::= { hwAsEntry 20 }


		-- 1.3.6.1.4.1.2011.5.25.327.2.1.1.50
		hwAsRowstatus OBJECT-TYPE
			SYNTAX RowStatus
			MAX-ACCESS read-create
			STATUS current
			DESCRIPTION
				"The RowStatus of this table."
			::= { hwAsEntry 50 }


		-- 1.3.6.1.4.1.2011.5.25.327.2.2
		hwAsIfTable OBJECT-TYPE
			SYNTAX SEQUENCE OF HwAsIfEntry
			MAX-ACCESS not-accessible
			STATUS current
			DESCRIPTION
				"AS interface table entry."
			::= { hwAsmngObjects 2 }


		-- 1.3.6.1.4.1.2011.5.25.327.2.2.1
		hwAsIfEntry OBJECT-TYPE
			SYNTAX HwAsIfEntry
			MAX-ACCESS not-accessible
			STATUS current
			DESCRIPTION
				"The entry of AS If table."
			INDEX { hwAsIfIndex }
			::= { hwAsIfTable 1 }


		HwAsIfEntry ::=
			SEQUENCE {
				hwAsIfIndex
					Integer32,
				hwAsIfDescr
					OCTET STRING,
				hwAsIfType
					Integer32,
				hwAsIfMtu
					Integer32,
				hwAsIfSpeed
					Gauge32,
				hwAsIfPhysAddress
					OCTET STRING,
				hwAsIfAdminStatus
					INTEGER,
				hwAsIfOperStatus
					INTEGER,
				hwAsIfInUcastPkts
					Counter32,
				hwAsIfOutUcastPkts
					Counter32
			 }

		-- 1.3.6.1.4.1.2011.5.25.327.2.2.1.1
		hwAsIfIndex OBJECT-TYPE
			SYNTAX Integer32
			MAX-ACCESS read-only
			STATUS current
			DESCRIPTION
				"The interface index of AS."
			::= { hwAsIfEntry 1 }


		-- 1.3.6.1.4.1.2011.5.25.327.2.2.1.2
		hwAsIfDescr OBJECT-TYPE
			SYNTAX OCTET STRING
			MAX-ACCESS read-only
			STATUS current
			DESCRIPTION
				"The interface description of AS."
			::= { hwAsIfEntry 2 }


		-- 1.3.6.1.4.1.2011.5.25.327.2.2.1.3
		hwAsIfType OBJECT-TYPE
			SYNTAX Integer32
			MAX-ACCESS read-only
			STATUS current
			DESCRIPTION
				"The interface type of AS."
			::= { hwAsIfEntry 3 }


		-- 1.3.6.1.4.1.2011.5.25.327.2.2.1.4
		hwAsIfMtu OBJECT-TYPE
			SYNTAX Integer32
			MAX-ACCESS read-write
			STATUS current
			DESCRIPTION
				"The interface MTU of AS."
			::= { hwAsIfEntry 4 }


		-- 1.3.6.1.4.1.2011.5.25.327.2.2.1.5
		hwAsIfSpeed OBJECT-TYPE
			SYNTAX Gauge32
			MAX-ACCESS read-only
			STATUS current
			DESCRIPTION
				"An estimate of the as interface's current bandwidth in bits per second."
			::= { hwAsIfEntry 5 }


		-- 1.3.6.1.4.1.2011.5.25.327.2.2.1.6
		hwAsIfPhysAddress OBJECT-TYPE
			SYNTAX OCTET STRING
			MAX-ACCESS read-only
			STATUS current
			DESCRIPTION
				"The physical address of AS interface."
			::= { hwAsIfEntry 6 }


		-- 1.3.6.1.4.1.2011.5.25.327.2.2.1.7
		hwAsIfAdminStatus OBJECT-TYPE
			SYNTAX INTEGER
				{
				up(1),
				down(2)
				}
			MAX-ACCESS read-write
			STATUS current
			DESCRIPTION
				"The administration stauts of AS interface."
			::= { hwAsIfEntry 7 }


		-- 1.3.6.1.4.1.2011.5.25.327.2.2.1.8
		hwAsIfOperStatus OBJECT-TYPE
			SYNTAX INTEGER
				{
				up(1),
				down(2)
				}
			MAX-ACCESS read-only
			STATUS current
			DESCRIPTION
				"The operation stauts of AS interface."
			::= { hwAsIfEntry 8 }


		-- 1.3.6.1.4.1.2011.5.25.327.2.2.1.9
		hwAsIfInUcastPkts OBJECT-TYPE
			SYNTAX Counter32
			MAX-ACCESS read-only
			STATUS current
			DESCRIPTION
				"The number of unicast packets received on the interface of AS. "
			::= { hwAsIfEntry 9 }


		-- 1.3.6.1.4.1.2011.5.25.327.2.2.1.10
		hwAsIfOutUcastPkts OBJECT-TYPE
			SYNTAX Counter32
			MAX-ACCESS read-only
			STATUS current
			DESCRIPTION
				"The number of unicast packets sent on the interface of AS. "
			::= { hwAsIfEntry 10 }


		-- 1.3.6.1.4.1.2011.5.25.327.2.3
		hwAsIfXTable OBJECT-TYPE
			SYNTAX SEQUENCE OF HwAsIfXEntry
			MAX-ACCESS not-accessible
			STATUS current
			DESCRIPTION
				"The extent table of AS."
			::= { hwAsmngObjects 3 }


		-- 1.3.6.1.4.1.2011.5.25.327.2.3.1
		hwAsIfXEntry OBJECT-TYPE
			SYNTAX HwAsIfXEntry
			MAX-ACCESS not-accessible
			STATUS current
			DESCRIPTION
				"The entry of table."
			INDEX { hwAsIfIndex }
			::= { hwAsIfXTable 1 }


		HwAsIfXEntry ::=
			SEQUENCE {
				hwAsIfName
					OCTET STRING,
				hwAsIfLinkUpDownTrapEnable
					INTEGER,
				hwAsIfHighSpeed
					Integer32,
				hwAsIfAlias
					OCTET STRING,
				hwAsIfAsId
					Integer32,
				hwAsIfHCOutOctets
					Counter64,
				hwAsIfInMulticastPkts
					Counter32,
				hwAsIfInBroadcastPkts
					Counter32,
				hwAsIfOutMulticastPkts
					Counter32,
				hwAsIfOutBroadcastPkts
					Counter32,
				hwAsIfHCInOctets
					Counter64,
				hwAsIfXLastUpTime
					OCTET STRING,
				hwAsIfXLastDownTime
					OCTET STRING
			 }

		-- 1.3.6.1.4.1.2011.5.25.327.2.3.1.1
		hwAsIfName OBJECT-TYPE
			SYNTAX OCTET STRING
			MAX-ACCESS read-only
			STATUS current
			DESCRIPTION
				"The name of AS interface."
			::= { hwAsIfXEntry 1 }


		-- 1.3.6.1.4.1.2011.5.25.327.2.3.1.2
		hwAsIfLinkUpDownTrapEnable OBJECT-TYPE
			SYNTAX INTEGER
				{
				enabled(1),
				disabled(2)
				}
			MAX-ACCESS read-write
			STATUS current
			DESCRIPTION
				"Indicates whether linkUp/linkDown traps should be generated for this as interface."
			::= { hwAsIfXEntry 2 }


		-- 1.3.6.1.4.1.2011.5.25.327.2.3.1.3
		hwAsIfHighSpeed OBJECT-TYPE
			SYNTAX Integer32
			MAX-ACCESS read-only
			STATUS current
			DESCRIPTION
				"An estimate of the as interface's current bandwidth in units of 1,000,000 bits per second."
			::= { hwAsIfXEntry 3 }


		-- 1.3.6.1.4.1.2011.5.25.327.2.3.1.4
		hwAsIfAlias OBJECT-TYPE
			SYNTAX OCTET STRING
			MAX-ACCESS read-write
			STATUS current
			DESCRIPTION
				"This object is an 'alias' name for the AS's interface as specified by a network manager, and provides a non-volatile 'handle' for the interface."
			::= { hwAsIfXEntry 4 }


		-- 1.3.6.1.4.1.2011.5.25.327.2.3.1.5
		hwAsIfAsId OBJECT-TYPE
			SYNTAX Integer32
			MAX-ACCESS read-only
			STATUS current
			DESCRIPTION
				"The ID of AS."
			::= { hwAsIfXEntry 5 }


		-- 1.3.6.1.4.1.2011.5.25.327.2.3.1.6
		hwAsIfHCOutOctets OBJECT-TYPE
			SYNTAX Counter64
			MAX-ACCESS read-only
			STATUS current
			DESCRIPTION
				"The total number of octets sent on the interface of AS."
			::= { hwAsIfXEntry 6 }


		-- 1.3.6.1.4.1.2011.5.25.327.2.3.1.7
		hwAsIfInMulticastPkts OBJECT-TYPE
			SYNTAX Counter32
			MAX-ACCESS read-only
			STATUS current
			DESCRIPTION
				"The number of multicast packets received on the interface of AS. "
			::= { hwAsIfXEntry 7 }


		-- 1.3.6.1.4.1.2011.5.25.327.2.3.1.8
		hwAsIfInBroadcastPkts OBJECT-TYPE
			SYNTAX Counter32
			MAX-ACCESS read-only
			STATUS current
			DESCRIPTION
				"The number of broadcast packets received on the interface of AS. "
			::= { hwAsIfXEntry 8 }


		-- 1.3.6.1.4.1.2011.5.25.327.2.3.1.9
		hwAsIfOutMulticastPkts OBJECT-TYPE
			SYNTAX Counter32
			MAX-ACCESS read-only
			STATUS current
			DESCRIPTION
				"The number of multicast packets sent on the interface of AS. "
			::= { hwAsIfXEntry 9 }


		-- 1.3.6.1.4.1.2011.5.25.327.2.3.1.10
		hwAsIfOutBroadcastPkts OBJECT-TYPE
			SYNTAX Counter32
			MAX-ACCESS read-only
			STATUS current
			DESCRIPTION
				"The number of broadcast packets sent on the interface of AS. "
			::= { hwAsIfXEntry 10 }


		-- 1.3.6.1.4.1.2011.5.25.327.2.3.1.11
		hwAsIfHCInOctets OBJECT-TYPE
			SYNTAX Counter64
			MAX-ACCESS read-only
			STATUS current
			DESCRIPTION
				"The total number of octets received on the interface of AS."
			::= { hwAsIfXEntry 11 }


		-- 1.3.6.1.4.1.2011.5.25.327.2.3.1.12
		hwAsIfXLastUpTime OBJECT-TYPE
			SYNTAX OCTET STRING
			MAX-ACCESS read-only
			STATUS current
			DESCRIPTION
				"The last up time of AS interface."
			::= { hwAsIfXEntry 12 }


		-- 1.3.6.1.4.1.2011.5.25.327.2.3.1.13
		hwAsIfXLastDownTime OBJECT-TYPE
			SYNTAX OCTET STRING
			MAX-ACCESS read-only
			STATUS current
			DESCRIPTION
				"The last down time of AS interface."
			::= { hwAsIfXEntry 13 }

		-- 1.3.6.1.4.1.2011.5.25.327.2.4
		hwAsSlotTable OBJECT-TYPE
			SYNTAX SEQUENCE OF HwAsSlotEntry
			MAX-ACCESS not-accessible
			STATUS current
			DESCRIPTION
				"The slot table of AS."
			::= { hwAsmngObjects 4 }


		-- 1.3.6.1.4.1.2011.5.25.327.2.4.1
		hwAsSlotEntry OBJECT-TYPE
			SYNTAX HwAsSlotEntry
			MAX-ACCESS not-accessible
			STATUS current
			DESCRIPTION
				"The entry of table."
			INDEX { hwAsIndex, hwAsSlotId }
			::= { hwAsSlotTable 1 }


		HwAsSlotEntry ::=
			SEQUENCE {
				hwAsSlotId
					Integer32,
				hwAsSlotState
					INTEGER,
				hwAsSlotModel
					OCTET STRING,
				hwAsSlotRowStatus
					RowStatus
			 }

		-- 1.3.6.1.4.1.2011.5.25.327.2.4.1.1
		hwAsSlotId OBJECT-TYPE
			SYNTAX Integer32 (0..8)
			MAX-ACCESS not-accessible
			STATUS current
			DESCRIPTION
				"The ID of AS slot."
			::= { hwAsSlotEntry 1 }


		-- 1.3.6.1.4.1.2011.5.25.327.2.4.1.2
		hwAsSlotState OBJECT-TYPE
			SYNTAX INTEGER
				{
				enabled(1),
				disabled(2)
				}
			MAX-ACCESS read-create
			STATUS current
			DESCRIPTION
				"The state of AS slot."
			::= { hwAsSlotEntry 2 }

		-- 1.3.6.1.4.1.2011.5.25.327.2.4.1.3
		hwAsSlotModel OBJECT-TYPE
			SYNTAX OCTET STRING (SIZE (1..23))
			MAX-ACCESS read-create
			STATUS current
			DESCRIPTION
				"The slot model of AS. "
			::= { hwAsSlotEntry 3 }

		-- 1.3.6.1.4.1.2011.5.25.327.2.4.1.20
		hwAsSlotRowStatus OBJECT-TYPE
			SYNTAX RowStatus
			MAX-ACCESS read-create
			STATUS current
			DESCRIPTION
				"The RowStatus of this table."
			::= { hwAsSlotEntry 20 }


		-- 1.3.6.1.4.1.2011.5.25.327.2.5
		hwAsmngGlobalObjects OBJECT IDENTIFIER ::= { hwAsmngObjects 5 }


		-- 1.3.6.1.4.1.2011.5.25.327.2.5.1
		hwAsAutoReplaceEnable OBJECT-TYPE
			SYNTAX INTEGER
				{
				enabled(1),
				disabled(2)
				}
			MAX-ACCESS read-write
			STATUS current
			DESCRIPTION
				"The enable status of auto replace."
			::= { hwAsmngGlobalObjects 1 }


		-- 1.3.6.1.4.1.2011.5.25.327.2.5.2
		hwAsAuthMode OBJECT-TYPE
			SYNTAX INTEGER
				{
				auth(1),
				noAuth(2)
				}
			MAX-ACCESS read-write
			STATUS current
			DESCRIPTION
				"The authentication mode of AS."
			::= { hwAsmngGlobalObjects 2 }


		-- 1.3.6.1.4.1.2011.5.25.327.2.6
		hwAsMacWhitelistTable OBJECT-TYPE
			SYNTAX SEQUENCE OF HwAsMacWhitelistEntry
			MAX-ACCESS not-accessible
			STATUS current
			DESCRIPTION
				"The table of whitelist."
			::= { hwAsmngObjects 6 }


		-- 1.3.6.1.4.1.2011.5.25.327.2.6.1
		hwAsMacWhitelistEntry OBJECT-TYPE
			SYNTAX HwAsMacWhitelistEntry
			MAX-ACCESS not-accessible
			STATUS current
			DESCRIPTION
				"The entry of table."
			INDEX { hwAsMacWhitelistMacAddr }
			::= { hwAsMacWhitelistTable 1 }


		HwAsMacWhitelistEntry ::=
			SEQUENCE {
				hwAsMacWhitelistMacAddr
					MacAddress,
				hwAsMacWhitelistRowStatus
					RowStatus
			 }

		-- 1.3.6.1.4.1.2011.5.25.327.2.6.1.1
		hwAsMacWhitelistMacAddr OBJECT-TYPE
			SYNTAX MacAddress
			MAX-ACCESS not-accessible
			STATUS current
			DESCRIPTION
				"The MAC address of white list."
			::= { hwAsMacWhitelistEntry 1 }


		-- 1.3.6.1.4.1.2011.5.25.327.2.6.1.2
		hwAsMacWhitelistRowStatus OBJECT-TYPE
			SYNTAX RowStatus
			MAX-ACCESS read-create
			STATUS current
			DESCRIPTION
				"The RowStatus of table."
			::= { hwAsMacWhitelistEntry 2 }


		-- 1.3.6.1.4.1.2011.5.25.327.2.7
		hwAsMacBlacklistTable OBJECT-TYPE
			SYNTAX SEQUENCE OF HwAsMacBlacklistEntry
			MAX-ACCESS not-accessible
			STATUS current
			DESCRIPTION
				"The table of blacklist."
			::= { hwAsmngObjects 7 }


		-- 1.3.6.1.4.1.2011.5.25.327.2.7.1
		hwAsMacBlacklistEntry OBJECT-TYPE
			SYNTAX HwAsMacBlacklistEntry
			MAX-ACCESS not-accessible
			STATUS current
			DESCRIPTION
				"The entry of table."
			INDEX { hwAsMacBlacklistMacAddr }
			::= { hwAsMacBlacklistTable 1 }


		HwAsMacBlacklistEntry ::=
			SEQUENCE {
				hwAsMacBlacklistMacAddr
					MacAddress,
				hwAsMacBlacklistRowStatus
					RowStatus
			 }

		-- 1.3.6.1.4.1.2011.5.25.327.2.7.1.1
		hwAsMacBlacklistMacAddr OBJECT-TYPE
			SYNTAX MacAddress
			MAX-ACCESS not-accessible
			STATUS current
			DESCRIPTION
				"The MAC address of black list."
			::= { hwAsMacBlacklistEntry 1 }


		-- 1.3.6.1.4.1.2011.5.25.327.2.7.1.2
		hwAsMacBlacklistRowStatus OBJECT-TYPE
			SYNTAX RowStatus
			MAX-ACCESS read-create
			STATUS current
			DESCRIPTION
				"The RowStatus of table."
			::= { hwAsMacBlacklistEntry 2 }


		-- 1.3.6.1.4.1.2011.5.25.327.2.8
		hwAsEntityPhysicalTable OBJECT-TYPE
			SYNTAX SEQUENCE OF HwAsEntityPhysicalEntry
			MAX-ACCESS not-accessible
			STATUS current
			DESCRIPTION
				"The physical table of AS."
			::= { hwAsmngObjects 8 }


		-- 1.3.6.1.4.1.2011.5.25.327.2.8.1
		hwAsEntityPhysicalEntry OBJECT-TYPE
			SYNTAX HwAsEntityPhysicalEntry
			MAX-ACCESS not-accessible
			STATUS current
			DESCRIPTION
				"The entry of table."
			INDEX { hwAsIndex, hwAsEntityPhysicalIndex }
			::= { hwAsEntityPhysicalTable 1 }


		HwAsEntityPhysicalEntry ::=
			SEQUENCE {
				hwAsEntityPhysicalIndex
					Integer32,
				hwAsEntityPhysicalDescr
					OCTET STRING,
				hwAsEntityPhysicalVendorType
					AutonomousType,
				hwAsEntityPhysicalContainedIn
					Integer32,
				hwAsEntityPhysicalClass
					INTEGER,
				hwAsEntityPhysicalParentRelPos
					Integer32,
				hwAsEntityPhysicalName
					OCTET STRING,
				hwAsEntityPhysicalHardwareRev
					OCTET STRING,
				hwAsEntityPhysicalFirmwareRev
					OCTET STRING,
				hwAsEntityPhysicalSoftwareRev
					OCTET STRING,
				hwAsEntityPhysicalSerialNum
					OCTET STRING,
				hwAsEntityPhysicalMfgName
					OCTET STRING
			 }

		-- 1.3.6.1.4.1.2011.5.25.327.2.8.1.1
		hwAsEntityPhysicalIndex OBJECT-TYPE
			SYNTAX Integer32
			MAX-ACCESS not-accessible
			STATUS current
			DESCRIPTION
				"The physical index of AS."
			::= { hwAsEntityPhysicalEntry 1 }


		-- 1.3.6.1.4.1.2011.5.25.327.2.8.1.2
		hwAsEntityPhysicalDescr OBJECT-TYPE
			SYNTAX OCTET STRING
			MAX-ACCESS read-only
			STATUS current
			DESCRIPTION
				"A textual description of physical entity. "
			::= { hwAsEntityPhysicalEntry 2 }


		-- 1.3.6.1.4.1.2011.5.25.327.2.8.1.3
		hwAsEntityPhysicalVendorType OBJECT-TYPE
			SYNTAX AutonomousType
			MAX-ACCESS read-only
			STATUS current
			DESCRIPTION
				"An indication of the vendor-specific hardware type of the physical entity.  "
			::= { hwAsEntityPhysicalEntry 3 }


		-- 1.3.6.1.4.1.2011.5.25.327.2.8.1.4
		hwAsEntityPhysicalContainedIn OBJECT-TYPE
			SYNTAX Integer32
			MAX-ACCESS read-only
			STATUS current
			DESCRIPTION
				"The value of hwAsEntityPhysicalIndex for the physical entity which 'contains' this physical entity.  "
			::= { hwAsEntityPhysicalEntry 4 }


		-- 1.3.6.1.4.1.2011.5.25.327.2.8.1.5
		hwAsEntityPhysicalClass OBJECT-TYPE
			SYNTAX INTEGER
				{
				other(1),
				unknown(2),
				chassis(3),
				backplane(4),
				container(5),
				powerSupply(6),
				fan(7),
				sensor(8),
				module(9),
				port(10),
				stack(11)
				}
			MAX-ACCESS read-only
			STATUS current
			DESCRIPTION
				"An indication of the general hardware type of the physical entity."
			::= { hwAsEntityPhysicalEntry 5 }


		-- 1.3.6.1.4.1.2011.5.25.327.2.8.1.6
		hwAsEntityPhysicalParentRelPos OBJECT-TYPE
			SYNTAX Integer32
			MAX-ACCESS read-only
			STATUS current
			DESCRIPTION
				"An indication of the relative position of this 'child' component among all its 'sibling' components."
			::= { hwAsEntityPhysicalEntry 6 }


		-- 1.3.6.1.4.1.2011.5.25.327.2.8.1.7
		hwAsEntityPhysicalName OBJECT-TYPE
			SYNTAX OCTET STRING
			MAX-ACCESS read-only
			STATUS current
			DESCRIPTION
				"The textual name of the physical entity. "
			::= { hwAsEntityPhysicalEntry 7 }


		-- 1.3.6.1.4.1.2011.5.25.327.2.8.1.8
		hwAsEntityPhysicalHardwareRev OBJECT-TYPE
			SYNTAX OCTET STRING
			MAX-ACCESS read-only
			STATUS current
			DESCRIPTION
				"The vendor-specific hardware revision string for the physical entity. "
			::= { hwAsEntityPhysicalEntry 8 }


		-- 1.3.6.1.4.1.2011.5.25.327.2.8.1.9
		hwAsEntityPhysicalFirmwareRev OBJECT-TYPE
			SYNTAX OCTET STRING
			MAX-ACCESS read-only
			STATUS current
			DESCRIPTION
				"The vendor-specific firmware revision string for the physical entity."
			::= { hwAsEntityPhysicalEntry 9 }


		-- 1.3.6.1.4.1.2011.5.25.327.2.8.1.10
		hwAsEntityPhysicalSoftwareRev OBJECT-TYPE
			SYNTAX OCTET STRING
			MAX-ACCESS read-only
			STATUS current
			DESCRIPTION
				"The vendor-specific software revision string for the physical entity."
			::= { hwAsEntityPhysicalEntry 10 }


		-- 1.3.6.1.4.1.2011.5.25.327.2.8.1.11
		hwAsEntityPhysicalSerialNum OBJECT-TYPE
			SYNTAX OCTET STRING
			MAX-ACCESS read-only
			STATUS current
			DESCRIPTION
				"The vendor-specific serial number string for the physical entity."
			::= { hwAsEntityPhysicalEntry 11 }


		-- 1.3.6.1.4.1.2011.5.25.327.2.8.1.12
		hwAsEntityPhysicalMfgName OBJECT-TYPE
			SYNTAX OCTET STRING
			MAX-ACCESS read-only
			STATUS current
			DESCRIPTION
				"The name of the manufacturer of this physical component."
			::= { hwAsEntityPhysicalEntry 12 }


		-- 1.3.6.1.4.1.2011.5.25.327.2.9
		hwAsEntityStateTable OBJECT-TYPE
			SYNTAX SEQUENCE OF HwAsEntityStateEntry
			MAX-ACCESS not-accessible
			STATUS current
			DESCRIPTION
				"The entity state table."
			::= { hwAsmngObjects 9 }


		-- 1.3.6.1.4.1.2011.5.25.327.2.9.1
		hwAsEntityStateEntry OBJECT-TYPE
			SYNTAX HwAsEntityStateEntry
			MAX-ACCESS not-accessible
			STATUS current
			DESCRIPTION
				"The entry of table."
			INDEX { hwAsIndex, hwAsEntityPhysicalIndex }
			::= { hwAsEntityStateTable 1 }


		HwAsEntityStateEntry ::=
			SEQUENCE {
				hwAsEntityAdminStatus
					INTEGER,
				hwAsEntityOperStatus
					INTEGER,
				hwAsEntityStandbyStatus
					INTEGER,
				hwAsEntityAlarmLight
					AlarmStatus,
				hwAsEntityPortType
					INTEGER
			 }

		-- 1.3.6.1.4.1.2011.5.25.327.2.9.1.1
		hwAsEntityAdminStatus OBJECT-TYPE
			SYNTAX INTEGER
				{
				notSupported(1),
				locked(2),
				shuttingDown(3),
				unlocked(4),
				up(11),
				down(12),
				loopback(13)
				}
			MAX-ACCESS read-only
			STATUS current
			DESCRIPTION
				"The administrative state for this object."
			::= { hwAsEntityStateEntry 1 }


		-- 1.3.6.1.4.1.2011.5.25.327.2.9.1.2
		hwAsEntityOperStatus OBJECT-TYPE
			SYNTAX INTEGER
				{
				notSupported(1),
				disabled(2),
				enabled(3),
				offline(4),
				up(11),
				down(12),
				connect(13),
				protocolUp(15),
				linkUp(16),
				linkDown(17)
				}
			MAX-ACCESS read-only
			STATUS current
			DESCRIPTION
				"The operational state for this object."
			::= { hwAsEntityStateEntry 2 }


		-- 1.3.6.1.4.1.2011.5.25.327.2.9.1.3
		hwAsEntityStandbyStatus OBJECT-TYPE
			SYNTAX INTEGER
				{
				notSupported(1),
				hotStandby(2),
				coldStandby(3),
				providingService(4)
				}
			MAX-ACCESS read-only
			STATUS current
			DESCRIPTION
				"This object is used for monitoring standby status."
			::= { hwAsEntityStateEntry 3 }


		-- 1.3.6.1.4.1.2011.5.25.327.2.9.1.4
		hwAsEntityAlarmLight OBJECT-TYPE
			SYNTAX AlarmStatus
			MAX-ACCESS read-only
			STATUS current
			DESCRIPTION
				"The alarm status for this entity."
			::= { hwAsEntityStateEntry 4 }


		-- 1.3.6.1.4.1.2011.5.25.327.2.9.1.5
		hwAsEntityPortType OBJECT-TYPE
			SYNTAX INTEGER
				{
				notSupported(1),
				copper(2),
				fiber100(3),
				fiber1000(4),
				fiber10000(5),
				opticalnotExist(6),
				optical(7)
				}
			MAX-ACCESS read-only
			STATUS current
			DESCRIPTION
				"Indicates the type of the Ethernet interface."
			::= { hwAsEntityStateEntry 5 }


		-- 1.3.6.1.4.1.2011.5.25.327.2.10
		hwAsEntityAliasMappingTable OBJECT-TYPE
			SYNTAX SEQUENCE OF HwAsEntityAliasMappingEntry
			MAX-ACCESS not-accessible
			STATUS current
			DESCRIPTION
				"The entity alias mapping table."
			::= { hwAsmngObjects 10 }


		-- 1.3.6.1.4.1.2011.5.25.327.2.10.1
		hwAsEntityAliasMappingEntry OBJECT-TYPE
			SYNTAX HwAsEntityAliasMappingEntry
			MAX-ACCESS not-accessible
			STATUS current
			DESCRIPTION
				"The entry of table."
			INDEX { hwAsIndex, hwAsEntityPhysicalIndex, hwAsEntryAliasLogicalIndexOrZero }
			::= { hwAsEntityAliasMappingTable 1 }


		HwAsEntityAliasMappingEntry ::=
			SEQUENCE {
				hwAsEntryAliasLogicalIndexOrZero
					Integer32,
				hwAsEntryAliasMappingIdentifier
					AutonomousType
			 }

		-- 1.3.6.1.4.1.2011.5.25.327.2.10.1.1
		hwAsEntryAliasLogicalIndexOrZero OBJECT-TYPE
			SYNTAX Integer32
			MAX-ACCESS not-accessible
			STATUS current
			DESCRIPTION
				"The value of this object identifies the logical entity."
			::= { hwAsEntityAliasMappingEntry 1 }


		-- 1.3.6.1.4.1.2011.5.25.327.2.10.1.2
		hwAsEntryAliasMappingIdentifier OBJECT-TYPE
			SYNTAX AutonomousType
			MAX-ACCESS read-only
			STATUS current
			DESCRIPTION
				"The value of this object identifies a particular conceptual row
				associated with the indicated entPhysicalIndex and logical index pair."
			::= { hwAsEntityAliasMappingEntry 2 }


		-- 1.3.6.1.4.1.2011.5.25.327.3
		hwTopomngObjects OBJECT IDENTIFIER ::= { hwUnimngMIB 3 }


		-- 1.3.6.1.4.1.2011.5.25.327.3.1
		hwTopomngExploreTime OBJECT-TYPE
			SYNTAX Integer32 (0..1440)
			MAX-ACCESS read-write
			STATUS current
			DESCRIPTION
				"Topology collect time in minutes."
			DEFVAL { 10 }
			::= { hwTopomngObjects 1 }


		-- 1.3.6.1.4.1.2011.5.25.327.3.2
		hwTopomngLastCollectDuration OBJECT-TYPE
			SYNTAX Integer32
			MAX-ACCESS read-only
			STATUS current
			DESCRIPTION
				"Duration of the latest topology collection, measured in milliseconds."
			::= { hwTopomngObjects 2 }


		-- 1.3.6.1.4.1.2011.5.25.327.3.11
		hwTopomngTopoTable OBJECT-TYPE
			SYNTAX SEQUENCE OF HwTopomngTopoEntry
			MAX-ACCESS not-accessible
			STATUS current
			DESCRIPTION
				"The topology table."
			::= { hwTopomngObjects 11 }


		-- 1.3.6.1.4.1.2011.5.25.327.3.11.1
		hwTopomngTopoEntry OBJECT-TYPE
			SYNTAX HwTopomngTopoEntry
			MAX-ACCESS not-accessible
			STATUS current
			DESCRIPTION
				"The entry of topology table."
			INDEX { hwTopoLocalHop, hwTopoLocalMac, hwTopoPeerDeviceIndex }
			::= { hwTopomngTopoTable 1 }


		HwTopomngTopoEntry ::=
			SEQUENCE {
				hwTopoLocalHop
					Integer32,
				hwTopoLocalMac
					MacAddress,
				hwTopoPeerDeviceIndex
					Integer32,
				hwTopoPeerMac
					MacAddress,
				hwTopoLocalPortName
					OCTET STRING,
				hwTopoPeerPortName
					OCTET STRING,
				hwTopoLocalTrunkId
					Integer32,
				hwTopoPeerTrunkId
					Integer32,
				hwTopoLocalRole
					INTEGER,
				hwTopoPeerRole
					INTEGER
			 }

		-- 1.3.6.1.4.1.2011.5.25.327.3.11.1.1
		hwTopoLocalHop OBJECT-TYPE
			SYNTAX Integer32 (1..8)
			MAX-ACCESS not-accessible
			STATUS current
			DESCRIPTION
				"The topoloy hop."
			::= { hwTopomngTopoEntry 1 }


		-- 1.3.6.1.4.1.2011.5.25.327.3.11.1.2
		hwTopoLocalMac OBJECT-TYPE
			SYNTAX MacAddress
			MAX-ACCESS not-accessible
			STATUS current
			DESCRIPTION
				"The local device ID, defined by 6 bytes of MAC."
			::= { hwTopomngTopoEntry 2 }


		-- 1.3.6.1.4.1.2011.5.25.327.3.11.1.3
		hwTopoPeerDeviceIndex OBJECT-TYPE
			SYNTAX Integer32 (1..65535)
			MAX-ACCESS not-accessible
			STATUS current
			DESCRIPTION
				"The index of neighbor device."
			::= { hwTopomngTopoEntry 3 }


		-- 1.3.6.1.4.1.2011.5.25.327.3.11.1.4
		hwTopoPeerMac OBJECT-TYPE
			SYNTAX MacAddress
			MAX-ACCESS read-only
			STATUS current
			DESCRIPTION
				"The neighbor device ID, defined by 6 bytes of MAC."
			::= { hwTopomngTopoEntry 4 }


		-- 1.3.6.1.4.1.2011.5.25.327.3.11.1.5
		hwTopoLocalPortName OBJECT-TYPE
			SYNTAX OCTET STRING (SIZE (0..64))
			MAX-ACCESS read-only
			STATUS current
			DESCRIPTION
				"The port name of local device, same as ifName (defined in IETF RFC 2863)."
			::= { hwTopomngTopoEntry 5 }


		-- 1.3.6.1.4.1.2011.5.25.327.3.11.1.6
		hwTopoPeerPortName OBJECT-TYPE
			SYNTAX OCTET STRING (SIZE (0..64))
			MAX-ACCESS read-only
			STATUS current
			DESCRIPTION
				"The port name of neighbor device, same as ifName (defined in IETF RFC 2863)."
			::= { hwTopomngTopoEntry 6 }


		-- 1.3.6.1.4.1.2011.5.25.327.3.11.1.7
		hwTopoLocalTrunkId OBJECT-TYPE
			SYNTAX Integer32 (0..65535)
			MAX-ACCESS read-only
			STATUS current
			DESCRIPTION
				"The trunk ID of local port, 65535 identify the local port is not in trunk."
			::= { hwTopomngTopoEntry 7 }


		-- 1.3.6.1.4.1.2011.5.25.327.3.11.1.8
		hwTopoPeerTrunkId OBJECT-TYPE
			SYNTAX Integer32 (0..65535)
			MAX-ACCESS read-only
			STATUS current
			DESCRIPTION
				"The trunk ID of neighbor port, 65535 identify the neighbor port is not in trunk."
			::= { hwTopomngTopoEntry 8 }


		-- 1.3.6.1.4.1.2011.5.25.327.3.11.1.9
		hwTopoLocalRole OBJECT-TYPE
			SYNTAX INTEGER
				{
				roleUC(1),
				roleAS(2),
				roleAP(3)
				}
			MAX-ACCESS read-only
			STATUS current
			DESCRIPTION
				"The role of local topology node."
			::= { hwTopomngTopoEntry 9 }


		-- 1.3.6.1.4.1.2011.5.25.327.3.11.1.10
		hwTopoPeerRole OBJECT-TYPE
			SYNTAX INTEGER
				{
				roleUC(1),
				roleAS(2),
				roleAP(3)
				}
			MAX-ACCESS read-only
			STATUS current
			DESCRIPTION
				"The role of neighbor topology node."
			::= { hwTopomngTopoEntry 10 }


		-- 1.3.6.1.4.1.2011.5.25.327.4
		hwMbrmngObjects OBJECT IDENTIFIER ::= { hwUnimngMIB 4 }


		-- 1.3.6.1.4.1.2011.5.25.327.4.2
		hwMbrMngFabricPortTable OBJECT-TYPE
			SYNTAX SEQUENCE OF HwMbrMngFabricPortEntry
			MAX-ACCESS not-accessible
			STATUS current
			DESCRIPTION
				"The table of fabric port information."
			::= { hwMbrmngObjects 2 }


		-- 1.3.6.1.4.1.2011.5.25.327.4.2.1
		hwMbrMngFabricPortEntry OBJECT-TYPE
			SYNTAX HwMbrMngFabricPortEntry
			MAX-ACCESS not-accessible
			STATUS current
			DESCRIPTION
				"The entry of the table of fabric port information."
			INDEX { hwMbrMngASId, hwMbrMngFabricPortId }
			::= { hwMbrMngFabricPortTable 1 }


		HwMbrMngFabricPortEntry ::=
			SEQUENCE {
				hwMbrMngASId
					Integer32,
				hwMbrMngFabricPortId
					Integer32,
				hwMbrMngFabricPortMemberIfName
					OCTET STRING,
				hwMbrMngFabricPortDirection
					INTEGER,
				hwMbrMngFabricPortIndirectFlag
					INTEGER,
				hwMbrMngFabricPortDescription
					OCTET STRING,
				hwMbrMngFabricPortModeFlag
					INTEGER
			 }

		-- 1.3.6.1.4.1.2011.5.25.327.4.2.1.1
		hwMbrMngASId OBJECT-TYPE
			SYNTAX Integer32 (1..65535)
			MAX-ACCESS not-accessible
			STATUS current
			DESCRIPTION
				"AS index, is used to specify thd AS. 65535 represents the parent node."
			::= { hwMbrMngFabricPortEntry 1 }


		-- 1.3.6.1.4.1.2011.5.25.327.4.2.1.2
		hwMbrMngFabricPortId OBJECT-TYPE
			SYNTAX Integer32 (1..256)
			MAX-ACCESS not-accessible
			STATUS current
			DESCRIPTION
				"The Fabric-port index."
			::= { hwMbrMngFabricPortEntry 2 }


		-- 1.3.6.1.4.1.2011.5.25.327.4.2.1.3
		hwMbrMngFabricPortMemberIfName OBJECT-TYPE
			SYNTAX OCTET STRING (SIZE (1..64))
			MAX-ACCESS read-only
			STATUS current
			DESCRIPTION
				"Interface name of the Fabric-port's member."
			::= { hwMbrMngFabricPortEntry 3 }


		-- 1.3.6.1.4.1.2011.5.25.327.4.2.1.4
		hwMbrMngFabricPortDirection OBJECT-TYPE
			SYNTAX INTEGER
				{
				downDirection(1),
				upDirection(2)
				}
			MAX-ACCESS read-only
			STATUS current
			DESCRIPTION
				"The direction of Fabric-port."
			::= { hwMbrMngFabricPortEntry 4 }


		-- 1.3.6.1.4.1.2011.5.25.327.4.2.1.5
		hwMbrMngFabricPortIndirectFlag OBJECT-TYPE
			SYNTAX INTEGER
				{
				indirect(1),
				direct(2)
				}
			MAX-ACCESS read-only
			STATUS current
			DESCRIPTION
				"The indirect flag of Fabric-port."
			::= { hwMbrMngFabricPortEntry 5 }


		-- 1.3.6.1.4.1.2011.5.25.327.4.2.1.6
		hwMbrMngFabricPortDescription OBJECT-TYPE
			SYNTAX OCTET STRING (SIZE (1..64))
			MAX-ACCESS read-only
			STATUS current
			DESCRIPTION
				"The description of Fabric-port."
			::= { hwMbrMngFabricPortEntry 6 }

		-- 1.3.6.1.4.1.2011.5.25.327.4.2.1.7
		hwMbrMngFabricPortModeFlag OBJECT-TYPE
			SYNTAX INTEGER
				{
				centralized(1),
				independent(2)
				}
			MAX-ACCESS read-only
			STATUS current
			DESCRIPTION
				"Mode of the AS connected to the fabric-port."
			::= { hwMbrMngFabricPortEntry 7 }

		-- 1.3.6.1.4.1.2011.5.25.327.5
		hwVermngObjects OBJECT IDENTIFIER ::= { hwUnimngMIB 5 }


		-- 1.3.6.1.4.1.2011.5.25.327.5.1
		hwVermngGlobalObjects OBJECT IDENTIFIER ::= { hwVermngObjects 1 }


		-- 1.3.6.1.4.1.2011.5.25.327.5.1.1
		hwVermngFileServerType OBJECT-TYPE
			SYNTAX INTEGER
				{
				ftp(1),
				sftp(2),
				none(255)
				}
			MAX-ACCESS read-only
			STATUS current
			DESCRIPTION
				"The type of file server."
			::= { hwVermngGlobalObjects 1 }


		-- 1.3.6.1.4.1.2011.5.25.327.5.2
		hwVermngUpgradeInfoTable OBJECT-TYPE
			SYNTAX SEQUENCE OF HwVermngUpgradeInfoEntry
			MAX-ACCESS not-accessible
			STATUS current
			DESCRIPTION
				"The table of AS upgrade information."
			::= { hwVermngObjects 2 }


		-- 1.3.6.1.4.1.2011.5.25.327.5.2.1
		hwVermngUpgradeInfoEntry OBJECT-TYPE
			SYNTAX HwVermngUpgradeInfoEntry
			MAX-ACCESS not-accessible
			STATUS current
			DESCRIPTION
				"The entry of the table of AS upgrade information."
			INDEX { hwVermngUpgradeInfoAsIndex }
			::= { hwVermngUpgradeInfoTable 1 }


		HwVermngUpgradeInfoEntry ::=
			SEQUENCE {
				hwVermngUpgradeInfoAsIndex
					Integer32,
				hwVermngUpgradeInfoAsName
					DisplayString,
				hwVermngUpgradeInfoAsSysSoftware
					DisplayString,
				hwVermngUpgradeInfoAsSysSoftwareVer
					DisplayString,
				hwVermngUpgradeInfoAsSysPatch
					DisplayString,
				hwVermngUpgradeInfoAsDownloadSoftware
					DisplayString,
				hwVermngUpgradeInfoAsDownloadSoftwareVer
					DisplayString,
				hwVermngUpgradeInfoAsDownloadPatch
					DisplayString,
				hwVermngUpgradeInfoAsUpgradeState
					INTEGER,
				hwVermngUpgradeInfoAsUpgradeType
					INTEGER,
				hwVermngUpgradeInfoAsFilePhase
					INTEGER,
				hwVermngUpgradeInfoAsUpgradePhase
					INTEGER,
				hwVermngUpgradeInfoAsUpgradeResult
					INTEGER,
				hwVermngUpgradeInfoAsErrorCode
					Integer32,
				hwVermngUpgradeInfoAsErrorDescr
					DisplayString
			 }

		-- 1.3.6.1.4.1.2011.5.25.327.5.2.1.1
		hwVermngUpgradeInfoAsIndex OBJECT-TYPE
			SYNTAX Integer32 (1..256)
			MAX-ACCESS not-accessible
			STATUS current
			DESCRIPTION
				"The ID of AS."
			::= { hwVermngUpgradeInfoEntry 1 }


		-- 1.3.6.1.4.1.2011.5.25.327.5.2.1.2
		hwVermngUpgradeInfoAsName OBJECT-TYPE
			SYNTAX DisplayString
			MAX-ACCESS read-only
			STATUS current
			DESCRIPTION
				"The name of AS."
			::= { hwVermngUpgradeInfoEntry 2 }


		-- 1.3.6.1.4.1.2011.5.25.327.5.2.1.3
		hwVermngUpgradeInfoAsSysSoftware OBJECT-TYPE
			SYNTAX DisplayString
			MAX-ACCESS read-only
			STATUS current
			DESCRIPTION
				"The filename of running system software of AS."
			::= { hwVermngUpgradeInfoEntry 3 }


		-- 1.3.6.1.4.1.2011.5.25.327.5.2.1.4
		hwVermngUpgradeInfoAsSysSoftwareVer OBJECT-TYPE
			SYNTAX DisplayString
			MAX-ACCESS read-only
			STATUS current
			DESCRIPTION
				"The version of running system software of AS."
			::= { hwVermngUpgradeInfoEntry 4 }


		-- 1.3.6.1.4.1.2011.5.25.327.5.2.1.5
		hwVermngUpgradeInfoAsSysPatch OBJECT-TYPE
			SYNTAX DisplayString
			MAX-ACCESS read-only
			STATUS current
			DESCRIPTION
				"The filename of running patch of AS."
			::= { hwVermngUpgradeInfoEntry 5 }


		-- 1.3.6.1.4.1.2011.5.25.327.5.2.1.6
		hwVermngUpgradeInfoAsDownloadSoftware OBJECT-TYPE
			SYNTAX DisplayString
			MAX-ACCESS read-only
			STATUS current
			DESCRIPTION
				"The filename of system software which will be downloaded to AS."
			::= { hwVermngUpgradeInfoEntry 6 }


		-- 1.3.6.1.4.1.2011.5.25.327.5.2.1.7
		hwVermngUpgradeInfoAsDownloadSoftwareVer OBJECT-TYPE
			SYNTAX DisplayString
			MAX-ACCESS read-only
			STATUS current
			DESCRIPTION
				"The version of system software which will be downloaded to AS.."
			::= { hwVermngUpgradeInfoEntry 7 }


		-- 1.3.6.1.4.1.2011.5.25.327.5.2.1.8
		hwVermngUpgradeInfoAsDownloadPatch OBJECT-TYPE
			SYNTAX DisplayString
			MAX-ACCESS read-only
			STATUS current
			DESCRIPTION
				"The filename of patch which will be downloaded to AS."
			::= { hwVermngUpgradeInfoEntry 8 }


		-- 1.3.6.1.4.1.2011.5.25.327.5.2.1.9
		hwVermngUpgradeInfoAsUpgradeState OBJECT-TYPE
			SYNTAX INTEGER
				{
				noUpgrade(1),
				upgrading(2),
				none(255)
				}
			MAX-ACCESS read-only
			STATUS current
			DESCRIPTION
				"The upgrade status of AS."
			::= { hwVermngUpgradeInfoEntry 9 }


		-- 1.3.6.1.4.1.2011.5.25.327.5.2.1.10
		hwVermngUpgradeInfoAsUpgradeType OBJECT-TYPE
			SYNTAX INTEGER
				{
				verSync(1),
				manual(2),
				none(255)
				}
			MAX-ACCESS read-only
			STATUS current
			DESCRIPTION
				"The type of upgrade."
			::= { hwVermngUpgradeInfoEntry 10 }


		-- 1.3.6.1.4.1.2011.5.25.327.5.2.1.11
		hwVermngUpgradeInfoAsFilePhase OBJECT-TYPE
			SYNTAX INTEGER
				{
				systemSoftware(1),
				patch(2),
				none(255)
				}
			MAX-ACCESS read-only
			STATUS current
			DESCRIPTION
				"The file type which is in downloading."
			::= { hwVermngUpgradeInfoEntry 11 }


		-- 1.3.6.1.4.1.2011.5.25.327.5.2.1.12
		hwVermngUpgradeInfoAsUpgradePhase OBJECT-TYPE
			SYNTAX INTEGER
				{
				downloadFile(1),
				wait(2),
				activateFile(3),
				reboot(4),
				none(255)
				}
			MAX-ACCESS read-only
			STATUS current
			DESCRIPTION
				"The state in downloading file."
			::= { hwVermngUpgradeInfoEntry 12 }


		-- 1.3.6.1.4.1.2011.5.25.327.5.2.1.13
		hwVermngUpgradeInfoAsUpgradeResult OBJECT-TYPE
			SYNTAX INTEGER
				{
				successful(1),
				failed(2),
				none(255)
				}
			MAX-ACCESS read-only
			STATUS current
			DESCRIPTION
				"The result of upgrade."
			::= { hwVermngUpgradeInfoEntry 13 }


		-- 1.3.6.1.4.1.2011.5.25.327.5.2.1.14
		hwVermngUpgradeInfoAsErrorCode OBJECT-TYPE
			SYNTAX Integer32
			MAX-ACCESS read-only
			STATUS current
			DESCRIPTION
				"The error code in upgrading."
			::= { hwVermngUpgradeInfoEntry 14 }


		-- 1.3.6.1.4.1.2011.5.25.327.5.2.1.15
		hwVermngUpgradeInfoAsErrorDescr OBJECT-TYPE
			SYNTAX DisplayString
			MAX-ACCESS read-only
			STATUS current
			DESCRIPTION
				"The eroor description in upgrading."
			::= { hwVermngUpgradeInfoEntry 15 }


		-- 1.3.6.1.4.1.2011.5.25.327.5.3
		hwVermngAsTypeCfgInfoTable OBJECT-TYPE
			SYNTAX SEQUENCE OF HwVermngAsTypeCfgInfoEntry
			MAX-ACCESS not-accessible
			STATUS current
			DESCRIPTION
				"The table of configuration with AS type."
			::= { hwVermngObjects 3 }


		-- 1.3.6.1.4.1.2011.5.25.327.5.3.1
		hwVermngAsTypeCfgInfoEntry OBJECT-TYPE
			SYNTAX HwVermngAsTypeCfgInfoEntry
			MAX-ACCESS not-accessible
			STATUS current
			DESCRIPTION
				"The entry of AS type configuration table."
			INDEX { hwVermngAsTypeCfgInfoAsTypeIndex }
			::= { hwVermngAsTypeCfgInfoTable 1 }


		HwVermngAsTypeCfgInfoEntry ::=
			SEQUENCE {
				hwVermngAsTypeCfgInfoAsTypeIndex
					Integer32,
				hwVermngAsTypeCfgInfoAsTypeName
					DisplayString,
				hwVermngAsTypeCfgInfoSystemSoftware
					DisplayString,
				hwVermngAsTypeCfgInfoSystemSoftwareVer
					DisplayString,
				hwVermngAsTypeCfgInfoPatch
					DisplayString,
				hwVermngAsTypeCfgInfoRowStatus
					RowStatus
			 }

		-- 1.3.6.1.4.1.2011.5.25.327.5.3.1.1
		hwVermngAsTypeCfgInfoAsTypeIndex OBJECT-TYPE
			SYNTAX Integer32 (1..256)
			MAX-ACCESS not-accessible
			STATUS current
			DESCRIPTION
				"The index of AS type."
			::= { hwVermngAsTypeCfgInfoEntry 1 }


		-- 1.3.6.1.4.1.2011.5.25.327.5.3.1.2
		hwVermngAsTypeCfgInfoAsTypeName OBJECT-TYPE
			SYNTAX DisplayString
			MAX-ACCESS read-create
			STATUS current
			DESCRIPTION
				"The name of AS type."
			::= { hwVermngAsTypeCfgInfoEntry 2 }


		-- 1.3.6.1.4.1.2011.5.25.327.5.3.1.3
		hwVermngAsTypeCfgInfoSystemSoftware OBJECT-TYPE
			SYNTAX DisplayString
			MAX-ACCESS read-create
			STATUS current
			DESCRIPTION
				"The filename of system software configured."
			::= { hwVermngAsTypeCfgInfoEntry 3 }


		-- 1.3.6.1.4.1.2011.5.25.327.5.3.1.4
		hwVermngAsTypeCfgInfoSystemSoftwareVer OBJECT-TYPE
			SYNTAX DisplayString
			MAX-ACCESS read-create
			STATUS current
			DESCRIPTION
				"The version of system software."
			::= { hwVermngAsTypeCfgInfoEntry 4 }


		-- 1.3.6.1.4.1.2011.5.25.327.5.3.1.5
		hwVermngAsTypeCfgInfoPatch OBJECT-TYPE
			SYNTAX DisplayString
			MAX-ACCESS read-create
			STATUS current
			DESCRIPTION
				"The filename of patch configured."
			::= { hwVermngAsTypeCfgInfoEntry 5 }


		-- 1.3.6.1.4.1.2011.5.25.327.5.3.1.50
		hwVermngAsTypeCfgInfoRowStatus OBJECT-TYPE
			SYNTAX RowStatus
			MAX-ACCESS read-create
			STATUS current
			DESCRIPTION
				"The RowStatus of table."
			::= { hwVermngAsTypeCfgInfoEntry 50 }


		-- 1.3.6.1.4.1.2011.5.25.327.6
		hwTplmObjects OBJECT IDENTIFIER ::= { hwUnimngMIB 6 }


		-- 1.3.6.1.4.1.2011.5.25.327.6.11
		hwTplmASGroupTable OBJECT-TYPE
			SYNTAX SEQUENCE OF HwTplmASGroupEntry
			MAX-ACCESS not-accessible
			STATUS current
			DESCRIPTION
				"The table of template management with AS group."
			::= { hwTplmObjects 11 }


		-- 1.3.6.1.4.1.2011.5.25.327.6.11.1
		hwTplmASGroupEntry OBJECT-TYPE
			SYNTAX HwTplmASGroupEntry
			MAX-ACCESS not-accessible
			STATUS current
			DESCRIPTION
				"The entry of AS group table."
			INDEX { hwTplmASGroupIndex }
			::= { hwTplmASGroupTable 1 }


		HwTplmASGroupEntry ::=
			SEQUENCE {
				hwTplmASGroupIndex
					Integer32,
				hwTplmASGroupName
					OCTET STRING,
				hwTplmASAdminProfileName
					OCTET STRING,
				hwTplmASGroupProfileStatus
					INTEGER,
				hwTplmASGroupRowStatus
					RowStatus
			 }

		-- 1.3.6.1.4.1.2011.5.25.327.6.11.1.1
		hwTplmASGroupIndex OBJECT-TYPE
			SYNTAX Integer32 (1..16)
			MAX-ACCESS not-accessible
			STATUS current
			DESCRIPTION
				"The index of AS group table."
			::= { hwTplmASGroupEntry 1 }


		-- 1.3.6.1.4.1.2011.5.25.327.6.11.1.2
		hwTplmASGroupName OBJECT-TYPE
			SYNTAX OCTET STRING (SIZE (1..31))
			MAX-ACCESS read-create
			STATUS current
			DESCRIPTION
				"The name of AS group."
			::= { hwTplmASGroupEntry 2 }


		-- 1.3.6.1.4.1.2011.5.25.327.6.11.1.3
		hwTplmASAdminProfileName OBJECT-TYPE
			SYNTAX OCTET STRING (SIZE (1..31))
			MAX-ACCESS read-create
			STATUS current
			DESCRIPTION
				"The name of AS group's admin profile."
			::= { hwTplmASGroupEntry 3 }


		-- 1.3.6.1.4.1.2011.5.25.327.6.11.1.4
		hwTplmASGroupProfileStatus OBJECT-TYPE
			SYNTAX INTEGER
				{
				enable(1),
				disable(2)
				}
			MAX-ACCESS read-create
			STATUS current
			DESCRIPTION
				"The status of AS group's admin profile."
			::= { hwTplmASGroupEntry 4 }


		-- 1.3.6.1.4.1.2011.5.25.327.6.11.1.11
		hwTplmASGroupRowStatus OBJECT-TYPE
			SYNTAX RowStatus
			MAX-ACCESS read-create
			STATUS current
			DESCRIPTION
				"The row status of as group table."
			::= { hwTplmASGroupEntry 11 }


		-- 1.3.6.1.4.1.2011.5.25.327.6.12
		hwTplmASTable OBJECT-TYPE
			SYNTAX SEQUENCE OF HwTplmASEntry
			MAX-ACCESS not-accessible
			STATUS current
			DESCRIPTION
				"The table of template management with AS."
			::= { hwTplmObjects 12 }


		-- 1.3.6.1.4.1.2011.5.25.327.6.12.1
		hwTplmASEntry OBJECT-TYPE
			SYNTAX HwTplmASEntry
			MAX-ACCESS not-accessible
			STATUS current
			DESCRIPTION
				"The entry of AS table."
			INDEX { hwTplmASId }
			::= { hwTplmASTable 1 }


		HwTplmASEntry ::=
			SEQUENCE {
				hwTplmASId
					Integer32,
				hwTplmASASGroupName
					OCTET STRING,
				hwTplmASRowStatus
					RowStatus
			 }

		-- 1.3.6.1.4.1.2011.5.25.327.6.12.1.1
		hwTplmASId OBJECT-TYPE
			SYNTAX Integer32 (1..256)
			MAX-ACCESS not-accessible
			STATUS current
			DESCRIPTION
				"AS index."
			::= { hwTplmASEntry 1 }


		-- 1.3.6.1.4.1.2011.5.25.327.6.12.1.2
		hwTplmASASGroupName OBJECT-TYPE
			SYNTAX OCTET STRING (SIZE (1..31))
			MAX-ACCESS read-create
			STATUS current
			DESCRIPTION
				"The name of AS group which the AS belongs to."
			::= { hwTplmASEntry 2 }


		-- 1.3.6.1.4.1.2011.5.25.327.6.12.1.11
		hwTplmASRowStatus OBJECT-TYPE
			SYNTAX RowStatus
			MAX-ACCESS read-create
			STATUS current
			DESCRIPTION
				"The row status of as table."
			::= { hwTplmASEntry 11 }


		-- 1.3.6.1.4.1.2011.5.25.327.6.13
		hwTplmPortGroupTable OBJECT-TYPE
			SYNTAX SEQUENCE OF HwTplmPortGroupEntry
			MAX-ACCESS not-accessible
			STATUS current
			DESCRIPTION
				"The table of template management with port group."
			::= { hwTplmObjects 13 }


		-- 1.3.6.1.4.1.2011.5.25.327.6.13.1
		hwTplmPortGroupEntry OBJECT-TYPE
			SYNTAX HwTplmPortGroupEntry
			MAX-ACCESS not-accessible
			STATUS current
			DESCRIPTION
				"The entry of port group table."
			INDEX { hwTplmPortGroupIndex }
			::= { hwTplmPortGroupTable 1 }


		HwTplmPortGroupEntry ::=
			SEQUENCE {
				hwTplmPortGroupIndex
					Integer32,
				hwTplmPortGroupName
					OCTET STRING,
				hwTplmPortGroupType
					INTEGER,
				hwTplmPortGroupNetworkBasicProfile
					OCTET STRING,
				hwTplmPortGroupNetworkEnhancedProfile
					OCTET STRING,
				hwTplmPortGroupUserAccessProfile
					OCTET STRING,
				hwTplmPortGroupProfileStatus
					INTEGER,
				hwTplmPortGroupRowStatus
					RowStatus
			 }

		-- 1.3.6.1.4.1.2011.5.25.327.6.13.1.1
		hwTplmPortGroupIndex OBJECT-TYPE
			SYNTAX Integer32 (1..513)
			MAX-ACCESS not-accessible
			STATUS current
			DESCRIPTION
				"The index of port group table."
			::= { hwTplmPortGroupEntry 1 }


		-- 1.3.6.1.4.1.2011.5.25.327.6.13.1.2
		hwTplmPortGroupName OBJECT-TYPE
			SYNTAX OCTET STRING (SIZE (1..31))
			MAX-ACCESS read-create
			STATUS current
			DESCRIPTION
				"The name of port group."
			::= { hwTplmPortGroupEntry 2 }


		-- 1.3.6.1.4.1.2011.5.25.327.6.13.1.3
		hwTplmPortGroupType OBJECT-TYPE
			SYNTAX INTEGER
				{
				service(1),
				ap(2)
				}
			MAX-ACCESS read-create
			STATUS current
			DESCRIPTION
				"The type of port group."
			::= { hwTplmPortGroupEntry 3 }


		-- 1.3.6.1.4.1.2011.5.25.327.6.13.1.4
		hwTplmPortGroupNetworkBasicProfile OBJECT-TYPE
			SYNTAX OCTET STRING (SIZE (1..31))
			MAX-ACCESS read-create
			STATUS current
			DESCRIPTION
				"The name of port group's network basic profile."
			::= { hwTplmPortGroupEntry 4 }


		-- 1.3.6.1.4.1.2011.5.25.327.6.13.1.5
		hwTplmPortGroupNetworkEnhancedProfile OBJECT-TYPE
			SYNTAX OCTET STRING (SIZE (1..31))
			MAX-ACCESS read-create
			STATUS current
			DESCRIPTION
				"The name of port group's network enhanced profile."
			::= { hwTplmPortGroupEntry 5 }


		-- 1.3.6.1.4.1.2011.5.25.327.6.13.1.6
		hwTplmPortGroupUserAccessProfile OBJECT-TYPE
			SYNTAX OCTET STRING (SIZE (1..31))
			MAX-ACCESS read-create
			STATUS current
			DESCRIPTION
				"The name of port group's user access profile."
			::= { hwTplmPortGroupEntry 6 }


		-- 1.3.6.1.4.1.2011.5.25.327.6.13.1.7
		hwTplmPortGroupProfileStatus OBJECT-TYPE
			SYNTAX INTEGER
				{
				enable(1),
				disable(2)
				}
			MAX-ACCESS read-create
			STATUS current
			DESCRIPTION
				"The status of port group's profile."
			::= { hwTplmPortGroupEntry 7 }


		-- 1.3.6.1.4.1.2011.5.25.327.6.13.1.11
		hwTplmPortGroupRowStatus OBJECT-TYPE
			SYNTAX RowStatus
			MAX-ACCESS read-create
			STATUS current
			DESCRIPTION
				"The row status of port group table."
			::= { hwTplmPortGroupEntry 11 }


		-- 1.3.6.1.4.1.2011.5.25.327.6.14
		hwTplmPortTable OBJECT-TYPE
			SYNTAX SEQUENCE OF HwTplmPortEntry
			MAX-ACCESS not-accessible
			STATUS current
			DESCRIPTION
				"The table of template management with AS's port."
			::= { hwTplmObjects 14 }


		-- 1.3.6.1.4.1.2011.5.25.327.6.14.1
		hwTplmPortEntry OBJECT-TYPE
			SYNTAX HwTplmPortEntry
			MAX-ACCESS not-accessible
			STATUS current
			DESCRIPTION
				"The entry of port table."
			INDEX { hwTplmPortIfIndex }
			::= { hwTplmPortTable 1 }


		HwTplmPortEntry ::=
			SEQUENCE {
				hwTplmPortIfIndex
					Integer32,
				hwTplmPortPortGroupName
					OCTET STRING,
				hwTplmPortRowStatus
					RowStatus
			 }

		-- 1.3.6.1.4.1.2011.5.25.327.6.14.1.1
		hwTplmPortIfIndex OBJECT-TYPE
			SYNTAX Integer32
			MAX-ACCESS not-accessible
			STATUS current
			DESCRIPTION
				"The interface index of AS's port."
			::= { hwTplmPortEntry 1 }


		-- 1.3.6.1.4.1.2011.5.25.327.6.14.1.2
		hwTplmPortPortGroupName OBJECT-TYPE
			SYNTAX OCTET STRING (SIZE (1..31))
			MAX-ACCESS read-create
			STATUS current
			DESCRIPTION
				"The name of port group which the AS's port belongs to."
			::= { hwTplmPortEntry 2 }


		-- 1.3.6.1.4.1.2011.5.25.327.6.14.1.11
		hwTplmPortRowStatus OBJECT-TYPE
			SYNTAX RowStatus
			MAX-ACCESS read-create
			STATUS current
			DESCRIPTION
				"The row status of port table."
			::= { hwTplmPortEntry 11 }


		-- 1.3.6.1.4.1.2011.5.25.327.6.15
		hwTplmConfigManagement OBJECT IDENTIFIER ::= { hwTplmObjects 15 }


		-- 1.3.6.1.4.1.2011.5.25.327.6.15.1
		hwTplmConfigCommitAll OBJECT-TYPE
			SYNTAX INTEGER { commit(1) }
			MAX-ACCESS read-write
			STATUS current
			DESCRIPTION
				"Apply configuration of template management to all ASs."
			::= { hwTplmConfigManagement 1 }


		-- 1.3.6.1.4.1.2011.5.25.327.6.15.2
		hwTplmConfigManagementTable OBJECT-TYPE
			SYNTAX SEQUENCE OF HwTplmConfigManagementEntry
			MAX-ACCESS not-accessible
			STATUS current
			DESCRIPTION
				"The table of committing configuration of template management."
			::= { hwTplmConfigManagement 2 }


		-- 1.3.6.1.4.1.2011.5.25.327.6.15.2.1
		hwTplmConfigManagementEntry OBJECT-TYPE
			SYNTAX HwTplmConfigManagementEntry
			MAX-ACCESS not-accessible
			STATUS current
			DESCRIPTION
				"The entry of committing table."
			INDEX { hwTplmConfigManagementASId }
			::= { hwTplmConfigManagementTable 1 }


		HwTplmConfigManagementEntry ::=
			SEQUENCE {
				hwTplmConfigManagementASId
					Integer32,
				hwTplmConfigManagementCommit
					INTEGER
			 }

		-- 1.3.6.1.4.1.2011.5.25.327.6.15.2.1.1
		hwTplmConfigManagementASId OBJECT-TYPE
			SYNTAX Integer32 (1..256)
			MAX-ACCESS not-accessible
			STATUS current
			DESCRIPTION
				"AS index."
			::= { hwTplmConfigManagementEntry 1 }


		-- 1.3.6.1.4.1.2011.5.25.327.6.15.2.1.2
		hwTplmConfigManagementCommit OBJECT-TYPE
			SYNTAX INTEGER { commit(1) }
			MAX-ACCESS read-write
			STATUS current
			DESCRIPTION
				"Apply configuration of template management to the specified AS."
			::= { hwTplmConfigManagementEntry 2 }


		-- 1.3.6.1.4.1.2011.5.25.327.7
		hwMaintenMngObjects OBJECT IDENTIFIER ::= { hwUnimngMIB 7 }


		-- 1.3.6.1.4.1.2011.5.25.327.7.2
		hwUnAuthenUserTable OBJECT-TYPE
			SYNTAX SEQUENCE OF HwUnAuthenUserEntry
			MAX-ACCESS not-accessible
			STATUS current
			DESCRIPTION
				"The table of unauthen user."
			::= { hwMaintenMngObjects 2 }


		-- 1.3.6.1.4.1.2011.5.25.327.7.2.1
		hwUnAuthenUserEntry OBJECT-TYPE
			SYNTAX HwUnAuthenUserEntry
			MAX-ACCESS not-accessible
			STATUS current
			DESCRIPTION
				"The entry of the table of unauthen user."
			INDEX { hwUnAuthenUserAsIndex, hwUnAuthenUserVlan, hwUnAuthenUserMac }
			::= { hwUnAuthenUserTable 1 }


		HwUnAuthenUserEntry ::=
			SEQUENCE {
				hwUnAuthenUserAsIndex
					Integer32,
				hwUnAuthenUserVlan
					Integer32,
				hwUnAuthenUserMac
					MacAddress,
				hwUnAuthenUserIP
					IpAddress,
				hwUnAuthenUserAsName
					DisplayString,
				hwUnAuthenUserIfName
					OCTET STRING
			 }

		-- 1.3.6.1.4.1.2011.5.25.327.7.2.1.1
		hwUnAuthenUserAsIndex OBJECT-TYPE
			SYNTAX Integer32 (1..256)
			MAX-ACCESS read-only
			STATUS current
			DESCRIPTION
				"Access AS index of unauthen user."
			::= { hwUnAuthenUserEntry 1 }


		-- 1.3.6.1.4.1.2011.5.25.327.7.2.1.2
		hwUnAuthenUserVlan OBJECT-TYPE
			SYNTAX Integer32 (1..4094)
			MAX-ACCESS read-only
			STATUS current
			DESCRIPTION
				"The VLAN id of unauthen user."
			::= { hwUnAuthenUserEntry 2 }


		-- 1.3.6.1.4.1.2011.5.25.327.7.2.1.3
		hwUnAuthenUserMac OBJECT-TYPE
			SYNTAX MacAddress
			MAX-ACCESS read-only
			STATUS current
			DESCRIPTION
				"The MAC address of unauthen user."
			::= { hwUnAuthenUserEntry 3 }


		-- 1.3.6.1.4.1.2011.5.25.327.7.2.1.4
		hwUnAuthenUserIP OBJECT-TYPE
			SYNTAX IpAddress
			MAX-ACCESS read-only
			STATUS current
			DESCRIPTION
				"The IP address of unauthen user."
			::= { hwUnAuthenUserEntry 4 }


		-- 1.3.6.1.4.1.2011.5.25.327.7.2.1.5
		hwUnAuthenUserAsName OBJECT-TYPE
			SYNTAX DisplayString
			MAX-ACCESS read-only
			STATUS current
			DESCRIPTION
				"Access AS name of unauthen user."
			::= { hwUnAuthenUserEntry 5 }


		-- 1.3.6.1.4.1.2011.5.25.327.7.2.1.6
		hwUnAuthenUserIfName OBJECT-TYPE
			SYNTAX OCTET STRING (SIZE (1..64))
			MAX-ACCESS read-only
			STATUS current
			DESCRIPTION
				"Access interface name of unauthen user."
			::= { hwUnAuthenUserEntry 6 }


		-- 1.3.6.1.4.1.2011.5.25.327.7.3
		hwAuthenUserTable OBJECT-TYPE
			SYNTAX SEQUENCE OF HwAuthenUserEntry
			MAX-ACCESS not-accessible
			STATUS current
			DESCRIPTION
				"The table of authen user."
			::= { hwMaintenMngObjects 3 }


		-- 1.3.6.1.4.1.2011.5.25.327.7.3.1
		hwAuthenUserEntry OBJECT-TYPE
			SYNTAX HwAuthenUserEntry
			MAX-ACCESS not-accessible
			STATUS current
			DESCRIPTION
				"The entry of the table of authen user."
			INDEX { hwAuthenUserAsIndex, hwAuthenUserVlan, hwAuthenUserMac }
			::= { hwAuthenUserTable 1 }


		HwAuthenUserEntry ::=
			SEQUENCE {
				hwAuthenUserAsIndex
					Integer32,
				hwAuthenUserVlan
					Integer32,
				hwAuthenUserMac
					MacAddress,
				hwAuthenUserIP
					IpAddress,
				hwAuthenUserAsName
					DisplayString,
				hwAuthenUserIfName
					OCTET STRING
			 }

		-- 1.3.6.1.4.1.2011.5.25.327.7.3.1.1
		hwAuthenUserAsIndex OBJECT-TYPE
			SYNTAX Integer32 (1..256)
			MAX-ACCESS read-only
			STATUS current
			DESCRIPTION
				"Access AS index of authen user."
			::= { hwAuthenUserEntry 1 }


		-- 1.3.6.1.4.1.2011.5.25.327.7.3.1.2
		hwAuthenUserVlan OBJECT-TYPE
			SYNTAX Integer32 (1..4094)
			MAX-ACCESS read-only
			STATUS current
			DESCRIPTION
				"The VLAN id of authen user."
			::= { hwAuthenUserEntry 2 }


		-- 1.3.6.1.4.1.2011.5.25.327.7.3.1.3
		hwAuthenUserMac OBJECT-TYPE
			SYNTAX MacAddress
			MAX-ACCESS read-only
			STATUS current
			DESCRIPTION
				"The MAC address of authen user."
			::= { hwAuthenUserEntry 3 }


		-- 1.3.6.1.4.1.2011.5.25.327.7.3.1.4
		hwAuthenUserIP OBJECT-TYPE
			SYNTAX IpAddress
			MAX-ACCESS read-only
			STATUS current
			DESCRIPTION
				"The IP address of authen user."
			::= { hwAuthenUserEntry 4 }


		-- 1.3.6.1.4.1.2011.5.25.327.7.3.1.5
		hwAuthenUserAsName OBJECT-TYPE
			SYNTAX DisplayString
			MAX-ACCESS read-only
			STATUS current
			DESCRIPTION
				"Access AS name of authen user."
			::= { hwAuthenUserEntry 5 }


		-- 1.3.6.1.4.1.2011.5.25.327.7.3.1.6
		hwAuthenUserIfName OBJECT-TYPE
			SYNTAX OCTET STRING (SIZE (1..64))
			MAX-ACCESS read-only
			STATUS current
			DESCRIPTION
				"Access interface name of authen user."
			::= { hwAuthenUserEntry 6 }


		-- 1.3.6.1.4.1.2011.5.25.327.31
		hwUnimngNotification OBJECT IDENTIFIER ::= { hwUnimngMIB 31 }


		-- 1.3.6.1.4.1.2011.5.25.327.31.1
		hwTopomngTrap OBJECT IDENTIFIER ::= { hwUnimngNotification 1 }


		-- 1.3.6.1.4.1.2011.5.25.327.31.1.1
		hwTopomngTrapObjects OBJECT IDENTIFIER ::= { hwTopomngTrap 1 }


		-- 1.3.6.1.4.1.2011.5.25.327.31.1.1.1
		hwTopomngTrapLocalMac OBJECT-TYPE
			SYNTAX MacAddress
			MAX-ACCESS accessible-for-notify
			STATUS current
			DESCRIPTION
				"Topomng trap message local MAC, defined as the device ID."
			::= { hwTopomngTrapObjects 1 }


		-- 1.3.6.1.4.1.2011.5.25.327.31.1.1.2
		hwTopomngTrapLocalPortName OBJECT-TYPE
			SYNTAX OCTET STRING (SIZE (0..64))
			MAX-ACCESS accessible-for-notify
			STATUS current
			DESCRIPTION
				"Topomng trap message local port name."
			::= { hwTopomngTrapObjects 2 }


		-- 1.3.6.1.4.1.2011.5.25.327.31.1.1.3
		hwTopomngTrapLocalTrunkId OBJECT-TYPE
			SYNTAX Integer32 (0..65535)
			MAX-ACCESS accessible-for-notify
			STATUS current
			DESCRIPTION
				"Topomng trap message local trunk ID, 65535 defines a phy port."
			::= { hwTopomngTrapObjects 3 }


		-- 1.3.6.1.4.1.2011.5.25.327.31.1.1.4
		hwTopomngTrapPeerMac OBJECT-TYPE
			SYNTAX MacAddress
			MAX-ACCESS accessible-for-notify
			STATUS current
			DESCRIPTION
				"Topomng trap message peer MAC, defined as the device ID."
			::= { hwTopomngTrapObjects 4 }


		-- 1.3.6.1.4.1.2011.5.25.327.31.1.1.5
		hwTopomngTrapPeerPortName OBJECT-TYPE
			SYNTAX OCTET STRING (SIZE (0..64))
			MAX-ACCESS accessible-for-notify
			STATUS current
			DESCRIPTION
				"Topomng trap message peer port name."
			::= { hwTopomngTrapObjects 5 }


		-- 1.3.6.1.4.1.2011.5.25.327.31.1.1.6
		hwTopomngTrapPeerTrunkId OBJECT-TYPE
			SYNTAX Integer32 (0..65535)
			MAX-ACCESS accessible-for-notify
			STATUS current
			DESCRIPTION
				"Topomng trap message peer trunk ID, 65535 defines a phy port."
			::= { hwTopomngTrapObjects 6 }


		-- 1.3.6.1.4.1.2011.5.25.327.31.1.1.7
		hwTopomngTrapReason OBJECT-TYPE
			SYNTAX OCTET STRING (SIZE (0..64))
			MAX-ACCESS accessible-for-notify
			STATUS current
			DESCRIPTION
				"Topomng trap message Reason."
			::= { hwTopomngTrapObjects 7 }


		-- 1.3.6.1.4.1.2011.5.25.327.31.1.2
		hwTopomngTraps OBJECT IDENTIFIER ::= { hwTopomngTrap 2 }


		-- 1.3.6.1.4.1.2011.5.25.327.31.1.2.1
		hwTopomngLinkNormal NOTIFICATION-TYPE
			OBJECTS { hwTopomngTrapLocalMac, hwTopomngTrapLocalPortName, hwTopomngTrapLocalTrunkId, hwTopomngTrapPeerMac, hwTopomngTrapPeerPortName,
				hwTopomngTrapPeerTrunkId, hwTopomngTrapReason }
			STATUS current
			DESCRIPTION
				"The notification of topology link normal."
			::= { hwTopomngTraps 1 }


		-- 1.3.6.1.4.1.2011.5.25.327.31.1.2.2
		hwTopomngLinkAbnormal NOTIFICATION-TYPE
			OBJECTS { hwTopomngTrapLocalMac, hwTopomngTrapLocalPortName, hwTopomngTrapLocalTrunkId, hwTopomngTrapPeerMac, hwTopomngTrapPeerPortName,
				hwTopomngTrapPeerTrunkId, hwTopomngTrapReason }
			STATUS current
			DESCRIPTION
				"The notification of topology link abnormal."
			::= { hwTopomngTraps 2 }


		-- 1.3.6.1.4.1.2011.5.25.327.31.2
		hwAsmngTrap OBJECT IDENTIFIER ::= { hwUnimngNotification 2 }


		-- 1.3.6.1.4.1.2011.5.25.327.31.2.1
		hwAsmngTrapObjects OBJECT IDENTIFIER ::= { hwAsmngTrap 1 }


		-- 1.3.6.1.4.1.2011.5.25.327.31.2.1.1
		hwAsmngTrapAsIndex OBJECT-TYPE
			SYNTAX Integer32
			MAX-ACCESS accessible-for-notify
			STATUS current
			DESCRIPTION
				"The AS index."
			::= { hwAsmngTrapObjects 1 }


		-- 1.3.6.1.4.1.2011.5.25.327.31.2.1.2
		hwAsmngTrapAsModel OBJECT-TYPE
			SYNTAX OCTET STRING
			MAX-ACCESS accessible-for-notify
			STATUS current
			DESCRIPTION
				"The model of AS."
			::= { hwAsmngTrapObjects 2 }


		-- 1.3.6.1.4.1.2011.5.25.327.31.2.1.3
		hwAsmngTrapAsSysName OBJECT-TYPE
			SYNTAX OCTET STRING
			MAX-ACCESS accessible-for-notify
			STATUS current
			DESCRIPTION
				"The name of AS."
			::= { hwAsmngTrapObjects 3 }


		-- 1.3.6.1.4.1.2011.5.25.327.31.2.1.4
		hwAsmngTrapAsMac OBJECT-TYPE
			SYNTAX MacAddress
			MAX-ACCESS accessible-for-notify
			STATUS current
			DESCRIPTION
				"The MAC address of AS."
			::= { hwAsmngTrapObjects 4 }


		-- 1.3.6.1.4.1.2011.5.25.327.31.2.1.5
		hwAsmngTrapAsSn OBJECT-TYPE
			SYNTAX OCTET STRING
			MAX-ACCESS accessible-for-notify
			STATUS current
			DESCRIPTION
				"The SN of AS."
			::= { hwAsmngTrapObjects 5 }


		-- 1.3.6.1.4.1.2011.5.25.327.31.2.1.6
		hwAsmngTrapAsIfIndex OBJECT-TYPE
			SYNTAX Integer32
			MAX-ACCESS accessible-for-notify
			STATUS current
			DESCRIPTION
				"The interface index of AS."
			::= { hwAsmngTrapObjects 6 }


		-- 1.3.6.1.4.1.2011.5.25.327.31.2.1.7
		hwAsmngTrapAsIfOperStatus OBJECT-TYPE
			SYNTAX Integer32
			MAX-ACCESS accessible-for-notify
			STATUS current
			DESCRIPTION
				"The operation stauts of AS."
			::= { hwAsmngTrapObjects 7 }


		-- 1.3.6.1.4.1.2011.5.25.327.31.2.1.8
		hwAsmngTrapAsFaultTimes OBJECT-TYPE
			SYNTAX Integer32
			MAX-ACCESS accessible-for-notify
			STATUS current
			DESCRIPTION
				"The fault times of AS."
			::= { hwAsmngTrapObjects 8 }


		-- 1.3.6.1.4.1.2011.5.25.327.31.2.1.9
		hwAsmngTrapAsIfAdminStatus OBJECT-TYPE
			SYNTAX Integer32
			MAX-ACCESS accessible-for-notify
			STATUS current
			DESCRIPTION
				"AS interface adminnistrator status."
			::= { hwAsmngTrapObjects 9 }


		-- 1.3.6.1.4.1.2011.5.25.327.31.2.1.10
		hwAsmngTrapAsIfName OBJECT-TYPE
			SYNTAX OCTET STRING
			MAX-ACCESS accessible-for-notify
			STATUS current
			DESCRIPTION
				"The name of AS."
			::= { hwAsmngTrapObjects 10 }


		-- 1.3.6.1.4.1.2011.5.25.327.31.2.1.11
		hwAsmngTrapAsActualeType OBJECT-TYPE
			SYNTAX OCTET STRING
			MAX-ACCESS accessible-for-notify
			STATUS current
			DESCRIPTION
				"The actual type of AS."
			::= { hwAsmngTrapObjects 11 }


		-- 1.3.6.1.4.1.2011.5.25.327.31.2.1.12
		hwAsmngTrapAsVersion OBJECT-TYPE
			SYNTAX OCTET STRING
			MAX-ACCESS accessible-for-notify
			STATUS current
			DESCRIPTION
				"The version of AS."
			::= { hwAsmngTrapObjects 12 }


		-- 1.3.6.1.4.1.2011.5.25.327.31.2.1.13
		hwAsmngTrapParentVersion OBJECT-TYPE
			SYNTAX OCTET STRING
			MAX-ACCESS accessible-for-notify
			STATUS current
			DESCRIPTION
				"The version of parent."
			::= { hwAsmngTrapObjects 13 }


		-- 1.3.6.1.4.1.2011.5.25.327.31.2.1.14
		hwAsmngTrapAddedAsMac OBJECT-TYPE
			SYNTAX MacAddress
			MAX-ACCESS accessible-for-notify
			STATUS current
			DESCRIPTION
				"The MAC address of added AS."
			::= { hwAsmngTrapObjects 14 }


		-- 1.3.6.1.4.1.2011.5.25.327.31.2.1.15
		hwAsmngTrapAsSlotId OBJECT-TYPE
			SYNTAX Integer32
			MAX-ACCESS accessible-for-notify
			STATUS current
			DESCRIPTION
				"The slot ID of AS."
			::= { hwAsmngTrapObjects 15 }


		-- 1.3.6.1.4.1.2011.5.25.327.31.2.1.16
		hwAsmngTrapAddedAsSlotType OBJECT-TYPE
			SYNTAX OCTET STRING
			MAX-ACCESS accessible-for-notify
			STATUS current
			DESCRIPTION
				"The slot type of added AS."
			::= { hwAsmngTrapObjects 16 }


		-- 1.3.6.1.4.1.2011.5.25.327.31.2.1.17
		hwAsmngTrapAsPermitNum OBJECT-TYPE
			SYNTAX Integer32
			MAX-ACCESS accessible-for-notify
			STATUS current
			DESCRIPTION
				"The maxium number of permitted AS."
			::= { hwAsmngTrapObjects 17 }


		-- 1.3.6.1.4.1.2011.5.25.327.31.2.1.18
		hwAsmngTrapAsUnimngMode OBJECT-TYPE
			SYNTAX Integer32
			MAX-ACCESS accessible-for-notify
			STATUS current
			DESCRIPTION
				"The UNI-MNG mode of AS."
			::= { hwAsmngTrapObjects 18 }


		-- 1.3.6.1.4.1.2011.5.25.327.31.2.1.19
		hwAsmngTrapParentUnimngMode OBJECT-TYPE
			SYNTAX Integer32
			MAX-ACCESS accessible-for-notify
			STATUS current
			DESCRIPTION
				"The UNI-MNG mode of parent."
			::= { hwAsmngTrapObjects 19 }


		-- 1.3.6.1.4.1.2011.5.25.327.31.2.1.20
		hwAsmngTrapAsIfType OBJECT-TYPE
			SYNTAX Integer32
			MAX-ACCESS accessible-for-notify
			STATUS current
			DESCRIPTION
				"The interface type of AS."
			::= { hwAsmngTrapObjects 20 }


		-- 1.3.6.1.4.1.2011.5.25.327.31.2.1.21
		hwAsmngTrapAsOnlineFailReasonId OBJECT-TYPE
			SYNTAX Integer32
			MAX-ACCESS accessible-for-notify
			STATUS current
			DESCRIPTION
				"The reason ID of AS online failed."
			::= { hwAsmngTrapObjects 21 }


		-- 1.3.6.1.4.1.2011.5.25.327.31.2.1.22
		hwAsmngTrapAsOnlineFailReasonDesc OBJECT-TYPE
			SYNTAX OCTET STRING
			MAX-ACCESS accessible-for-notify
			STATUS current
			DESCRIPTION
				"The description of AS online failed."
			::= { hwAsmngTrapObjects 22 }


		-- 1.3.6.1.4.1.2011.5.25.327.31.2.1.23
		hwAsmngTrapAsSlotOnlineFailReasonId OBJECT-TYPE
			SYNTAX Integer32
			MAX-ACCESS accessible-for-notify
			STATUS current
			DESCRIPTION
				"The reason ID of AS slot online failed."
			::= { hwAsmngTrapObjects 23 }


		-- 1.3.6.1.4.1.2011.5.25.327.31.2.1.24
		hwAsmngTrapAsSlotOnlineFailReasonDesc OBJECT-TYPE
			SYNTAX OCTET STRING
			MAX-ACCESS accessible-for-notify
			STATUS current
			DESCRIPTION
				"The description of AS slot online failed."
			::= { hwAsmngTrapObjects 24 }

		-- 1.3.6.1.4.1.2011.5.25.327.31.2.2
		hwAsmngTraps OBJECT IDENTIFIER ::= { hwAsmngTrap 2 }


		-- 1.3.6.1.4.1.2011.5.25.327.31.2.2.1
		hwAsFaultNotify NOTIFICATION-TYPE
			OBJECTS { hwAsmngTrapAsIndex, hwAsmngTrapAsSysName, hwAsmngTrapAsModel, hwAsmngTrapAsMac, hwAsmngTrapAsFaultTimes
				 }
			STATUS current
			DESCRIPTION
				"This notification occurs when AS become fault."
			::= { hwAsmngTraps 1 }


		-- 1.3.6.1.4.1.2011.5.25.327.31.2.2.2
		hwAsNormalNotify NOTIFICATION-TYPE
			OBJECTS { hwAsmngTrapAsIndex, hwAsmngTrapAsSysName, hwAsmngTrapAsModel, hwAsmngTrapAsMac }
			STATUS current
			DESCRIPTION
				"This notification occurs when AS become normal."
			::= { hwAsmngTraps 2 }


		-- 1.3.6.1.4.1.2011.5.25.327.31.2.2.3
		hwAsAddOffLineNotify NOTIFICATION-TYPE
			OBJECTS { hwAsmngTrapAsIndex, hwAsmngTrapAsSysName, hwAsmngTrapAsModel, hwAsmngTrapAsMac }
			STATUS current
			DESCRIPTION
				"This notification occurs when added an AS offline."
			::= { hwAsmngTraps 3 }


		-- 1.3.6.1.4.1.2011.5.25.327.31.2.2.4
		hwAsDelOffLineNotify NOTIFICATION-TYPE
			OBJECTS { hwAsmngTrapAsIndex, hwAsmngTrapAsSysName, hwAsmngTrapAsModel, hwAsmngTrapAsMac }
			STATUS current
			DESCRIPTION
				"This notification occurs when deleted an AS offline."
			::= { hwAsmngTraps 4 }


		-- 1.3.6.1.4.1.2011.5.25.327.31.2.2.5
		hwAsPortStateChangeToDownNotify NOTIFICATION-TYPE
			OBJECTS { hwAsmngTrapAsIndex, hwAsmngTrapAsIfIndex, hwAsmngTrapAsSysName, hwAsmngTrapAsModel, hwAsmngTrapAsMac,
				hwAsmngTrapAsIfName, hwAsmngTrapAsIfAdminStatus, hwAsmngTrapAsIfOperStatus }
			STATUS current
			DESCRIPTION
				"This notification occurs when port status changed to DOWN."
			::= { hwAsmngTraps 5 }


		-- 1.3.6.1.4.1.2011.5.25.327.31.2.2.6
		hwAsPortStateChangeToUpNotify NOTIFICATION-TYPE
			OBJECTS { hwAsmngTrapAsIndex, hwAsmngTrapAsIfIndex, hwAsmngTrapAsSysName, hwAsmngTrapAsModel, hwAsmngTrapAsMac,
				hwAsmngTrapAsIfName, hwAsmngTrapAsIfAdminStatus, hwAsmngTrapAsIfOperStatus }
			STATUS current
			DESCRIPTION
				"This notification occurs when port status changed to UP."
			::= { hwAsmngTraps 6 }


		-- 1.3.6.1.4.1.2011.5.25.327.31.2.2.7
		hwAsModelNotMatchNotify NOTIFICATION-TYPE
			OBJECTS { hwAsmngTrapAsIndex, hwAsmngTrapAsSysName, hwAsmngTrapAsMac, hwAsmngTrapAsModel, hwAsmngTrapAsActualeType
				 }
			STATUS current
			DESCRIPTION
				"This notification occurs when the model of AS is mismatch."
			::= { hwAsmngTraps 7 }


		-- 1.3.6.1.4.1.2011.5.25.327.31.2.2.8
		hwAsVersionNotMatchNotify NOTIFICATION-TYPE
			OBJECTS { hwAsmngTrapAsIndex, hwAsmngTrapAsSysName, hwAsmngTrapAsVersion, hwAsmngTrapParentVersion }
			STATUS current
			DESCRIPTION
				"This notification occurs when the version of AS is mismatch."
			::= { hwAsmngTraps 8 }


		-- 1.3.6.1.4.1.2011.5.25.327.31.2.2.9
		hwAsNameConflictNotify NOTIFICATION-TYPE
			OBJECTS { hwAsmngTrapAsIndex, hwAsmngTrapAsSysName, hwAsmngTrapAsMac, hwAsmngTrapAddedAsMac }
			STATUS current
			DESCRIPTION
				"This notification occurs when the name of AS is conflicted."
			::= { hwAsmngTraps 9 }


		-- 1.3.6.1.4.1.2011.5.25.327.31.2.2.10
		hwAsSlotModelNotMatchNotify NOTIFICATION-TYPE
			OBJECTS { hwAsmngTrapAsIndex, hwAsmngTrapAsSysName, hwAsmngTrapAsModel, hwAsmngTrapAsSlotId, hwAsmngTrapAddedAsSlotType
				 }
			STATUS current
			DESCRIPTION
				"This notification occurs when the slot model of AS is mismatch."
			::= { hwAsmngTraps 10 }


		-- 1.3.6.1.4.1.2011.5.25.327.31.2.2.11
		hwAsFullNotify NOTIFICATION-TYPE
			OBJECTS { hwAsmngTrapAsSysName, hwAsmngTrapAsModel, hwAsmngTrapAsMac, hwAsmngTrapAsPermitNum }
			STATUS current
			DESCRIPTION
				"This notification occurs when the model of a slot is different from other slots."
			::= { hwAsmngTraps 11 }


		-- 1.3.6.1.4.1.2011.5.25.327.31.2.2.12
		hwUnimngModeNotMatchNotify NOTIFICATION-TYPE
			OBJECTS { hwAsmngTrapAsSysName, hwAsmngTrapAsModel, hwAsmngTrapAsMac, hwAsmngTrapAsUnimngMode, hwAsmngTrapParentUnimngMode
				 }
			STATUS current
			DESCRIPTION
				"This notification occurs when the UNI-MNG mode of AS is different parent's."
			::= { hwAsmngTraps 12 }


		-- 1.3.6.1.4.1.2011.5.25.327.31.2.2.13
		hwAsBoardAddNotify NOTIFICATION-TYPE
			OBJECTS { hwAsmngTrapAsIndex, hwAsmngTrapAsSysName, hwAsmngTrapAsModel, hwAsmngTrapAsSlotId }
			STATUS current
			DESCRIPTION
				"This notification occurs when a slot is added."
			::= { hwAsmngTraps 13 }


		-- 1.3.6.1.4.1.2011.5.25.327.31.2.2.14
		hwAsBoardDeleteNotify NOTIFICATION-TYPE
			OBJECTS { hwAsmngTrapAsIndex, hwAsmngTrapAsSysName, hwAsmngTrapAsModel, hwAsmngTrapAsSlotId }
			STATUS current
			DESCRIPTION
				"This notification occurs when a slot is deleted."
			::= { hwAsmngTraps 14 }


		-- 1.3.6.1.4.1.2011.5.25.327.31.2.2.15
		hwAsBoardPlugInNotify NOTIFICATION-TYPE
			OBJECTS { hwAsmngTrapAsIndex, hwAsmngTrapAsSysName, hwAsmngTrapAsModel, hwAsmngTrapAsSlotId }
			STATUS current
			DESCRIPTION
				"This notification occurs when a slot is plugged in."
			::= { hwAsmngTraps 15 }


		-- 1.3.6.1.4.1.2011.5.25.327.31.2.2.16
		hwAsBoardPlugOutNotify NOTIFICATION-TYPE
			OBJECTS { hwAsmngTrapAsIndex, hwAsmngTrapAsSysName, hwAsmngTrapAsModel, hwAsmngTrapAsSlotId }
			STATUS current
			DESCRIPTION
				"This notification occurs when a slot is pulled out."
			::= { hwAsmngTraps 16 }


		-- 1.3.6.1.4.1.2011.5.25.327.31.2.2.17
		hwAsInBlacklistNotify NOTIFICATION-TYPE
			OBJECTS { hwAsmngTrapAsSysName, hwAsmngTrapAsModel, hwAsmngTrapAsMac }
			STATUS current
			DESCRIPTION
				"This notification occurs when AS is in blacklist."
			::= { hwAsmngTraps 17 }


		-- 1.3.6.1.4.1.2011.5.25.327.31.2.2.18
		hwAsUnconfirmedNotify NOTIFICATION-TYPE
			OBJECTS { hwAsmngTrapAsSysName, hwAsmngTrapAsModel, hwAsmngTrapAsMac }
			STATUS current
			DESCRIPTION
				"This notification occurs when AS is not confirmed."
			::= { hwAsmngTraps 18 }


		-- 1.3.6.1.4.1.2011.5.25.327.31.2.2.19
		hwAsComboPortTypeChangeNotify NOTIFICATION-TYPE
			OBJECTS { hwAsmngTrapAsIndex, hwAsmngTrapAsIfIndex, hwAsmngTrapAsSysName, hwAsmngTrapAsIfName, hwAsmngTrapAsIfType
				 }
			STATUS current
			DESCRIPTION
				"This notification occurs when combo type change."
			::= { hwAsmngTraps 19 }


		-- 1.3.6.1.4.1.2011.5.25.327.31.2.2.20
		hwAsOnlineFailNotify NOTIFICATION-TYPE
			OBJECTS { hwAsmngTrapAsSysName, hwAsmngTrapAsModel, hwAsmngTrapAsMac, hwAsmngTrapAsOnlineFailReasonId, hwAsmngTrapAsOnlineFailReasonDesc
				 }
			STATUS current
			DESCRIPTION
				"This notification occurs when AS online failed."
			::= { hwAsmngTraps 20 }


		-- 1.3.6.1.4.1.2011.5.25.327.31.2.2.21
		hwAsSlotIdInvalidNotify NOTIFICATION-TYPE
			OBJECTS { hwAsmngTrapAsIndex, hwAsmngTrapAsSysName, hwAsmngTrapAsModel, hwAsmngTrapAsSlotId }
			STATUS current
			DESCRIPTION
				"This notification occurs when the slot ID of AS is invalid."
			::= { hwAsmngTraps 21 }


		-- 1.3.6.1.4.1.2011.5.25.327.31.2.2.22
		hwAsSysmacSwitchCfgErrNotify NOTIFICATION-TYPE
			OBJECTS { hwAsmngTrapAsSysName }
			STATUS current
			DESCRIPTION
				"This notification occurs when the configuration of system MAC address switching delay is error."
			::= { hwAsmngTraps 22 }


		-- 1.3.6.1.4.1.2011.5.25.327.31.2.2.23
		hwAsSlotOnlineFailNotify NOTIFICATION-TYPE
			OBJECTS { hwAsmngTrapAsIndex, hwAsmngTrapAsSysName, hwAsmngTrapAsModel, hwAsmngTrapAsSlotId, hwAsmngTrapAsSlotOnlineFailReasonId, hwAsmngTrapAsSlotOnlineFailReasonDesc}
			STATUS current
			DESCRIPTION
				"This notification occurs when AS slot online failed."
			::= { hwAsmngTraps 23 }


		-- 1.3.6.1.4.1.2011.5.25.327.31.3
		hwUniMbrTrap OBJECT IDENTIFIER ::= { hwUnimngNotification 3 }


		-- 1.3.6.1.4.1.2011.5.25.327.31.3.1
		hwUniMbrTrapObjects OBJECT IDENTIFIER ::= { hwUniMbrTrap 1 }


		-- 1.3.6.1.4.1.2011.5.25.327.31.3.1.1
		hwUniMbrLinkStatTrapLocalMac OBJECT-TYPE
			SYNTAX MacAddress
			MAX-ACCESS accessible-for-notify
			STATUS current
			DESCRIPTION
				"UNIMBR trap message local mac."
			::= { hwUniMbrTrapObjects 1 }


		-- 1.3.6.1.4.1.2011.5.25.327.31.3.1.2
		hwUniMbrLinkStatTrapLocalPortName OBJECT-TYPE
			SYNTAX OCTET STRING
			MAX-ACCESS accessible-for-notify
			STATUS current
			DESCRIPTION
				"UNIMBR trap message local port name."
			::= { hwUniMbrTrapObjects 2 }


		-- 1.3.6.1.4.1.2011.5.25.327.31.3.1.3
		hwUniMbrLinkStatTrapChangeType OBJECT-TYPE
			SYNTAX INTEGER
				{
				up2down(1),
				down2up(2)
				}
			MAX-ACCESS accessible-for-notify
			STATUS current
			DESCRIPTION
				"UNIMBR trap message changing type of link state."
			::= { hwUniMbrTrapObjects 3 }


		-- 1.3.6.1.4.1.2011.5.25.327.31.3.1.4
		hwUniMbrTrapConnectErrorReason OBJECT-TYPE
			SYNTAX OCTET STRING
			MAX-ACCESS accessible-for-notify
			STATUS current
			DESCRIPTION
				"The reason of UNIMBR fabric-port connect error."
			::= { hwUniMbrTrapObjects 4 }


		-- 1.3.6.1.4.1.2011.5.25.327.31.3.1.5
		hwUniMbrTrapReceivePktRate OBJECT-TYPE
			SYNTAX Integer32
			MAX-ACCESS accessible-for-notify
			STATUS current
			DESCRIPTION
				"AS Discover packet rate."
			::= { hwUniMbrTrapObjects 5 }


		-- 1.3.6.1.4.1.2011.5.25.327.31.3.1.6
		hwUniMbrTrapAsIndex OBJECT-TYPE
			SYNTAX Integer32
			MAX-ACCESS accessible-for-notify
			STATUS current
			DESCRIPTION
				"AS index."
			::= { hwUniMbrTrapObjects 6 }


		-- 1.3.6.1.4.1.2011.5.25.327.31.3.1.7
		hwUniMbrTrapAsSysName OBJECT-TYPE
			SYNTAX OCTET STRING
			MAX-ACCESS accessible-for-notify
			STATUS current
			DESCRIPTION
				"Name of AS."
			::= { hwUniMbrTrapObjects 7 }


		-- 1.3.6.1.4.1.2011.5.25.327.31.3.1.8
		hwUniMbrParaSynFailReason OBJECT-TYPE
			SYNTAX OCTET STRING
			MAX-ACCESS accessible-for-notify
			STATUS current
			DESCRIPTION
				"The reason of UNIMBR parameter synchronization failed."
			::= { hwUniMbrTrapObjects 8 }


		-- 1.3.6.1.4.1.2011.5.25.327.31.3.1.9
		hwUniMbrTrapIllegalConfigReason OBJECT-TYPE
			SYNTAX OCTET STRING
			MAX-ACCESS accessible-for-notify
			STATUS current
			DESCRIPTION
				"The reason of UNIMBR illegal configuration."
			::= { hwUniMbrTrapObjects 9 }

		-- 1.3.6.1.4.1.2011.5.25.327.31.3.1.10
		hwUniMbrAsTrapInfo OBJECT-TYPE
			SYNTAX OCTET STRING
			MAX-ACCESS accessible-for-notify
			STATUS current
			DESCRIPTION
				"The AS service trap infomation."
			::= { hwUniMbrTrapObjects 10 }

		-- 1.3.6.1.4.1.2011.5.25.327.31.3.2
		hwUniMbrTraps OBJECT IDENTIFIER ::= { hwUniMbrTrap 2 }


		-- 1.3.6.1.4.1.2011.5.25.327.31.3.2.1
		hwUniMbrConnectError NOTIFICATION-TYPE
			OBJECTS { hwUniMbrTrapConnectErrorReason }
			STATUS current
			DESCRIPTION
				"The notification of fabric-port connect error."
			::= { hwUniMbrTraps 1 }


		-- 1.3.6.1.4.1.2011.5.25.327.31.3.2.2
		hwUniMbrASDiscoverAttack NOTIFICATION-TYPE
			OBJECTS { hwUniMbrTrapAsSysName, hwUniMbrTrapAsIndex, hwUniMbrLinkStatTrapLocalPortName, hwUniMbrTrapReceivePktRate }
			STATUS current
			DESCRIPTION
				"An AS discover packet attack is detected."
			::= { hwUniMbrTraps 2 }


		-- 1.3.6.1.4.1.2011.5.25.327.31.3.2.3
		hwUniMbrFabricPortMemberDelete NOTIFICATION-TYPE
			OBJECTS { hwUniMbrTrapAsSysName, hwUniMbrTrapAsIndex, hwUniMbrLinkStatTrapLocalPortName }
			STATUS current
			DESCRIPTION
				"The notification of deleting member of fabric port."
			::= { hwUniMbrTraps 3 }


		-- 1.3.6.1.4.1.2011.5.25.327.31.3.2.4
		hwUniMbrIllegalFabricConfig NOTIFICATION-TYPE
			OBJECTS { hwUniMbrTrapAsSysName, hwUniMbrTrapAsIndex, hwUniMbrTrapIllegalConfigReason }
			STATUS current
			DESCRIPTION
				"The notification of IllegalFabricConfig."
			::= { hwUniMbrTraps 4 }

		-- 1.3.6.1.4.1.2011.5.25.327.31.3.2.5
		hwUniMbrAsServiceAbnormal NOTIFICATION-TYPE
			OBJECTS { hwUniMbrTrapAsSysName, hwUniMbrTrapAsIndex, hwUniMbrAsTrapInfo }
			STATUS current
			DESCRIPTION
				"The notification of service trap on AS."
			::= { hwUniMbrTraps 5 }

		-- 1.3.6.1.4.1.2011.5.25.327.31.4
		hwVermngTrap OBJECT IDENTIFIER ::= { hwUnimngNotification 4 }


		-- 1.3.6.1.4.1.2011.5.25.327.31.4.1
		hwVermngTrapObjects OBJECT IDENTIFIER ::= { hwVermngTrap 1 }


		-- 1.3.6.1.4.1.2011.5.25.327.31.4.2
		hwVermngTraps OBJECT IDENTIFIER ::= { hwVermngTrap 2 }


		-- 1.3.6.1.4.1.2011.5.25.327.31.4.2.1
		hwVermngUpgradeFail NOTIFICATION-TYPE
			OBJECTS { hwAsmngTrapAsSysName, hwVermngUpgradeInfoAsErrorCode, hwVermngUpgradeInfoAsErrorDescr }
			STATUS current
			DESCRIPTION
				"Upgrade failed."
			::= { hwVermngTraps 1 }


		-- 1.3.6.1.4.1.2011.5.25.327.31.5
		hwTplmTrap OBJECT IDENTIFIER ::= { hwUnimngNotification 5 }


		-- 1.3.6.1.4.1.2011.5.25.327.31.5.1
		hwTplmTrapObjects OBJECT IDENTIFIER ::= { hwTplmTrap 1 }


		-- 1.3.6.1.4.1.2011.5.25.327.31.5.1.1
		hwTplmTrapASName OBJECT-TYPE
			SYNTAX OCTET STRING (SIZE (1..31))
			MAX-ACCESS accessible-for-notify
			STATUS current
			DESCRIPTION
				"The name of AS."
			::= { hwTplmTrapObjects 1 }


		-- 1.3.6.1.4.1.2011.5.25.327.31.5.1.2
		hwTplmTrapFailedReason OBJECT-TYPE
			SYNTAX OCTET STRING
			MAX-ACCESS accessible-for-notify
			STATUS current
			DESCRIPTION
				"The reason of failure."
			::= { hwTplmTrapObjects 2 }


		-- 1.3.6.1.4.1.2011.5.25.327.31.5.2
		hwTplmTraps OBJECT IDENTIFIER ::= { hwTplmTrap 2 }


		-- 1.3.6.1.4.1.2011.5.25.327.31.5.2.1
		hwTplmCmdExecuteFailedNotify NOTIFICATION-TYPE
			OBJECTS { hwTplmTrapASName, hwTplmTrapFailedReason }
			STATUS current
			DESCRIPTION
				"The notification of command execution failure."
			::= { hwTplmTraps 1 }


		-- 1.3.6.1.4.1.2011.5.25.327.31.5.2.2
		hwTplmCmdExecuteSuccessfulNotify NOTIFICATION-TYPE
			OBJECTS { hwTplmTrapASName }
			STATUS current
			DESCRIPTION
				"The notification of command execution failure cleared."
			::= { hwTplmTraps 2 }


		-- 1.3.6.1.4.1.2011.5.25.327.31.5.2.3
		hwTplmDirectCmdRecoverFail NOTIFICATION-TYPE
			OBJECTS { hwTplmTrapASName }
			STATUS current
			DESCRIPTION
				"The notification of direct command recovery failure."
			::= { hwTplmTraps 3 }


		-- 1.3.6.1.4.1.2011.5.25.327.31.6
		hwUniAsBaseTrap OBJECT IDENTIFIER ::= { hwUnimngNotification 6 }


		-- 1.3.6.1.4.1.2011.5.25.327.31.6.1
		hwUniAsBaseTrapObjects OBJECT IDENTIFIER ::= { hwUniAsBaseTrap 1 }


		-- 1.3.6.1.4.1.2011.5.25.327.31.6.1.1
		hwUniAsBaseAsName OBJECT-TYPE
			SYNTAX DisplayString
			MAX-ACCESS accessible-for-notify
			STATUS current
			DESCRIPTION
				"The name of AS."
			::= { hwUniAsBaseTrapObjects 1 }


		-- 1.3.6.1.4.1.2011.5.25.327.31.6.1.2
		hwUniAsBaseAsId OBJECT-TYPE
			SYNTAX Integer32
			MAX-ACCESS accessible-for-notify
			STATUS current
			DESCRIPTION
				"AS id."
			::= { hwUniAsBaseTrapObjects 2 }


		-- 1.3.6.1.4.1.2011.5.25.327.31.6.1.3
		hwUniAsBaseEntityPhysicalIndex OBJECT-TYPE
			SYNTAX Integer32
			MAX-ACCESS accessible-for-notify
			STATUS current
			DESCRIPTION
				"The index of AS physical."
			::= { hwUniAsBaseTrapObjects 3 }


		-- 1.3.6.1.4.1.2011.5.25.327.31.6.1.4
		hwUniAsBaseTrapSeverity OBJECT-TYPE
			SYNTAX Integer32
			MAX-ACCESS accessible-for-notify
			STATUS current
			DESCRIPTION
				"To describe the level of trap."
			::= { hwUniAsBaseTrapObjects 4 }


		-- 1.3.6.1.4.1.2011.5.25.327.31.6.1.5
		hwUniAsBaseTrapProbableCause OBJECT-TYPE
			SYNTAX Integer32
			MAX-ACCESS accessible-for-notify
			STATUS current
			DESCRIPTION
				"To describe the probable cause of trap."
			::= { hwUniAsBaseTrapObjects 5 }


		-- 1.3.6.1.4.1.2011.5.25.327.31.6.1.6
		hwUniAsBaseTrapEventType OBJECT-TYPE
			SYNTAX Integer32
			MAX-ACCESS accessible-for-notify
			STATUS current
			DESCRIPTION
				"To describe the type of trap."
			::= { hwUniAsBaseTrapObjects 6 }


		-- 1.3.6.1.4.1.2011.5.25.327.31.6.1.7
		hwUniAsBaseEntPhysicalContainedIn OBJECT-TYPE
			SYNTAX Integer32
			MAX-ACCESS accessible-for-notify
			STATUS current
			DESCRIPTION
				"The value of entPhysicalIndex for the physical entity which contains this physical entity."
			::= { hwUniAsBaseTrapObjects 7 }


		-- 1.3.6.1.4.1.2011.5.25.327.31.6.1.8
		hwUniAsBaseEntPhysicalName OBJECT-TYPE
			SYNTAX DisplayString
			MAX-ACCESS accessible-for-notify
			STATUS current
			DESCRIPTION
				"The textual name of the physical entity."
			::= { hwUniAsBaseTrapObjects 8 }


		-- 1.3.6.1.4.1.2011.5.25.327.31.6.1.9
		hwUniAsBaseRelativeResource OBJECT-TYPE
			SYNTAX DisplayString
			MAX-ACCESS accessible-for-notify
			STATUS current
			DESCRIPTION
				"This object may contain a key word to indicate the relative resource of an entity."
			::= { hwUniAsBaseTrapObjects 9 }


		-- 1.3.6.1.4.1.2011.5.25.327.31.6.1.10
		hwUniAsBaseReasonDescription OBJECT-TYPE
			SYNTAX DisplayString
			MAX-ACCESS accessible-for-notify
			STATUS current
			DESCRIPTION
				"Reason description."
			::= { hwUniAsBaseTrapObjects 10 }


		-- 1.3.6.1.4.1.2011.5.25.327.31.6.1.11
		hwUniAsBaseThresholdType OBJECT-TYPE
			SYNTAX Integer32
			MAX-ACCESS accessible-for-notify
			STATUS current
			DESCRIPTION
				"The index to indicate the type of threshold for an entry."
			::= { hwUniAsBaseTrapObjects 11 }


		-- 1.3.6.1.4.1.2011.5.25.327.31.6.1.12
		hwUniAsBaseThresholdValue OBJECT-TYPE
			SYNTAX Integer32
			MAX-ACCESS accessible-for-notify
			STATUS current
			DESCRIPTION
				"The current value that been measured."
			::= { hwUniAsBaseTrapObjects 12 }


		-- 1.3.6.1.4.1.2011.5.25.327.31.6.1.13
		hwUniAsBaseThresholdUnit OBJECT-TYPE
			SYNTAX Integer32
			MAX-ACCESS accessible-for-notify
			STATUS current
			DESCRIPTION
				"The unit for this threshold value."
			::= { hwUniAsBaseTrapObjects 13 }


		-- 1.3.6.1.4.1.2011.5.25.327.31.6.1.14
		hwUniAsBaseThresholdHighWarning OBJECT-TYPE
			SYNTAX Integer32
			MAX-ACCESS accessible-for-notify
			STATUS current
			DESCRIPTION
				"The normal warning threshold for rising alarm."
			::= { hwUniAsBaseTrapObjects 14 }


		-- 1.3.6.1.4.1.2011.5.25.327.31.6.1.15
		hwUniAsBaseThresholdHighCritical OBJECT-TYPE
			SYNTAX Integer32
			MAX-ACCESS accessible-for-notify
			STATUS current
			DESCRIPTION
				"The critical alarm threshold for rising alarm."
			::= { hwUniAsBaseTrapObjects 15 }


		-- 1.3.6.1.4.1.2011.5.25.327.31.6.1.16
		hwUniAsBaseThresholdLowWarning OBJECT-TYPE
			SYNTAX Integer32
			MAX-ACCESS accessible-for-notify
			STATUS current
			DESCRIPTION
				"The normal warning threshold for falling alarm."
			::= { hwUniAsBaseTrapObjects 16 }


		-- 1.3.6.1.4.1.2011.5.25.327.31.6.1.17
		hwUniAsBaseThresholdLowCritical OBJECT-TYPE
			SYNTAX Integer32
			MAX-ACCESS accessible-for-notify
			STATUS current
			DESCRIPTION
				"The critical alarm threshold for falling alarm."
			::= { hwUniAsBaseTrapObjects 17 }


		-- 1.3.6.1.4.1.2011.5.25.327.31.6.1.18
		hwUniAsBaseEntityTrapEntType OBJECT-TYPE
			SYNTAX Integer32
			MAX-ACCESS accessible-for-notify
			STATUS current
			DESCRIPTION
				"The entity type."
			::= { hwUniAsBaseTrapObjects 18 }


		-- 1.3.6.1.4.1.2011.5.25.327.31.6.1.19
		hwUniAsBaseEntityTrapEntFaultID OBJECT-TYPE
			SYNTAX Integer32
			MAX-ACCESS accessible-for-notify
			STATUS current
			DESCRIPTION
				"To describe the fault id of trap."
			::= { hwUniAsBaseTrapObjects 19 }


		-- 1.3.6.1.4.1.2011.5.25.327.31.6.1.20
		hwUniAsBaseEntityTrapCommunicateType OBJECT-TYPE
			SYNTAX Integer32
			MAX-ACCESS accessible-for-notify
			STATUS current
			DESCRIPTION
				"The communicate type."
			::= { hwUniAsBaseTrapObjects 20 }


		-- 1.3.6.1.4.1.2011.5.25.327.31.6.1.21
		hwUniAsBaseThresholdEntValue OBJECT-TYPE
			SYNTAX Integer32
			MAX-ACCESS accessible-for-notify
			STATUS current
			DESCRIPTION
				"The threshold value."
			::= { hwUniAsBaseTrapObjects 21 }


		-- 1.3.6.1.4.1.2011.5.25.327.31.6.1.22
		hwUniAsBaseThresholdEntCurrent OBJECT-TYPE
			SYNTAX Integer32
			MAX-ACCESS accessible-for-notify
			STATUS current
			DESCRIPTION
				"The current value that been measured."
			::= { hwUniAsBaseTrapObjects 22 }


		-- 1.3.6.1.4.1.2011.5.25.327.31.6.1.23
		hwUniAsBaseEntPhysicalIndex OBJECT-TYPE
			SYNTAX Integer32
			MAX-ACCESS accessible-for-notify
			STATUS current
			DESCRIPTION
				"The index of AS physical."
			::= { hwUniAsBaseTrapObjects 23 }


		-- 1.3.6.1.4.1.2011.5.25.327.31.6.1.24
		hwUniAsBaseThresholdHwBaseThresholdType OBJECT-TYPE
			SYNTAX Integer32
			MAX-ACCESS accessible-for-notify
			STATUS current
			DESCRIPTION
				"The type of base threshold."
			::= { hwUniAsBaseTrapObjects 24 }


		-- 1.3.6.1.4.1.2011.5.25.327.31.6.1.25
		hwUniAsBaseThresholdHwBaseThresholdIndex OBJECT-TYPE
			SYNTAX Integer32
			MAX-ACCESS accessible-for-notify
			STATUS current
			DESCRIPTION
				"The index of base threshold."
			::= { hwUniAsBaseTrapObjects 25 }


		-- 1.3.6.1.4.1.2011.5.25.327.31.6.2
		hwUniAsBaseTraps OBJECT IDENTIFIER ::= { hwUniAsBaseTrap 2 }


		-- 1.3.6.1.4.1.2011.5.25.327.31.6.2.2
		hwASEnvironmentTrap OBJECT IDENTIFIER ::= { hwUniAsBaseTraps 2 }


		-- 1.3.6.1.4.1.2011.5.25.327.31.6.2.2.1
		hwASBrdTempAlarm NOTIFICATION-TYPE
			OBJECTS { hwUniAsBaseAsName, hwUniAsBaseAsId, hwUniAsBaseEntPhysicalIndex, hwUniAsBaseEntityPhysicalIndex, hwUniAsBaseEntPhysicalName,
				hwUniAsBaseThresholdType, hwUniAsBaseThresholdEntValue, hwUniAsBaseThresholdEntCurrent, hwUniAsBaseEntityTrapEntFaultID }
			STATUS current
			DESCRIPTION
				"Temperature rise over or fall below the warning alarm threshold."
			::= { hwASEnvironmentTrap 1 }


		-- 1.3.6.1.4.1.2011.5.25.327.31.6.2.2.2
		hwASBrdTempResume NOTIFICATION-TYPE
			OBJECTS { hwUniAsBaseAsName, hwUniAsBaseAsId, hwUniAsBaseEntPhysicalIndex, hwUniAsBaseEntityPhysicalIndex, hwUniAsBaseEntPhysicalName,
				hwUniAsBaseThresholdType, hwUniAsBaseThresholdEntValue, hwUniAsBaseThresholdEntCurrent, hwUniAsBaseEntityTrapEntFaultID }
			STATUS current
			DESCRIPTION
				"Temperature back to normal level."
			::= { hwASEnvironmentTrap 2 }


		-- 1.3.6.1.4.1.2011.5.25.327.31.6.2.3
		hwASBoardTrap OBJECT IDENTIFIER ::= { hwUniAsBaseTraps 3 }


		-- 1.3.6.1.4.1.2011.5.25.327.31.6.2.3.1
		hwASBoardFail NOTIFICATION-TYPE
			OBJECTS { hwUniAsBaseAsName, hwUniAsBaseAsId, hwUniAsBaseEntPhysicalIndex, hwUniAsBaseEntityPhysicalIndex, hwUniAsBaseEntPhysicalName,
				hwUniAsBaseEntityTrapEntType, hwUniAsBaseEntityTrapEntFaultID }
			STATUS current
			DESCRIPTION
				"Board become failure for some reason."
			::= { hwASBoardTrap 1 }


		-- 1.3.6.1.4.1.2011.5.25.327.31.6.2.3.2
		hwASBoardFailResume NOTIFICATION-TYPE
			OBJECTS { hwUniAsBaseAsName, hwUniAsBaseAsId, hwUniAsBaseEntPhysicalIndex, hwUniAsBaseEntityPhysicalIndex, hwUniAsBaseEntPhysicalName,
				hwUniAsBaseEntityTrapEntType, hwUniAsBaseEntityTrapEntFaultID }
			STATUS current
			DESCRIPTION
				"Board resume from failure."
			::= { hwASBoardTrap 2 }


		-- 1.3.6.1.4.1.2011.5.25.327.31.6.2.4
		hwASOpticalTrap OBJECT IDENTIFIER ::= { hwUniAsBaseTraps 4 }


		-- 1.3.6.1.4.1.2011.5.25.327.31.6.2.4.1
		hwASOpticalInvalid NOTIFICATION-TYPE
			OBJECTS { hwUniAsBaseAsName, hwUniAsBaseAsId, hwUniAsBaseEntPhysicalIndex, hwUniAsBaseEntityPhysicalIndex, hwUniAsBaseEntPhysicalName,
				hwUniAsBaseEntityTrapEntFaultID }
			STATUS current
			DESCRIPTION
				"Optical Module is invalid for some reason."
			::= { hwASOpticalTrap 1 }


		-- 1.3.6.1.4.1.2011.5.25.327.31.6.2.4.2
		hwASOpticalInvalidResume NOTIFICATION-TYPE
			OBJECTS { hwUniAsBaseAsName, hwUniAsBaseAsId, hwUniAsBaseEntPhysicalIndex, hwUniAsBaseEntityPhysicalIndex, hwUniAsBaseEntPhysicalName,
				hwUniAsBaseEntityTrapEntFaultID }
			STATUS current
			DESCRIPTION
				"Optical Module resume from invalid situation."
			::= { hwASOpticalTrap 2 }


		-- 1.3.6.1.4.1.2011.5.25.327.31.6.2.5
		hwASPowerTrap OBJECT IDENTIFIER ::= { hwUniAsBaseTraps 5 }


		-- 1.3.6.1.4.1.2011.5.25.327.31.6.2.5.1
		hwASPowerRemove NOTIFICATION-TYPE
			OBJECTS { hwUniAsBaseAsName, hwUniAsBaseAsId, hwUniAsBaseEntPhysicalIndex, hwUniAsBaseEntityPhysicalIndex, hwUniAsBaseEntPhysicalName,
				hwUniAsBaseEntityTrapEntFaultID }
			STATUS current
			DESCRIPTION
				"Power has been removed."
			::= { hwASPowerTrap 1 }


		-- 1.3.6.1.4.1.2011.5.25.327.31.6.2.5.2
		hwASPowerInsert NOTIFICATION-TYPE
			OBJECTS { hwUniAsBaseAsName, hwUniAsBaseAsId, hwUniAsBaseEntPhysicalIndex, hwUniAsBaseEntityPhysicalIndex, hwUniAsBaseEntPhysicalName,
				hwUniAsBaseEntityTrapEntFaultID }
			STATUS current
			DESCRIPTION
				"Power has been inserted."
			::= { hwASPowerTrap 2 }


		-- 1.3.6.1.4.1.2011.5.25.327.31.6.2.5.3
		hwASPowerInvalid NOTIFICATION-TYPE
			OBJECTS { hwUniAsBaseAsName, hwUniAsBaseAsId, hwUniAsBaseEntPhysicalIndex, hwUniAsBaseEntityPhysicalIndex, hwUniAsBaseEntPhysicalName,
				hwUniAsBaseEntityTrapEntFaultID }
			STATUS current
			DESCRIPTION
				"Power is invalid for some reason."
			::= { hwASPowerTrap 3 }


		-- 1.3.6.1.4.1.2011.5.25.327.31.6.2.5.4
		hwASPowerInvalidResume NOTIFICATION-TYPE
			OBJECTS { hwUniAsBaseAsName, hwUniAsBaseAsId, hwUniAsBaseEntPhysicalIndex, hwUniAsBaseEntityPhysicalIndex, hwUniAsBaseEntPhysicalName,
				hwUniAsBaseEntityTrapEntFaultID }
			STATUS current
			DESCRIPTION
				"Power resume from invalid situation."
			::= { hwASPowerTrap 4 }


		-- 1.3.6.1.4.1.2011.5.25.327.31.6.2.6
		hwASFanTrap OBJECT IDENTIFIER ::= { hwUniAsBaseTraps 6 }


		-- 1.3.6.1.4.1.2011.5.25.327.31.6.2.6.1
		hwASFanRemove NOTIFICATION-TYPE
			OBJECTS { hwUniAsBaseAsName, hwUniAsBaseAsId, hwUniAsBaseEntPhysicalIndex, hwUniAsBaseEntityPhysicalIndex, hwUniAsBaseEntPhysicalName,
				hwUniAsBaseEntityTrapEntFaultID }
			STATUS current
			DESCRIPTION
				"Fan has been removed."
			::= { hwASFanTrap 1 }


		-- 1.3.6.1.4.1.2011.5.25.327.31.6.2.6.2
		hwASFanInsert NOTIFICATION-TYPE
			OBJECTS { hwUniAsBaseAsName, hwUniAsBaseAsId, hwUniAsBaseEntPhysicalIndex, hwUniAsBaseEntityPhysicalIndex, hwUniAsBaseEntPhysicalName,
				hwUniAsBaseEntityTrapEntFaultID }
			STATUS current
			DESCRIPTION
				"Fan has been inserted."
			::= { hwASFanTrap 2 }


		-- 1.3.6.1.4.1.2011.5.25.327.31.6.2.6.3
		hwASFanInvalid NOTIFICATION-TYPE
			OBJECTS { hwUniAsBaseAsName, hwUniAsBaseAsId, hwUniAsBaseEntPhysicalIndex, hwUniAsBaseEntityPhysicalIndex, hwUniAsBaseEntPhysicalName,
				hwUniAsBaseEntityTrapEntFaultID }
			STATUS current
			DESCRIPTION
				"Fan is invalid for some reason."
			::= { hwASFanTrap 3 }


		-- 1.3.6.1.4.1.2011.5.25.327.31.6.2.6.4
		hwASFanInvalidResume NOTIFICATION-TYPE
			OBJECTS { hwUniAsBaseAsName, hwUniAsBaseAsId, hwUniAsBaseEntPhysicalIndex, hwUniAsBaseEntityPhysicalIndex, hwUniAsBaseEntPhysicalName,
				hwUniAsBaseEntityTrapEntFaultID }
			STATUS current
			DESCRIPTION
				"Fan resume from invalid situation."
			::= { hwASFanTrap 4 }


		-- 1.3.6.1.4.1.2011.5.25.327.31.6.2.7
		hwASCommunicateTrap OBJECT IDENTIFIER ::= { hwUniAsBaseTraps 7 }


		-- 1.3.6.1.4.1.2011.5.25.327.31.6.2.7.1
		hwASCommunicateError NOTIFICATION-TYPE
			OBJECTS { hwUniAsBaseAsName, hwUniAsBaseAsId, hwUniAsBaseEntPhysicalIndex, hwUniAsBaseEntityPhysicalIndex, hwUniAsBaseEntPhysicalName,
				hwUniAsBaseEntityTrapEntType, hwUniAsBaseEntityTrapEntFaultID, hwUniAsBaseEntityTrapCommunicateType }
			STATUS current
			DESCRIPTION
				"Communication error has been detected."
			::= { hwASCommunicateTrap 1 }


		-- 1.3.6.1.4.1.2011.5.25.327.31.6.2.7.2
		hwASCommunicateResume NOTIFICATION-TYPE
			OBJECTS { hwUniAsBaseAsName, hwUniAsBaseAsId, hwUniAsBaseEntPhysicalIndex, hwUniAsBaseEntityPhysicalIndex, hwUniAsBaseEntPhysicalName,
				hwUniAsBaseEntityTrapEntType, hwUniAsBaseEntityTrapEntFaultID, hwUniAsBaseEntityTrapCommunicateType }
			STATUS current
			DESCRIPTION
				"Resume from communication error situation."
			::= { hwASCommunicateTrap 2 }


		-- 1.3.6.1.4.1.2011.5.25.327.31.6.2.8
		hwASCPUTrap OBJECT IDENTIFIER ::= { hwUniAsBaseTraps 8 }


		-- 1.3.6.1.4.1.2011.5.25.327.31.6.2.8.1
		hwASCPUUtilizationRising NOTIFICATION-TYPE
			OBJECTS { hwUniAsBaseAsName, hwUniAsBaseAsId, hwUniAsBaseEntPhysicalIndex, hwUniAsBaseEntityPhysicalIndex, hwUniAsBaseEntPhysicalName,
				hwUniAsBaseThresholdType, hwUniAsBaseThresholdEntValue, hwUniAsBaseThresholdEntCurrent, hwUniAsBaseEntityTrapEntFaultID }
			STATUS current
			DESCRIPTION
				"CPU utilization overrun."
			::= { hwASCPUTrap 1 }


		-- 1.3.6.1.4.1.2011.5.25.327.31.6.2.8.2
		hwASCPUUtilizationResume NOTIFICATION-TYPE
			OBJECTS { hwUniAsBaseAsName, hwUniAsBaseAsId, hwUniAsBaseEntPhysicalIndex, hwUniAsBaseEntityPhysicalIndex, hwUniAsBaseEntPhysicalName,
				hwUniAsBaseThresholdType, hwUniAsBaseThresholdEntValue, hwUniAsBaseThresholdEntCurrent, hwUniAsBaseEntityTrapEntFaultID }
			STATUS current
			DESCRIPTION
				"CPU utilization back to normal level."
			::= { hwASCPUTrap 2 }


		-- 1.3.6.1.4.1.2011.5.25.327.31.6.2.9
		hwASMemoryTrap OBJECT IDENTIFIER ::= { hwUniAsBaseTraps 9 }


		-- 1.3.6.1.4.1.2011.5.25.327.31.6.2.9.1
		hwASMemUtilizationRising NOTIFICATION-TYPE
			OBJECTS { hwUniAsBaseAsName, hwUniAsBaseAsId, hwUniAsBaseEntPhysicalIndex, hwUniAsBaseEntityPhysicalIndex, hwUniAsBaseEntPhysicalName,
				hwUniAsBaseThresholdType, hwUniAsBaseThresholdEntValue, hwUniAsBaseThresholdEntCurrent, hwUniAsBaseEntityTrapEntFaultID }
			STATUS current
			DESCRIPTION
				"Memory utilization overrun."
			::= { hwASMemoryTrap 1 }


		-- 1.3.6.1.4.1.2011.5.25.327.31.6.2.9.2
		hwASMemUtilizationResume NOTIFICATION-TYPE
			OBJECTS { hwUniAsBaseAsName, hwUniAsBaseAsId, hwUniAsBaseEntPhysicalIndex, hwUniAsBaseEntityPhysicalIndex, hwUniAsBaseEntPhysicalName,
				hwUniAsBaseThresholdType, hwUniAsBaseThresholdEntValue, hwUniAsBaseThresholdEntCurrent, hwUniAsBaseEntityTrapEntFaultID }
			STATUS current
			DESCRIPTION
				"Memory utilization back to normal level."
			::= { hwASMemoryTrap 2 }


		-- 1.3.6.1.4.1.2011.5.25.327.31.6.2.10
		hwASMadTrap OBJECT IDENTIFIER ::= { hwUniAsBaseTraps 10 }


		-- 1.3.6.1.4.1.2011.5.25.327.31.6.2.10.1
		hwASMadConflictDetect NOTIFICATION-TYPE
			OBJECTS { hwUniAsBaseAsName, hwUniAsBaseAsId }
			STATUS current
			DESCRIPTION
				"Notify the NMS that dual-active scenario is detected."
			::= { hwASMadTrap 1 }


		-- 1.3.6.1.4.1.2011.5.25.327.31.6.2.10.2
		hwASMadConflictResume NOTIFICATION-TYPE
			OBJECTS { hwUniAsBaseAsName, hwUniAsBaseAsId }
			STATUS current
			DESCRIPTION
				"Notify the NMS that dual-active scenario is merged."
			::= { hwASMadTrap 2 }


		-- 1.3.6.1.4.1.2011.5.25.327.50
		hwUnimngConformance OBJECT IDENTIFIER ::= { hwUnimngMIB 50 }


		-- 1.3.6.1.4.1.2011.5.25.327.50.1
		hwTopomngCompliances OBJECT IDENTIFIER ::= { hwUnimngConformance 1 }


-- this module
		-- 1.3.6.1.4.1.2011.5.25.327.50.1.1
		hwTopomngCompliance MODULE-COMPLIANCE
			STATUS current
			DESCRIPTION
				"The compliance statement for SNMP entities supporting topomng."
			MODULE -- this module
				MANDATORY-GROUPS { hwTopomngObjectsGroup, hwTopomngTopoGroup, hwTopomngTrapObjectsGroup, hwTopomngTrapsGroup }
			::= { hwTopomngCompliances 1 }


		-- 1.3.6.1.4.1.2011.5.25.327.50.1.1.1
		hwTopomngObjectsGroup OBJECT-GROUP
			OBJECTS { hwTopomngExploreTime, hwTopomngLastCollectDuration }
			STATUS current
			DESCRIPTION
				"The topomng objects group."
			::= { hwTopomngCompliance 1 }


		-- 1.3.6.1.4.1.2011.5.25.327.50.1.1.2
		hwTopomngTopoGroup OBJECT-GROUP
			OBJECTS { hwTopoPeerMac, hwTopoLocalPortName, hwTopoPeerPortName, hwTopoLocalTrunkId, hwTopoPeerTrunkId,
				hwTopoLocalRole, hwTopoPeerRole }
			STATUS current
			DESCRIPTION
				"The topology table group."
			::= { hwTopomngCompliance 2 }


		-- 1.3.6.1.4.1.2011.5.25.327.50.1.1.3
		hwTopomngTrapObjectsGroup OBJECT-GROUP
			OBJECTS { hwTopomngTrapLocalMac, hwTopomngTrapLocalPortName, hwTopomngTrapLocalTrunkId, hwTopomngTrapPeerMac, hwTopomngTrapPeerPortName,
				hwTopomngTrapPeerTrunkId, hwTopomngTrapReason }
			STATUS current
			DESCRIPTION
				"The topomng trap objects group."
			::= { hwTopomngCompliance 3 }


		-- 1.3.6.1.4.1.2011.5.25.327.50.1.1.4
		hwTopomngTrapsGroup NOTIFICATION-GROUP
			NOTIFICATIONS { hwTopomngLinkNormal, hwTopomngLinkAbnormal }
			STATUS current
			DESCRIPTION
				"The topomng notification objects group."
			::= { hwTopomngCompliance 4 }


		-- 1.3.6.1.4.1.2011.5.25.327.50.2
		hwAsmngCompliances OBJECT IDENTIFIER ::= { hwUnimngConformance 2 }


-- this module
		-- 1.3.6.1.4.1.2011.5.25.327.50.2.1
		hwAsmngCompliance MODULE-COMPLIANCE
			STATUS current
			DESCRIPTION
				"The compliance statement for SNMP entities supporting asmng."
			MODULE -- this module
				MANDATORY-GROUPS { hwAsmngObjectsGroup, hwAsmngAsGroup, hwAsmngAsIfGroup, hwAsmngAsIfXGroup, hwAsmngTrapObjectsGroup,
					hwAsmngTrapsGroup, hwAsmngGlobalObjectsGroup, hwAsmngMacWhitelistGroup, hwAsmngMacBlacklistGroup, hwAsmngEntityPhysicalGroup,
					hwAsmngEntityStateGroup, hwAsmngEntityAliasMappingGroup, hwAsmngSlotGroup }
			::= { hwAsmngCompliances 1 }


		-- 1.3.6.1.4.1.2011.5.25.327.50.2.1.1
		hwAsmngObjectsGroup OBJECT-GROUP
			OBJECTS { hwUniMngEnable }
			STATUS current
			DESCRIPTION
				"The AS management objects group."
			::= { hwAsmngCompliance 1 }


		-- 1.3.6.1.4.1.2011.5.25.327.50.2.1.2
		hwAsmngAsGroup OBJECT-GROUP
			OBJECTS { hwAsHardwareVersion, hwAsIpAddress, hwAsIpNetMask, hwAsAccessUser, hwAsMac,
				hwAsSn, hwAsSysName, hwAsRunState, hwAsSoftwareVersion, hwAsDns,
				hwAsOnlineTime, hwAsCpuUseage, hwAsMemoryUseage, hwAsSysMac, hwAsStackEnable,
				hwAsGatewayIp, hwAsRowstatus, hwAsModel, hwAsIndex, hwAsVpnInstance, hwAsMode }
			STATUS current
			DESCRIPTION
				"The as table group."
			::= { hwAsmngCompliance 2 }


		-- 1.3.6.1.4.1.2011.5.25.327.50.2.1.3
		hwAsmngAsIfGroup OBJECT-GROUP
			OBJECTS { hwAsIfDescr, hwAsIfType, hwAsIfMtu, hwAsIfSpeed, hwAsIfPhysAddress,
				hwAsIfAdminStatus, hwAsIfInUcastPkts, hwAsIfOutUcastPkts, hwAsIfOperStatus, hwAsIfIndex
				 }
			STATUS current
			DESCRIPTION
				"The as table group."
			::= { hwAsmngCompliance 3 }


		-- 1.3.6.1.4.1.2011.5.25.327.50.2.1.4
		hwAsmngAsIfXGroup OBJECT-GROUP
			OBJECTS { hwAsIfLinkUpDownTrapEnable, hwAsIfHighSpeed, hwAsIfAlias, hwAsIfInUcastPkts, hwAsIfOutUcastPkts,
				hwAsIfHCOutOctets, hwAsIfInMulticastPkts, hwAsIfInBroadcastPkts, hwAsIfOutMulticastPkts, hwAsIfOutBroadcastPkts,
				hwAsIfHCInOctets, hwAsIfXLastUpTime, hwAsIfXLastDownTime, hwAsIfAsId, hwAsIfName }
			STATUS current
			DESCRIPTION
				"The as table group."
			::= { hwAsmngCompliance 4 }


		-- 1.3.6.1.4.1.2011.5.25.327.50.2.1.5
		hwAsmngTrapObjectsGroup OBJECT-GROUP
			OBJECTS { hwAsmngTrapAsIndex, hwAsmngTrapAsModel, hwAsmngTrapAsSysName, hwAsmngTrapAsMac, hwAsmngTrapAsSn,
				hwAsmngTrapAsIfIndex, hwAsmngTrapAsIfOperStatus, hwAsmngTrapAsFaultTimes, hwAsmngTrapAsIfAdminStatus, hwAsmngTrapAsIfName,
				hwAsmngTrapAsActualeType, hwAsmngTrapAsVersion, hwAsmngTrapParentVersion, hwAsmngTrapAddedAsMac, hwAsmngTrapAsSlotId,
				hwAsmngTrapAddedAsSlotType, hwAsmngTrapAsPermitNum, hwAsmngTrapAsUnimngMode, hwAsmngTrapParentUnimngMode, hwAsmngTrapAsIfType,
				hwAsmngTrapAsOnlineFailReasonId, hwAsmngTrapAsOnlineFailReasonDesc, hwAsmngTrapAsSlotOnlineFailReasonId, hwAsmngTrapAsSlotOnlineFailReasonDesc }
			STATUS current
			DESCRIPTION
				"The AS management trap objects group."
			::= { hwAsmngCompliance 5 }


		-- 1.3.6.1.4.1.2011.5.25.327.50.2.1.6
		hwAsmngTrapsGroup NOTIFICATION-GROUP
			NOTIFICATIONS { hwAsFaultNotify, hwAsNormalNotify, hwAsAddOffLineNotify, hwAsDelOffLineNotify, hwAsPortStateChangeToDownNotify,
				hwAsPortStateChangeToUpNotify, hwAsModelNotMatchNotify, hwAsVersionNotMatchNotify, hwAsNameConflictNotify, hwAsSlotModelNotMatchNotify,
				hwAsFullNotify, hwUnimngModeNotMatchNotify, hwAsBoardAddNotify, hwAsBoardDeleteNotify, hwAsBoardPlugInNotify,
				hwAsBoardPlugOutNotify, hwAsInBlacklistNotify, hwAsUnconfirmedNotify, hwAsComboPortTypeChangeNotify, hwAsOnlineFailNotify,
				hwAsSlotIdInvalidNotify, hwAsSysmacSwitchCfgErrNotify, hwAsSlotOnlineFailNotify }
			STATUS current
			DESCRIPTION
				"The AS management notification objects group."
			::= { hwAsmngCompliance 6 }


		-- 1.3.6.1.4.1.2011.5.25.327.50.2.1.7
		hwAsmngGlobalObjectsGroup OBJECT-GROUP
			OBJECTS { hwAsAutoReplaceEnable, hwAsAuthMode }
			STATUS current
			DESCRIPTION
				"Description."
			::= { hwAsmngCompliance 7 }


		-- 1.3.6.1.4.1.2011.5.25.327.50.2.1.8
		hwAsmngMacWhitelistGroup OBJECT-GROUP
			OBJECTS { hwAsMacWhitelistRowStatus }
			STATUS current
			DESCRIPTION
				"Description."
			::= { hwAsmngCompliance 8 }


		-- 1.3.6.1.4.1.2011.5.25.327.50.2.1.9
		hwAsmngMacBlacklistGroup OBJECT-GROUP
			OBJECTS { hwAsMacBlacklistRowStatus }
			STATUS current
			DESCRIPTION
				"Description."
			::= { hwAsmngCompliance 9 }


		-- 1.3.6.1.4.1.2011.5.25.327.50.2.1.10
		hwAsmngEntityPhysicalGroup OBJECT-GROUP
			OBJECTS { hwAsEntityPhysicalDescr, hwAsEntityPhysicalVendorType, hwAsEntityPhysicalContainedIn, hwAsEntityPhysicalClass, hwAsEntityPhysicalParentRelPos,
				hwAsEntityPhysicalName, hwAsEntityPhysicalHardwareRev, hwAsEntityPhysicalFirmwareRev, hwAsEntityPhysicalSoftwareRev, hwAsEntityPhysicalSerialNum,
				hwAsEntityPhysicalMfgName }
			STATUS current
			DESCRIPTION
				"Description."
			::= { hwAsmngCompliance 10 }


		-- 1.3.6.1.4.1.2011.5.25.327.50.2.1.11
		hwAsmngEntityStateGroup OBJECT-GROUP
			OBJECTS { hwAsEntityAdminStatus, hwAsEntityOperStatus, hwAsEntityStandbyStatus, hwAsEntityAlarmLight, hwAsEntityPortType
				 }
			STATUS current
			DESCRIPTION
				"Description."
			::= { hwAsmngCompliance 11 }


		-- 1.3.6.1.4.1.2011.5.25.327.50.2.1.12
		hwAsmngEntityAliasMappingGroup OBJECT-GROUP
			OBJECTS { hwAsEntryAliasMappingIdentifier }
			STATUS current
			DESCRIPTION
				"Description."
			::= { hwAsmngCompliance 12 }


		-- 1.3.6.1.4.1.2011.5.25.327.50.2.1.13
		hwAsmngSlotGroup OBJECT-GROUP
			OBJECTS { hwAsSlotState, hwAsSlotRowStatus, hwAsSlotModel }
			STATUS current
			DESCRIPTION
				"Description."
			::= { hwAsmngCompliance 13 }


		-- 1.3.6.1.4.1.2011.5.25.327.50.3
		hwMbrCompliances OBJECT IDENTIFIER ::= { hwUnimngConformance 3 }


-- this module
		-- 1.3.6.1.4.1.2011.5.25.327.50.3.1
		hwMbrCompliance MODULE-COMPLIANCE
			STATUS current
			DESCRIPTION
				"The compliance statement for SNMP entities supporting mbrmng."
			MODULE -- this module
				MANDATORY-GROUPS { hwMbrTrapObjectsGroup, hwMbrTrapsGroup, hwMbrFabricPortGroup }
			::= { hwMbrCompliances 1 }


		-- 1.3.6.1.4.1.2011.5.25.327.50.3.1.1
		hwMbrTrapObjectsGroup OBJECT-GROUP
			OBJECTS { hwUniMbrLinkStatTrapLocalMac, hwUniMbrLinkStatTrapLocalPortName, hwUniMbrLinkStatTrapChangeType, hwUniMbrTrapConnectErrorReason, hwUniMbrTrapReceivePktRate,
				hwUniMbrTrapAsIndex, hwUniMbrTrapAsSysName, hwUniMbrParaSynFailReason, hwUniMbrTrapIllegalConfigReason, hwUniMbrAsTrapInfo }
			STATUS current
			DESCRIPTION
				"The mbrmng trap objects group."
			::= { hwMbrCompliance 1 }


		-- 1.3.6.1.4.1.2011.5.25.327.50.3.1.2
		hwMbrTrapsGroup NOTIFICATION-GROUP
			NOTIFICATIONS { hwUniMbrConnectError, hwUniMbrASDiscoverAttack, hwUniMbrFabricPortMemberDelete, hwUniMbrIllegalFabricConfig, hwUniMbrAsServiceAbnormal }
			STATUS current
			DESCRIPTION
				"The mbrmng notification objects group."
			::= { hwMbrCompliance 2 }


		-- 1.3.6.1.4.1.2011.5.25.327.50.3.1.3
		hwMbrFabricPortGroup OBJECT-GROUP
			OBJECTS { hwMbrMngFabricPortMemberIfName, hwMbrMngFabricPortDirection, hwMbrMngFabricPortIndirectFlag, hwMbrMngFabricPortDescription, hwMbrMngFabricPortModeFlag }
			STATUS current
			DESCRIPTION
				"The mbrmng fabric port group."
			::= { hwMbrCompliance 3 }


		-- 1.3.6.1.4.1.2011.5.25.327.50.4
		hwVermngCompliances OBJECT IDENTIFIER ::= { hwUnimngConformance 4 }


-- this module
		-- 1.3.6.1.4.1.2011.5.25.327.50.4.1
		hwVermngCompliance MODULE-COMPLIANCE
			STATUS current
			DESCRIPTION
				"The compliance of version management."
			MODULE -- this module
				MANDATORY-GROUPS { hwVermngObjectsGroup, hwVermngUpgradeInfoGroup, hwVermngAsTypeCfgInfoGroup, hwVermngTrapsGroup }
			::= { hwVermngCompliances 1 }


		-- 1.3.6.1.4.1.2011.5.25.327.50.4.1.1
		hwVermngObjectsGroup OBJECT-GROUP
			OBJECTS { hwVermngFileServerType }
			STATUS current
			DESCRIPTION
				"The group of global objects."
			::= { hwVermngCompliance 1 }


		-- 1.3.6.1.4.1.2011.5.25.327.50.4.1.2
		hwVermngUpgradeInfoGroup OBJECT-GROUP
			OBJECTS { hwVermngUpgradeInfoAsName, hwVermngUpgradeInfoAsSysSoftware, hwVermngUpgradeInfoAsSysSoftwareVer, hwVermngUpgradeInfoAsSysPatch, hwVermngUpgradeInfoAsDownloadSoftware,
				hwVermngUpgradeInfoAsDownloadSoftwareVer, hwVermngUpgradeInfoAsDownloadPatch, hwVermngUpgradeInfoAsUpgradeState, hwVermngUpgradeInfoAsUpgradeType, hwVermngUpgradeInfoAsFilePhase,
				hwVermngUpgradeInfoAsUpgradePhase, hwVermngUpgradeInfoAsUpgradeResult, hwVermngUpgradeInfoAsErrorCode, hwVermngUpgradeInfoAsErrorDescr }
			STATUS current
			DESCRIPTION
				"The group of upgrade info."
			::= { hwVermngCompliance 2 }


		-- 1.3.6.1.4.1.2011.5.25.327.50.4.1.3
		hwVermngAsTypeCfgInfoGroup OBJECT-GROUP
			OBJECTS { hwVermngAsTypeCfgInfoPatch, hwVermngAsTypeCfgInfoSystemSoftwareVer, hwVermngAsTypeCfgInfoRowStatus, hwVermngAsTypeCfgInfoSystemSoftware, hwVermngAsTypeCfgInfoAsTypeName
				 }
			STATUS current
			DESCRIPTION
				"The group of AS type."
			::= { hwVermngCompliance 3 }


		-- 1.3.6.1.4.1.2011.5.25.327.50.4.1.4
		hwVermngTrapsGroup NOTIFICATION-GROUP
			NOTIFICATIONS { hwVermngUpgradeFail }
			STATUS current
			DESCRIPTION
				"The group of notification of version management."
			::= { hwVermngCompliance 4 }


		-- 1.3.6.1.4.1.2011.5.25.327.50.5
		hwTplmCompliances OBJECT IDENTIFIER ::= { hwUnimngConformance 5 }


-- this module
		-- 1.3.6.1.4.1.2011.5.25.327.50.5.1
		hwTplmCompliance MODULE-COMPLIANCE
			STATUS current
			DESCRIPTION
				"The compliance of template management."
			MODULE -- this module
				MANDATORY-GROUPS { hwVermngObjectsGroup, hwVermngUpgradeInfoGroup, hwVermngAsTypeCfgInfoGroup, hwVermngTrapsGroup }
			::= { hwTplmCompliances 1 }


		-- 1.3.6.1.4.1.2011.5.25.327.50.5.1.1
		hwTplmASGroupGoup OBJECT-GROUP
			OBJECTS { hwTplmASGroupName, hwTplmASAdminProfileName, hwTplmASGroupProfileStatus, hwTplmASGroupRowStatus }
			STATUS current
			DESCRIPTION
				"The group of as group."
			::= { hwTplmCompliance 1 }


		-- 1.3.6.1.4.1.2011.5.25.327.50.5.1.2
		hwTplmASGoup OBJECT-GROUP
			OBJECTS { hwTplmASASGroupName, hwTplmASRowStatus }
			STATUS current
			DESCRIPTION
				"The group of as."
			::= { hwTplmCompliance 2 }


		-- 1.3.6.1.4.1.2011.5.25.327.50.5.1.3
		hwTplmPortGroupGoup OBJECT-GROUP
			OBJECTS { hwTplmPortGroupName, hwTplmPortGroupType, hwTplmPortGroupNetworkBasicProfile, hwTplmPortGroupNetworkEnhancedProfile, hwTplmPortGroupUserAccessProfile,
				hwTplmPortGroupProfileStatus, hwTplmPortGroupRowStatus }
			STATUS current
			DESCRIPTION
				"The group of port group."
			::= { hwTplmCompliance 3 }


		-- 1.3.6.1.4.1.2011.5.25.327.50.5.1.4
		hwTplmPortGoup OBJECT-GROUP
			OBJECTS { hwTplmPortPortGroupName, hwTplmPortRowStatus }
			STATUS current
			DESCRIPTION
				"The group of port."
			::= { hwTplmCompliance 4 }


		-- 1.3.6.1.4.1.2011.5.25.327.50.5.1.5
		hwTplmConfigManagementGoup OBJECT-GROUP
			OBJECTS { hwTplmConfigCommitAll, hwTplmConfigManagementCommit }
			STATUS current
			DESCRIPTION
				"The group of configuration management."
			::= { hwTplmCompliance 5 }


		-- 1.3.6.1.4.1.2011.5.25.327.50.5.1.6
		hwTplmTrapObjectsGroup OBJECT-GROUP
			OBJECTS { hwTplmTrapASName, hwTplmTrapFailedReason }
			STATUS current
			DESCRIPTION
				"The tplm trap objects group."
			::= { hwTplmCompliance 6 }


		-- 1.3.6.1.4.1.2011.5.25.327.50.5.1.7
		hwTplmTrapsGroup NOTIFICATION-GROUP
			NOTIFICATIONS { hwTplmCmdExecuteFailedNotify, hwTplmCmdExecuteSuccessfulNotify, hwTplmDirectCmdRecoverFail }
			STATUS current
			DESCRIPTION
				"The tplm notification objects group."
			::= { hwTplmCompliance 7 }


		-- 1.3.6.1.4.1.2011.5.25.327.50.6
		hwUniBaseTrapCompliances OBJECT IDENTIFIER ::= { hwUnimngConformance 6 }


--  this module
		-- 1.3.6.1.4.1.2011.5.25.327.50.6.1
		hwUniBaseTrapCompliance MODULE-COMPLIANCE
			STATUS current
			DESCRIPTION
				"The compliance statement for SNMP entities supporting unimng base trap."
			MODULE -- this module
				MANDATORY-GROUPS { hwUniBaseTrapObjectsGroup, hwUniBaseTrapsGroup }
			::= { hwUniBaseTrapCompliances 1 }


		-- 1.3.6.1.4.1.2011.5.25.327.50.6.1.1
		hwUniBaseTrapObjectsGroup OBJECT-GROUP
			OBJECTS { hwUniAsBaseAsName, hwUniAsBaseAsId, hwUniAsBaseEntityPhysicalIndex, hwUniAsBaseTrapSeverity, hwUniAsBaseTrapProbableCause,
				hwUniAsBaseTrapEventType, hwUniAsBaseEntPhysicalContainedIn, hwUniAsBaseEntPhysicalName, hwUniAsBaseRelativeResource, hwUniAsBaseReasonDescription,
				hwUniAsBaseThresholdType, hwUniAsBaseThresholdValue, hwUniAsBaseThresholdUnit, hwUniAsBaseThresholdHighWarning, hwUniAsBaseThresholdHighCritical,
				hwUniAsBaseThresholdLowWarning, hwUniAsBaseThresholdLowCritical, hwUniAsBaseEntityTrapEntType, hwUniAsBaseEntityTrapEntFaultID, hwUniAsBaseEntityTrapCommunicateType,
				hwUniAsBaseThresholdEntValue, hwUniAsBaseThresholdEntCurrent, hwUniAsBaseEntPhysicalIndex, hwUniAsBaseThresholdHwBaseThresholdType, hwUniAsBaseThresholdHwBaseThresholdIndex
				 }
			STATUS current
			DESCRIPTION
				"The unimng base trap objects group."
			::= { hwUniBaseTrapCompliance 1 }


		-- 1.3.6.1.4.1.2011.5.25.327.50.6.1.2
		hwUniBaseTrapsGroup NOTIFICATION-GROUP
			NOTIFICATIONS { hwASBoardFail, hwASBoardFailResume, hwASOpticalInvalid, hwASOpticalInvalidResume, hwASPowerRemove,
				hwASPowerInsert, hwASPowerInvalid, hwASPowerInvalidResume, hwASFanRemove, hwASFanInsert,
				hwASFanInvalid, hwASFanInvalidResume, hwASCommunicateError, hwASCommunicateResume, hwASCPUUtilizationRising,
				hwASCPUUtilizationResume, hwASMemUtilizationRising, hwASMemUtilizationResume, hwASMadConflictDetect, hwASMadConflictResume,
				hwASBrdTempAlarm, hwASBrdTempResume }
			STATUS current
			DESCRIPTION
				"The unimng base notification objects group."
			::= { hwUniBaseTrapCompliance 2 }


		-- 1.3.6.1.4.1.2011.5.25.327.50.7
		hwMaintenMngCompliances OBJECT IDENTIFIER ::= { hwUnimngConformance 7 }

-- this module
		-- 1.3.6.1.4.1.2011.5.25.327.50.7.1
		hwMaintenMngCompliance MODULE-COMPLIANCE
			STATUS current
			DESCRIPTION
				"The compliance of maintenance management."
			MODULE -- this module
				MANDATORY-GROUPS { hwUnAuthenUserObjectsGroup }
			::= { hwMaintenMngCompliances 1 }


		-- 1.3.6.1.4.1.2011.5.25.327.50.7.1.1
		hwUnAuthenUserObjectsGroup OBJECT-GROUP
			OBJECTS { hwUnAuthenUserAsIndex, hwUnAuthenUserVlan, hwUnAuthenUserMac, hwUnAuthenUserIP, hwUnAuthenUserAsName, hwUnAuthenUserIfName }
			STATUS current
			DESCRIPTION
				"The entry of the table of unauthen user."
			::= { hwMaintenMngCompliance 1 }

		-- 1.3.6.1.4.1.2011.5.25.327.50.7.1.2
		hwAuthenUserObjectsGroup OBJECT-GROUP
			OBJECTS { hwAuthenUserAsIndex, hwAuthenUserVlan, hwAuthenUserMac, hwAuthenUserIP, hwAuthenUserAsName, hwAuthenUserIfName }
			STATUS current
			DESCRIPTION
				"The entry of the table of authen user."
			::= { hwMaintenMngCompliance 2 }

		END

--
-- HUAWEI-UNIMNG-MIB.1.15.mib
--
