-- ============================================================================
-- Copyright (C) 2017 by  HUAWEI TECHNOLOGIES. All rights reserved.
-- Description: The entity of ont configuration and control.
-- Reference:
-- Version: V1.29
-- ============================================================================

    --MIB Define
      HUAWEI-VOIP-ONT-MIB DEFINITIONS ::= BEGIN

    --Import types
      IMPORTS
                MODULE-IDENTITY, OBJECT-TYPE, NOTIFICATION-TYPE, private
                    FROM SNMPv2-SMI
                MODULE-COMPLIANCE, OBJECT-GROUP, NOTIFICATION-GROUP
                    FROM SNMPv2-CONF
                TEXTUAL-CONVENTION
                    FROM SNMPv2-TC
                IpAddress,TimeTicks,Counter32,Integer32,Unsigned32
                    FROM SNMPv2-SMI
                RowStatus,DisplayString
                    FROM SNMPv2-TC
                huaweiUtility
                    FROM HUAWEI-MIB
                hwFrameIndex,hwSlotIndex,hwPortIndex
                    FROM HUAWEI-DEVICE-MIB;


    --Module define
      hwVoip MODULE-IDENTITY
                LAST-UPDATED "201707061450Z"
                ORGANIZATION "Huawei Technologies Co.,Ltd."
                CONTACT-INFO
                             "Huawei Industrial Base
                              Bantian, Longgang
                              Shenzhen 518129
                              People's Republic of China
                              Website: http://www.huawei.com
                              Email: support@huawei.com
                             "
                DESCRIPTION
                         "
                         The entity of ont configuration and control.
                         "
				--  Revision history
                REVISION     "201707061450Z"
                DESCRIPTION  "V1.29, change in this revision:
                              -Modified the parameter of hwOntMassVoipFaultEventTrap
                             "

                --  Revision history
                REVISION     "201706071850Z"
                DESCRIPTION  "V1.28, change in this revision:
                              -Added hwOntVoipMassMGAlarmThreshold,
                              -Added hwOntMassMgInterfaceFaultAlarmTrap
                              -Added hwOntMassMgInterfaceRestoreAlarmTrap
                             "

			        	REVISION     "201706011450Z"
                DESCRIPTION  "V1.27, change in this revision:
                              -Modified the type of the following leaves, including:
                               hwOntVoipFaultEventStartHour
                               hwOntVoipFaultEventStartMinute
                               hwOntVoipFaultEventEndHour
							                 hwOntVoipFaultEventEndMinute
                             "

                REVISION     "201705091421Z"
                DESCRIPTION  "V1.26, change in this revision:
                              -Added hwOntVoipSingleAlarmSwitch,
                              -Added hwOntVoipMassAlarmSwitch
                              -Added hwOntVoipMassEventSwitch
                              -Added hwOntVoipMassEventContent
                              -Added hwOntVoipMassEventThreshold
			                        -Added hwOntVoipFaultEventStartHour
			                        -Added hwOntVoipFaultEventStartMinute
			                        -Added hwOntVoipFaultEventEndHour
			                        -Added hwOntVoipFaultEventEndMinute
                              -Added hwOntMassVoipFaultEventTrap
			      			            -Added hwOntRecentVoipAlarmRecordTable
			      			            -Added hwOntRecentVoipAlarmRecordEntry
			      			            -Added hwOntRecentVoipAlarmBlockIndex
			      		          	  -Added hwOntRecentVoipAlarmOctetString
                              "

                REVISION     "201607211421Z"
                DESCRIPTION  "V1.25, change in this revision:
                              -Modified the default value description of the following leaves, including:
                               hwOntPstnCTPNewServiceRight
                               hwOntMgPstnCTPCodecSelect
                               hwOntMgPstnCTPOrder2stPacketPeriod
                             "

                REVISION     "201505201520Z"
                DESCRIPTION  "V1.24, change in this revision:
                              -Added hwOntVoipToneTable,
                              -Added hwOntVoipSignalProfileTable
                              -Added hwOntVoipBindSignalProfileTable
                              -Added hwOntVoipIpIndexTable
                              -Added hwOntVoipRingTable
                             "

                REVISION     "201504041437Z"
                DESCRIPTION  "V1.23, change in this revision:
                              --Modified the description of the following leaves, including:
                               hwOntPstnCallerEmulateTestStatus
                             "

                REVISION     "201411171541Z"
                DESCRIPTION  "V1.22, change in this revision:
                              -Modified the range of the following leaves, including:
                               hwOntPstnCTPIPIndex
                               hwOntMgVagIpIndex
                               hwOntSipVagIpIndex
                             "

                REVISION    "201409221000Z"
                DESCRIPTION "V1.21,  change in this revision:
		             -Modified the MAX-ACCESS value of the following leaves, including
			      hwOntPotsRowStatus
                              hwOntSipAgentRowStatus
                              hwOntDigitMapRowStatus
                              hwOntPotsCTPRowStatus
                              hwOntMgVagRowStatus
                              hwOntSipVagRowStatus
                              hwOntMgPstnCTPRowStatus
                              hwOntSIPCTPRowStatus

			     -Modified the range value of the following leaves, including
			      hwOntSipAgentTemplateIndex
                              hwOntMgVagIfIndex
                              hwOntMgVagOntIndex
                              hwOntMgAttrIfIndex
                              hwOntMgAttrOntIndex
                              hwOntSipVagIfIndex
                              hwOntSipVagOntIndex

			     -Modified the description of the leaf hwOntMgAttrSilence

			     -Deleted the OBJECT of the following traps, including
			      hwOntMassSipUserRegisterAuthAlarmTrap
                              hwOntMassSipUserRegisterAuthRestoreAlarmTrap
                              hwOntMassSipUserRegisterTimeoutAlarmTrap
                              hwOntMassSipUserRegisterTimeoutRestoreAlarmTrap
                              hwOntMassSipUserRegisterFailAlarmTrap
                              hwOntMassSipUserRegisterFailRestoreAlarmTrap
			     "

                REVISION     "201406041040Z"
                DESCRIPTION  "V1.20, Modified the syntax for OMSYS"

                REVISION     "201405121000Z"
                DESCRIPTION  "V1.19, change in this revision:
                              -Added hwOntVoipAlarmCfgTable,
                              -Added hwOntMassSipUserRegisterAuthAlarmTrap
                              -Added hwOntMassSipUserRegisterAuthRestoreAlarmTrap
                              -Added hwOntMassSipUserRegisterTimeoutAlarmTrap
                              -Added hwOntMassSipUserRegisterTimeoutRestoreAlarmTrap
                              -Added hwOntMassSipUserRegisterFailAlarmTrap
                              -Added hwOntMassSipUserRegisterFailRestoreAlarmTrap
                             "

                REVISION     "201403171000Z"
                DESCRIPTION  "V1.18, change in this revision:
                              -Added leaves, including:
                               hwOntSipAgentServerType
                               hwOntSipVagServerType
                              -Modified the description of the following tables, including:
                               hwOntPstnCTPConfigTable
                               hwOntMgVagTable
                               hwOntMgAttrConfigTable
                               hwOntSipVagTable
                               hwOntMgCTPConfigTable
                               hwOntSIPCTPConfigTable
                              "

                REVISION     "201311111600Z"
                DESCRIPTION  "V1.17, change in this revision:
                              -Modified the range of the following leaves, including:
                               hwOntPstnCTPTelNo
                               hwOntPstnCTPUsername
                               hwOntSIPCTPTelno
                               hwOntSIPCTPUsername
                             "

                REVISION     "201306201600Z"
                DESCRIPTION  "V1.16, change in this revision:
                              -Added hwOntRecentCallRecordsTable
                             "

                REVISION     "201306191500Z"
                DESCRIPTION  "V1.15, change in this revision:
                              -Modified the size of the leaf hwOntPstnCTPUsername and hwOntSIPCTPUsername.
                             "

                REVISION     "201301181500Z"
                DESCRIPTION  "V1.14, change in this revision:
                              -Modified the name and description of the following tables, including:
                               hwOntMgVagTable
                               hwOntMgCTPConfigTable

                              -Modified the description of the table hwMgStatusTable.

                              -Added hwOntMgInterfaceFaultAlarmTrap
                              -Added hwOntMgInterfaceRestoreAlarmTrap
                             "

                REVISION     "201210191900Z"
                DESCRIPTION  "V1.13, change in this revision:
                              -Modified the description of the leaf hwOntPotsPTPImpedance and hwOntPotsImpedance.
                             "

                REVISION     "201207201900Z"
                DESCRIPTION  "V1.12, change in this revision:
                              -Modified the description of the leaf hwOntVsqmPacketLossRate.
                             "

                REVISION     "201205081500Z"
                DESCRIPTION  "V1.11, change in this revision:
                             -Modified the range and description of the following leaves, including:
                              hwOntPstnProtocolVariant
                              hwOntMgAttrPstnProtocolVariant

                             -Delete the Default value of the leaves in the following tables, including:
                              hwOntH248VagTable
                              hwOntMgAttrConfigTable
                              hwOntSipVagTable

                             -Modified the description of the following leaves, including:
                              hwOntH248VagPrimaryMgcPort
                              hwOntH248VagSecondaryMgcPort
                              hwOntSipVagProxyPort
                              hwOntSipVagSecondaryProxyPort
                              hwOntSipVagRegisterPort
                              hwOntSipVagSecondaryRegisterPort
                              hwOntSipVagOutboundPort
                              "

                REVISION     "201201161124Z"
                DESCRIPTION  "V1.10, change in this revision:
                              -Created tables, including:
                               hwOntH248VagTable,
                               hwOntMgAttrConfigTable,
                               hwOntSipVagTable,
                               hwOntPotsPTPConfigTable,
                               hwOntH248CTPConfigTable,
                               hwOntSIPCTPConfigTable,
                               hwOntDigitMapBodyTable.

                              -Added hwOntDigitMapRohTime into
                               hwOntDigitMapTemplateTable.

                              -Modified the scope of some leaves, including:
                               hwOntPotsImpedance,
                               hwOntSipAgentProxyUri,
                               hwOntSipAgentRegisterUri,
                               hwOntSipAgentVoicemailUri,
                               hwOntSipAgentConfFactoryUri,
                               hwOntSipAgentBridgedLineAgentUri,
                               hwOntSipAgentUserAuthRealm,
                               hwOntSipAgentRtpPortMin,
                               hwOntSipAgentRtpPortMax,
                               hwOntSipAgentSignalPortId,
                               hwOntJitterBuffTarget,
                               hwOntJitterBuffMax,
                               hwOntPstnCTPTelNo,
                               hwOntPstnCTPHotlineUri,
                               hwOntPstnCTPUsername,
                               hwOntPstnCTPPassword,
                               hwOntPotsCTPTemplateIndex
                               hwOntPotsCTPTemplateName,
                               hwOntPstnCTPDigitmapTemplateIndex,
                               hwOntPstnCTPDigitmapTemplateName,
                               hwOntPstnCTPSipAgentTemplateIndex,
                               hwOntPstnCTPSipAgentTemplateName,
                               hwOntPstnCTPIPIndex.

                              -Changed the name of hwOntPotsSendGian to
                               hwOntPotsSendGain,

                              -Changed the name of hwOntPotsRecvGian to
                               hwOntPotsRecvGain.

                              -Modified the description of some leaves, including:
                               hwOntDigitMapCriticalDialTime,
                               hwOntDigitMapPartialDialTime.
                              "

                REVISION     "201112241547Z"
                DESCRIPTION  "V1.09, change in this revision:
                              Added hwOntSipAgentHomeDomain into
                              hwOntSipAgentTemplateTable.
                             "

                REVISION     "201111251511Z"
                DESCRIPTION  "V1.08, change in this revision:
                              -Added hwOntSipUserRegisterAuthAlarmTrap
                              -Added hwOntSipUserRegisterAuthRestoreAlarmTrap
                              -Added hwOntSipUserRegisterTimeoutAlarmTrap
                              -Added hwOntSipUserRegisterTimeoutRestoreAlarmTrap
                              -Added hwOntSipUserRegisterFailAlarmTrap
                              -Added hwOntSipUserRegisterFailRestoreAlarmTrap
                             "

                REVISION     "201108081511Z"
                DESCRIPTION  "V1.07, change in this revision:
                              -Modified the scope of some leaves,including:
                               hwVoiceOntIndex
                             "

                REVISION     "201012272333Z"
                DESCRIPTION  "V1.06, change in this revision:
                              -Created tables, include: hwOntPotsStatusTable.
                              - Added the definition of the hwOntPstnCallerEmulateOprTable,including:
                              hwOntPstnCallerEmulateTestRequestID
                              - Added the definition of the hwOntPstnCalledEmulateOprTable,including:
                              hwOntPstnCalledEmulateTestRequestID
                              - Created traps, include:
                                hwOntCallerEmulateOperatorTrap
                                hwOntCalledEmulateOperatorTrap
                             "

                REVISION     "201012092209Z"
                DESCRIPTION  "V1.05, change in this revision:
                              -Modified the scope of some leaves,including:
                               hwOntPotsCTPTemplateIndex
                               hwOntPstnCTPDigitmapTemplateIndex
                               hwOntPstnCTPSipAgentTemplateIndex
                               hwOntPstnCTPIPIndex
                             "

                REVISION     "201011172312Z"
                DESCRIPTION  "V1.04, change in this revision:
                              -Modified the description"

                REVISION     "201011090000Z"
                DESCRIPTION  "
                              V1.03, change in this revision:
                              -Modified the description of some tables.
                              -Corrected the SYNTAX.
                             "

    --  Revision history
                REVISION     "201007100000Z"
                DESCRIPTION  "
                              V1.02, change in this revision:
                              -Modified the description of all tables.
                             "

    --  Revision history
                REVISION     "201005100000Z"
                DESCRIPTION  "
                              V1.01, change in this revision:
                              Added HUAWEI-VOIP-ONT-MIB
                             "
                            ::= { huaweiUtility 36 }

    --Type difine

      -- 1.3.6.1.4.1.2011.6.36.11
      hwVoipOntObjects OBJECT IDENTIFIER ::= { hwVoip 11 }
      hwVoipOntTraps OBJECT IDENTIFIER ::= { hwVoip 12 }

    --Pstn Table define
      hwPstnStatusTable OBJECT-TYPE
        SYNTAX      SEQUENCE OF HwPstnStatusEntry
        MAX-ACCESS  not-accessible
        STATUS      current
        DESCRIPTION
          "The PSTN states table ,for Mib display only
           The indexes of this table are hwVoiceIfIndex, hwVoiceOntIndex,hwVoiceOntPortIndex"
        ::= { hwVoipOntObjects 1 }


      hwPstnStatusEntry OBJECT-TYPE
        SYNTAX      HwPstnStatusEntry
        MAX-ACCESS  not-accessible
        STATUS      current
        DESCRIPTION
          "The PSTN states table ,for Mib display only
           The indexes of this entry are hwVoiceIfIndex, hwVoiceOntIndex,hwVoiceOntPortIndex"
        INDEX    {
                  hwVoiceIfIndex,
                  hwVoiceOntIndex,
                  hwVoiceOntPortIndex
                 }
        ::= { hwPstnStatusTable 1 }

    --Pstn Node define
      HwPstnStatusEntry ::=
        SEQUENCE
        {
          hwVoiceIfIndex       Integer32,
          hwVoiceOntIndex      Integer32,
          hwVoiceOntPortIndex  Integer32,
          hwLineStatus         INTEGER,
          hwServiceStatus      INTEGER,
          hwPortCodec          INTEGER
        }

    --Pstn leaf define
      hwVoiceIfIndex OBJECT-TYPE
        SYNTAX      Integer32
        MAX-ACCESS  accessible-for-notify
        STATUS      current
        DESCRIPTION
            "ifIndex"
        ::= { hwPstnStatusEntry 1 }

      hwVoiceOntIndex OBJECT-TYPE
        SYNTAX      Integer32
        MAX-ACCESS  accessible-for-notify
        STATUS      current
        DESCRIPTION
            "ONT Index"
        ::= { hwPstnStatusEntry 2 }

      hwVoiceOntPortIndex OBJECT-TYPE
        SYNTAX      Integer32(1..255)
        MAX-ACCESS  accessible-for-notify
        STATUS      current
        DESCRIPTION
            "Port in ONT"
        ::= { hwPstnStatusEntry 3 }

      hwLineStatus OBJECT-TYPE
        SYNTAX      INTEGER{registering(1),idle(2),picking(3),dialing(4),ringing(5),backringing(6),connecting(7),connected(8),releasing(9),failregister(10),inactive(11),other(-1)}
        MAX-ACCESS  read-only
        STATUS      current
        DESCRIPTION
            "
            hwLineStatus
            Options:
            1. registering(1)      -indicates the port is registering now
            2. idle(2)             -indicates the port is idle
            3. picking(3)          -indicates pick up
            4. dialing(4)          -indicates dialing
            5. ringing(5)          -indicates ringing
            6. backringing(6)      -indicates ringing for back
            7. connecting(7)       -indicates connecting now
            8. connected(8)        -indicates the port is connected
            9. releasing(9)        -indicates connect is releasing
            10. failregister(10)   -indicates the port register failed
            11. inactive(11)       -indicates the port is not active
            12. other(-1)          -indicates other
            "
        ::= { hwPstnStatusEntry 4 }

      hwServiceStatus OBJECT-TYPE
        SYNTAX      INTEGER{endLocal(1),endRemote(2),endAuto(3),normal(4),other(-1)}
        MAX-ACCESS  read-only
        STATUS      current
        DESCRIPTION
            "
            Service Status
            Options:
            1. endLocal(1)  -indicates end service at local,occured by disable users
            2. endRemote(2) -indicates end service at other side,occured by MGC send out commands
            3. endAuto(3)   -indicates auto end service ,occured by failure of MGC
            4. normal(4)    -indicates service is normal
            5. other(-1)   -other
            "
        ::= { hwPstnStatusEntry 5 }

      hwPortCodec OBJECT-TYPE
        SYNTAX      INTEGER{g711a(1),g729(2),g711u(3),g723(4),g726(5),t38(6),other(-1)}
        MAX-ACCESS  read-only
        STATUS      current
        DESCRIPTION
            "
            Ont Pstn Port Codec
            Options:
            1.g711a(1)  -indicates the codec mode is G.711A
            2.g729(2)   -indicates the codec mode is g729
            3.g711u(3)  -indicates the codec mode is G.711U
            4.g723(4)   -indicates the codec mode is g723
            5.g726(5)   -indicates the codec mode is G.726
            6.t38(6)    -indicates the codec mode is T.38
            7.other(-1) -indicates the codec mode is other
            "
        ::= { hwPstnStatusEntry 6 }


    --Mg Table define, which added by zx
      hwMgStatusTable OBJECT-TYPE
        SYNTAX      SEQUENCE OF HwMgStatusEntry
        MAX-ACCESS  not-accessible
        STATUS      current
        DESCRIPTION
          "The Mg states table ,for Mib display only
           The indexes of this table are hwVoiceIfIndex, hwVoiceOntIndex, hwVoiceOntMgId"
        ::= { hwVoipOntObjects 2 }

    --Mg Node define
      hwMgStatusEntry OBJECT-TYPE
        SYNTAX      HwMgStatusEntry
        MAX-ACCESS  not-accessible
        STATUS      current
        DESCRIPTION
          "The Mg states table ,for Mib display only
           The indexes of this entry are hwVoiceIfIndex, hwVoiceOntIndex, hwVoiceOntMgId"
        INDEX    {
                  hwVoiceIfIndex,
                  hwVoiceOntIndex,
                  hwVoiceOntMgId
                 }
        ::= { hwMgStatusTable 1 }

      HwMgStatusEntry ::=
        SEQUENCE
        {
          hwVoiceOntMgId        Integer32,
          hwMgStatus            INTEGER
        }


    --Mg leaf define
      hwVoiceOntMgId OBJECT-TYPE
        SYNTAX      Integer32
        MAX-ACCESS  accessible-for-notify
        STATUS      current
        DESCRIPTION
            "MgId in ONT"
        ::= { hwMgStatusEntry 1 }

      hwMgStatus   OBJECT-TYPE
        SYNTAX      INTEGER{registering(1),registerok(2),malfunction(3),logout(4),rebooting(5), protocolincorrect(255), other(-1)}
        MAX-ACCESS  read-only
        STATUS      current
        DESCRIPTION
            "
            Mg Status.
            Options:
            1.registering(1) -indicates the mg status is registering.
            2.registerok(2)  -indicates the mg status is register sucessfully
            3.malfunction(3) -indicates the mg status is malfunction
            4.logout(4)      -indicates the mg status is log-out
            5.rebooting(5)   -indicates the mg status is rebooting
            6.protocolincorrect(255) -indicates the protocol is incorrect
            7.other(-1)      -other
            "
        ::= { hwMgStatusEntry 2 }




    -- 1.3.6.1.4.1.2011.6.36.11.3
    hwOntPotsTemplateTable OBJECT-TYPE
        SYNTAX SEQUENCE OF HwOntPotsTemplateEntry
        MAX-ACCESS not-accessible
        STATUS current
        DESCRIPTION
            "The Table of POTS profile
             The index of this table is hwOntPotsTemplateIndex"
        ::= { hwVoipOntObjects 3 }

    -- 1.3.6.1.4.1.2011.6.36.11.3.1
    hwOntPotsTemplateEntry OBJECT-TYPE
        SYNTAX HwOntPotsTemplateEntry
        MAX-ACCESS not-accessible
        STATUS current
        DESCRIPTION
            "The Table of POTS profile
             The index of this entry is hwOntPotsTemplateIndex"
        INDEX { hwOntPotsTemplateIndex }
        ::= { hwOntPotsTemplateTable 1 }

    HwOntPotsTemplateEntry ::=
        SEQUENCE {
            hwOntPotsTemplateIndex
                Integer32,
            hwOntPotsTemplateName
                OCTET STRING,
            hwOntPotsImpedance
                Integer32,
            hwOntPotsSendGain
                Integer32,
            hwOntPotsRecvGain
                Integer32,
            hwOntPotsPotsSignaling
                INTEGER,
            hwOntPotsRowStatus
                RowStatus,
            hwOntPotsTemplateBindTimes
                Integer32
         }

    -- 1.3.6.1.4.1.2011.6.36.11.3.1.1
    hwOntPotsTemplateIndex OBJECT-TYPE
        SYNTAX Integer32 (-1|1..64)
        MAX-ACCESS not-accessible
        STATUS current
        DESCRIPTION
            "The Profile ID of POTS profile Table"
        ::= { hwOntPotsTemplateEntry 1 }

    -- 1.3.6.1.4.1.2011.6.36.11.3.1.2
    hwOntPotsTemplateName OBJECT-TYPE
        SYNTAX OCTET STRING (SIZE (1..32))
        MAX-ACCESS read-write
        STATUS current
        DESCRIPTION
            "The Profile Name of POTS profile Table."
        ::= { hwOntPotsTemplateEntry 2 }

    -- 1.3.6.1.4.1.2011.6.36.11.3.1.3
    hwOntPotsImpedance OBJECT-TYPE
        SYNTAX Integer32 (1..76)
        MAX-ACCESS read-write
        STATUS current
        DESCRIPTION
            "Impedance.
            Options:
            1  :600 Ohms
            2  :900 Ohms
            3  :C1=150 nF, R1=750 Ohm, R2=270 Ohm
            4  :C1=115 nF, R1=820 Ohm, R2=220 Ohm
            5  :C1=230 nF, R1=1050 Ohm, R2=320 Ohm
            65 :Bureau machine in China(200+680|| 100nf)
            66 :User Machine in China(200+560|| 100nf)
            67 :Interface of Russian(150+510|| 47nf)
            68 :(220+820|| 120nf )
            69 :Interface of Brazil(800|| 50nf)
            70 :Abandoned
            71 :HK_BT3(Zin=370+620|| 310nf,Zload=600)
            72 :HK_BT5(Zin=270+264|| 357nf+1434|| 265nf,Zload=600)
            73 :BT1(Zin=87+1052||228nF+229||28.4nF, Zload=93+615||471nF+179||495nF+244||32nF)
            74 :BT2(Zin=87+1052||228nF+229||28.4nF, Zload=270+264||357nF+1434||265nF)
            75 :BT3(Zin=87+1052||228nF+229||28.4nF, Zload=164+162||363nF+1227||350nF)
            76 :New Zealand(Zin=370+620|| 310nf)
            Default: 3: C1=150nF,R1=750Ohm,R2=270Ohm
            Impedance value 6~64 is not supported now.
            "
        DEFVAL { 3 }
        ::= { hwOntPotsTemplateEntry 3 }

    -- 1.3.6.1.4.1.2011.6.36.11.3.1.4
    hwOntPotsSendGain OBJECT-TYPE
        SYNTAX Integer32 (1..37)
        MAX-ACCESS read-write
        STATUS current
        DESCRIPTION
            "param  value of sendgain
            Options:
            1  :-12.0 dB
            2  :-11.5 dB
            3  :-11.0 dB
            4  :-10.5 dB
            5  :-10.0 dB
            6  :-9.5 dB
            7  :-9.0 dB
            8  :-8.5 dB
            9  :-8.0 dB
            10 :-7.5 dB
            11 :-7.0 dB
            12 :-6.5 dB
            13 :-6.0 dB
            14 :-5.5 dB
            15 :-5.0 dB
            16 :-4.5 dB
            17 :-4.0 dB
            18 :-3.5 dB
            19 :-3.0 dB
            20 :-2.5 dB
            21 :-2.0 dB
            22 :-1.5 dB
            23 :-1.0 dB
            24 :-0.5 dB
            25 :  0  dB
            26 :+0.5 dB
            27 :+1.0 dB
            28 :+1.5 dB
            29 :+2.0 dB
            30 :+2.5 dB
            31 :+3.0 dB
            32 :+3.5 dB
            33 :+4.0 dB
            34 :+4.5 dB
            35 :+5.0 dB
            36 :+5.5 dB
            37 :+6.0 dB
            Default: 25"
        DEFVAL { 25 }
        ::= { hwOntPotsTemplateEntry 4 }

    -- 1.3.6.1.4.1.2011.6.36.11.3.1.5
    hwOntPotsRecvGain OBJECT-TYPE
        SYNTAX Integer32 (1..37)
        MAX-ACCESS read-write
        STATUS current
        DESCRIPTION
            "param  value of recvgain
            Options:
            1  :-12.0 dB
            2  :-11.5 dB
            3  :-11.0 dB
            4  :-10.5 dB
            5  :-10.0 dB
            6  :-9.5 dB
            7  :-9.0 dB
            8  :-8.5 dB
            9  :-8.0 dB
            10 :-7.5 dB
            11 :-7.0 dB
            12 :-6.5 dB
            13 :-6.0 dB
            14 :-5.5 dB
            15 :-5.0 dB
            16 :-4.5 dB
            17 :-4.0 dB
            18 :-3.5 dB
            19 :-3.0 dB
            20 :-2.5 dB
            21 :-2.0 dB
            22 :-1.5 dB
            23 :-1.0 dB
            24 :-0.5 dB
            25 :  0  dB
            26 :+0.5 dB
            27 :+1.0 dB
            28 :+1.5 dB
            29 :+2.0 dB
            30 :+2.5 dB
            31 :+3.0 dB
            32 :+3.5 dB
            33 :+4.0 dB
            34 :+4.5 dB
            35 :+5.0 dB
            36 :+5.5 dB
            37 :+6.0 dB
            Default: 25"
        DEFVAL { 25 }
        ::= { hwOntPotsTemplateEntry 5 }

    -- 1.3.6.1.4.1.2011.6.36.11.3.1.6
    hwOntPotsPotsSignaling OBJECT-TYPE
        SYNTAX INTEGER
            {
            loopStart(1),
            groundStart(2),
            loopReverseBattery(3),
            coinFirst(4),
            dialToneFirst(5),
            multiParty(6)
            }
        MAX-ACCESS read-write
        STATUS current
        DESCRIPTION
            "pots signaling
            Options:
            1.loopStart(1)             -indicates the pots signaling is loop-start
            2.groundStart(2)           -indicates the pots signaling is ground-start
            3.loopReverseBattery(3)    -indicates the pots signaling is loop-reverse-battery
            4.coinFirst(4)             -indicates the pots signaling is coin-first
            5.dialToneFirst(5)         -indicates the pots signaling is dial-tone-first
            6.multiParty(6)            -indicates the pots signaling is multi-party
            Default:loopStart(1)"
        DEFVAL { loopStart }
        ::= { hwOntPotsTemplateEntry 6 }

    -- 1.3.6.1.4.1.2011.6.36.11.3.1.7
    hwOntPotsRowStatus OBJECT-TYPE
        SYNTAX RowStatus
        MAX-ACCESS read-create
        STATUS current
        DESCRIPTION
            "Options:
            1.active(1)          -indicates active
            2.notInService(2)    -indicates not in service
            3.notReady(3)        -indicates not ready
            4.createAndGo(4)     -indicates create and go
            5.createAndWait(5)   -indicates create and wait
            6.destroy(6)         -indicates destroy
            Only 4 and 6 is support Now."
        ::= { hwOntPotsTemplateEntry 7 }

    -- 1.3.6.1.4.1.2011.6.36.11.3.1.8
    hwOntPotsTemplateBindTimes OBJECT-TYPE
        SYNTAX Integer32
        MAX-ACCESS read-only
        STATUS current
        DESCRIPTION
            "The bind time of this profile"
        ::= { hwOntPotsTemplateEntry 8 }



    -- 1.3.6.1.4.1.2011.6.36.11.4
    hwOntSipAgentTemplateTable OBJECT-TYPE
        SYNTAX SEQUENCE OF HwOntSipAgentTemplateEntry
        MAX-ACCESS not-accessible
        STATUS current
        DESCRIPTION
            "Sipagent profile table.
            The index of this table is hwOntSipAgentTemplateIndex"
        ::= { hwVoipOntObjects 4 }

    -- 1.3.6.1.4.1.2011.6.36.11.4.1
    hwOntSipAgentTemplateEntry OBJECT-TYPE
        SYNTAX HwOntSipAgentTemplateEntry
        MAX-ACCESS not-accessible
        STATUS current
        DESCRIPTION
            "Sipagent profile table.
            The index of this entry is hwOntSipAgentTemplateIndex"
        INDEX { hwOntSipAgentTemplateIndex }
        ::= { hwOntSipAgentTemplateTable 1 }

    HwOntSipAgentTemplateEntry ::=
        SEQUENCE {
            hwOntSipAgentTemplateIndex
                Integer32,
            hwOntSipAgentTemplateName
                OCTET STRING,
            hwOntSipAgentProxyUri
                OCTET STRING,
            hwOntSipAgentRtpPortMin
                Integer32,
            hwOntSipAgentRtpPortMax
                Integer32,
            hwOntSipAgentRtpDscp
                Integer32,
            hwOntSipAgentSignalTransMode
                INTEGER,
            hwOntSipAgentSignalPortId
                Integer32,
            hwOntSipAgentSignalDscp
                Integer32,
            hwOntSipAgentRegisterUri
                OCTET STRING,
            hwOntSipAgentRegExpiration
                Integer32,
            hwOntSipAgentReRegStartTime
                Integer32,
            hwOntSipAgentVoicemailUri
                OCTET STRING,
            hwOntSipAgentVoicemailSubExpir
                Integer32,
            hwOntSipAgentConfFactoryUri
                OCTET STRING,
            hwOntSipAgentBridgedLineAgentUri
                OCTET STRING,
            hwOntSipAgentUserAuthRealm
                OCTET STRING,
            hwOntSipAgentRowStatus
                RowStatus,
            hwOntSipAgentTemplateBindTimes
                Integer32,
            hwOntSipAgentHomeDomain
                OCTET STRING,
            hwOntSipAgentServerType
                INTEGER
         }

    -- 1.3.6.1.4.1.2011.6.36.11.4.1.1
    hwOntSipAgentTemplateIndex OBJECT-TYPE
        SYNTAX Integer32 (-1|1..64)
        MAX-ACCESS not-accessible
        STATUS current
        DESCRIPTION
            "The profile ID of sipagent profile table."
        ::= { hwOntSipAgentTemplateEntry 1 }

    -- 1.3.6.1.4.1.2011.6.36.11.4.1.2
    hwOntSipAgentTemplateName OBJECT-TYPE
        SYNTAX OCTET STRING (SIZE (1..32))
        MAX-ACCESS read-write
        STATUS current
        DESCRIPTION
            "The profile Name of sipagent profile table."
        ::= { hwOntSipAgentTemplateEntry 2 }

    -- 1.3.6.1.4.1.2011.6.36.11.4.1.3
    hwOntSipAgentProxyUri OBJECT-TYPE
        SYNTAX OCTET STRING (SIZE (0..64))
        MAX-ACCESS read-write
        STATUS current
        DESCRIPTION
            "Proxy server uri."
        ::= { hwOntSipAgentTemplateEntry 3 }

    -- 1.3.6.1.4.1.2011.6.36.11.4.1.4
    hwOntSipAgentRtpPortMin OBJECT-TYPE
        SYNTAX Integer32 (0..65535)
        MAX-ACCESS read-write
        STATUS current
        DESCRIPTION
            "The min udp port of RTP.
             Default: 50000
            "
        DEFVAL { 50000 }
        ::= { hwOntSipAgentTemplateEntry 4 }

    -- 1.3.6.1.4.1.2011.6.36.11.4.1.5
    hwOntSipAgentRtpPortMax OBJECT-TYPE
        SYNTAX Integer32 (0..65535)
        MAX-ACCESS read-write
        STATUS current
        DESCRIPTION
            "The max udp port of RTP.
             Default: 60000
            "
        DEFVAL { 60000 }
        ::= { hwOntSipAgentTemplateEntry 5 }

    -- 1.3.6.1.4.1.2011.6.36.11.4.1.6
    hwOntSipAgentRtpDscp OBJECT-TYPE
        SYNTAX Integer32 (0..63)
        MAX-ACCESS read-write
        STATUS current
        DESCRIPTION
            "The DSCP of Rtp.
             Default: 46
            "
        DEFVAL { 46 }
        ::= { hwOntSipAgentTemplateEntry 6 }

    -- 1.3.6.1.4.1.2011.6.36.11.4.1.7
    hwOntSipAgentSignalTransMode OBJECT-TYPE
        SYNTAX INTEGER
            {
            tcp(1),
            udp(2)
            }
        MAX-ACCESS read-write
        STATUS current
        DESCRIPTION
            "Transfer mode of signal.
            Options:
            1.tcp(1)    -indicates the signal transfer mode is tcp
            2.udp(2)    -indicates the signal transfer mode is udp
            Default:udp(2)"
        DEFVAL { udp }
        ::= { hwOntSipAgentTemplateEntry 7 }

    -- 1.3.6.1.4.1.2011.6.36.11.4.1.8
    hwOntSipAgentSignalPortId OBJECT-TYPE
        SYNTAX Integer32 (0..65535)
        MAX-ACCESS read-write
        STATUS current
        DESCRIPTION
            "The udp port of signal."
        ::= { hwOntSipAgentTemplateEntry 8 }

    -- 1.3.6.1.4.1.2011.6.36.11.4.1.9
    hwOntSipAgentSignalDscp OBJECT-TYPE
        SYNTAX Integer32 (0..63)
        MAX-ACCESS read-write
        STATUS current
        DESCRIPTION
            "The DSCP of signal.
             Default: 24
            "
        DEFVAL { 24 }
        ::= { hwOntSipAgentTemplateEntry 9 }

    -- 1.3.6.1.4.1.2011.6.36.11.4.1.10
    hwOntSipAgentRegisterUri OBJECT-TYPE
        SYNTAX OCTET STRING (SIZE (0..64))
        MAX-ACCESS read-write
        STATUS current
        DESCRIPTION
            "The URI of register server."
        ::= { hwOntSipAgentTemplateEntry 10 }

    -- 1.3.6.1.4.1.2011.6.36.11.4.1.11
    hwOntSipAgentRegExpiration OBJECT-TYPE
        SYNTAX Integer32
        MAX-ACCESS read-write
        STATUS current
        DESCRIPTION
            "The valid time of register."
        ::= { hwOntSipAgentTemplateEntry 11 }

    -- 1.3.6.1.4.1.2011.6.36.11.4.1.12
    hwOntSipAgentReRegStartTime OBJECT-TYPE
        SYNTAX Integer32
        MAX-ACCESS read-write
        STATUS current
        DESCRIPTION
            "The time before refresh when reg time will timeout."
        ::= { hwOntSipAgentTemplateEntry 12 }

    -- 1.3.6.1.4.1.2011.6.36.11.4.1.13
    hwOntSipAgentVoicemailUri OBJECT-TYPE
        SYNTAX OCTET STRING (SIZE (0..64))
        MAX-ACCESS read-write
        STATUS current
        DESCRIPTION
            "The URI of voicemail server."
        ::= { hwOntSipAgentTemplateEntry 13 }

    -- 1.3.6.1.4.1.2011.6.36.11.4.1.14
    hwOntSipAgentVoicemailSubExpir OBJECT-TYPE
        SYNTAX Integer32
        MAX-ACCESS read-write
        STATUS current
        DESCRIPTION
            "The voicemail's valid time of reg."
        ::= { hwOntSipAgentTemplateEntry 14 }

    -- 1.3.6.1.4.1.2011.6.36.11.4.1.15
    hwOntSipAgentConfFactoryUri OBJECT-TYPE
        SYNTAX OCTET STRING (SIZE (0..64))
        MAX-ACCESS read-write
        STATUS current
        DESCRIPTION
            "The uri of Confence Factory's server."
        ::= { hwOntSipAgentTemplateEntry 15 }

    -- 1.3.6.1.4.1.2011.6.36.11.4.1.16
    hwOntSipAgentBridgedLineAgentUri OBJECT-TYPE
        SYNTAX OCTET STRING (SIZE (0..64))
        MAX-ACCESS read-write
        STATUS current
        DESCRIPTION
            "The BridgedLine's Server URI."
        ::= { hwOntSipAgentTemplateEntry 16 }

    -- 1.3.6.1.4.1.2011.6.36.11.4.1.17
    hwOntSipAgentUserAuthRealm OBJECT-TYPE
        SYNTAX OCTET STRING (SIZE (0..24))
        MAX-ACCESS read-write
        STATUS current
        DESCRIPTION
            "The user Realm."
        ::= { hwOntSipAgentTemplateEntry 17 }

    -- 1.3.6.1.4.1.2011.6.36.11.4.1.18
    hwOntSipAgentRowStatus OBJECT-TYPE
        SYNTAX RowStatus
        MAX-ACCESS read-create
        STATUS current
        DESCRIPTION
            "Options:
            1.active(1)          -indicates active
            2.notInService(2)    -indicates not in service
            3.notReady(3)        -indicates not ready
            4.createAndGo(4)     -indicates create and go
            5.createAndWait(5)   -indicates create and wait
            6.destroy(6)         -indicates destroy
            Only 4 and 6 is support Now."
        ::= { hwOntSipAgentTemplateEntry 18 }

    -- 1.3.6.1.4.1.2011.6.36.11.4.1.19
    hwOntSipAgentTemplateBindTimes OBJECT-TYPE
        SYNTAX Integer32
        MAX-ACCESS read-only
        STATUS current
        DESCRIPTION
            "The bind time of this profile."
        ::= { hwOntSipAgentTemplateEntry 19 }

    -- 1.3.6.1.4.1.2011.6.36.11.4.1.20
    hwOntSipAgentHomeDomain OBJECT-TYPE
        SYNTAX OCTET STRING (SIZE (0..64))
        MAX-ACCESS read-write
        STATUS current
        DESCRIPTION
            "The Home Domain."
        ::= { hwOntSipAgentTemplateEntry 20 }

    hwOntSipAgentServerType OBJECT-TYPE
        SYNTAX INTEGER
            {
            general(1),
            ims(2)
            }
        MAX-ACCESS read-write
        STATUS current
        DESCRIPTION
            "The server type. It is valid for EPON ONT and invalid for GPON ONT.
            Options:
            1.general(1)     -indicates general SIP server
            2.ims(2)         -indicates IMS
            Default:general(1)
            "
        ::= { hwOntSipAgentTemplateEntry 21 }

    -- 1.3.6.1.4.1.2011.6.36.11.5
    hwOntDigitMapTemplateTable OBJECT-TYPE
        SYNTAX SEQUENCE OF HwOntDigitMapTemplateEntry
        MAX-ACCESS not-accessible
        STATUS current
        DESCRIPTION
            "The DigitMap profile table.
            The index of this table is hwOntDigitMapTemplateIndex"
        ::= { hwVoipOntObjects 5 }

    -- 1.3.6.1.4.1.2011.6.36.11.5.1
    hwOntDigitMapTemplateEntry OBJECT-TYPE
        SYNTAX HwOntDigitMapTemplateEntry
        MAX-ACCESS not-accessible
        STATUS current
        DESCRIPTION
            "The DigitMap profile table.
            The index of this entry is hwOntDigitMapTemplateIndex"
        INDEX { hwOntDigitMapTemplateIndex }
        ::= { hwOntDigitMapTemplateTable 1 }

    HwOntDigitMapTemplateEntry ::=
        SEQUENCE {
            hwOntDigitMapTemplateIndex
                Integer32,
            hwOntDigitMapTemplateName
                OCTET STRING,
            hwOntDigitMapCriticalDialTime
                Integer32,
            hwOntDigitMapPartialDialTime
                Integer32,
            hwOntDigitMapFormat
                INTEGER,
            hwOntDigitMapRowStatus
                RowStatus,
            hwOntDigitMapTemplateBindTimes
                Integer32,
            hwOntDigitMapRohTime
                Integer32
         }

    --  1.3.6.1.4.1.2011.6.36.11.5.1.1
    -- 1.3.6.1.4.1.2011.6.36.11.5.1.1
    hwOntDigitMapTemplateIndex OBJECT-TYPE
        SYNTAX Integer32 (-1|1..64)
        MAX-ACCESS not-accessible
        STATUS current
        DESCRIPTION
            "The profile ID digitmap table."
        ::= { hwOntDigitMapTemplateEntry 1 }

    --  1.3.6.1.4.1.2011.6.36.11.5.1.2
    -- 1.3.6.1.4.1.2011.6.36.11.5.1.2
    hwOntDigitMapTemplateName OBJECT-TYPE
        SYNTAX OCTET STRING (SIZE (1..32))
        MAX-ACCESS read-write
        STATUS current
        DESCRIPTION
            "The profile Name digitmap table."
        ::= { hwOntDigitMapTemplateEntry 2 }

    --  1.3.6.1.4.1.2011.6.36.11.5.1.3
    -- 1.3.6.1.4.1.2011.6.36.11.5.1.3
    hwOntDigitMapCriticalDialTime OBJECT-TYPE
        SYNTAX Integer32 (1..65535)
        MAX-ACCESS read-write
        STATUS current
        DESCRIPTION
            "The Critical Dial Time.
             Default: 4000
             Unit:    ms
            "
        DEFVAL{ 4000 }
        ::= { hwOntDigitMapTemplateEntry 3 }

    --  1.3.6.1.4.1.2011.6.36.11.5.1.4
    -- 1.3.6.1.4.1.2011.6.36.11.5.1.4
    hwOntDigitMapPartialDialTime OBJECT-TYPE
        SYNTAX Integer32 (1..65535)
        MAX-ACCESS read-write
        STATUS current
        DESCRIPTION
            "The Partial Dial Time.
             Default: 16000
             Unit:    ms
            "
        DEFVAL{ 16000 }
        ::= { hwOntDigitMapTemplateEntry 4 }

    --  1.3.6.1.4.1.2011.6.36.11.5.1.5
    -- 1.3.6.1.4.1.2011.6.36.11.5.1.5
    hwOntDigitMapFormat OBJECT-TYPE
        SYNTAX INTEGER
        {
           notDefined(1),
           h248Format(2),
           nscFormat(3),
           vendorSpencificFormat(4)
        }
        MAX-ACCESS read-write
        STATUS current
        DESCRIPTION
            "The Format of Digitmap.
            Options:
            1. notDefined(1)               -indicates the digital format is not defined
            2. h248Format(2)               -indicates the digital format is h248
            3. nscFormat(3)                -indicates the digital format is nsc
            4. vendorSpencificFormat(4)    -indicates the digital format is vendor-spencific
            Default:h248Format(2)"
        DEFVAL { h248Format }
        ::= { hwOntDigitMapTemplateEntry 5 }

    --  1.3.6.1.4.1.2011.6.36.11.5.1.6
    -- 1.3.6.1.4.1.2011.6.36.11.5.1.6
    hwOntDigitMapRowStatus OBJECT-TYPE
        SYNTAX RowStatus
        MAX-ACCESS read-create
        STATUS current
        DESCRIPTION
            "Options:
            1.active(1)          -indicates active
            2.notInService(2)    -indicates not in service
            3.notReady(3)        -indicates not ready
            4.createAndGo(4)     -indicates create and go
            5.createAndWait(5)   -indicates create and wait
            6.destroy(6)         -indicates destroy
            Only 4 and 6 is support Now."
        ::= { hwOntDigitMapTemplateEntry 6 }

    --  1.3.6.1.4.1.2011.6.36.11.5.1.7
    -- 1.3.6.1.4.1.2011.6.36.11.5.1.7
    hwOntDigitMapTemplateBindTimes OBJECT-TYPE
        SYNTAX Integer32
        MAX-ACCESS read-only
        STATUS current
        DESCRIPTION
            "The bind time of this profile."
        ::= { hwOntDigitMapTemplateEntry 7 }

    --  1.3.6.1.4.1.2011.6.36.11.5.1.8
    -- 1.3.6.1.4.1.2011.6.36.11.5.1.8
    hwOntDigitMapRohTime  OBJECT-TYPE
        SYNTAX Integer32 (0..255)
        MAX-ACCESS read-write
        STATUS current
        DESCRIPTION
            "The Roh Time.
             Default: 6
             Unit:    s
            "
        DEFVAL{ 6 }
        ::= { hwOntDigitMapTemplateEntry 8 }


    --  1.3.6.1.4.1.2011.6.36.11.6
    -- 1.3.6.1.4.1.2011.6.36.11.6
    hwOntDigitMapTemplateTokenTable OBJECT-TYPE
        SYNTAX SEQUENCE OF HwOntDigitMapTemplateTokenEntry
        MAX-ACCESS not-accessible
        STATUS current
        DESCRIPTION
            "The digitmap token table.
            The indexes of this table are hwOntDigitMapTemplateIndex, hwOntDigitMapTokenId"
        ::= { hwVoipOntObjects 6 }

    --  1.3.6.1.4.1.2011.6.36.11.6.1
    -- 1.3.6.1.4.1.2011.6.36.11.6.1
    hwOntDigitMapTemplateTokenEntry OBJECT-TYPE
        SYNTAX HwOntDigitMapTemplateTokenEntry
        MAX-ACCESS not-accessible
        STATUS current
        DESCRIPTION
            "The digitmap token table.
             The indexes of this entry are hwOntDigitMapTemplateIndex, hwOntDigitMapTokenId"
        INDEX { hwOntDigitMapTemplateIndex, hwOntDigitMapTokenId }
        ::= { hwOntDigitMapTemplateTokenTable 1 }

    HwOntDigitMapTemplateTokenEntry ::=
        SEQUENCE {
            hwOntDigitMapTokenId
                Integer32,
            hwOntDigitMapToken
                OCTET STRING,
            hwOntDigitMapTokenRowStatus
                INTEGER
         }

    --  1.3.6.1.4.1.2011.6.36.11.6.1.1
    -- 1.3.6.1.4.1.2011.6.36.11.6.1.1
    hwOntDigitMapTokenId OBJECT-TYPE
        SYNTAX Integer32 (1..200)
        MAX-ACCESS not-accessible
        STATUS current
        DESCRIPTION
            "The digitmap token Id."
        ::= { hwOntDigitMapTemplateTokenEntry 1 }

    --  1.3.6.1.4.1.2011.6.36.11.6.1.2
    -- 1.3.6.1.4.1.2011.6.36.11.6.1.2
    hwOntDigitMapToken OBJECT-TYPE
        SYNTAX OCTET STRING (SIZE (1..27))
        MAX-ACCESS read-write
        STATUS current
        DESCRIPTION
            "The digitmap token body."
        ::= { hwOntDigitMapTemplateTokenEntry 2 }

    --  1.3.6.1.4.1.2011.6.36.11.6.1.3
    -- 1.3.6.1.4.1.2011.6.36.11.6.1.3
    hwOntDigitMapTokenRowStatus OBJECT-TYPE
        SYNTAX INTEGER
            {
            active(1),
            notInservice(2),
            notReady(3),
            createAndGo(4),
            createAndWait(5),
            destroy(6)
            }
        MAX-ACCESS read-write
        STATUS current
        DESCRIPTION
            "Options:
            1.active(1)         -indicates active
            2.notInservice(2)   -indicates not in service
            3.notReady(3)       -indicates not ready
            4.createAndGo(4)    -indicates create and go
            5.createAndWait(5)  -indicates create and wait
            6.destroy(6)        -indicates destroy
            Only 4 and 6 is support Now.."

        ::= { hwOntDigitMapTemplateTokenEntry 3 }



    --  1.3.6.1.4.1.2011.6.36.11.7
    -- 1.3.6.1.4.1.2011.6.36.11.7
    hwOntGlbMediaAttributeTable OBJECT IDENTIFIER ::= { hwVoipOntObjects 7 }

    --  1.3.6.1.4.1.2011.6.36.11.7.1
    -- 1.3.6.1.4.1.2011.6.36.11.7.1
    hwOntFaxMode OBJECT-TYPE
        SYNTAX INTEGER
            {
            passthru(1),
            t38(2)
            }
        MAX-ACCESS read-write
        STATUS current
        DESCRIPTION
            "fax mode.
            Options:
            1.passthru(1)   -indicates the fax mode is passthrough
            2.t38(2)        -indicates the fax mode is T38
            defalut: t38"
        ::= { hwOntGlbMediaAttributeTable 1 }

    --  1.3.6.1.4.1.2011.6.36.11.7.2
    -- 1.3.6.1.4.1.2011.6.36.11.7.2
    hwOntOrder1stCodec OBJECT-TYPE
        SYNTAX Integer32 (0..95)
        MAX-ACCESS read-write
        STATUS current
        DESCRIPTION
            "codec of order 1
            defalut: 8"
        ::= { hwOntGlbMediaAttributeTable 2 }

    --  1.3.6.1.4.1.2011.6.36.11.7.3
    -- 1.3.6.1.4.1.2011.6.36.11.7.3
    hwOntOrder1stPacketPeriod OBJECT-TYPE
        SYNTAX INTEGER
            {
            time10ms(1),
            time15ms(2),
            time20ms(3),
            time25ms(4),
            time30ms(5)
            }
        MAX-ACCESS read-write
        STATUS current
        DESCRIPTION
            "packet period of order 1,
            Options:
            1.time10ms(1)  -indicates the packet period is 10ms
            2.time15ms(2)  -indicates the packet period is 15ms
            3.time20ms(3)  -indicates the packet period is 20ms
            4.time25ms(4)  -indicates the packet period is 25ms
            5.time30ms(5)  -indicates the packet period is 30ms
            Defalut: time20ms(3)"
        ::= { hwOntGlbMediaAttributeTable 3 }

    --  1.3.6.1.4.1.2011.6.36.11.7.4
    -- 1.3.6.1.4.1.2011.6.36.11.7.4
    hwOntOrder1stSilenceFlag OBJECT-TYPE
        SYNTAX INTEGER
            {
            off(1),
            on(2)
            }
        MAX-ACCESS read-write
        STATUS current
        DESCRIPTION
            "silence suppression of order 1,
            Options:
            1.off(1)    -indicates the silence suppression is off
            2.on(2)     -indicates the silence suppression is on
            Defalut: off(1)"
        ::= { hwOntGlbMediaAttributeTable 4 }

    --  1.3.6.1.4.1.2011.6.36.11.7.5
    -- 1.3.6.1.4.1.2011.6.36.11.7.5
    hwOntOrder2stCodec OBJECT-TYPE
        SYNTAX Integer32 (0..95)
        MAX-ACCESS read-write
        STATUS current
        DESCRIPTION
            "codec of order 2,
            Default: 0"
        ::= { hwOntGlbMediaAttributeTable 5 }

    --  1.3.6.1.4.1.2011.6.36.11.7.6
    -- 1.3.6.1.4.1.2011.6.36.11.7.6
    hwOntOrder2stPacketPeriod OBJECT-TYPE
        SYNTAX INTEGER
            {
            time10ms(1),
            time15ms(2),
            time20ms(3),
            time25ms(4),
            time30ms(5)
            }
        MAX-ACCESS read-write
        STATUS current
        DESCRIPTION
            "packet period of order 2,
            Options:
            1.time10ms(1)  -indicates the packet period is 10ms
            2.time15ms(2)  -indicates the packet period is 15ms
            3.time20ms(3)  -indicates the packet period is 20ms
            4.time25ms(4)  -indicates the packet period is 25ms
            5.time30ms(5)  -indicates the packet period is 30ms
            Defalut: time20ms(3)"

        ::= { hwOntGlbMediaAttributeTable 6 }

    --  1.3.6.1.4.1.2011.6.36.11.7.7
    -- 1.3.6.1.4.1.2011.6.36.11.7.7
    hwOntOrder2stSilenceFlag OBJECT-TYPE
        SYNTAX INTEGER
            {
            off(1),
            on(2)
            }
        MAX-ACCESS read-write
        STATUS current
        DESCRIPTION
            "silence suppression of order 2,
            Options:
            1.off(1)    -indicates the silence suppression is off
            2.on(2)     -indicates the silence suppression is on
            Defalut: off(1)"

        ::= { hwOntGlbMediaAttributeTable 7 }

    --  1.3.6.1.4.1.2011.6.36.11.7.8
    -- 1.3.6.1.4.1.2011.6.36.11.7.8
    hwOntOrder3stCodec OBJECT-TYPE
        SYNTAX Integer32 (0..95)
        MAX-ACCESS read-write
        STATUS current
        DESCRIPTION
            "codec of order 3,
            defalut: 18"
        ::= { hwOntGlbMediaAttributeTable 8 }

    --  1.3.6.1.4.1.2011.6.36.11.7.9
    -- 1.3.6.1.4.1.2011.6.36.11.7.9
    hwOntOrder3stPacketPeriod OBJECT-TYPE
        SYNTAX INTEGER
            {
            time10ms(1),
            time15ms(2),
            time20ms(3),
            time25ms(4),
            time30ms(5)
            }
        MAX-ACCESS read-write
        STATUS current
        DESCRIPTION
            "packet period of order 3.
            Options:
            1.time10ms(1)  -indicates the packet period is 10ms
            2.time15ms(2)  -indicates the packet period is 15ms
            3.time20ms(3)  -indicates the packet period is 20ms
            4.time25ms(4)  -indicates the packet period is 25ms
            5.time30ms(5)  -indicates the packet period is 30ms
            Defalut: time20ms(3)"

        ::= { hwOntGlbMediaAttributeTable 9 }

    --  1.3.6.1.4.1.2011.6.36.11.7.10
    -- 1.3.6.1.4.1.2011.6.36.11.7.10
    hwOntOrder3stSilenceFlag OBJECT-TYPE
        SYNTAX INTEGER
            {
            off(1),
            on(2)
            }
        MAX-ACCESS read-write
        STATUS current
        DESCRIPTION
            "silence suppression of order 3.
            Options:
            1.off(1)    -indicates the silence suppression is off
            2.on(2)     -indicates the silence suppression is on
            Defalut: off(1)"

        ::= { hwOntGlbMediaAttributeTable 10 }

    --  1.3.6.1.4.1.2011.6.36.11.7.11
    -- 1.3.6.1.4.1.2011.6.36.11.7.11
    hwOntOrder4stCodec OBJECT-TYPE
        SYNTAX Integer32 (0..95)
        MAX-ACCESS read-write
        STATUS current
        DESCRIPTION
            "codec of order 4,
            defalut: 9"
        ::= { hwOntGlbMediaAttributeTable 11 }

    --  1.3.6.1.4.1.2011.6.36.11.7.12
    -- 1.3.6.1.4.1.2011.6.36.11.7.12
    hwOntOrder4stPacketPeriod OBJECT-TYPE
        SYNTAX INTEGER
            {
            time10ms(1),
            time15ms(2),
            time20ms(3),
            time25ms(4),
            time30ms(5)
            }
        MAX-ACCESS read-write
        STATUS current
        DESCRIPTION
            "packet period of order 4,
            Options:
            1.time10ms(1)  -indicates the packet period is 10ms
            2.time15ms(2)  -indicates the packet period is 15ms
            3.time20ms(3)  -indicates the packet period is 20ms
            4.time25ms(4)  -indicates the packet period is 25ms
            5.time30ms(5)  -indicates the packet period is 30ms
            Defalut: time20ms(3)"

        ::= { hwOntGlbMediaAttributeTable 12 }

    --  1.3.6.1.4.1.2011.6.36.11.7.13
    -- 1.3.6.1.4.1.2011.6.36.11.7.13
    hwOntOrder4stSilenceFlag OBJECT-TYPE
        SYNTAX INTEGER
            {
            off(1),
            on(2)
            }
        MAX-ACCESS read-write
        STATUS current
        DESCRIPTION
            "silence suppression of order 4,
            Options:
            1.off(1)    -indicates the silence suppression is off
            2.on(2)     -indicates the silence suppression is on
            Defalut: off(1)"

        ::= { hwOntGlbMediaAttributeTable 13 }

    --  1.3.6.1.4.1.2011.6.36.11.7.14
    -- 1.3.6.1.4.1.2011.6.36.11.7.14
    hwOntOobDtmfFlag OBJECT-TYPE
        SYNTAX INTEGER
            {
            disable(1),
            enable(2)
            }
        MAX-ACCESS read-write
        STATUS current
        DESCRIPTION
            "Oob Dtmf Flag,
            Options:
            1.disable(1)    -indicates the Oob DTMF is disable
            2.enable(2)     -indicates the Oob DTMF is enable
            Defalut: disable(1)"
        ::= { hwOntGlbMediaAttributeTable 14 }

    --  1.3.6.1.4.1.2011.6.36.11.7.15
    -- 1.3.6.1.4.1.2011.6.36.11.7.15
    hwOntAnnouncementType OBJECT-TYPE
        SYNTAX INTEGER
            {
            silence(1),
            reordertone(2),
            fastbusy(3),
            voiceannouncement(4),
            none(5)
            }
        MAX-ACCESS read-write
        STATUS current
        DESCRIPTION
            "Announcement after off hook time out,
            Options:
            1.silence(1)            -indicates play the voice of silence after off hook time out
            2.reordertone(2)        -indicates play the voice of reorder tone after off hook time out
            3.fastbusy(3)           -indicates play the voice of fast busy after off hook time out
            4.voiceannouncement(4)  -indicates play the voice of voiceannouncement after off hook time out
            5.none(5)               -indicates play none after off hook time out
            Default: fastbusy(3)"
        ::= { hwOntGlbMediaAttributeTable 15 }

    --  1.3.6.1.4.1.2011.6.36.11.7.16
    -- 1.3.6.1.4.1.2011.6.36.11.7.16
    hwOntJitterBuffTarget OBJECT-TYPE
        SYNTAX Integer32 (1..65535)
        MAX-ACCESS read-write
        STATUS current
        DESCRIPTION
            "target value of jitter buffer."
        ::= { hwOntGlbMediaAttributeTable 16 }

    --  1.3.6.1.4.1.2011.6.36.11.7.17
    -- 1.3.6.1.4.1.2011.6.36.11.7.17
    hwOntJitterBuffMax OBJECT-TYPE
        SYNTAX Integer32 (1..65535)
        MAX-ACCESS read-write
        STATUS current
        DESCRIPTION
            "max value of jitter buffer."
        ::= { hwOntGlbMediaAttributeTable 17 }

    --  1.3.6.1.4.1.2011.6.36.11.7.18
    -- 1.3.6.1.4.1.2011.6.36.11.7.18
    hwOntEchoFlag OBJECT-TYPE
        SYNTAX INTEGER { off(1), on(2) }
        MAX-ACCESS read-write
        STATUS current
        DESCRIPTION
            "echo flag.
            Options:
            1.off(1)    -indicates the echo flag is off
            2.on(2)     -indicates the echo flag is on
            Defalut: on(2)"
        ::= { hwOntGlbMediaAttributeTable 18 }

    --  1.3.6.1.4.1.2011.6.36.11.7.19
    -- 1.3.6.1.4.1.2011.6.36.11.7.19
    hwOntPstnProtocolVariant OBJECT-TYPE
        SYNTAX Integer32 (0..65535)
        MAX-ACCESS read-write
        STATUS current
        DESCRIPTION
            "country code, means geography location,
             Options:
             Indicate the E.164 country code
             Defalut: 0"
        ::= { hwOntGlbMediaAttributeTable 19 }

    --  1.3.6.1.4.1.2011.6.36.11.7.20
    -- 1.3.6.1.4.1.2011.6.36.11.7.20
    hwOntPiggybackEventFlag OBJECT-TYPE
        SYNTAX INTEGER
            {
            disable(1),
            enable(2)
            }
        MAX-ACCESS read-write
        STATUS current
        DESCRIPTION
            "whether process piggyback events or not,
            Options:
            1.disable(1)    -indicates don's process piggyback events
            2.enable(2)     -indicates process piggyback events
            Defalut: disable(1)"
        ::= { hwOntGlbMediaAttributeTable 20 }

    --  1.3.6.1.4.1.2011.6.36.11.7.21
    -- 1.3.6.1.4.1.2011.6.36.11.7.21
    hwOntToneEventFlag OBJECT-TYPE
        SYNTAX INTEGER
            {
            disable(1),
            enable(2)
            }
        MAX-ACCESS read-write
        STATUS current
        DESCRIPTION
            "whether process Tone events or not,
            Options:
            1.disable(1)    -indicates don's process Tone events
            2.enable(2)     -indicates process Tone events
            Defalut: disable(1)"
        ::= { hwOntGlbMediaAttributeTable 21 }

    --  1.3.6.1.4.1.2011.6.36.11.7.22
    -- 1.3.6.1.4.1.2011.6.36.11.7.22
    hwOntDtmfEventFlag OBJECT-TYPE
        SYNTAX INTEGER
            {
            disable(1),
            enable(2)
            }
        MAX-ACCESS read-write
        STATUS current
        DESCRIPTION
            "whether process Dtmf events or not,
            Options:
            1.disable(1)    -indicates don's process Dtmf events
            2.enable(2)     -indicates process Dtmf events
            Defalut: disable(1)"
        ::= { hwOntGlbMediaAttributeTable 22 }

    --  1.3.6.1.4.1.2011.6.36.11.7.23
    -- 1.3.6.1.4.1.2011.6.36.11.7.23
    hwOntCasEventFlag OBJECT-TYPE
        SYNTAX INTEGER
            {
            disable(1),
            enable(2)
            }
        MAX-ACCESS read-write
        STATUS current
        DESCRIPTION
            "whether process cas events or not,
            Options:
            1.disable(1)    -indicates don's process cas events
            2.enable(2)     -indicates process cas events
            Defalut: disable(1)"
        ::= { hwOntGlbMediaAttributeTable 23 }



    --  1.3.6.1.4.1.2011.6.36.11.8
    -- 1.3.6.1.4.1.2011.6.36.11.8
    hwOntPstnCTPConfigTable OBJECT-TYPE
        SYNTAX SEQUENCE OF HwOntPstnCTPConfigEntry
        MAX-ACCESS not-accessible
        STATUS current
        DESCRIPTION
            "Pstn CTP Config Table.
            The indexes of this table are hwVoiceIfIndex, hwVoiceOntIndex, hwVoiceOntPortIndex."
        ::= { hwVoipOntObjects 8 }

    --  1.3.6.1.4.1.2011.6.36.11.8.1
    -- 1.3.6.1.4.1.2011.6.36.11.8.1
    hwOntPstnCTPConfigEntry OBJECT-TYPE
        SYNTAX HwOntPstnCTPConfigEntry
        MAX-ACCESS not-accessible
        STATUS current
        DESCRIPTION
            "Pstn CTP Config Table.
            The indexes of this entry are hwVoiceIfIndex, hwVoiceOntIndex, hwVoiceOntPortIndex."
        INDEX { hwVoiceIfIndex, hwVoiceOntIndex, hwVoiceOntPortIndex }
        ::= { hwOntPstnCTPConfigTable 1 }

    HwOntPstnCTPConfigEntry ::=
        SEQUENCE {
            hwOntPstnCTPTelNo
                OCTET STRING,
            hwOntPstnCTPNewServiceRight
                BITS,
            hwOntPstnCTPHotlineUri
                OCTET STRING,
            hwOntPstnCTPUsername
                OCTET STRING,
            hwOntPstnCTPPassword
                OCTET STRING,
            hwOntPotsCTPTemplateIndex
                Integer32,
            hwOntPotsCTPTemplateName
                OCTET STRING,
            hwOntPstnCTPDigitmapTemplateIndex
                Integer32,
            hwOntPstnCTPDigitmapTemplateName
                OCTET STRING,
            hwOntPstnCTPSipAgentTemplateIndex
                Integer32,
            hwOntPstnCTPSipAgentTemplateName
                OCTET STRING,
            hwOntPstnCTPIPIndex
                Integer32,
            hwOntPotsAdministrativeState
                INTEGER,
            hwOntPotsCTPRowStatus
                RowStatus
         }

    --  1.3.6.1.4.1.2011.6.36.11.8.1.1
    -- 1.3.6.1.4.1.2011.6.36.11.8.1.1
    hwOntPstnCTPTelNo OBJECT-TYPE
        SYNTAX OCTET STRING (SIZE (0..64))
        MAX-ACCESS read-write
        STATUS current
        DESCRIPTION
            "POTS user's telephone number of ONT"
        ::= { hwOntPstnCTPConfigEntry 1 }

    --  1.3.6.1.4.1.2011.6.36.11.8.1.2
    -- 1.3.6.1.4.1.2011.6.36.11.8.1.2
    hwOntPstnCTPNewServiceRight OBJECT-TYPE
        SYNTAX BITS
            {
            callWaiting(0),
            threeParty(1),
            callTransfer(2),
            callHold(3),
            callPark(4),
            doNotDisturb(5),
            conference(6),
            messageWaitingIndication(7),
            hotline(8),
            hotdelay(9)
            }
        MAX-ACCESS read-write
        STATUS current
        DESCRIPTION
            "POTS user's service right of ONT. It is valid for GPON ONT and invalid for EPON ONT.
            Options:
            0.callWaiting(0),
            1.threeParty(1),
            2.callTransfer(2),
            3.callHold(3),
            4.callPark(4),
            5.doNotDisturb(5),
            6.conference(6),
            7.messageWaitingIndication(7),
            8.hotline(8),
            9.hotdelay(9)
            Default: d000"

        ::= { hwOntPstnCTPConfigEntry 2 }

    --  1.3.6.1.4.1.2011.6.36.11.8.1.3
    -- 1.3.6.1.4.1.2011.6.36.11.8.1.3
    hwOntPstnCTPHotlineUri OBJECT-TYPE
        SYNTAX OCTET STRING (SIZE (0..32))
        MAX-ACCESS read-write
        STATUS current
        DESCRIPTION
            "user's hot line number(URI). It is valid for GPON ONT and invalid for EPON ONT."
        ::= { hwOntPstnCTPConfigEntry 3 }

    --  1.3.6.1.4.1.2011.6.36.11.8.1.4
    -- 1.3.6.1.4.1.2011.6.36.11.8.1.4
    hwOntPstnCTPUsername OBJECT-TYPE
        SYNTAX OCTET STRING (SIZE (0..50))
        MAX-ACCESS read-write
        STATUS current
        DESCRIPTION
            "user's name."
        ::= { hwOntPstnCTPConfigEntry 4 }

    --  1.3.6.1.4.1.2011.6.36.11.8.1.5
    -- 1.3.6.1.4.1.2011.6.36.11.8.1.5
    hwOntPstnCTPPassword OBJECT-TYPE
        SYNTAX OCTET STRING (SIZE (0..24))
        MAX-ACCESS read-write
        STATUS current
        DESCRIPTION
            "user's password."
        ::= { hwOntPstnCTPConfigEntry 5 }

    --  1.3.6.1.4.1.2011.6.36.11.8.1.6
    -- 1.3.6.1.4.1.2011.6.36.11.8.1.6
    hwOntPotsCTPTemplateIndex OBJECT-TYPE
        SYNTAX Integer32 (-1|1..64)
        MAX-ACCESS read-write
        STATUS current
        DESCRIPTION
            "POTS profile index which is bound to POTS user. It is valid for GPON ONT and invalid for EPON ONT."
        ::= { hwOntPstnCTPConfigEntry 6 }

    --  1.3.6.1.4.1.2011.6.36.11.8.1.7
    -- 1.3.6.1.4.1.2011.6.36.11.8.1.7
    hwOntPotsCTPTemplateName OBJECT-TYPE
        SYNTAX OCTET STRING (SIZE (0..32))
        MAX-ACCESS read-write
        STATUS current
        DESCRIPTION
            "POTS profile name which is bound to POTS user. It is valid for GPON ONT and invalid for EPON ONT."
        ::= { hwOntPstnCTPConfigEntry 7 }

    --  1.3.6.1.4.1.2011.6.36.11.8.1.8
    -- 1.3.6.1.4.1.2011.6.36.11.8.1.8
    hwOntPstnCTPDigitmapTemplateIndex OBJECT-TYPE
        SYNTAX Integer32 (-1|1..64)
        MAX-ACCESS read-write
        STATUS current
        DESCRIPTION
            "DigitalMap profile index which is bound to POTS user.
            If only set digitmap profile(only setting hwOntPstnCTPDigitmapTemplateIndex and hwOntPstnCTPDigitmapTemplateName) for EPON ONT,
            hwVoiceOntPortIndex is invalid(means that all users of the EPON ONT will be bound to the specify digitmap profile)."
        ::= { hwOntPstnCTPConfigEntry 8 }

    --  1.3.6.1.4.1.2011.6.36.11.8.1.9
    -- 1.3.6.1.4.1.2011.6.36.11.8.1.9
    hwOntPstnCTPDigitmapTemplateName OBJECT-TYPE
        SYNTAX OCTET STRING (SIZE (0..32))
        MAX-ACCESS read-write
        STATUS current
        DESCRIPTION
            "DigitalMap profile name which is bound to POTS user.
            If only set digitmap profile(only setting hwOntPstnCTPDigitmapTemplateIndex and hwOntPstnCTPDigitmapTemplateName) for EPON ONT,
            hwVoiceOntPortIndex is invalid(means that all users of the EPON ONT will be bound to the specify digitmap profile)."
        ::= { hwOntPstnCTPConfigEntry 9 }

    --  1.3.6.1.4.1.2011.6.36.11.8.1.10
    -- 1.3.6.1.4.1.2011.6.36.11.8.1.10
    hwOntPstnCTPSipAgentTemplateIndex OBJECT-TYPE
        SYNTAX Integer32 (-1|1..64)
        MAX-ACCESS read-write
        STATUS current
        DESCRIPTION
            "SipAgent profile index which is bound to POTS user."
        ::= { hwOntPstnCTPConfigEntry 10 }

    --  1.3.6.1.4.1.2011.6.36.11.8.1.11
    -- 1.3.6.1.4.1.2011.6.36.11.8.1.11
    hwOntPstnCTPSipAgentTemplateName OBJECT-TYPE
        SYNTAX OCTET STRING (SIZE (0..32))
        MAX-ACCESS read-write
        STATUS current
        DESCRIPTION
            "SipAgent profile name which is bound to POTS user."
        ::= { hwOntPstnCTPConfigEntry 11 }

    --  1.3.6.1.4.1.2011.6.36.11.8.1.12
    -- 1.3.6.1.4.1.2011.6.36.11.8.1.12
    hwOntPstnCTPIPIndex OBJECT-TYPE
        SYNTAX Integer32 (-1|0..3)
        MAX-ACCESS read-write
        STATUS current
        DESCRIPTION
            "IP address index which is bound to POTS user."
        ::= { hwOntPstnCTPConfigEntry 12 }

    --  1.3.6.1.4.1.2011.6.36.11.8.1.13
    -- 1.3.6.1.4.1.2011.6.36.11.8.1.13
    hwOntPotsAdministrativeState OBJECT-TYPE
        SYNTAX INTEGER
            {
            unlock(1),
            lock(2)
            }
        MAX-ACCESS read-write
        STATUS current
        DESCRIPTION
            "Pots' administrative state.
            Options:
            1.unlock(1) -indicates the pots is unlocked
            2.lock(2)   -indicates the pots is locked
            Default: unlock(1)
            "
        DEFVAL { unlock }
        ::= { hwOntPstnCTPConfigEntry 13 }

    --  1.3.6.1.4.1.2011.6.36.11.8.1.14
    -- 1.3.6.1.4.1.2011.6.36.11.8.1.14
    hwOntPotsCTPRowStatus OBJECT-TYPE
        SYNTAX RowStatus
        MAX-ACCESS read-create
        STATUS current
        DESCRIPTION
            "row status.
            Options:
            1.active(1)          -indicates active
            2.notInService(2)    -indicates not in service
            3.notReady(3)        -indicates not ready
            4.createAndGo(4)     -indicates create and go
            5.createAndWait(5)   -indicates create and wait
            6.destroy(6)         -indicates destroy
            Only 4 and 6 is support Now."
        ::= { hwOntPstnCTPConfigEntry 14 }




    --  1.3.6.1.4.1.2011.6.36.11.9
    -- 1.3.6.1.4.1.2011.6.36.11.9
    hwSIPAgentPerformanceMonitorTable OBJECT-TYPE
        SYNTAX SEQUENCE OF HwSIPAgentPerformanceMonitorEntry
        MAX-ACCESS not-accessible
        STATUS current
        DESCRIPTION
            "SIPAgent Performance Monitor Table.
            The indexes of this table are hwVoiceIfIndex, hwVoiceOntIndex, hwVoiceOntPortIndex."
        ::= { hwVoipOntObjects 9 }

    --  1.3.6.1.4.1.2011.6.36.11.9.1
    -- 1.3.6.1.4.1.2011.6.36.11.9.1
    hwSIPAgentPerformanceMonitorEntry OBJECT-TYPE
        SYNTAX HwSIPAgentPerformanceMonitorEntry
        MAX-ACCESS not-accessible
        STATUS current
        DESCRIPTION
            "SIPAgent Performance Monitor Table.
            The indexes of this entry are hwVoiceIfIndex, hwVoiceOntIndex, hwVoiceOntPortIndex."
        INDEX { hwVoiceIfIndex, hwVoiceOntIndex, hwVoiceOntPortIndex }
        ::= { hwSIPAgentPerformanceMonitorTable 1 }

    HwSIPAgentPerformanceMonitorEntry ::=
        SEQUENCE {
            hwSIPAgentTransactions
                Integer32,
            hwSIPAgentRxInviteReqs
                Integer32,
            hwSIPAgentRxInviteRetrans
                Integer32,
            hwSIPAgentRxNoninviteReqs
                Integer32,
            hwSIPAgentRxNoninviteRetrans
                Integer32,
            hwSIPAgentRxResponse
                Integer32,
            hwSIPAgentRxResponseRetransmissions
                Integer32,
            hwSIPAgentTxInviteReqs
                Integer32,
            hwSIPAgentTxInviteRetrans
                Integer32,
            hwSIPAgentTxNoninviteReqs
                Integer32,
            hwSIPAgentTxNoninviteRetrans
                Integer32,
            hwSIPAgentTxResponse
                Integer32,
            hwSIPAgentTxResponseRetransmissions
                Integer32
         }

    --  1.3.6.1.4.1.2011.6.36.11.9.1.1
    -- 1.3.6.1.4.1.2011.6.36.11.9.1.1
    hwSIPAgentTransactions OBJECT-TYPE
        SYNTAX Integer32
        MAX-ACCESS read-only
        STATUS current
        DESCRIPTION
            "This attribute counts the number of new transactions that were initiated."
        ::= { hwSIPAgentPerformanceMonitorEntry 1 }

    --  1.3.6.1.4.1.2011.6.36.11.9.1.2
    -- 1.3.6.1.4.1.2011.6.36.11.9.1.2
    hwSIPAgentRxInviteReqs OBJECT-TYPE
        SYNTAX Integer32
        MAX-ACCESS read-only
        STATUS current
        DESCRIPTION
            " This attribute counts received invite messages, including retransmissions."
        ::= { hwSIPAgentPerformanceMonitorEntry 2 }

    --  1.3.6.1.4.1.2011.6.36.11.9.1.3
    -- 1.3.6.1.4.1.2011.6.36.11.9.1.3
    hwSIPAgentRxInviteRetrans OBJECT-TYPE
        SYNTAX Integer32
        MAX-ACCESS read-only
        STATUS current
        DESCRIPTION
            "This attribute counts received invite retransmission messages."
        ::= { hwSIPAgentPerformanceMonitorEntry 3 }

    --  1.3.6.1.4.1.2011.6.36.11.9.1.4
    -- 1.3.6.1.4.1.2011.6.36.11.9.1.4
    hwSIPAgentRxNoninviteReqs OBJECT-TYPE
        SYNTAX Integer32
        MAX-ACCESS read-only
        STATUS current
        DESCRIPTION
            " This attribute counts received non-invite messages, including retransmissions."
        ::= { hwSIPAgentPerformanceMonitorEntry 4 }

    --  1.3.6.1.4.1.2011.6.36.11.9.1.5
    -- 1.3.6.1.4.1.2011.6.36.11.9.1.5
    hwSIPAgentRxNoninviteRetrans OBJECT-TYPE
        SYNTAX Integer32
        MAX-ACCESS read-only
        STATUS current
        DESCRIPTION
            "This attribute counts received non-invite retransmission messages."
        ::= { hwSIPAgentPerformanceMonitorEntry 5 }

    --  1.3.6.1.4.1.2011.6.36.11.9.1.6
    -- 1.3.6.1.4.1.2011.6.36.11.9.1.6
    hwSIPAgentRxResponse OBJECT-TYPE
        SYNTAX Integer32
        MAX-ACCESS read-only
        STATUS current
        DESCRIPTION
            "This attribute counts total responses received."
        ::= { hwSIPAgentPerformanceMonitorEntry 6 }

    --  1.3.6.1.4.1.2011.6.36.11.9.1.7
    -- 1.3.6.1.4.1.2011.6.36.11.9.1.7
    hwSIPAgentRxResponseRetransmissions OBJECT-TYPE
        SYNTAX Integer32
        MAX-ACCESS read-only
        STATUS current
        DESCRIPTION
            " This attribute counts total response retransmissions received."
        ::= { hwSIPAgentPerformanceMonitorEntry 7 }

    --  1.3.6.1.4.1.2011.6.36.11.9.1.8
    -- 1.3.6.1.4.1.2011.6.36.11.9.1.8
    hwSIPAgentTxInviteReqs OBJECT-TYPE
        SYNTAX Integer32
        MAX-ACCESS read-only
        STATUS current
        DESCRIPTION
            "This attribute counts transmitted invite messages, including retransmissions."
        ::= { hwSIPAgentPerformanceMonitorEntry 8 }

    --  1.3.6.1.4.1.2011.6.36.11.9.1.9
    -- 1.3.6.1.4.1.2011.6.36.11.9.1.9
    hwSIPAgentTxInviteRetrans OBJECT-TYPE
        SYNTAX Integer32
        MAX-ACCESS read-only
        STATUS current
        DESCRIPTION
            "This attribute counts transmitted invite retransmission messages."
        ::= { hwSIPAgentPerformanceMonitorEntry 9 }

    --  1.3.6.1.4.1.2011.6.36.11.9.1.10
    -- 1.3.6.1.4.1.2011.6.36.11.9.1.10
    hwSIPAgentTxNoninviteReqs OBJECT-TYPE
        SYNTAX Integer32
        MAX-ACCESS read-only
        STATUS current
        DESCRIPTION
            "This attribute counts transmitted non-invite messages, including retransmissions."
        ::= { hwSIPAgentPerformanceMonitorEntry 10 }

    --  1.3.6.1.4.1.2011.6.36.11.9.1.11
    -- 1.3.6.1.4.1.2011.6.36.11.9.1.11
    hwSIPAgentTxNoninviteRetrans OBJECT-TYPE
        SYNTAX Integer32
        MAX-ACCESS read-only
        STATUS current
        DESCRIPTION
            " This attribute counts transmitted non-invite retransmission messages."
        ::= { hwSIPAgentPerformanceMonitorEntry 11 }

    --  1.3.6.1.4.1.2011.6.36.11.9.1.12
    -- 1.3.6.1.4.1.2011.6.36.11.9.1.12
    hwSIPAgentTxResponse OBJECT-TYPE
        SYNTAX Integer32
        MAX-ACCESS read-only
        STATUS current
        DESCRIPTION
            "This attribute counts the total responses sent."
        ::= { hwSIPAgentPerformanceMonitorEntry 12 }

    --  1.3.6.1.4.1.2011.6.36.11.9.1.13
    -- 1.3.6.1.4.1.2011.6.36.11.9.1.13
    hwSIPAgentTxResponseRetransmissions OBJECT-TYPE
        SYNTAX Integer32
        MAX-ACCESS read-only
        STATUS current
        DESCRIPTION
            " This attribute counts total response retransmissions sent."
        ::= { hwSIPAgentPerformanceMonitorEntry 13 }



    --  1.3.6.1.4.1.2011.6.36.11.10
    -- 1.3.6.1.4.1.2011.6.36.11.10
    hwSIPCallPerformanceMonitorTable OBJECT-TYPE
        SYNTAX SEQUENCE OF HwSIPCallPerformanceMonitorEntry
        MAX-ACCESS not-accessible
        STATUS current
        DESCRIPTION
            "SIP Call Performance Monitor Table.
            The indexes of this table are hwVoiceIfIndex, hwVoiceOntIndex, hwVoiceOntPortIndex."
        ::= { hwVoipOntObjects 10 }

    --  1.3.6.1.4.1.2011.6.36.11.10.1
    -- 1.3.6.1.4.1.2011.6.36.11.10.1
    hwSIPCallPerformanceMonitorEntry OBJECT-TYPE
        SYNTAX HwSIPCallPerformanceMonitorEntry
        MAX-ACCESS not-accessible
        STATUS current
        DESCRIPTION
            "SIP Call Performance Monitor Table.
            The indexes of this entry are hwVoiceIfIndex, hwVoiceOntIndex, hwVoiceOntPortIndex."
        INDEX { hwVoiceIfIndex, hwVoiceOntIndex, hwVoiceOntPortIndex }
        ::= { hwSIPCallPerformanceMonitorTable 1 }

    HwSIPCallPerformanceMonitorEntry ::=
        SEQUENCE {
            hwSIPCallFailedToConnectCounter
                Integer32,
            hwSIPCallFailedToValidateCounter
                Integer32,
            hwSIPCallTimeoutCounter
                Integer32,
            hwSIPCallFailedReceivedCounter
                Integer32,
            hwSIPCallFailedToAuthenticateCounter
                Integer32
         }

    --  1.3.6.1.4.1.2011.6.36.11.10.1.1
    -- 1.3.6.1.4.1.2011.6.36.11.10.1.1
    hwSIPCallFailedToConnectCounter OBJECT-TYPE
        SYNTAX Integer32
        MAX-ACCESS read-only
        STATUS current
        DESCRIPTION
            "This attribute counts the number of times
            the SIP UA failed to reach/connect its TCP/UDP peer
            during SIP call initiations."
        ::= { hwSIPCallPerformanceMonitorEntry 1 }

    --  1.3.6.1.4.1.2011.6.36.11.10.1.2
    -- 1.3.6.1.4.1.2011.6.36.11.10.1.2
    hwSIPCallFailedToValidateCounter OBJECT-TYPE
        SYNTAX Integer32
        MAX-ACCESS read-only
        STATUS current
        DESCRIPTION
            " This attribute counts the number of times the SIP UA
            failed to validate its peer during SIP call initiations."
        ::= { hwSIPCallPerformanceMonitorEntry 2 }

    --  1.3.6.1.4.1.2011.6.36.11.10.1.3
    -- 1.3.6.1.4.1.2011.6.36.11.10.1.3
    hwSIPCallTimeoutCounter OBJECT-TYPE
        SYNTAX Integer32
        MAX-ACCESS read-only
        STATUS current
        DESCRIPTION
            "This attribute counts the number of times the SIP UA
            timed out during SIP call initiations."
        ::= { hwSIPCallPerformanceMonitorEntry 3 }

    --  1.3.6.1.4.1.2011.6.36.11.10.1.4
    -- 1.3.6.1.4.1.2011.6.36.11.10.1.4
    hwSIPCallFailedReceivedCounter OBJECT-TYPE
        SYNTAX Integer32
        MAX-ACCESS read-only
        STATUS current
        DESCRIPTION
            "This attribute counts the number of times the SIP UA
            received a failure error code during SIP call initiations."
        ::= { hwSIPCallPerformanceMonitorEntry 4 }

    --  1.3.6.1.4.1.2011.6.36.11.10.1.5
    -- 1.3.6.1.4.1.2011.6.36.11.10.1.5
    hwSIPCallFailedToAuthenticateCounter OBJECT-TYPE
        SYNTAX Integer32
        MAX-ACCESS read-only
        STATUS current
        DESCRIPTION
            " This attribute counts the number of times the SIP UA
            failed to authenticate itself during SIP call initiations."
        ::= { hwSIPCallPerformanceMonitorEntry 5 }




    --  1.3.6.1.4.1.2011.6.36.11.11
    -- 1.3.6.1.4.1.2011.6.36.11.11
    hwOntPstnCallerEmulateOprTable OBJECT-TYPE
        SYNTAX SEQUENCE OF HwOntPstnCallerEmulateOprEntry
        MAX-ACCESS not-accessible
        STATUS current
        DESCRIPTION
            "ont caller emulate test table.
            The indexes of this table are hwVoiceIfIndex, hwVoiceOntIndex, hwVoiceOntPortIndex."
            ::= { hwVoipOntObjects 11 }

    --  1.3.6.1.4.1.2011.6.36.11.11.1
    -- 1.3.6.1.4.1.2011.6.36.11.11.1
    hwOntPstnCallerEmulateOprEntry OBJECT-TYPE
        SYNTAX HwOntPstnCallerEmulateOprEntry
        MAX-ACCESS not-accessible
        STATUS current
        DESCRIPTION
            "ont caller emulate test table.
            The indexes of this entry are hwVoiceIfIndex, hwVoiceOntIndex, hwVoiceOntPortIndex."
        INDEX { hwVoiceIfIndex, hwVoiceOntIndex, hwVoiceOntPortIndex }
        ::= { hwOntPstnCallerEmulateOprTable 1 }

    HwOntPstnCallerEmulateOprEntry ::=
        SEQUENCE {
            hwOntPstnCallerEmulateOprType
                INTEGER,
            hwOntPstnCallerEmulateCalledTelNo
                OCTET STRING,
            hwOntPstnCallerEmulateTestStatus
                INTEGER,
            hwOntPstnCallerEmulateTestResult
                INTEGER,
            hwOntPstnCallerEmulateTestHoldTime
                Integer32,
            hwOntPstnCallerEmulateReportTelNo
                OCTET STRING,
            hwOntPstnCallerEmulateErrorCode
                Integer32,
            hwOntPstnCallerEmulateTestRequestID
                Integer32
         }

    --  1.3.6.1.4.1.2011.6.36.11.11.1.1
    -- 1.3.6.1.4.1.2011.6.36.11.11.1.1
    hwOntPstnCallerEmulateOprType OBJECT-TYPE
        SYNTAX INTEGER
            {
            stop(1),
            start(2)
            }
        MAX-ACCESS read-write
        STATUS current
        DESCRIPTION
            "Operation type
            Options:
            1.stop(1) -indicates that stop test;
            2.start(2) -indicates that start test"
        ::= { hwOntPstnCallerEmulateOprEntry 1 }

    --  1.3.6.1.4.1.2011.6.36.11.11.1.2
    -- 1.3.6.1.4.1.2011.6.36.11.11.1.2
    hwOntPstnCallerEmulateCalledTelNo OBJECT-TYPE
        SYNTAX OCTET STRING (SIZE (1..32))
        MAX-ACCESS read-write
        STATUS current
        DESCRIPTION
            "Called telephone number"
        ::= { hwOntPstnCallerEmulateOprEntry 2 }

    --  1.3.6.1.4.1.2011.6.36.11.11.1.3
    -- 1.3.6.1.4.1.2011.6.36.11.11.1.3
    hwOntPstnCallerEmulateTestStatus OBJECT-TYPE
        SYNTAX INTEGER{startSuccessfully(1),stopSuccessfully(2), sendDTMFSuccessfully(3), testOuttime(4), noDialtone(5),
                        callerDialNumberAlready(6), noRinging(7), noRingbackTone(8), waitingAgentMessageOuttime(9),
                        testingFailure(10), agentMessageAck(11),calledoffhook(12),testingAbnormal(13),broadbandtesting(14),
                        capturefail(15),notratb(16),configsuccessfully(17), ring(18), calleroffhook(19), playdialtone(20),
                        dialnumbercomplete(21),idle(22),receiving(23), ringingBack(24), connect(25), busyTone(26),
                        onHook(27), testEnd(28), other(255)}
        MAX-ACCESS read-only
        STATUS current
        DESCRIPTION
            "Test Status.
              Options:
              1. startSuccessfully(1)           -indicates start test successfully
              2. stopSuccessfully(2)            -indicates stop test successfully
              3. sendDTMFSuccessfully(3)        -indicates send DTMF successfully
              4. testOuttime(4)                 -indicates test is time out
              5. noDialtone(5)                  -indicates no dial tone
              6. callerDialNumberAlready(6)     -indicates that caller already dials a number
              7. noRinging(7)                   -indicates on ringing
              8. noRingbackTone(8)              -indicates no ring back tone
              9. waitingAgentMessageOuttime(9)  -indicates that timed-out (waiting for EMS processing)
              10. testingFailure(10)            -indicates that test failure
              11. agentMessageAck(11)           -indicates that host responds to the EMS
              12. calledoffhook(12)             -indicates that off hook (called party)
              13. testingAbnormal(13)           -indicates test is abnormal
              14. broadbandtesting(14)          -indicates capture fail
              15. capturefail(15)               -indicates that line capture failure
              16. notratb(16)                   -indicates that relay transfer board does not exist
              17. configsuccessfully(17)        -indicates configure successfully
              18. ring(18)                      -indicates ringing
              19. calleroffhook(19)             -indicates that off hook (calling party)
              20. playdialtone(20)              -indicates that play the dial tone
              21. dialnumbercomplete(21)        -indicates that dialup is finished
              22. idle(22)                      -indicates idle
              23. receiving(23)                 -indicates receiving
              24. ringingBack(24)              -indicates ringing back
              25. connect(25)                   -indicates that off hook (called party)
              26. busyTone(26)                  -indicates busy tone
              27. onHook(27)                    -indicates on hook
              28. testEnd(28)                   -indicates that test is end
              29. other(255)                    -other
             "
        ::= { hwOntPstnCallerEmulateOprEntry 3 }

    --  1.3.6.1.4.1.2011.6.36.11.11.1.4
    -- 1.3.6.1.4.1.2011.6.36.11.11.1.4
    hwOntPstnCallerEmulateTestResult OBJECT-TYPE
        SYNTAX INTEGER{callerNoDialogTone(1), callerOffHookingBusy(2), callerDialogingBusy(3), callerNoDialog(4),
                        callerDialogedBusy(5), callerDialogedNoTalk(6), callRelease(7), matchNoCompleted(8),
                        sendNoCompleted(9), testSucceed(10), callerMatchFailed(11),notReceiveSSOffhookSignal(12),
                        dialNumberNotCompared(13), backToneNotReceived(14), chanelCreateFailed(15),
                        ssNoResponseHookSignal(16), other(255)}
        MAX-ACCESS read-only
        STATUS current
        DESCRIPTION
            "Test Result.
             Options:
             1. callerNoDialogTone(1)           -indicates that the caller has no dialog tone
             2. callerOffHookingBusy(2)         -indicates that the caller is offhooking busy
             3. callerDialogingBusy(3)          -indicates that the caller is dialog busy
             4. callerNoDialog(4)               -indicates that the caller has no dialog
             5. callerDialogedBusy(5)           -indicates that the caller is dialoged busy
             6. callerDialogedNoTalk(6)         -indicates that the caller is dialoged not talk
             7. callRelease(7)                  -indicates the call is released
             8. matchNoCompleted(8)             -indicates the match is not completed
             9. sendNoCompleted(9)              -indicates the send is not completed
             10. testSucceed(10)                -indicates the test succeed
             11. callerMatchFailed(11)          -indicates the caller match failed
             12. notReceiveSSOffhookSignal(12)  -indicates not receive off hook signal
             13. dialNumberNotCompared(13)      -indicates the dial number is not compared
             14. backToneNotReceived(14)        -indicates the back tone has not received
             15. chanelCreateFailed(15)         -indicates the channel create failed
             16. ssNoResponseHookSignal(16)     -indicates SS do not response a hook signal
             17. other(255)                     -other
            "
        ::= { hwOntPstnCallerEmulateOprEntry 4 }

    --  1.3.6.1.4.1.2011.6.36.11.11.1.5
    -- 1.3.6.1.4.1.2011.6.36.11.11.1.5
    hwOntPstnCallerEmulateTestHoldTime OBJECT-TYPE
        SYNTAX Integer32 (1..600)
        MAX-ACCESS read-write
        STATUS current
        DESCRIPTION
            "
            Caller Emulate test hold time, the test will auto ended when this time out.
            "
        ::= { hwOntPstnCallerEmulateOprEntry 5 }

    --  1.3.6.1.4.1.2011.6.36.11.11.1.6
    -- 1.3.6.1.4.1.2011.6.36.11.11.1.6
    hwOntPstnCallerEmulateReportTelNo OBJECT-TYPE
        SYNTAX OCTET STRING (SIZE (1..32))
        MAX-ACCESS read-only
        STATUS current
        DESCRIPTION
            "
            The actual called number string checked and send to MGC or IMS.
            "
        ::= { hwOntPstnCallerEmulateOprEntry 6 }

    --  1.3.6.1.4.1.2011.6.36.11.11.1.7
    -- 1.3.6.1.4.1.2011.6.36.11.11.1.7
    hwOntPstnCallerEmulateErrorCode OBJECT-TYPE
        SYNTAX Integer32
        MAX-ACCESS read-only
        STATUS current
        DESCRIPTION
            "Error code"
        ::= { hwOntPstnCallerEmulateOprEntry 7 }

    hwOntPstnCallerEmulateTestRequestID OBJECT-TYPE
        SYNTAX Integer32
        MAX-ACCESS read-only
        STATUS current
        DESCRIPTION
            "Request ID"
        ::= { hwOntPstnCallerEmulateOprEntry 8 }

    --  1.3.6.1.4.1.2011.6.36.11.12
    -- 1.3.6.1.4.1.2011.6.36.11.12
    hwOntPstnCalledEmulateOprTable OBJECT-TYPE
        SYNTAX SEQUENCE OF HwOntPstnCalledEmulateOprEntry
        MAX-ACCESS not-accessible
        STATUS current
        DESCRIPTION
            "ont called emulate test table.
            The indexes of this table are hwVoiceIfIndex, hwVoiceOntIndex, hwVoiceOntPortIndex"
        ::= { hwVoipOntObjects 12 }

    --  1.3.6.1.4.1.2011.6.36.11.12.1
    -- 1.3.6.1.4.1.2011.6.36.11.12.1
    hwOntPstnCalledEmulateOprEntry OBJECT-TYPE
        SYNTAX HwOntPstnCalledEmulateOprEntry
        MAX-ACCESS not-accessible
        STATUS current
        DESCRIPTION
            "ont called emulate test table.
            The indexes of this entry are hwVoiceIfIndex, hwVoiceOntIndex, hwVoiceOntPortIndex"
        INDEX { hwVoiceIfIndex, hwVoiceOntIndex, hwVoiceOntPortIndex }
        ::= { hwOntPstnCalledEmulateOprTable 1 }

    HwOntPstnCalledEmulateOprEntry ::=
        SEQUENCE {
            hwOntPstnCalledEmulateOprType
                INTEGER,
            hwOntPstnCalledEmulateTestStatus
                INTEGER,
            hwOntPstnCalledEmulateTestResult
                INTEGER,
            hwOntPstnCalledEmulateTestHoldTime
                Integer32,
            hwOntPstnCalledEmulateTestRequestID
                Integer32
         }

    --  1.3.6.1.4.1.2011.6.36.11.12.1.1
    -- 1.3.6.1.4.1.2011.6.36.11.12.1.1
    hwOntPstnCalledEmulateOprType OBJECT-TYPE
        SYNTAX INTEGER
            {
            stop(1),
            start(2)
            }
        MAX-ACCESS read-write
        STATUS current
        DESCRIPTION
            "Operation type .
            Options:
            1. stop(1)  -Stop test
            2. start(2) -Start test
            "
        ::= { hwOntPstnCalledEmulateOprEntry 1 }

    --  1.3.6.1.4.1.2011.6.36.11.12.1.2
    -- 1.3.6.1.4.1.2011.6.36.11.12.1.2
    hwOntPstnCalledEmulateTestStatus OBJECT-TYPE
        SYNTAX INTEGER{startSuccessfully(1),stopSuccessfully(2), sendDTMFSuccessfully(3), testOuttime(4),
                        noDialtone(5), callerDialNumberAlready(6), noRinging(7), noRingbackTone(8),
                        waitingAgentMessageOuttime(9), testingFailure(10), agentMessageAck(11),calledoffhook(12),
                        testingAbnormal(13),broadbandtesting(14),capturefail(15),notratb(16),configsuccessfully(17),
                        ring(18),calleroffhook(19),playdialtone(20),dialnumbercomplete(21),onHook(22), testEnd(23), connected(24), other(255)}
        MAX-ACCESS read-only
        STATUS current
        DESCRIPTION
            "Test Status.
              Options:
              1. startSuccessfully(1)           -indicates start test successfully
              2. stopSuccessfully(2)            -indicates stop test successfully
              3. sendDTMFSuccessfully(3)        -indicates send DTMF successfully
              4. testOuttime(4)                 -indicates test is time out
              5. noDialtone(5)                  -indicates no dial tone
              6. callerDialNumberAlready(6)     -indicates that caller already dials a number
              7. noRinging(7)                   -indicates on ringing
              8. noRingbackTone(8)              -indicates no ring back tone
              9. waitingAgentMessageOuttime(9)  -indicates that timed-out (waiting for EMS processing)
              10. testingFailure(10)            -indicates that test failure
              11. agentMessageAck(11)           -indicates that host responds to the EMS
              12. calledoffhook(12)             -indicates that off hook (called party)
              13. testingAbnormal(13)           -indicates test is abnormal
              14. broadbandtesting(14)          -indicates capture fail
              15. capturefail(15)               -indicates that line capture failure
              16. notratb(16)                   -indicates that relay transfer board does not exist
              17. configsuccessfully(17)        -indicates configure successfully
              18. ring(18)                      -indicates ringing
              19. calleroffhook(19)             -indicates that off hook (calling party)
              20. playdialtone(20)              -indicates that play the dial tone
              21. dialnumbercomplete(21)        -indicates that dialup is finished
              22. onHook(22)                    -indicates on hook
              23. testEnd(23)                   -indicates that test is end
              24. connected(24)                 -indicates that off hook (called party)
              25. other(255)                    -other
             "
        ::= { hwOntPstnCalledEmulateOprEntry 2 }

    --  1.3.6.1.4.1.2011.6.36.11.12.1.3
    -- 1.3.6.1.4.1.2011.6.36.11.12.1.3
    hwOntPstnCalledEmulateTestResult OBJECT-TYPE
        SYNTAX INTEGER{calledNoRing(1),calledNoOffHook(2), calledOffHookingBusy(3), calledNoTalk(4),
                        callRelease(5),matchNoCompleted(6), sendNoCompleted(7), testSucceed(8),
                        calledMatchFailed(9),mGInsideReason(10), other(255)}
        MAX-ACCESS read-only
        STATUS current
        DESCRIPTION
            "Test Result.
            Options:
            1. calledNoRing(1)          -indicates that the called does not ring
            2. calledNoOffHook(2)       -indicates that the called does not off hook
            3. calledOffHookingBusy(3)  -indicates that the called is offhooking busy
            4. calledNoTalk(4)          -indicates that the called does not talk
            5. callRelease(5)           -indicates the call is released
            6. matchNoCompleted(6)      -indicates the match is not completed
            7. sendNoCompleted(7)       -indicates the send is not completed
            8. testSucceed(8)           -indicates the test succeed
            9. calledMatchFailed(9)     -indicates the caller match failed
            10. mGInsideReason(10)      -indicates the MG inside reason
            11. other(255)             -other
            "
        ::= { hwOntPstnCalledEmulateOprEntry 3 }

    --  1.3.6.1.4.1.2011.6.36.11.12.1.4
    -- 1.3.6.1.4.1.2011.6.36.11.12.1.4
    hwOntPstnCalledEmulateTestHoldTime OBJECT-TYPE
        SYNTAX Integer32 (1..600)
        MAX-ACCESS read-write
        STATUS current
        DESCRIPTION
            "
            Called Emulate test hold time, the test will auto ended when this time out.
            "
        ::= { hwOntPstnCalledEmulateOprEntry 4 }

    hwOntPstnCalledEmulateTestRequestID OBJECT-TYPE
        SYNTAX Integer32
        MAX-ACCESS read-only
        STATUS current
        DESCRIPTION
            "
            Request ID
            "
        ::= { hwOntPstnCalledEmulateOprEntry 5 }


    --  1.3.6.1.4.1.2011.6.36.11.13
    -- 1.3.6.1.4.1.2011.6.36.11.13
    hwOntVsqmWorstHistoryStatisticTable OBJECT-TYPE
        SYNTAX SEQUENCE OF HwOntVsqmWorstHistoryStatisticEntry
        MAX-ACCESS not-accessible
        STATUS current
        DESCRIPTION
            "ont port qos query table.
            The indexes of this table are hwVoiceIfIndex, hwVoiceOntIndex, hwVoiceOntPortIndex, hwOntVsqmStatisticIndex"
        ::= { hwVoipOntObjects 13 }

    --  1.3.6.1.4.1.2011.6.36.11.13.1
    -- 1.3.6.1.4.1.2011.6.36.11.13.1
    hwOntVsqmWorstHistoryStatisticEntry OBJECT-TYPE
        SYNTAX HwOntVsqmWorstHistoryStatisticEntry
        MAX-ACCESS not-accessible
        STATUS current
        DESCRIPTION
            "ont port qos query table.
            The indexes of this entry are hwVoiceIfIndex, hwVoiceOntIndex, hwVoiceOntPortIndex, hwOntVsqmStatisticIndex"
        INDEX { hwVoiceIfIndex, hwVoiceOntIndex, hwVoiceOntPortIndex, hwOntVsqmStatisticIndex}
        ::= { hwOntVsqmWorstHistoryStatisticTable 1 }

    HwOntVsqmWorstHistoryStatisticEntry ::=
        SEQUENCE {
            hwOntVsqmStatisticIndex
                Integer32,
            hwOntVsqmStatisticDateTime
                Unsigned32,
            hwOntVsqmTotalReceivePacketNum
                Unsigned32,
            hwOntVsqmTotalSendPacketNum
                Unsigned32,
            hwOntVsqmMeanLoopDelay
                Integer32,
            hwOntVsqmMeanJitter
                    Integer32,
            hwOntVsqmPacketLossRate
                Integer32
         }

    --  1.3.6.1.4.1.2011.6.36.11.13.1.1
    -- 1.3.6.1.4.1.2011.6.36.11.13.1.1
    hwOntVsqmStatisticIndex OBJECT-TYPE
        SYNTAX Integer32 (0..9)
        MAX-ACCESS not-accessible
        STATUS current
        DESCRIPTION
            "Indicates the  index"
        ::= { hwOntVsqmWorstHistoryStatisticEntry 1 }

    --  1.3.6.1.4.1.2011.6.36.11.13.1.2
    -- 1.3.6.1.4.1.2011.6.36.11.13.1.2
    hwOntVsqmStatisticDateTime OBJECT-TYPE
        SYNTAX Unsigned32
        MAX-ACCESS read-only
        STATUS current
        DESCRIPTION
            "Indicates the Statistic Date Time."
        ::= { hwOntVsqmWorstHistoryStatisticEntry 2 }

    --  1.3.6.1.4.1.2011.6.36.11.13.1.3
    -- 1.3.6.1.4.1.2011.6.36.11.13.1.3
    hwOntVsqmTotalReceivePacketNum OBJECT-TYPE
        SYNTAX Unsigned32
        MAX-ACCESS read-only
        STATUS current
        DESCRIPTION
            "Indicates the total receive packet number."
        ::= { hwOntVsqmWorstHistoryStatisticEntry 3 }

    --  1.3.6.1.4.1.2011.6.36.11.13.1.4
    -- 1.3.6.1.4.1.2011.6.36.11.13.1.4
    hwOntVsqmTotalSendPacketNum OBJECT-TYPE
        SYNTAX Unsigned32
        MAX-ACCESS read-only
        STATUS current
        DESCRIPTION
            "Indicates the total send packet number."
        ::= { hwOntVsqmWorstHistoryStatisticEntry 4 }

    --  1.3.6.1.4.1.2011.6.36.11.13.1.5
    -- 1.3.6.1.4.1.2011.6.36.11.13.1.5
    hwOntVsqmMeanLoopDelay OBJECT-TYPE
        SYNTAX Integer32
        MAX-ACCESS read-only
        STATUS current
        DESCRIPTION
            "Indicates the mean Loop Delay.
             Unit: millisecond
            "
        ::= { hwOntVsqmWorstHistoryStatisticEntry 5 }

    --  1.3.6.1.4.1.2011.6.36.11.13.1.6
    -- 1.3.6.1.4.1.2011.6.36.11.13.1.6
    hwOntVsqmMeanJitter OBJECT-TYPE
        SYNTAX Integer32
        MAX-ACCESS read-only
        STATUS current
        DESCRIPTION
            "Indicates the Mean Network Jitter.
             Unit: millisecond
            "
        ::= { hwOntVsqmWorstHistoryStatisticEntry 6 }

    --  1.3.6.1.4.1.2011.6.36.11.13.1.7
    -- 1.3.6.1.4.1.2011.6.36.11.13.1.7
    hwOntVsqmPacketLossRate OBJECT-TYPE
        SYNTAX Integer32
        MAX-ACCESS read-only
        STATUS current
        DESCRIPTION
            "Indicates the Packet Loss Rate in the interval.
             Unit: 1/100
            "
        ::= { hwOntVsqmWorstHistoryStatisticEntry 7 }


      hwOntPotsStatusTable OBJECT-TYPE
        SYNTAX      SEQUENCE OF HwOntPotsStatusEntry
        MAX-ACCESS  not-accessible
        STATUS      current
        DESCRIPTION
          "The table is used to display ptp and the ctp status of the ont
           The indexes of this table are hwVoiceIfIndex, hwVoiceOntIndex,hwVoiceOntPortIndex"
        ::= { hwVoipOntObjects 14 }


      hwOntPotsStatusEntry OBJECT-TYPE
        SYNTAX      HwOntPotsStatusEntry
        MAX-ACCESS  not-accessible
        STATUS      current
        DESCRIPTION
          "The table is used to display ptp and the ctp status of the ont
           The indexes of this entry are hwVoiceIfIndex, hwVoiceOntIndex,hwVoiceOntPortIndex"
        INDEX    {
                  hwVoiceIfIndex,
                  hwVoiceOntIndex,
                  hwVoiceOntPortIndex
                 }
        ::= { hwOntPotsStatusTable 1 }

      HwOntPotsStatusEntry ::=
        SEQUENCE
        {
          hwOntPotsPtpAdmState Integer32,
          hwOntPotsCtpSrvType  Integer32,
          hwOntPotsHookState   Integer32,
          hwOntPotsCallState   Integer32,
          hwOntPotsCtpSrvState Integer32,
          hwOntPotsCodec       Integer32
        }

      hwOntPotsPtpAdmState OBJECT-TYPE
        SYNTAX      Integer32(0..255)
        MAX-ACCESS  read-only
        STATUS      current
        DESCRIPTION
            "This attribute reports the current administrative state of a VoIP POTS port.Code points are assigned as follows:
             0: unlock
             1: lock
             The others means invaild.
            "
        ::= { hwOntPotsStatusEntry 1 }

      hwOntPotsCtpSrvType OBJECT-TYPE
        SYNTAX      Integer32(0..255)
        MAX-ACCESS  read-only
        STATUS      current
        DESCRIPTION
            "This attribute reports the current state of a VoIP POTS port session.Code points are assigned as follows:
             0: idle/none
             1: 2way
             2: 3way
             3: fax
             4: telem
             5: conference
             The others means invaild.
            "
        ::= { hwOntPotsStatusEntry 2 }

      hwOntPotsHookState OBJECT-TYPE
        SYNTAX      Integer32(0..255)
        MAX-ACCESS  read-only
        STATUS      current
        DESCRIPTION
            "This attribute indicates the current state of the subscriber line.Code points are assigned as follows:
            0: onhook,
            1: offhook
            The others means invaild.
            "
        ::= { hwOntPotsStatusEntry 3 }

      hwOntPotsCallState OBJECT-TYPE
        SYNTAX      Integer32(0..255)
        MAX-ACCESS  read-only
        STATUS      current
        DESCRIPTION
            "This attribute reports the POTS call status.Code points are assigned as follows:
            0: Registering
            1: Idle,on-hook
            2: Off-hook
            3: Dialing
            4: Ringing
            5: RingBack
            6: Connecting
            7: Connected
            8: Disconnecting
            9: Failed Registration
            10: Deactivated
            0xFF: Fault
            The others means invaild.
            "
        ::= { hwOntPotsStatusEntry 4 }

      hwOntPotsCtpSrvState OBJECT-TYPE
        SYNTAX      Integer32(0..255)
        MAX-ACCESS  read-only
        STATUS      current
        DESCRIPTION
            "This attribute reports the POTS service status. Code points are assigned as follows:
            0: endLocal(out of service by local)
            1: endRemote(out of service by remote without user)
            2: endAuto(out of service by remote fault)
            3: normal(In service)
            The others means invaild.
            "
        ::= { hwOntPotsStatusEntry 5 }

      hwOntPotsCodec OBJECT-TYPE
        SYNTAX      Integer32(0..255)
        MAX-ACCESS  read-only
        STATUS      current
        DESCRIPTION
            "Reports the current codec used for a VoIP POTS port.Code points are assigned as follows:
             0: G.711A
             1: G.729
             2: G.711U
             3: G.723
             4: G.726
             5: T.38
             6: G.722
             7: reserved
             8: reserved
             9: GSM
             10: DVI4, 8 kHz
             11: DVI4, 16 kHz
             12: LPC
             13: L16, 2 channels
             14: L16, 1 channel
             15: QCELP
             16: CN
             17: MPA
             18: G.728
             29: DVI4,11.025kHz
             20: DVI4,22.050kHz
             The others means invaild.
             "
        ::= { hwOntPotsStatusEntry 6 }

        hwOntMgVagTable OBJECT-TYPE
        SYNTAX SEQUENCE OF HwOntMgVagEntry
        MAX-ACCESS not-accessible
        STATUS current
        DESCRIPTION
            "Ont H248 and MGCP interface table.
            The indexes of this table are hwOntMgVagIfIndex,hwOntMgVagOntIndex,hwOntMgVagMgId"
        ::= { hwVoipOntObjects 15 }

        hwOntMgVagEntry OBJECT-TYPE
        SYNTAX HwOntMgVagEntry
        MAX-ACCESS not-accessible
        STATUS current
        DESCRIPTION
            "Ont H248 and MGCP interface table.
            The indexes of this entry are hwOntMgVagIfIndex,hwOntMgVagOntIndex,hwOntMgVagMgId"
        INDEX { hwOntMgVagIfIndex,hwOntMgVagOntIndex,hwOntMgVagMgId }
        ::= { hwOntMgVagTable 1 }

        HwOntMgVagEntry ::=
        SEQUENCE {
            hwOntMgVagIfIndex
                Unsigned32,
            hwOntMgVagOntIndex
                Integer32,
            hwOntMgVagMgId
                Integer32,
            hwOntMgVagIpIndex
                Integer32,
            hwOntMgVagPrimaryMgc
                OCTET STRING,
            hwOntMgVagPrimaryMgcPort
                Integer32,
            hwOntMgVagSecondaryMgc
                OCTET STRING,
            hwOntMgVagSecondaryMgcPort
                Integer32,
            hwOntMgVagMinPort
                Integer32,
            hwOntMgVagMaxPort
                Integer32,
            hwOntMgVagMediaDscp
                Integer32,
            hwOntMgVagSignalPort
                Integer32,
            hwOntMgVagSignalDscp
                Integer32,
            hwOntMgVagMidType
                INTEGER,
            hwOntMgVagMid
                OCTET STRING,
            hwOntMgVagMessageFormat
                INTEGER,
            hwOntMgVagVersion
                INTEGER,
            hwOntMgVagTidBase
                OCTET STRING,
            hwOntMgVagHeartbeatMode
                INTEGER,
            hwOntMgVagHeartbeatCycle
                Integer32,
            hwOntMgVagHeartbeatCount
                Integer32,
            hwOntMgVagTidNumber
                Integer32,
            hwOntMgVagTidPrefix
                OCTET STRING,
            hwOntMgVagTidMode
                INTEGER,
            hwOntMgVagTidDigitBegin
                Integer32,
            hwOntMgVagTidDigitLength
                Integer32,
            hwOntMgVagRowStatus
                RowStatus,
            hwOntMgProtocolType
                INTEGER
           }

    hwOntMgVagIfIndex OBJECT-TYPE
        SYNTAX Unsigned32
        MAX-ACCESS not-accessible
        STATUS current
        DESCRIPTION
            "The ifindex of xPON port."
        ::= { hwOntMgVagEntry 1 }

    hwOntMgVagOntIndex OBJECT-TYPE
        SYNTAX Integer32 (0..255)
        MAX-ACCESS not-accessible
        STATUS current
        DESCRIPTION
            "The ONT index."
        ::= { hwOntMgVagEntry 2 }

    hwOntMgVagMgId OBJECT-TYPE
        SYNTAX Integer32 (1..32)
        MAX-ACCESS not-accessible
        STATUS current
        DESCRIPTION
            "The MG ID."
        ::= { hwOntMgVagEntry 3 }

    hwOntMgVagIpIndex OBJECT-TYPE
        SYNTAX Integer32 (0..3)
        MAX-ACCESS read-write
        STATUS current
        DESCRIPTION
            "The IP index."
        ::= { hwOntMgVagEntry 4 }

    hwOntMgVagPrimaryMgc OBJECT-TYPE
        SYNTAX OCTET STRING (SIZE (0..64))
        MAX-ACCESS read-write
        STATUS current
        DESCRIPTION
            "Primary mgc."
        ::= { hwOntMgVagEntry 5 }

    hwOntMgVagPrimaryMgcPort OBJECT-TYPE
        SYNTAX Integer32 (0..65535)
        MAX-ACCESS read-write
        STATUS current
        DESCRIPTION
            "The port of primary mgc."
        ::= { hwOntMgVagEntry 6 }

    hwOntMgVagSecondaryMgc OBJECT-TYPE
        SYNTAX OCTET STRING (SIZE (0..64))
        MAX-ACCESS read-write
        STATUS current
        DESCRIPTION
            "Secondary mgc."
        ::= { hwOntMgVagEntry 7 }

    hwOntMgVagSecondaryMgcPort OBJECT-TYPE
        SYNTAX Integer32 (0..65535)
        MAX-ACCESS read-write
        STATUS current
        DESCRIPTION
            "The port of secondary mgc."
        ::= { hwOntMgVagEntry 8 }

    hwOntMgVagMinPort OBJECT-TYPE
        SYNTAX Integer32 (0..65535)
        MAX-ACCESS read-write
        STATUS current
        DESCRIPTION
            "The min udp port of media rtp. It is valid for GPON ONT and invalid for EPON ONT."
       ::= { hwOntMgVagEntry 9 }

    hwOntMgVagMaxPort OBJECT-TYPE
        SYNTAX Integer32 (0..65535)
        MAX-ACCESS read-write
        STATUS current
        DESCRIPTION
            "The max udp port of media rtp. It is valid for GPON ONT and invalid for EPON ONT."
         ::= { hwOntMgVagEntry 10 }

    hwOntMgVagMediaDscp OBJECT-TYPE
        SYNTAX Integer32 (0..63)
        MAX-ACCESS read-write
        STATUS current
        DESCRIPTION
            "The DSCP of media RTP. It is valid for GPON ONT and invalid for EPON ONT."
        ::= { hwOntMgVagEntry 11 }

    hwOntMgVagSignalPort OBJECT-TYPE
        SYNTAX Integer32 (0..65535)
        MAX-ACCESS read-write
        STATUS current
        DESCRIPTION
            "The udp port of signal. It is valid for GPON ONT and invalid for EPON ONT."
        ::= { hwOntMgVagEntry 12 }

    hwOntMgVagSignalDscp OBJECT-TYPE
        SYNTAX Integer32 (0..63)
        MAX-ACCESS read-write
        STATUS current
        DESCRIPTION
            "The DSCP of signal. It is valid for GPON ONT and invalid for EPON ONT."
        ::= { hwOntMgVagEntry 13 }

    hwOntMgVagMidType OBJECT-TYPE
        SYNTAX INTEGER
            {
            ip4Address(1),
            domainName(2),
            deviceName(3)
            }
        MAX-ACCESS read-write
        STATUS current
        DESCRIPTION
            "The MID type of the MG message, just used by H248.
            Options:
            1.ip4Address(1)    -indicates the MID type is ip4Address
            2.domainName(2)    -indicates the MID type is domainName
            3.deviceName(3)    -indicates the MID type is deviceName
            "
        ::= { hwOntMgVagEntry 14 }

    hwOntMgVagMid OBJECT-TYPE
        SYNTAX OCTET STRING (SIZE (0..64))
        MAX-ACCESS read-write
        STATUS current
        DESCRIPTION
            "The name of the MG device."
        ::= { hwOntMgVagEntry 15 }

    hwOntMgVagMessageFormat OBJECT-TYPE
        SYNTAX INTEGER
            {
            textLong(1),
            textShort(2),
            binary(3)
            }
        MAX-ACCESS read-write
        STATUS current
        DESCRIPTION
            "The message format of MG interface, just used by H248. It is valid for GPON ONT and invalid for EPON ONT.
            Options:
            1.textLong(1)     -indicates the message format of MG interface is text-long
            2.textShort(2)    -indicates the message format of MG interface is text-short
            3.binary(3)       -indicates the message format of MG interface is binary
            "
        ::= { hwOntMgVagEntry 16 }

    hwOntMgVagVersion OBJECT-TYPE
        SYNTAX INTEGER
            {
            ontDefault(1),
            v1(2),
            v2(3),
            v3(4)
            }
        MAX-ACCESS read-write
        STATUS current
        DESCRIPTION
            "The H.248 version of MG interface, just used by H248. It is valid for GPON ONT and invalid for EPON ONT.
            Options:
            1.ontDefault(1)  -indicates the H.248 version of MG interface is ont-default
            2.v1(2)          -indicates the H.248 version of MG interface is v1
            3.v2(3)          -indicates the H.248 version of MG interface is v2
            4.v3(4)          -indicates the H.248 version of MG interface is v3
            "
        ::= { hwOntMgVagEntry 17 }

    hwOntMgVagTidBase OBJECT-TYPE
        SYNTAX OCTET STRING (SIZE (0..24))
        MAX-ACCESS read-write
        STATUS current
        DESCRIPTION
            "The base string for the H.248 physical tid."
        ::= { hwOntMgVagEntry 18 }

    hwOntMgVagHeartbeatMode OBJECT-TYPE
        SYNTAX INTEGER
            {
            disable(1),
            notifyMethod(2)
            }
        MAX-ACCESS read-write
        STATUS current
        DESCRIPTION
            "The heartbeat mode.
            Options:
            1.disable(1)         -indicates the heartbeat mode is disable
            2.notifyMethod(2)    -indicates the heartbeat mode is notify-method
            "
        ::= { hwOntMgVagEntry 19 }

    hwOntMgVagHeartbeatCycle OBJECT-TYPE
        SYNTAX Integer32 (5..655)
        MAX-ACCESS read-write
        STATUS current
        DESCRIPTION
            "The heartbeat cycle."
        ::= { hwOntMgVagEntry 20 }

    hwOntMgVagHeartbeatCount OBJECT-TYPE
        SYNTAX Integer32 (1..20)
        MAX-ACCESS read-write
        STATUS current
        DESCRIPTION
            "The heartbeat count."
        ::= { hwOntMgVagEntry 21 }

    hwOntMgVagTidNumber OBJECT-TYPE
        SYNTAX Integer32 (1..255)
        MAX-ACCESS read-write
        STATUS current
        DESCRIPTION
            "The rtp tid number."
        ::= { hwOntMgVagEntry 22 }

    hwOntMgVagTidPrefix OBJECT-TYPE
        SYNTAX OCTET STRING (SIZE (0..16))
        MAX-ACCESS read-write
        STATUS current
        DESCRIPTION
            "The rtp tid prefix."
        ::= { hwOntMgVagEntry 23 }

    hwOntMgVagTidMode OBJECT-TYPE
        SYNTAX INTEGER
            {
            aligned(1),
            notAligned(2)
            }
        MAX-ACCESS read-write
        STATUS current
        DESCRIPTION
            "The rtp tid mode.
            Options:
            1.aligned(1)        -indicates the rtp tid mode is aligned
            2.notAligned(2)     -indicates the rtp tid mode is not-aligned
            "
        ::= { hwOntMgVagEntry 24 }

    hwOntMgVagTidDigitBegin OBJECT-TYPE
        SYNTAX Integer32 (0..99999999)
        MAX-ACCESS read-write
        STATUS current
        DESCRIPTION
            "The beginning number of the rtp tid digit."
        ::= { hwOntMgVagEntry 25 }

    hwOntMgVagTidDigitLength OBJECT-TYPE
        SYNTAX Integer32 (1..16)
        MAX-ACCESS read-write
        STATUS current
        DESCRIPTION
            "The length of the rtp tid digit."
        ::= { hwOntMgVagEntry 26 }

    hwOntMgVagRowStatus OBJECT-TYPE
        SYNTAX RowStatus
        MAX-ACCESS read-create
        STATUS current
        DESCRIPTION
            "Options:
            1.active(1)          -indicates active
            2.notInService(2)    -indicates not in service
            3.notReady(3)        -indicates not ready
            4.createAndGo(4)     -indicates create and go
            5.createAndWait(5)   -indicates create and wait
            6.destroy(6)         -indicates destroy
            Only 4 and 6 is support Now."
        ::= { hwOntMgVagEntry 27 }

    hwOntMgProtocolType OBJECT-TYPE
        SYNTAX INTEGER
            {
            h248(1),
            mgcp(2)
            }
        MAX-ACCESS read-write
        STATUS current
        DESCRIPTION
            "The mg protocol type.
            Options:
            1.h248(1)        -indicates the mg protocol is H248
            2.mgcp(2)        -indicates the mg protocol is MGCP
            Default: H248(1)
            "
        ::= { hwOntMgVagEntry 28 }

    hwOntMgAttrConfigTable OBJECT-TYPE
        SYNTAX SEQUENCE OF HwOntMgAttrConfigEntry
        MAX-ACCESS not-accessible
        STATUS current
        DESCRIPTION
            "Ont MG public attribute table.
            The index of this table is hwOntMgAttrIfIndex,hwOntMgAttrOntIndex,hwOntMgAttrMgId"
        ::= { hwVoipOntObjects 16 }

    hwOntMgAttrConfigEntry OBJECT-TYPE
        SYNTAX HwOntMgAttrConfigEntry
        MAX-ACCESS not-accessible
        STATUS current
        DESCRIPTION
            "Ont MG public attribute table.
            The index of this entry is hwOntMgAttrIfIndex,hwOntMgAttrOntIndex,hwOntMgAttrMgId"
        INDEX { hwOntMgAttrIfIndex,hwOntMgAttrOntIndex,hwOntMgAttrMgId }
        ::= { hwOntMgAttrConfigTable 1 }


    HwOntMgAttrConfigEntry ::=
        SEQUENCE {
            hwOntMgAttrIfIndex
                Unsigned32,
            hwOntMgAttrOntIndex
                Integer32,
            hwOntMgAttrMgId
                Integer32,
            hwOntMgAttrFaxMode
                INTEGER,
            hwOntMgAttrNegoMode
                INTEGER,
            hwOntMgAttrOrder1stCodec
                Integer32,
            hwOntMgAttrOrder1stPacketPeriod
                INTEGER,
            hwOntMgAttrOrder1stSilenceFlag
                INTEGER,
            hwOntMgAttrOrder2stCodec
                Integer32,
            hwOntMgAttrOrder2stPacketPeriod
                INTEGER,
            hwOntMgAttrOrder2stSilenceFlag
                INTEGER,
            hwOntMgAttrOrder3stCodec
                Integer32,
            hwOntMgAttrOrder3stPacketPeriod
                INTEGER,
            hwOntMgAttrOrder3stSilenceFlag
                INTEGER,
            hwOntMgAttrOrder4stCodec
                Integer32,
            hwOntMgAttrOrder4stPacketPeriod
                INTEGER,
            hwOntMgAttrOrder4stSilenceFlag
                INTEGER,
            hwOntMgAttrOobDtmfFlag
                INTEGER,
            hwOntMgAttrAnnouncementType
                INTEGER,
            hwOntMgAttrJitterBuffTarget
                Integer32,
            hwOntMgAttrJitterBuffMax
                Integer32,
            hwOntMgAttrJitterBuffMin
                Integer32,
            hwOntMgAttrJitterBuffDynTarget
                Integer32,
            hwOntMgAttrEchoFlag
                INTEGER,
            hwOntMgAttrPstnProtocolVariant
                Integer32,
            hwOntMgAttrPiggybackEventFlag
                INTEGER,
            hwOntMgAttrToneEventFlag
                INTEGER,
            hwOntMgAttrDtmfEventFlag
                INTEGER,
            hwOntMgAttrCasEventFlag
                INTEGER,
            hwOntMgAttrFlashUpper
                Integer32,
            hwOntMgAttrFlashLower
                Integer32,
            hwOntMgAttrSilence
                INTEGER
           }

    hwOntMgAttrIfIndex OBJECT-TYPE
        SYNTAX Unsigned32
        MAX-ACCESS not-accessible
        STATUS current
        DESCRIPTION
            "The ifindex of xPON port."
        ::= { hwOntMgAttrConfigEntry 1 }

    hwOntMgAttrOntIndex OBJECT-TYPE
        SYNTAX Integer32 (0..255)
        MAX-ACCESS not-accessible
        STATUS current
        DESCRIPTION
            "The ONT index."
        ::= { hwOntMgAttrConfigEntry 2 }

    hwOntMgAttrMgId OBJECT-TYPE
        SYNTAX Integer32 (1..32)
        MAX-ACCESS not-accessible
        STATUS current
        DESCRIPTION
            "The MG ID."
        ::= { hwOntMgAttrConfigEntry 3 }

    hwOntMgAttrFaxMode OBJECT-TYPE
        SYNTAX INTEGER
            {
            passthru(1),
            t38(2)
            }
        MAX-ACCESS read-write
        STATUS current
        DESCRIPTION
            "The fax mode.
            Options:
            1.passthru(1)   -indicates the fax mode is passthru
            2.t38(2)        -indicates the fax mode is t38
            "
        ::= { hwOntMgAttrConfigEntry 4 }

    hwOntMgAttrNegoMode OBJECT-TYPE
        SYNTAX INTEGER
            {
            negotiate(1),
            selfSwitch(2)
            }
        MAX-ACCESS read-write
        STATUS current
        DESCRIPTION
            "The negotiate mode.
            Options:
            1.negotiate(1)      -indicates the negotiate mode is negotiate
            2.selfSwitch(2)     -indicates the fax mode is self-switch
            "
        ::= { hwOntMgAttrConfigEntry 5 }

    hwOntMgAttrOrder1stCodec OBJECT-TYPE
        SYNTAX Integer32 (0..95|255)
        MAX-ACCESS read-write
        STATUS current
        DESCRIPTION
            "codec of order 1. It is valid for GPON ONT and invalid for EPON ONT."
        ::= { hwOntMgAttrConfigEntry 6 }

    hwOntMgAttrOrder1stPacketPeriod OBJECT-TYPE
        SYNTAX INTEGER
            {
            time10ms(1),
            time15ms(2),
            time20ms(3),
            time25ms(4),
            time30ms(5)
            }
        MAX-ACCESS read-write
        STATUS current
        DESCRIPTION
            "packet period of order 1. It is valid for GPON ONT and invalid for EPON ONT.
            Options:
            1.time10ms(1)  -indicates the packet period is 10ms
            2.time15ms(2)  -indicates the packet period is 15ms
            3.time20ms(3)  -indicates the packet period is 20ms
            4.time25ms(4)  -indicates the packet period is 25ms
            5.time30ms(5)  -indicates the packet period is 30ms
            "
        ::= { hwOntMgAttrConfigEntry 7 }

    hwOntMgAttrOrder1stSilenceFlag OBJECT-TYPE
        SYNTAX INTEGER
            {
            off(1),
            on(2)
            }
        MAX-ACCESS read-write
        STATUS current
        DESCRIPTION
            "silence suppression of order 1. It is valid for GPON ONT and invalid for EPON ONT.
            Options:
            1.off(1)    -indicates the silence suppression is off
            2.on(2)     -indicates the silence suppression is on
            "
        ::= { hwOntMgAttrConfigEntry 8 }

    hwOntMgAttrOrder2stCodec OBJECT-TYPE
        SYNTAX Integer32 (0..95|255)
        MAX-ACCESS read-write
        STATUS current
        DESCRIPTION
            "codec of order 2. It is valid for GPON ONT and invalid for EPON ONT."
        ::= { hwOntMgAttrConfigEntry 9 }

    hwOntMgAttrOrder2stPacketPeriod OBJECT-TYPE
        SYNTAX INTEGER
            {
            time10ms(1),
            time15ms(2),
            time20ms(3),
            time25ms(4),
            time30ms(5)
            }
        MAX-ACCESS read-write
        STATUS current
        DESCRIPTION
            "packet period of order 2. It is valid for GPON ONT and invalid for EPON ONT.
            Options:
            1.time10ms(1)  -indicates the packet period is 10ms
            2.time15ms(2)  -indicates the packet period is 15ms
            3.time20ms(3)  -indicates the packet period is 20ms
            4.time25ms(4)  -indicates the packet period is 25ms
            5.time30ms(5)  -indicates the packet period is 30ms
            "
        ::= { hwOntMgAttrConfigEntry 10 }

    hwOntMgAttrOrder2stSilenceFlag OBJECT-TYPE
        SYNTAX INTEGER
            {
            off(1),
            on(2)
            }
        MAX-ACCESS read-write
        STATUS current
        DESCRIPTION
            "silence suppression of order 2. It is valid for GPON ONT and invalid for EPON ONT.
            Options:
            1.off(1)    -indicates the silence suppression is off
            2.on(2)     -indicates the silence suppression is on
            "
        ::= { hwOntMgAttrConfigEntry 11 }

    hwOntMgAttrOrder3stCodec OBJECT-TYPE
        SYNTAX Integer32 (0..95|255)
        MAX-ACCESS read-write
        STATUS current
        DESCRIPTION
            "codec of order 3. It is valid for GPON ONT and invalid for EPON ONT."
        ::= { hwOntMgAttrConfigEntry 12 }

    hwOntMgAttrOrder3stPacketPeriod OBJECT-TYPE
        SYNTAX INTEGER
            {
            time10ms(1),
            time15ms(2),
            time20ms(3),
            time25ms(4),
            time30ms(5)
            }
        MAX-ACCESS read-write
        STATUS current
        DESCRIPTION
            "packet period of order 3. It is valid for GPON ONT and invalid for EPON ONT.
            Options:
            1.time10ms(1)  -indicates the packet period is 10ms
            2.time15ms(2)  -indicates the packet period is 15ms
            3.time20ms(3)  -indicates the packet period is 20ms
            4.time25ms(4)  -indicates the packet period is 25ms
            5.time30ms(5)  -indicates the packet period is 30ms
            "
        ::= { hwOntMgAttrConfigEntry 13 }

    hwOntMgAttrOrder3stSilenceFlag OBJECT-TYPE
        SYNTAX INTEGER
            {
            off(1),
            on(2)
            }
        MAX-ACCESS read-write
        STATUS current
        DESCRIPTION
            "silence suppression of order 3. It is valid for GPON ONT and invalid for EPON ONT.
            Options:
            1.off(1)    -indicates the silence suppression is off
            2.on(2)     -indicates the silence suppression is on
            "
        ::= { hwOntMgAttrConfigEntry 14 }

    hwOntMgAttrOrder4stCodec OBJECT-TYPE
        SYNTAX Integer32 (0..95|255)
        MAX-ACCESS read-write
        STATUS current
        DESCRIPTION
            "codec of order 4. It is valid for GPON ONT and invalid for EPON ONT."
        ::= { hwOntMgAttrConfigEntry 15 }

    hwOntMgAttrOrder4stPacketPeriod OBJECT-TYPE
        SYNTAX INTEGER
            {
            time10ms(1),
            time15ms(2),
            time20ms(3),
            time25ms(4),
            time30ms(5)
            }
        MAX-ACCESS read-write
        STATUS current
        DESCRIPTION
            "packet period of order 3. It is valid for GPON ONT and invalid for EPON ONT.
            Options:
            1.time10ms(1)  -indicates the packet period is 10ms
            2.time15ms(2)  -indicates the packet period is 15ms
            3.time20ms(3)  -indicates the packet period is 20ms
            4.time25ms(4)  -indicates the packet period is 25ms
            5.time30ms(5)  -indicates the packet period is 30ms
            "
        ::= { hwOntMgAttrConfigEntry 16 }

    hwOntMgAttrOrder4stSilenceFlag OBJECT-TYPE
        SYNTAX INTEGER
            {
            off(1),
            on(2)
            }
        MAX-ACCESS read-write
        STATUS current
        DESCRIPTION
            "silence suppression of order 4. It is valid for GPON ONT and invalid for EPON ONT.
            Options:
            1.off(1)    -indicates the silence suppression is off
            2.on(2)     -indicates the silence suppression is on
            "
        ::= { hwOntMgAttrConfigEntry 17 }

    hwOntMgAttrOobDtmfFlag OBJECT-TYPE
        SYNTAX INTEGER
            {
            disable(1),
            enable(2)
            }
        MAX-ACCESS read-write
        STATUS current
        DESCRIPTION
            "Oob Dtmf Flag. It is valid for GPON ONT and invalid for EPON ONT.
            Options:
            1.disable(1)    -indicates the Oob DTMF is disable
            2.enable(2)     -indicates the Oob DTMF is enable
            "
        ::= { hwOntMgAttrConfigEntry 18 }

    hwOntMgAttrAnnouncementType OBJECT-TYPE
        SYNTAX INTEGER
            {
            silence(1),
            reordertone(2),
            fastbusy(3),
            voiceannouncement(4),
            none(5)
            }
        MAX-ACCESS read-write
        STATUS current
        DESCRIPTION
            "Announcement after off hook time out. It is valid for GPON ONT and invalid for EPON ONT.
            Options:
            1.silence(1)            -indicates play the voice of silence after off hook time out
            2.reordertone(2)        -indicates play the voice of reorder tone after off hook time out
            3.fastbusy(3)           -indicates play the voice of fast busy after off hook time out
            4.voiceannouncement(4)  -indicates play the voice of voiceannouncement after off hook time out
            5.none(5)               -indicates play none after off hook time out
            "
        ::= { hwOntMgAttrConfigEntry 19 }

    hwOntMgAttrJitterBuffTarget OBJECT-TYPE
        SYNTAX Integer32 (1..65535)
        MAX-ACCESS read-write
        STATUS current
        DESCRIPTION
            "The target value of fixed jitter buffer. It is valid for GPON ONT and invalid for EPON ONT."
        ::= { hwOntMgAttrConfigEntry 20 }

    hwOntMgAttrJitterBuffMax OBJECT-TYPE
        SYNTAX Integer32 (1..65535)
        MAX-ACCESS read-write
        STATUS current
        DESCRIPTION
            "The max value of jitter buffer. It is valid for GPON ONT and invalid for EPON ONT."
        ::= { hwOntMgAttrConfigEntry 21 }

    hwOntMgAttrJitterBuffMin OBJECT-TYPE
        SYNTAX Integer32 (1..65535)
        MAX-ACCESS read-write
        STATUS current
        DESCRIPTION
            "The min value of jitter buffer. It is valid for GPON ONT and invalid for EPON ONT."
        ::= { hwOntMgAttrConfigEntry 22 }

    hwOntMgAttrJitterBuffDynTarget OBJECT-TYPE
        SYNTAX Integer32 (1..65535)
        MAX-ACCESS read-write
        STATUS current
        DESCRIPTION
            "The target value of dynamic jitter buffer. It is valid for GPON ONT and invalid for EPON ONT."
        ::= { hwOntMgAttrConfigEntry 23 }

    hwOntMgAttrEchoFlag OBJECT-TYPE
        SYNTAX INTEGER
            {
            off(1),
            on(2)
            }
        MAX-ACCESS read-write
        STATUS current
        DESCRIPTION
            "echo flag. It is valid for GPON ONT and invalid for EPON ONT.
            Options:
            1.off(1)    -indicates the echo flag is off
            2.on(2)     -indicates the echo flag is on
            "
        ::= { hwOntMgAttrConfigEntry 24 }

     hwOntMgAttrPstnProtocolVariant OBJECT-TYPE
        SYNTAX Integer32 (0..65535)
        MAX-ACCESS read-write
        STATUS current
        DESCRIPTION
            "country code, means geography location. It is valid for GPON ONT and invalid for EPON ONT.
            Options:
            Indicate the E.164 country code
            "
        ::= { hwOntMgAttrConfigEntry 25 }

     hwOntMgAttrPiggybackEventFlag OBJECT-TYPE
        SYNTAX INTEGER
            {
            disable(1),
            enable(2)
            }
        MAX-ACCESS read-write
        STATUS current
        DESCRIPTION
            "whether process piggyback events or not. It is valid for GPON ONT and invalid for EPON ONT.
            Options:
            1.disable(1)    -indicates don't process piggyback events
            2.enable(2)     -indicates process piggyback events
            "
        ::= { hwOntMgAttrConfigEntry 26 }

    hwOntMgAttrToneEventFlag OBJECT-TYPE
        SYNTAX INTEGER
            {
            disable(1),
            enable(2)
            }
        MAX-ACCESS read-write
        STATUS current
        DESCRIPTION
            "whether process Tone events or not. It is valid for GPON ONT and invalid for EPON ONT.
            Options:
            1.disable(1)    -indicates don't process Tone events
            2.enable(2)     -indicates process Tone events
            "
        ::= { hwOntMgAttrConfigEntry 27 }

    hwOntMgAttrDtmfEventFlag OBJECT-TYPE
        SYNTAX INTEGER
            {
            disable(1),
            enable(2)
            }
        MAX-ACCESS read-write
        STATUS current
        DESCRIPTION
            "whether process Dtmf events or not. It is valid for GPON ONT and invalid for EPON ONT.
            Options:
            1.disable(1)    -indicates don't process Dtmf events
            2.enable(2)     -indicates process Dtmf events
            "
        ::= { hwOntMgAttrConfigEntry 28 }

    hwOntMgAttrCasEventFlag OBJECT-TYPE
        SYNTAX INTEGER
            {
            disable(1),
            enable(2)
            }
        MAX-ACCESS read-write
        STATUS current
        DESCRIPTION
            "whether process cas events or not. It is valid for GPON ONT and invalid for EPON ONT.
            Options:
            1.disable(1)    -indicates don't process cas events
            2.enable(2)     -indicates process cas events
            "
        ::= { hwOntMgAttrConfigEntry 29 }

    hwOntMgAttrFlashUpper OBJECT-TYPE
        SYNTAX Integer32 (0..65535)
        MAX-ACCESS read-write
        STATUS current
        DESCRIPTION
            "The flash upper limit. It is valid for GPON ONT and invalid for EPON ONT.
             If the value is 0, it indicates ONT own default value.
            "
        ::= { hwOntMgAttrConfigEntry 30 }

    hwOntMgAttrFlashLower OBJECT-TYPE
        SYNTAX Integer32 (0..65535)
        MAX-ACCESS read-write
        STATUS current
        DESCRIPTION
            "The flash lower limit. It is valid for GPON ONT and invalid for EPON ONT.
             If the value is 0, it indicates ONT own default value.
            "
        ::= { hwOntMgAttrConfigEntry 31 }

    hwOntMgAttrSilence OBJECT-TYPE
        SYNTAX INTEGER
            {
            disable(1),
            enable(2),
            baseOnCodec(3)
            }
        MAX-ACCESS read-write
        STATUS current
        DESCRIPTION
            "The silence switch. It is valid for GPON ONT and invalid for EPON ONT.
            Options:
            1.disable(1)        -indicates the silence switch is disable
            2.enable(2)         -indicates the silence switch is enable
            3.baseOnCodec(3)    -indicates the silence switch is base-on-codec
            "
        ::= { hwOntMgAttrConfigEntry 32 }

    hwOntSipVagTable OBJECT-TYPE
        SYNTAX SEQUENCE OF HwOntSipVagEntry
        MAX-ACCESS not-accessible
        STATUS current
        DESCRIPTION
            "SIP VAG Table.
            The indexes of this table are hwOntSipVagIfIndex, hwOntSipVagOntIndex, hwOntSipVagMgId."
        ::= { hwVoipOntObjects 17 }

    hwOntSipVagEntry OBJECT-TYPE
        SYNTAX HwOntSipVagEntry
        MAX-ACCESS not-accessible
        STATUS current
        DESCRIPTION
            "SIP VAG Table.
            The indexes of this entry are hwOntSipVagIfIndex, hwOntSipVagOntIndex, hwOntSipVagMgId."
        INDEX { hwOntSipVagIfIndex, hwOntSipVagOntIndex, hwOntSipVagMgId }
        ::= { hwOntSipVagTable 1 }

    HwOntSipVagEntry ::=
        SEQUENCE {
            hwOntSipVagIfIndex
                Unsigned32,
            hwOntSipVagOntIndex
                Integer32,
            hwOntSipVagMgId
                Integer32,
            hwOntSipVagIpIndex
                Integer32,
            hwOntSipVagProxyPort
                Integer32,
            hwOntSipVagSecondaryProxyUri
                OCTET STRING,
            hwOntSipVagSecondaryProxyPort
                Integer32,
            hwOntSipVagRegisterPort
                Integer32,
            hwOntSipVagSecondaryRegisterUri
                OCTET STRING,
            hwOntSipVagSecondaryRegisterPort
                Integer32,
            hwOntSipVagOutboundUri
                OCTET STRING,
            hwOntSipVagOutboundPort
                Integer32,
            hwOntSipVagHeartbeatMode
                INTEGER,
            hwOntSipVagHeartbeatCycle
                Integer32,
            hwOntSipVagHeartbeatCount
                Integer32,
            hwOntSipVagProxyUri
                OCTET STRING,
            hwOntSipVagRtpPortMin
                Integer32,
            hwOntSipVagRtpPortMax
                Integer32,
            hwOntSipVagRtpDscp
                Integer32,
            hwOntSipVagSignalTransMode
                INTEGER,
            hwOntSipVagSignalPortId
                Integer32,
            hwOntSipVagSignalDscp
                Integer32,
            hwOntSipVagRegisterUri
                OCTET STRING,
            hwOntSipVagRegExpiration
                Integer32,
            hwOntSipVagReRegStartTime
                Integer32,
            hwOntSipVagVoicemailUri
                OCTET STRING,
            hwOntSipVagVoicemailSubExpir
                Unsigned32,
            hwOntSipVagConfFactoryUri
                OCTET STRING,
            hwOntSipVagBridgedLineAgentUri
                OCTET STRING,
            hwOntSipVagUserAuthRealm
                OCTET STRING,
            hwOntSipVagHomeDomain
                OCTET STRING,
            hwOntSipVagRowStatus
                RowStatus,
            hwOntSipVagServerType
                INTEGER
         }

    hwOntSipVagIfIndex OBJECT-TYPE
        SYNTAX Unsigned32
        MAX-ACCESS not-accessible
        STATUS current
        DESCRIPTION
            "The ifindex."
        ::= { hwOntSipVagEntry 1 }

    hwOntSipVagOntIndex OBJECT-TYPE
        SYNTAX Integer32 (0..255)
        MAX-ACCESS not-accessible
        STATUS current
        DESCRIPTION
            "The ONT ID."
        ::= { hwOntSipVagEntry 2 }

    hwOntSipVagMgId OBJECT-TYPE
        SYNTAX Integer32 (1..32)
        MAX-ACCESS not-accessible
        STATUS current
        DESCRIPTION
            "The MG ID."
        ::= { hwOntSipVagEntry 3 }

    hwOntSipVagIpIndex OBJECT-TYPE
        SYNTAX Integer32 (0..3)
        MAX-ACCESS read-write
        STATUS current
        DESCRIPTION
            "The index of IP interface.
            "
        ::= { hwOntSipVagEntry 4 }

    hwOntSipVagProxyPort OBJECT-TYPE
        SYNTAX Integer32 (0..65535)
        MAX-ACCESS read-write
        STATUS current
        DESCRIPTION
            "The port of proxy server."
        ::= { hwOntSipVagEntry 5 }

    hwOntSipVagSecondaryProxyUri OBJECT-TYPE
        SYNTAX OCTET STRING (SIZE (0..64))
        MAX-ACCESS read-write
        STATUS current
        DESCRIPTION
            "The URI of secondary proxy server."
        ::= { hwOntSipVagEntry 6 }

    hwOntSipVagSecondaryProxyPort OBJECT-TYPE
        SYNTAX Integer32 (0..65535)
        MAX-ACCESS read-write
        STATUS current
        DESCRIPTION
            "The port of secondary proxy server. "
        ::= { hwOntSipVagEntry 7 }

    hwOntSipVagRegisterPort OBJECT-TYPE
        SYNTAX Integer32 (0..65535)
        MAX-ACCESS read-write
        STATUS current
        DESCRIPTION
            "The port of register server. It is invalid For EPON ONT when server type is IMS."
        ::= { hwOntSipVagEntry 8 }

    hwOntSipVagSecondaryRegisterUri OBJECT-TYPE
        SYNTAX OCTET STRING (SIZE (0..64))
        MAX-ACCESS read-write
        STATUS current
        DESCRIPTION
            "The URI of secondary register server. It is invalid For EPON ONT when server type is IMS."
        ::= { hwOntSipVagEntry 9 }

    hwOntSipVagSecondaryRegisterPort OBJECT-TYPE
        SYNTAX Integer32 (0..65535)
        MAX-ACCESS read-write
        STATUS current
        DESCRIPTION
            "The port of secondary register server. It is invalid For EPON ONT when server type is IMS. "
        ::= { hwOntSipVagEntry 10 }

    hwOntSipVagOutboundUri OBJECT-TYPE
        SYNTAX OCTET STRING (SIZE (0..64))
        MAX-ACCESS read-write
        STATUS current
        DESCRIPTION
            "The URI of outbound server. It is invalid For EPON ONT when server type is IMS."
        ::= { hwOntSipVagEntry 11 }

    hwOntSipVagOutboundPort OBJECT-TYPE
        SYNTAX Integer32 (0..65535)
        MAX-ACCESS read-write
        STATUS current
        DESCRIPTION
            "The port of outbound server. It is invalid For EPON ONT when server type is IMS."
        ::= { hwOntSipVagEntry 12 }

    hwOntSipVagHeartbeatMode OBJECT-TYPE
        SYNTAX INTEGER
            {
            disable(1),
            enable(2)
            }
        MAX-ACCESS read-write
        STATUS current
        DESCRIPTION
            "The heartbeat mode of ONT SIP agent.
            Options:
            1.disable(1)    -indicates disable heartbeat
            2.enable(2)     -indicates enable heartbeat
            "
        ::= { hwOntSipVagEntry 13 }

    hwOntSipVagHeartbeatCycle OBJECT-TYPE
        SYNTAX Integer32 (1..1000)
        MAX-ACCESS read-write
        STATUS current
        DESCRIPTION
            "The heartbeat cycle of ONT SIP agent."
        ::= { hwOntSipVagEntry 14 }

    hwOntSipVagHeartbeatCount OBJECT-TYPE
        SYNTAX Integer32 (1..30)
        MAX-ACCESS read-write
        STATUS current
        DESCRIPTION
            "The heartbeat count of ONT SIP agent."
        ::= { hwOntSipVagEntry 15 }

    hwOntSipVagProxyUri OBJECT-TYPE
        SYNTAX OCTET STRING (SIZE (0..64))
        MAX-ACCESS read-write
        STATUS current
        DESCRIPTION
            "The URI of proxy server."
        ::= { hwOntSipVagEntry 16 }

    hwOntSipVagRtpPortMin OBJECT-TYPE
        SYNTAX Integer32 (0..65535)
        MAX-ACCESS read-write
        STATUS current
        DESCRIPTION
            "The minimal port of media. It is valid for GPON ONT and invalid for EPON ONT."
        ::= { hwOntSipVagEntry 17 }

    hwOntSipVagRtpPortMax OBJECT-TYPE
        SYNTAX Integer32 (0..65535)
        MAX-ACCESS read-write
        STATUS current
        DESCRIPTION
            "The maximal port of media. It is valid for GPON ONT and invalid for EPON ONT."
     ::= { hwOntSipVagEntry 18 }

    hwOntSipVagRtpDscp OBJECT-TYPE
        SYNTAX Integer32 (0..63)
        MAX-ACCESS read-write
        STATUS current
        DESCRIPTION
            "The DSCP of media. It is valid for GPON ONT and invalid for EPON ONT."
        ::= { hwOntSipVagEntry 19 }

    hwOntSipVagSignalTransMode OBJECT-TYPE
        SYNTAX INTEGER
            {
            tcp(1),
            udp(2)
            }
        MAX-ACCESS read-write
        STATUS current
        DESCRIPTION
            "The transfer mode of signal. It is valid for GPON ONT and invalid for EPON ONT.
            Options:
            1.tcp(1)     -indicates tcp
            2.udp(2)     -indicates udp
            "
        ::= { hwOntSipVagEntry 20 }

    hwOntSipVagSignalPortId OBJECT-TYPE
        SYNTAX Integer32 (0..65535)
        MAX-ACCESS read-write
        STATUS current
        DESCRIPTION
            "The port ID of signal."
        ::= { hwOntSipVagEntry 21 }

    hwOntSipVagSignalDscp OBJECT-TYPE
        SYNTAX Integer32 (0..63)
        MAX-ACCESS read-write
        STATUS current
        DESCRIPTION
            "The DSCP of signal. It is valid for GPON ONT and invalid for EPON ONT."
        ::= { hwOntSipVagEntry 22 }

    hwOntSipVagRegisterUri OBJECT-TYPE
        SYNTAX OCTET STRING (SIZE (0..64))
        MAX-ACCESS read-write
        STATUS current
        DESCRIPTION
            "The URI of register server. It is invalid for EPON ONT when server type is IMS."
        ::= { hwOntSipVagEntry 23 }

    hwOntSipVagRegExpiration OBJECT-TYPE
        SYNTAX Integer32 (1..65534)
        MAX-ACCESS read-write
        STATUS current
        DESCRIPTION
            "The expiration of registration."
        ::= { hwOntSipVagEntry 24 }

    hwOntSipVagReRegStartTime OBJECT-TYPE
        SYNTAX Integer32 (1..65534)
        MAX-ACCESS read-write
        STATUS current
        DESCRIPTION
            "Registration rereg head start time. It is valid for GPON ONT and invalid for EPON ONT."
        ::= { hwOntSipVagEntry 25 }

    hwOntSipVagVoicemailUri OBJECT-TYPE
        SYNTAX OCTET STRING (SIZE (0..64))
        MAX-ACCESS read-write
        STATUS current
        DESCRIPTION
            "The URI of voicemail. It is valid for GPON ONT and invalid for EPON ONT."
        ::= { hwOntSipVagEntry 26 }

    hwOntSipVagVoicemailSubExpir OBJECT-TYPE
        SYNTAX Unsigned32 (1..4294967295)
        MAX-ACCESS read-write
        STATUS current
        DESCRIPTION
            "The subscrition expiration of voicemail. It is valid for GPON ONT and invalid for EPON ONT."
        ::= { hwOntSipVagEntry 27 }

    hwOntSipVagConfFactoryUri OBJECT-TYPE
        SYNTAX OCTET STRING (SIZE (0..64))
        MAX-ACCESS read-write
        STATUS current
        DESCRIPTION
            "The URI of conference factory. It is valid for GPON ONT and invalid for EPON ONT."
        ::= { hwOntSipVagEntry 28 }

    hwOntSipVagBridgedLineAgentUri OBJECT-TYPE
        SYNTAX OCTET STRING (SIZE (0..64))
        MAX-ACCESS read-write
        STATUS current
        DESCRIPTION
            "The URI of bridged line agent. It is valid for GPON ONT and invalid for EPON ONT."
        ::= { hwOntSipVagEntry 29 }

    hwOntSipVagUserAuthRealm OBJECT-TYPE
        SYNTAX OCTET STRING (SIZE (0..24))
        MAX-ACCESS read-write
        STATUS current
        DESCRIPTION
            "The auth realm. It is valid for GPON ONT and invalid for EPON ONT."
        ::= { hwOntSipVagEntry 30 }

     hwOntSipVagHomeDomain OBJECT-TYPE
        SYNTAX OCTET STRING (SIZE (0..64))
        MAX-ACCESS read-write
        STATUS current
        DESCRIPTION
            "The home domain. It is invalid for EPON ONT when server type is not IMS."
        ::= { hwOntSipVagEntry 31 }

    hwOntSipVagRowStatus OBJECT-TYPE
        SYNTAX RowStatus
        MAX-ACCESS read-create
        STATUS current
        DESCRIPTION
            "Options:
            1.active(1)          -indicates active
            2.notInService(2)    -indicates not in service
            3.notReady(3)        -indicates not ready
            4.createAndGo(4)     -indicates create and go
            5.createAndWait(5)   -indicates create and wait
            6.destroy(6)         -indicates destroy
            Only createAndGo(4) and destroy(6) is support Now."
        ::= { hwOntSipVagEntry 32 }

    hwOntSipVagServerType OBJECT-TYPE
        SYNTAX INTEGER
            {
            general(1),
            ims(2)
            }
        MAX-ACCESS read-write
        STATUS current
        DESCRIPTION
            "The server type. It is valid for EPON ONT and invalid for GPON ONT.
            Options:
            1.general(1)     -indicates general SIP server
            2.ims(2)         -indicates IMS
            Default:general(1)
            "
        ::= { hwOntSipVagEntry 33 }

    hwOntPotsPTPConfigTable OBJECT-TYPE
        SYNTAX SEQUENCE OF HwOntPotsPTPConfigEntry
        MAX-ACCESS not-accessible
        STATUS current
        DESCRIPTION
            "POTS PTP Electrical Attribute Table.
            The indexes of this table are hwVoiceIfIndex, hwVoiceOntIndex, hwVoiceOntPortIndex."
        ::= { hwVoipOntObjects 18 }

    hwOntPotsPTPConfigEntry OBJECT-TYPE
        SYNTAX HwOntPotsPTPConfigEntry
        MAX-ACCESS not-accessible
        STATUS current
        DESCRIPTION
            "POTS PTP Electrical Attribute Table.
            The indexes of this entry are hwVoiceIfIndex, hwVoiceOntIndex, hwVoiceOntPortIndex."
        INDEX { hwVoiceIfIndex, hwVoiceOntIndex, hwVoiceOntPortIndex }
        ::= { hwOntPotsPTPConfigTable 1 }

    HwOntPotsPTPConfigEntry ::=
        SEQUENCE {
            hwOntPotsPTPSendGain
                Integer32,
            hwOntPotsPTPRecvGain
                Integer32,
            hwOntPotsPTPImpedance
                Integer32,
            hwOntPotsPTPSignaling
                Integer32
         }

    hwOntPotsPTPSendGain OBJECT-TYPE
        SYNTAX Integer32 (1..37)
        MAX-ACCESS read-write
        STATUS current
        DESCRIPTION
            "Send Gain.
             1  : -12.0db
             2  : -11.5db
             3  : -11.0db
             4  : -10.5db
             5  : -10.0db
             6  : -9.5db
             7  : -9.0db
             8  : -8.5db
             9  : -8.0db
             10 : -7.5db
             11 : -7.0db
             12 : -6.5db
             13 : -6.0db
             14 : -5.5db
             15 : -5.0db
             16 : -4.5db
             17 : -4.0db
             18 : -3.5db
             19 : -3.0db
             20 : -2.5db
             21 : -2.0db
             22 : -1.5db
             23 : -1.0db
             24 : -0.5db
             25 :   0db
             26 : +0.5db
             27 : +1.0db
             28 : +1.5db
             29 : +2.0db
             30 : +2.5db
             31 : +3.0db
             32 : +3.5db
             33 : +4.0db
             34 : +4.5db
             35 : +5.0db
             36 : +5.5db
             37 : +6.0db"
        DEFVAL { 25 }
        ::= { hwOntPotsPTPConfigEntry 1 }

    hwOntPotsPTPRecvGain OBJECT-TYPE
        SYNTAX Integer32 (1..37)
        MAX-ACCESS read-write
        STATUS current
        DESCRIPTION
            "Recv Gain.
             1  : -12.0db
             2  : -11.5db
             3  : -11.0db
             4  : -10.5db
             5  : -10.0db
             6  : -9.5db
             7  : -9.0db
             8  : -8.5db
             9  : -8.0db
             10 : -7.5db
             11 : -7.0db
             12 : -6.5db
             13 : -6.0db
             14 : -5.5db
             15 : -5.0db
             16 : -4.5db
             17 : -4.0db
             18 : -3.5db
             19 : -3.0db
             20 : -2.5db
             21 : -2.0db
             22 : -1.5db
             23 : -1.0db
             24 : -0.5db
             25 :   0db
             26 : +0.5db
             27 : +1.0db
             28 : +1.5db
             29 : +2.0db
             30 : +2.5db
             31 : +3.0db
             32 : +3.5db
             33 : +4.0db
             34 : +4.5db
             35 : +5.0db
             36 : +5.5db
             37 : +6.0db"
        DEFVAL { 25 }
        ::= { hwOntPotsPTPConfigEntry 2 }

    hwOntPotsPTPImpedance OBJECT-TYPE
        SYNTAX Integer32 (1..76)
        MAX-ACCESS read-write
        STATUS current
        DESCRIPTION
            "Impedance.
            1: r-600 Ohms(1)
            2: r-900 Ohms(2)
            3: c1:150 nF-R1:750 Ohm-R2:270 Ohm(3)
            4: c1:115 nF-R1:820 Ohm-R2:220 Ohm(4)
            5: c1:230 nF-R1:1500 Ohm-R2:320 Ohm(5)
            65: Bureau machine in China(200+680|| 100nf)
            66: User Machine in China(200+560|| 100nf)
            67: Interface of Russian(150+510|| 47nf)
            68: (220+820|| 120nf )
            69: Interface of Brazil(800|| 50nf)
            70: Abandoned
            71: HK_BT3(Zin=370+620|| 310nf,Zload=600)
            72: HK_BT5(Zin=270+264|| 357nf+1434|| 265nf,Zload=600)
            73: BT1(Zin=87+1052||228nF+229||28.4nF,
                Zload=93+615||471nF+179||495nF+244||32nF)
            74: BT2(Zin=87+1052||228nF+229||28.4nF,
                Zload=270+264||357nF+1434||265nF)
            75: BT3(Zin=87+1052||228nF+229||28.4nF,
                Zload=164+162||363nF+1227||350nF)
            76: New Zealand(Zin=370+620|| 310nf)"
        DEFVAL { 3 }
        ::= { hwOntPotsPTPConfigEntry 3 }

    hwOntPotsPTPSignaling OBJECT-TYPE
        SYNTAX Integer32 (1..6)
        MAX-ACCESS read-write
        STATUS current
        DESCRIPTION
            "Pots side signaling.
             1: loopStart(1)
             2: groundStart(2)
             3: loopReverseBattery(3)
             4: coinFirst(4)
             5: dialToneFirst(5)
             6: multiParty(6)
            "
        DEFVAL { 1 }
        ::= { hwOntPotsPTPConfigEntry 4 }

    hwOntMgCTPConfigTable OBJECT-TYPE
        SYNTAX SEQUENCE OF HwOntMgCTPConfigEntry
        MAX-ACCESS not-accessible
        STATUS current
        DESCRIPTION
            "Ont H248 and MGCP PSTN CTP table.
            The indexes of this table are hwVoiceIfIndex,hwVoiceOntIndex,hwVoiceOntPortIndex"
        ::= { hwVoipOntObjects 19 }

    hwOntMgCTPConfigEntry OBJECT-TYPE
        SYNTAX HwOntMgCTPConfigEntry
        MAX-ACCESS not-accessible
        STATUS current
        DESCRIPTION
            "Ont H248 and MGCP PSTN CTP table.
            The indexes of this entry are hwVoiceIfIndex,hwVoiceOntIndex,hwVoiceOntPortIndex"
        INDEX { hwVoiceIfIndex,hwVoiceOntIndex,hwVoiceOntPortIndex }
        ::= { hwOntMgCTPConfigTable 1 }

    HwOntMgCTPConfigEntry ::=
        SEQUENCE {
            hwOntMgPstnCTPMgId
                Integer32,
            hwOntMgPstnCTPTerminalId
                OCTET STRING,
            hwOntMgPstnCTPCodecSelect
                INTEGER,
            hwOntMgPstnCTPOrder1stCodec
                Integer32,
            hwOntMgPstnCTPOrder1stPacketPeriod
                INTEGER,
            hwOntMgPstnCTPOrder1stSilenceFlag
                INTEGER,
            hwOntMgPstnCTPOrder2stCodec
                Integer32,
            hwOntMgPstnCTPOrder2stPacketPeriod
                INTEGER,
            hwOntMgPstnCTPOrder2stSilenceFlag
                INTEGER,
            hwOntMgPstnCTPOrder3stCodec
                Integer32,
            hwOntMgPstnCTPOrder3stPacketPeriod
                INTEGER,
            hwOntMgPstnCTPOrder3stSilenceFlag
                INTEGER,
            hwOntMgPstnCTPOrder4stCodec
                Integer32,
            hwOntMgPstnCTPOrder4stPacketPeriod
                INTEGER,
            hwOntMgPstnCTPOrder4stSilenceFlag
                INTEGER,
            hwOntMgPstnCTPRowStatus
                RowStatus
           }

    hwOntMgPstnCTPMgId OBJECT-TYPE
        SYNTAX Integer32 (1..32)
        MAX-ACCESS read-write
        STATUS current
        DESCRIPTION
            "The H.248 MG ID."
        ::= { hwOntMgCTPConfigEntry 1 }

    hwOntMgPstnCTPTerminalId OBJECT-TYPE
        SYNTAX OCTET STRING (SIZE (0..64))
        MAX-ACCESS read-write
        STATUS current
        DESCRIPTION
            "The terminal ID."
        ::= { hwOntMgCTPConfigEntry 2 }

    hwOntMgPstnCTPCodecSelect OBJECT-TYPE
        SYNTAX INTEGER
            {
            baseOnUser(1),
            baseOnMg(2)
            }
        MAX-ACCESS read-write
        STATUS current
        DESCRIPTION
            "Selecting codec configuration from MG or user. It is valid for GPON ONT and invalid for EPON ONT.
            Options:
            1.baseOnUser(1)  -indicates the codec is base-on-user
            2.baseOnMg(2)    -indicates the codec is base-on-mg
            Defalut: baseOnMg(2)
            "
        DEFVAL {  baseOnMg }
        ::= { hwOntMgCTPConfigEntry 3 }

    hwOntMgPstnCTPOrder1stCodec OBJECT-TYPE
        SYNTAX Integer32 (0..95|255)
        MAX-ACCESS read-write
        STATUS current
        DESCRIPTION
            "codec of order 1. It is valid for GPON ONT and invalid for EPON ONT.
            defalut: 8
            "
        DEFVAL { 8 }
        ::= { hwOntMgCTPConfigEntry 4 }

    hwOntMgPstnCTPOrder1stPacketPeriod OBJECT-TYPE
        SYNTAX INTEGER
            {
            time10ms(1),
            time15ms(2),
            time20ms(3),
            time25ms(4),
            time30ms(5)
            }
        MAX-ACCESS read-write
        STATUS current
        DESCRIPTION
            "packet period of order 1. It is valid for GPON ONT and invalid for EPON ONT.
            Options:
            1.time10ms(1)  -indicates the packet period is 10ms
            2.time15ms(2)  -indicates the packet period is 15ms
            3.time20ms(3)  -indicates the packet period is 20ms
            4.time25ms(4)  -indicates the packet period is 25ms
            5.time30ms(5)  -indicates the packet period is 30ms
            Defalut: time20ms(3)
            "
        DEFVAL { time20ms }
        ::= { hwOntMgCTPConfigEntry 5 }

    hwOntMgPstnCTPOrder1stSilenceFlag OBJECT-TYPE
        SYNTAX INTEGER
            {
            off(1),
            on(2)
            }
        MAX-ACCESS read-write
        STATUS current
        DESCRIPTION
            "silence suppression of order 1. It is valid for GPON ONT and invalid for EPON ONT.
            Options:
            1.off(1)    -indicates the silence suppression is off
            2.on(2)     -indicates the silence suppression is on
            Defalut: off(1)
            "
        DEFVAL { off }
        ::= { hwOntMgCTPConfigEntry 6 }

    hwOntMgPstnCTPOrder2stCodec OBJECT-TYPE
        SYNTAX Integer32 (0..95|255)
        MAX-ACCESS read-write
        STATUS current
        DESCRIPTION
            "codec of order 2. It is valid for GPON ONT and invalid for EPON ONT.
            defalut: 0
            "
        DEFVAL { 0 }
        ::= { hwOntMgCTPConfigEntry 7 }

    hwOntMgPstnCTPOrder2stPacketPeriod OBJECT-TYPE
        SYNTAX INTEGER
            {
            time10ms(1),
            time15ms(2),
            time20ms(3),
            time25ms(4),
            time30ms(5)
            }
        MAX-ACCESS read-write
        STATUS current
        DESCRIPTION
            "packet period of order 2. It is valid for GPON ONT and invalid for EPON ONT.
            Options:
            1.time10ms(1)  -indicates the packet period is 10ms
            2.time15ms(2)  -indicates the packet period is 15ms
            3.time20ms(3)  -indicates the packet period is 20ms
            4.time25ms(4)  -indicates the packet period is 25ms
            5.time30ms(5)  -indicates the packet period is 30ms
            Defalut: time20ms(3)
            "
        DEFVAL { time20ms }
        ::= { hwOntMgCTPConfigEntry 8 }

    hwOntMgPstnCTPOrder2stSilenceFlag OBJECT-TYPE
        SYNTAX INTEGER
            {
            off(1),
            on(2)
            }
        MAX-ACCESS read-write
        STATUS current
        DESCRIPTION
            "silence suppression of order 2. It is valid for GPON ONT and invalid for EPON ONT.
            Options:
            1.off(1)    -indicates the silence suppression is off
            2.on(2)     -indicates the silence suppression is on
            Defalut: off(1)
            "
        DEFVAL { off }
        ::= { hwOntMgCTPConfigEntry 9 }

    hwOntMgPstnCTPOrder3stCodec OBJECT-TYPE
        SYNTAX Integer32 (0..95|255)
        MAX-ACCESS read-write
        STATUS current
        DESCRIPTION
            "codec of order 3. It is valid for GPON ONT and invalid for EPON ONT.
            defalut: 18
            "
        DEFVAL { 18 }
        ::= { hwOntMgCTPConfigEntry 10 }

    hwOntMgPstnCTPOrder3stPacketPeriod OBJECT-TYPE
        SYNTAX INTEGER
            {
            time10ms(1),
            time15ms(2),
            time20ms(3),
            time25ms(4),
            time30ms(5)
            }
        MAX-ACCESS read-write
        STATUS current
        DESCRIPTION
            "packet period of order 3. It is valid for GPON ONT and invalid for EPON ONT.
            Options:
            1.time10ms(1)  -indicates the packet period is 10ms
            2.time15ms(2)  -indicates the packet period is 15ms
            3.time20ms(3)  -indicates the packet period is 20ms
            4.time25ms(4)  -indicates the packet period is 25ms
            5.time30ms(5)  -indicates the packet period is 30ms
            Defalut: time20ms(3)
            "
        DEFVAL { time20ms }
        ::= { hwOntMgCTPConfigEntry 11 }

    hwOntMgPstnCTPOrder3stSilenceFlag OBJECT-TYPE
        SYNTAX INTEGER
            {
            off(1),
            on(2)
            }
        MAX-ACCESS read-write
        STATUS current
        DESCRIPTION
            "silence suppression of order 3. It is valid for GPON ONT and invalid for EPON ONT.
            Options:
            1.off(1)    -indicates the silence suppression is off
            2.on(2)     -indicates the silence suppression is on
            Defalut: off(1)
            "
        DEFVAL { off }
        ::= { hwOntMgCTPConfigEntry 12 }

    hwOntMgPstnCTPOrder4stCodec OBJECT-TYPE
        SYNTAX Integer32 (0..95|255)
        MAX-ACCESS read-write
        STATUS current
        DESCRIPTION
            "codec of order 4. It is valid for GPON ONT and invalid for EPON ONT.
            defalut: 9
            "
        DEFVAL { 9 }
        ::= { hwOntMgCTPConfigEntry 13 }

    hwOntMgPstnCTPOrder4stPacketPeriod OBJECT-TYPE
        SYNTAX INTEGER
            {
            time10ms(1),
            time15ms(2),
            time20ms(3),
            time25ms(4),
            time30ms(5)
            }
        MAX-ACCESS read-write
        STATUS current
        DESCRIPTION
            "packet period of order 4. It is valid for GPON ONT and invalid for EPON ONT.
            Options:
            1.time10ms(1)  -indicates the packet period is 10ms
            2.time15ms(2)  -indicates the packet period is 15ms
            3.time20ms(3)  -indicates the packet period is 20ms
            4.time25ms(4)  -indicates the packet period is 25ms
            5.time30ms(5)  -indicates the packet period is 30ms
            Defalut: time20ms(3)
            "
        DEFVAL { time20ms }
        ::= { hwOntMgCTPConfigEntry 14 }

    hwOntMgPstnCTPOrder4stSilenceFlag OBJECT-TYPE
        SYNTAX INTEGER
            {
            off(1),
            on(2)
            }
        MAX-ACCESS read-write
        STATUS current
        DESCRIPTION
            "silence suppression of order 4. It is valid for GPON ONT and invalid for EPON ONT.
            Options:
            1.off(1)    -indicates the silence suppression is off
            2.on(2)     -indicates the silence suppression is on
            Defalut: off(1)
            "
        DEFVAL { off }
        ::= { hwOntMgCTPConfigEntry 15 }

    hwOntMgPstnCTPRowStatus OBJECT-TYPE
        SYNTAX RowStatus
        MAX-ACCESS read-create
        STATUS current
        DESCRIPTION
            "Options:
            1.active(1)          -indicates active
            2.notInService(2)    -indicates not in service
            3.notReady(3)        -indicates not ready
            4.createAndGo(4)     -indicates create and go
            5.createAndWait(5)   -indicates create and wait
            6.destroy(6)         -indicates destroy
            Only 4 and 6 is support Now."
        ::= { hwOntMgCTPConfigEntry 16 }

    --  1.3.6.1.4.1.2011.6.36.11.20
    -- 1.3.6.1.4.1.2011.6.36.11.20
    hwOntSIPCTPConfigTable OBJECT-TYPE
        SYNTAX SEQUENCE OF HwOntSIPCTPConfigEntry
        MAX-ACCESS not-accessible
        STATUS current
        DESCRIPTION
            "SIP PSTN CTP Config Table.
            The indexes of this table are hwVoiceIfIndex, hwVoiceOntIndex, hwVoiceOntPortIndex."
        ::= { hwVoipOntObjects 20 }

    --  1.3.6.1.4.1.2011.6.36.11.20.1
    -- 1.3.6.1.4.1.2011.6.36.11.20.1
    hwOntSIPCTPConfigEntry OBJECT-TYPE
        SYNTAX HwOntSIPCTPConfigEntry
        MAX-ACCESS not-accessible
        STATUS current
        DESCRIPTION
            "SIP PSTN CTP Config Table.
            The indexes of this entry are hwVoiceIfIndex, hwVoiceOntIndex, hwVoiceOntPortIndex."
        INDEX { hwVoiceIfIndex, hwVoiceOntIndex, hwVoiceOntPortIndex }
        ::= { hwOntSIPCTPConfigTable 1 }

    HwOntSIPCTPConfigEntry ::=
        SEQUENCE {
            hwOntSIPCTPDigitmapTemplateIndex
                Integer32,
            hwOntSIPCTPDigitmapTemplateName
                OCTET STRING,
            hwOntSIPCTPMgID
                Integer32,
            hwOntSIPCTPTelno
                OCTET STRING,
            hwOntSIPCTPUsername
                OCTET STRING,
            hwOntSIPCTPPassword
                OCTET STRING,
            hwOntSIPCTPNewServiceRight
                BITS,
            hwOntSIPCTPHotlineUri
                OCTET STRING,
            hwOntSIPPstnCTPCodecSelect
                INTEGER,
            hwOntSIPPstnCTPOrder1stCodec
                Integer32,
            hwOntSIPPstnCTPOrder1stPacketPeriod
                INTEGER,
            hwOntSIPPstnCTPOrder1stSilenceFlag
                INTEGER,
            hwOntSIPPstnCTPOrder2stCodec
                Integer32,
            hwOntSIPPstnCTPOrder2stPacketPeriod
                INTEGER,
            hwOntSIPPstnCTPOrder2stSilenceFlag
                INTEGER,
            hwOntSIPPstnCTPOrder3stCodec
                Integer32,
            hwOntSIPPstnCTPOrder3stPacketPeriod
                INTEGER,
            hwOntSIPPstnCTPOrder3stSilenceFlag
                INTEGER,
            hwOntSIPPstnCTPOrder4stCodec
                Integer32,
            hwOntSIPPstnCTPOrder4stPacketPeriod
                INTEGER,
            hwOntSIPPstnCTPOrder4stSilenceFlag
                INTEGER,
            hwOntSIPCTPRowStatus
                RowStatus
         }

    --  1.3.6.1.4.1.2011.6.36.11.20.1.1
    -- 1.3.6.1.4.1.2011.6.36.11.20.1.1
    hwOntSIPCTPDigitmapTemplateIndex OBJECT-TYPE
        SYNTAX Integer32 (1..64)
        MAX-ACCESS read-write
        STATUS current
        DESCRIPTION
            "DigitalMap profile index which is bound to POTS user.
            If only set digitmap profile(including hwOntSIPCTPDigitmapTemplateIndex and hwOntSIPCTPDigitmapTemplateName) for EPON ONT,
            hwVoiceOntPortIndex is invalid(means that all users of the EPON ONT will be bind to the specify digitmap profile)."
        DEFVAL { 1 }
        ::= { hwOntSIPCTPConfigEntry 1 }

    --  1.3.6.1.4.1.2011.6.36.11.20.1.2
    -- 1.3.6.1.4.1.2011.6.36.11.20.1.2
    hwOntSIPCTPDigitmapTemplateName OBJECT-TYPE
        SYNTAX OCTET STRING (SIZE (0..32))
        MAX-ACCESS read-write
        STATUS current
        DESCRIPTION
            "DigitalMap profile name which is bound to POTS user.
            If only set digitmap profile(including hwOntSIPCTPDigitmapTemplateIndex and hwOntSIPCTPDigitmapTemplateName) for EPON ONT,
            hwVoiceOntPortIndex is invalid(means that all users of the EPON ONT will be bind to the specify digitmap profile)."
        ::= { hwOntSIPCTPConfigEntry 2 }

    hwOntSIPCTPMgID OBJECT-TYPE
        SYNTAX Integer32 (1..32)
        MAX-ACCESS read-write
        STATUS current
        DESCRIPTION
            "The SIP MG ID."
        ::= { hwOntSIPCTPConfigEntry 3 }

    hwOntSIPCTPTelno OBJECT-TYPE
        SYNTAX OCTET STRING (SIZE (0..64))
        MAX-ACCESS read-write
        STATUS current
        DESCRIPTION
            "SIP user's telephone number of ONT."
        ::= { hwOntSIPCTPConfigEntry 4 }

    --  1.3.6.1.4.1.2011.6.36.11.20.1.5
    -- 1.3.6.1.4.1.2011.6.36.11.20.1.5
    hwOntSIPCTPUsername OBJECT-TYPE
        SYNTAX OCTET STRING (SIZE (0..50))
        MAX-ACCESS read-write
        STATUS current
        DESCRIPTION
            "SIP user's name."
        ::= { hwOntSIPCTPConfigEntry 5 }

    --  1.3.6.1.4.1.2011.6.36.11.20.1.6
    -- 1.3.6.1.4.1.2011.6.36.11.20.1.6
    hwOntSIPCTPPassword OBJECT-TYPE
        SYNTAX OCTET STRING (SIZE (0..24))
        MAX-ACCESS read-write
        STATUS current
        DESCRIPTION
            "SIP user's password."
        ::= { hwOntSIPCTPConfigEntry 6 }

    --  1.3.6.1.4.1.2011.6.36.11.20.1.7
    -- 1.3.6.1.4.1.2011.6.36.11.20.1.7
    hwOntSIPCTPNewServiceRight OBJECT-TYPE
        SYNTAX BITS
            {
            callWaiting(0),
            threeParty(1),
            callTransfer(2),
            callHold(3),
            callPark(4),
            doNotDisturb(5),
            conference(6),
            messageWaitingIndication(7),
            hotline(8),
            hotdelay(9)
            }
        MAX-ACCESS read-write
        STATUS current
        DESCRIPTION
            "SIP user's service right of ONT. It is valid for GPON ONT and invalid for EPON ONT.
            Options:
            0.callWaiting(0),
            1.threeParty(1),
            2.callTransfer(2),
            3.callHold(3),
            4.callPark(4),
            5.doNotDisturb(5),
            6.conference(6),
            7.messageWaitingIndication(7),
            8.hotline(8),
            9.hotdelay(9)
            "
        ::= { hwOntSIPCTPConfigEntry 7 }

    --  1.3.6.1.4.1.2011.6.36.11.20.1.8
    -- 1.3.6.1.4.1.2011.6.36.11.20.1.8
    hwOntSIPCTPHotlineUri OBJECT-TYPE
        SYNTAX OCTET STRING (SIZE (0..32))
        MAX-ACCESS read-write
        STATUS current
        DESCRIPTION
            "SIP user's hot line number(URI). It is valid for GPON ONT and invalid for EPON ONT."
        ::= { hwOntSIPCTPConfigEntry 8 }

    hwOntSIPPstnCTPCodecSelect OBJECT-TYPE
        SYNTAX INTEGER
            {
            baseOnUser(1),
            baseOnMg(2)
            }
        MAX-ACCESS read-write
        STATUS current
        DESCRIPTION
            "Ont SIP Pstn user's selected codec. It is valid for GPON ONT and invalid for EPON ONT.
            Options:
            1.baseOnUser(1)  -indicates the codec is base-on-user
            2.baseOnMg(2)    -indicates the codec is base-on-mg
            Defalut: baseOnMg(2)
            "
        DEFVAL { baseOnMg }
        ::= { hwOntSIPCTPConfigEntry 9 }

    hwOntSIPPstnCTPOrder1stCodec OBJECT-TYPE
        SYNTAX Integer32 (0..95|255)
        MAX-ACCESS read-write
        STATUS current
        DESCRIPTION
            "codec of order 1. It is valid for GPON ONT and invalid for EPON ONT.
            defalut: 8
            "
        DEFVAL { 8 }
        ::= { hwOntSIPCTPConfigEntry 10 }

    hwOntSIPPstnCTPOrder1stPacketPeriod OBJECT-TYPE
        SYNTAX INTEGER
            {
            time10ms(1),
            time15ms(2),
            time20ms(3),
            time25ms(4),
            time30ms(5)
            }
        MAX-ACCESS read-write
        STATUS current
        DESCRIPTION
            "packet period of order 1. It is valid for GPON ONT and invalid for EPON ONT.
            Options:
            1.time10ms(1)  -indicates the packet period is 10ms
            2.time15ms(2)  -indicates the packet period is 15ms
            3.time20ms(3)  -indicates the packet period is 20ms
            4.time25ms(4)  -indicates the packet period is 25ms
            5.time30ms(5)  -indicates the packet period is 30ms
            Defalut: time20ms(3)
            "
        DEFVAL { time20ms }
        ::= { hwOntSIPCTPConfigEntry 11 }

    hwOntSIPPstnCTPOrder1stSilenceFlag OBJECT-TYPE
        SYNTAX INTEGER
            {
            off(1),
            on(2)
            }
        MAX-ACCESS read-write
        STATUS current
        DESCRIPTION
            "silence suppression of order 1. It is valid for GPON ONT and invalid for EPON ONT.
            Options:
            1.off(1)    -indicates the silence suppression is off
            2.on(2)     -indicates the silence suppression is on
            Defalut: off(1)
            "
        DEFVAL { off }
        ::= { hwOntSIPCTPConfigEntry 12 }

    hwOntSIPPstnCTPOrder2stCodec OBJECT-TYPE
        SYNTAX Integer32 (0..95|255)
        MAX-ACCESS read-write
        STATUS current
        DESCRIPTION
            "codec of order 2. It is valid for GPON ONT and invalid for EPON ONT.
            defalut: 0
            "
        DEFVAL { 0 }
        ::= { hwOntSIPCTPConfigEntry 13 }

    hwOntSIPPstnCTPOrder2stPacketPeriod OBJECT-TYPE
        SYNTAX INTEGER
            {
            time10ms(1),
            time15ms(2),
            time20ms(3),
            time25ms(4),
            time30ms(5)
            }
        MAX-ACCESS read-write
        STATUS current
        DESCRIPTION
            "packet period of order 2. It is valid for GPON ONT and invalid for EPON ONT.
            Options:
            1.time10ms(1)  -indicates the packet period is 10ms
            2.time15ms(2)  -indicates the packet period is 15ms
            3.time20ms(3)  -indicates the packet period is 20ms
            4.time25ms(4)  -indicates the packet period is 25ms
            5.time30ms(5)  -indicates the packet period is 30ms
            Defalut: time20ms(3)
            "
        DEFVAL { time20ms }
        ::= { hwOntSIPCTPConfigEntry 14 }

    hwOntSIPPstnCTPOrder2stSilenceFlag OBJECT-TYPE
        SYNTAX INTEGER
            {
            off(1),
            on(2)
            }
        MAX-ACCESS read-write
        STATUS current
        DESCRIPTION
            "silence suppression of order 2. It is valid for GPON ONT and invalid for EPON ONT.
            Options:
            1.off(1)    -indicates the silence suppression is off
            2.on(2)     -indicates the silence suppression is on
            Defalut: off(1)
            "
        DEFVAL { off }
        ::= { hwOntSIPCTPConfigEntry 15 }

    hwOntSIPPstnCTPOrder3stCodec OBJECT-TYPE
        SYNTAX Integer32 (0..95|255)
        MAX-ACCESS read-write
        STATUS current
        DESCRIPTION
            "codec of order 3. It is valid for GPON ONT and invalid for EPON ONT.
            defalut: 18
            "
        DEFVAL { 18 }
        ::= { hwOntSIPCTPConfigEntry 16 }

    hwOntSIPPstnCTPOrder3stPacketPeriod OBJECT-TYPE
        SYNTAX INTEGER
            {
            time10ms(1),
            time15ms(2),
            time20ms(3),
            time25ms(4),
            time30ms(5)
            }
        MAX-ACCESS read-write
        STATUS current
        DESCRIPTION
            "packet period of order 3. It is valid for GPON ONT and invalid for EPON ONT.
            Options:
            1.time10ms(1)  -indicates the packet period is 10ms
            2.time15ms(2)  -indicates the packet period is 15ms
            3.time20ms(3)  -indicates the packet period is 20ms
            4.time25ms(4)  -indicates the packet period is 25ms
            5.time30ms(5)  -indicates the packet period is 30ms
            Defalut: time20ms(3)
            "
        DEFVAL { time20ms }
        ::= { hwOntSIPCTPConfigEntry 17 }

    hwOntSIPPstnCTPOrder3stSilenceFlag OBJECT-TYPE
        SYNTAX INTEGER
            {
            off(1),
            on(2)
            }
        MAX-ACCESS read-write
        STATUS current
        DESCRIPTION
            "silence suppression of order 3. It is valid for GPON ONT and invalid for EPON ONT.
            Options:
            1.off(1)    -indicates the silence suppression is off
            2.on(2)     -indicates the silence suppression is on
            Defalut: off(1)
            "
        DEFVAL { off }
        ::= { hwOntSIPCTPConfigEntry 18 }

    hwOntSIPPstnCTPOrder4stCodec OBJECT-TYPE
        SYNTAX Integer32 (0..95|255)
        MAX-ACCESS read-write
        STATUS current
        DESCRIPTION
            "codec of order 4. It is valid for GPON ONT and invalid for EPON ONT.
            defalut: 9
            "
        DEFVAL { 9 }
        ::= { hwOntSIPCTPConfigEntry 19 }

    hwOntSIPPstnCTPOrder4stPacketPeriod OBJECT-TYPE
        SYNTAX INTEGER
            {
            time10ms(1),
            time15ms(2),
            time20ms(3),
            time25ms(4),
            time30ms(5)
            }
        MAX-ACCESS read-write
        STATUS current
        DESCRIPTION
            "packet period of order 4. It is valid for GPON ONT and invalid for EPON ONT.
            Options:
            1.time10ms(1)  -indicates the packet period is 10ms
            2.time15ms(2)  -indicates the packet period is 15ms
            3.time20ms(3)  -indicates the packet period is 20ms
            4.time25ms(4)  -indicates the packet period is 25ms
            5.time30ms(5)  -indicates the packet period is 30ms
            Defalut: time20ms(3)
            "
        DEFVAL { time20ms }
        ::= { hwOntSIPCTPConfigEntry 20 }

    hwOntSIPPstnCTPOrder4stSilenceFlag OBJECT-TYPE
        SYNTAX INTEGER
            {
            off(1),
            on(2)
            }
        MAX-ACCESS read-write
        STATUS current
        DESCRIPTION
            "silence suppression of order 4. It is valid for GPON ONT and invalid for EPON ONT.
            Options:
            1.off(1)    -indicates the silence suppression is off
            2.on(2)     -indicates the silence suppression is on
            Defalut: off(1)
            "
        DEFVAL { off }
        ::= { hwOntSIPCTPConfigEntry 21 }

    hwOntSIPCTPRowStatus OBJECT-TYPE
        SYNTAX RowStatus
        MAX-ACCESS read-create
        STATUS current
        DESCRIPTION
            "Options:
            1.active(1)          -indicates active
            2.notInService(2)    -indicates not in service
            3.notReady(3)        -indicates not ready
            4.createAndGo(4)     -indicates create and go
            5.createAndWait(5)   -indicates create and wait
            6.destroy(6)         -indicates destroy
            Only 4 and 6 is support Now."
        ::= { hwOntSIPCTPConfigEntry 22 }

    hwOntDigitMapBodyTable OBJECT-TYPE
        SYNTAX SEQUENCE OF HwOntDigitMapBodyEntry
        MAX-ACCESS not-accessible
        STATUS current
        DESCRIPTION
            "The digitmap body table.
            The indexes of this table are hwOntDigitMapTemplateIndex"
        ::= { hwVoipOntObjects 21 }

    hwOntDigitMapBodyEntry OBJECT-TYPE
        SYNTAX HwOntDigitMapBodyEntry
        MAX-ACCESS not-accessible
        STATUS current
        DESCRIPTION
            "The digitmap body table.
             The indexes of this entry are hwOntDigitMapTemplateIndex"
        INDEX { hwOntDigitMapTemplateIndex }
        ::= { hwOntDigitMapBodyTable 1 }

    HwOntDigitMapBodyEntry ::=
        SEQUENCE {
            hwOntDigitMapBodyLength
                Integer32,
            hwOntDigitMapBodySliceNo
                Integer32,
            hwOntDigitMapBodyString
                OCTET STRING
            }

    hwOntDigitMapBodyLength OBJECT-TYPE
        SYNTAX Integer32 (0..65535)
        MAX-ACCESS read-write
        STATUS current
        DESCRIPTION
            "The digitmap body length."
        ::= { hwOntDigitMapBodyEntry 1 }

    hwOntDigitMapBodySliceNo OBJECT-TYPE
        SYNTAX Integer32 (0..65535)
        MAX-ACCESS read-write
        STATUS current
        DESCRIPTION
            "The digitmap body slice.
             The high 8bits indicates total slice number.
             The low 8bits indicates current slice serial number(begin with 0)."
        ::= { hwOntDigitMapBodyEntry 2 }

    hwOntDigitMapBodyString OBJECT-TYPE
        SYNTAX OCTET STRING (SIZE (0..8191))
        MAX-ACCESS read-write
        STATUS current
        DESCRIPTION
            "The digitmap body string."
        ::= { hwOntDigitMapBodyEntry 3 }

    hwOntRecentCallRecordsTable OBJECT-TYPE
        SYNTAX SEQUENCE OF HwOntRecentCallRecordsEntry
        MAX-ACCESS not-accessible
        STATUS current
        DESCRIPTION
            "The ONT recent call records table.
            The indexes of this table are hwVoiceIfIndex, hwVoiceOntIndex, hwVoiceOntPortIndex, hwOntRecentCallRecordIndex"
        ::= { hwVoipOntObjects 22 }

    hwOntRecentCallRecordsEntry OBJECT-TYPE
        SYNTAX HwOntRecentCallRecordsEntry
        MAX-ACCESS not-accessible
        STATUS current
        DESCRIPTION
            "The ONT recent call records table.
             The indexes of this entry are hwVoiceIfIndex, hwVoiceOntIndex, hwVoiceOntPortIndex, hwOntRecentCallRecordIndex"
        INDEX { hwVoiceIfIndex, hwVoiceOntIndex, hwVoiceOntPortIndex, hwOntRecentCallRecordIndex }
        ::= { hwOntRecentCallRecordsTable 1 }

    HwOntRecentCallRecordsEntry ::=
        SEQUENCE {
            hwOntRecentCallRecordIndex
                Integer32,
            hwOntRecentCallStartDate
                Unsigned32,
            hwOntRecentCallStartTime
                Unsigned32,
            hwOntRecentCallDuration
                Integer32,
            hwOntRecentCallType
                INTEGER,
            hwOntRecentCallCodec
                Integer32,
            hwOntRecentCallerNumber
                OCTET STRING,
            hwOntRecentCalleeNumber
                OCTET STRING,
            hwOntRecentCallPacketsSent
                Integer32,
            hwOntRecentCallPacketsReceived
                Integer32,
            hwOntRecentCallPacketsLost
                Integer32,
            hwOntRecentCallRoundTripDelay
                Integer32,
            hwOntRecentCallRcvInterArrivJitter
                Integer32,
            hwOntRecentCallMosLq
                Integer32
            }

    hwOntRecentCallRecordIndex OBJECT-TYPE
        SYNTAX Integer32 (1..20)
        MAX-ACCESS not-accessible
        STATUS current
        DESCRIPTION
            "Indicates the index of the call record. If the index is 1, it indicates the last call that has ended on the port.
            If this index is 2, it indicates the penultimate call that has ended on the port."
        ::= { hwOntRecentCallRecordsEntry 1 }

    hwOntRecentCallStartDate OBJECT-TYPE
        SYNTAX Unsigned32
        MAX-ACCESS read-only
        STATUS current
        DESCRIPTION
            "Indicates the start date of the call. 'AAAABBCC' indicates the date, among which, 'AAAA' indicates the year, 'BB' indicates the month, and 'CC' indicates the day."
        ::= { hwOntRecentCallRecordsEntry 2 }

    hwOntRecentCallStartTime OBJECT-TYPE
        SYNTAX Unsigned32
        MAX-ACCESS read-only
        STATUS current
        DESCRIPTION
            "Indicates the start time of the call. 'AABBCCDD' indicates the time, among which, 'AA' indicates the hour, 'BB' indicates the minute, 'CC' indicates the second, 'DD' is unused and reserved. "
        ::= { hwOntRecentCallRecordsEntry 3 }

    hwOntRecentCallDuration OBJECT-TYPE
        SYNTAX Integer32
        MAX-ACCESS read-only
        STATUS current
        DESCRIPTION
            "Indicates the duration of the call (unit: second)."
        ::= { hwOntRecentCallRecordsEntry 4 }

    hwOntRecentCallType OBJECT-TYPE
        SYNTAX INTEGER
            {
                outgoingCall(1),
                incomingCall(2)
            }
        MAX-ACCESS read-only
        STATUS current
        DESCRIPTION
            "Indicates the type of the call.
            Options:
            1.outgoingCall(1)    -indicates the call is a outgoing call
            2.incomingCall(2)    -indicates the call is a incoming call
            "
        ::= { hwOntRecentCallRecordsEntry 5 }

    hwOntRecentCallCodec OBJECT-TYPE
        SYNTAX Integer32 (0..18|250)
        MAX-ACCESS read-only
        STATUS current
        DESCRIPTION
            "Indicates the codec used in the call. Codec points are assigned as follows:
             0: G.711U
             1: Reserved
             2: G.726
             3: GSM
             4: G.723
             5: DVI4-8K
             6: DVI4-16K
             7: LPC
             8: G.711A
             9: G.722
             10: L16-2 channels
             11: L16-1 channels
             12: QCELP
             13: CN
             14: MPA
             15: G.728
             16: DVI4-11K
             17: DVI4-22K
             18: G.729
             250: T.38
             "
        ::= { hwOntRecentCallRecordsEntry 6 }

    hwOntRecentCallerNumber OBJECT-TYPE
        SYNTAX OCTET STRING  (SIZE (0..32))
        MAX-ACCESS read-only
        STATUS current
        DESCRIPTION
            "Indicates the calling number."
        ::= { hwOntRecentCallRecordsEntry 7 }

    hwOntRecentCalleeNumber OBJECT-TYPE
        SYNTAX OCTET STRING  (SIZE (0..32))
        MAX-ACCESS read-only
        STATUS current
        DESCRIPTION
            "Indicates the called number."
        ::= { hwOntRecentCallRecordsEntry 8 }

    hwOntRecentCallPacketsSent OBJECT-TYPE
        SYNTAX Integer32
        MAX-ACCESS read-only
        STATUS current
        DESCRIPTION
            "Indicates the number of packets sent during the call.."
        ::= { hwOntRecentCallRecordsEntry 9 }

    hwOntRecentCallPacketsReceived OBJECT-TYPE
        SYNTAX Integer32
        MAX-ACCESS read-only
        STATUS current
        DESCRIPTION
            "Indicates the number of packets received during the call."
        ::= { hwOntRecentCallRecordsEntry 10 }

    hwOntRecentCallPacketsLost OBJECT-TYPE
        SYNTAX Integer32
        MAX-ACCESS read-only
        STATUS current
        DESCRIPTION
            "Indicates the number of packets discarded during the call."
        ::= { hwOntRecentCallRecordsEntry 11 }

    hwOntRecentCallRoundTripDelay OBJECT-TYPE
        SYNTAX Integer32
        MAX-ACCESS read-only
        STATUS current
        DESCRIPTION
            "Indicates the loop delay of the call (unit: ms)."
        ::= { hwOntRecentCallRecordsEntry 12 }

    hwOntRecentCallRcvInterArrivJitter OBJECT-TYPE
        SYNTAX Integer32
        MAX-ACCESS read-only
        STATUS current
        DESCRIPTION
            "Indicates the jitter of the call in the Rx direction (unit: ms)."
        ::= { hwOntRecentCallRecordsEntry 13 }

    hwOntRecentCallMosLq OBJECT-TYPE
        SYNTAX Integer32
        MAX-ACCESS read-only
        STATUS current
        DESCRIPTION
            "Indicates the average MOS value of the call (this value has been increased by 10 times)."
        ::= { hwOntRecentCallRecordsEntry 14 }

    hwOntVoipAlarmCfgTable OBJECT IDENTIFIER ::= { hwVoipOntObjects 23 }

    hwOntAlarmMassSipAlarmThreshold OBJECT-TYPE
        SYNTAX Integer32 (10..1000)
        MAX-ACCESS read-write
        STATUS current
        DESCRIPTION
            "Indicates the threshold for mass SIP alarm.
             Default: 100"
        ::= { hwOntVoipAlarmCfgTable 1 }

    hwOntVoipSingleAlarmSwitch OBJECT-TYPE
        SYNTAX INTEGER
            {
            disable(1),
            enable(2)
            }
        MAX-ACCESS read-write
        STATUS current
        DESCRIPTION
            "Indicates the switch for single ONT voip alarm.
            Options:
            1.disable(1)             -indicates the single alarm switch is off
            2.enable(2)              -indicates the single alarm switch is on
            Default:disable(1)
            "
        DEFVAL { disable }
        ::= { hwOntVoipAlarmCfgTable 2 }

    hwOntVoipMassAlarmSwitch OBJECT-TYPE
       SYNTAX Integer32
           {
           disable(1),
           enable(2)
           }
       MAX-ACCESS read-write
       STATUS current
       DESCRIPTION
           "Indicates the switch for mass ONT voip alarm
           Options:
           1.disable(1)             -indicates the mass alarm switch is off
           2.enable(2)              -indicates the mass alarm switch is on
           Default:disable(1)
		   "
       DEFVAL { disable }
       ::= { hwOntVoipAlarmCfgTable 3 }

    hwOntVoipMassEventSwitch OBJECT-TYPE
       SYNTAX Integer32
           {
           disable(1),
           enable(2)
           }
       MAX-ACCESS read-write
       STATUS current
       DESCRIPTION
           "Indicates the switch for mass ONT voip alarm event in 15 minutes
           Options:
           1.disable(1)             -indicates the mass event switch is off
           2.enable(2)              -indicates the mass event switch is on
           Default:disable(1)
		   "
       DEFVAL { disable }
       ::= { hwOntVoipAlarmCfgTable 4 }

    hwOntVoipMassEventContent OBJECT-TYPE
        SYNTAX Integer32 (1..15)
        MAX-ACCESS read-write
        STATUS current
        DESCRIPTION
            "Indicates the content for mass ONT voip alarm event in 15 minutes.
			The mass event content list:
			1  -indicates MG interface fault
			2  -indicates SIP user register timeout
			3  -indicates MG interface fault, SIP user register timeout
			4  -indicates SIP user register fail
			5  -indicates MG interface fault, SIP user register fail
			6  -indicates SIP user register timeout, SIP user register fail
			7  -indicates MG interface fault, SIP user register timeout, SIP user register fail
			8  -indicates SIP user authenticate fail
			9  -indicates MG interface fault, SIP user authenticate fail
			10 -indicates SIP user register timeout, SIP user authenticate fail
			11 -indicates MG interface fault, SIP user register timeout, SIP user authenticate fail
			12 -indicates SIP user register fail, SIP user authenticate fail
			13 -indicates MG interface fault, SIP user register fail, SIP user authenticate fail
			14 -indicates SIP user register timeout, SIP user register fail, SIP user authenticate fail
			15 -indicates MG interface fault, SIP user register timeout, SIP user register fail, SIP user authenticate fail
   Default: 3"
        ::= { hwOntVoipAlarmCfgTable 5 }

    hwOntVoipMassEventThreshold OBJECT-TYPE
        SYNTAX Integer32 (10..1000)
        MAX-ACCESS read-write
        STATUS current
        DESCRIPTION
            "Indicates the threshold for mass ONT voip alarm event in 15 minutes.
             Default: 100"
        ::= { hwOntVoipAlarmCfgTable 6 }

	  hwOntVoipFaultEventStartHour OBJECT-TYPE
        SYNTAX OCTET STRING (SIZE(1..3))
        MAX-ACCESS read-only
        STATUS current
        DESCRIPTION
            "Indicates the start time(hour) of detecting mass event."
        ::= { hwOntVoipAlarmCfgTable 7 }

	  hwOntVoipFaultEventStartMinute OBJECT-TYPE
        SYNTAX OCTET STRING (SIZE(1..3))
        MAX-ACCESS read-only
        STATUS current
        DESCRIPTION
            "Indicates the start time(minute) of detecting mass event."
        ::= { hwOntVoipAlarmCfgTable 8 }

	  hwOntVoipFaultEventEndHour OBJECT-TYPE
        SYNTAX OCTET STRING (SIZE(1..3))
        MAX-ACCESS read-only
        STATUS current
        DESCRIPTION
            "Indicates the end time(hour) of detecting mass event."
        ::= { hwOntVoipAlarmCfgTable 9 }

	  hwOntVoipFaultEventEndMinute OBJECT-TYPE
        SYNTAX OCTET STRING (SIZE(1..3))
        MAX-ACCESS read-only
        STATUS current
        DESCRIPTION
            "Indicates the end time(minute) of detecting mass event."
        ::= { hwOntVoipAlarmCfgTable 10 }

    hwOntVoipMassMGAlarmThreshold OBJECT-TYPE
        SYNTAX Integer32 (10..1000)
        MAX-ACCESS read-write
        STATUS current
        DESCRIPTION
            "Indicates the threshold for mass MG interface alarm.
             Default: 100"
        ::= { hwOntVoipAlarmCfgTable 11 }

    hwOntVoipToneTable OBJECT-TYPE
        SYNTAX SEQUENCE OF HwOntVoipToneEntry
        MAX-ACCESS not-accessible
        STATUS current
        DESCRIPTION
            "The ONT VoIP tone table.
            The indexes of this table are hwOntVoipToneProfileIndex, hwOntVoipToneIndex"
        ::= { hwVoipOntObjects 24 }

    hwOntVoipToneEntry OBJECT-TYPE
        SYNTAX HwOntVoipToneEntry
        MAX-ACCESS not-accessible
        STATUS current
        DESCRIPTION
            "The ONT VoIP tone table.
             The indexes of this entry are hwOntVoipToneProfileIndex, hwOntVoipToneIndex"
        INDEX { hwOntVoipToneProfileIndex, hwOntVoipToneIndex }
        ::= { hwOntVoipToneTable 1 }

    HwOntVoipToneEntry ::=
        SEQUENCE {
            hwOntVoipToneProfileIndex
                Unsigned32,
            hwOntVoipToneIndex
                Unsigned32,
            hwOntVoipToneCadence1Freq1
                Integer32,
            hwOntVoipToneCadence1Freq2
                Integer32,
            hwOntVoipToneCadence1Freq3
                Integer32,
            hwOntVoipToneCadence1Freq4
                Integer32,
            hwOntVoipToneCadence1Level1
                Integer32,
            hwOntVoipToneCadence1Level2
                Integer32,
            hwOntVoipToneCadence1Level3
                Integer32,
            hwOntVoipToneCadence1Level4
                Integer32,
            hwOntVoipToneCadence1ModulationFreq
                Integer32,
            hwOntVoipToneCadence1ModulationLevel
                Integer32,
            hwOntVoipToneCadence1OnTime
                Integer32,
            hwOntVoipToneCadence1OffTime
                Integer32,
            hwOntVoipToneCadence1RepeatTimes
                Unsigned32,
            hwOntVoipToneCadence2Freq1
                Integer32,
            hwOntVoipToneCadence2Freq2
                Integer32,
            hwOntVoipToneCadence2Freq3
                Integer32,
            hwOntVoipToneCadence2Freq4
                Integer32,
            hwOntVoipToneCadence2Level1
                Integer32,
            hwOntVoipToneCadence2Level2
                Integer32,
            hwOntVoipToneCadence2Level3
                Integer32,
            hwOntVoipToneCadence2Level4
                Integer32,
            hwOntVoipToneCadence2ModulationFreq
                Integer32,
            hwOntVoipToneCadence2ModulationLevel
                Integer32,
            hwOntVoipToneCadence2OnTime
                Integer32,
            hwOntVoipToneCadence2OffTime
                Integer32,
            hwOntVoipToneCadence2RepeatTimes
                Unsigned32,
            hwOntVoipToneCadence3Freq1
                Integer32,
            hwOntVoipToneCadence3Freq2
                Integer32,
            hwOntVoipToneCadence3Freq3
                Integer32,
            hwOntVoipToneCadence3Freq4
                Integer32,
            hwOntVoipToneCadence3Level1
                Integer32,
            hwOntVoipToneCadence3Level2
                Integer32,
            hwOntVoipToneCadence3Level3
                Integer32,
            hwOntVoipToneCadence3Level4
                Integer32,
            hwOntVoipToneCadence3ModulationFreq
                Integer32,
            hwOntVoipToneCadence3ModulationLevel
                Integer32,
            hwOntVoipToneCadence3OnTime
                Integer32,
            hwOntVoipToneCadence3OffTime
                Integer32,
            hwOntVoipToneCadence3RepeatTimes
                Unsigned32,
            hwOntVoipToneCadence4Freq1
                Integer32,
            hwOntVoipToneCadence4Freq2
                Integer32,
            hwOntVoipToneCadence4Freq3
                Integer32,
            hwOntVoipToneCadence4Freq4
                Integer32,
            hwOntVoipToneCadence4Level1
                Integer32,
            hwOntVoipToneCadence4Level2
                Integer32,
            hwOntVoipToneCadence4Level3
                Integer32,
            hwOntVoipToneCadence4Level4
                Integer32,
            hwOntVoipToneCadence4ModulationFreq
                Integer32,
            hwOntVoipToneCadence4ModulationLevel
                Integer32,
            hwOntVoipToneCadence4OnTime
                Integer32,
            hwOntVoipToneCadence4OffTime
                Integer32,
            hwOntVoipToneCadence4RepeatTimes
                Unsigned32,
            hwOntVoipToneCadence5Freq1
                Integer32,
            hwOntVoipToneCadence5Freq2
                Integer32,
            hwOntVoipToneCadence5Freq3
                Integer32,
            hwOntVoipToneCadence5Freq4
                Integer32,
            hwOntVoipToneCadence5Level1
                Integer32,
            hwOntVoipToneCadence5Level2
                Integer32,
            hwOntVoipToneCadence5Level3
                Integer32,
            hwOntVoipToneCadence5Level4
                Integer32,
            hwOntVoipToneCadence5ModulationFreq
                Integer32,
            hwOntVoipToneCadence5ModulationLevel
                Integer32,
            hwOntVoipToneCadence5OnTime
                Integer32,
            hwOntVoipToneCadence5OffTime
                Integer32,
            hwOntVoipToneCadence5RepeatTimes
                Unsigned32,
            hwOntVoipToneCadence6Freq1
                Integer32,
            hwOntVoipToneCadence6Freq2
                Integer32,
            hwOntVoipToneCadence6Freq3
                Integer32,
            hwOntVoipToneCadence6Freq4
                Integer32,
            hwOntVoipToneCadence6Level1
                Integer32,
            hwOntVoipToneCadence6Level2
                Integer32,
            hwOntVoipToneCadence6Level3
                Integer32,
            hwOntVoipToneCadence6Level4
                Integer32,
            hwOntVoipToneCadence6ModulationFreq
                Integer32,
            hwOntVoipToneCadence6ModulationLevel
                Integer32,
            hwOntVoipToneCadence6OnTime
                Integer32,
            hwOntVoipToneCadence6OffTime
                Integer32,
            hwOntVoipToneCadence6RepeatTimes
                Unsigned32,
            hwOntVoipToneRowStatus
                RowStatus
            }

    hwOntVoipToneProfileIndex OBJECT-TYPE
        SYNTAX Unsigned32 (1..8)
        MAX-ACCESS not-accessible
        STATUS current
        DESCRIPTION
            "Indicates the index of the voip ont profile."
        ::= { hwOntVoipToneEntry 1 }


    hwOntVoipToneIndex OBJECT-TYPE
        SYNTAX Unsigned32 (1..255)
        MAX-ACCESS not-accessible
        STATUS current
        DESCRIPTION
            "Indicates the index of the ont voip tone.
            Options:
            1. Busy
            2. Confirmation
            3. Dial
            4. Message waiting
            5. Off hook warning (receiver off hook)
            6. Ringback (audible ring)
            7. Reorder
            8. Stutter dial
            9. Call waiting 1
            10. Call waiting 2
            11. Call waiting 3
            12. Call waiting 4
            13. Alerting signal
            14. Special dial
            15. Special info
            16. Release
            17. Congestion
            18. User defined 1
            19. User defined 2
            20. User defined 3
            21. User defined 4
            22..32. Reserved
            33. Intrusion
            34. Dead tone
            35..223. Reserved
            224..255. Vendor-specific codes, not to be standardized"
        ::= { hwOntVoipToneEntry 2 }

    hwOntVoipToneCadence1Freq1 OBJECT-TYPE
        SYNTAX Integer32 (0..65534)
        MAX-ACCESS read-write
        STATUS current
        DESCRIPTION
            "Indicates the tone frequency 1 used by cadence 1, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is mandatory. "
        ::= { hwOntVoipToneEntry 3 }

    hwOntVoipToneCadence1Freq2 OBJECT-TYPE
        SYNTAX Integer32 (0..65534)
        MAX-ACCESS read-write
        STATUS current
        DESCRIPTION
            "Indicates the tone frequency 2 used by cadence 1, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 4 }

    hwOntVoipToneCadence1Freq3 OBJECT-TYPE
        SYNTAX Integer32 (0..65534)
        MAX-ACCESS read-write
        STATUS current
        DESCRIPTION
            "Indicates the tone frequency 3 used by cadence 1, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 5 }

    hwOntVoipToneCadence1Freq4 OBJECT-TYPE
        SYNTAX Integer32 (0..65534)
        MAX-ACCESS read-write
        STATUS current
        DESCRIPTION
            "Indicates the tone frequency 4 used by cadence 1, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 6 }

    hwOntVoipToneCadence1Level1 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution. Three additional pairs of frequency-power components may be specified to define a complex tone. If a pair of possibilities is not to be used, its frequency field should be set to 0.
             This parameter is mandatory. "
        ::= { hwOntVoipToneEntry 7 }

    hwOntVoipToneCadence1Level2 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution.
             This parameter is optional."
        ::= { hwOntVoipToneEntry 8 }

    hwOntVoipToneCadence1Level3 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution.
             This parameter is optional."
        ::= { hwOntVoipToneEntry 9 }

    hwOntVoipToneCadence1Level4 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution.
             This parameter is optional."
        ::= { hwOntVoipToneEntry 10 }

    hwOntVoipToneCadence1ModulationFreq OBJECT-TYPE
        SYNTAX Integer32 (0..65534)
        MAX-ACCESS read-write
        STATUS current
        DESCRIPTION
            "The pair of frequency-power components allows the composite tone to be modulated (warble effect). If this effect is not to be used, the frequency should be set to 0.
             This parameter is optional."
        ::= { hwOntVoipToneEntry 11 }

    hwOntVoipToneCadence1ModulationLevel OBJECT-TYPE
        SYNTAX Integer32 (0..255)
        MAX-ACCESS read-write
        STATUS current
        DESCRIPTION
            "The pair of frequency-power components allows the composite tone to be modulated (warble effect). If this effect is not to be used, the frequency should be set to 0.
             This parameter is optional."
        ::= { hwOntVoipToneEntry 12 }

    hwOntVoipToneCadence1OnTime OBJECT-TYPE
        SYNTAX Integer32 (-1 | 1..65534)
        MAX-ACCESS read-write
        STATUS current
        DESCRIPTION
            "Indicates the tone on duration of cadence 1. Value -1 indicates that the ringing duration is invalid or is not set.
             Unit: millisecond (ms).
             This parameter is mandatory."
        ::= { hwOntVoipToneEntry 13 }

    hwOntVoipToneCadence1OffTime OBJECT-TYPE
        SYNTAX Integer32 (-1 | 1..65534)
        MAX-ACCESS read-write
        STATUS current
        DESCRIPTION
            "Indicates the tone off duration of cadence 1. If the tone is off, the frequency and power fields are not meaningful. Value -1 indicates that the ringing duration is invalid or is not set.
             Unit: millisecond (ms).
             This parameter is optional."
        ::= { hwOntVoipToneEntry 14 }

    hwOntVoipToneCadence1RepeatTimes OBJECT-TYPE
        SYNTAX Unsigned32 (1..8)
        MAX-ACCESS read-write
        STATUS current
        DESCRIPTION
            "Indicates the times of playing cadence 1. If this parameter is set, the cadence is played for the specified times according to the ratio of ontime to offtime.
             This parameter is optional.
             Default: 1 "
        ::= { hwOntVoipToneEntry 15 }

    hwOntVoipToneCadence2Freq1 OBJECT-TYPE
        SYNTAX Integer32 (0..65534)
        MAX-ACCESS read-write
        STATUS current
        DESCRIPTION
            "Indicates the tone frequency 1 used by cadence 2, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 16 }

    hwOntVoipToneCadence2Freq2 OBJECT-TYPE
        SYNTAX Integer32 (0..65534)
        MAX-ACCESS read-write
        STATUS current
        DESCRIPTION
            "Indicates the tone frequency 2 used by cadence 2, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 17 }

    hwOntVoipToneCadence2Freq3 OBJECT-TYPE
        SYNTAX Integer32 (0..65534)
        MAX-ACCESS read-write
        STATUS current
        DESCRIPTION
            "Indicates the tone frequency 3 used by cadence 2, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 18 }

    hwOntVoipToneCadence2Freq4 OBJECT-TYPE
        SYNTAX Integer32 (0..65534)
        MAX-ACCESS read-write
        STATUS current
        DESCRIPTION
            "Indicates the tone frequency 4 used by cadence 2, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 19 }

    hwOntVoipToneCadence2Level1 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution. Three additional pairs of frequency-power components may be specified to define a complex tone. If a pair of possibilities is not to be used, its frequency field should be set to 0.
             This parameter is optional. "
        ::= { hwOntVoipToneEntry 20 }

    hwOntVoipToneCadence2Level2 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution.
             This parameter is optional."
        ::= { hwOntVoipToneEntry 21 }

    hwOntVoipToneCadence2Level3 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution.
             This parameter is optional."
        ::= { hwOntVoipToneEntry 22 }

    hwOntVoipToneCadence2Level4 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution.
             This parameter is optional."
        ::= { hwOntVoipToneEntry 23 }

    hwOntVoipToneCadence2ModulationFreq OBJECT-TYPE
        SYNTAX Integer32 (0..65534)
        MAX-ACCESS read-write
        STATUS current
        DESCRIPTION
            "The pair of frequency-power components allows the composite tone to be modulated (warble effect). If this effect is not to be used, the frequency should be set to 0.
             This parameter is optional."
        ::= { hwOntVoipToneEntry 24 }

    hwOntVoipToneCadence2ModulationLevel OBJECT-TYPE
        SYNTAX Integer32 (0..255)
        MAX-ACCESS read-write
        STATUS current
        DESCRIPTION
            "The pair of frequency-power components allows the composite tone to be modulated (warble effect). If this effect is not to be used, the frequency should be set to 0.
             This parameter is optional."
        ::= { hwOntVoipToneEntry 25 }

    hwOntVoipToneCadence2OnTime OBJECT-TYPE
        SYNTAX Integer32 (-1 | 1..65534)
        MAX-ACCESS read-write
        STATUS current
        DESCRIPTION
            "Indicates the tone on duration of cadence 2. Value -1 indicates that the ringing duration is invalid or is not set.
             Unit: millisecond (ms).
             This parameter is optional."
        ::= { hwOntVoipToneEntry 26 }

    hwOntVoipToneCadence2OffTime OBJECT-TYPE
        SYNTAX Integer32 (-1 | 1..65534)
        MAX-ACCESS read-write
        STATUS current
        DESCRIPTION
            "Indicates the tone off duration of cadence 2. If the tone is off, the frequency and power fields are not meaningful. Value -1 indicates that the ringing duration is invalid or is not set.
             Unit: millisecond (ms).
             This parameter is optional."
        ::= { hwOntVoipToneEntry 27 }

    hwOntVoipToneCadence2RepeatTimes OBJECT-TYPE
        SYNTAX Unsigned32 (1..8)
        MAX-ACCESS read-write
        STATUS current
        DESCRIPTION
            "Indicates the times of playing cadence 2. If this parameter is set, the cadence is played for the specified times according to the ratio of ontime to offtime.
             This parameter is optional.
             Default: 1 "
        ::= { hwOntVoipToneEntry 28 }

    hwOntVoipToneCadence3Freq1 OBJECT-TYPE
        SYNTAX Integer32 (0..65534)
        MAX-ACCESS read-write
        STATUS current
        DESCRIPTION
            "Indicates the tone frequency 1 used by cadence 3, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 29 }

    hwOntVoipToneCadence3Freq2 OBJECT-TYPE
        SYNTAX Integer32 (0..65534)
        MAX-ACCESS read-write
        STATUS current
        DESCRIPTION
            "Indicates the tone frequency 2 used by cadence 3, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 30 }

    hwOntVoipToneCadence3Freq3 OBJECT-TYPE
        SYNTAX Integer32 (0..65534)
        MAX-ACCESS read-write
        STATUS current
        DESCRIPTION
            "Indicates the tone frequency 3 used by cadence 3, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 31 }

    hwOntVoipToneCadence3Freq4 OBJECT-TYPE
        SYNTAX Integer32 (0..65534)
        MAX-ACCESS read-write
        STATUS current
        DESCRIPTION
            "Indicates the tone frequency 4 used by cadence 3, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 32 }

    hwOntVoipToneCadence3Level1 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution. Three additional pairs of frequency-power components may be specified to define a complex tone. If a pair of possibilities is not to be used, its frequency field should be set to 0.
             This parameter is optional. "
        ::= { hwOntVoipToneEntry 33 }

    hwOntVoipToneCadence3Level2 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution.
             This parameter is optional."
        ::= { hwOntVoipToneEntry 34 }

    hwOntVoipToneCadence3Level3 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution.
             This parameter is optional."
        ::= { hwOntVoipToneEntry 35 }

    hwOntVoipToneCadence3Level4 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution.
             This parameter is optional."
        ::= { hwOntVoipToneEntry 36 }

    hwOntVoipToneCadence3ModulationFreq OBJECT-TYPE
        SYNTAX Integer32 (0..65534)
        MAX-ACCESS read-write
        STATUS current
        DESCRIPTION
            "The pair of frequency-power components allows the composite tone to be modulated (warble effect). If this effect is not to be used, the frequency should be set to 0.
             This parameter is optional."
        ::= { hwOntVoipToneEntry 37 }

    hwOntVoipToneCadence3ModulationLevel OBJECT-TYPE
        SYNTAX Integer32 (0..255)
        MAX-ACCESS read-write
        STATUS current
        DESCRIPTION
            "The pair of frequency-power components allows the composite tone to be modulated (warble effect). If this effect is not to be used, the frequency should be set to 0.
             This parameter is optional."
        ::= { hwOntVoipToneEntry 38 }

    hwOntVoipToneCadence3OnTime OBJECT-TYPE
        SYNTAX Integer32 (-1 | 1..65534)
        MAX-ACCESS read-write
        STATUS current
        DESCRIPTION
            "Indicates the tone on duration of cadence 3. Value -1 indicates that the ringing duration is invalid or is not set.
             Unit: millisecond (ms).
             This parameter is optional."
        ::= { hwOntVoipToneEntry 39 }

    hwOntVoipToneCadence3OffTime OBJECT-TYPE
        SYNTAX Integer32 (-1 | 1..65534)
        MAX-ACCESS read-write
        STATUS current
        DESCRIPTION
            "Indicates the tone off duration of cadence 3. If the tone is off, the frequency and power fields are not meaningful. Value -1 indicates that the ringing duration is invalid or is not set.
             Unit: millisecond (ms).
             This parameter is optional."
        ::= { hwOntVoipToneEntry 40 }

    hwOntVoipToneCadence3RepeatTimes OBJECT-TYPE
        SYNTAX Unsigned32 (1..8)
        MAX-ACCESS read-write
        STATUS current
        DESCRIPTION
            "Indicates the times of playing cadence 3. If this parameter is set, the cadence is played for the specified times according to the ratio of ontime to offtime.
             This parameter is optional.
             Default: 1 "
        ::= { hwOntVoipToneEntry 41 }

    hwOntVoipToneCadence4Freq1 OBJECT-TYPE
        SYNTAX Integer32 (0..65534)
        MAX-ACCESS read-write
        STATUS current
        DESCRIPTION
            "Indicates the tone frequency 1 used by cadence 4, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 42 }

    hwOntVoipToneCadence4Freq2 OBJECT-TYPE
        SYNTAX Integer32 (0..65534)
        MAX-ACCESS read-write
        STATUS current
        DESCRIPTION
            "Indicates the tone frequency 2 used by cadence 4, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 43 }

    hwOntVoipToneCadence4Freq3 OBJECT-TYPE
        SYNTAX Integer32 (0..65534)
        MAX-ACCESS read-write
        STATUS current
        DESCRIPTION
            "Indicates the tone frequency 3 used by cadence 4, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 44 }

    hwOntVoipToneCadence4Freq4 OBJECT-TYPE
        SYNTAX Integer32 (0..65534)
        MAX-ACCESS read-write
        STATUS current
        DESCRIPTION
            "Indicates the tone frequency 4 used by cadence 4, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 45 }

    hwOntVoipToneCadence4Level1 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution. Three additional pairs of frequency-power components may be specified to define a complex tone. If a pair of possibilities is not to be used, its frequency field should be set to 0.
             This parameter is optional."
        ::= { hwOntVoipToneEntry 46 }

    hwOntVoipToneCadence4Level2 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution.
             This parameter is optional."
        ::= { hwOntVoipToneEntry 47 }

    hwOntVoipToneCadence4Level3 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution.
             This parameter is optional."
        ::= { hwOntVoipToneEntry 48 }

    hwOntVoipToneCadence4Level4 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution.
             This parameter is optional."
        ::= { hwOntVoipToneEntry 49 }

    hwOntVoipToneCadence4ModulationFreq OBJECT-TYPE
        SYNTAX Integer32 (0..65534)
        MAX-ACCESS read-write
        STATUS current
        DESCRIPTION
            "The pair of frequency-power components allows the composite tone to be modulated (warble effect). If this effect is not to be used, the frequency should be set to 0.
             This parameter is optional."
        ::= { hwOntVoipToneEntry 50 }

    hwOntVoipToneCadence4ModulationLevel OBJECT-TYPE
        SYNTAX Integer32 (0..255)
        MAX-ACCESS read-write
        STATUS current
        DESCRIPTION
            "The pair of frequency-power components allows the composite tone to be modulated (warble effect). If this effect is not to be used, the frequency should be set to 0.
             This parameter is optional."
        ::= { hwOntVoipToneEntry 51 }

    hwOntVoipToneCadence4OnTime OBJECT-TYPE
        SYNTAX Integer32 (-1 | 1..65534)
        MAX-ACCESS read-write
        STATUS current
        DESCRIPTION
            "Indicates the tone on duration of cadence 4. Value -1 indicates that the ringing duration is invalid or is not set.
             Unit: millisecond (ms).
             This parameter is optional."
        ::= { hwOntVoipToneEntry 52 }

    hwOntVoipToneCadence4OffTime OBJECT-TYPE
        SYNTAX Integer32 (-1 | 1..65534)
        MAX-ACCESS read-write
        STATUS current
        DESCRIPTION
            "Indicates the tone off duration of cadence 4. If the tone is off, the frequency and power fields are not meaningful. Value -1 indicates that the ringing duration is invalid or is not set.
             Unit: millisecond (ms).
             This parameter is optional."
        ::= { hwOntVoipToneEntry 53 }

    hwOntVoipToneCadence4RepeatTimes OBJECT-TYPE
        SYNTAX Unsigned32 (1..8)
        MAX-ACCESS read-write
        STATUS current
        DESCRIPTION
            "Indicates the times of playing cadence 4. If this parameter is set, the cadence is played for the specified times according to the ratio of ontime to offtime.
             This parameter is optional.
             Default: 1 "
        ::= { hwOntVoipToneEntry 54 }

    hwOntVoipToneCadence5Freq1 OBJECT-TYPE
        SYNTAX Integer32 (0..65534)
        MAX-ACCESS read-write
        STATUS current
        DESCRIPTION
            "Indicates the tone frequency 1 used by cadence 5, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 55 }

    hwOntVoipToneCadence5Freq2 OBJECT-TYPE
        SYNTAX Integer32 (0..65534)
        MAX-ACCESS read-write
        STATUS current
        DESCRIPTION
            "Indicates the tone frequency 2 used by cadence 5, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 56 }

    hwOntVoipToneCadence5Freq3 OBJECT-TYPE
        SYNTAX Integer32 (0..65534)
        MAX-ACCESS read-write
        STATUS current
        DESCRIPTION
            "Indicates the tone frequency 3 used by cadence 5, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 57 }

    hwOntVoipToneCadence5Freq4 OBJECT-TYPE
        SYNTAX Integer32 (0..65534)
        MAX-ACCESS read-write
        STATUS current
        DESCRIPTION
            "Indicates the tone frequency 4 used by cadence 5, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 58 }

    hwOntVoipToneCadence5Level1 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution. Three additional pairs of frequency-power components may be specified to define a complex tone. If a pair of possibilities is not to be used, its frequency field should be set to 0.
             This parameter is optional."
        ::= { hwOntVoipToneEntry 59 }

    hwOntVoipToneCadence5Level2 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution.
             This parameter is optional."
        ::= { hwOntVoipToneEntry 60 }

    hwOntVoipToneCadence5Level3 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution.
             This parameter is optional."
        ::= { hwOntVoipToneEntry 61 }

    hwOntVoipToneCadence5Level4 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution.
             This parameter is optional."
        ::= { hwOntVoipToneEntry 62 }

    hwOntVoipToneCadence5ModulationFreq OBJECT-TYPE
        SYNTAX Integer32 (0..65534)
        MAX-ACCESS read-write
        STATUS current
        DESCRIPTION
            "The pair of frequency-power components allows the composite tone to be modulated (warble effect). If this effect is not to be used, the frequency should be set to 0.
             This parameter is optional."
        ::= { hwOntVoipToneEntry 63 }

    hwOntVoipToneCadence5ModulationLevel OBJECT-TYPE
        SYNTAX Integer32 (0..255)
        MAX-ACCESS read-write
        STATUS current
        DESCRIPTION
            "The pair of frequency-power components allows the composite tone to be modulated (warble effect). If this effect is not to be used, the frequency should be set to 0.
             This parameter is optional."
        ::= { hwOntVoipToneEntry 64 }

    hwOntVoipToneCadence5OnTime OBJECT-TYPE
        SYNTAX Integer32 (-1 | 1..65534)
        MAX-ACCESS read-write
        STATUS current
        DESCRIPTION
            "Indicates the tone on duration of cadence 5. Value -1 indicates that the ringing duration is invalid or is not set.
             Unit: millisecond (ms).
             This parameter is optional."
        ::= { hwOntVoipToneEntry 65 }

    hwOntVoipToneCadence5OffTime OBJECT-TYPE
        SYNTAX Integer32 (-1 | 1..65534)
        MAX-ACCESS read-write
        STATUS current
        DESCRIPTION
            "Indicates the tone off duration of cadence 5. If the tone is off, the frequency and power fields are not meaningful. Value -1 indicates that the ringing duration is invalid or is not set.
             Unit: millisecond (ms).
             This parameter is optional."
        ::= { hwOntVoipToneEntry 66 }

    hwOntVoipToneCadence5RepeatTimes OBJECT-TYPE
        SYNTAX Unsigned32 (1..8)
        MAX-ACCESS read-write
        STATUS current
        DESCRIPTION
            "Indicates the times of playing cadence 5. If this parameter is set, the cadence is played for the specified times according to the ratio of ontime to offtime.
             This parameter is optional.
             Default: 1 "
        ::= { hwOntVoipToneEntry 67 }

    hwOntVoipToneCadence6Freq1 OBJECT-TYPE
        SYNTAX Integer32 (0..65534)
        MAX-ACCESS read-write
        STATUS current
        DESCRIPTION
            "Indicates the tone frequency 1 used by cadence 6, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 68 }

    hwOntVoipToneCadence6Freq2 OBJECT-TYPE
        SYNTAX Integer32 (0..65534)
        MAX-ACCESS read-write
        STATUS current
        DESCRIPTION
            "Indicates the tone frequency 2 used by cadence 6, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 69 }

    hwOntVoipToneCadence6Freq3 OBJECT-TYPE
        SYNTAX Integer32 (0..65534)
        MAX-ACCESS read-write
        STATUS current
        DESCRIPTION
            "Indicates the tone frequency 3 used by cadence 6, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 70 }

    hwOntVoipToneCadence6Freq4 OBJECT-TYPE
        SYNTAX Integer32 (0..65534)
        MAX-ACCESS read-write
        STATUS current
        DESCRIPTION
            "Indicates the tone frequency 4 used by cadence 6, which can be single-frequency, dual-frequency, three-frequency, and four-frequency.
             Single-frequency tone: Only freq1 is configured.
             Dual-frequency tone: freq1 and freq2 are configured.
             Three-frequency tone: freq1, freq2 and freq3 are configured.
             Four-frequency tone: freq1, freq2, freq3 and freq4 are configured.
             Value 0 indicates that the tone frequency is invalid or is not set.
             Unit: Hz.
             This parameter is optional. "
        ::= { hwOntVoipToneEntry 71 }

    hwOntVoipToneCadence6Level1 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution. Three additional pairs of frequency-power components may be specified to define a complex tone. If a pair of possibilities is not to be used, its frequency field should be set to 0.
             This parameter is optional. "
        ::= { hwOntVoipToneEntry 72 }

    hwOntVoipToneCadence6Level2 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution.
             This parameter is optional. "
        ::= { hwOntVoipToneEntry 73 }

    hwOntVoipToneCadence6Level3 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution.
             This parameter is optional. "
        ::= { hwOntVoipToneEntry 74 }

    hwOntVoipToneCadence6Level4 OBJECT-TYPE
        SYNTAX Integer32 (0..255)
        MAX-ACCESS read-write
        STATUS current
        DESCRIPTION
            "Indicates the power level of the corresponding frequency component. It  ranges from 0 (coded as 0) to -25.5 (coded as 255 )  dBm0 with 0.1 dB resolution.
             This parameter is optional. "
        ::= { hwOntVoipToneEntry 75 }

    hwOntVoipToneCadence6ModulationFreq OBJECT-TYPE
        SYNTAX Integer32 (0..65534)
        MAX-ACCESS read-write
        STATUS current
        DESCRIPTION
            "The pair of frequency-power components allows the composite tone to be modulated (warble effect). If this effect is not to be used, the frequency should be set to 0.
             This parameter is optional. "
        ::= { hwOntVoipToneEntry 76 }

    hwOntVoipToneCadence6ModulationLevel OBJECT-TYPE
        SYNTAX Integer32 (0..255)
        MAX-ACCESS read-write
        STATUS current
        DESCRIPTION
            "The pair of frequency-power components allows the composite tone to be modulated (warble effect). If this effect is not to be used, the frequency should be set to 0.
             This parameter is optional. "
        ::= { hwOntVoipToneEntry 77 }

    hwOntVoipToneCadence6OnTime OBJECT-TYPE
        SYNTAX Integer32 (-1 | 1..65534)
        MAX-ACCESS read-write
        STATUS current
        DESCRIPTION
            "Indicates the tone on duration of cadence 6. Value -1 indicates that the ringing duration is invalid or is not set.
             Unit: millisecond (ms).
             This parameter is optional."
        ::= { hwOntVoipToneEntry 78 }

    hwOntVoipToneCadence6OffTime OBJECT-TYPE
        SYNTAX Integer32 (-1 | 1..65534)
        MAX-ACCESS read-write
        STATUS current
        DESCRIPTION
            "Indicates the tone off duration of cadence 6. If the tone is off, the frequency and power fields are not meaningful. Value -1 indicates that the ringing duration is invalid or is not set.
             Unit: millisecond (ms).
             This parameter is optional."
        ::= { hwOntVoipToneEntry 79 }

    hwOntVoipToneCadence6RepeatTimes OBJECT-TYPE
        SYNTAX Unsigned32 (1..8)
        MAX-ACCESS read-write
        STATUS current
        DESCRIPTION
            "Indicates the times of playing cadence 6. If this parameter is set, the cadence is played for the specified times according to the ratio of ontime to offtime.
             This parameter is optional.
             Default: 1 "
        ::= { hwOntVoipToneEntry 80 }

    hwOntVoipToneRowStatus OBJECT-TYPE
        SYNTAX RowStatus
        MAX-ACCESS read-create
        STATUS current
        DESCRIPTION
            "Options:
            1.active(1)          -indicates active
            2.notInService(2)    -indicates not in service
            3.notReady(3)        -indicates not ready
            4.createAndGo(4)     -indicates create and go
            5.createAndWait(5)   -indicates create and wait
            6.destroy(6)         -indicates destroy
            Only 4 and 6 is support Now."
        ::= { hwOntVoipToneEntry 81 }

    hwOntVoipRingTable OBJECT-TYPE
        SYNTAX SEQUENCE OF HwOntVoipRingEntry
        MAX-ACCESS not-accessible
        STATUS current
        DESCRIPTION
            "The ONT VoIP ring table.
            The indexes of this entry are hwOntVoipRingProfileIndex, hwOntVoipRingIndex"
        ::= { hwVoipOntObjects 25 }

    hwOntVoipRingEntry OBJECT-TYPE
        SYNTAX HwOntVoipRingEntry
        MAX-ACCESS not-accessible
        STATUS current
        DESCRIPTION
            "The ONT VoIP ring table.
            The indexes of this entry are hwOntVoipRingProfileIndex, hwOntVoipRingIndex"
        INDEX { hwOntVoipRingProfileIndex, hwOntVoipRingIndex }
        ::= { hwOntVoipRingTable 1 }

    HwOntVoipRingEntry ::=
        SEQUENCE {
            hwOntVoipRingProfileIndex
                Unsigned32,
            hwOntVoipRingIndex
                Unsigned32,
            hwOntVoipRingCadence1OnTime
                Integer32,
            hwOntVoipRingCadence1OffTime
                Integer32,
            hwOntVoipRingCadence2OnTime
                Integer32,
            hwOntVoipRingCadence2OffTime
                Integer32,
            hwOntVoipRingCadence3OnTime
                Integer32,
            hwOntVoipRingCadence3OffTime
                Integer32,
            hwOntVoipRingRowStatus
                RowStatus
            }

    hwOntVoipRingProfileIndex OBJECT-TYPE
        SYNTAX Unsigned32 (1..8)
        MAX-ACCESS not-accessible
        STATUS current
        DESCRIPTION
            "Indicates the index of the ont voip ring profile."
        ::= { hwOntVoipRingEntry 1 }

    hwOntVoipRingIndex OBJECT-TYPE
        SYNTAX Unsigned32 (1..255)
        MAX-ACCESS not-accessible
        STATUS current
        DESCRIPTION
            "Indicates the index of the ont voip ring.
            Options:
            1. Default
			2. Splash
			3..223. Reserved
			224..255. Vendor-specific codes, not to be standardized"
		::= { hwOntVoipRingEntry 2 }

	hwOntVoipRingCadence1OnTime OBJECT-TYPE
		SYNTAX Integer32 (-1 | 1..65534)
        MAX-ACCESS read-write
        STATUS current
        DESCRIPTION
            "Indicates the ringing on duration of cadence 1. Unit: millisecond (ms). Value -1 indicates that the ringing duration is invalid or is not set.
             This parameter is mandatory. "
        ::= { hwOntVoipRingEntry 3 }

	hwOntVoipRingCadence1OffTime OBJECT-TYPE
		SYNTAX Integer32 (-1 | 1..65534)
        MAX-ACCESS read-write
        STATUS current
        DESCRIPTION
            "Indicates the ringing off duration of cadence 1. Unit: millisecond (ms). Value -1 indicates that the ringing stop duration is invalid or is not set.
             This parameter is optional."
        ::= { hwOntVoipRingEntry 4 }

    hwOntVoipRingCadence2OnTime OBJECT-TYPE
		SYNTAX Integer32 (-1 | 1..65534)
        MAX-ACCESS read-write
        STATUS current
        DESCRIPTION
            "Indicates the ringing on duration of cadence 2. Unit: millisecond (ms). Value -1 indicates that the ringing duration is invalid or is not set.
             This parameter is optional. "
        ::= { hwOntVoipRingEntry 5 }

	hwOntVoipRingCadence2OffTime OBJECT-TYPE
		SYNTAX Integer32 (-1 | 1..65534)
        MAX-ACCESS read-write
        STATUS current
        DESCRIPTION
            "Indicates the ringing off duration of cadence 2. Unit: millisecond (ms). Value -1 indicates that the ringing stop duration is invalid or is not set.
             This parameter is optional."
        ::= { hwOntVoipRingEntry 6 }

    hwOntVoipRingCadence3OnTime OBJECT-TYPE
		SYNTAX Integer32 (-1 | 1..65534)
        MAX-ACCESS read-write
        STATUS current
        DESCRIPTION
            "Indicates the ringing on duration of cadence 3. Unit: millisecond (ms). Value -1 indicates that the ringing duration is invalid or is not set.
             This parameter is optional. "
        ::= { hwOntVoipRingEntry 7 }

	hwOntVoipRingCadence3OffTime OBJECT-TYPE
		SYNTAX Integer32 (-1 | 1..65534)
        MAX-ACCESS read-write
        STATUS current
        DESCRIPTION
            "Indicates the ringing off duration of cadence 3. Unit: millisecond (ms). Value -1 indicates that the ringing stop duration is invalid or is not set.
             This parameter is optional."
        ::= { hwOntVoipRingEntry 8 }

	hwOntVoipRingRowStatus OBJECT-TYPE
		SYNTAX RowStatus
        MAX-ACCESS read-create
        STATUS current
        DESCRIPTION
            "Options:
			1.active(1)          -indicates active
			2.notInService(2)    -indicates not in service
			3.notReady(3)        -indicates not ready
			4.createAndGo(4)     -indicates create and go
			5.createAndWait(5)   -indicates create and wait
			6.destroy(6)         -indicates destroy
			Only 4 and 6 is support Now."
        ::= { hwOntVoipRingEntry 9 }

    hwOntVoipSignalProfileTable OBJECT-TYPE
        SYNTAX SEQUENCE OF HwOntVoipSignalProfileEntry
        MAX-ACCESS not-accessible
        STATUS current
        DESCRIPTION
            "The ONT VoIP signal profile table.
            The index of this table is hwOntVoipSignalProfileIndex."
        ::= { hwVoipOntObjects 26 }

    hwOntVoipSignalProfileEntry OBJECT-TYPE
        SYNTAX HwOntVoipSignalProfileEntry
        MAX-ACCESS not-accessible
        STATUS current
        DESCRIPTION
            "The ONT VoIP signal profile table.
            The index of this entry is hwOntVoipSignalProfileIndex."
        INDEX { hwOntVoipSignalProfileIndex }
        ::= { hwOntVoipSignalProfileTable 1 }

    HwOntVoipSignalProfileEntry ::=
        SEQUENCE {
            hwOntVoipSignalProfileIndex
                Unsigned32,
            hwOntVoipSignalProfileName
                OCTET STRING,
            hwOntVoipSignalProfileBinNum
                Unsigned32,
            hwOntVoipSignalProfileCommit
                INTEGER,
            hwOntVoipSignalProfileCommitResult
                INTEGER,
            hwOntVoipSignalProfileRowStatus
                RowStatus
            }

    hwOntVoipSignalProfileIndex OBJECT-TYPE
        SYNTAX Unsigned32 (1..8)
        MAX-ACCESS not-accessible
        STATUS current
        DESCRIPTION
            "Indicates the index of the ONT VoIP signal profile."
        ::= { hwOntVoipSignalProfileEntry 1 }

    hwOntVoipSignalProfileName OBJECT-TYPE
        SYNTAX OCTET STRING  (SIZE (1..32))
        MAX-ACCESS read-write
        STATUS current
        DESCRIPTION
            "Indicates the name of the ONT VoIP signal profile."
        ::= { hwOntVoipSignalProfileEntry 2 }

    hwOntVoipSignalProfileBinNum OBJECT-TYPE
        SYNTAX Unsigned32
        MAX-ACCESS read-only
        STATUS current
        DESCRIPTION
            "Indicates the  number of ONT bound with ONT VoIP signal profile."
        ::= { hwOntVoipSignalProfileEntry 3 }

    hwOntVoipSignalProfileCommit OBJECT-TYPE
        SYNTAX INTEGER
            {
                commitExecute(1),
                clearResult(2),
                invalid(-1)
            }
        MAX-ACCESS read-write
        STATUS current
        DESCRIPTION
            "Indicates the ONT VoIP signal profile Configuration Commit.
             Options:
             1. commitExecute(1)      - Execute the ONT VoIP signal profile configuration commit
             2. clearResult(2)        - Clear the commit result
             3. invalid(-1)           - Indicates that the query fails or no information is detected"
        ::= { hwOntVoipSignalProfileEntry 4 }

    hwOntVoipSignalProfileCommitResult OBJECT-TYPE
        SYNTAX INTEGER
            {
                success(1),
                fail(2),
                operating(3),
                invalid(-1)
            }
        MAX-ACCESS read-only
        STATUS current
        DESCRIPTION
            "Indicates the commit result of a ONT VoIP signal profile, the aging time of the result is 20s.
             Options:
             1. success(1)   - Indicates that the commit result is success
             2. fail(2)      - Indicates that the commit result is fail
             3. operating(3) - Indicates that the commit does not complete
             4. invalid(-1)  - Indicates that no commit is being operated "
        ::= { hwOntVoipSignalProfileEntry 5 }

    hwOntVoipSignalProfileRowStatus OBJECT-TYPE
        SYNTAX RowStatus
        MAX-ACCESS read-create
        STATUS current
        DESCRIPTION
            "Options:
            1.active(1)          -indicates active
            2.notInService(2)    -indicates not in service
            3.notReady(3)        -indicates not ready
            4.createAndGo(4)     -indicates create and go
            5.createAndWait(5)   -indicates create and wait
            6.destroy(6)         -indicates destroy
            Only 4 and 6 is support Now."
        ::= { hwOntVoipSignalProfileEntry 6 }

    hwOntVoipBindSignalProfileTable OBJECT-TYPE
        SYNTAX SEQUENCE OF HwOntVoipBindSignalProfileEntry
        MAX-ACCESS not-accessible
        STATUS current
        DESCRIPTION
            "The ONT VoIP bind config table.
            The indexes of this table are hwVoiceIfIndex, hwVoiceOntIndex."
        ::= { hwVoipOntObjects 27 }

    hwOntVoipBindSignalProfileEntry OBJECT-TYPE
        SYNTAX HwOntVoipBindSignalProfileEntry
        MAX-ACCESS not-accessible
        STATUS current
        DESCRIPTION
            "The ONT VoIP bind config table.
            The indexes of this entry are hwVoiceIfIndex, hwVoiceOntIndex."
        INDEX { hwVoiceIfIndex, hwVoiceOntIndex }
        ::= { hwOntVoipBindSignalProfileTable 1 }

    HwOntVoipBindSignalProfileEntry ::=
        SEQUENCE {
            hwOntVoipBindOprType
                INTEGER,
            hwOntVoipBindSignalProfileIndex
                Integer32
            }

    hwOntVoipBindOprType OBJECT-TYPE
        SYNTAX INTEGER
            {
                bind(1),
                unbind(2),
                invalid(-1)
            }
        MAX-ACCESS read-write
        STATUS current
        DESCRIPTION
            "Indicates the bind operator type.
             Options:
             1. bind(1)      - Indicates that the bind operator
             2. unbind(2)    - Indicates that the unbind operator
             4. invalid(-1)  - Indicates that the query fails or no information is detected"
        ::= { hwOntVoipBindSignalProfileEntry 1 }

    hwOntVoipBindSignalProfileIndex OBJECT-TYPE
        SYNTAX Integer32 (-1 | 1..8)
        MAX-ACCESS read-write
        STATUS current
        DESCRIPTION
            "Indicates the index of bind voip signal profile."
        ::= { hwOntVoipBindSignalProfileEntry 2 }

    hwOntVoipIpIndexTable OBJECT-TYPE
        SYNTAX SEQUENCE OF HwOntVoipIpIndexEntry
        MAX-ACCESS not-accessible
        STATUS current
        DESCRIPTION
            "The ONT tr069 VoIP config table.
            The indexes of this table are hwVoiceIfIndex, hwVoiceOntIndex."
        ::= { hwVoipOntObjects 28 }

    hwOntVoipIpIndexEntry OBJECT-TYPE
        SYNTAX HwOntVoipIpIndexEntry
        MAX-ACCESS not-accessible
        STATUS current
        DESCRIPTION
            "The ONT tr069 VoIP config table.
            The indexes of this entry are hwVoiceIfIndex, hwVoiceOntIndex."
        INDEX { hwVoiceIfIndex, hwVoiceOntIndex }
        ::= { hwOntVoipIpIndexTable 1 }

    HwOntVoipIpIndexEntry ::=
        SEQUENCE {
            hwOntVoipIpIndexOprType
                INTEGER,
            hwOntVoipIpIndex
                Integer32
            }

    hwOntVoipIpIndexOprType OBJECT-TYPE
        SYNTAX INTEGER
            {
                bind(1),
                unbind(2),
                invalid(-1)
            }
        MAX-ACCESS read-write
        STATUS current
        DESCRIPTION
            "Indicates the bind operator type.
             Options:
             1. bind(1)      - Indicates that the bind operator
             2. unbind(2)    - Indicates that the unbind operator
             4. invalid(-1)  - Indicates that the query fails or no information is detected"
        ::= { hwOntVoipIpIndexEntry 1 }

    hwOntVoipIpIndex OBJECT-TYPE
        SYNTAX Integer32 (-1 | 0..3)
        MAX-ACCESS read-write
        STATUS current
        DESCRIPTION
            "Indicates the IP index. Value -1 indicates that the query fails or no information is detected"
        ::= { hwOntVoipIpIndexEntry 2 }

    hwOntRecentVoipAlarmRecordTable OBJECT-TYPE
        SYNTAX SEQUENCE OF HwOntRecentVoipAlarmRecordEntry
        MAX-ACCESS not-accessible
        STATUS current
        DESCRIPTION
            "The ONT voip Alarm Record table.
            The indexes of this table is hwOntRecentVoipAlarmBlockIndex."
        ::= { hwVoipOntObjects 29 }

    hwOntRecentVoipAlarmRecordEntry OBJECT-TYPE
        SYNTAX HwOntRecentVoipAlarmRecordEntry
        MAX-ACCESS not-accessible
        STATUS current
        DESCRIPTION
            "The ONT voip Alarm Record config table.
            The indexes of this entry is hwOntRecentVoipAlarmBlockIndex."
        INDEX { hwOntRecentVoipAlarmBlockIndex }
        ::= { hwOntRecentVoipAlarmRecordTable 1 }

    HwOntRecentVoipAlarmRecordEntry ::=
        SEQUENCE {
            hwOntRecentVoipAlarmBlockIndex
                Integer32,
            hwOntRecentVoipAlarmOctetString
                OCTET STRING
            }

    hwOntRecentVoipAlarmBlockIndex OBJECT-TYPE
        SYNTAX Integer32 (1..200)
        MAX-ACCESS not-accessible
        STATUS current
        DESCRIPTION
            "Indicates the index of the ONT voip Alarm Record."
        ::= { hwOntRecentVoipAlarmRecordEntry 1 }

    hwOntRecentVoipAlarmOctetString OBJECT-TYPE
        SYNTAX OCTET STRING  (SIZE (2..902))
        MAX-ACCESS read-only
        STATUS current
        DESCRIPTION
            "Indicates the ONT voip Alarm Record.
             Every index indicates 50 records maximum.
             Every record includes 18 bytes.
             Record number()
             Year(2byte)  : 65535-invalid
			 Month(1byte) : 255-invalid
			 Day(1byte)   : 255-invalid
			 Hour(1byte)  : 255-invalid
			 Minute(1byte): 255-invalid
			 Second(1byte): 255-invalid
			 Frame(1byte)
			 Slot(1byte)
			 Port(1byte)
			 ONTID(2byte)

			 ALARMSTATE(1Byte)
			 -0 inactive,1 active

			 ALARM Type(1 Byte)
			 1-	MG fault
			 2-	MG recover
			 3-	SIP auth fail
			 4-	SIP auth recover
			 5-	SIP register timeout
			 6-	SIP register time out recover
			 7-	SIP register fail
			 8-	SIP register fail recover

			 ALARMPARA(4Byte)"
        ::= { hwOntRecentVoipAlarmRecordEntry 2 }


  hwOntCallerEmulateOperatorTrap NOTIFICATION-TYPE
    OBJECTS { hwOntPstnCallerEmulateTestRequestID,
              hwVoiceIfIndex,
              hwVoiceOntIndex,
              hwVoiceOntPortIndex,
              hwOntPstnCallerEmulateTestStatus,
              hwOntPstnCallerEmulateTestResult,
              hwOntPstnCallerEmulateCalledTelNo,
              hwOntPstnCallerEmulateReportTelNo}

    STATUS current
    DESCRIPTION
            "This notification indicates that the trap for ont caller emulate test result:
             1. hwOntPstnCallerEmulateTestRequestID
             2. hwVoiceIfIndex
             3. hwVoiceOntIndex
             4. hwVoiceOntPortIndex
             5. hwOntPstnCallerEmulateTestStatus
             6. hwOntPstnCallerEmulateTestResult
             7. hwOntPstnCallerEmulateCalledTelNo
             8. hwOntPstnCallerEmulateReportTelNo"
    ::= { hwVoipOntTraps 0 }

  hwOntCalledEmulateOperatorTrap NOTIFICATION-TYPE
    OBJECTS { hwOntPstnCalledEmulateTestRequestID,
              hwVoiceIfIndex,
              hwVoiceOntIndex,
              hwVoiceOntPortIndex,
              hwOntPstnCalledEmulateTestStatus,
              hwOntPstnCalledEmulateTestResult}
    STATUS current
    DESCRIPTION
            "This notification indicates that the trap for ont called emulate test result:
             1. hwOntPstnCalledEmulateTestRequestID
             2. hwVoiceIfIndex
             3. hwVoiceOntIndex
             4. hwVoiceOntPortIndex
             5. hwOntPstnCalledEmulateTestStatus
             6. hwOntPstnCalledEmulateTestResult"
    ::= { hwVoipOntTraps 1 }

  hwOntSipUserRegisterAuthAlarmTrap NOTIFICATION-TYPE
    OBJECTS { hwFrameIndex,
              hwSlotIndex,
              hwPortIndex,
              hwVoiceOntIndex,
              hwVoiceOntPortIndex}
    STATUS current
    DESCRIPTION
            "This notification indicates that the trap for ont sip user authenticate fail:
             1. hwFrameIndex
             2. hwSlotIndex
             3. hwPortIndex
             4. hwVoiceOntIndex
             5. hwVoiceOntPortIndex"
    ::= { hwVoipOntTraps 2 }

  hwOntSipUserRegisterAuthRestoreAlarmTrap NOTIFICATION-TYPE
    OBJECTS { hwFrameIndex,
              hwSlotIndex,
              hwPortIndex,
              hwVoiceOntIndex,
              hwVoiceOntPortIndex}
    STATUS current
    DESCRIPTION
            "This notification indicates that the trap for ont sip user authenticate fail restore:
             1. hwFrameIndex
             2. hwSlotIndex
             3. hwPortIndex
             4. hwVoiceOntIndex
             5. hwVoiceOntPortIndex"
    ::= { hwVoipOntTraps 3 }

  hwOntSipUserRegisterTimeoutAlarmTrap NOTIFICATION-TYPE
    OBJECTS { hwFrameIndex,
              hwSlotIndex,
              hwPortIndex,
              hwVoiceOntIndex,
              hwVoiceOntPortIndex}
    STATUS current
    DESCRIPTION
            "This notification indicates that the trap for ont sip user register time out:
             1. hwFrameIndex
             2. hwSlotIndex
             3. hwPortIndex
             4. hwVoiceOntIndex
             5. hwVoiceOntPortIndex"
    ::= { hwVoipOntTraps 4 }

  hwOntSipUserRegisterTimeoutRestoreAlarmTrap NOTIFICATION-TYPE
    OBJECTS { hwFrameIndex,
              hwSlotIndex,
              hwPortIndex,
              hwVoiceOntIndex,
              hwVoiceOntPortIndex}
    STATUS current
    DESCRIPTION
            "This notification indicates that the trap for ont sip user register time out restore:
             1. hwFrameIndex
             2. hwSlotIndex
             3. hwPortIndex
             4. hwVoiceOntIndex
             5. hwVoiceOntPortIndex"
    ::= { hwVoipOntTraps 5 }

  hwOntSipUserRegisterFailAlarmTrap NOTIFICATION-TYPE
    OBJECTS { hwFrameIndex,
              hwSlotIndex,
              hwPortIndex,
              hwVoiceOntIndex,
              hwVoiceOntPortIndex}
    STATUS current
    DESCRIPTION
            "This notification indicates that the trap for ont sip user register fail:
             1. hwFrameIndex
             2. hwSlotIndex
             3. hwPortIndex
             4. hwVoiceOntIndex
             5. hwVoiceOntPortIndex"
    ::= { hwVoipOntTraps 6 }

  hwOntSipUserRegisterFailRestoreAlarmTrap NOTIFICATION-TYPE
    OBJECTS { hwFrameIndex,
              hwSlotIndex,
              hwPortIndex,
              hwVoiceOntIndex,
              hwVoiceOntPortIndex}
    STATUS current
    DESCRIPTION
            "This notification indicates that the trap for ont sip user register fail restore:
             1. hwFrameIndex
             2. hwSlotIndex
             3. hwPortIndex
             4. hwVoiceOntIndex
             5. hwVoiceOntPortIndex"
    ::= { hwVoipOntTraps 7 }

  hwOntMgInterfaceFaultAlarmTrap NOTIFICATION-TYPE
    OBJECTS { hwFrameIndex,
              hwSlotIndex,
              hwPortIndex,
              hwVoiceOntIndex,
              hwVoiceOntMgId}
    STATUS current
    DESCRIPTION
            "This notification indicates that the trap for ont mg interface fault:
             1. hwFrameIndex
             2. hwSlotIndex
             3. hwPortIndex
             4. hwVoiceOntIndex
             5. hwVoiceOntMgId"
    ::= { hwVoipOntTraps 8 }

  hwOntMgInterfaceRestoreAlarmTrap NOTIFICATION-TYPE
    OBJECTS { hwFrameIndex,
              hwSlotIndex,
              hwPortIndex,
              hwVoiceOntIndex,
              hwVoiceOntMgId}
    STATUS current
    DESCRIPTION
            "This notification indicates that the trap for ont mg interface restore:
             1. hwFrameIndex
             2. hwSlotIndex
             3. hwPortIndex
             4. hwVoiceOntIndex
             5. hwVoiceOntMgId"
    ::= { hwVoipOntTraps 9 }

  hwOntMassSipUserRegisterAuthAlarmTrap NOTIFICATION-TYPE
    STATUS current
    DESCRIPTION
            "This notification indicates that the trap for a mass of ont sip users authenticate fail."
    ::= { hwVoipOntTraps 10 }

  hwOntMassSipUserRegisterAuthRestoreAlarmTrap NOTIFICATION-TYPE
    STATUS current
    DESCRIPTION
            "This notification indicates that the trap for a mass of ont sip users authenticate fail restore."
    ::= { hwVoipOntTraps 11 }

  hwOntMassSipUserRegisterTimeoutAlarmTrap NOTIFICATION-TYPE
    STATUS current
    DESCRIPTION
            "This notification indicates that the trap for a mass of ont sip users register time out."
    ::= { hwVoipOntTraps 12 }

  hwOntMassSipUserRegisterTimeoutRestoreAlarmTrap NOTIFICATION-TYPE
    STATUS current
    DESCRIPTION
            "This notification indicates that the trap for a mass of ont sip users register time out restore."
    ::= { hwVoipOntTraps 13 }

  hwOntMassSipUserRegisterFailAlarmTrap NOTIFICATION-TYPE
    STATUS current
    DESCRIPTION
            "This notification indicates that the trap for a mass of ont sip users register fail."
    ::= { hwVoipOntTraps 14 }

  hwOntMassSipUserRegisterFailRestoreAlarmTrap NOTIFICATION-TYPE
    STATUS current
    DESCRIPTION
            "This notification indicates that the trap for a mass of ont sip users register fail restore."
    ::= { hwVoipOntTraps 15 }

  hwOntMassVoipFaultEventTrap NOTIFICATION-TYPE
    OBJECTS { hwOntVoipFaultEventStartHour,
              hwOntVoipFaultEventStartMinute,
              hwOntVoipFaultEventEndHour,
              hwOntVoipFaultEventEndMinute,
			        hwOntVoipMassEventThreshold}
    STATUS current
    DESCRIPTION
            "This notification indicates that the trap for a mass of ont voip fault in 15 minutes:
             1. hwOntVoipFaultEventStartHour
             2. hwOntVoipFaultEventStartMinute
             3. hwOntVoipFaultEventEndHour
             4. hwOntVoipFaultEventEndMinute
			       5. hwOntVoipMassEventThreshold"
    ::= { hwVoipOntTraps 16 }

  hwOntMassMgInterfaceFaultAlarmTrap NOTIFICATION-TYPE
    STATUS current
    DESCRIPTION
            "This notification indicates that the trap for a mass of ont mg interface fail."
    ::= { hwVoipOntTraps 17 }

  hwOntMassMgInterfaceRestoreAlarmTrap NOTIFICATION-TYPE
    STATUS current
    DESCRIPTION
            "This notification indicates that the trap for a mass of ont mg interface restore."
    ::= { hwVoipOntTraps 18 }

    END
