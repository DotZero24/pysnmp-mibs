-- ============================================================================
-- Copyright (C) 2010 by  HUAWEI TECHNOLOGIES. All rights reserved.
-- Description: The mib is used for defining huawei's IPDSLAM PVCIPOA MIB objects.
-- Reference:   RFC2320 RFC2225
-- Version:     V1.07
-- ============================================================================

HUAWEI-IPDSLAM-PVCIPOA-MIB DEFINITIONS ::= BEGIN

IMPORTS
	OBJECT-TYPE, MODULE-IDENTITY, IpAddress, Integer32, NOTIFICATION-TYPE
		FROM SNMPv2-SMI
	TruthValue
 		FROM SNMPv2-TC
        hwSlotIndex, hwPortIndex
 		FROM HUAWEI-DEVICE-MIB
	huaweiUtility
		FROM HUAWEI-MIB;

hwIpDslamPvcIpoa MODULE-IDENTITY
	LAST-UPDATED "201008241600Z"
	ORGANIZATION "Huawei Technologies Co.,Ltd."
	CONTACT-INFO
	             "Huawei Industrial Base
	              Bantian, Longgang
	              Shenzhen 518129
	              People's Republic of China
	              Website: http://www.huawei.com
	              Email: support@huawei.com
	             "
	DESCRIPTION  "The mib is used for defining huawei's IPDSLAM PVCIPOA MIB objects."

        --  Revision history
        REVISION     "201109251600Z"
	DESCRIPTION  "V1.07, added hwIpDslamPvcIpoaTagMode to support configuring the VLAN tag-mode of IPoA."

        REVISION     "201008241600Z"
	DESCRIPTION  "V1.06, modified the description of hwIpDslamPvcIpoaAgeTimeout."

	REVISION     "201006251600Z"
	DESCRIPTION  "V1.05, modified the module identity."

	REVISION     "201003160000Z"
	DESCRIPTION  "
	             V1.04, modified the description of hwIpDslamPvcIpoaEnable, hwIpDslamPvcIpoaDefaultGatewayIp
	             and hwIpDslamPvcIpoaAgeTimeout.
	             "

	REVISION     "201001270000Z"
	DESCRIPTION  "
	             V1.03, added the definition for the alarm trap leaf hwIpDslamPvcIpoaSrcIpConflictTrap that is used
	             when the source IP address of the IPoA user conflicts.
	             Added the definition for hwIpDslamPvcIpoaOriginVpi, hwIpDslamPvcIpoaOriginVci,
	             hwIpDslamPvcIpoaNewVpi, hwIpDslamPvcIpoaNewVci, hwIpDslamPvcIpoaConflictIpAddress that is bound
	             to the alarm trap leaf hwIpDslamPvcIpoaSrcIpConflictTrap used when the source IP address of the
	             IPoA user conflicts.
	             "

	REVISION     "201001090900Z"
	DESCRIPTION  "V1.02, modified the description and fix the compiling error."

	REVISION     "200806100900Z"
	DESCRIPTION  "V1.01, change in this revision:
	             - Removed the description in Chinese, and keep it in English
	             all through the file.
	             "

	REVISION     "200407050000Z"
	DESCRIPTION  "V1.00, initial version."

        ::= { huaweiUtility 46}


	hwIpDslamPvcIpoaEnable OBJECT-TYPE
		SYNTAX       TruthValue
		MAX-ACCESS   read-write
		STATUS       current
		DESCRIPTION
			     "
			     Indicates the global enable switch of IPoA-to-IPoE conversion.
			     Options:
			     1. true(1)  -Enable the global switch of IPoA-to-IPoE conversion
			     2. false(2) -Disable the global switch of IPoA-to-IPoE conversion
			     Default: false(2)
			     "
		::= { hwIpDslamPvcIpoa 1 }


	hwIpDslamPvcIpoaDefaultGatewayIp OBJECT-TYPE
		SYNTAX       IpAddress
		MAX-ACCESS   read-write
		STATUS       current
		DESCRIPTION
			     "
			     Indicates the IPoA default gateway.
			     "
		::= { hwIpDslamPvcIpoa 2 }


	hwIpDslamPvcIpoaAgeTimeout OBJECT-TYPE
		SYNTAX       Integer32(180..1200)
		UNITS 	     "minute"
		MAX-ACCESS   read-write
		STATUS       current
		DESCRIPTION
			     "
			     Indicates the aging time of an IPoA user.
			     Unit: minute
			     DEFVAL { 1200 }
			     "
		::= { hwIpDslamPvcIpoa 3 }


    hwIpDslamPvcIpoaTrapsVbOids OBJECT IDENTIFIER ::= { hwIpDslamPvcIpoa 4 }

    -- Add Alarm Trap OID
    hwIpDslamPvcIpoaOriginVpi OBJECT-TYPE
	    SYNTAX Integer32 (0..4095)
	    MAX-ACCESS	accessible-for-notify
	    STATUS current
	    DESCRIPTION
		    "The original VPI in the source IP address conflict of the IPoA user."
	    ::= { hwIpDslamPvcIpoaTrapsVbOids 1 }

    hwIpDslamPvcIpoaOriginVci OBJECT-TYPE
	    SYNTAX Integer32 (32..1023)
	    MAX-ACCESS	accessible-for-notify
	    STATUS current
	    DESCRIPTION
		    "The original VCI in the source IP address conflict of the IPoA user."
	    ::= { hwIpDslamPvcIpoaTrapsVbOids 2 }

    hwIpDslamPvcIpoaNewVpi OBJECT-TYPE
	    SYNTAX Integer32 (0..4095)
	    MAX-ACCESS	accessible-for-notify
	    STATUS current
	    DESCRIPTION
		    "The new VPI in the source IP address conflict of the IPoA user."
	    ::= { hwIpDslamPvcIpoaTrapsVbOids 3 }

    hwIpDslamPvcIpoaNewVci OBJECT-TYPE
	    SYNTAX Integer32 (32..1023)
	    MAX-ACCESS	accessible-for-notify
	    STATUS current
	    DESCRIPTION
		    "The new VCI in the source IP address conflict of the IPoA user."
	    ::= { hwIpDslamPvcIpoaTrapsVbOids 4 }

    hwIpDslamPvcIpoaConflictIpAddress OBJECT-TYPE
	    SYNTAX IpAddress
	    MAX-ACCESS	accessible-for-notify
	    STATUS current
	    DESCRIPTION
		    "The IP address in the source IP address conflict of the IPoA user."
	    ::= { hwIpDslamPvcIpoaTrapsVbOids 5 }

    -- Add Trap Node
    hwIpDslamPvcIpoaTraps OBJECT IDENTIFIER ::= { hwIpDslamPvcIpoa 5 }

    hwIpDslamPvcIpoaAlarmTraps OBJECT IDENTIFIER ::= { hwIpDslamPvcIpoaTraps 1 }

    -- Alarm traps
	hwIpDslamPvcIpoaSrcIpConflictTrap NOTIFICATION-TYPE
		OBJECTS {
		        hwSlotIndex,
                hwPortIndex,
		        hwIpDslamPvcIpoaOriginVpi,
		        hwIpDslamPvcIpoaOriginVci,
		        hwSlotIndex,
                hwPortIndex,
		        hwIpDslamPvcIpoaNewVpi,
		        hwIpDslamPvcIpoaNewVci,
		        hwIpDslamPvcIpoaConflictIpAddress
				}
		STATUS	current
		DESCRIPTION
			"
			This trap is sent when the source IP address of the IPoA user conflicts.
			hwSlotIndex:The original slot ID in the source IP address conflict of the IPoA user.
			hwPortIndex:The original port ID in the source IP address conflict of the IPoA user.
			hwIpDslamPvcIpoaOriginVpi:The original VPI in the source IP address conflict of the IPoA user.
			hwIpDslamPvcIpoaOriginVci:The original VCI in the source IP address conflict of the IPoA user.
			hwSlotIndex:The new slot ID in the source IP address conflict of the IPoA user.
			hwPortIndex:The new port ID in the source IP address conflict of the IPoA user.
			hwIpDslamPvcIpoaNewVpi:The new VPI in the source IP address conflict of the IPoA user.
			hwIpDslamPvcIpoaNewVci:The new VCI in the source IP address conflict of the IPoA user.
			hwIpDslamPvcIpoaConflictIpAddress:The IP address in the source IP address conflict of the IPoA user.
			"
		::= { hwIpDslamPvcIpoaAlarmTraps 0 1 }


	hwIpDslamPvcIpoaTagMode OBJECT-TYPE
		SYNTAX INTEGER
		  {
		    single(1),
		    double(2)
		  }
		MAX-ACCESS   read-write
		STATUS       current
		DESCRIPTION
			     "
			     Indicates the VLAN tag-mode of IPoA.
			     Options:
			     1. single(1)  -Set IPoA single tag-mode
			     2. double(2)  -Set IPoA double tag-mode
			     Default: single(1)
			     "
		::= { hwIpDslamPvcIpoa 6 }


	END
