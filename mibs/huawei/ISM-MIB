--
-- ISM-MIB.mib
-- MIB generated by MG-SOFT Visual MIB Builder Version 4.0 Build 347
-- Thursday, March 27, 2014 at 11:38:12
--

	ISM-MIB DEFINITIONS ::= BEGIN

		IMPORTS
			OBJECT-GROUP, MODULE-COMPLIANCE
				FROM SNMPv2-CONF
			enterprises, Unsigned32, OBJECT-TYPE, MODULE-IDENTITY
				FROM SNMPv2-SMI
			DisplayString, DateAndTime, RowStatus, TEXTUAL-CONVENTION
				FROM SNMPv2-TC;


		hwStorage MODULE-IDENTITY
			LAST-UPDATED "201008111239Z"		-- August 11, 2010 at 12:39 GMT
			ORGANIZATION
				"Huawei Technologies Co.,Ltd."
			CONTACT-INFO
				"Huawei Industrial Base
				Bantian, Longgang
				Shenzhen 518129
				People's Republic of China
				Website: http://www.huawei.com
				Email: support@huawei.com"
			DESCRIPTION
				"Description."
			REVISION "201304061354Z"		-- April 06, 2013 at 13:54 GMT
			DESCRIPTION
				" "
			::= { huaweistorage 4 }



--
-- Textual conventions
--

		NodeCodeString ::= TEXTUAL-CONVENTION
			DISPLAY-HINT
				"255a"
			STATUS current
			DESCRIPTION
				"characters in length."
			SYNTAX OCTET STRING (SIZE (15..17))


--
-- Node definitions
--

		huaweistorage OBJECT IDENTIFIER ::= { enterprises 34774 }


		hwISM OBJECT IDENTIFIER ::= { hwStorage 1 }


		hwMIB OBJECT IDENTIFIER ::= { hwISM 22 }


		hwInfoControllerTable OBJECT-TYPE
			SYNTAX SEQUENCE OF HwInfoControllerEntry
			MAX-ACCESS not-accessible
			STATUS current
			DESCRIPTION
				" "
			::= { hwMIB 1 }


		hwInfoControllerEntry OBJECT-TYPE
			SYNTAX HwInfoControllerEntry
			MAX-ACCESS not-accessible
			STATUS current
			DESCRIPTION
				" "
			INDEX { hwInfoControllerID }
			::= { hwInfoControllerTable 1 }


		HwInfoControllerEntry ::=
			SEQUENCE {
				hwInfoControllerID
					Unsigned32,
				hwInfoControllerIP
					OCTET STRING,
				hwInfoControllerIsMaster
					Unsigned32,
				hwInfoControllerCpuUsingRatio
					Unsigned32,
				hwInfoControllerMemoryUsingRatio
					Unsigned32,
				hwInfoControllerVersion
					OCTET STRING,
				hwInfoControllerStatus
					Unsigned32,
				hwInfoControllerDescription
					OCTET STRING
			 }

		hwInfoControllerID OBJECT-TYPE
			SYNTAX Unsigned32
			MAX-ACCESS read-only
			STATUS current
			DESCRIPTION
				"0:A
				1:B"
			::= { hwInfoControllerEntry 1 }


		hwInfoControllerIP OBJECT-TYPE
			SYNTAX OCTET STRING
			MAX-ACCESS read-only
			STATUS current
			DESCRIPTION
				" "
			::= { hwInfoControllerEntry 2 }


		hwInfoControllerIsMaster OBJECT-TYPE
			SYNTAX Unsigned32
			MAX-ACCESS read-only
			STATUS current
			DESCRIPTION
				"0:Secondary
				1:Primary"
			::= { hwInfoControllerEntry 3 }


		hwInfoControllerCpuUsingRatio OBJECT-TYPE
			SYNTAX Unsigned32
			UNITS "%"
			MAX-ACCESS read-only
			STATUS current
			DESCRIPTION
				" "
			::= { hwInfoControllerEntry 4 }


		hwInfoControllerMemoryUsingRatio OBJECT-TYPE
			SYNTAX Unsigned32
			UNITS "%"
			MAX-ACCESS read-only
			STATUS current
			DESCRIPTION
				" "
			::= { hwInfoControllerEntry 5 }


		hwInfoControllerVersion OBJECT-TYPE
			SYNTAX OCTET STRING
			MAX-ACCESS read-only
			STATUS current
			DESCRIPTION
				" "
			::= { hwInfoControllerEntry 6 }


		hwInfoControllerStatus OBJECT-TYPE
			SYNTAX Unsigned32
			MAX-ACCESS read-only
			STATUS current
			DESCRIPTION
				"0:Offline
				1:Normal
				2:Abnormal
				3:Not exist"
			::= { hwInfoControllerEntry 7 }


		hwInfoControllerDescription OBJECT-TYPE
			SYNTAX OCTET STRING
			MAX-ACCESS read-only
			STATUS current
			DESCRIPTION
				" "
			::= { hwInfoControllerEntry 8 }


		hwInfoPhysicDiskTable OBJECT-TYPE
			SYNTAX SEQUENCE OF HwInfoPhysicDiskEntry
			MAX-ACCESS not-accessible
			STATUS current
			DESCRIPTION
				" "
			::= { hwMIB 2 }


		hwInfoPhysicDiskEntry OBJECT-TYPE
			SYNTAX HwInfoPhysicDiskEntry
			MAX-ACCESS not-accessible
			STATUS current
			DESCRIPTION
				" "
			INDEX { hwInfoPhysicDiskFrameID, hwInfoPhysicDiskSlotID }
			::= { hwInfoPhysicDiskTable 1 }


		HwInfoPhysicDiskEntry ::=
			SEQUENCE {
				hwInfoPhysicDiskFrameID
					Unsigned32,
				hwInfoPhysicDiskSlotID
					Unsigned32,
				hwInfoPhysicDiskStatus
					Unsigned32,
				hwInfoPhysicDiskSZType
					Unsigned32,
				hwInfoPhysicDiskSZVendor
					OCTET STRING,
				hwInfoPhysicDiskSZModel
					OCTET STRING,
				hwInfoPhysicDiskSZSerial
					OCTET STRING,
				hwInfoPhysicDiskSZFirmware
					OCTET STRING,
				hwInfoPhysicDiskSpinSpeed
					Unsigned32,
				hwInfoPhysicDiskCurrentSpeed
					Unsigned32,
				hwInfoPhysicDiskRawCapacity
					Unsigned32
			 }

		hwInfoPhysicDiskFrameID OBJECT-TYPE
			SYNTAX Unsigned32
			MAX-ACCESS read-only
			STATUS current
			DESCRIPTION
				"Description."
			::= { hwInfoPhysicDiskEntry 1 }


		hwInfoPhysicDiskSlotID OBJECT-TYPE
			SYNTAX Unsigned32
			MAX-ACCESS read-only
			STATUS current
			DESCRIPTION
				"Description."
			::= { hwInfoPhysicDiskEntry 2 }


		hwInfoPhysicDiskStatus OBJECT-TYPE
			SYNTAX Unsigned32
			MAX-ACCESS read-only
			STATUS current
			DESCRIPTION
				"0:Normal
				3:Fault
				196611:Fault
				771:Fault
				197379:Fault
				4:Off line
				773:Single path
				196613:Single path
				5:Single path
				196608:Normal
				768:Normal
				9:Write protect
				777:Write protect
				196617:Write protect
				197385:Write protect
				6:Invalid
				197382:Invalid
				10:Isolated
				999:Invalid"
			::= { hwInfoPhysicDiskEntry 3 }


		hwInfoPhysicDiskSZType OBJECT-TYPE
			SYNTAX Unsigned32
			MAX-ACCESS read-only
			STATUS current
			DESCRIPTION
				"0:FC
				1:SAS
				2:SATA
				3:SSD
				4:NL SAS
				9:Invalid"
			::= { hwInfoPhysicDiskEntry 4 }


		hwInfoPhysicDiskSZVendor OBJECT-TYPE
			SYNTAX OCTET STRING
			MAX-ACCESS read-only
			STATUS current
			DESCRIPTION
				"Description."
			::= { hwInfoPhysicDiskEntry 5 }


		hwInfoPhysicDiskSZModel OBJECT-TYPE
			SYNTAX OCTET STRING
			MAX-ACCESS read-only
			STATUS current
			DESCRIPTION
				"Description."
			::= { hwInfoPhysicDiskEntry 6 }


		hwInfoPhysicDiskSZSerial OBJECT-TYPE
			SYNTAX OCTET STRING
			UNITS "GB"
			MAX-ACCESS read-only
			STATUS current
			DESCRIPTION
				" "
			::= { hwInfoPhysicDiskEntry 7 }


		hwInfoPhysicDiskSZFirmware OBJECT-TYPE
			SYNTAX OCTET STRING
			MAX-ACCESS read-only
			STATUS current
			DESCRIPTION
				" "
			::= { hwInfoPhysicDiskEntry 8 }


		hwInfoPhysicDiskSpinSpeed OBJECT-TYPE
			SYNTAX Unsigned32
			UNITS "RPM"
			MAX-ACCESS read-only
			STATUS current
			DESCRIPTION
				"
				"
			::= { hwInfoPhysicDiskEntry 9 }


		hwInfoPhysicDiskCurrentSpeed OBJECT-TYPE
			SYNTAX Unsigned32
			UNITS "0.1Gpbs"
			MAX-ACCESS read-only
			STATUS current
			DESCRIPTION
				" "
			::= { hwInfoPhysicDiskEntry 10 }


		hwInfoPhysicDiskRawCapacity OBJECT-TYPE
			SYNTAX Unsigned32
			UNITS "GB"
			MAX-ACCESS read-only
			STATUS current
			DESCRIPTION
				"Description."
			::= { hwInfoPhysicDiskEntry 11 }


		hwInfoLogicDiskTable OBJECT-TYPE
			SYNTAX SEQUENCE OF HwInfoLogicDiskEntry
			MAX-ACCESS not-accessible
			STATUS current
			DESCRIPTION
				" "
			::= { hwMIB 3 }


		hwInfoLogicDiskEntry OBJECT-TYPE
			SYNTAX HwInfoLogicDiskEntry
			MAX-ACCESS not-accessible
			STATUS current
			DESCRIPTION
				" "
			INDEX { hwInfoLogicDiskFrameID, hwInfoLogicDiskSlotID }
			::= { hwInfoLogicDiskTable 1 }


		HwInfoLogicDiskEntry ::=
			SEQUENCE {
				hwInfoLogicDiskFrameID
					Unsigned32,
				hwInfoLogicDiskSlotID
					Unsigned32,
				hwInfoLogicDiskLogicStatus
					Unsigned32,
				hwInfoLogicDiskLogicType
					Unsigned32,
				hwInfoLogicDiskSize
					Unsigned32
			 }

		hwInfoLogicDiskFrameID OBJECT-TYPE
			SYNTAX Unsigned32
			MAX-ACCESS read-only
			STATUS current
			DESCRIPTION
				"Description."
			::= { hwInfoLogicDiskEntry 1 }


		hwInfoLogicDiskSlotID OBJECT-TYPE
			SYNTAX Unsigned32
			MAX-ACCESS read-only
			STATUS current
			DESCRIPTION
				"Description."
			::= { hwInfoLogicDiskEntry 2 }


		hwInfoLogicDiskLogicStatus OBJECT-TYPE
			SYNTAX Unsigned32
			MAX-ACCESS read-only
			STATUS current
			DESCRIPTION
				"1:Normal
				2:Fault
				3:Reconstruction is in progress
				4:Reconstructed
				5:Copyback is in process
				6:Free spare
				7:Used spare
				8:Precopying
				9:Invalid"
			::= { hwInfoLogicDiskEntry 3 }


		hwInfoLogicDiskLogicType OBJECT-TYPE
			SYNTAX Unsigned32
			MAX-ACCESS read-only
			STATUS current
			DESCRIPTION
				"0:Free
				1:Free
				2:Member
				3:Spare
				4:SmartCache Member
				9:Invalid"
			::= { hwInfoLogicDiskEntry 4 }


		hwInfoLogicDiskSize OBJECT-TYPE
			SYNTAX Unsigned32
			UNITS "GB"
			MAX-ACCESS read-only
			STATUS current
			DESCRIPTION
				"Description."
			::= { hwInfoLogicDiskEntry 5 }


		hwInfoPowerTable OBJECT-TYPE
			SYNTAX SEQUENCE OF HwInfoPowerEntry
			MAX-ACCESS not-accessible
			STATUS current
			DESCRIPTION
				" "
			::= { hwMIB 4 }


		hwInfoPowerEntry OBJECT-TYPE
			SYNTAX HwInfoPowerEntry
			MAX-ACCESS not-accessible
			STATUS current
			DESCRIPTION
				" "
			INDEX { hwInfoPowerID, hwInfoPowerSubrackID }
			::= { hwInfoPowerTable 1 }


		HwInfoPowerEntry ::=
			SEQUENCE {
				hwInfoPowerID
					Unsigned32,
				hwInfoPowerSubrackID
					Unsigned32,
				hwInfoPowerStatus
					Unsigned32,
				hwInfoPowerTemperature
					Unsigned32,
				hwInfoPowerVendor
					OCTET STRING,
				hwInfoPowerModle
					OCTET STRING,
				hwInfoPowerVersion
					OCTET STRING,
				hwInfoPowerDate
					OCTET STRING,
				hwInfoPowerType
					Unsigned32,
				hwInfoPowerSN
					OCTET STRING,
				hwInfoPowerDisplayID
					OCTET STRING,
				hwInfoPowerDescription
					OCTET STRING
			 }

		hwInfoPowerID OBJECT-TYPE
			SYNTAX Unsigned32
			MAX-ACCESS read-only
			STATUS current
			DESCRIPTION
				" "
			::= { hwInfoPowerEntry 1 }


		hwInfoPowerSubrackID OBJECT-TYPE
			SYNTAX Unsigned32
			MAX-ACCESS read-only
			STATUS current
			DESCRIPTION
				" "
			::= { hwInfoPowerEntry 2 }


		hwInfoPowerStatus OBJECT-TYPE
			SYNTAX Unsigned32
			MAX-ACCESS read-only
			STATUS current
			DESCRIPTION
				"0:Normal
				1:Not Exist
				2:No Input
				3:Voltage High
				4:Voltage Low
				5:Alarm
				6:Fault
				7:Switch Off
				9:Input Abnormal"
			::= { hwInfoPowerEntry 3 }


		hwInfoPowerTemperature OBJECT-TYPE
			SYNTAX Unsigned32
			UNITS "Degrees Celsius"
			MAX-ACCESS read-only
			STATUS current
			DESCRIPTION
				" "
			::= { hwInfoPowerEntry 4 }


		hwInfoPowerVendor OBJECT-TYPE
			SYNTAX OCTET STRING
			MAX-ACCESS read-only
			STATUS current
			DESCRIPTION
				" "
			::= { hwInfoPowerEntry 5 }


		hwInfoPowerModle OBJECT-TYPE
			SYNTAX OCTET STRING
			MAX-ACCESS read-only
			STATUS current
			DESCRIPTION
				" "
			::= { hwInfoPowerEntry 6 }


		hwInfoPowerVersion OBJECT-TYPE
			SYNTAX OCTET STRING
			MAX-ACCESS read-only
			STATUS current
			DESCRIPTION
				" "
			::= { hwInfoPowerEntry 7 }


		hwInfoPowerDate OBJECT-TYPE
			SYNTAX OCTET STRING
			MAX-ACCESS read-only
			STATUS current
			DESCRIPTION
				" "
			::= { hwInfoPowerEntry 8 }


		hwInfoPowerType OBJECT-TYPE
			SYNTAX Unsigned32
			MAX-ACCESS read-only
			STATUS current
			DESCRIPTION
				"0:DC(No Battery)
				1:AC(No Battery)
				2:AC(Battery)
				3:DC(Battery)
				4:AC"
			::= { hwInfoPowerEntry 9 }


		hwInfoPowerSN OBJECT-TYPE
			SYNTAX OCTET STRING
			MAX-ACCESS read-only
			STATUS current
			DESCRIPTION
				" "
			::= { hwInfoPowerEntry 10 }


		hwInfoPowerDisplayID OBJECT-TYPE
			SYNTAX OCTET STRING
			MAX-ACCESS read-only
			STATUS current
			DESCRIPTION
				" "
			::= { hwInfoPowerEntry 11 }


		hwInfoPowerDescription OBJECT-TYPE
			SYNTAX OCTET STRING
			MAX-ACCESS read-only
			STATUS current
			DESCRIPTION
				" "
			::= { hwInfoPowerEntry 12 }


		hwInfoBBUTable OBJECT-TYPE
			SYNTAX SEQUENCE OF HwInfoBBUEntry
			MAX-ACCESS not-accessible
			STATUS current
			DESCRIPTION
				" "
			::= { hwMIB 5 }


		hwInfoBBUEntry OBJECT-TYPE
			SYNTAX HwInfoBBUEntry
			MAX-ACCESS not-accessible
			STATUS current
			DESCRIPTION
				" "
			INDEX { hwInfoBBUID, hwInfoBBUControllerID }
			::= { hwInfoBBUTable 1 }


		HwInfoBBUEntry ::=
			SEQUENCE {
				hwInfoBBUID
					Unsigned32,
				hwInfoBBUControllerID
					Unsigned32,
				hwInfoBBUPresentStatus
					Unsigned32,
				hwInfoBBUStatus
					Unsigned32,
				hwInfoBBUCurrentVoltage
					Unsigned32,
				hwInfoBBUIsChargeFull
					Unsigned32,
				hwInfoBBUDischargeTime
					Unsigned32,
				hwInfoBBURemainLife
					Unsigned32,
				hwInfoBBUFWVersion
					OCTET STRING,
				hwInfoBBUELable
					OCTET STRING,
				hwInfoBBUChargeState
					Unsigned32
			 }

		hwInfoBBUID OBJECT-TYPE
			SYNTAX Unsigned32
			MAX-ACCESS read-only
			STATUS current
			DESCRIPTION
				" "
			::= { hwInfoBBUEntry 1 }


		hwInfoBBUControllerID OBJECT-TYPE
			SYNTAX Unsigned32
			MAX-ACCESS read-only
			STATUS current
			DESCRIPTION
				"0:A
				1:B"
			::= { hwInfoBBUEntry 2 }


		hwInfoBBUPresentStatus OBJECT-TYPE
			SYNTAX Unsigned32
			MAX-ACCESS read-only
			STATUS current
			DESCRIPTION
				"0:Online
				1:Not exist"
			::= { hwInfoBBUEntry 3 }


		hwInfoBBUStatus OBJECT-TYPE
			SYNTAX Unsigned32
			MAX-ACCESS read-only
			STATUS current
			DESCRIPTION
				"0:Normal
				1:Fault"
			::= { hwInfoBBUEntry 4 }


		hwInfoBBUCurrentVoltage OBJECT-TYPE
			SYNTAX Unsigned32
			UNITS "0.1V"
			MAX-ACCESS read-only
			STATUS current
			DESCRIPTION
				" "
			::= { hwInfoBBUEntry 5 }


		hwInfoBBUIsChargeFull OBJECT-TYPE
			SYNTAX Unsigned32
			MAX-ACCESS read-only
			STATUS current
			DESCRIPTION
				"0:Not full
				1:Full
				2:Sufficient
				3:Insufficient"
			::= { hwInfoBBUEntry 6 }


		hwInfoBBUDischargeTime OBJECT-TYPE
			SYNTAX Unsigned32
			UNITS "number of times"
			MAX-ACCESS read-only
			STATUS current
			DESCRIPTION
				" "
			::= { hwInfoBBUEntry 7 }


		hwInfoBBURemainLife OBJECT-TYPE
			SYNTAX Unsigned32
			UNITS "days"
			MAX-ACCESS read-only
			STATUS current
			DESCRIPTION
				" "
			::= { hwInfoBBUEntry 8 }


		hwInfoBBUFWVersion OBJECT-TYPE
			SYNTAX OCTET STRING
			MAX-ACCESS read-only
			STATUS current
			DESCRIPTION
				" "
			::= { hwInfoBBUEntry 9 }


		hwInfoBBUELable OBJECT-TYPE
			SYNTAX OCTET STRING
			MAX-ACCESS read-only
			STATUS current
			DESCRIPTION
				" "
			::= { hwInfoBBUEntry 10 }


		hwInfoBBUChargeState OBJECT-TYPE
			SYNTAX Unsigned32
			MAX-ACCESS read-only
			STATUS current
			DESCRIPTION
				"2:Free
				3:Charging
				5:Discharging"
			::= { hwInfoBBUEntry 11 }


		hwInfoFanTable OBJECT-TYPE
			SYNTAX SEQUENCE OF HwInfoFanEntry
			MAX-ACCESS not-accessible
			STATUS current
			DESCRIPTION
				" "
			::= { hwMIB 6 }


		hwInfoFanEntry OBJECT-TYPE
			SYNTAX HwInfoFanEntry
			MAX-ACCESS not-accessible
			STATUS current
			DESCRIPTION
				" "
			INDEX { hwInfoFanID, hwInfoFanSubrackId }
			::= { hwInfoFanTable 1 }


		HwInfoFanEntry ::=
			SEQUENCE {
				hwInfoFanID
					Unsigned32,
				hwInfoFanSubrackId
					Unsigned32,
				hwInfoFanRunningStatus
					Unsigned32,
				hwInfoFanRunningLevel
					Unsigned32,
				hwInfoFanRunningSection
					Unsigned32,
				hwInfoFanELable
					OCTET STRING,
				hwInfoFanDescription
					OCTET STRING
			 }

		hwInfoFanID OBJECT-TYPE
			SYNTAX Unsigned32
			MAX-ACCESS read-only
			STATUS current
			DESCRIPTION
				" "
			::= { hwInfoFanEntry 1 }


		hwInfoFanSubrackId OBJECT-TYPE
			SYNTAX Unsigned32
			MAX-ACCESS read-only
			STATUS current
			DESCRIPTION
				" "
			::= { hwInfoFanEntry 2 }


		hwInfoFanRunningStatus OBJECT-TYPE
			SYNTAX Unsigned32
			MAX-ACCESS read-only
			STATUS current
			DESCRIPTION
				"0:Normal
				1:Not Exist
				2:Fault"
			::= { hwInfoFanEntry 3 }


		hwInfoFanRunningLevel OBJECT-TYPE
			SYNTAX Unsigned32
			MAX-ACCESS read-only
			STATUS current
			DESCRIPTION
				" "
			::= { hwInfoFanEntry 4 }


		hwInfoFanRunningSection OBJECT-TYPE
			SYNTAX Unsigned32
			MAX-ACCESS read-only
			STATUS current
			DESCRIPTION
				"0:Very Low
				1:Low
				2:Medium
				3:High"
			::= { hwInfoFanEntry 5 }


		hwInfoFanELable OBJECT-TYPE
			SYNTAX OCTET STRING
			MAX-ACCESS read-only
			STATUS current
			DESCRIPTION
				" "
			::= { hwInfoFanEntry 6 }


		hwInfoFanDescription OBJECT-TYPE
			SYNTAX OCTET STRING
			MAX-ACCESS read-only
			STATUS current
			DESCRIPTION
				" "
			::= { hwInfoFanEntry 7 }


		hwInfoExpBoardTable OBJECT-TYPE
			SYNTAX SEQUENCE OF HwInfoExpBoardEntry
			MAX-ACCESS not-accessible
			STATUS current
			DESCRIPTION
				" "
			::= { hwMIB 7 }


		hwInfoExpBoardEntry OBJECT-TYPE
			SYNTAX HwInfoExpBoardEntry
			MAX-ACCESS not-accessible
			STATUS current
			DESCRIPTION
				" "
			INDEX { hwInfoExpBoardID, hwInfoExpBoardSubrackID }
			::= { hwInfoExpBoardTable 1 }


		HwInfoExpBoardEntry ::=
			SEQUENCE {
				hwInfoExpBoardSubrackID
					Unsigned32,
				hwInfoExpBoardID
					Unsigned32,
				hwInfoExpBoardStatus
					Unsigned32,
				hwInfoExpBoardLogicVersion
					OCTET STRING,
				hwInfoExpBoardPCBversion
					OCTET STRING,
				hwInfoExpBoardProduceInfo
					OCTET STRING,
				hwInfoExpBoardType
					Unsigned32
			 }

		hwInfoExpBoardSubrackID OBJECT-TYPE
			SYNTAX Unsigned32
			MAX-ACCESS read-only
			STATUS current
			DESCRIPTION
				" "
			::= { hwInfoExpBoardEntry 1 }


		hwInfoExpBoardID OBJECT-TYPE
			SYNTAX Unsigned32
			MAX-ACCESS read-only
			STATUS current
			DESCRIPTION
				"0:A
				1:B"
			::= { hwInfoExpBoardEntry 2 }


		hwInfoExpBoardStatus OBJECT-TYPE
			SYNTAX Unsigned32
			MAX-ACCESS read-only
			STATUS current
			DESCRIPTION
				"0:Abnormal
				1:Normal"
			::= { hwInfoExpBoardEntry 3 }


		hwInfoExpBoardLogicVersion OBJECT-TYPE
			SYNTAX OCTET STRING
			MAX-ACCESS read-only
			STATUS current
			DESCRIPTION
				" "
			::= { hwInfoExpBoardEntry 4 }


		hwInfoExpBoardPCBversion OBJECT-TYPE
			SYNTAX OCTET STRING
			MAX-ACCESS read-only
			STATUS current
			DESCRIPTION
				" "
			::= { hwInfoExpBoardEntry 5 }


		hwInfoExpBoardProduceInfo OBJECT-TYPE
			SYNTAX OCTET STRING
			MAX-ACCESS read-only
			STATUS current
			DESCRIPTION
				" "
			::= { hwInfoExpBoardEntry 6 }


		hwInfoExpBoardType OBJECT-TYPE
			SYNTAX Unsigned32
			MAX-ACCESS read-only
			STATUS current
			DESCRIPTION
				"0:SAS Expansion Module
				1:FC Expansion Module"
			::= { hwInfoExpBoardEntry 7 }


		hwInfoInterfaceTable OBJECT-TYPE
			SYNTAX SEQUENCE OF HwInfoInterfaceEntry
			MAX-ACCESS not-accessible
			STATUS current
			DESCRIPTION
				" "
			::= { hwMIB 8 }


		hwInfoInterfaceEntry OBJECT-TYPE
			SYNTAX HwInfoInterfaceEntry
			MAX-ACCESS not-accessible
			STATUS current
			DESCRIPTION
				" "
			INDEX { hwInfoInterfaceID, hwInfoInterfaceControllerID }
			::= { hwInfoInterfaceTable 1 }


		HwInfoInterfaceEntry ::=
			SEQUENCE {
				hwInfoInterfaceID
					Unsigned32,
				hwInfoInterfaceControllerID
					Unsigned32,
				hwInfoInterfaceType
					Unsigned32,
				hwInfoInterfaceStatus
					Unsigned32,
				hwInfoInterfaceLogicVersion
					OCTET STRING,
				hwInfoInterfacePCBVersion
					OCTET STRING,
				hwInfoInterfaceVendorInfo
					OCTET STRING,
				hwInfoInterfaceDescription
					OCTET STRING
			 }

		hwInfoInterfaceID OBJECT-TYPE
			SYNTAX Unsigned32
			MAX-ACCESS read-only
			STATUS current
			DESCRIPTION
				" "
			::= { hwInfoInterfaceEntry 1 }


		hwInfoInterfaceControllerID OBJECT-TYPE
			SYNTAX Unsigned32
			MAX-ACCESS read-only
			STATUS current
			DESCRIPTION
				"0:A
				1:B"
			::= { hwInfoInterfaceEntry 2 }


		hwInfoInterfaceType OBJECT-TYPE
			SYNTAX Unsigned32
			MAX-ACCESS read-only
			STATUS current
			DESCRIPTION
				"1:4 x 4G FC Interface Module
				2:2 x 4G FC Interface Module
				3:2 x 1G iSCSI Interface Module
				4:4 x SAS I Interface Module
				5:Swapped FC Interface Module
				6:2 x 10G iSCSI Interface Module
				7:1 x 8G FC Interface Module
				8:2 x 8G FC Interface Module
				9:2 x SAS II Interface Module
				10:4 x SAS II Interface Module
				11:2 FC + 2 GE Interface Module
				12:4 x 1G iSCSI Interface Module
				13:4 x 8G FC Interface Module
				16:4 x 3G MINI SAS Interface Module
				21:4 x 1G FCoE Interface Module
				22:2 x 6G SAS Interface Module
				23:2 x 6G SAS Interface Module"
			::= { hwInfoInterfaceEntry 3 }


		hwInfoInterfaceStatus OBJECT-TYPE
			SYNTAX Unsigned32
			MAX-ACCESS read-only
			STATUS current
			DESCRIPTION
				"0:Abnormal
				1:Normal
				2:Fault
				3:Unactivated
				4:Powering On
				5:Powering Off
				6:Power Off"
			::= { hwInfoInterfaceEntry 4 }


		hwInfoInterfaceLogicVersion OBJECT-TYPE
			SYNTAX OCTET STRING
			MAX-ACCESS read-only
			STATUS current
			DESCRIPTION
				" "
			::= { hwInfoInterfaceEntry 5 }


--
--
		hwInfoInterfacePCBVersion OBJECT-TYPE
			SYNTAX OCTET STRING
			MAX-ACCESS read-only
			STATUS current
			DESCRIPTION
				" "
			::= { hwInfoInterfaceEntry 6 }


		hwInfoInterfaceVendorInfo OBJECT-TYPE
			SYNTAX OCTET STRING
			MAX-ACCESS read-only
			STATUS current
			DESCRIPTION
				" "
			::= { hwInfoInterfaceEntry 7 }


		hwInfoInterfaceDescription OBJECT-TYPE
			SYNTAX OCTET STRING
			MAX-ACCESS read-only
			STATUS current
			DESCRIPTION
				" "
			::= { hwInfoInterfaceEntry 8 }


		hwInfoRAIDTable OBJECT-TYPE
			SYNTAX SEQUENCE OF HwInfoRAIDEntry
			MAX-ACCESS not-accessible
			STATUS current
			DESCRIPTION
				" "
			::= { hwMIB 9 }


		hwInfoRAIDEntry OBJECT-TYPE
			SYNTAX HwInfoRAIDEntry
			MAX-ACCESS not-accessible
			STATUS current
			DESCRIPTION
				" "
			INDEX { hwInfoRAIDID }
			::= { hwInfoRAIDTable 1 }


		HwInfoRAIDEntry ::=
			SEQUENCE {
				hwInfoRAIDID
					Unsigned32,
				hwInfoRAIDName
					OCTET STRING,
				hwInfoRAIDLevel
					Unsigned32,
				hwInfoRAIDFreeCapacity
					Unsigned32,
				hwInfoRAIDStatus
					Unsigned32,
				hwInfoRAIDDiskList
					OCTET STRING,
				hwInfoRAIDTotalSize
					Unsigned32
			 }

		hwInfoRAIDID OBJECT-TYPE
			SYNTAX Unsigned32
			MAX-ACCESS read-only
			STATUS current
			DESCRIPTION
				" "
			::= { hwInfoRAIDEntry 1 }


		hwInfoRAIDName OBJECT-TYPE
			SYNTAX OCTET STRING
			MAX-ACCESS read-only
			STATUS current
			DESCRIPTION
				" "
			::= { hwInfoRAIDEntry 2 }


		hwInfoRAIDLevel OBJECT-TYPE
			SYNTAX Unsigned32
			MAX-ACCESS read-only
			STATUS current
			DESCRIPTION
				"1:RAID10
				2:RAID5
				3:RAID0
				4:RAID1
				5:RAID6
				6:RAID50
				7:RAID3
				8:INVALID"
			::= { hwInfoRAIDEntry 3 }


		hwInfoRAIDFreeCapacity OBJECT-TYPE
			SYNTAX Unsigned32
			UNITS "MB"
			MAX-ACCESS read-only
			STATUS current
			DESCRIPTION
				" "
			::= { hwInfoRAIDEntry 4 }


		hwInfoRAIDStatus OBJECT-TYPE
			SYNTAX Unsigned32
			MAX-ACCESS read-only
			STATUS current
			DESCRIPTION
				"1:NORMAL
				2:FAULT
				3:DEGRADE
				4:INVALID"
			::= { hwInfoRAIDEntry 5 }


		hwInfoRAIDDiskList OBJECT-TYPE
			SYNTAX OCTET STRING
			MAX-ACCESS read-only
			STATUS current
			DESCRIPTION
				" "
			::= { hwInfoRAIDEntry 6 }


		hwInfoRAIDTotalSize OBJECT-TYPE
			SYNTAX Unsigned32
			UNITS "MB"
			MAX-ACCESS read-only
			STATUS current
			DESCRIPTION
				" "
			::= { hwInfoRAIDEntry 7 }


		hwInfoCacheTable OBJECT-TYPE
			SYNTAX SEQUENCE OF HwInfoCacheEntry
			MAX-ACCESS not-accessible
			STATUS current
			DESCRIPTION
				" "
			::= { hwMIB 10 }


		hwInfoCacheEntry OBJECT-TYPE
			SYNTAX HwInfoCacheEntry
			MAX-ACCESS not-accessible
			STATUS current
			DESCRIPTION
				" "
			INDEX { hwInfoCacheID }
			::= { hwInfoCacheTable 1 }


		HwInfoCacheEntry ::=
			SEQUENCE {
				hwInfoCacheID
					Unsigned32,
				hwInfoCacheTotalMemoryCapacity
					Unsigned32,
				hwInfoCacheSystemMemoryCapacity
					Unsigned32,
				hwInfoCacheCacheCapacity
					Unsigned32,
				hwInfoCacheCacheUtilization
					Unsigned32,
				hwInfoCacheCacheHitRatio
					Unsigned32,
				hwInfoCacheCurrentCacheWaterLevel
					Unsigned32,
				hwInfoCacheCacheHighWaterLevel
					Unsigned32,
				hwInfoCacheCacheLowWaterLevel
					Unsigned32,
				hwInfoCacheReadCacheUtility
					Unsigned32,
				hwInfoCacheWriteCacheUtililty
					Unsigned32,
				hwInfoCacheMirroringWriteCacheUtility
					Unsigned32,
				hwInfoCacheWhetherDirtyDataExists
					Unsigned32
			 }

		hwInfoCacheID OBJECT-TYPE
			SYNTAX Unsigned32
			MAX-ACCESS read-only
			STATUS current
			DESCRIPTION
				" "
			::= { hwInfoCacheEntry 1 }


		hwInfoCacheTotalMemoryCapacity OBJECT-TYPE
			SYNTAX Unsigned32
			UNITS "MB"
			MAX-ACCESS read-only
			STATUS current
			DESCRIPTION
				" "
			::= { hwInfoCacheEntry 2 }


		hwInfoCacheSystemMemoryCapacity OBJECT-TYPE
			SYNTAX Unsigned32
			UNITS "MB"
			MAX-ACCESS read-only
			STATUS current
			DESCRIPTION
				" "
			::= { hwInfoCacheEntry 3 }


		hwInfoCacheCacheCapacity OBJECT-TYPE
			SYNTAX Unsigned32
			UNITS "MB"
			MAX-ACCESS read-only
			STATUS current
			DESCRIPTION
				" "
			::= { hwInfoCacheEntry 4 }


		hwInfoCacheCacheUtilization OBJECT-TYPE
			SYNTAX Unsigned32
			UNITS "%"
			MAX-ACCESS read-only
			STATUS current
			DESCRIPTION
				" "
			::= { hwInfoCacheEntry 5 }


		hwInfoCacheCacheHitRatio OBJECT-TYPE
			SYNTAX Unsigned32
			UNITS "%"
			MAX-ACCESS read-only
			STATUS current
			DESCRIPTION
				" "
			::= { hwInfoCacheEntry 6 }


		hwInfoCacheCurrentCacheWaterLevel OBJECT-TYPE
			SYNTAX Unsigned32
			UNITS "%"
			MAX-ACCESS read-only
			STATUS current
			DESCRIPTION
				" "
			::= { hwInfoCacheEntry 7 }


		hwInfoCacheCacheHighWaterLevel OBJECT-TYPE
			SYNTAX Unsigned32
			UNITS "%"
			MAX-ACCESS read-only
			STATUS current
			DESCRIPTION
				" "
			::= { hwInfoCacheEntry 8 }


		hwInfoCacheCacheLowWaterLevel OBJECT-TYPE
			SYNTAX Unsigned32
			UNITS "%"
			MAX-ACCESS read-only
			STATUS current
			DESCRIPTION
				" "
			::= { hwInfoCacheEntry 9 }


		hwInfoCacheReadCacheUtility OBJECT-TYPE
			SYNTAX Unsigned32
			UNITS "%"
			MAX-ACCESS read-only
			STATUS current
			DESCRIPTION
				" "
			::= { hwInfoCacheEntry 10 }


		hwInfoCacheWriteCacheUtililty OBJECT-TYPE
			SYNTAX Unsigned32
			UNITS "%"
			MAX-ACCESS read-only
			STATUS current
			DESCRIPTION
				" "
			::= { hwInfoCacheEntry 11 }


		hwInfoCacheMirroringWriteCacheUtility OBJECT-TYPE
			SYNTAX Unsigned32
			UNITS "%"
			MAX-ACCESS read-only
			STATUS current
			DESCRIPTION
				" "
			::= { hwInfoCacheEntry 12 }


		hwInfoCacheWhetherDirtyDataExists OBJECT-TYPE
			SYNTAX Unsigned32
			MAX-ACCESS read-only
			STATUS current
			DESCRIPTION
				"0:No
				1:Yes"
			::= { hwInfoCacheEntry 13 }


		hwPerfRAIDTable OBJECT-TYPE
			SYNTAX SEQUENCE OF HwPerfRAIDEntry
			MAX-ACCESS not-accessible
			STATUS current
			DESCRIPTION
				" "
			::= { hwMIB 11 }


		hwPerfRAIDEntry OBJECT-TYPE
			SYNTAX HwPerfRAIDEntry
			MAX-ACCESS not-accessible
			STATUS current
			DESCRIPTION
				" "
			INDEX { hwPerfRAIDID }
			::= { hwPerfRAIDTable 1 }


		HwPerfRAIDEntry ::=
			SEQUENCE {
				hwPerfRAIDID
					Unsigned32,
				hwPerfRAIDCurrentBandwidth
					Unsigned32,
				hwPerfRAIDThroughput
					Unsigned32,
				hwPerfRAIDReadBandwidth
					Unsigned32,
				hwPerfRAIDReadThroughput
					Unsigned32,
				hwPerfRAIDWriteBandwidth
					Unsigned32,
				hwPerfRAIDWriteThroughput
					Unsigned32
			 }

		hwPerfRAIDID OBJECT-TYPE
			SYNTAX Unsigned32
			MAX-ACCESS read-only
			STATUS current
			DESCRIPTION
				" "
			::= { hwPerfRAIDEntry 1 }


		hwPerfRAIDCurrentBandwidth OBJECT-TYPE
			SYNTAX Unsigned32
			UNITS "MB/s"
			MAX-ACCESS read-only
			STATUS current
			DESCRIPTION
				" "
			::= { hwPerfRAIDEntry 2 }


		hwPerfRAIDThroughput OBJECT-TYPE
			SYNTAX Unsigned32
			UNITS "IO/s"
			MAX-ACCESS read-only
			STATUS current
			DESCRIPTION
				" "
			::= { hwPerfRAIDEntry 3 }


		hwPerfRAIDReadBandwidth OBJECT-TYPE
			SYNTAX Unsigned32
			UNITS "MB/s"
			MAX-ACCESS read-only
			STATUS current
			DESCRIPTION
				" "
			::= { hwPerfRAIDEntry 4 }


		hwPerfRAIDReadThroughput OBJECT-TYPE
			SYNTAX Unsigned32
			UNITS "IO/s"
			MAX-ACCESS read-only
			STATUS current
			DESCRIPTION
				" "
			::= { hwPerfRAIDEntry 5 }


		hwPerfRAIDWriteBandwidth OBJECT-TYPE
			SYNTAX Unsigned32
			UNITS "MB/s"
			MAX-ACCESS read-only
			STATUS current
			DESCRIPTION
				" "
			::= { hwPerfRAIDEntry 6 }


		hwPerfRAIDWriteThroughput OBJECT-TYPE
			SYNTAX Unsigned32
			UNITS "IO/s"
			MAX-ACCESS read-only
			STATUS current
			DESCRIPTION
				" "
			::= { hwPerfRAIDEntry 7 }


		hwPerfControllerTable OBJECT-TYPE
			SYNTAX SEQUENCE OF HwPerfControllerEntry
			MAX-ACCESS not-accessible
			STATUS current
			DESCRIPTION
				" "
			::= { hwMIB 12 }


		hwPerfControllerEntry OBJECT-TYPE
			SYNTAX HwPerfControllerEntry
			MAX-ACCESS not-accessible
			STATUS current
			DESCRIPTION
				" "
			INDEX { hwPerfControllerID }
			::= { hwPerfControllerTable 1 }


		HwPerfControllerEntry ::=
			SEQUENCE {
				hwPerfControllerID
					Unsigned32,
				hwPerfControllerCacheHit
					Unsigned32,
				hwPerfControllerThroughput
					Unsigned32,
				hwPerfControllerReadBandwidth
					Unsigned32,
				hwPerfControllerReadThroughput
					Unsigned32,
				hwPerfControllerWriteBandwidth
					Unsigned32,
				hwPerfControllerWriteThroughput
					Unsigned32,
				hwPerfControllerCPUUsage
					Unsigned32,
				hwPerfControllerMemoryUsage
					Unsigned32
			 }

		hwPerfControllerID OBJECT-TYPE
			SYNTAX Unsigned32
			MAX-ACCESS read-only
			STATUS current
			DESCRIPTION
				" "
			::= { hwPerfControllerEntry 1 }


		hwPerfControllerCacheHit OBJECT-TYPE
			SYNTAX Unsigned32
			UNITS "%"
			MAX-ACCESS read-only
			STATUS current
			DESCRIPTION
				" "
			::= { hwPerfControllerEntry 2 }


		hwPerfControllerThroughput OBJECT-TYPE
			SYNTAX Unsigned32
			UNITS "IO/s"
			MAX-ACCESS read-only
			STATUS current
			DESCRIPTION
				" "
			::= { hwPerfControllerEntry 3 }


		hwPerfControllerReadBandwidth OBJECT-TYPE
			SYNTAX Unsigned32
			UNITS "MB/s"
			MAX-ACCESS read-only
			STATUS current
			DESCRIPTION
				" "
			::= { hwPerfControllerEntry 4 }


		hwPerfControllerReadThroughput OBJECT-TYPE
			SYNTAX Unsigned32
			UNITS "IO/s"
			MAX-ACCESS read-only
			STATUS current
			DESCRIPTION
				" "
			::= { hwPerfControllerEntry 5 }


		hwPerfControllerWriteBandwidth OBJECT-TYPE
			SYNTAX Unsigned32
			UNITS "MB/s"
			MAX-ACCESS read-only
			STATUS current
			DESCRIPTION
				" "
			::= { hwPerfControllerEntry 6 }


		hwPerfControllerWriteThroughput OBJECT-TYPE
			SYNTAX Unsigned32
			UNITS "IO/s"
			MAX-ACCESS read-only
			STATUS current
			DESCRIPTION
				" "
			::= { hwPerfControllerEntry 7 }


		hwPerfControllerCPUUsage OBJECT-TYPE
			SYNTAX Unsigned32
			UNITS "%"
			MAX-ACCESS read-only
			STATUS current
			DESCRIPTION
				" "
			::= { hwPerfControllerEntry 8 }


		hwPerfControllerMemoryUsage OBJECT-TYPE
			SYNTAX Unsigned32
			UNITS "%"
			MAX-ACCESS read-only
			STATUS current
			DESCRIPTION
				" "
			::= { hwPerfControllerEntry 9 }


		hwPerfNASPortTable OBJECT-TYPE
			SYNTAX SEQUENCE OF HwPerfNASPortEntry
			MAX-ACCESS not-accessible
			STATUS current
			DESCRIPTION
				" "
			::= { hwMIB 13 }


		hwPerfNASPortEntry OBJECT-TYPE
			SYNTAX HwPerfNASPortEntry
			MAX-ACCESS not-accessible
			STATUS current
			DESCRIPTION
				" "
			INDEX { hwPerfNASPortIndex }
			::= { hwPerfNASPortTable 1 }


		HwPerfNASPortEntry ::=
			SEQUENCE {
				hwPerfNASPortIndex
					Unsigned32,
				hwPerfNASPortCurrentBandwidth
					Unsigned32,
				hwPerfNASPortReadBandwidth
					Unsigned32,
				hwPerfNASPortWriteBandwidth
					Unsigned32,
				hwPerfNASPortTotalPackages
					Unsigned32,
				hwPerfNASPortInboundPackages
					Unsigned32,
				hwPerfNASPortOutboundPackages
					Unsigned32,
				hwPerfNASPortDescription
					OCTET STRING
			 }

		hwPerfNASPortIndex OBJECT-TYPE
			SYNTAX Unsigned32
			MAX-ACCESS read-only
			STATUS current
			DESCRIPTION
				" "
			::= { hwPerfNASPortEntry 1 }


		hwPerfNASPortCurrentBandwidth OBJECT-TYPE
			SYNTAX Unsigned32
			UNITS "MB/s"
			MAX-ACCESS read-only
			STATUS current
			DESCRIPTION
				" "
			::= { hwPerfNASPortEntry 2 }


		hwPerfNASPortReadBandwidth OBJECT-TYPE
			SYNTAX Unsigned32
			UNITS "MB/s"
			MAX-ACCESS read-only
			STATUS current
			DESCRIPTION
				" "
			::= { hwPerfNASPortEntry 3 }


		hwPerfNASPortWriteBandwidth OBJECT-TYPE
			SYNTAX Unsigned32
			UNITS "MB/s"
			MAX-ACCESS read-only
			STATUS current
			DESCRIPTION
				" "
			::= { hwPerfNASPortEntry 4 }


		hwPerfNASPortTotalPackages OBJECT-TYPE
			SYNTAX Unsigned32
			UNITS "Packets/s"
			MAX-ACCESS read-only
			STATUS current
			DESCRIPTION
				" "
			::= { hwPerfNASPortEntry 5 }


		hwPerfNASPortInboundPackages OBJECT-TYPE
			SYNTAX Unsigned32
			UNITS "Packets/s"
			MAX-ACCESS read-only
			STATUS current
			DESCRIPTION
				" "
			::= { hwPerfNASPortEntry 6 }


		hwPerfNASPortOutboundPackages OBJECT-TYPE
			SYNTAX Unsigned32
			UNITS "Packets/s"
			MAX-ACCESS read-only
			STATUS current
			DESCRIPTION
				" "
			::= { hwPerfNASPortEntry 7 }


		hwPerfNASPortDescription OBJECT-TYPE
			SYNTAX OCTET STRING
			MAX-ACCESS read-only
			STATUS current
			DESCRIPTION
				" "
			::= { hwPerfNASPortEntry 8 }


		hwInfoControllerBoardTable OBJECT-TYPE
			SYNTAX SEQUENCE OF HwInfoControllerBoardEntry
			MAX-ACCESS not-accessible
			STATUS current
			DESCRIPTION
				" "
			::= { hwMIB 14 }


		hwInfoControllerBoardEntry OBJECT-TYPE
			SYNTAX HwInfoControllerBoardEntry
			MAX-ACCESS not-accessible
			STATUS current
			DESCRIPTION
				" "
			INDEX { hwInfoControllerBoardID }
			::= { hwInfoControllerBoardTable 1 }


		HwInfoControllerBoardEntry ::=
			SEQUENCE {
				hwInfoControllerBoardID
					Unsigned32,
				hwInfoControllerBoardStatus
					Unsigned32,
				hwInfoControllerBoardLogicVer
					OCTET STRING,
				hwInfoControllerBoardPCBVer
					OCTET STRING,
				hwInfoControllerBoardBIOSVer
					OCTET STRING,
				hwInfoControllerBoardELabel
					OCTET STRING,
				hwInfoControllerBoardType
					Unsigned32
			 }

		hwInfoControllerBoardID OBJECT-TYPE
			SYNTAX Unsigned32
			MAX-ACCESS read-only
			STATUS current
			DESCRIPTION
				" "
			::= { hwInfoControllerBoardEntry 1 }


		hwInfoControllerBoardStatus OBJECT-TYPE
			SYNTAX Unsigned32
			MAX-ACCESS read-only
			STATUS current
			DESCRIPTION
				" "
			::= { hwInfoControllerBoardEntry 2 }


		hwInfoControllerBoardLogicVer OBJECT-TYPE
			SYNTAX OCTET STRING
			MAX-ACCESS read-only
			STATUS current
			DESCRIPTION
				" "
			::= { hwInfoControllerBoardEntry 3 }


		hwInfoControllerBoardPCBVer OBJECT-TYPE
			SYNTAX OCTET STRING
			MAX-ACCESS read-only
			STATUS current
			DESCRIPTION
				" "
			::= { hwInfoControllerBoardEntry 4 }


		hwInfoControllerBoardBIOSVer OBJECT-TYPE
			SYNTAX OCTET STRING
			MAX-ACCESS read-only
			STATUS current
			DESCRIPTION
				" "
			::= { hwInfoControllerBoardEntry 5 }


		hwInfoControllerBoardELabel OBJECT-TYPE
			SYNTAX OCTET STRING
			MAX-ACCESS read-only
			STATUS current
			DESCRIPTION
				" "
			::= { hwInfoControllerBoardEntry 6 }


		hwInfoControllerBoardType OBJECT-TYPE
			SYNTAX Unsigned32
			MAX-ACCESS read-only
			STATUS current
			DESCRIPTION
				" "
			::= { hwInfoControllerBoardEntry 7 }


		hwInfoFileSystemTable OBJECT-TYPE
			SYNTAX SEQUENCE OF HwInfoFileSystemEntry
			MAX-ACCESS not-accessible
			STATUS current
			DESCRIPTION
				" "
			::= { hwMIB 15 }


		hwInfoFileSystemEntry OBJECT-TYPE
			SYNTAX HwInfoFileSystemEntry
			MAX-ACCESS not-accessible
			STATUS current
			DESCRIPTION
				" "
			INDEX { hwInfoFileSystemName }
			::= { hwInfoFileSystemTable 1 }


		HwInfoFileSystemEntry ::=
			SEQUENCE {
				hwInfoFileSystemName
					OCTET STRING,
				hwInfoFileSystemStatus
					OCTET STRING,
				hwInfoFileSystemSize
					OCTET STRING,
				hwInfoFileSystemLayout
					OCTET STRING,
				hwInfoFileSystemMirrors
					Unsigned32,
				hwInfoFileSystemColumns
					Unsigned32,
				hwInfoFileSystemUsage
					OCTET STRING,
				hwInfoFileSystemNFSShared
					OCTET STRING,
				hwInfoFileSystemCIFSShared
					OCTET STRING,
				hwInfoFileSystemSecondaryTier
					OCTET STRING,
				hwInfoFileSystemPoolList
					OCTET STRING
			 }

		hwInfoFileSystemName OBJECT-TYPE
			SYNTAX OCTET STRING
			MAX-ACCESS read-only
			STATUS current
			DESCRIPTION
				" "
			::= { hwInfoFileSystemEntry 1 }


		hwInfoFileSystemStatus OBJECT-TYPE
			SYNTAX OCTET STRING
			MAX-ACCESS read-only
			STATUS current
			DESCRIPTION
				" "
			::= { hwInfoFileSystemEntry 2 }


		hwInfoFileSystemSize OBJECT-TYPE
			SYNTAX OCTET STRING
			MAX-ACCESS read-only
			STATUS current
			DESCRIPTION
				" "
			::= { hwInfoFileSystemEntry 3 }


		hwInfoFileSystemLayout OBJECT-TYPE
			SYNTAX OCTET STRING
			UNITS "Degrees Celsius"
			MAX-ACCESS read-only
			STATUS current
			DESCRIPTION
				" "
			::= { hwInfoFileSystemEntry 4 }


		hwInfoFileSystemMirrors OBJECT-TYPE
			SYNTAX Unsigned32
			MAX-ACCESS read-only
			STATUS current
			DESCRIPTION
				" "
			::= { hwInfoFileSystemEntry 5 }


		hwInfoFileSystemColumns OBJECT-TYPE
			SYNTAX Unsigned32
			MAX-ACCESS read-only
			STATUS current
			DESCRIPTION
				" "
			::= { hwInfoFileSystemEntry 6 }


		hwInfoFileSystemUsage OBJECT-TYPE
			SYNTAX OCTET STRING
			MAX-ACCESS read-only
			STATUS current
			DESCRIPTION
				" "
			::= { hwInfoFileSystemEntry 7 }


		hwInfoFileSystemNFSShared OBJECT-TYPE
			SYNTAX OCTET STRING
			MAX-ACCESS read-only
			STATUS current
			DESCRIPTION
				" "
			::= { hwInfoFileSystemEntry 8 }


		hwInfoFileSystemCIFSShared OBJECT-TYPE
			SYNTAX OCTET STRING
			MAX-ACCESS read-only
			STATUS current
			DESCRIPTION
				" "
			::= { hwInfoFileSystemEntry 9 }


		hwInfoFileSystemSecondaryTier OBJECT-TYPE
			SYNTAX OCTET STRING
			MAX-ACCESS read-only
			STATUS current
			DESCRIPTION
				" "
			::= { hwInfoFileSystemEntry 10 }


		hwInfoFileSystemPoolList OBJECT-TYPE
			SYNTAX OCTET STRING
			MAX-ACCESS read-only
			STATUS current
			DESCRIPTION
				" "
			::= { hwInfoFileSystemEntry 11 }


		hwInfoClusterNodesTable OBJECT-TYPE
			SYNTAX SEQUENCE OF HwInfoClusterNodesEntry
			MAX-ACCESS not-accessible
			STATUS current
			DESCRIPTION
				" "
			::= { hwMIB 16 }


		hwInfoClusterNodesEntry OBJECT-TYPE
			SYNTAX HwInfoClusterNodesEntry
			MAX-ACCESS not-accessible
			STATUS current
			DESCRIPTION
				" "
			INDEX { hwInfoClusterNodesID }
			::= { hwInfoClusterNodesTable 1 }


		HwInfoClusterNodesEntry ::=
			SEQUENCE {
				hwInfoClusterNodesID
					Unsigned32,
				hwInfoClusterNodesName
					OCTET STRING,
				hwInfoClusterNodesIsMaster
					Unsigned32,
				hwInfoClusterNodesStatus
					Unsigned32,
				hwInfoClusterNodesRuningStatus
					Unsigned32,
				hwInfoClusterNodesIP
					OCTET STRING
			 }

		hwInfoClusterNodesID OBJECT-TYPE
			SYNTAX Unsigned32
			MAX-ACCESS read-only
			STATUS current
			DESCRIPTION
				" "
			::= { hwInfoClusterNodesEntry 1 }


		hwInfoClusterNodesName OBJECT-TYPE
			SYNTAX OCTET STRING
			MAX-ACCESS read-only
			STATUS current
			DESCRIPTION
				" "
			::= { hwInfoClusterNodesEntry 2 }


		hwInfoClusterNodesIsMaster OBJECT-TYPE
			SYNTAX Unsigned32
			MAX-ACCESS read-only
			STATUS current
			DESCRIPTION
				" "
			::= { hwInfoClusterNodesEntry 3 }


		hwInfoClusterNodesStatus OBJECT-TYPE
			SYNTAX Unsigned32
			MAX-ACCESS read-only
			STATUS current
			DESCRIPTION
				" "
			::= { hwInfoClusterNodesEntry 4 }


		hwInfoClusterNodesRuningStatus OBJECT-TYPE
			SYNTAX Unsigned32
			UNITS "0.1V"
			MAX-ACCESS read-only
			STATUS current
			DESCRIPTION
				" "
			::= { hwInfoClusterNodesEntry 5 }


		hwInfoClusterNodesIP OBJECT-TYPE
			SYNTAX OCTET STRING
			MAX-ACCESS read-only
			STATUS current
			DESCRIPTION
				" "
			::= { hwInfoClusterNodesEntry 6 }


		hwInfoNasControllerTable OBJECT-TYPE
			SYNTAX SEQUENCE OF HwInfoNasControllerEntry
			MAX-ACCESS not-accessible
			STATUS current
			DESCRIPTION
				" "
			::= { hwMIB 17 }


		hwInfoNasControllerEntry OBJECT-TYPE
			SYNTAX HwInfoNasControllerEntry
			MAX-ACCESS not-accessible
			STATUS current
			DESCRIPTION
				" "
			INDEX { hwInfoNasControllerName }
			::= { hwInfoNasControllerTable 1 }


		HwInfoNasControllerEntry ::=
			SEQUENCE {
				hwInfoNasControllerName
					OCTET STRING,
				hwInfoNasControllerBarCode
					OCTET STRING,
				hwInfoNasControllerFirmwareVersion
					OCTET STRING,
				hwInfoNasControllerDescription
					OCTET STRING
			 }

		hwInfoNasControllerName OBJECT-TYPE
			SYNTAX OCTET STRING
			MAX-ACCESS read-only
			STATUS current
			DESCRIPTION
				" "
			::= { hwInfoNasControllerEntry 1 }


		hwInfoNasControllerBarCode OBJECT-TYPE
			SYNTAX OCTET STRING
			MAX-ACCESS read-only
			STATUS current
			DESCRIPTION
				" "
			::= { hwInfoNasControllerEntry 2 }


		hwInfoNasControllerFirmwareVersion OBJECT-TYPE
			SYNTAX OCTET STRING
			MAX-ACCESS read-only
			STATUS current
			DESCRIPTION
				" "
			::= { hwInfoNasControllerEntry 3 }


		hwInfoNasControllerDescription OBJECT-TYPE
			SYNTAX OCTET STRING
			MAX-ACCESS read-only
			STATUS current
			DESCRIPTION
				" "
			::= { hwInfoNasControllerEntry 4 }


		isoConformance OBJECT IDENTIFIER ::= { iso 6 }


		isoGroups OBJECT IDENTIFIER ::= { isoConformance 1 }


		currentObjectGroup OBJECT-GROUP
			OBJECTS { hwInfoControllerBoardID, hwInfoControllerBoardType, hwInfoControllerBoardStatus, hwInfoControllerBoardLogicVer, hwInfoControllerBoardPCBVer,
				hwInfoControllerBoardBIOSVer, hwInfoControllerBoardELabel, hwPerfNASPortIndex, hwPerfNASPortCurrentBandwidth, hwPerfNASPortReadBandwidth,
				hwPerfNASPortWriteBandwidth, hwPerfNASPortTotalPackages, hwPerfNASPortInboundPackages, hwPerfNASPortOutboundPackages, hwInfoPhysicDiskFrameID,
				hwInfoPhysicDiskSlotID, hwInfoPhysicDiskStatus, hwInfoPhysicDiskSZType, hwInfoPhysicDiskSZVendor, hwInfoPhysicDiskSZModel,
				hwInfoPhysicDiskSZSerial, hwInfoPhysicDiskSZFirmware, hwInfoPhysicDiskSpinSpeed, hwInfoPhysicDiskCurrentSpeed, hwInfoPhysicDiskRawCapacity,
				hwInfoLogicDiskFrameID, hwInfoLogicDiskSlotID, hwInfoLogicDiskLogicStatus, hwInfoLogicDiskLogicType, hwInfoLogicDiskSize,
				hwInfoRAIDID, hwInfoRAIDName, hwInfoRAIDLevel, hwInfoRAIDFreeCapacity, hwInfoRAIDStatus,
				hwInfoRAIDDiskList, hwPerfRAIDID, hwPerfRAIDCurrentBandwidth, hwPerfRAIDThroughput, hwPerfRAIDReadBandwidth,
				hwPerfRAIDReadThroughput, hwPerfRAIDWriteBandwidth, hwPerfRAIDWriteThroughput, hwInfoFanRunningStatus, hwInfoFanRunningLevel,
				hwInfoFanRunningSection, hwInfoControllerIP, hwInfoControllerIsMaster, hwInfoControllerCpuUsingRatio, hwInfoControllerMemoryUsingRatio,
				hwInfoControllerVersion, hwInfoControllerStatus, hwInfoPowerSubrackID, hwInfoPowerTemperature, hwInfoPowerModle,
				hwInfoPowerVersion, hwInfoPowerDate, hwInfoPowerSN, hwInfoBBUControllerID, hwInfoBBUPresentStatus,
				hwInfoBBUIsChargeFull, hwInfoBBUDischargeTime, hwInfoBBURemainLife, hwInfoBBUFWVersion, hwInfoBBUELable,
				hwInfoBBUChargeState, hwInfoFanSubrackId, hwInfoExpBoardID, hwInfoExpBoardSubrackID, hwInfoExpBoardStatus,
				hwInfoExpBoardLogicVersion, hwInfoExpBoardPCBversion, hwInfoExpBoardProduceInfo, hwInfoExpBoardType, hwInfoInterfaceLogicVersion,
				hwInfoInterfacePCBVersion, hwInfoInterfaceVendorInfo, hwInfoControllerID, hwInfoPowerID, hwInfoPowerStatus,
				hwInfoPowerVendor, hwInfoPowerType, hwInfoBBUID, hwInfoBBUStatus, hwInfoBBUCurrentVoltage,
				hwInfoFanID, hwInfoInterfaceID, hwInfoInterfaceControllerID, hwInfoInterfaceType, hwInfoInterfaceStatus,
				hwPerfControllerID, hwPerfControllerCacheHit, hwPerfControllerThroughput, hwPerfControllerReadBandwidth, hwPerfControllerReadThroughput,
				hwPerfControllerWriteBandwidth, hwPerfControllerWriteThroughput, hwPerfControllerCPUUsage, hwInfoPowerDisplayID, hwInfoFanELable,
				hwInfoRAIDTotalSize, hwPerfNASPortDescription, hwInfoControllerDescription, hwInfoPowerDescription, hwInfoFanDescription,
				hwInfoInterfaceDescription, hwInfoFileSystemName, hwInfoFileSystemStatus, hwInfoFileSystemSize, hwInfoFileSystemLayout,
				hwInfoFileSystemMirrors, hwInfoFileSystemColumns, hwInfoFileSystemUsage, hwInfoFileSystemNFSShared, hwInfoFileSystemCIFSShared,
				hwInfoFileSystemSecondaryTier, hwInfoFileSystemPoolList, hwInfoClusterNodesID, hwInfoClusterNodesName, hwInfoClusterNodesIsMaster,
				hwInfoClusterNodesStatus, hwInfoClusterNodesRuningStatus, hwInfoClusterNodesIP, hwInfoNasControllerName, hwInfoNasControllerBarCode,
				hwInfoNasControllerFirmwareVersion, hwInfoNasControllerDescription, hwPerfControllerMemoryUsage, hwInfoCacheID, hwInfoCacheTotalMemoryCapacity,
				hwInfoCacheSystemMemoryCapacity, hwInfoCacheCacheCapacity, hwInfoCacheCacheUtilization, hwInfoCacheCacheHitRatio, hwInfoCacheCurrentCacheWaterLevel,
				hwInfoCacheCacheHighWaterLevel, hwInfoCacheCacheLowWaterLevel, hwInfoCacheReadCacheUtility, hwInfoCacheWriteCacheUtililty, hwInfoCacheMirroringWriteCacheUtility,
				hwInfoCacheWhetherDirtyDataExists }
			STATUS current
			DESCRIPTION
				"Enter the description of the created OBJECT-GROUP."
			::= { isoGroups 1 }


		isoCompliances OBJECT IDENTIFIER ::= { isoConformance 2 }


		basicCompliance MODULE-COMPLIANCE
			STATUS current
			DESCRIPTION
				"Enter the description of the created MODULE-COMPLIANCE."
			MODULE -- this module
				MANDATORY-GROUPS { currentObjectGroup }
			::= { isoCompliances 1 }



	END

--
-- ISM-MIB.mib
--
