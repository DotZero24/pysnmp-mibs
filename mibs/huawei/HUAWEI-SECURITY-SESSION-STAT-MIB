--  =================================================================
-- Copyright (C) 2014 by  HUAWEI TECHNOLOGIES. All rights reserved
--
-- Description:
-- Reference:
-- Version: V1.0
-- History:
-- 2014-04-09,initial version
-- =================================================================

    HUAWEI-SECURITY-SESSION-STAT-MIB DEFINITIONS ::= BEGIN

        IMPORTS
	   	IpAddress, Counter32, Gauge32, OBJECT-TYPE, MODULE-IDENTITY
			FROM SNMPv2-SMI
		MODULE-COMPLIANCE, OBJECT-GROUP, NOTIFICATION-GROUP
		            FROM SNMPv2-CONF
    		enterprises
		            FROM RFC1155-SMI;

        hwSecSessStatMIB MODULE-IDENTITY
            LAST-UPDATED "201404090000Z"
            ORGANIZATION
                "Huawei Technologies co.,Ltd."
            CONTACT-INFO
                "
                R&D BeiJing, Huawei Technologies co.,Ltd.
                Huawei Bld.,NO.3 Xinxi Rd.,
                Shang-Di Information Industry Base,
                Hai-Dian District Beijing P.R. China
                Zip:100085
                Http://www.huawei.com
                E-mail:support@huawei.com
                "
            DESCRIPTION
                "
                V1.00
                The HUAWEI-SECURITY-SESSION-STAT-MIB contains objects to manage the security statistics for firewall product.
                "
            ::= { hwSecurity 69 }

--
-- Node definitions
--
 	-- 1.3.6.1.4.1.2011
	huawei OBJECT IDENTIFIER ::= { enterprises 2011 }

        -- 1.3.6.1.4.1.2011.6
        huaweiUtility OBJECT IDENTIFIER ::= { huawei 6 }

        -- 1.3.6.1.4.1.2011.6.122
        hwSecurity OBJECT IDENTIFIER ::= { huaweiUtility 122 }

        -- 1.3.6.1.4.1.2011.6.122.69.1
        hwSecSessStatTable OBJECT IDENTIFIER ::= { hwSecSessStatMIB 1 }

        -- 1.3.6.1.4.1.2011.6.122.69.1.1
        hwSecSessStatEntry OBJECT IDENTIFIER ::= { hwSecSessStatTable 1 }

        -- 1.3.6.1.4.1.2011.6.122.69.1.1.1
        hwSecCurrSessThreshold OBJECT-TYPE
            SYNTAX INTEGER
            MAX-ACCESS read-only
            STATUS current
            DESCRIPTION
                "
                threshold for concurrent sessions
                "
            ::= { hwSecSessStatEntry 1 }

        -- 1.3.6.1.4.1.2011.6.122.69.1.1.2
        hwSecCurrSessNum OBJECT-TYPE
            SYNTAX INTEGER
            MAX-ACCESS read-only
            STATUS current
            DESCRIPTION
                "
                number of concurrent sessions
                "
            ::= { hwSecSessStatEntry 2 }

        -- 1.3.6.1.4.1.2011.6.122.69.1.1.3
        hwSecConSessThreshold OBJECT-TYPE
            SYNTAX INTEGER
            MAX-ACCESS read-only
            STATUS current
            DESCRIPTION
                "
                threshold for new sessions
                "
            ::= { hwSecSessStatEntry 3 }

        -- 1.3.6.1.4.1.2011.6.122.69.1.1.4
        hwSecConSessNum OBJECT-TYPE
            SYNTAX INTEGER
            MAX-ACCESS read-only
            STATUS current
            DESCRIPTION
                "
                number of new sessions
                "
            ::= { hwSecSessStatEntry 4 }

    END

--
-- HUAWEI-SECURITY-SESSION-STAT-MIB
--
