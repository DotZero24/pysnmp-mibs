-- ============================================================================
-- Copyright (C) 2012 by  HUAWEI TECHNOLOGIES. All rights reserved.
-- Description: This file is used for defining the MIB entities of voice statistics.
-- Reference:
-- Version: V1.14
-- ============================================================================

HUAWEI-MS-MIB DEFINITIONS ::= BEGIN
IMPORTS
    MODULE-IDENTITY, OBJECT-TYPE, NOTIFICATION-TYPE, private
        FROM SNMPv2-SMI
    MODULE-COMPLIANCE, OBJECT-GROUP, NOTIFICATION-GROUP
        FROM SNMPv2-CONF
    TEXTUAL-CONVENTION
        FROM SNMPv2-TC
    RowStatus,DateAndTime
        FROM SNMPv2-TC
    Integer32
        FROM SNMPv2-SMI
    Counter32
        FROM SNMPv2-SMI
    Counter64
        FROM SNMPv2-SMI
    huaweiUtility
        FROM HUAWEI-MIB
;

hwMs MODULE-IDENTITY
        LAST-UPDATED "201011150000Z"
        ORGANIZATION "Huawei Technologies Co.,Ltd."
        CONTACT-INFO
                     "Huawei Industrial Base
                      Bantian, Longgang
                      Shenzhen 518129
                      People's Republic of China
                      Website: http://www.huawei.com
                      Email: support@huawei.com
                     "
        DESCRIPTION
                     "
                     This file is used for defining the MIB entities of voice statistics.
                     "
--  Revision history

        REVISION    "201206130000Z"
        DESCRIPTION "V1.14, change in this revision:
                     - Added the hwMsE1ErrorTable.
                     - Corrected the SYNTAX.
                     "

--  Revision history

        REVISION    "201011150000Z"
        DESCRIPTION "V1.13, change in this revision:
                     - Added the following leaves into hwMsKPIStatTable:
                        hwMsAttCallsIn
                        hwMsAttCallsOut
                        hwMsAttSuccessCallsIn
                        hwMsAttSuccessCallsOut"

--  Revision history

        REVISION    "201007230000Z"
        DESCRIPTION "V1.12, change in this revision:
                    - Modified the description of all tables."


--  Revision history

        REVISION    "201007090000Z"
        DESCRIPTION "V1.11, change in this revision:
                    - Added the hwMsPeriodStatChangeTrap."

--  Revision history

        REVISION    "201003240000Z"
        DESCRIPTION "V1.10, change in this revision:
                    - Corrected the SYNTAX."
    ::= { huaweiUtility 41 }



-- enterprises OBJECT IDENTIFIER ::= { private 1 }

-- huawei OBJECT IDENTIFIER ::= { enterprises 2011 }

-- huaweiUtility OBJECT IDENTIFIER ::= { huawei 6 }


    hwMsPeriodTable OBJECT-TYPE
    SYNTAX      SEQUENCE OF HwMsPeriodEntry
    MAX-ACCESS  not-accessible
    STATUS      current
    DESCRIPTION
      "
        Indicates the period setting table.
        hwMsPeriodUnit, hwMsPeriodObject1, and hwMsPeriodObject2 are used in combinations as the index.
        The indexes of this table are hwMsPeriodUnit,hwMsPeriodObject1 and hwMsPeriodObject2.
        The indexes of this table are:
        hwMsPeriodUnit                                                               hwMsPeriodObject1   hwMsPeriodObject2
        1  MS_V5_INTERFACE_TRAF,         V5 interface message statistics             0                   V5INTERFACEID
        2  MS_V5_TRAFFIC,                V5 interface traffic statistics             0                   V5INTERFACEID
        3  MS_SYSTEM_TRAFFIC,            System traffic statistics                   0                   0
        4  MS_V5_TK_TRAFFIC,             V5 interface trunk traffic statistics       0                   V5INTERFACEID
        5  MS_FRAME_TK_TRAFFIC,          Service shelf trunk traffic statistics      0                   FRAMEID
        6  MS_SINGLE_SUBSCRIBER_TRAFFIC, Single subscriber traffic statistics        0                   USERINDEX   (FRAME<<24|SLOT<<16|PORT)
        7  MS_V5_BCHL_TRAF,              V5B channel message statistics              0                   V5INTERFACEID
        8  MS_E1_PORT_TRAF,              E1 port message statistics                  0                   E1PORTINDEX (FRAME<<24|SLOT<<16|PORT)
        9  MS_V5_PSTN_TRAF,              PSTN message statistics                     0                   V5INTERFACEID
        10 MS_V5_BCC_TRAF,               BCC message statistics                      0                   V5INTERFACEID
        11 MS_V5_CFID_TRAF,              Common Control Protocol message statistics  0                   V5INTERFACEID
        12 MS_V5_CPFE_TRAF,              Port Control Protocol message statistics    0                   V5INTERFACEID
        13 MS_V5_FE_TRAF,                Link Control Protocol message statistics    0                   V5INTERFACEID
        14 MS_V5_PROT_TRAF,              Protection protocol message statistics      0                   V5INTERFACEID
        15 MS_V5_ISDN_TRAF,              ISDN message statistics                     0                   V5INTERFACEID
        16 MS_V5_LOGCCHL_TRAF,           V5 logical C channel message statistics     V5INTERFACEID       V5LGCCHLID
        17 MS_H248_MG_INTERFACE_TRAF,    MG interface call statistics                0                   MGINTERFACEID
        18 MS_OVERLOAD_STATISTIC,        MG interface overload statistics            0                   MGINTERFACEID
        19 MS_SYSTEM_PERFORMANCE_STATS,  System performance statistics               0                   0
        20 MS_MG_OVERLOAD_STATISTIC,     VAG overload performance statistics         0                   MGINTERFACEID
        21 MS_E1_LAYER1_STATS,           E1 port physical layer statistics           0                   E1PORTINDEX (FRAME<<24|SLOT<<16|PORT)
        22 MS_BTOVERLOAD_AVERAGE_STATS   MG overload average statistics              0                   0
        23 MS_KPI_STATS                  Indicates the count of KPI                  0                   0
      "
    ::= { hwMs 1 }

  hwMsPeriodEntry OBJECT-TYPE
    SYNTAX      HwMsPeriodEntry
    MAX-ACCESS  not-accessible
    STATUS      current
    DESCRIPTION
      "
        Indicates the period setting table.
        hwMsPeriodUnit, hwMsPeriodObject1, and hwMsPeriodObject2 are used in combinations as the index.
        The indexes of this entry are hwMsPeriodUnit,hwMsPeriodObject1 and hwMsPeriodObject2.
        The indexes of this entry are:
        hwMsPeriodUnit                                                               hwMsPeriodObject1   hwMsPeriodObject2
        1  MS_V5_INTERFACE_TRAF,         V5 interface message statistics             0                   V5INTERFACEID
        2  MS_V5_TRAFFIC,                V5 interface traffic statistics             0                   V5INTERFACEID
        3  MS_SYSTEM_TRAFFIC,            System traffic statistics                   0                   0
        4  MS_V5_TK_TRAFFIC,             V5 interface trunk traffic statistics       0                   V5INTERFACEID
        5  MS_FRAME_TK_TRAFFIC,          Service shelf trunk traffic statistics      0                   FRAMEID
        6  MS_SINGLE_SUBSCRIBER_TRAFFIC, Single subscriber traffic statistics        0                   USERINDEX   (FRAME<<24|SLOT<<16|PORT)
        7  MS_V5_BCHL_TRAF,              V5B channel message statistics              0                   V5INTERFACEID
        8  MS_E1_PORT_TRAF,              E1 port message statistics                  0                   E1PORTINDEX (FRAME<<24|SLOT<<16|PORT)
        9  MS_V5_PSTN_TRAF,              PSTN message statistics                     0                   V5INTERFACEID
        10 MS_V5_BCC_TRAF,               BCC message statistics                      0                   V5INTERFACEID
        11 MS_V5_CFID_TRAF,              Common Control Protocol message statistics  0                   V5INTERFACEID
        12 MS_V5_CPFE_TRAF,              Port Control Protocol message statistics    0                   V5INTERFACEID
        13 MS_V5_FE_TRAF,                Link Control Protocol message statistics    0                   V5INTERFACEID
        14 MS_V5_PROT_TRAF,              Protection protocol message statistics      0                   V5INTERFACEID
        15 MS_V5_ISDN_TRAF,              ISDN message statistics                     0                   V5INTERFACEID
        16 MS_V5_LOGCCHL_TRAF,           V5 logical C channel message statistics     V5INTERFACEID       V5LGCCHLID
        17 MS_H248_MG_INTERFACE_TRAF,    MG interface call statistics                0                   MGINTERFACEID
        18 MS_OVERLOAD_STATISTIC,        MG interface overload statistics            0                   MGINTERFACEID
        19 MS_SYSTEM_PERFORMANCE_STATS,  System performance statistics               0                   0
        20 MS_MG_OVERLOAD_STATISTIC,     VAG overload performance statistics         0                   MGINTERFACEID
        21 MS_E1_LAYER1_STATS,           E1 port physical layer statistics           0                   E1PORTINDEX (FRAME<<24|SLOT<<16|PORT)
        22 MS_BTOVERLOAD_AVERAGE_STATS   MG overload average statistics              0                   0
        23 MS_KPI_STATS                  Indicates the count of KPI                  0                   0
      "
    INDEX    {
              hwMsPeriodUnit,
              hwMsPeriodObject1,
              hwMsPeriodObject2
             }
    ::= { hwMsPeriodTable 1 }

  HwMsPeriodEntry ::=
    SEQUENCE
    {
      hwMsPeriodUnit    Integer32,
      hwMsPeriodObject1 Integer32,
      hwMsPeriodObject2 Integer32,
      hwMsPeriodPeriod  INTEGER,
      hwMsPeriodOperate RowStatus
    }

  hwMsPeriodUnit OBJECT-TYPE
    SYNTAX      Integer32(1..22)
    MAX-ACCESS  not-accessible
    STATUS      current
    DESCRIPTION
        "
        Indicates the measurement unit. "
    ::= { hwMsPeriodEntry 1 }

  hwMsPeriodObject1 OBJECT-TYPE
    SYNTAX      Integer32
    MAX-ACCESS  not-accessible
    STATUS      current
    DESCRIPTION
        "
        Indicates measurement object 1. "
    ::= { hwMsPeriodEntry 2 }

  hwMsPeriodObject2 OBJECT-TYPE
    SYNTAX      Integer32
    MAX-ACCESS  not-accessible
    STATUS      current
    DESCRIPTION
        "
        Indicates measurement object 2. "
    ::= { hwMsPeriodEntry 3 }

  hwMsPeriodPeriod OBJECT-TYPE
    SYNTAX      INTEGER{fifteenmin(1),hour(2),day(3),fivemin(4)}
    MAX-ACCESS  read-create
    STATUS      current
    DESCRIPTION
        "
        Indicates the measurement period.
        Options:
        1. fifteenmin(1) -indicates that the measurement period is 15 minutes
        2. hour(2)       -indicates that the measurement period is 1 hour
        3. day(3)        -indicates that the measurement period is 1 day
        4. fivemin(4)    -indicates that the measurement period is 5 minutes
        "
    ::= { hwMsPeriodEntry 4 }

  hwMsPeriodOperate OBJECT-TYPE
    SYNTAX      RowStatus
    MAX-ACCESS  read-create
    STATUS      current
    DESCRIPTION
        "
        Indicates the period setting table, row status. "
    ::= { hwMsPeriodEntry 5 }

  hwMsV5InterfaceTable OBJECT-TYPE
    SYNTAX      SEQUENCE OF HwMsV5InterfaceEntry
    MAX-ACCESS  not-accessible
    STATUS      current
    DESCRIPTION
        "
        Indicates the V5 interface message statistics table.
        The index of this table is hwV5InterfaceID."
    ::= { hwMs 2 }

  hwMsV5InterfaceEntry OBJECT-TYPE
    SYNTAX      HwMsV5InterfaceEntry
    MAX-ACCESS  not-accessible
    STATUS      current
    DESCRIPTION
        "
        Indicates the V5 interface message statistics table.
        The index of this entry is hwV5InterfaceID."
    INDEX    {
              hwV5InterfaceID
             }
    ::= { hwMsV5InterfaceTable 1 }

  HwMsV5InterfaceEntry ::=
    SEQUENCE
    {
      hwV5InterfaceID   Integer32,
      hwMsV5InterfaceRestart    Counter32,
      hwMsV5InterfaceSwitchOver Counter32,
      hwMsV5InterfaceSwitchOverFail Counter32,
      hwMsV5InterfaceSwitchOverOk   Counter32,
      hwMsV5InterfaceUnavailTime    Counter32,
      hwMsV5InterfaceUnavailCChl    Counter32,
      hwMsV5InterfaceRemoteBlockkCChl   Counter32,
      hwMsV5InterfaceLocalBlockkCChl    Counter32
    }

  hwV5InterfaceID OBJECT-TYPE
    SYNTAX      Integer32
    MAX-ACCESS  not-accessible
    STATUS      current
    DESCRIPTION
        "
        Indicates the V5 interface ID. "
    ::= { hwMsV5InterfaceEntry 1 }

  hwMsV5InterfaceRestart OBJECT-TYPE
    SYNTAX      Counter32
    MAX-ACCESS  read-only
    STATUS      current
    DESCRIPTION
        "
        Indicates the count of interface startup. "
    ::= { hwMsV5InterfaceEntry 2 }

  hwMsV5InterfaceSwitchOver OBJECT-TYPE
    SYNTAX      Counter32
    MAX-ACCESS  read-only
    STATUS      current
    DESCRIPTION
        "
        Indicates the count of interface protection switchover. "
    ::= { hwMsV5InterfaceEntry 3 }

  hwMsV5InterfaceSwitchOverFail OBJECT-TYPE
    SYNTAX      Counter32
    MAX-ACCESS  read-only
    STATUS      current
    DESCRIPTION
        "
        Indicates the count of failed interface protection switchover. "
    ::= { hwMsV5InterfaceEntry 4 }

  hwMsV5InterfaceSwitchOverOk OBJECT-TYPE
    SYNTAX      Counter32
    MAX-ACCESS  read-only
    STATUS      current
    DESCRIPTION
        "
        Indicates the count of successful interface protection switchover. "
    ::= { hwMsV5InterfaceEntry 5 }

  hwMsV5InterfaceUnavailTime OBJECT-TYPE
    SYNTAX      Counter32
    MAX-ACCESS  read-only
    STATUS      current
    DESCRIPTION
        "
        Indicates the unavailable time of the V5 interface (second). "
    ::= { hwMsV5InterfaceEntry 6 }

  hwMsV5InterfaceUnavailCChl OBJECT-TYPE
    SYNTAX      Counter32
    MAX-ACCESS  read-only
    STATUS      current
    DESCRIPTION
        "
        Indicates the count of unavailable C channels due to any cause. "
    ::= { hwMsV5InterfaceEntry 7 }

  hwMsV5InterfaceRemoteBlockkCChl OBJECT-TYPE
    SYNTAX      Counter32
    MAX-ACCESS  read-only
    STATUS      current
    DESCRIPTION
        "
        Indicates the count of unavailable C channels due to remote block. "
    ::= { hwMsV5InterfaceEntry 8 }

  hwMsV5InterfaceLocalBlockkCChl OBJECT-TYPE
    SYNTAX      Counter32
    MAX-ACCESS  read-only
    STATUS      current
    DESCRIPTION
        "
        Indicates the count of unavailable C channels due to local block. "
    ::= { hwMsV5InterfaceEntry 9 }

  hwMsV5CallTable OBJECT-TYPE
    SYNTAX      SEQUENCE OF HwMsV5CallEntry
    MAX-ACCESS  not-accessible
    STATUS      current
    DESCRIPTION
      "
       Indicates the traffic statistics of the V5 interface.
       The index of this table is hwV5InterfaceID."
    ::= { hwMs 3 }

  hwMsV5CallEntry OBJECT-TYPE
    SYNTAX      HwMsV5CallEntry
    MAX-ACCESS  not-accessible
    STATUS      current
    DESCRIPTION
      "Indicates the traffic statistics of the V5 interface.
       The index of this entry is hwV5InterfaceID."
    INDEX    {
              hwV5InterfaceID
             }
    ::= { hwMsV5CallTable 1 }

  HwMsV5CallEntry ::=
    SEQUENCE
    {
      hwMsV5AllCall Counter32,
      hwMsV5SucessfulCall   Counter32,
      hwMsV5FailedBySystemCall  Counter32,
      hwMsV5FailedByUseCall Counter32,
      hwMsV5InUseCall   Counter32,
      hwMsV5FailedByResCall Counter32,
      hwMsV5FailedByOtherSideCall   Counter32
    }

  hwMsV5AllCall OBJECT-TYPE
    SYNTAX      Counter32
    MAX-ACCESS  read-only
    STATUS      current
    DESCRIPTION
        "
        Indicates the count of call requests. "
    ::= { hwMsV5CallEntry 1 }

  hwMsV5SucessfulCall OBJECT-TYPE
    SYNTAX      Counter32
    MAX-ACCESS  read-only
    STATUS      current
    DESCRIPTION
        "
        Indicates the count of successful calls. "
    ::= { hwMsV5CallEntry 2 }

  hwMsV5FailedBySystemCall OBJECT-TYPE
    SYNTAX      Counter32
    MAX-ACCESS  read-only
    STATUS      current
    DESCRIPTION
        "
        Indicates the count of calls discarded by the system. "
    ::= { hwMsV5CallEntry 3 }

  hwMsV5FailedByUseCall OBJECT-TYPE
    SYNTAX      Counter32
    MAX-ACCESS  read-only
    STATUS      current
    DESCRIPTION
        "
        Indicates the count of calls discarded by the subscriber. "
    ::= { hwMsV5CallEntry 4 }

  hwMsV5InUseCall OBJECT-TYPE
    SYNTAX      Counter32
    MAX-ACCESS  read-only
    STATUS      current
    DESCRIPTION
        "
        Indicates the count of ongoing calls. "
    ::= { hwMsV5CallEntry 5 }

  hwMsV5FailedByResCall OBJECT-TYPE
    SYNTAX      Counter32
    MAX-ACCESS  read-only
    STATUS      current
    DESCRIPTION
        "
        Indicates the count of failed connections due to unavailable resource. "
    ::= { hwMsV5CallEntry 6 }

  hwMsV5FailedByOtherSideCall OBJECT-TYPE
    SYNTAX      Counter32
    MAX-ACCESS  read-only
    STATUS      current
    DESCRIPTION
        "
        Indicates the count of failed connections due to the rejection of the peer end. "
    ::= { hwMsV5CallEntry 7 }

  hwMsSystemCallTable OBJECT-TYPE
    SYNTAX      SEQUENCE OF HwMsSystemCallEntry
    MAX-ACCESS  not-accessible
    STATUS      current
    DESCRIPTION
      "
       Indicates the traffic statistics of the system.
       The index of this table is hwMsSystemResultNo. "
    ::= { hwMs 4 }

  hwMsSystemCallEntry OBJECT-TYPE
    SYNTAX      HwMsSystemCallEntry
    MAX-ACCESS  not-accessible
    STATUS      current
    DESCRIPTION
      "Indicates the traffic statistics of the system.
      The index of this entry is hwMsSystemResultNo."
    INDEX    {
              hwMsSystemResultNo
             }
    ::= { hwMsSystemCallTable 1 }

  HwMsSystemCallEntry ::=
    SEQUENCE
    {
      hwMsSystemResultNo    Integer32,
      hwMsSystemAllCall Counter32,
      hwMsSystemInCall  Counter32,
      hwMsSystemOutCall Counter32,
      hwMsSystemTraffic Counter32,
      hwMsSystemInTraffic   Counter32,
      hwMsSystemOutTraffic  Counter32,
      hwMsSystemCallTime    DateAndTime
    }

  hwMsSystemResultNo OBJECT-TYPE
    SYNTAX      Integer32(0..9)
    MAX-ACCESS  not-accessible
    STATUS      current
    DESCRIPTION
        "
        Indicates the result number. "
    ::= { hwMsSystemCallEntry 1 }

  hwMsSystemAllCall OBJECT-TYPE
    SYNTAX      Counter32
    MAX-ACCESS  read-only
    STATUS      current
    DESCRIPTION
        "
        Indicates the count of successful calls of the system traffic. "
    ::= { hwMsSystemCallEntry 2 }

  hwMsSystemInCall OBJECT-TYPE
    SYNTAX      Counter32
    MAX-ACCESS  read-only
    STATUS      current
    DESCRIPTION
        "
        Indicates the count of successful incoming calls of the system traffic. "
    ::= { hwMsSystemCallEntry 3 }

  hwMsSystemOutCall OBJECT-TYPE
    SYNTAX      Counter32
    MAX-ACCESS  read-only
    STATUS      current
    DESCRIPTION
        "
        Indicates the count of successful outgoing calls of the system traffic. "
    ::= { hwMsSystemCallEntry 4 }

  hwMsSystemTraffic OBJECT-TYPE
    SYNTAX      Counter32
    MAX-ACCESS  read-only
    STATUS      current
    DESCRIPTION
        "
        Indicates the average traffic per line (ERL x 1000) of the system traffic. For the NMS, the value is divided by 1000. "
    ::= { hwMsSystemCallEntry 5 }

  hwMsSystemInTraffic OBJECT-TYPE
    SYNTAX      Counter32
    MAX-ACCESS  read-only
    STATUS      current
    DESCRIPTION
        "
        Indicates the average incoming traffic per line (ERL x 1000) of the system traffic. For the NMS, the value is divided by 1000. "
    ::= { hwMsSystemCallEntry 6 }

  hwMsSystemOutTraffic OBJECT-TYPE
    SYNTAX      Counter32
    MAX-ACCESS  read-only
    STATUS      current
    DESCRIPTION
        "
        Indicates the average outgoing traffic per line (ERL x 1000) of the system traffic. For the NMS, the value is divided by 1000. "
    ::= { hwMsSystemCallEntry 7 }

  hwMsSystemCallTime OBJECT-TYPE
    SYNTAX      DateAndTime
    MAX-ACCESS  read-only
    STATUS      current
    DESCRIPTION
        "
        Indicates the system time. "
    ::= { hwMsSystemCallEntry 8 }

  hwMsV5TKCallTable OBJECT-TYPE
    SYNTAX      SEQUENCE OF HwMsV5TKCallEntry
    MAX-ACCESS  not-accessible
    STATUS      current
    DESCRIPTION
      "
       Indicates the V5 interface trunk traffic statistics.
       The indexes of this table are hwMsV5TKIndex and hwMsV5TKResultNo. "
    ::= { hwMs 5 }

  hwMsV5TKCallEntry OBJECT-TYPE
    SYNTAX      HwMsV5TKCallEntry
    MAX-ACCESS  not-accessible
    STATUS      current
    DESCRIPTION
      "
       Indicates the V5 interface trunk traffic statistics.
       The indexes of this entry are hwMsV5TKIndex and hwMsV5TKResultNo."
    INDEX    {
              hwMsV5TKIndex,
              hwMsV5TKResultNo
             }
    ::= { hwMsV5TKCallTable 1 }

  HwMsV5TKCallEntry ::=
    SEQUENCE
    {
      hwMsV5TKIndex Integer32,
      hwMsV5TKResultNo  Integer32,
      hwMsV5TKCall  Counter32,
      hwMsV5TKInCall    Counter32,
      hwMsV5TKOutCall   Counter32,
      hwMsV5TKTraffic   Counter32,
      hwMsV5TKInTraffic Counter32,
      hwMsV5TKOutTraffic    Counter32,
      hwMsV5TKCallTime  DateAndTime
    }

  hwMsV5TKIndex OBJECT-TYPE
    SYNTAX      Integer32
    MAX-ACCESS  not-accessible
    STATUS      current
    DESCRIPTION
        "
        Indicates the V5 interface ID. "
    ::= { hwMsV5TKCallEntry 1 }

  hwMsV5TKResultNo OBJECT-TYPE
    SYNTAX      Integer32(0..9)
    MAX-ACCESS  not-accessible
    STATUS      current
    DESCRIPTION
        "
        Indicates the result number. "
    ::= { hwMsV5TKCallEntry 2 }

  hwMsV5TKCall OBJECT-TYPE
    SYNTAX      Counter32
    MAX-ACCESS  read-only
    STATUS      current
    DESCRIPTION
        "
        Indicates the count of successful V5 interface trunk calls. "
    ::= { hwMsV5TKCallEntry 3 }

  hwMsV5TKInCall OBJECT-TYPE
    SYNTAX      Counter32
    MAX-ACCESS  read-only
    STATUS      current
    DESCRIPTION
        "
        Indicates the count of successful incoming V5 interface trunk calls. "
    ::= { hwMsV5TKCallEntry 4 }

  hwMsV5TKOutCall OBJECT-TYPE
    SYNTAX      Counter32
    MAX-ACCESS  read-only
    STATUS      current
    DESCRIPTION
        "
        Indicates the count of successful outgoing V5 interface trunk calls. "
    ::= { hwMsV5TKCallEntry 5 }

  hwMsV5TKTraffic OBJECT-TYPE
    SYNTAX      Counter32
    MAX-ACCESS  read-only
    STATUS      current
    DESCRIPTION
        "
        Indicates the V5 interface trunk traffic (ERL x 1000). For the NMS, the value is divided by 1000. "
    ::= { hwMsV5TKCallEntry 6 }

  hwMsV5TKInTraffic OBJECT-TYPE
    SYNTAX      Counter32
    MAX-ACCESS  read-only
    STATUS      current
    DESCRIPTION
        "
        Indicates the incoming V5 interface trunk traffic (ERL x 1000). For the NMS, the value is divided by 1000. "
    ::= { hwMsV5TKCallEntry 7 }

  hwMsV5TKOutTraffic OBJECT-TYPE
    SYNTAX      Counter32
    MAX-ACCESS  read-only
    STATUS      current
    DESCRIPTION
        "
        Indicates the outgoing V5 interface trunk traffic (ERL x 1000). For the NMS, the value is divided by 1000. "
    ::= { hwMsV5TKCallEntry 8 }

  hwMsV5TKCallTime OBJECT-TYPE
    SYNTAX      DateAndTime
    MAX-ACCESS  read-only
    STATUS      current
    DESCRIPTION
        "
        Indicates the system time. "
    ::= { hwMsV5TKCallEntry 9 }

  hwMsFrameTKCallTable OBJECT-TYPE
    SYNTAX      SEQUENCE OF HwMsFrameTKCallEntry
    MAX-ACCESS  not-accessible
    STATUS      current
    DESCRIPTION
      "
       Indicates the service shelf trunk traffic statistics.
       The indexes of this table are hwMsFrameTKIndex and hwMsFrameTKResultNo. "
    ::= { hwMs 6 }

  hwMsFrameTKCallEntry OBJECT-TYPE
    SYNTAX      HwMsFrameTKCallEntry
    MAX-ACCESS  not-accessible
    STATUS      current
    DESCRIPTION
      "Indicates the service shelf trunk traffic statistics.
       The indexes of this entry are hwMsFrameTKIndex and hwMsFrameTKResultNo."
    INDEX    {
              hwMsFrameTKIndex,
              hwMsFrameTKResultNo
             }
    ::= { hwMsFrameTKCallTable 1 }

  HwMsFrameTKCallEntry ::=
    SEQUENCE
    {
      hwMsFrameTKIndex  Integer32,
      hwMsFrameTKResultNo   Integer32,
      hwMsFrameTKCall   Counter32,
      hwMsFrameTKInCall Counter32,
      hwMsFrameTKOutCall    Counter32,
      hwMsFrameTKTraffic    Counter32,
      hwMsFrameTKInTraffic  Counter32,
      hwMsFrameTKOutTraffic Counter32,
      hwMsFrameTKCallTime   DateAndTime
    }

  hwMsFrameTKIndex OBJECT-TYPE
    SYNTAX      Integer32
    MAX-ACCESS  not-accessible
    STATUS      current
    DESCRIPTION
        "
        Indicates the shelf number. "
    ::= { hwMsFrameTKCallEntry 1 }

  hwMsFrameTKResultNo OBJECT-TYPE
    SYNTAX      Integer32(0..9)
    MAX-ACCESS  not-accessible
    STATUS      current
    DESCRIPTION
        "
        Indicates the result number. "
    ::= { hwMsFrameTKCallEntry 2 }

  hwMsFrameTKCall OBJECT-TYPE
    SYNTAX      Counter32
    MAX-ACCESS  read-only
    STATUS      current
    DESCRIPTION
        "
        Indicates the count of successful service shelf trunk calls. "
    ::= { hwMsFrameTKCallEntry 3 }

  hwMsFrameTKInCall OBJECT-TYPE
    SYNTAX      Counter32
    MAX-ACCESS  read-only
    STATUS      current
    DESCRIPTION
        "
        Indicates the count of successful incoming service shelf trunk calls. "
    ::= { hwMsFrameTKCallEntry 4 }

  hwMsFrameTKOutCall OBJECT-TYPE
    SYNTAX      Counter32
    MAX-ACCESS  read-only
    STATUS      current
    DESCRIPTION
        "
        Indicates the count of successful outgoing service shelf trunk calls. "
    ::= { hwMsFrameTKCallEntry 5 }

  hwMsFrameTKTraffic OBJECT-TYPE
    SYNTAX      Counter32
    MAX-ACCESS  read-only
    STATUS      current
    DESCRIPTION
        "
        Indicates the service shelf trunk traffic (ERL x 1000). For the NMS, the value is divided by 1000. "
    ::= { hwMsFrameTKCallEntry 6 }

  hwMsFrameTKInTraffic OBJECT-TYPE
    SYNTAX      Counter32
    MAX-ACCESS  read-only
    STATUS      current
    DESCRIPTION
        "
        Indicates the incoming service shelf trunk traffic (ERL x 1000). For the NMS, the value is divided by 1000. "
    ::= { hwMsFrameTKCallEntry 7 }

  hwMsFrameTKOutTraffic OBJECT-TYPE
    SYNTAX      Counter32
    MAX-ACCESS  read-only
    STATUS      current
    DESCRIPTION
        "
        Indicates the outgoing service shelf trunk traffic (ERL x 1000). For the NMS, the value is divided by 1000. "
    ::= { hwMsFrameTKCallEntry 8 }

  hwMsFrameTKCallTime OBJECT-TYPE
    SYNTAX      DateAndTime
    MAX-ACCESS  read-only
    STATUS      current
    DESCRIPTION
        "
        Indicates the system time. "
    ::= { hwMsFrameTKCallEntry 9 }

  hwMsSingleSubscrberCallTable OBJECT-TYPE
    SYNTAX      SEQUENCE OF HwMsSingleSubscrberCallEntry
    MAX-ACCESS  not-accessible
    STATUS      current
    DESCRIPTION
      "
       Indicates the traffic statistics of a single subscriber.
       The indexes of this table are hwMsSingleSubscrberIndex and hwMsSingleSubscrberResultNo. "
    ::= { hwMs 7 }

  hwMsSingleSubscrberCallEntry OBJECT-TYPE
    SYNTAX      HwMsSingleSubscrberCallEntry
    MAX-ACCESS  not-accessible
    STATUS      current
    DESCRIPTION
      "
       Indicates the traffic statistics of a single subscriber.
       The indexes of this entry are hwMsSingleSubscrberIndex and hwMsSingleSubscrberResultNo."
    INDEX    {
              hwMsSingleSubscrberIndex,
              hwMsSingleSubscrberResultNo
             }
    ::= { hwMsSingleSubscrberCallTable 1 }

  HwMsSingleSubscrberCallEntry ::=
    SEQUENCE
    {
      hwMsSingleSubscrberIndex  Integer32,
      hwMsSingleSubscrberResultNo   Integer32,
      hwMsSingleSubscrberCall   Counter32,
      hwMsSingleSubscrberInCall Counter32,
      hwMsSingleSubscrberOutCall    Counter32,
      hwMsSingleSubscrberTraffic    Counter32,
      hwMsSingleSubscrberInTraffic  Counter32,
      hwMsSingleSubscrberOutTraffic Counter32,
      hwMsSingleSubscrberCallTime   DateAndTime
    }

  hwMsSingleSubscrberIndex OBJECT-TYPE
    SYNTAX      Integer32
    MAX-ACCESS  not-accessible
    STATUS      current
    DESCRIPTION
        "
        Indicates the service shelf/slot/port index. "
    ::= { hwMsSingleSubscrberCallEntry 1 }

  hwMsSingleSubscrberResultNo OBJECT-TYPE
    SYNTAX      Integer32(0..9)
    MAX-ACCESS  not-accessible
    STATUS      current
    DESCRIPTION
        "
        Indicates the result number. "
    ::= { hwMsSingleSubscrberCallEntry 2 }

  hwMsSingleSubscrberCall OBJECT-TYPE
    SYNTAX      Counter32
    MAX-ACCESS  read-only
    STATUS      current
    DESCRIPTION
        "
        Indicates the count of successful calls of a single subscriber. "
    ::= { hwMsSingleSubscrberCallEntry 3 }

  hwMsSingleSubscrberInCall OBJECT-TYPE
    SYNTAX      Counter32
    MAX-ACCESS  read-only
    STATUS      current
    DESCRIPTION
        "
        Indicates the count of successful incoming calls of a single subscriber. "
    ::= { hwMsSingleSubscrberCallEntry 4 }

  hwMsSingleSubscrberOutCall OBJECT-TYPE
    SYNTAX      Counter32
    MAX-ACCESS  read-only
    STATUS      current
    DESCRIPTION
        "
        Indicates the count of successful outgoing calls of a single subscriber. "
    ::= { hwMsSingleSubscrberCallEntry 5 }

  hwMsSingleSubscrberTraffic OBJECT-TYPE
    SYNTAX      Counter32
    MAX-ACCESS  read-only
    STATUS      current
    DESCRIPTION
        "
        Indicates the trunk traffic of a single subscriber (ERL x 1000). For the NMS, the value is divided by 1000. "
    ::= { hwMsSingleSubscrberCallEntry 6 }

  hwMsSingleSubscrberInTraffic OBJECT-TYPE
    SYNTAX      Counter32
    MAX-ACCESS  read-only
    STATUS      current
    DESCRIPTION
        "
        Indicates the incoming trunk traffic of a single subscriber (ERL x 1000). For the NMS, the value is divided by 1000. "
    ::= { hwMsSingleSubscrberCallEntry 7 }

  hwMsSingleSubscrberOutTraffic OBJECT-TYPE
    SYNTAX      Counter32
    MAX-ACCESS  read-only
    STATUS      current
    DESCRIPTION
        "
        Indicates the outgoing trunk traffic of a single subscriber (ERL x 1000). For the NMS, the value is divided by 1000. "
    ::= { hwMsSingleSubscrberCallEntry 8 }

  hwMsSingleSubscrberCallTime OBJECT-TYPE
    SYNTAX      DateAndTime
    MAX-ACCESS  read-only
    STATUS      current
    DESCRIPTION
        "
        Indicates the system time. "
    ::= { hwMsSingleSubscrberCallEntry 9 }

  hwMsV5BChlInfoTable OBJECT-TYPE
    SYNTAX      SEQUENCE OF HwMsV5BChlInfoEntry
    MAX-ACCESS  not-accessible
    STATUS      current
    DESCRIPTION
      "
        Indicates the message statistics of the V5 B channel.
        The index of this table is hwV5InterfaceID. "
    ::= { hwMs 8 }

  hwMsV5BChlInfoEntry OBJECT-TYPE
    SYNTAX      HwMsV5BChlInfoEntry
    MAX-ACCESS  not-accessible
    STATUS      current
    DESCRIPTION
      "
        Indicates the message statistics of the V5 B channel.
        The index of this entry is hwV5InterfaceID."
    INDEX    {
              hwV5InterfaceID
             }
    ::= { hwMsV5BChlInfoTable 1 }

  HwMsV5BChlInfoEntry ::=
    SEQUENCE
    {
      hwMsV5BChlAlloc   Counter32,
      hwMsV5BChlHwTsBusyAllocFail   Counter32,
      hwMsV5BChlInvalidTsAllocFail  Counter32,
      hwMsV5BChlInvalidLinkIdAllocFail  Counter32,
      hwMsV5BChlUsedPhyCChlAllocFail    Counter32,
      hwMsV5BChlLinkUnavailAllocFail    Counter32,
      hwMsV5BChlNoPsnProviedAllocFail   Counter32,
      hwMsV5BChlUnavailAllocFail    Counter32,
      hwMsV5BChlAllocFail   Counter32,
      hwMsV5BChlInAllocFail Counter32,
      hwMsV5BChlOutAllocFail    Counter32,
      hwMsV5BChlAllocSuccess    Counter32,
      hwMsV5BChlAllocTime   Counter32,
      hwMsV5BChlAllocAverTime   Counter32,
      hwMsV5BChlAvailRate   Counter32,
      hwMsV5BChlCanAllocNum Counter32
    }

  hwMsV5BChlAlloc OBJECT-TYPE
    SYNTAX      Counter32
    MAX-ACCESS  read-only
    STATUS      current
    DESCRIPTION
        "
        Indicates the count of bearer channel allocation. "
    ::= { hwMsV5BChlInfoEntry 1 }

  hwMsV5BChlHwTsBusyAllocFail OBJECT-TYPE
    SYNTAX      Counter32
    MAX-ACCESS  read-only
    STATUS      current
    DESCRIPTION
        "
        Indicates that a connection to another port already exists on the V5 timeslot. "
    ::= { hwMsV5BChlInfoEntry 2 }

  hwMsV5BChlInvalidTsAllocFail OBJECT-TYPE
    SYNTAX      Counter32
    MAX-ACCESS  read-only
    STATUS      current
    DESCRIPTION
        "
        Indicates an invalid V5 timeslot ID. "
    ::= { hwMsV5BChlInfoEntry 3 }

  hwMsV5BChlInvalidLinkIdAllocFail OBJECT-TYPE
    SYNTAX      Counter32
    MAX-ACCESS  read-only
    STATUS      current
    DESCRIPTION
        "
         Indicates an invalid V5 2 M link ID. "
    ::= { hwMsV5BChlInfoEntry 4 }

  hwMsV5BChlUsedPhyCChlAllocFail OBJECT-TYPE
    SYNTAX      Counter32
    MAX-ACCESS  read-only
    STATUS      current
    DESCRIPTION
        "
         Indicates that the V5 timeslot is functioning as a physical C channel. "
    ::= { hwMsV5BChlInfoEntry 5 }

  hwMsV5BChlLinkUnavailAllocFail OBJECT-TYPE
    SYNTAX      Counter32
    MAX-ACCESS  read-only
    STATUS      current
    DESCRIPTION
        "
         Indicates that the V5 link is unavailable (blocked). "
    ::= { hwMsV5BChlInfoEntry 6 }

  hwMsV5BChlNoPsnProviedAllocFail OBJECT-TYPE
    SYNTAX      Counter32
    MAX-ACCESS  read-only
    STATUS      current
    DESCRIPTION
        "
         Indicates that the subscriber port is not allocated. "
    ::= { hwMsV5BChlInfoEntry 7 }

  hwMsV5BChlUnavailAllocFail OBJECT-TYPE
    SYNTAX      Counter32
    MAX-ACCESS  read-only
    STATUS      current
    DESCRIPTION
        "
         Indicates that the bearer channel resource is unavailable. "
    ::= { hwMsV5BChlInfoEntry 8 }

  hwMsV5BChlAllocFail OBJECT-TYPE
    SYNTAX      Counter32
    MAX-ACCESS  read-only
    STATUS      current
    DESCRIPTION
        "
        Indicates the count of failed allocation of the bearer channel for calls (the sum of the preceding seven items). "
    ::= { hwMsV5BChlInfoEntry 9 }

  hwMsV5BChlInAllocFail OBJECT-TYPE
    SYNTAX      Counter32
    MAX-ACCESS  read-only
    STATUS      current
    DESCRIPTION
        "
        Indicates the count of failed allocations for incoming calls. "
    ::= { hwMsV5BChlInfoEntry 10 }

  hwMsV5BChlOutAllocFail OBJECT-TYPE
    SYNTAX      Counter32
    MAX-ACCESS  read-only
    STATUS      current
    DESCRIPTION
        "
        Indicates the count of failed allocations for outgoing calls. "
    ::= { hwMsV5BChlInfoEntry 11 }

  hwMsV5BChlAllocSuccess OBJECT-TYPE
    SYNTAX      Counter32
    MAX-ACCESS  read-only
    STATUS      current
    DESCRIPTION
        "
        Indicates the total count of successful allocations of bearer channel. "
    ::= { hwMsV5BChlInfoEntry 12 }

  hwMsV5BChlAllocTime OBJECT-TYPE
    SYNTAX      Counter32
    MAX-ACCESS  read-only
    STATUS      current
    DESCRIPTION
        "
        Indicates the total duration when the bearer channel is occupied by calls (second). The total duration is the sum of the duration of all the calls that occur within the specified time. "
    ::= { hwMsV5BChlInfoEntry 13 }

  hwMsV5BChlAllocAverTime OBJECT-TYPE
    SYNTAX      Counter32
    MAX-ACCESS  read-only
    STATUS      current
    DESCRIPTION
        "
        The average occupation duration of the bearer channel (second) = the total duration when the bearer channel is occupied by calls/the total count of successful allocations of bearer channel "
    ::= { hwMsV5BChlInfoEntry 14 }

  hwMsV5BChlAvailRate OBJECT-TYPE
    SYNTAX      Counter32
    MAX-ACCESS  read-only
    STATUS      current
    DESCRIPTION
        "
        The available rate of the bearer channel = [1 - the total duration when the bearer channel is occupied by calls/(statistics time x the count of available channels of the V5)] "
    ::= { hwMsV5BChlInfoEntry 15 }

  hwMsV5BChlCanAllocNum OBJECT-TYPE
    SYNTAX      Counter32
    MAX-ACCESS  read-only
    STATUS      current
    DESCRIPTION
        "
        Indicates the count of available channels of the V5. "
    ::= { hwMsV5BChlInfoEntry 16 }

  hwMsE1PortAlarmTable OBJECT-TYPE
    SYNTAX      SEQUENCE OF HwMsE1PortAlarmEntry
    MAX-ACCESS  not-accessible
    STATUS      current
    DESCRIPTION
      "
        Indicates the message statistics of the E1 port.
        The index of this table is hwMsE1PortIndex. "
    ::= { hwMs 9 }

  hwMsE1PortAlarmEntry OBJECT-TYPE
    SYNTAX      HwMsE1PortAlarmEntry
    MAX-ACCESS  not-accessible
    STATUS      current
    DESCRIPTION
      "Indicates the message statistics of the E1 port.
       The index of this entry is hwMsE1PortIndex."
    INDEX    {
              hwMsE1PortIndex
             }
    ::= { hwMsE1PortAlarmTable 1 }

  HwMsE1PortAlarmEntry ::=
    SEQUENCE
    {
      hwMsE1PortIndex   Integer32,
      hwMsE1PortLOSTime Counter32,
      hwMsE1PortCRCTime Counter32,
      hwMsE1PortAISTime Counter32,
      hwMsE1PortSYNCTime    Counter32,
      hwMsE1PortRAITime Counter32,
      hwMsE1PortLMFATime    Counter32
    }

  hwMsE1PortIndex OBJECT-TYPE
    SYNTAX      Integer32
    MAX-ACCESS  not-accessible
    STATUS      current
    DESCRIPTION
        "
        Indicates the shelf/slot/port index of the E1 port. "
    ::= { hwMsE1PortAlarmEntry 1 }

  hwMsE1PortLOSTime OBJECT-TYPE
    SYNTAX      Counter32
    MAX-ACCESS  read-only
    STATUS      current
    DESCRIPTION
        "
        Indicates the loss of signal seconds of the E1 port. "
    ::= { hwMsE1PortAlarmEntry 2 }

  hwMsE1PortCRCTime OBJECT-TYPE
    SYNTAX      Counter32
    MAX-ACCESS  read-only
    STATUS      current
    DESCRIPTION
        "
        Indicates the CRC error seconds of the E1 port. "
    ::= { hwMsE1PortAlarmEntry 3 }

  hwMsE1PortAISTime OBJECT-TYPE
    SYNTAX      Counter32
    MAX-ACCESS  read-only
    STATUS      current
    DESCRIPTION
        "
        Indicates the alarm indication signal seconds of the E1 port. "
    ::= { hwMsE1PortAlarmEntry 4 }

  hwMsE1PortSYNCTime OBJECT-TYPE
    SYNTAX      Counter32
    MAX-ACCESS  read-only
    STATUS      current
    DESCRIPTION
        "
        Indicates the loss of frame alignment seconds of the E1 port. "
    ::= { hwMsE1PortAlarmEntry 5 }

  hwMsE1PortRAITime OBJECT-TYPE
    SYNTAX      Counter32
    MAX-ACCESS  read-only
    STATUS      current
    DESCRIPTION
        "
        Indicates the remote alarm seconds of the E1 port. "
    ::= { hwMsE1PortAlarmEntry 6 }

  hwMsE1PortLMFATime OBJECT-TYPE
    SYNTAX      Counter32
    MAX-ACCESS  read-only
    STATUS      current
    DESCRIPTION
        "
        Indicates the loss of multiframe alignment seconds of the E1 port. "
    ::= { hwMsE1PortAlarmEntry 7 }

  hwMsPstnMsgTable OBJECT-TYPE
    SYNTAX      SEQUENCE OF HwMsPstnMsgEntry
    MAX-ACCESS  not-accessible
    STATUS      current
    DESCRIPTION
      "
        Indicates the PSTN message statistics.
        The index of this table is hwV5InterfaceID. "
    ::= { hwMs 10 }

  hwMsPstnMsgEntry OBJECT-TYPE
    SYNTAX      HwMsPstnMsgEntry
    MAX-ACCESS  not-accessible
    STATUS      current
    DESCRIPTION
      "Indicates the PSTN message statistics.
       The index of this entry is hwV5InterfaceID."
    INDEX    {
              hwV5InterfaceID
             }
    ::= { hwMsPstnMsgTable 1 }

  HwMsPstnMsgEntry ::=
    SEQUENCE
    {
      hwMsPstnEstablish Counter32,
      hwMsPstnEstablishAck  Counter32,
      hwMsPstnSignal    Counter32,
      hwMsPstnSignalAck Counter32,
      hwMsPstnDisconnect    Counter32,
      hwMsPstnDisconnectComp    Counter32,
      hwMsPstnStatusEnq Counter32,
      hwMsPstnStatus    Counter32,
      hwMsPstnProtocolPara  Counter32
    }

  hwMsPstnEstablish OBJECT-TYPE
    SYNTAX      Counter32
    MAX-ACCESS  read-only
    STATUS      current
    DESCRIPTION
        "
        Indicates the count of Establish messages. "
    ::= { hwMsPstnMsgEntry 1 }

  hwMsPstnEstablishAck OBJECT-TYPE
    SYNTAX      Counter32
    MAX-ACCESS  read-only
    STATUS      current
    DESCRIPTION
        "
        Indicates the count of EstablishAck messages. "
    ::= { hwMsPstnMsgEntry 2 }

  hwMsPstnSignal OBJECT-TYPE
    SYNTAX      Counter32
    MAX-ACCESS  read-only
    STATUS      current
    DESCRIPTION
        "
        Indicates the count of Signal messages. "
    ::= { hwMsPstnMsgEntry 3 }

  hwMsPstnSignalAck OBJECT-TYPE
    SYNTAX      Counter32
    MAX-ACCESS  read-only
    STATUS      current
    DESCRIPTION
        "
        Indicates the count of SignalAck messages. "
    ::= { hwMsPstnMsgEntry 4 }

  hwMsPstnDisconnect OBJECT-TYPE
    SYNTAX      Counter32
    MAX-ACCESS  read-only
    STATUS      current
    DESCRIPTION
        "
        Indicates the count of Disconnect messages. "
    ::= { hwMsPstnMsgEntry 5 }

  hwMsPstnDisconnectComp OBJECT-TYPE
    SYNTAX      Counter32
    MAX-ACCESS  read-only
    STATUS      current
    DESCRIPTION
        "
        Indicates the count of DisconnectComp messages. "
    ::= { hwMsPstnMsgEntry 6 }

  hwMsPstnStatusEnq OBJECT-TYPE
    SYNTAX      Counter32
    MAX-ACCESS  read-only
    STATUS      current
    DESCRIPTION
        "
        Indicates the count of StatusEnq messages. "
    ::= { hwMsPstnMsgEntry 7 }

  hwMsPstnStatus OBJECT-TYPE
    SYNTAX      Counter32
    MAX-ACCESS  read-only
    STATUS      current
    DESCRIPTION
        "
        Indicates the count of Status messages. "
    ::= { hwMsPstnMsgEntry 8 }

  hwMsPstnProtocolPara OBJECT-TYPE
    SYNTAX      Counter32
    MAX-ACCESS  read-only
    STATUS      current
    DESCRIPTION
        "
        Indicates the count of ProtocolPara messages. "
    ::= { hwMsPstnMsgEntry 9 }

  hwMsBccMsgTable OBJECT-TYPE
    SYNTAX      SEQUENCE OF HwMsBccMsgEntry
    MAX-ACCESS  not-accessible
    STATUS      current
    DESCRIPTION
      "
        Indicates the BCC message statistics.
        The index of this table is hwV5InterfaceID. "
    ::= { hwMs 11 }

  hwMsBccMsgEntry OBJECT-TYPE
    SYNTAX      HwMsBccMsgEntry
    MAX-ACCESS  not-accessible
    STATUS      current
    DESCRIPTION
      "
        Indicates the BCC message statistics.
        The index of this entry is hwV5InterfaceID."
    INDEX    {
              hwV5InterfaceID
             }
    ::= { hwMsBccMsgTable 1 }

  HwMsBccMsgEntry ::=
    SEQUENCE
    {
      hwMsBccAllocation Counter32,
      hwMsBccAllocationComp Counter32,
      hwMsBccAllocationRej  Counter32,
      hwMsBccDeallocation   Counter32,
      hwMsBccDeallocationComp   Counter32,
      hwMsBccDeallocationRej    Counter32,
      hwMsBccAudit  Counter32,
      hwMsBccAuditComp  Counter32,
      hwMsBccAnFault    Counter32,
      hwMsBccAnFaultAck Counter32,
      hwMsBccProtocolError  Counter32
    }

  hwMsBccAllocation OBJECT-TYPE
    SYNTAX      Counter32
    MAX-ACCESS  read-only
    STATUS      current
    DESCRIPTION
        "
        Indicates the count of Allocation messages. "
    ::= { hwMsBccMsgEntry 1 }

  hwMsBccAllocationComp OBJECT-TYPE
    SYNTAX      Counter32
    MAX-ACCESS  read-only
    STATUS      current
    DESCRIPTION
        "
        Indicates the count of AllocationComp messages. "
    ::= { hwMsBccMsgEntry 2 }

  hwMsBccAllocationRej OBJECT-TYPE
    SYNTAX      Counter32
    MAX-ACCESS  read-only
    STATUS      current
    DESCRIPTION
        "
        Indicates the count of AllocationRej messages. "
    ::= { hwMsBccMsgEntry 3 }

  hwMsBccDeallocation OBJECT-TYPE
    SYNTAX      Counter32
    MAX-ACCESS  read-only
    STATUS      current
    DESCRIPTION
        "
        Indicates the count of Deallocation messages. "
    ::= { hwMsBccMsgEntry 4 }

  hwMsBccDeallocationComp OBJECT-TYPE
    SYNTAX      Counter32
    MAX-ACCESS  read-only
    STATUS      current
    DESCRIPTION
        "
        Indicates the count of DeallocationComp messages. "
    ::= { hwMsBccMsgEntry 5 }

  hwMsBccDeallocationRej OBJECT-TYPE
    SYNTAX      Counter32
    MAX-ACCESS  read-only
    STATUS      current
    DESCRIPTION
        "
        Indicates the count of DeallocationRej messages. "
    ::= { hwMsBccMsgEntry 6 }

  hwMsBccAudit OBJECT-TYPE
    SYNTAX      Counter32
    MAX-ACCESS  read-only
    STATUS      current
    DESCRIPTION
        "
        Indicates the count of Audit messages. "
    ::= { hwMsBccMsgEntry 7 }

  hwMsBccAuditComp OBJECT-TYPE
    SYNTAX      Counter32
    MAX-ACCESS  read-only
    STATUS      current
    DESCRIPTION
        "
        Indicates the count of AuditComp messages. "
    ::= { hwMsBccMsgEntry 8 }

  hwMsBccAnFault OBJECT-TYPE
    SYNTAX      Counter32
    MAX-ACCESS  read-only
    STATUS      current
    DESCRIPTION
        "
        Indicates the count of AN faults. "
    ::= { hwMsBccMsgEntry 9 }

  hwMsBccAnFaultAck OBJECT-TYPE
    SYNTAX      Counter32
    MAX-ACCESS  read-only
    STATUS      current
    DESCRIPTION
        "
        Indicates the count of AN fault acknowledgement. "
    ::= { hwMsBccMsgEntry 10 }

  hwMsBccProtocolError OBJECT-TYPE
    SYNTAX      Counter32
    MAX-ACCESS  read-only
    STATUS      current
    DESCRIPTION
        "
        Indicates the count of protocol errors. "
    ::= { hwMsBccMsgEntry 11 }

  hwMsCommonCtrlMsgTable OBJECT-TYPE
    SYNTAX      SEQUENCE OF HwMsCommonCtrlMsgEntry
    MAX-ACCESS  not-accessible
    STATUS      current
    DESCRIPTION
      "
        Indicates the messages statistics of the Common Control Protocol.
        The index of this table is hwV5InterfaceID. "
    ::= { hwMs 12 }

  hwMsCommonCtrlMsgEntry OBJECT-TYPE
    SYNTAX      HwMsCommonCtrlMsgEntry
    MAX-ACCESS  not-accessible
    STATUS      current
    DESCRIPTION
      "
        Indicates the messages statistics of the Common Control Protocol.
        The index of this entry is hwV5InterfaceID."
    INDEX    {
              hwV5InterfaceID
             }
    ::= { hwMsCommonCtrlMsgTable 1 }

  HwMsCommonCtrlMsgEntry ::=
    SEQUENCE
    {
      hwMsCfidVerifyReprov  Counter32,
      hwMsCfidRdyForReprov  Counter32,
      hwMsCfidNrdyForReprov Counter32,
      hwMsCfidSwitchToNewVar    Counter32,
      hwMsCfidReprovStarted Counter32,
      hwMsCfidCannotReprov  Counter32,
      hwMsCfidReqVarIid Counter32,
      hwMsCfidVarAndIid Counter32,
      hwMsCfidBlockingStarted   Counter32,
      hwMsCfidRestartReq    Counter32,
      hwMsCfidRestartComp   Counter32,
      hwMsCfidUnblockAllPortReq Counter32,
      hwMsCfidUnblockAllPortAck Counter32,
      hwMsCfidUnblockAllPortRej Counter32,
      hwMsCfidUnblockAllPortComp    Counter32,
      hwMsCfidUnblockAllPstnPortReq Counter32,
      hwMsCfidUnblockAllPstnPortAck Counter32,
      hwMsCfidUnblockAllPstnPortRej Counter32,
      hwMsCfidUnblockAllPstnPortComp    Counter32,
      hwMsCfidUnblockAllIsdnPortReq Counter32,
      hwMsCfidUnblockAllIsdnPortAck Counter32,
      hwMsCfidUnblockAllIsdnPortRej Counter32,
      hwMsCfidUnblockAllIsdnPortComp    Counter32,
      hwMsCfidBlockAllPstnPortReq   Counter32,
      hwMsCfidBlockAllPstnPortAck   Counter32,
      hwMsCfidBlockAllPstnPortRej   Counter32,
      hwMsCfidBlockAllPstnPortComp  Counter32,
      hwMsCfidBlockAllIsdnPortReq   Counter32,
      hwMsCfidBlockAllIsdnPortAck   Counter32,
      hwMsCfidBlockAllIsdnPortRej   Counter32,
      hwMsCfidBlockAllIsdnPortComp  Counter32
    }

  hwMsCfidVerifyReprov OBJECT-TYPE
    SYNTAX      Counter32
    MAX-ACCESS  read-only
    STATUS      current
    DESCRIPTION
        "
        Indicates the count of verifying the reprovision. "
    ::= { hwMsCommonCtrlMsgEntry 1 }

  hwMsCfidRdyForReprov OBJECT-TYPE
    SYNTAX      Counter32
    MAX-ACCESS  read-only
    STATUS      current
    DESCRIPTION
        "
        Indicates the count of ready reprovision. "
    ::= { hwMsCommonCtrlMsgEntry 2 }

  hwMsCfidNrdyForReprov OBJECT-TYPE
    SYNTAX      Counter32
    MAX-ACCESS  read-only
    STATUS      current
    DESCRIPTION
        "
        Indicates the count of not-ready reprovision. "
    ::= { hwMsCommonCtrlMsgEntry 3 }

  hwMsCfidSwitchToNewVar OBJECT-TYPE
    SYNTAX      Counter32
    MAX-ACCESS  read-only
    STATUS      current
    DESCRIPTION
        "
        Indicates the count of switching to a new variable. "
    ::= { hwMsCommonCtrlMsgEntry 4 }

  hwMsCfidReprovStarted OBJECT-TYPE
    SYNTAX      Counter32
    MAX-ACCESS  read-only
    STATUS      current
    DESCRIPTION
        "
        Indicates the count of starting reprovision. "
    ::= { hwMsCommonCtrlMsgEntry 5 }

  hwMsCfidCannotReprov OBJECT-TYPE
    SYNTAX      Counter32
    MAX-ACCESS  read-only
    STATUS      current
    DESCRIPTION
        "
        Indicates the count of failed reprovision. "
    ::= { hwMsCommonCtrlMsgEntry 6 }

  hwMsCfidReqVarIid OBJECT-TYPE
    SYNTAX      Counter32
    MAX-ACCESS  read-only
    STATUS      current
    DESCRIPTION
        "
        Indicates the count of requesting for the variable and the interface ID. "
    ::= { hwMsCommonCtrlMsgEntry 7 }

  hwMsCfidVarAndIid OBJECT-TYPE
    SYNTAX      Counter32
    MAX-ACCESS  read-only
    STATUS      current
    DESCRIPTION
        "
        Indicates the count of the variable and the interface ID. "
    ::= { hwMsCommonCtrlMsgEntry 8 }

  hwMsCfidBlockingStarted OBJECT-TYPE
    SYNTAX      Counter32
    MAX-ACCESS  read-only
    STATUS      current
    DESCRIPTION
        "
        Indicates the count of started block. "
    ::= { hwMsCommonCtrlMsgEntry 9 }

  hwMsCfidRestartReq OBJECT-TYPE
    SYNTAX      Counter32
    MAX-ACCESS  read-only
    STATUS      current
    DESCRIPTION
        "
        Indicates the count of restart requests. "
    ::= { hwMsCommonCtrlMsgEntry 10 }

  hwMsCfidRestartComp OBJECT-TYPE
    SYNTAX      Counter32
    MAX-ACCESS  read-only
    STATUS      current
    DESCRIPTION
        "
        Indicates the count of completed restarts. "
    ::= { hwMsCommonCtrlMsgEntry 11 }

  hwMsCfidUnblockAllPortReq OBJECT-TYPE
    SYNTAX      Counter32
    MAX-ACCESS  read-only
    STATUS      current
    DESCRIPTION
        "
        Indicates the count of the requests for unblocking all the ports. "
    ::= { hwMsCommonCtrlMsgEntry 12 }

  hwMsCfidUnblockAllPortAck OBJECT-TYPE
    SYNTAX      Counter32
    MAX-ACCESS  read-only
    STATUS      current
    DESCRIPTION
        "
        Indicates the count of the acknowledgement for unblocking all the ports. "
    ::= { hwMsCommonCtrlMsgEntry 13 }

  hwMsCfidUnblockAllPortRej OBJECT-TYPE
    SYNTAX      Counter32
    MAX-ACCESS  read-only
    STATUS      current
    DESCRIPTION
        "
        Indicates the count of the rejection to unblocking all the ports. "
    ::= { hwMsCommonCtrlMsgEntry 14 }

  hwMsCfidUnblockAllPortComp OBJECT-TYPE
    SYNTAX      Counter32
    MAX-ACCESS  read-only
    STATUS      current
    DESCRIPTION
        "
        Indicates the count of unblocking all the ports. "
    ::= { hwMsCommonCtrlMsgEntry 15 }

  hwMsCfidUnblockAllPstnPortReq OBJECT-TYPE
    SYNTAX      Counter32
    MAX-ACCESS  read-only
    STATUS      current
    DESCRIPTION
        "
        Indicates the count of the requests for unblocking all the PSTN ports. "
    ::= { hwMsCommonCtrlMsgEntry 16 }

  hwMsCfidUnblockAllPstnPortAck OBJECT-TYPE
    SYNTAX      Counter32
    MAX-ACCESS  read-only
    STATUS      current
    DESCRIPTION
        "
        Indicates the count of the acknowledgement for unblocking all the PSTN ports. "
    ::= { hwMsCommonCtrlMsgEntry 17 }

  hwMsCfidUnblockAllPstnPortRej OBJECT-TYPE
    SYNTAX      Counter32
    MAX-ACCESS  read-only
    STATUS      current
    DESCRIPTION
        "
        Indicates the count of the rejection to unblocking all the PSTN ports. "
    ::= { hwMsCommonCtrlMsgEntry 18 }

  hwMsCfidUnblockAllPstnPortComp OBJECT-TYPE
    SYNTAX      Counter32
    MAX-ACCESS  read-only
    STATUS      current
    DESCRIPTION
        "
        Indicates the count of unblocking all the PSTN ports. "
    ::= { hwMsCommonCtrlMsgEntry 19 }

  hwMsCfidUnblockAllIsdnPortReq OBJECT-TYPE
    SYNTAX      Counter32
    MAX-ACCESS  read-only
    STATUS      current
    DESCRIPTION
        "
        Indicates the count of the requests for unblocking all the ISDN ports. "
    ::= { hwMsCommonCtrlMsgEntry 20 }

  hwMsCfidUnblockAllIsdnPortAck OBJECT-TYPE
    SYNTAX      Counter32
    MAX-ACCESS  read-only
    STATUS      current
    DESCRIPTION
        "
        Indicates the count of the acknowledgement for unblocking all the ISDN ports. "
    ::= { hwMsCommonCtrlMsgEntry 21 }

  hwMsCfidUnblockAllIsdnPortRej OBJECT-TYPE
    SYNTAX      Counter32
    MAX-ACCESS  read-only
    STATUS      current
    DESCRIPTION
        "
        Indicates the count of the rejection to unblocking all the ISDN ports. "
    ::= { hwMsCommonCtrlMsgEntry 22 }

  hwMsCfidUnblockAllIsdnPortComp OBJECT-TYPE
    SYNTAX      Counter32
    MAX-ACCESS  read-only
    STATUS      current
    DESCRIPTION
        "
        Indicates the count of unblocking all the ISDN ports. "
    ::= { hwMsCommonCtrlMsgEntry 23 }

  hwMsCfidBlockAllPstnPortReq OBJECT-TYPE
    SYNTAX      Counter32
    MAX-ACCESS  read-only
    STATUS      current
    DESCRIPTION
        "
        Indicates the count of the requests for blocking all the PSTN ports. "
    ::= { hwMsCommonCtrlMsgEntry 24 }

  hwMsCfidBlockAllPstnPortAck OBJECT-TYPE
    SYNTAX      Counter32
    MAX-ACCESS  read-only
    STATUS      current
    DESCRIPTION
        "
        Indicates the count of the acknowledgement for blocking all the PSTN ports. "
    ::= { hwMsCommonCtrlMsgEntry 25 }

  hwMsCfidBlockAllPstnPortRej OBJECT-TYPE
    SYNTAX      Counter32
    MAX-ACCESS  read-only
    STATUS      current
    DESCRIPTION
        "
        Indicates the count of the rejection to blocking all the PSTN ports. "
    ::= { hwMsCommonCtrlMsgEntry 26 }

  hwMsCfidBlockAllPstnPortComp OBJECT-TYPE
    SYNTAX      Counter32
    MAX-ACCESS  read-only
    STATUS      current
    DESCRIPTION
        "
        Indicates the count of blocking all the PSTN ports. "
    ::= { hwMsCommonCtrlMsgEntry 27 }

  hwMsCfidBlockAllIsdnPortReq OBJECT-TYPE
    SYNTAX      Counter32
    MAX-ACCESS  read-only
    STATUS      current
    DESCRIPTION
        "
        Indicates the count of the requests for blocking all the ISDN ports. "
    ::= { hwMsCommonCtrlMsgEntry 28 }

  hwMsCfidBlockAllIsdnPortAck OBJECT-TYPE
    SYNTAX      Counter32
    MAX-ACCESS  read-only
    STATUS      current
    DESCRIPTION
        "
        Indicates the count of the acknowledgement for blocking all the ISDN ports. "
    ::= { hwMsCommonCtrlMsgEntry 29 }

  hwMsCfidBlockAllIsdnPortRej OBJECT-TYPE
    SYNTAX      Counter32
    MAX-ACCESS  read-only
    STATUS      current
    DESCRIPTION
        "
        Indicates the count of the rejection to blocking all the ISDN ports. "
    ::= { hwMsCommonCtrlMsgEntry 30 }

  hwMsCfidBlockAllIsdnPortComp OBJECT-TYPE
    SYNTAX      Counter32
    MAX-ACCESS  read-only
    STATUS      current
    DESCRIPTION
        "
        Indicates the count of blocking all the ISDN ports. "
    ::= { hwMsCommonCtrlMsgEntry 31 }

  hwMsPortCtrlMsgTable OBJECT-TYPE
    SYNTAX      SEQUENCE OF HwMsPortCtrlMsgEntry
    MAX-ACCESS  not-accessible
    STATUS      current
    DESCRIPTION
      "
        Indicates the messages statistics of the Port Control Protocol.
        The index of this table is hwV5InterfaceID. "
    ::= { hwMs 13 }

  hwMsPortCtrlMsgEntry OBJECT-TYPE
    SYNTAX      HwMsPortCtrlMsgEntry
    MAX-ACCESS  not-accessible
    STATUS      current
    DESCRIPTION
      "
        Indicates the messages statistics of the Port Control Protocol.
        The index of this entry is hwV5InterfaceID."
    INDEX    {
              hwV5InterfaceID
             }
    ::= { hwMsPortCtrlMsgTable 1 }

  HwMsPortCtrlMsgEntry ::=
    SEQUENCE
    {
      hwMsCpfeUpFe101   Counter32,
      hwMsCpfeUpFe102   Counter32,
      hwMsCpfeUpFe103   Counter32,
      hwMsCpfeUpFe104   Counter32,
      hwMsCpfeUpFe105   Counter32,
      hwMsCpfeUpFe106   Counter32,
      hwMsCpfeUpFe201   Counter32,
      hwMsCpfeUpFe202   Counter32,
      hwMsCpfeUpFe203   Counter32,
      hwMsCpfeUpFe204   Counter32,
      hwMsCpfeUpFe205   Counter32,
      hwMsCpfeUpFe206   Counter32,
      hwMsCpfeUpFe207   Counter32,
      hwMsCpfeUpFe208   Counter32,
      hwMsCpfeUpFe209   Counter32,
      hwMsCpfeUpFe210   Counter32
    }

  hwMsCpfeUpFe101 OBJECT-TYPE
    SYNTAX      Counter32
    MAX-ACCESS  read-only
    STATUS      current
    DESCRIPTION
        "
        Indicates the count of Activate Access. "
    ::= { hwMsPortCtrlMsgEntry 1 }

  hwMsCpfeUpFe102 OBJECT-TYPE
    SYNTAX      Counter32
    MAX-ACCESS  read-only
    STATUS      current
    DESCRIPTION
        "
        Indicates the count of Activated by User. "
    ::= { hwMsPortCtrlMsgEntry 2 }

  hwMsCpfeUpFe103 OBJECT-TYPE
    SYNTAX      Counter32
    MAX-ACCESS  read-only
    STATUS      current
    DESCRIPTION
        "
        Indicates the count of DS (access digital section) Activated. "
    ::= { hwMsPortCtrlMsgEntry 3 }

  hwMsCpfeUpFe104 OBJECT-TYPE
    SYNTAX      Counter32
    MAX-ACCESS  read-only
    STATUS      current
    DESCRIPTION
        "
        Indicates the count of Access Activated. "
    ::= { hwMsPortCtrlMsgEntry 4 }

  hwMsCpfeUpFe105 OBJECT-TYPE
    SYNTAX      Counter32
    MAX-ACCESS  read-only
    STATUS      current
    DESCRIPTION
        "
        Indicates the count of Deactivate Access. "
    ::= { hwMsPortCtrlMsgEntry 5 }

  hwMsCpfeUpFe106 OBJECT-TYPE
    SYNTAX      Counter32
    MAX-ACCESS  read-only
    STATUS      current
    DESCRIPTION
        "
        Indicates the count of Access Deactivated. "
    ::= { hwMsPortCtrlMsgEntry 6 }

  hwMsCpfeUpFe201 OBJECT-TYPE
    SYNTAX      Counter32
    MAX-ACCESS  read-only
    STATUS      current
    DESCRIPTION
        "
        Indicates the count of Unblock 201. "
    ::= { hwMsPortCtrlMsgEntry 7 }

  hwMsCpfeUpFe202 OBJECT-TYPE
    SYNTAX      Counter32
    MAX-ACCESS  read-only
    STATUS      current
    DESCRIPTION
        "
        Indicates the count of Unblock 202. "
    ::= { hwMsPortCtrlMsgEntry 8 }

  hwMsCpfeUpFe203 OBJECT-TYPE
    SYNTAX      Counter32
    MAX-ACCESS  read-only
    STATUS      current
    DESCRIPTION
        "
        Indicates the count of Block 203. "
    ::= { hwMsPortCtrlMsgEntry 9 }

  hwMsCpfeUpFe204 OBJECT-TYPE
    SYNTAX      Counter32
    MAX-ACCESS  read-only
    STATUS      current
    DESCRIPTION
        "
        Indicates the count of Block 204. "
    ::= { hwMsPortCtrlMsgEntry 10 }

  hwMsCpfeUpFe205 OBJECT-TYPE
    SYNTAX      Counter32
    MAX-ACCESS  read-only
    STATUS      current
    DESCRIPTION
        "
        Indicates the count of Block Request. "
    ::= { hwMsPortCtrlMsgEntry 11 }

  hwMsCpfeUpFe206 OBJECT-TYPE
    SYNTAX      Counter32
    MAX-ACCESS  read-only
    STATUS      current
    DESCRIPTION
        "
        Indicates the count of Performance Level. "
    ::= { hwMsPortCtrlMsgEntry 12 }

  hwMsCpfeUpFe207 OBJECT-TYPE
    SYNTAX      Counter32
    MAX-ACCESS  read-only
    STATUS      current
    DESCRIPTION
        "
        Indicates the count of Block D-channel. "
    ::= { hwMsPortCtrlMsgEntry 13 }

  hwMsCpfeUpFe208 OBJECT-TYPE
    SYNTAX      Counter32
    MAX-ACCESS  read-only
    STATUS      current
    DESCRIPTION
        "
        Indicates the count of Unblock D-channel. "
    ::= { hwMsPortCtrlMsgEntry 14 }

  hwMsCpfeUpFe209 OBJECT-TYPE
    SYNTAX      Counter32
    MAX-ACCESS  read-only
    STATUS      current
    DESCRIPTION
        "
        Indicates the count of TE Service Terminated. "
    ::= { hwMsPortCtrlMsgEntry 15 }

  hwMsCpfeUpFe210 OBJECT-TYPE
    SYNTAX      Counter32
    MAX-ACCESS  read-only
    STATUS      current
    DESCRIPTION
        "
        Indicates the count of Intra-network Fault. "
    ::= { hwMsPortCtrlMsgEntry 16 }

  hwMsLinkCtrlMsgTable OBJECT-TYPE
    SYNTAX      SEQUENCE OF HwMsLinkCtrlMsgEntry
    MAX-ACCESS  not-accessible
    STATUS      current
    DESCRIPTION
      "
        Indicates the Link Control Protocol message statistics.
        The index of this table is hwV5InterfaceID. "
    ::= { hwMs 14 }

  hwMsLinkCtrlMsgEntry OBJECT-TYPE
    SYNTAX      HwMsLinkCtrlMsgEntry
    MAX-ACCESS  not-accessible
    STATUS      current
    DESCRIPTION
      "
        Indicates the Link Control Protocol message statistics.
        The index of this entry is hwV5InterfaceID."
    INDEX    {
              hwV5InterfaceID
             }
    ::= { hwMsLinkCtrlMsgTable 1 }

  HwMsLinkCtrlMsgEntry ::=
    SEQUENCE
    {
      hwMsFeIDReq   Counter32,
      hwMsFeIDAck   Counter32,
      hwMsFeIDRel   Counter32,
      hwMsFeIDRej   Counter32,
      hwMsFe301 Counter32,
      hwMsFe302 Counter32,
      hwMsFe303 Counter32,
      hwMsFe304 Counter32,
      hwMsFe305 Counter32,
      hwMsFe306 Counter32
    }

  hwMsFeIDReq OBJECT-TYPE
    SYNTAX      Counter32
    MAX-ACCESS  read-only
    STATUS      current
    DESCRIPTION
        "
        Indicates the count of Link ID Request. "
    ::= { hwMsLinkCtrlMsgEntry 1 }

  hwMsFeIDAck OBJECT-TYPE
    SYNTAX      Counter32
    MAX-ACCESS  read-only
    STATUS      current
    DESCRIPTION
        "
        Indicates the count of Link ID Ackowledged. "
    ::= { hwMsLinkCtrlMsgEntry 2 }

  hwMsFeIDRel OBJECT-TYPE
    SYNTAX      Counter32
    MAX-ACCESS  read-only
    STATUS      current
    DESCRIPTION
        "
        Indicates the count of Link ID Released. "
    ::= { hwMsLinkCtrlMsgEntry 3 }

  hwMsFeIDRej OBJECT-TYPE
    SYNTAX      Counter32
    MAX-ACCESS  read-only
    STATUS      current
    DESCRIPTION
        "
        Indicates the count of Link ID Rejected. "
    ::= { hwMsLinkCtrlMsgEntry 4 }

  hwMsFe301 OBJECT-TYPE
    SYNTAX      Counter32
    MAX-ACCESS  read-only
    STATUS      current
    DESCRIPTION
        "
        Indicates the count of Unblock Link (LE -> AN). "
    ::= { hwMsLinkCtrlMsgEntry 5 }

  hwMsFe302 OBJECT-TYPE
    SYNTAX      Counter32
    MAX-ACCESS  read-only
    STATUS      current
    DESCRIPTION
        "
        Indicates the count of Unblock Link (AN -> LE). "
    ::= { hwMsLinkCtrlMsgEntry 6 }

  hwMsFe303 OBJECT-TYPE
    SYNTAX      Counter32
    MAX-ACCESS  read-only
    STATUS      current
    DESCRIPTION
        "
        Indicates the count of Block Link (LE -> AN). "
    ::= { hwMsLinkCtrlMsgEntry 7 }

  hwMsFe304 OBJECT-TYPE
    SYNTAX      Counter32
    MAX-ACCESS  read-only
    STATUS      current
    DESCRIPTION
        "
        Indicates the count of Block Link (AN -> LE). "
    ::= { hwMsLinkCtrlMsgEntry 8 }

  hwMsFe305 OBJECT-TYPE
    SYNTAX      Counter32
    MAX-ACCESS  read-only
    STATUS      current
    DESCRIPTION
        "
        Indicates the count of Block Request Deferrable. "
    ::= { hwMsLinkCtrlMsgEntry 9 }

  hwMsFe306 OBJECT-TYPE
    SYNTAX      Counter32
    MAX-ACCESS  read-only
    STATUS      current
    DESCRIPTION
        "
        Indicates the count of Block Request Not Deferrable. "
    ::= { hwMsLinkCtrlMsgEntry 10 }

  hwMsProtMsgTable OBJECT-TYPE
    SYNTAX      SEQUENCE OF HwMsProtMsgEntry
    MAX-ACCESS  not-accessible
    STATUS      current
    DESCRIPTION
      "
        Indicates the count of Protect Control Protocol message statistics.
        The index of this table is hwV5InterfaceID. "
    ::= { hwMs 15 }

  hwMsProtMsgEntry OBJECT-TYPE
    SYNTAX      HwMsProtMsgEntry
    MAX-ACCESS  not-accessible
    STATUS      current
    DESCRIPTION
      "
        Indicates the count of Protect Control Protocol message statistics.
        The index of this entry is hwV5InterfaceID."
    INDEX    {
              hwV5InterfaceID
             }
    ::= { hwMsProtMsgTable 1 }

  HwMsProtMsgEntry ::=
    SEQUENCE
    {
      hwMsProtSwitchOverReq Counter32,
      hwMsProtSwitchOverCom Counter32,
      hwMsProtOsSwitchOverCom   Counter32,
      hwMsProtSwitchOverAck Counter32,
      hwMsProtSwitchOverRej Counter32,
      hwMsProtProtocolError Counter32,
      hwMsProtResetSnCom    Counter32,
      hwMsProtResetSnAck    Counter32
    }

  hwMsProtSwitchOverReq OBJECT-TYPE
    SYNTAX      Counter32
    MAX-ACCESS  read-only
    STATUS      current
    DESCRIPTION
        "
        Indicates the count of Switchover Request. "
    ::= { hwMsProtMsgEntry 1 }

  hwMsProtSwitchOverCom OBJECT-TYPE
    SYNTAX      Counter32
    MAX-ACCESS  read-only
    STATUS      current
    DESCRIPTION
        "
        Indicates the count of Switchover Command. "
    ::= { hwMsProtMsgEntry 2 }

  hwMsProtOsSwitchOverCom OBJECT-TYPE
    SYNTAX      Counter32
    MAX-ACCESS  read-only
    STATUS      current
    DESCRIPTION
        "
        Indicates the count of OS Switchover Command. "
    ::= { hwMsProtMsgEntry 3 }

  hwMsProtSwitchOverAck OBJECT-TYPE
    SYNTAX      Counter32
    MAX-ACCESS  read-only
    STATUS      current
    DESCRIPTION
        "
        Indicates the count of Switchover Acknowledged. "
    ::= { hwMsProtMsgEntry 4 }

  hwMsProtSwitchOverRej OBJECT-TYPE
    SYNTAX      Counter32
    MAX-ACCESS  read-only
    STATUS      current
    DESCRIPTION
        "
        Indicates the count of Switchover Rejected. "
    ::= { hwMsProtMsgEntry 5 }

  hwMsProtProtocolError OBJECT-TYPE
    SYNTAX      Counter32
    MAX-ACCESS  read-only
    STATUS      current
    DESCRIPTION
        "
        Indicates the count of Protocol Error. "
    ::= { hwMsProtMsgEntry 6 }

  hwMsProtResetSnCom OBJECT-TYPE
    SYNTAX      Counter32
    MAX-ACCESS  read-only
    STATUS      current
    DESCRIPTION
        "
        Indicates the count of Reset Suit Command. "
    ::= { hwMsProtMsgEntry 7 }

  hwMsProtResetSnAck OBJECT-TYPE
    SYNTAX      Counter32
    MAX-ACCESS  read-only
    STATUS      current
    DESCRIPTION
        "
        Indicates the count of Reset Suit Acknowledged. "
    ::= { hwMsProtMsgEntry 8 }

  hwMsIsdnMsgTable OBJECT-TYPE
    SYNTAX      SEQUENCE OF HwMsIsdnMsgEntry
    MAX-ACCESS  not-accessible
    STATUS      current
    DESCRIPTION
      "
        Indicates the ISDN message statistics.
        The index of this table is hwV5InterfaceID. "
    ::= { hwMs 16 }

  hwMsIsdnMsgEntry OBJECT-TYPE
    SYNTAX      HwMsIsdnMsgEntry
    MAX-ACCESS  not-accessible
    STATUS      current
    DESCRIPTION
      "
        Indicates the ISDN message statistics.
        The index of this entry is hwV5InterfaceID."
    INDEX    {
              hwV5InterfaceID
             }
    ::= { hwMsIsdnMsgTable 1 }

  HwMsIsdnMsgEntry ::=
    SEQUENCE
    {
      hwMsIsdnRecievew  Counter32,
      hwMsIsdnSend  Counter32
    }

  hwMsIsdnRecievew OBJECT-TYPE
    SYNTAX      Counter32
    MAX-ACCESS  read-only
    STATUS      current
    DESCRIPTION
        "
        Indicates the count of Received Messages. "
    ::= { hwMsIsdnMsgEntry 1 }

  hwMsIsdnSend OBJECT-TYPE
    SYNTAX      Counter32
    MAX-ACCESS  read-only
    STATUS      current
    DESCRIPTION
        "
        Indicates the count of Transmitted Messages. "
    ::= { hwMsIsdnMsgEntry 2 }

  hwMsLogCChlTable OBJECT-TYPE
    SYNTAX      SEQUENCE OF HwMsLogCChlEntry
    MAX-ACCESS  not-accessible
    STATUS      current
    DESCRIPTION
      "
        Indicates the message statistics of the V5 logical C channel.
        The indexes of this table are hwV5InterfaceID and hwMsLogCChlID. "
    ::= { hwMs 17 }

  hwMsLogCChlEntry OBJECT-TYPE
    SYNTAX      HwMsLogCChlEntry
    MAX-ACCESS  not-accessible
    STATUS      current
    DESCRIPTION
      "
        Indicates the message statistics of the V5 logical C channel.
        The indexes of this entry are hwV5InterfaceID and hwMsLogCChlID."
    INDEX    {
              hwV5InterfaceID,
              hwMsLogCChlID
             }
    ::= { hwMsLogCChlTable 1 }

  HwMsLogCChlEntry ::=
    SEQUENCE
    {
      hwMsLogCChlID Integer32,
      hwMsLogCChlSendFrames Counter32,
      hwMsLogCChlResendFrames   Counter32,
      hwMsLogCChlSendBytes  Counter32,
      hwMsLogCChlResendBytes    Counter32,
      hwMsLogCChlReceivedFrames Counter32,
      hwMsLogCChlReceivedBytes  Counter32,
      hwMsLogCChlReceivedInvalidFrames  Counter32,
      hwMsLogCChlT200Expiry Counter32,
      hwMsLogCChlT300Expiry Counter32
    }

  hwMsLogCChlID OBJECT-TYPE
    SYNTAX      Integer32
    MAX-ACCESS  not-accessible
    STATUS      current
    DESCRIPTION
        "
         Indicates the logical C channel ID. "
    ::= { hwMsLogCChlEntry 1 }

  hwMsLogCChlSendFrames OBJECT-TYPE
    SYNTAX      Counter32
    MAX-ACCESS  read-only
    STATUS      current
    DESCRIPTION
        "
        Indicates the count of Transmitted Frames. "
    ::= { hwMsLogCChlEntry 2 }

  hwMsLogCChlResendFrames OBJECT-TYPE
    SYNTAX      Counter32
    MAX-ACCESS  read-only
    STATUS      current
    DESCRIPTION
        "
        Indicates the count of Retransmitted Frames. "
    ::= { hwMsLogCChlEntry 3 }

  hwMsLogCChlSendBytes OBJECT-TYPE
    SYNTAX      Counter32
    MAX-ACCESS  read-only
    STATUS      current
    DESCRIPTION
        "
        Indicates the count of Transmitted Bytes. "
    ::= { hwMsLogCChlEntry 4 }

  hwMsLogCChlResendBytes OBJECT-TYPE
    SYNTAX      Counter32
    MAX-ACCESS  read-only
    STATUS      current
    DESCRIPTION
        "
        Indicates the count of Retransmitted Bytes. "
    ::= { hwMsLogCChlEntry 5 }

  hwMsLogCChlReceivedFrames OBJECT-TYPE
    SYNTAX      Counter32
    MAX-ACCESS  read-only
    STATUS      current
    DESCRIPTION
        "
        Indicates the count of Received Frames. "
    ::= { hwMsLogCChlEntry 6 }

  hwMsLogCChlReceivedBytes OBJECT-TYPE
    SYNTAX      Counter32
    MAX-ACCESS  read-only
    STATUS      current
    DESCRIPTION
        "
        Indicates the count of Received Bytes. "
    ::= { hwMsLogCChlEntry 7 }

  hwMsLogCChlReceivedInvalidFrames OBJECT-TYPE
    SYNTAX      Counter32
    MAX-ACCESS  read-only
    STATUS      current
    DESCRIPTION
        "
        Indicates the count of Received Invalid Frames. "
    ::= { hwMsLogCChlEntry 8 }

  hwMsLogCChlT200Expiry OBJECT-TYPE
    SYNTAX      Counter32
    MAX-ACCESS  read-only
    STATUS      current
    DESCRIPTION
        "
        Indicates the count of T200 ACK Timeouts. "
    ::= { hwMsLogCChlEntry 9 }

  hwMsLogCChlT300Expiry OBJECT-TYPE
    SYNTAX      Counter32
    MAX-ACCESS  read-only
    STATUS      current
    DESCRIPTION
        "
        Indicates the count of T203 ACK Timeouts. "
    ::= { hwMsLogCChlEntry 10 }


  hwMsMgInterfaceTable OBJECT-TYPE
    SYNTAX      SEQUENCE OF HwMsMgInterfaceEntry
    MAX-ACCESS  not-accessible
    STATUS      current
    DESCRIPTION
      "
        Indicates the MG interface call statistics.
        The indexes of this table are hwMsMgInterfaceMGID and hwMsMgInterfaceResultNo. "
    ::= { hwMs 18 }

  hwMsMgInterfaceEntry OBJECT-TYPE
    SYNTAX      HwMsMgInterfaceEntry
    MAX-ACCESS  not-accessible
    STATUS      current
    DESCRIPTION
      "
        Indicates the MG interface call statistics.
        The indexes of this entry are hwMsMgInterfaceMGID and hwMsMgInterfaceResultNo."
    INDEX    {
              hwMsMgInterfaceMGID,
              hwMsMgInterfaceResultNo
             }
    ::= { hwMsMgInterfaceTable 1 }

  HwMsMgInterfaceEntry ::=
    SEQUENCE
    {
      hwMsMgInterfaceMGID           Integer32,
      hwMsMgInterfaceResultNo       Integer32,
      hwMsMgInterfaceCallOffhook        Counter32,
      hwMsMgInterfaceCalledOffhook   Counter32,
      hwMsMgInterfaceFax            Counter32,
      hwMsMgInterfaceModem          Counter32,
      hwMsMgInterfaceResultTime     DateAndTime
    }

  hwMsMgInterfaceMGID OBJECT-TYPE
    SYNTAX      Integer32(0..16777215)
    MAX-ACCESS  not-accessible
    STATUS      current
    DESCRIPTION
        "
         Indicates the MG ID. "
    ::= { hwMsMgInterfaceEntry 1 }

  hwMsMgInterfaceResultNo OBJECT-TYPE
    SYNTAX      Integer32(0..9)
    MAX-ACCESS  not-accessible
    STATUS      current
    DESCRIPTION
        "
         Indicates the call statistics result number. "
    ::= { hwMsMgInterfaceEntry 2 }

  hwMsMgInterfaceCallOffhook OBJECT-TYPE
    SYNTAX      Counter32
    MAX-ACCESS  read-only
    STATUS      current
    DESCRIPTION
        "
        Indicates the count of caller pickups. "
    ::= { hwMsMgInterfaceEntry 3 }

  hwMsMgInterfaceCalledOffhook OBJECT-TYPE
    SYNTAX      Counter32
    MAX-ACCESS  read-only
    STATUS      current
    DESCRIPTION
        "
        Indicates the count of called pickups. "
    ::= { hwMsMgInterfaceEntry 4 }


  hwMsMgInterfaceFax OBJECT-TYPE
    SYNTAX      Counter32
    MAX-ACCESS  read-only
    STATUS      current
    DESCRIPTION
        "
        Indicates the count of fax occurrences.
        The fax occurrences of the MG in a period of time are counted. The fax detection of the MG is the occurring flag, and the fax occurrences are counted when the fax is finished. The V.34 high-speed fax is similar to the modem, so the occurrences of the V.34 high-speed fax are not counted.
        "
    ::= { hwMsMgInterfaceEntry 5 }

  hwMsMgInterfaceModem OBJECT-TYPE
    SYNTAX      Counter32
    MAX-ACCESS  read-only
    STATUS      current
    DESCRIPTION
        "
        Indicates the count of modem occurrences.
        The modem occurrences of the MG in a period of time are counted. The modem detection of the MG is the occurring flag, and the modem occurrences are counted when the fax is finished. The V.34 high-speed fax is similar to the modem, so the occurrences of the V.34 high-speed fax are counted as the modem occurrences.
        "
    ::= { hwMsMgInterfaceEntry 6 }

  hwMsMgInterfaceResultTime OBJECT-TYPE
    SYNTAX      DateAndTime
    MAX-ACCESS  read-only
    STATUS      current
    DESCRIPTION
        "
        Indicates the start time of counting results. "
    ::= { hwMsMgInterfaceEntry 7 }

  hwMsOverloadTable OBJECT-TYPE
    SYNTAX      SEQUENCE OF HwMsOverloadEntry
    MAX-ACCESS  not-accessible
    STATUS      current
    DESCRIPTION
      "
      Indicates the overload statistics.
      The index of this table is hwMsOverloadMGID.
      "
    ::= { hwMs 19 }

  hwMsOverloadEntry OBJECT-TYPE
    SYNTAX      HwMsOverloadEntry
    MAX-ACCESS  not-accessible
    STATUS      current
    DESCRIPTION
      "
      Indicates the overload statistics.
      The index of this entry is hwMsOverloadMGID."
    INDEX    {
              hwMsOverloadMGID
             }
    ::= { hwMsOverloadTable 1 }

  HwMsOverloadEntry ::=
    SEQUENCE
    {
      hwMsOverloadMGID                   Integer32,
      hwMsOverloadRejectedCallCPU        Counter32,
      hwMsOverloadEmergencyCallCPU       Counter32,
      hwMsOverloadRejectedCallBandwidth  Counter32,
      hwMsOverloadEmergencyCallBandwidth Counter32
    }

  hwMsOverloadMGID OBJECT-TYPE
    SYNTAX      Integer32(0..16777215)
    MAX-ACCESS  not-accessible
    STATUS      current
    DESCRIPTION
        "
        Indicates the interface ID.
        "
    ::= { hwMsOverloadEntry 1 }

  hwMsOverloadRejectedCallCPU OBJECT-TYPE
    SYNTAX      Counter32
    MAX-ACCESS  read-only
    STATUS      current
    DESCRIPTION
        "
        Indicates the count of rejected calls during the CPU overload.
        "
    ::= { hwMsOverloadEntry 2 }

  hwMsOverloadEmergencyCallCPU OBJECT-TYPE
    SYNTAX      Counter32
    MAX-ACCESS  read-only
    STATUS      current
    DESCRIPTION
        "
        Indicates the count of passed emergency calls during the CPU overload.
        "
    ::= { hwMsOverloadEntry 3 }

  hwMsOverloadRejectedCallBandwidth OBJECT-TYPE
    SYNTAX      Counter32
    MAX-ACCESS  read-only
    STATUS      current
    DESCRIPTION
        "
        Indicates the count of rejected calls due to insufficient bandwidth.
        "
    ::= { hwMsOverloadEntry 4 }

  hwMsOverloadEmergencyCallBandwidth OBJECT-TYPE
    SYNTAX      Counter32
    MAX-ACCESS  read-only
    STATUS      current
    DESCRIPTION
        "
        Indicates the count of passed emergency calls due to insufficient bandwidth.
        "
    ::= { hwMsOverloadEntry 5 }



  hwMsFEPortTrafTable OBJECT IDENTIFIER ::= { hwMs 20 }

  hwMsFEPortInOctets OBJECT-TYPE
    SYNTAX      Counter64
    MAX-ACCESS  read-only
    STATUS      current
    DESCRIPTION
        "
         Indicates the count of received octets. "
    ::= { hwMsFEPortTrafTable 1 }

  hwMsFEPortInPkts OBJECT-TYPE
    SYNTAX      Counter64
    MAX-ACCESS  read-only
    STATUS      current
    DESCRIPTION
        "
        Indicates the count of received packets (excluding the count of error packets). "
    ::= { hwMsFEPortTrafTable 2 }

  hwMsFEPortInErrors OBJECT-TYPE
    SYNTAX      Counter32
    MAX-ACCESS  read-only
    STATUS      current
    DESCRIPTION
        "
        Indicates the count of received error packets. "
    ::= { hwMsFEPortTrafTable 3 }

  hwMsFEPortOutOctets OBJECT-TYPE
    SYNTAX      Counter64
    MAX-ACCESS  read-only
    STATUS      current
    DESCRIPTION
        "
        Indicates the count of transmitted octets. "
    ::= { hwMsFEPortTrafTable 4 }

  hwMsFEPortOutPkts OBJECT-TYPE
    SYNTAX      Counter64
    MAX-ACCESS  read-only
    STATUS      current
    DESCRIPTION
        "
        Indicates the count of transmitted packets. "
    ::= { hwMsFEPortTrafTable 5 }


  hwMsIUALinksetTable OBJECT-TYPE
    SYNTAX      SEQUENCE OF HwMsIUALinksetEntry
    MAX-ACCESS  not-accessible
    STATUS      current
    DESCRIPTION
        "
        A list of hwMsIUALinksetTable objects.
        The index of this table is hwMsIUALinksetNo. "
    ::= { hwMs 21 }

  hwMsIUALinksetEntry OBJECT-TYPE
    SYNTAX      HwMsIUALinksetEntry
    MAX-ACCESS  not-accessible
    STATUS      current
    DESCRIPTION
        "
        A list of hwMsIUALinksetTable objects.
        The index of this entry is hwMsIUALinksetNo."
    INDEX    {
              hwMsIUALinksetNo
             }
    ::= { hwMsIUALinksetTable 1 }

  HwMsIUALinksetEntry ::=
    SEQUENCE
    {
      hwMsIUALinksetNo                          Integer32,
      hwMsIUALinkSetNumOfTxCtrlMsg              Integer32,
      hwMsIUALinkSetNumOfRxCtrlMsg              Integer32,
      hwMsIUALinkSetNumOfTxUserMsg              Integer32,
      hwMsIUALinkSetNumOfRxUserMsg              Integer32,
      hwMsIUALinkSetNumOfRxErrorMsg             Integer32,
      hwMsIUALinkSetBytesOfTxCtrlMsg            Integer32,
      hwMsIUALinkSetBytesOfRxCtrlMsg            Integer32,
      hwMsIUALinkSetBytesOfTxUserMsg            Integer32,
      hwMsIUALinkSetBytesOfRxUserMsg            Integer32,
      hwMsIUALinkSetNumOfPending                Integer32,
      hwMsIUALinkSetDurOfLinksetAct             Integer32,
      hwMsIUALinkSetNumOfLinksetOutOfServ       Integer32,
      hwMsIUALinkSetDurOfLinksetOutOfServ       Integer32,
      hwMsIUALinkSetCumDurOfLinksetOutOfServ    Integer32,
      hwMsIUALinksetAdminStatus                 INTEGER
    }

  hwMsIUALinksetNo OBJECT-TYPE
    SYNTAX      Integer32(0..15)
    MAX-ACCESS  not-accessible
    STATUS      current
    DESCRIPTION
        "Indicates the link set number."
    ::= { hwMsIUALinksetEntry 1 }

  hwMsIUALinkSetNumOfTxCtrlMsg OBJECT-TYPE
    SYNTAX      Integer32
    MAX-ACCESS  read-only
    STATUS      current
    DESCRIPTION
        "Indicates the count of transmitted control messages."
    ::= { hwMsIUALinksetEntry 2 }

  hwMsIUALinkSetNumOfRxCtrlMsg OBJECT-TYPE
    SYNTAX      Integer32
    MAX-ACCESS  read-only
    STATUS      current
    DESCRIPTION
        "Indicates the count of received control messages."
    ::= { hwMsIUALinksetEntry 3 }

  hwMsIUALinkSetNumOfTxUserMsg OBJECT-TYPE
    SYNTAX      Integer32
    MAX-ACCESS  read-only
    STATUS      current
    DESCRIPTION
        "Indicates the count of transmitted service messages."
    ::= { hwMsIUALinksetEntry 4 }

  hwMsIUALinkSetNumOfRxUserMsg OBJECT-TYPE
    SYNTAX      Integer32
    MAX-ACCESS  read-only
    STATUS      current
    DESCRIPTION
        "Indicates the count of received service messages."
    ::= { hwMsIUALinksetEntry 5 }

  hwMsIUALinkSetNumOfRxErrorMsg OBJECT-TYPE
    SYNTAX      Integer32
    MAX-ACCESS  read-only
    STATUS      current
    DESCRIPTION
        "Indicates the count of received error messages."
    ::= { hwMsIUALinksetEntry 6 }

  hwMsIUALinkSetBytesOfTxCtrlMsg OBJECT-TYPE
    SYNTAX      Integer32
    MAX-ACCESS  read-only
    STATUS      current
    DESCRIPTION
        "Indicates the count of transmitted control message bytes."
    ::= { hwMsIUALinksetEntry 7 }

  hwMsIUALinkSetBytesOfRxCtrlMsg OBJECT-TYPE
    SYNTAX      Integer32
    MAX-ACCESS  read-only
    STATUS      current
    DESCRIPTION
        "Indicates the count of received control message bytes."
    ::= { hwMsIUALinksetEntry 8 }

  hwMsIUALinkSetBytesOfTxUserMsg OBJECT-TYPE
    SYNTAX      Integer32
    MAX-ACCESS  read-only
    STATUS      current
    DESCRIPTION
        "Indicates the count of sent service message bytes."
    ::= { hwMsIUALinksetEntry 9 }

  hwMsIUALinkSetBytesOfRxUserMsg OBJECT-TYPE
    SYNTAX      Integer32
    MAX-ACCESS  read-only
    STATUS      current
    DESCRIPTION
        "Indicates the count of received service message bytes."
    ::= { hwMsIUALinksetEntry 10 }

  hwMsIUALinkSetNumOfPending OBJECT-TYPE
    SYNTAX      Integer32
    MAX-ACCESS  read-only
    STATUS      current
    DESCRIPTION
        "Indicates the pending count of the link set."
    ::= { hwMsIUALinksetEntry 11 }

  hwMsIUALinkSetDurOfLinksetAct OBJECT-TYPE
    SYNTAX      Integer32
    MAX-ACCESS  read-only
    STATUS      current
    DESCRIPTION
        "Indicates the duration for activating the IUA link set."
    ::= { hwMsIUALinksetEntry 12 }

  hwMsIUALinkSetNumOfLinksetOutOfServ OBJECT-TYPE
    SYNTAX      Integer32
    MAX-ACCESS  read-only
    STATUS      current
    DESCRIPTION
        "Indicates the count of service interruption of the IUA link set."
    ::= { hwMsIUALinksetEntry 13 }

  hwMsIUALinkSetDurOfLinksetOutOfServ OBJECT-TYPE
    SYNTAX      Integer32
    MAX-ACCESS  read-only
    STATUS      current
    DESCRIPTION
        "Indicates the duration of service interruption of the IUA link set."
    ::= { hwMsIUALinksetEntry 14 }

  hwMsIUALinkSetCumDurOfLinksetOutOfServ OBJECT-TYPE
    SYNTAX      Integer32
    MAX-ACCESS  read-only
    STATUS      current
    DESCRIPTION
        "Indicates the cumulative duration of service interruption of the IUA link set."
    ::= { hwMsIUALinksetEntry 15 }

  hwMsIUALinksetAdminStatus OBJECT-TYPE
    SYNTAX      INTEGER{clear(1)}
    MAX-ACCESS  read-write
    STATUS      current
    DESCRIPTION
        "Indicates to clear the statistics of the link set. 1-Clear.
        Options:
        1. clear(1) -indicates to clear the statistics of the link set
        "
    ::= { hwMsIUALinksetEntry 16 }

  hwMsIUALinkTable OBJECT-TYPE
    SYNTAX      SEQUENCE OF HwMsIUALinkEntry
    MAX-ACCESS  not-accessible
    STATUS      current
    DESCRIPTION
        "
        A list of hwMsIUALinkTable objects.
        The index of this table is hwMsIUALinkNo. "
    ::= { hwMs 22 }

  hwMsIUALinkEntry OBJECT-TYPE
    SYNTAX      HwMsIUALinkEntry
    MAX-ACCESS  not-accessible
    STATUS      current
    DESCRIPTION
        "
        A list of hwMsIUALinkTable objects.
        The index of this entry is hwMsIUALinkNo."
    INDEX    {
              hwMsIUALinkNo
             }
    ::= { hwMsIUALinkTable 1 }

  HwMsIUALinkEntry ::=
    SEQUENCE
    {
      hwMsIUALinkNo                     Integer32,
      hwMsIUALinkNumOfTxCtrlMsg         Integer32,
      hwMsIUALinkNumOfRxCtrlMsg         Integer32,
      hwMsIUALinkNumOfTxUserMsg         Integer32,
      hwMsIUALinkNumOfRxUserMsg         Integer32,
      hwMsIUALinkNumOfRxErrorMsg        Integer32,
      hwMsIUALinkBytesOfTxCtrlMsg       Integer32,
      hwMsIUALinkBytesOfRxCtrlMsg       Integer32,
      hwMsIUALinkBytesOfTxUserMsg       Integer32,
      hwMsIUALinkBytesOfRxUserMsg       Integer32,
      hwMsIUALinkDurOfLinkAct           Integer32,
      hwMsIUALinkNumOfLinkOutOfServ     Integer32,
      hwMsIUALinkDurOfLinkOutOfServ     Integer32,
      hwMsIUALinkCumDurOfLinkOutOfServ  Integer32,
      hwMsIUALinkAdminStatus            INTEGER
    }

  hwMsIUALinkNo OBJECT-TYPE
    SYNTAX      Integer32(0..15)
    MAX-ACCESS  not-accessible
    STATUS      current
    DESCRIPTION
        "Indicates the link set number."
    ::= { hwMsIUALinkEntry 1 }

  hwMsIUALinkNumOfTxCtrlMsg OBJECT-TYPE
    SYNTAX      Integer32
    MAX-ACCESS  read-only
    STATUS      current
    DESCRIPTION
        "Indicates the count of transmitted control messages."
    ::= { hwMsIUALinkEntry 2 }

  hwMsIUALinkNumOfRxCtrlMsg OBJECT-TYPE
    SYNTAX      Integer32
    MAX-ACCESS  read-only
    STATUS      current
    DESCRIPTION
        "Indicates the count of received control messages."
    ::= { hwMsIUALinkEntry 3 }

  hwMsIUALinkNumOfTxUserMsg OBJECT-TYPE
    SYNTAX      Integer32
    MAX-ACCESS  read-only
    STATUS      current
    DESCRIPTION
        "Indicates the count of transmitted service messages."
    ::= { hwMsIUALinkEntry 4 }

  hwMsIUALinkNumOfRxUserMsg OBJECT-TYPE
    SYNTAX      Integer32
    MAX-ACCESS  read-only
    STATUS      current
    DESCRIPTION
        "Indicates the count of received service messages."
    ::= { hwMsIUALinkEntry 5 }

  hwMsIUALinkNumOfRxErrorMsg OBJECT-TYPE
    SYNTAX      Integer32
    MAX-ACCESS  read-only
    STATUS      current
    DESCRIPTION
        "Indicates the count of received error messages."
    ::= { hwMsIUALinkEntry 6 }

  hwMsIUALinkBytesOfTxCtrlMsg OBJECT-TYPE
    SYNTAX      Integer32
    MAX-ACCESS  read-only
    STATUS      current
    DESCRIPTION
        "Indicates the count of transmitted control message bytes."
    ::= { hwMsIUALinkEntry 7 }

  hwMsIUALinkBytesOfRxCtrlMsg OBJECT-TYPE
    SYNTAX      Integer32
    MAX-ACCESS  read-only
    STATUS      current
    DESCRIPTION
        "Indicates the count of received control message bytes."
    ::= { hwMsIUALinkEntry 8 }

  hwMsIUALinkBytesOfTxUserMsg OBJECT-TYPE
    SYNTAX      Integer32
    MAX-ACCESS  read-only
    STATUS      current
    DESCRIPTION
        "Indicates the count of sent service message bytes."
    ::= { hwMsIUALinkEntry 9 }

  hwMsIUALinkBytesOfRxUserMsg OBJECT-TYPE
    SYNTAX      Integer32
    MAX-ACCESS  read-only
    STATUS      current
    DESCRIPTION
        "Indicates the count of received service message bytes."
    ::= { hwMsIUALinkEntry 10 }

  hwMsIUALinkDurOfLinkAct OBJECT-TYPE
    SYNTAX      Integer32
    MAX-ACCESS  read-only
    STATUS      current
    DESCRIPTION
        "Indicates the duration for activating the IUA link."
    ::= { hwMsIUALinkEntry 11 }

  hwMsIUALinkNumOfLinkOutOfServ OBJECT-TYPE
    SYNTAX      Integer32
    MAX-ACCESS  read-only
    STATUS      current
    DESCRIPTION
        "Indicates the count of service interruption of the IUA link."
    ::= { hwMsIUALinkEntry 12 }

  hwMsIUALinkDurOfLinkOutOfServ OBJECT-TYPE
    SYNTAX      Integer32
    MAX-ACCESS  read-only
    STATUS      current
    DESCRIPTION
        "Indicates the duration of service interruption of the IUA link."
    ::= { hwMsIUALinkEntry 13 }

  hwMsIUALinkCumDurOfLinkOutOfServ OBJECT-TYPE
    SYNTAX      Integer32
    MAX-ACCESS  read-only
    STATUS      current
    DESCRIPTION
        "Indicates the cumulative duration of service interruption of the IUA link."
    ::= { hwMsIUALinkEntry 14 }

  hwMsIUALinkAdminStatus OBJECT-TYPE
    SYNTAX      INTEGER{clear(1)}
    MAX-ACCESS  read-write
    STATUS      current
    DESCRIPTION
        "Indicates to clear the statistics of the link. 1-Clear.
        Options:
        1. clear(1) -indicates to clear the statistics of the link
        "
    ::= { hwMsIUALinkEntry 15 }

   hwH248StatTable OBJECT-TYPE
     SYNTAX      SEQUENCE OF HwH248StatEntry
     MAX-ACCESS  not-accessible
     STATUS      current
     DESCRIPTION
         "
         Indicates the performance statistics of the H248 module.
         The index of this table is hwMsH248StatMgId.
         "
     ::= { hwMs 23 }

   hwH248StatEntry OBJECT-TYPE
     SYNTAX      HwH248StatEntry
     MAX-ACCESS  not-accessible
     STATUS      current
     DESCRIPTION
         "
         Indicates the performance statistics of the H248 module.
         The index of this entry is hwMsH248StatMgId."
     INDEX    {
               hwMsH248StatMgId
              }
     ::= { hwH248StatTable 1 }

   HwH248StatEntry ::=
     SEQUENCE
     {
       hwMsH248StatMgId         Integer32,
       hwMsH248InPkts           Counter32,
       hwMsH248OutPkts          Counter32,
       hwMsH248ReSentPkts       Counter32,
       hwMsH248InTransRequests  Counter32,
       hwMsH248InTransReplys    Counter32,
       hwMsH248OutTransRequests Counter32,
       hwMsH248OutTransReplys   Counter32,
       hwMsH248ReSentTrans      Counter32,
       hwMsH248DailTones        Counter32,
       hwMsH248BusyTones        Counter32,
       hwMsH248RingingTones     Counter32,
       hwMsH248HowlerTones      Counter32,
       hwMsH248Error400         Counter32,
       hwMsH248Error401         Counter32,
       hwMsH248Error402         Counter32,
       hwMsH248Error403         Counter32,
       hwMsH248Error406         Counter32,
       hwMsH248Error410         Counter32,
       hwMsH248Error411         Counter32,
       hwMsH248Error412         Counter32,
       hwMsH248Error421         Counter32,
       hwMsH248Error422         Counter32,
       hwMsH248Error430         Counter32,
       hwMsH248Error431         Counter32,
       hwMsH248Error432         Counter32,
       hwMsH248Error433         Counter32,
       hwMsH248Error434         Counter32,
       hwMsH248Error435         Counter32,
       hwMsH248Error440         Counter32,
       hwMsH248Error441         Counter32,
       hwMsH248Error442         Counter32,
       hwMsH248Error443         Counter32,
       hwMsH248Error444         Counter32,
       hwMsH248Error445         Counter32,
       hwMsH248Error446         Counter32,
       hwMsH248Error447         Counter32,
       hwMsH248Error448         Counter32,
       hwMsH248Error450         Counter32,
       hwMsH248Error451         Counter32,
       hwMsH248Error452         Counter32,
       hwMsH248Error453         Counter32,
       hwMsH248Error454         Counter32,
       hwMsH248Error455         Counter32,
       hwMsH248Error456         Counter32,
       hwMsH248Error457         Counter32,
       hwMsH248Error459         Counter32,
       hwMsH248Error471         Counter32,
       hwMsH248Error500         Counter32,
       hwMsH248Error501         Counter32,
       hwMsH248Error502         Counter32,
       hwMsH248Error503         Counter32,
       hwMsH248Error504         Counter32,
       hwMsH248Error505         Counter32,
       hwMsH248Error506         Counter32,
       hwMsH248Error510         Counter32,
       hwMsH248Error512         Counter32,
       hwMsH248Error513         Counter32,
       hwMsH248Error514         Counter32,
       hwMsH248Error515         Counter32,
       -- hwMsH248Error516         Counter32,
       hwMsH248Error517         Counter32,
       hwMsH248Error518         Counter32,
       hwMsH248Error519         Counter32,
       hwMsH248Error520         Counter32,
       hwMsH248Error521         Counter32,
       hwMsH248Error526         Counter32,
       hwMsH248Error529         Counter32,
       hwMsH248Error530         Counter32,
       hwMsH248Error531         Counter32,
       hwMsH248Error532         Counter32,
       hwMsH248Error533         Counter32,
       hwMsH248Error534         Counter32,
       hwMsH248Error540         Counter32,
       hwMsH248Error581         Counter32

     }

   hwMsH248StatMgId OBJECT-TYPE
     SYNTAX      Integer32(0..16777215)
     MAX-ACCESS  not-accessible
     STATUS      current
     DESCRIPTION
         "
         Indicates the MG ID.
         "
     ::= { hwH248StatEntry 1 }

   hwMsH248InPkts OBJECT-TYPE
     SYNTAX      Counter32
     MAX-ACCESS  read-only
     STATUS      current
     DESCRIPTION
         "
         Indicates the count of Received Messages.
         "
     ::= { hwH248StatEntry 2 }

   hwMsH248OutPkts OBJECT-TYPE
     SYNTAX      Counter32
     MAX-ACCESS  read-only
     STATUS      current
     DESCRIPTION
         "
         Indicates the count of Transmitted Messages.
         "
     ::= { hwH248StatEntry 3 }

   hwMsH248ReSentPkts OBJECT-TYPE
     SYNTAX      Counter32
     MAX-ACCESS  read-only
     STATUS      current
     DESCRIPTION
         "
         Indicates the count of retransmitted messages.
         "
     ::= { hwH248StatEntry 4 }

   hwMsH248InTransRequests OBJECT-TYPE
     SYNTAX      Counter32
     MAX-ACCESS  read-only
     STATUS      current
     DESCRIPTION
         "
         Indicates the count of received transaction requests.
         "
     ::= { hwH248StatEntry 5 }

   hwMsH248InTransReplys OBJECT-TYPE
     SYNTAX      Counter32
     MAX-ACCESS  read-only
     STATUS      current
     DESCRIPTION
         "
         Indicates the count of received transaction replies.
         "
     ::= { hwH248StatEntry 6 }

   hwMsH248OutTransRequests OBJECT-TYPE
     SYNTAX      Counter32
     MAX-ACCESS  read-only
     STATUS      current
     DESCRIPTION
         "
         Indicates the count of transmitted transaction requests.
         "
     ::= { hwH248StatEntry 7 }

   hwMsH248OutTransReplys OBJECT-TYPE
     SYNTAX      Counter32
     MAX-ACCESS  read-only
     STATUS      current
     DESCRIPTION
         "
         Indicates the count of transmitted transaction replies.
         "
     ::= { hwH248StatEntry 8 }

   hwMsH248ReSentTrans OBJECT-TYPE
     SYNTAX      Counter32
     MAX-ACCESS  read-only
     STATUS      current
     DESCRIPTION
         "
         Indicates the count of retransmitted transactions.
         "
     ::= { hwH248StatEntry 9 }

   hwMsH248DailTones         OBJECT-TYPE
     SYNTAX      Counter32
     MAX-ACCESS  read-only
     STATUS      current
     DESCRIPTION
         "
         Indicates the count of received dial tone signals.
         "
     ::= { hwH248StatEntry 10 }

   hwMsH248BusyTones         OBJECT-TYPE
     SYNTAX      Counter32
     MAX-ACCESS  read-only
     STATUS      current
     DESCRIPTION
         "
         Indicates the count of received busy tone signals.
         "
     ::= { hwH248StatEntry 11 }

   hwMsH248RingingTones      OBJECT-TYPE
     SYNTAX      Counter32
     MAX-ACCESS  read-only
     STATUS      current
     DESCRIPTION
         "
         Indicates the count of received ringing tone signals.
         "
     ::= { hwH248StatEntry 12 }

   hwMsH248HowlerTones         OBJECT-TYPE
     SYNTAX      Counter32
     MAX-ACCESS  read-only
     STATUS      current
     DESCRIPTION
         "
         Indicates the count of received howling tone signals.
         "
     ::= { hwH248StatEntry 13 }

   hwMsH248Error400             OBJECT-TYPE
     SYNTAX      Counter32
     MAX-ACCESS  read-only
     STATUS      current
     DESCRIPTION
         "
         Indicates the count of ErrCode 400 (Bad Request).
         "
     ::= { hwH248StatEntry 14 }

   hwMsH248Error401             OBJECT-TYPE
     SYNTAX      Counter32
     MAX-ACCESS  read-only
     STATUS      current
     DESCRIPTION
         "
         Indicates the count of ErrCode 401 (Protocol Error).
         "
     ::= { hwH248StatEntry 15 }

   hwMsH248Error402 OBJECT-TYPE
     SYNTAX      Counter32
     MAX-ACCESS  read-only
     STATUS      current
     DESCRIPTION
         "
         Indicates the count of ErrCode 402 (Unauthorized).
         "
     ::= { hwH248StatEntry 16 }

   hwMsH248Error403 OBJECT-TYPE
     SYNTAX      Counter32
     MAX-ACCESS  read-only
     STATUS      current
     DESCRIPTION
         "
         Indicates the count of ErrCode 403 (Syntax Error in transaction).
         "
     ::= { hwH248StatEntry 17 }

   hwMsH248Error406 OBJECT-TYPE
     SYNTAX      Counter32
     MAX-ACCESS  read-only
     STATUS      current
     DESCRIPTION
         "
         Indicates the count of ErrCode 406 (Version Not Supported).
         "
     ::= { hwH248StatEntry 18 }

   hwMsH248Error410 OBJECT-TYPE
     SYNTAX      Counter32
     MAX-ACCESS  read-only
     STATUS      current
     DESCRIPTION
         "
         Indicates the count of ErrCode 410 (Incorrect identifier).
         "
     ::= { hwH248StatEntry 19 }

   hwMsH248Error411 OBJECT-TYPE
     SYNTAX      Counter32
     MAX-ACCESS  read-only
     STATUS      current
     DESCRIPTION
         "
         Indicates the count of ErrCode 411 (Transaction Refers To Unknown Context ID).
         "
     ::= { hwH248StatEntry 20 }

   hwMsH248Error412 OBJECT-TYPE
     SYNTAX      Counter32
     MAX-ACCESS  read-only
     STATUS      current
     DESCRIPTION
         "
         Indicates the count of ErrCode 412 (No Context IDs available).
         "
     ::= { hwH248StatEntry 21 }

    hwMsH248Error421 OBJECT-TYPE
     SYNTAX      Counter32
     MAX-ACCESS  read-only
     STATUS      current
     DESCRIPTION
         "
         Indicates the count of ErrCode 421 (Unknown or illegal of actions).
         "
     ::= { hwH248StatEntry 22 }

     hwMsH248Error422 OBJECT-TYPE
     SYNTAX      Counter32
     MAX-ACCESS  read-only
     STATUS      current
     DESCRIPTION
         "
         Indicates the count of ErrCode 422 (Syntax Error in Action).
         "
     ::= { hwH248StatEntry 23 }

     hwMsH248Error430 OBJECT-TYPE
     SYNTAX      Counter32
     MAX-ACCESS  read-only
     STATUS      current
     DESCRIPTION
         "
         Indicates the count of ErrCode 430 (Unknown Termination ID).
         "
     ::= { hwH248StatEntry 24 }

     hwMsH248Error431 OBJECT-TYPE
     SYNTAX      Counter32
     MAX-ACCESS  read-only
     STATUS      current
     DESCRIPTION
         "
         Indicates the count of ErrCode 431 (No Termination ID matched a wildcard).
         "
     ::= { hwH248StatEntry 25 }

     hwMsH248Error432 OBJECT-TYPE
     SYNTAX      Counter32
     MAX-ACCESS  read-only
     STATUS      current
     DESCRIPTION
         "
         Indicates the count of ErrCode 432 (Out Termination IDs or No Termination ID).
         "
     ::= { hwH248StatEntry 26 }

     hwMsH248Error433 OBJECT-TYPE
     SYNTAX      Counter32
     MAX-ACCESS  read-only
     STATUS      current
     DESCRIPTION
         "
         Indicates the count of ErrCode 433 (Termination ID is already in a Context).
         "
     ::= { hwH248StatEntry 27 }

     hwMsH248Error434 OBJECT-TYPE
     SYNTAX      Counter32
     MAX-ACCESS  read-only
     STATUS      current
     DESCRIPTION
         "
         Indicates the count of ErrCode 434 (Max of Terminations in a Context exceed).
         "
     ::= { hwH248StatEntry 28 }

     hwMsH248Error435 OBJECT-TYPE
     SYNTAX      Counter32
     MAX-ACCESS  read-only
     STATUS      current
     DESCRIPTION
         "
         Indicates the count of ErrCode 435 (Termination ID not in specified Context).
         "
     ::= { hwH248StatEntry 29 }


     hwMsH248Error440 OBJECT-TYPE
     SYNTAX      Counter32
     MAX-ACCESS  read-only
     STATUS      current
     DESCRIPTION
         "
         Indicates the count of ErrCode 440 (Unsupported or unknown Package).
         "
     ::= { hwH248StatEntry 30 }

     hwMsH248Error441 OBJECT-TYPE
     SYNTAX      Counter32
     MAX-ACCESS  read-only
     STATUS      current
     DESCRIPTION
         "
         Indicates the count of ErrCode 441 (Missing Remote Descriptor).
         "
     ::= { hwH248StatEntry 31 }

     hwMsH248Error442 OBJECT-TYPE
     SYNTAX      Counter32
     MAX-ACCESS  read-only
     STATUS      current
     DESCRIPTION
         "
         Indicates the count of ErrCode 442 (Syntax Error in Command).
         "
     ::= { hwH248StatEntry 32 }

     hwMsH248Error443 OBJECT-TYPE
     SYNTAX      Counter32
     MAX-ACCESS  read-only
     STATUS      current
     DESCRIPTION
         "
         Indicates the count of ErrCode 443 (Unsupported or Unknown Command).
         "
     ::= { hwH248StatEntry 33 }

     hwMsH248Error444 OBJECT-TYPE
     SYNTAX      Counter32
     MAX-ACCESS  read-only
     STATUS      current
     DESCRIPTION
         "
         Indicates the count of ErrCode 444 (Unsupported or Unknown Descriptor).
         "
     ::= { hwH248StatEntry 34 }

     hwMsH248Error445 OBJECT-TYPE
     SYNTAX      Counter32
     MAX-ACCESS  read-only
     STATUS      current
     DESCRIPTION
         "
         Indicates the count of ErrCode 445 (Unsupported or Unknown Property).
         "
     ::= { hwH248StatEntry 35 }

     hwMsH248Error446 OBJECT-TYPE
     SYNTAX      Counter32
     MAX-ACCESS  read-only
     STATUS      current
     DESCRIPTION
         "
         Indicates the count of ErrCode 446 (Unsupported or Unknown Parameter).
         "
     ::= { hwH248StatEntry 36 }

     hwMsH248Error447 OBJECT-TYPE
     SYNTAX      Counter32
     MAX-ACCESS  read-only
     STATUS      current
     DESCRIPTION
         "
         Indicates the count of ErrCode 447 (Descriptor not legal in this command).
         "
     ::= { hwH248StatEntry 37 }

     hwMsH248Error448 OBJECT-TYPE
     SYNTAX      Counter32
     MAX-ACCESS  read-only
     STATUS      current
     DESCRIPTION
         "
         Indicates the count of ErrCode 448 (Descriptor appears twice in a command).
         "
     ::= { hwH248StatEntry 38 }

     hwMsH248Error450 OBJECT-TYPE
     SYNTAX      Counter32
     MAX-ACCESS  read-only
     STATUS      current
     DESCRIPTION
         "
         Indicates the count of ErrCode 450 (No such property in this package).
         "
     ::= { hwH248StatEntry 39 }

     hwMsH248Error451 OBJECT-TYPE
     SYNTAX      Counter32
     MAX-ACCESS  read-only
     STATUS      current
     DESCRIPTION
         "
         Indicates the count of ErrCode 451 (No such event in this package).
         "
     ::= { hwH248StatEntry 40 }

     hwMsH248Error452 OBJECT-TYPE
     SYNTAX      Counter32
     MAX-ACCESS  read-only
     STATUS      current
     DESCRIPTION
         "
         Indicates the count of ErrCode 452 (No such signal in this package).
         "
     ::= { hwH248StatEntry 41 }

     hwMsH248Error453 OBJECT-TYPE
     SYNTAX      Counter32
     MAX-ACCESS  read-only
     STATUS      current
     DESCRIPTION
         "
         Indicates the count of ErrCode 453 (No such statistic in this package).
         "
     ::= { hwH248StatEntry 42 }

     hwMsH248Error454 OBJECT-TYPE
     SYNTAX      Counter32
     MAX-ACCESS  read-only
     STATUS      current
     DESCRIPTION
         "
         Indicates the count of ErrCode 454 (No such parameter in this package).
         "
     ::= { hwH248StatEntry 43 }

     hwMsH248Error455 OBJECT-TYPE
     SYNTAX      Counter32
     MAX-ACCESS  read-only
     STATUS      current
     DESCRIPTION
         "
         Indicates the count of ErrCode 455 (Parameter illegal in this Descriptor).
         "
     ::= { hwH248StatEntry 44 }

     hwMsH248Error456 OBJECT-TYPE
     SYNTAX      Counter32
     MAX-ACCESS  read-only
     STATUS      current
     DESCRIPTION
         "
         Indicates the count of ErrCode 456 (Parameter or Property appears twice).
         "
     ::= { hwH248StatEntry 45 }

     hwMsH248Error457 OBJECT-TYPE
     SYNTAX      Counter32
     MAX-ACCESS  read-only
     STATUS      current
     DESCRIPTION
         "
         Indicates the count of ErrCode 457 (Missing parameter in signal or event).
         "
     ::= { hwH248StatEntry 46 }

     hwMsH248Error459 OBJECT-TYPE
     SYNTAX      Counter32
     MAX-ACCESS  read-only
     STATUS      current
     DESCRIPTION
         "
         Indicates the count of ErrCode 459 (Unsupported or Unknown Profile).
         "
     ::= { hwH248StatEntry 47 }

     hwMsH248Error471 OBJECT-TYPE
     SYNTAX      Counter32
     MAX-ACCESS  read-only
     STATUS      current
     DESCRIPTION
         "
         Indicates the count of ErrCode 471 (Implied Add for Multiplex failure).
         "
     ::= { hwH248StatEntry 48 }

     hwMsH248Error500 OBJECT-TYPE
     SYNTAX      Counter32
     MAX-ACCESS  read-only
     STATUS      current
     DESCRIPTION
         "
         Indicates the count of ErrCode 500 (Internal Gateway Error).
         "
     ::= { hwH248StatEntry 49 }

     hwMsH248Error501 OBJECT-TYPE
     SYNTAX      Counter32
     MAX-ACCESS  read-only
     STATUS      current
     DESCRIPTION
         "
         Indicates the count of ErrCode 501 (Not Implemented).
         "
     ::= { hwH248StatEntry 50 }

     hwMsH248Error502 OBJECT-TYPE
     SYNTAX      Counter32
     MAX-ACCESS  read-only
     STATUS      current
     DESCRIPTION
         "
         Indicates the count of ErrCode 502 (Not ready).
         "
     ::= { hwH248StatEntry 51 }

     hwMsH248Error503 OBJECT-TYPE
     SYNTAX      Counter32
     MAX-ACCESS  read-only
     STATUS      current
     DESCRIPTION
         "
         Indicates the count of ErrCode 503 (Service Unavailable).
         "
     ::= { hwH248StatEntry 52 }

     hwMsH248Error504 OBJECT-TYPE
     SYNTAX      Counter32
     MAX-ACCESS  read-only
     STATUS      current
     DESCRIPTION
         "
         Indicates the count of ErrCode 504 (Command Received From Unauthorized Entity).
         "
     ::= { hwH248StatEntry 53 }

     hwMsH248Error505 OBJECT-TYPE
     SYNTAX      Counter32
     MAX-ACCESS  read-only
     STATUS      current
     DESCRIPTION
         "
         Indicates the count of ErrCode 505 (Command Received Before Restart Response).
         "
     ::= { hwH248StatEntry 54 }

     hwMsH248Error506 OBJECT-TYPE
     SYNTAX      Counter32
     MAX-ACCESS  read-only
     STATUS      current
     DESCRIPTION
         "
         Indicates the count of ErrCode 506 (Number of Transaction Pendings Exceed).
         "
     ::= { hwH248StatEntry 55 }

     hwMsH248Error510 OBJECT-TYPE
     SYNTAX      Counter32
     MAX-ACCESS  read-only
     STATUS      current
     DESCRIPTION
         "
         Indicates the count of ErrCode 510 (Insufficient resources).
         "
     ::= { hwH248StatEntry 56 }

     hwMsH248Error512 OBJECT-TYPE
     SYNTAX      Counter32
     MAX-ACCESS  read-only
     STATUS      current
     DESCRIPTION
         "
         Indicates the count of ErrCode 512 (MG unequipped detect requested Event).
         "
     ::= { hwH248StatEntry 57 }


     hwMsH248Error513 OBJECT-TYPE
     SYNTAX      Counter32
     MAX-ACCESS  read-only
     STATUS      current
     DESCRIPTION
         "
         Indicates the count of ErrCode 513 (MG unequipped generate requested Sig).
         "
     ::= { hwH248StatEntry 58}


     hwMsH248Error514 OBJECT-TYPE
     SYNTAX      Counter32
     MAX-ACCESS  read-only
     STATUS      current
     DESCRIPTION
         "
         Indicates the count of ErrCode 514 (MG cannot send specified announcement).
         "
     ::= { hwH248StatEntry 59 }

     hwMsH248Error515 OBJECT-TYPE
     SYNTAX      Counter32
     MAX-ACCESS  read-only
     STATUS      current
     DESCRIPTION
         "
         Indicates the count of ErrCode 515 (Unsupported Media Type).
         "
     ::= { hwH248StatEntry 60 }

     hwMsH248Error517 OBJECT-TYPE
     SYNTAX      Counter32
     MAX-ACCESS  read-only
     STATUS      current
     DESCRIPTION
         "
         Indicates the count of ErrCode 517 (Unsupported or invalid mode).
         "
     ::= { hwH248StatEntry 61 }

     hwMsH248Error518 OBJECT-TYPE
     SYNTAX      Counter32
     MAX-ACCESS  read-only
     STATUS      current
     DESCRIPTION
         "
         Indicates the count of ErrCode 518 (Event buffer full).
         "
     ::= { hwH248StatEntry 62 }

     hwMsH248Error519 OBJECT-TYPE
     SYNTAX      Counter32
     MAX-ACCESS  read-only
     STATUS      current
     DESCRIPTION
         "
         Indicates the count of ErrCode 519 (Out of space to store digit map).
         "
     ::= { hwH248StatEntry 63 }


     hwMsH248Error520 OBJECT-TYPE
     SYNTAX      Counter32
     MAX-ACCESS  read-only
     STATUS      current
     DESCRIPTION
         "
         Indicates the count of ErrCode 520 (DigitMap Media Gateway not have a map).
         "
     ::= { hwH248StatEntry 64 }


     hwMsH248Error521 OBJECT-TYPE
     SYNTAX      Counter32
     MAX-ACCESS  read-only
     STATUS      current
     DESCRIPTION
         "
         Indicates the count of ErrCode 521 (Termination is Service-Changeing).
         "
     ::= { hwH248StatEntry 65 }

     hwMsH248Error526 OBJECT-TYPE
     SYNTAX      Counter32
     MAX-ACCESS  read-only
     STATUS      current
     DESCRIPTION
         "
         Indicates the count of ErrCode 526 (Insufficient bandwidth).
         "
     ::= { hwH248StatEntry 66 }

     hwMsH248Error529 OBJECT-TYPE
     SYNTAX      Counter32
     MAX-ACCESS  read-only
     STATUS      current
     DESCRIPTION
         "
         Indicates the count of ErrCode 529 (Internal hardware failure).
         "
     ::= { hwH248StatEntry 67 }

     hwMsH248Error530 OBJECT-TYPE
     SYNTAX      Counter32
     MAX-ACCESS  read-only
     STATUS      current
     DESCRIPTION
         "
         Indicates the count of ErrCode 530 (Temporary Network failure).
         "
     ::= { hwH248StatEntry 68 }

     hwMsH248Error531 OBJECT-TYPE
     SYNTAX      Counter32
     MAX-ACCESS  read-only
     STATUS      current
     DESCRIPTION
         "
         Indicates the count of ErrCode 531 (Permanent Network failure).
         "
     ::= { hwH248StatEntry 69 }

     hwMsH248Error532 OBJECT-TYPE
     SYNTAX      Counter32
     MAX-ACCESS  read-only
     STATUS      current
     DESCRIPTION
         "
         Indicates the count of ErrCode 532 (Property Statistic Event Not Exist).
         "
     ::= { hwH248StatEntry 70 }



     hwMsH248Error533 OBJECT-TYPE
     SYNTAX      Counter32
     MAX-ACCESS  read-only
     STATUS      current
     DESCRIPTION
         "
         Indicates the count of ErrCode 533 (Eexceeds maximum transport size).
         "
     ::= { hwH248StatEntry 71 }

     hwMsH248Error534 OBJECT-TYPE
     SYNTAX      Counter32
     MAX-ACCESS  read-only
     STATUS      current
     DESCRIPTION
         "
         Indicates the count of ErrCode 534 (Illegal write of read only).
         "
     ::= { hwH248StatEntry 72 }

     hwMsH248Error540 OBJECT-TYPE
     SYNTAX      Counter32
     MAX-ACCESS  read-only
     STATUS      current
     DESCRIPTION
         "
         Indicates the count of ErrCode 540 (Unexpected initial hook state).
         "
     ::= { hwH248StatEntry 73 }

     hwMsH248Error581 OBJECT-TYPE
     SYNTAX      Counter32
     MAX-ACCESS  read-only
     STATUS      current
     DESCRIPTION
         "
         Indicates the count of ErrCode 581 (Does Not Exist).
         "
     ::= { hwH248StatEntry 74 }


   hwMedGwyStatTable OBJECT-TYPE
     SYNTAX      SEQUENCE OF HwMedGwyStatEntry
     MAX-ACCESS  not-accessible
     STATUS      current
     DESCRIPTION
         "
         A list of mediaGatewayTableEntry objects.
         The index of this table is hwMedGwyStatMgId.
         "
     ::= { hwMs 24 }

   hwMedGwyStatEntry OBJECT-TYPE
     SYNTAX      HwMedGwyStatEntry
     MAX-ACCESS  not-accessible
     STATUS      current
     DESCRIPTION
         "
         A list of mediaGatewayTableEntry objects.
         The index of this entry is hwMedGwyStatMgId."
     INDEX    {
               hwMedGwyStatMgId
              }
     ::= { hwMedGwyStatTable 1 }

   HwMedGwyStatEntry ::=
     SEQUENCE
     {
       hwMedGwyStatMgId Integer32,
       hwMedGwyNumInMessages    Counter32,
       hwMedGwyNumInOctets  Counter32,
       hwMedGwyNumOutMessages   Counter32,
       hwMedGwyNumOutOctets Counter32,
       hwMedGwyNumErrors    Counter32,
       hwMedGwyNumTimerRecovery Counter32,
       hwMedGwyTransportNumLosses   Counter32,
       hwMedGwyTransportNumSwitchover   Counter32,
       hwMedGwyTransportTotalNumAlarms  Counter32,
       hwMedGwyTransportLastEvent   INTEGER,
       hwMedGwyTransportLastEventTime   Counter32,
       hwMedGwyLastStatisticsReset  Counter32
     }

   hwMedGwyStatMgId OBJECT-TYPE
     SYNTAX      Integer32(0..16777215)
     MAX-ACCESS  not-accessible
     STATUS      current
     DESCRIPTION
         "
         Indicates the MG ID.
         "
     ::= { hwMedGwyStatEntry 1 }

   hwMedGwyNumInMessages OBJECT-TYPE
     SYNTAX      Counter32
     MAX-ACCESS  read-only
     STATUS      current
     DESCRIPTION
         "
         Indicates the total count of messages received on the link.
         "
     ::= { hwMedGwyStatEntry 2 }

   hwMedGwyNumInOctets OBJECT-TYPE
     SYNTAX      Counter32
     MAX-ACCESS  read-only
     STATUS      current
     DESCRIPTION
         "
         Indicates the total count of octets received on the link.
         "
     ::= { hwMedGwyStatEntry 3 }

   hwMedGwyNumOutMessages OBJECT-TYPE
     SYNTAX      Counter32
     MAX-ACCESS  read-only
     STATUS      current
     DESCRIPTION
         "
         Indicates the total count of messages sent on the link.
         "
     ::= { hwMedGwyStatEntry 4 }

   hwMedGwyNumOutOctets OBJECT-TYPE
     SYNTAX      Counter32
     MAX-ACCESS  read-only
     STATUS      current
     DESCRIPTION
         "
         Indicates the total count of octets sent on the link.
         "
     ::= { hwMedGwyStatEntry 5 }

   hwMedGwyNumErrors OBJECT-TYPE
     SYNTAX      Counter32
     MAX-ACCESS  read-only
     STATUS      current
     DESCRIPTION
         "
         Indicates the total count of signaling-level errors encountered. Includes, but is not limited to, number of bad messages received, number of failures to sent a message and number of other errors.
         "
     ::= { hwMedGwyStatEntry 6 }

   hwMedGwyNumTimerRecovery OBJECT-TYPE
     SYNTAX      Counter32
     MAX-ACCESS  read-only
     STATUS      current
     DESCRIPTION
         "
         Indicates the count of timer recovery events since the statistics was last reset. This reflects all timers.
         Currently not supported.
         "
     ::= { hwMedGwyStatEntry 7 }

   hwMedGwyTransportNumLosses OBJECT-TYPE
     SYNTAX      Counter32
     MAX-ACCESS  read-only
     STATUS      current
     DESCRIPTION
         "
         Indicates the count of times a transport link was lost (excluding switch-over cases).
         "
     ::= { hwMedGwyStatEntry 8 }

   hwMedGwyTransportNumSwitchover OBJECT-TYPE
     SYNTAX      Counter32
     MAX-ACCESS  read-only
     STATUS      current
     DESCRIPTION
         "
         Indicates the count of times when the signaling was switched over to an alternative link.
         "
     ::= { hwMedGwyStatEntry 9 }

   hwMedGwyTransportTotalNumAlarms OBJECT-TYPE
     SYNTAX      Counter32
     MAX-ACCESS  read-only
     STATUS      current
     DESCRIPTION
         "
         Indicates the total count of all alarms issued for the transport layer.
         "
     ::= { hwMedGwyStatEntry 10 }

   hwMedGwyTransportLastEvent OBJECT-TYPE
     SYNTAX      INTEGER{notApplicable(1),other(2),linkUp(3),linkLoss(4),persistentError(5),linkShutdown(6),switchOver(7)}
     MAX-ACCESS  read-only
     STATUS      current
     DESCRIPTION
         "
         Last event reported by the transport layer.
         Options:
         1. notApplicable(1)    -the last event reported by the transport layer is not applicable
         2. other(2)            -the last event reported by the transport layer is other
         3. linkUp(3)           -the last event reported by the transport layer is link up
         4. linkLoss(4)         -the last event reported by the transport layer is link loss
         5. persistentError(5)  -the last event reported by the transport layer is persistent error
         6. linkShutdown(6)     -the last event reported by the transport layer is link shut down
         7. switchOver(7)       -the last event reported by the transport layer is switch over
         "
     ::= { hwMedGwyStatEntry 11 }

   hwMedGwyTransportLastEventTime OBJECT-TYPE
     SYNTAX      Counter32
     MAX-ACCESS  read-only
     STATUS      current
     DESCRIPTION
         "
         The value of sysUpTime at the time when the event specified by mediaGatewayTransportLastEvent occured. If the last event occured prior to the last re-initialization of the local network management subsystem, then this object contains a zero value.
         "
     ::= { hwMedGwyStatEntry 12 }

   hwMedGwyLastStatisticsReset OBJECT-TYPE
     SYNTAX      Counter32
     MAX-ACCESS  read-only
     STATUS      current
     DESCRIPTION
         "
         The value of sysUpTime at the time when the statistics were reset. If the reset occured prior to the last re-initialization of the local network management subsystem, this object contains a zero value.
         "
     ::= { hwMedGwyStatEntry 13 }

   hwMgcpMgStatTable OBJECT-TYPE
     SYNTAX      SEQUENCE OF HwMgcpMgStatEntry
     MAX-ACCESS  not-accessible
     STATUS      current
     DESCRIPTION
         "
         Indicates the performance statistics of the MGCP module.
         The index of this table is hwMgcpMgStatMgId.
         "
     ::= { hwMs 25 }

   hwMgcpMgStatEntry OBJECT-TYPE
     SYNTAX      HwMgcpMgStatEntry
     MAX-ACCESS  not-accessible
     STATUS      current
     DESCRIPTION
         "
         Indicates the performance statistics of the MGCP module.
         The index of this entry is hwMgcpMgStatMgId."
     INDEX    {
               hwMgcpMgStatMgId
              }
     ::= { hwMgcpMgStatTable 1 }

   HwMgcpMgStatEntry ::=
     SEQUENCE
     {
       hwMgcpMgStatMgId Integer32,
       hwMgcpMgStatSendTotalCmd Counter32,
       hwMgcpMgStatSendTotalRsp Counter32,
       hwMgcpMgStatSendNtfyCmd  Counter32,
       hwMgcpMgStatSendRsipCmd  Counter32,
       hwMgcpMgStatSendDlcsCmd  Counter32,
       hwMgcpMgStatSendErrMsg   Counter32,
       hwMgcpMgStatRecvTotalCmd Counter32,
       hwMgcpMgStatRecvTotalRsp Counter32,
       hwMgcpMgStatRecvEpcfCmd  Counter32,
       hwMgcpMgStatRecvCrcxCmd  Counter32,
       hwMgcpMgStatRecvMdcxCmd  Counter32,
       hwMgcpMgStatRecvDlcxCmd  Counter32,
       hwMgcpMgStatRecvRqntCmd  Counter32,
       hwMgcpMgStatRecvAuepCmd  Counter32,
       hwMgcpMgStatRecvAucxCmd  Counter32,
       hwMgcpMgStatRecvErrRsp   Counter32
     }

   hwMgcpMgStatMgId OBJECT-TYPE
     SYNTAX      Integer32(0..16777215)
     MAX-ACCESS  not-accessible
     STATUS      current
     DESCRIPTION
         "
         Indicates the MG ID.
         "
     ::= { hwMgcpMgStatEntry 1 }

   hwMgcpMgStatSendTotalCmd OBJECT-TYPE
     SYNTAX      Counter32
     MAX-ACCESS  read-only
     STATUS      current
     DESCRIPTION
         "
         Indicates the total count of transmitted commands.
         "
     ::= { hwMgcpMgStatEntry 2 }

   hwMgcpMgStatSendTotalRsp OBJECT-TYPE
     SYNTAX      Counter32
     MAX-ACCESS  read-only
     STATUS      current
     DESCRIPTION
         "
         Indicates the total count of transmitted responses.
         "
     ::= { hwMgcpMgStatEntry 3 }

   hwMgcpMgStatSendNtfyCmd OBJECT-TYPE
     SYNTAX      Counter32
     MAX-ACCESS  read-only
     STATUS      current
     DESCRIPTION
         "
         Indicates the count of NTFY commands.
         "
     ::= { hwMgcpMgStatEntry 4 }

   hwMgcpMgStatSendRsipCmd OBJECT-TYPE
     SYNTAX      Counter32
     MAX-ACCESS  read-only
     STATUS      current
     DESCRIPTION
         "
         Indicates the count of RSIP commands.
         "
     ::= { hwMgcpMgStatEntry 5 }

   hwMgcpMgStatSendDlcsCmd OBJECT-TYPE
     SYNTAX      Counter32
     MAX-ACCESS  read-only
     STATUS      current
     DESCRIPTION
         "
         Indicates the count of DLCX commands.
         "
     ::= { hwMgcpMgStatEntry 6 }

   hwMgcpMgStatSendErrMsg OBJECT-TYPE
     SYNTAX      Counter32
     MAX-ACCESS  read-only
     STATUS      current
     DESCRIPTION
         "
         Indicates the count of transmitted error messages.
         "
     ::= { hwMgcpMgStatEntry 7 }

   hwMgcpMgStatRecvTotalCmd OBJECT-TYPE
     SYNTAX      Counter32
     MAX-ACCESS  read-only
     STATUS      current
     DESCRIPTION
         "
         Indicates the total count of received commands.
         "
     ::= { hwMgcpMgStatEntry 8 }

   hwMgcpMgStatRecvTotalRsp OBJECT-TYPE
     SYNTAX      Counter32
     MAX-ACCESS  read-only
     STATUS      current
     DESCRIPTION
         "
         Indicates the total count of received responses.
         "
     ::= { hwMgcpMgStatEntry 9 }

   hwMgcpMgStatRecvEpcfCmd OBJECT-TYPE
     SYNTAX      Counter32
     MAX-ACCESS  read-only
     STATUS      current
     DESCRIPTION
         "
         Indicates the count of received EPCF commands.
         "
     ::= { hwMgcpMgStatEntry 10 }

   hwMgcpMgStatRecvCrcxCmd OBJECT-TYPE
     SYNTAX      Counter32
     MAX-ACCESS  read-only
     STATUS      current
     DESCRIPTION
         "
         Indicates the count of received CRCX commands.
         "
     ::= { hwMgcpMgStatEntry 11 }

   hwMgcpMgStatRecvMdcxCmd OBJECT-TYPE
     SYNTAX      Counter32
     MAX-ACCESS  read-only
     STATUS      current
     DESCRIPTION
         "
         Indicates the count of received MDCX commands.
         "
     ::= { hwMgcpMgStatEntry 12 }

   hwMgcpMgStatRecvDlcxCmd OBJECT-TYPE
     SYNTAX      Counter32
     MAX-ACCESS  read-only
     STATUS      current
     DESCRIPTION
         "
         Indicates the count of received DLCX commands.
         "
     ::= { hwMgcpMgStatEntry 13 }

   hwMgcpMgStatRecvRqntCmd OBJECT-TYPE
     SYNTAX      Counter32
     MAX-ACCESS  read-only
     STATUS      current
     DESCRIPTION
         "
         Indicates the count of received RQNT commands.
         "
     ::= { hwMgcpMgStatEntry 14 }

   hwMgcpMgStatRecvAuepCmd OBJECT-TYPE
     SYNTAX      Counter32
     MAX-ACCESS  read-only
     STATUS      current
     DESCRIPTION
         "
         Indicates the count of received AUEP commands.
         "
     ::= { hwMgcpMgStatEntry 15 }

   hwMgcpMgStatRecvAucxCmd OBJECT-TYPE
     SYNTAX      Counter32
     MAX-ACCESS  read-only
     STATUS      current
     DESCRIPTION
         "
         Indicates the count of received AUCX commands.
         "
     ::= { hwMgcpMgStatEntry 16 }

   hwMgcpMgStatRecvErrRsp OBJECT-TYPE
     SYNTAX      Counter32
     MAX-ACCESS  read-only
     STATUS      current
     DESCRIPTION
         "
         Indicates the count of received error messages.
         "
     ::= { hwMgcpMgStatEntry 17 }


  hwMsSystemPerformanceTable OBJECT-TYPE
    SYNTAX      SEQUENCE OF HwMsSystemPerformanceEntry
    MAX-ACCESS  not-accessible
    STATUS      current
    DESCRIPTION
        "
        Indicates the performance statistics of the system.
        The index of this table is hwMsSystemPerfResultNo. "
    ::= { hwMs 26 }

  hwMsSystemPerformanceEntry OBJECT-TYPE
    SYNTAX      HwMsSystemPerformanceEntry
    MAX-ACCESS  not-accessible
    STATUS      current
    DESCRIPTION
        "
        Indicates the performance statistics of the system.
        The index of this entry is hwMsSystemPerfResultNo."
    INDEX    {
              hwMsSystemPerfResultNo
             }
    ::= { hwMsSystemPerformanceTable 1 }

  HwMsSystemPerformanceEntry ::=
    SEQUENCE
    {
      hwMsSystemPerfResultNo                                     Integer32,
      hwMsSysPerfAverageCpuRate                                  Integer32,
      hwMsSysPerfMaxCpuRate                                      Integer32,
      hwMsSysPerfStaticMemRate                                   Integer32,
      hwMsSysPerfDynMemRate                                      Integer32,
      hwMsSysPerfResvMemRate                                     Integer32,
      hwMsSysPerfAverageDynMemRate                               Integer32,
      hwMsSysPerfMaxDynMemRate                                   Integer32,
      hwMsSysPerfAverageMsgRate                                  Integer32,
      hwMsSysPerfMaxMsgRate                                      Integer32,
      hwMsSysPerfMaxTemperature                                  Integer32,
      hwMsSysPerfResultTime                                      DateAndTime
    }

  hwMsSystemPerfResultNo OBJECT-TYPE
    SYNTAX      Integer32(0..9)
    MAX-ACCESS  not-accessible
    STATUS      current
    DESCRIPTION
        "
         Indicates the result number of system performance statistics. "
    ::= { hwMsSystemPerformanceEntry 1 }

  hwMsSysPerfAverageCpuRate OBJECT-TYPE
    SYNTAX      Integer32(0..100)
    MAX-ACCESS  read-only
    STATUS      current
    DESCRIPTION
        "
        Indicates the average CPU occupancy rate of the system. "
    ::= { hwMsSystemPerformanceEntry 2 }


  hwMsSysPerfMaxCpuRate OBJECT-TYPE
    SYNTAX      Integer32(0..100)
    MAX-ACCESS  read-only
    STATUS      current
    DESCRIPTION
        "
        Indicates the maximum CPU occupancy rate of the system. "
    ::= { hwMsSystemPerformanceEntry 3 }

  hwMsSysPerfStaticMemRate OBJECT-TYPE
    SYNTAX      Integer32(0..100)
    MAX-ACCESS  read-only
    STATUS      current
    DESCRIPTION
        "
        Indicates the static memory rate of the system. "
    ::= { hwMsSystemPerformanceEntry 4 }

  hwMsSysPerfDynMemRate OBJECT-TYPE
    SYNTAX      Integer32(0..100)
    MAX-ACCESS  read-only
    STATUS      current
    DESCRIPTION
        "
        Indicates the dynamic memory rate of the system. "
    ::= { hwMsSystemPerformanceEntry 5 }

  hwMsSysPerfResvMemRate OBJECT-TYPE
    SYNTAX      Integer32(0..100)
    MAX-ACCESS  read-only
    STATUS      current
    DESCRIPTION
        "
        Indicates the reserved memory rate of the system. "
    ::= { hwMsSystemPerformanceEntry 6 }


  hwMsSysPerfAverageDynMemRate OBJECT-TYPE
    SYNTAX      Integer32(0..100)
    MAX-ACCESS  read-only
    STATUS      current
    DESCRIPTION
        "
        Indicates the average occupancy rate of the dynamic memory of the system. "
    ::= { hwMsSystemPerformanceEntry 7 }

  hwMsSysPerfMaxDynMemRate OBJECT-TYPE
    SYNTAX      Integer32(0..100)
    MAX-ACCESS  read-only
    STATUS      current
    DESCRIPTION
        "
        Indicates the maximum occupancy rate of the dynamic memory of the system. "
    ::= { hwMsSystemPerformanceEntry 8 }

  hwMsSysPerfAverageMsgRate OBJECT-TYPE
    SYNTAX      Integer32(0..100)
    MAX-ACCESS  read-only
    STATUS      current
    DESCRIPTION
        "
        Indicates the average message occupancy rate of the system. "
    ::= { hwMsSystemPerformanceEntry 9 }

  hwMsSysPerfMaxMsgRate OBJECT-TYPE
    SYNTAX      Integer32(0..100)
    MAX-ACCESS  read-only
    STATUS      current
    DESCRIPTION
        "
        Indicates the maximum message occupancy rate of the system. "
    ::= { hwMsSystemPerformanceEntry 10 }

  hwMsSysPerfMaxTemperature OBJECT-TYPE
    SYNTAX      Integer32
    MAX-ACCESS  read-only
    STATUS      current
    DESCRIPTION
        "
        Indicates the maximum temperature of the system (unit: 0.1 °C). "
    ::= { hwMsSystemPerformanceEntry 11 }

   hwMsSysPerfResultTime OBJECT-TYPE
    SYNTAX      DateAndTime
    MAX-ACCESS  read-only
    STATUS      current
    DESCRIPTION
        "
        Indicates the start time of counting results. "
    ::= { hwMsSystemPerformanceEntry 12 }

  hwMsMgOverloadTable OBJECT-TYPE
    SYNTAX      SEQUENCE OF HwMsMgOverloadEntry
    MAX-ACCESS  not-accessible
    STATUS      current
    DESCRIPTION
      "
        Indicates the MG overload performance statistics.
        The indexes of this table are hwMsMgOverloadMGID and hwMsMgOverloadResultNo. "
    ::= { hwMs 27 }

  hwMsMgOverloadEntry OBJECT-TYPE
    SYNTAX      HwMsMgOverloadEntry
    MAX-ACCESS  not-accessible
    STATUS      current
    DESCRIPTION
      "
        Indicates the MG overload performance statistics.
        The indexes of this entry are hwMsMgOverloadMGID and hwMsMgOverloadResultNo."
    INDEX    {
              hwMsMgOverloadMGID,
              hwMsMgOverloadResultNo
             }
    ::= { hwMsMgOverloadTable 1 }

  HwMsMgOverloadEntry ::=
    SEQUENCE
    {
      hwMsMgOverloadMGID                                         Integer32,
      hwMsMgOverloadResultNo                                     Integer32,
      hwMsMgOverloadOverloadMsgNum                           Counter32,
      hwMsMgOverloadCpuOverloadRejectPriorUserCall               Counter32,
      hwMsMgOverloadCpuOverloadRejectNotPriorUserCall            Counter32,
      hwMsMgOverloadDspOverloadRejectPriorUserCall               Counter32,
      hwMsMgOverloadDspOverloadRejectNotPriorUserCall            Counter32,
      hwMsMgOverloadBandwidthOverloadRejectPriorUserCall         Counter32,
      hwMsMgOverloadBandwidthOverloadRejectNotPriorUserCall      Counter32,
      hwMsMgOverloadResultTime                                   DateAndTime,
      hwMsMgOverloadOffHookNum                                   Counter32,
      hwMsMgOverloadADDNum                                       Counter32,
      hwMsMgOverloadH248AlarmEventNum                            Counter32,
      hwMsMgOverloadH248MsgNum                                   Counter32,
      hwMsMgOverloadMgcOverloadOffhookNumOrdinary                Counter32,
      hwMsMgOverloadMgcOverloadOffhookNumPriority                Counter32,
      hwMsMgOverloadMgcOverloadOffhookRejectNumOrdinary          Counter32,
      hwMsMgOverloadMgcOverloadOffhookRejectNumPriority          Counter32,
      hwMsMgOverloadMgcOverloadOffhookEmergencyNumOrdinaryAdmit  Counter32,
      hwMsMgOverloadMgcOverloadOffhookEmergencyNumPriorityAdmit  Counter32,
      hwMsMgOverloadMgcOverloadOffhookEmergencyRejectNumOrdinary Counter32,
      hwMsMgOverloadMgcOverloadOffhookEmergencyRejectNumPriority Counter32,
      hwMsMgOverloadMgcOverloadOffhookNumOrdinaryPass            Counter32,
      hwMsMgOverloadMgcOverloadOffhookNumPriorityPass            Counter32,
      hwMgOverloadReceiveIsdnCall                            Integer32,
      hwMgOverloadPassIsdnCall                                   Integer32,
      hwMgOverloadRejectIsdnCall                             Integer32,
      hwMsMgOverloadIsdnMgcOverloadSetUpNumOrdinary              Integer32,
      hwMsMgOverloadIsdnMgcOverloadSetUpNumPriority              Integer32,
      hwMsMgOverloadIsdnMgcOverloadSetUpNumRejectNumOrdinary     Integer32,
      hwMsMgOverloadIsdnMgcOverloadSetUpNumRejectNumPriority     Integer32,
      hwMsMgOverloadIsdnMgcOverloadSetUpEmergencyNumOrdinaryAdmit  Integer32,
      hwMsMgOverloadIsdnMgcOverloadSetUpEmergencyNumPriorityAdmit  Integer32,
      hwMsMgOverloadIsdnMgcOverloadSetUpEmergencyRejectNumOrdinary Integer32,
      hwMsMgOverloadIsdnMgcOverloadSetUpEmergencyRejectNumPriority Integer32,
      hwMsMgOverloadIsdnMgcOverloadSetUpNumOrdinaryPass            Integer32,
      hwMsMgOverloadIsdnMgcOverloadSetUpNumPriorityPass            Integer32
    }

  hwMsMgOverloadMGID OBJECT-TYPE
    SYNTAX      Integer32(0..16777215)
    MAX-ACCESS  not-accessible
    STATUS      current
    DESCRIPTION
        "
         Indicates the MG ID. "
    ::= { hwMsMgOverloadEntry 1 }

  hwMsMgOverloadResultNo OBJECT-TYPE
    SYNTAX      Integer32(0..9)
    MAX-ACCESS  not-accessible
    STATUS      current
    DESCRIPTION
        "
         Indicates the result number of MG overload statistics. "
    ::= { hwMsMgOverloadEntry 2 }

  hwMsMgOverloadOverloadMsgNum OBJECT-TYPE
    SYNTAX      Counter32
    MAX-ACCESS  read-only
    STATUS      current
    DESCRIPTION
        "
        Indicates the count of overload messages transmitted during the MG overload. "
    ::= { hwMsMgOverloadEntry 3 }

  hwMsMgOverloadCpuOverloadRejectPriorUserCall OBJECT-TYPE
    SYNTAX      Counter32
    MAX-ACCESS  read-only
    STATUS      current
    DESCRIPTION
        "
        Indicates the count of priority user calls rejected during the CPU overload. "
    ::= { hwMsMgOverloadEntry 4 }

  hwMsMgOverloadCpuOverloadRejectNotPriorUserCall OBJECT-TYPE
    SYNTAX      Counter32
    MAX-ACCESS  read-only
    STATUS      current
    DESCRIPTION
        "
        Indicates the count of non-priority user calls rejected during the CPU overload. "
    ::= { hwMsMgOverloadEntry 5 }

  hwMsMgOverloadDspOverloadRejectPriorUserCall OBJECT-TYPE
    SYNTAX      Counter32
    MAX-ACCESS  read-only
    STATUS      current
    DESCRIPTION
        "
        Indicates the count of priority user calls rejected during the DSP overload. "
    ::= { hwMsMgOverloadEntry 6 }

  hwMsMgOverloadDspOverloadRejectNotPriorUserCall OBJECT-TYPE
    SYNTAX      Counter32
    MAX-ACCESS  read-only
    STATUS      current
    DESCRIPTION
        "
        Indicates the count of non-priority user calls rejected during the DSP overload. "
    ::= { hwMsMgOverloadEntry 7 }

  hwMsMgOverloadBandwidthOverloadRejectPriorUserCall OBJECT-TYPE
    SYNTAX      Counter32
    MAX-ACCESS  read-only
    STATUS      current
    DESCRIPTION
        "
        Indicates the count of priority user calls rejected when the upstream bandwidth is restricted. "
    ::= { hwMsMgOverloadEntry 8 }

  hwMsMgOverloadBandwidthOverloadRejectNotPriorUserCall OBJECT-TYPE
    SYNTAX      Counter32
    MAX-ACCESS  read-only
    STATUS      current
    DESCRIPTION
        "
        Indicates the count of non-priority user calls rejected when the upstream bandwidth is restricted. "
    ::= { hwMsMgOverloadEntry 9 }

  hwMsMgOverloadResultTime OBJECT-TYPE
    SYNTAX      DateAndTime
    MAX-ACCESS  read-only
    STATUS      current
    DESCRIPTION
        "
        Indicates the start time of counting results. "
    ::= { hwMsMgOverloadEntry 10 }
  hwMsMgOverloadOffHookNum OBJECT-TYPE
    SYNTAX      Counter32
    MAX-ACCESS  read-only
    STATUS      current
    DESCRIPTION
        "
        Indicates the count of user pickups. "
    ::= { hwMsMgOverloadEntry 11 }

  hwMsMgOverloadADDNum OBJECT-TYPE
    SYNTAX      Counter32
    MAX-ACCESS  read-only
    STATUS      current
    DESCRIPTION
        "
        Indicates the count of received ADD commands. "
    ::= { hwMsMgOverloadEntry 12 }

  hwMsMgOverloadH248AlarmEventNum OBJECT-TYPE
    SYNTAX      Counter32
    MAX-ACCESS  read-only
    STATUS      current
    DESCRIPTION
        "
        Indicates the count of sent overload events. "
    ::= { hwMsMgOverloadEntry 13 }

  hwMsMgOverloadH248MsgNum OBJECT-TYPE
    SYNTAX      Counter32
    MAX-ACCESS  read-only
    STATUS      current
    DESCRIPTION
        "
        Indicates the count of received H.248 messages. "
    ::= { hwMsMgOverloadEntry 14 }

  hwMsMgOverloadMgcOverloadOffhookNumOrdinary OBJECT-TYPE
    SYNTAX      Counter32
    MAX-ACCESS  read-only
    STATUS      current
    DESCRIPTION
        "
        Indicates the count of ordinary user pickups. "
    ::= { hwMsMgOverloadEntry 15 }

  hwMsMgOverloadMgcOverloadOffhookNumPriority OBJECT-TYPE
    SYNTAX      Counter32
    MAX-ACCESS  read-only
    STATUS      current
    DESCRIPTION
        "
        Indicates the count of high priority user pickups. "
    ::= { hwMsMgOverloadEntry 16 }

  hwMsMgOverloadMgcOverloadOffhookRejectNumOrdinary OBJECT-TYPE
    SYNTAX      Counter32
    MAX-ACCESS  read-only
    STATUS      current
    DESCRIPTION
        "
        Indicates the count of ordinary user calls rejected by overload leaky bucket. "
    ::= { hwMsMgOverloadEntry 17 }

  hwMsMgOverloadMgcOverloadOffhookRejectNumPriority OBJECT-TYPE
    SYNTAX      Counter32
    MAX-ACCESS  read-only
    STATUS      current
    DESCRIPTION
        "
        Indicates the count of high priority user calls rejected by overload leaky bucket. "
    ::= { hwMsMgOverloadEntry 18 }

  hwMsMgOverloadMgcOverloadOffhookEmergencyNumOrdinaryAdmit OBJECT-TYPE
    SYNTAX      Counter32
    MAX-ACCESS  read-only
    STATUS      current
    DESCRIPTION
        "
        Indicates the count of ordinary user emergency calls. "
    ::= { hwMsMgOverloadEntry 19 }

  hwMsMgOverloadMgcOverloadOffhookEmergencyNumPriorityAdmit OBJECT-TYPE
    SYNTAX      Counter32
    MAX-ACCESS  read-only
    STATUS      current
    DESCRIPTION
        "
        Indicates the count of high priority user emergency calls. "
    ::= { hwMsMgOverloadEntry 20 }

  hwMsMgOverloadMgcOverloadOffhookEmergencyRejectNumOrdinary OBJECT-TYPE
    SYNTAX      Counter32
    MAX-ACCESS  read-only
    STATUS      current
    DESCRIPTION
        "
        Indicates the count of ordinary user emergency calls rejected for exceeding the emergency threshold.
        "
    ::= { hwMsMgOverloadEntry 21 }

  hwMsMgOverloadMgcOverloadOffhookEmergencyRejectNumPriority OBJECT-TYPE
    SYNTAX      Counter32
    MAX-ACCESS  read-only
    STATUS      current
    DESCRIPTION

        "
        Indicates the count of high priority user emergency calls rejected for exceeding the emergency threshold.
        "
    ::= { hwMsMgOverloadEntry 22 }

  hwMsMgOverloadMgcOverloadOffhookNumOrdinaryPass OBJECT-TYPE
    SYNTAX      Counter32
    MAX-ACCESS  read-only
    STATUS      current
    DESCRIPTION

        "
        Indicates the count of ordinary user calls that are not limited.
        "
    ::= { hwMsMgOverloadEntry 23 }

  hwMsMgOverloadMgcOverloadOffhookNumPriorityPass OBJECT-TYPE
    SYNTAX      Counter32
    MAX-ACCESS  read-only
    STATUS      current
    DESCRIPTION

        "
        Indicates the count of high priority user calls thar are not limited.
        "
    ::= { hwMsMgOverloadEntry 24 }

  hwMgOverloadReceiveIsdnCall OBJECT-TYPE
    SYNTAX      Integer32
    MAX-ACCESS  read-only
    STATUS      current
    DESCRIPTION
        "
        Indicates the count of received ISDN calls. "
    ::= { hwMsMgOverloadEntry 25 }
  hwMgOverloadPassIsdnCall  OBJECT-TYPE
    SYNTAX      Integer32
    MAX-ACCESS  read-only
    STATUS      current
    DESCRIPTION
        "
        Indicates the count of accepted ISDN calls. "
    ::= { hwMsMgOverloadEntry 26 }
  hwMgOverloadRejectIsdnCall OBJECT-TYPE
    SYNTAX      Integer32
    MAX-ACCESS  read-only
    STATUS      current
    DESCRIPTION
        "
        Indicates the count of rejected ISDN calls. "
    ::= { hwMsMgOverloadEntry 27 }

  hwMsMgOverloadIsdnMgcOverloadSetUpNumOrdinary OBJECT-TYPE
    SYNTAX      Integer32
    MAX-ACCESS  read-only
    STATUS      current
    DESCRIPTION

         "
         Indicates the count of ordinary user calls received by ISDN NR leaky bucket.
         "
    ::= { hwMsMgOverloadEntry 28 }

  hwMsMgOverloadIsdnMgcOverloadSetUpNumPriority OBJECT-TYPE
    SYNTAX      Integer32
    MAX-ACCESS  read-only
    STATUS      current
    DESCRIPTION

         "
         Indicates the count of high priority user calls received by ISDN NR leaky bucket.
         "
    ::= { hwMsMgOverloadEntry 29 }

  hwMsMgOverloadIsdnMgcOverloadSetUpNumRejectNumOrdinary OBJECT-TYPE
    SYNTAX      Integer32
    MAX-ACCESS  read-only
    STATUS      current
    DESCRIPTION

         "
         Indicates the count of ordinary user calls rejected by ISDN NR leaky bucket.
         "
    ::= { hwMsMgOverloadEntry 30 }

  hwMsMgOverloadIsdnMgcOverloadSetUpNumRejectNumPriority OBJECT-TYPE
    SYNTAX      Integer32
    MAX-ACCESS  read-only
    STATUS      current
    DESCRIPTION

         "
         Indicates the count of high priority user calls rejected by ISDN NR leaky bucket.
         "
    ::= { hwMsMgOverloadEntry 31 }

  hwMsMgOverloadIsdnMgcOverloadSetUpEmergencyNumOrdinaryAdmit OBJECT-TYPE
    SYNTAX      Integer32
    MAX-ACCESS  read-only
    STATUS      current
    DESCRIPTION

         "
         Indicates the count of ordinary user emergency calls accepted by ISDN NR leaky bucket.
         "
    ::= { hwMsMgOverloadEntry 32 }

  hwMsMgOverloadIsdnMgcOverloadSetUpEmergencyNumPriorityAdmit OBJECT-TYPE
    SYNTAX      Integer32
    MAX-ACCESS  read-only
    STATUS      current
    DESCRIPTION

         "
         Indicates the count of high priority user emergency calls accepted by ISDN NR leaky bucket.
         "
    ::= { hwMsMgOverloadEntry 33 }

  hwMsMgOverloadIsdnMgcOverloadSetUpEmergencyRejectNumOrdinary OBJECT-TYPE
    SYNTAX      Integer32
    MAX-ACCESS  read-only
    STATUS      current
    DESCRIPTION

         "
         Indicates the count of ordinary user emergency calls rejected by ISDN leaky bucket.
         "
    ::= { hwMsMgOverloadEntry 34 }

  hwMsMgOverloadIsdnMgcOverloadSetUpEmergencyRejectNumPriority OBJECT-TYPE
    SYNTAX      Integer32
    MAX-ACCESS  read-only
    STATUS      current
    DESCRIPTION

         "
         Indicates the count of high priority user emergency calls rejected by ISDN leaky bucket.
         "
    ::= { hwMsMgOverloadEntry 35 }

  hwMsMgOverloadIsdnMgcOverloadSetUpNumOrdinaryPass OBJECT-TYPE
    SYNTAX      Integer32
    MAX-ACCESS  read-only
    STATUS      current
    DESCRIPTION

         "
         Indicates the count of ordinary user calls accepted by ISDN leaky bucket (including emergency calls).
         "
    ::= { hwMsMgOverloadEntry 36 }

  hwMsMgOverloadIsdnMgcOverloadSetUpNumPriorityPass OBJECT-TYPE
    SYNTAX      Integer32
    MAX-ACCESS  read-only
    STATUS      current
    DESCRIPTION

         "
         Indicates the count of high priority user calls accepted by ISDN leaky bucket (including emergency calls).
         "
    ::= { hwMsMgOverloadEntry 37 }

  hwMsE1Layer1StatTable OBJECT-TYPE
    SYNTAX      SEQUENCE OF HwMsE1Layer1StatEntry
    MAX-ACCESS  not-accessible
    STATUS      current
    DESCRIPTION
      "
        Indicates the information statistics of the physical layer of the E1 port.
        The indexes of this table are hwMsE1Layer1Index and hwMsE1Layer1ResultNo. "
    ::= { hwMs 28 }

  hwMsE1Layer1StatEntry OBJECT-TYPE
    SYNTAX      HwMsE1Layer1StatEntry
    MAX-ACCESS  not-accessible
    STATUS      current
    DESCRIPTION
      "
        Indicates the information statistics of the physical layer of the E1 port.
        The indexes of this entry are hwMsE1Layer1Index and hwMsE1Layer1ResultNo."
    INDEX    {
              hwMsE1Layer1Index,
              hwMsE1Layer1ResultNo
             }
    ::= { hwMsE1Layer1StatTable 1 }

  HwMsE1Layer1StatEntry ::=
    SEQUENCE
    {
      hwMsE1Layer1Index                        Integer32,
      hwMsE1Layer1ResultNo                     Integer32,
      hwMsE1Layer1ErroredSeconds               Counter32,
      hwMsE1Layer1SeverelyErroredSeconds       Counter32,
      hwMsE1Layer1DegradedMinutes              Counter32,
      hwMsE1Layer1FarEndErroredSeconds         Counter32,
      hwMsE1Layer1FarEndSeverelyErroredSeconds Counter32
    }

  hwMsE1Layer1Index OBJECT-TYPE
    SYNTAX      Integer32
    MAX-ACCESS  not-accessible
    STATUS      current
    DESCRIPTION
        "
        Indicates the shelf/slot/port index of the E1 port. "
    ::= { hwMsE1Layer1StatEntry 1 }

  hwMsE1Layer1ResultNo OBJECT-TYPE
    SYNTAX      Integer32(0..9)
    MAX-ACCESS  not-accessible
    STATUS      current
    DESCRIPTION
        "
         Indicates the statistic result number of Layer 1 of the E1 port. "
    ::= { hwMsE1Layer1StatEntry 2 }

  hwMsE1Layer1ErroredSeconds OBJECT-TYPE
    SYNTAX      Counter32
    MAX-ACCESS  read-only
    STATUS      current
    DESCRIPTION
        "
        ERRORED SECONDS
        Indicates the count of errored seconds (when CRC is enabled, and if the CRC error is detected within one second, this second is called an errored second; when CRC is disabled, and if polarity reversal is detected within one second, this second is called an errored second). "
    ::= { hwMsE1Layer1StatEntry 3 }

  hwMsE1Layer1SeverelyErroredSeconds OBJECT-TYPE
    SYNTAX      Counter32
    MAX-ACCESS  read-only
    STATUS      current
    DESCRIPTION
        "
        SEVERELY ERRORED SECONDS
        Indicates the count of severely errored seconds (when CRC is enabled, and if 832 or more CRC errors are detected or the LOS/LOF/AIS alarm occurs within one second, this second is called a severely errored second; when CRC is disabled, and if 2048 or more polarity reversals are detected within one second, this second is called a severely errored second). "
    ::= { hwMsE1Layer1StatEntry 4 }

  hwMsE1Layer1DegradedMinutes OBJECT-TYPE
    SYNTAX      Counter32
    MAX-ACCESS  read-only
    STATUS      current
    DESCRIPTION
        "
        DEGRADED MINUTES
        Indicates the count of degraded minutes (within one minute, if 1 <= the count of CRC errors <= 240, this minute is called a degraded minute). "
    ::= { hwMsE1Layer1StatEntry 5 }

  hwMsE1Layer1FarEndErroredSeconds OBJECT-TYPE
    SYNTAX      Counter32
    MAX-ACCESS  read-only
    STATUS      current
    DESCRIPTION
        "
        FAR-END ERRORED SECONDS
        Indicates the count of far end errored seconds (if the far end alarm is detected within one second, this second is called a far end errored second). "
    ::= { hwMsE1Layer1StatEntry 6 }

  hwMsE1Layer1FarEndSeverelyErroredSeconds OBJECT-TYPE
    SYNTAX      Counter32
    MAX-ACCESS  read-only
    STATUS      current
    DESCRIPTION
        "
        FAR-END SEVERELY ERRORED SECONDS
        Indicates the count of far end severely errored seconds (if 832 or more far end alarms are detected within one second, this second is called a far end severely errored second). "
    ::= { hwMsE1Layer1StatEntry 7 }


  hwMsOverloadAverageTable OBJECT-TYPE
    SYNTAX      SEQUENCE OF HwMsOverloadAverageEntry
    MAX-ACCESS  not-accessible
    STATUS      current
    DESCRIPTION
        "
        Indicates the statistics of MG overload control.
        The index of this table is hwMsOverloadAverageResultNo.
        "
    ::= { hwMs 29 }

  hwMsOverloadAverageEntry OBJECT-TYPE
    SYNTAX      HwMsOverloadAverageEntry
    MAX-ACCESS  not-accessible
    STATUS      current
    DESCRIPTION
        "
        Indicates the statistics of MG overload control.
        The index of this entry is hwMsOverloadAverageResultNo."
    INDEX    {
              hwMsOverloadAverageResultNo
             }
    ::= { hwMsOverloadAverageTable 1 }

  HwMsOverloadAverageEntry ::=
    SEQUENCE
    {
      hwMsOverloadAverageResultNo                                Integer32,
      hwMsOverloadAveragePersentage                              Integer32,
      hwMsOverloadAverageTraffic                                 Integer32,
      hwMsOverloadAverageDSPUsed                                 Integer32,
      hwMsOverloadAverageResultTime                              DateAndTime
    }

  hwMsOverloadAverageResultNo OBJECT-TYPE
    SYNTAX      Integer32(0..9)
    MAX-ACCESS  not-accessible
    STATUS      current
    DESCRIPTION

         "
         Indicates the serial number of statistics of MG overload control.
         "
    ::= { hwMsOverloadAverageEntry 1 }

  hwMsOverloadAveragePersentage OBJECT-TYPE
    SYNTAX      Integer32(0..100)
    MAX-ACCESS  read-only
    STATUS      current
    DESCRIPTION

        "
        Indicates the percent of overload.
        "
    ::= { hwMsOverloadAverageEntry 2 }

  hwMsOverloadAverageTraffic OBJECT-TYPE
    SYNTAX      Integer32
    MAX-ACCESS  read-only
    STATUS      current
    DESCRIPTION

        "
        Indicates the average number of calls.
        "
    ::= { hwMsOverloadAverageEntry 3 }

  hwMsOverloadAverageDSPUsed OBJECT-TYPE
    SYNTAX      Integer32
    MAX-ACCESS  read-only
    STATUS      current
    DESCRIPTION

        "
        Indicates the average number of DSP channels in use.
        "
    ::= { hwMsOverloadAverageEntry 4 }

  hwMsOverloadAverageResultTime OBJECT-TYPE
    SYNTAX      DateAndTime
    MAX-ACCESS  read-only
    STATUS      current
    DESCRIPTION

        "Indicates the start time of statistics.
        "
    ::= { hwMsOverloadAverageEntry 5 }

  hwMsBraL1ErrTable OBJECT-TYPE
    SYNTAX      SEQUENCE OF HwMsBraL1ErrEntry
    MAX-ACCESS  not-accessible
    STATUS      current
    DESCRIPTION
        "
        Indicates the statistics of BRA CRC error in the case of the BRA port is activated.
        The indexes of this table are hwMsBraL1CRCErrIndex and hwMsBraL1CRCErrResultNo.
        "
    ::= { hwMs 30 }
  hwMsBraL1ErrEntry OBJECT-TYPE
    SYNTAX      HwMsBraL1ErrEntry
    MAX-ACCESS  not-accessible
    STATUS      current
    DESCRIPTION
        "
        Indicates the statistics of BRA CRC error in the case of the BRA port is activated.
        The indexes of this entry are hwMsBraL1CRCErrIndex and hwMsBraL1CRCErrResultNo."
    INDEX    {
              hwMsBraL1CRCErrIndex,
              hwMsBraL1CRCErrResultNo
             }
    ::= { hwMsBraL1ErrTable 1 }
  HwMsBraL1ErrEntry  ::=
    SEQUENCE
    {
      hwMsBraL1CRCErrIndex                                       Integer32,
      hwMsBraL1CRCErrResultNo                                    Integer32,
      hwMsBraL1CRCErrESU                                         Counter32,
      hwMsBraL1CRCErrSESU                                        Counter32,
      hwMsBraL1CRCErrDMU                                         Counter32,
      hwMsBraL1CRCErrESD                                         Counter32,
      hwMsBraL1CRCErrSESD                                        Counter32,
      hwMsBraL1CRCErrDMD                                         Counter32,
      hwMsBraL1CRCErrUnavailableTimeU                Counter32,
      hwMsBraL1CRCErrUnavailableTimeD                Counter32,
      hwMsBraL1CRCErrSAIBitChangTimes                Counter32,
      hwMsBraL1CRCErrACTBitChangTimes                Counter32,
      hwMsBraCRC4ErroredLastErroredTime                          DateAndTime
    }
  hwMsBraL1CRCErrIndex OBJECT-TYPE
    SYNTAX      Integer32
    MAX-ACCESS  not-accessible
    STATUS      current
    DESCRIPTION

        "
        Indicates the index of the port (FRAME<<24|SLOT<<16|PORT).
        "
    ::= { hwMsBraL1ErrEntry 1 }

  hwMsBraL1CRCErrResultNo OBJECT-TYPE
    SYNTAX      Integer32
    MAX-ACCESS  not-accessible
    STATUS      current
    DESCRIPTION

        "
        Indicates the result number of statistics, 0: current value; 1: the value of the last quarter.
        "
    ::= { hwMsBraL1ErrEntry 2 }

  hwMsBraL1CRCErrESU OBJECT-TYPE
    SYNTAX      Counter32
    MAX-ACCESS  read-only
    STATUS      current
    DESCRIPTION

        "
        Indicates the count of uplink errored seconds.
        "
    ::= { hwMsBraL1ErrEntry 3 }

  hwMsBraL1CRCErrSESU OBJECT-TYPE
    SYNTAX      Counter32
    MAX-ACCESS  read-only
    STATUS      current
    DESCRIPTION

        "
        Indicates the count of uplink severely errored seconds.
        "
    ::= { hwMsBraL1ErrEntry 4 }

  hwMsBraL1CRCErrDMU OBJECT-TYPE
    SYNTAX      Counter32
    MAX-ACCESS  read-only
    STATUS      current
    DESCRIPTION

        "
        Indicates the count of uplink degraded minutes.
        "
    ::= { hwMsBraL1ErrEntry 5 }

  hwMsBraL1CRCErrESD OBJECT-TYPE
    SYNTAX      Counter32
    MAX-ACCESS  read-only
    STATUS      current
    DESCRIPTION

        "
        Indicates the count of downlink errored seconds.
        "
    ::= { hwMsBraL1ErrEntry 6 }

  hwMsBraL1CRCErrSESD OBJECT-TYPE
    SYNTAX      Counter32
    MAX-ACCESS  read-only
    STATUS      current
    DESCRIPTION

        "
        Indicates the count of severely errored seconds.
        "
    ::= { hwMsBraL1ErrEntry 7 }

  hwMsBraL1CRCErrDMD OBJECT-TYPE
    SYNTAX      Counter32
    MAX-ACCESS  read-only
    STATUS      current
    DESCRIPTION

        "
        Indicates the count of downlink degraded minutes.
        "
    ::= { hwMsBraL1ErrEntry 8 }

  hwMsBraL1CRCErrUnavailableTimeU OBJECT-TYPE
    SYNTAX      Counter32
    MAX-ACCESS  read-only
    STATUS      current
    DESCRIPTION
        "
        Indicates the length of uplink unavailable time.
        "
    ::= { hwMsBraL1ErrEntry 9 }

  hwMsBraL1CRCErrUnavailableTimeD OBJECT-TYPE
    SYNTAX      Counter32
    MAX-ACCESS  read-only
    STATUS      current
    DESCRIPTION

        "
        Indicates the length of downlink unavailable time.
        "
    ::= { hwMsBraL1ErrEntry 10 }

  hwMsBraL1CRCErrSAIBitChangTimes OBJECT-TYPE
    SYNTAX      Counter32
    MAX-ACCESS  read-only
    STATUS      current
    DESCRIPTION
    "
        Indicates the count of SAI bit change.
        "
    ::= { hwMsBraL1ErrEntry 11 }

  hwMsBraL1CRCErrACTBitChangTimes OBJECT-TYPE
    SYNTAX      Counter32
    MAX-ACCESS  read-only
    STATUS      current
    DESCRIPTION
    "
        Indicates the count of ACT bit change.
        "
    ::= { hwMsBraL1ErrEntry 12 }

  hwMsBraCRC4ErroredLastErroredTime OBJECT-TYPE
    SYNTAX      DateAndTime
    MAX-ACCESS  read-only
    STATUS      current
    DESCRIPTION
        "
        Indicates the time for generating the last error code.
        "
    ::= { hwMsBraL1ErrEntry 13 }


  hwMsISDNL2ErrTable OBJECT-TYPE
    SYNTAX      SEQUENCE OF HwMsISDNL2ErrEntry
    MAX-ACCESS  not-accessible
    STATUS      current
    DESCRIPTION
        "
        Indicates the statistics of BRA/PRA port L2 error.
        The indexes of this table are hwMsISDNL2ErrPortIndex and hwMsISDNL2ErrResultNo.
        "
    ::= { hwMs 31 }
  hwMsISDNL2ErrEntry OBJECT-TYPE
    SYNTAX      HwMsISDNL2ErrEntry
    MAX-ACCESS  not-accessible
    STATUS      current
    DESCRIPTION
        "
        Indicates the statistics of BRA/PRA port L2 error.
        The indexes of this entry are hwMsISDNL2ErrPortIndex and hwMsISDNL2ErrResultNo."
    INDEX    {
              hwMsISDNL2ErrPortIndex,
              hwMsISDNL2ErrResultNo
             }
    ::= { hwMsISDNL2ErrTable 1 }
  HwMsISDNL2ErrEntry ::=
    SEQUENCE
    {
      hwMsISDNL2ErrPortIndex                                   Integer32,
      hwMsISDNL2ErrResultNo                                    Integer32,
      hwMsISDNL2ErrUnexpectRespond                             Counter32,
      hwMsISDNL2ErrMFRebuiltLinkRequest                        Counter32,
      hwMsISDNL2ErrN2000OutTime                                Counter32,
      hwMsISDNL2ErrQ921AddrDomainErr                           Counter32,
      hwMsISDNL2ErrMDLERRJ2O                                   Counter32,
      hwMsISDNL2ErrFrameSNErr                                  Counter32,
      hwMsISDNL2ErrBufferOverFlowUp                            Counter32,
      hwMsISDNL2ErrBufferOverFlowDown                          Counter32
    }
  hwMsISDNL2ErrPortIndex OBJECT-TYPE
    SYNTAX      Integer32
    MAX-ACCESS  not-accessible
    STATUS      current
    DESCRIPTION
        "
        Indicates the index of the port (FRAME<<24|SLOT<<16|PORT).
        "
    ::= { hwMsISDNL2ErrEntry 1 }

  hwMsISDNL2ErrResultNo OBJECT-TYPE
    SYNTAX      Integer32
    MAX-ACCESS  not-accessible
    STATUS      current
    DESCRIPTION
        "
        Indicates the result number of statistics, 0: current value; 1: the value of the last quarter.
        "
    ::= { hwMsISDNL2ErrEntry 2 }
  hwMsISDNL2ErrUnexpectRespond OBJECT-TYPE
    SYNTAX      Counter32
    MAX-ACCESS  read-only
    STATUS      current
    DESCRIPTION
        "
        Indicates the count of unexpected responses.
        "
    ::= { hwMsISDNL2ErrEntry 3 }
  hwMsISDNL2ErrMFRebuiltLinkRequest OBJECT-TYPE
    SYNTAX      Counter32
    MAX-ACCESS  read-only
    STATUS      current
    DESCRIPTION
         "
         Indicates the count of received link rebuild requests.
         "
    ::= { hwMsISDNL2ErrEntry 4 }
  hwMsISDNL2ErrN2000OutTime OBJECT-TYPE
    SYNTAX      Counter32
    MAX-ACCESS  read-only
    STATUS      current
    DESCRIPTION
        "
        Indicates the count of timeouts of the N200 timer.
        "
    ::= { hwMsISDNL2ErrEntry 5 }
  hwMsISDNL2ErrQ921AddrDomainErr OBJECT-TYPE
    SYNTAX      Counter32
    MAX-ACCESS  read-only
    STATUS      current
    DESCRIPTION
        "
        Indicates the count of Q.921 address domain errors.
        "
    ::= { hwMsISDNL2ErrEntry 6 }
  hwMsISDNL2ErrMDLERRJ2O OBJECT-TYPE
    SYNTAX      Counter32
    MAX-ACCESS  read-only
    STATUS      current
    DESCRIPTION
        "
        Indicates the count of Q.921 MDL error J-O.
        "
    ::= { hwMsISDNL2ErrEntry 7 }
  hwMsISDNL2ErrFrameSNErr OBJECT-TYPE
    SYNTAX      Counter32
    MAX-ACCESS  read-only
    STATUS      current
    DESCRIPTION
        "
        Indicates the count of frame serial number errors.
        "
    ::= { hwMsISDNL2ErrEntry 8 }
  hwMsISDNL2ErrBufferOverFlowUp OBJECT-TYPE
    SYNTAX      Counter32
    MAX-ACCESS  read-only
    STATUS      current
    DESCRIPTION
        "
        Indicates the count of up direction buffer overflow.
        "
    ::= { hwMsISDNL2ErrEntry 9 }
  hwMsISDNL2ErrBufferOverFlowDown OBJECT-TYPE
    SYNTAX      Counter32
    MAX-ACCESS  read-only
    STATUS      current
    DESCRIPTION
        "
        Indicates the count of down direction buffer overflow.BRA doesn't support it now.
        "
    ::= { hwMsISDNL2ErrEntry 10 }


  hwMsPraL1CRCErrTable OBJECT-TYPE
    SYNTAX      SEQUENCE OF HwMsPraL1CRCErrEntry
    MAX-ACCESS  not-accessible
    STATUS      current
    DESCRIPTION
        "
        Indicates the statistics of the PRA CRC error.
        The indexes of this table are hwMsPraMsgTableCRC4ErroredPortIndex and hwMsPraMsgTableCRC4ErroredResultNo. "
    ::= { hwMs 32 }
  hwMsPraL1CRCErrEntry OBJECT-TYPE
    SYNTAX      HwMsPraL1CRCErrEntry
    MAX-ACCESS  not-accessible
    STATUS      current
    DESCRIPTION
        "
        Indicates the statistics of the PRA CRC error.
        The indexes of this entry are hwMsPraMsgTableCRC4ErroredPortIndex and hwMsPraMsgTableCRC4ErroredResultNo."
    INDEX    {
              hwMsPraMsgTableCRC4ErroredPortIndex,
              hwMsPraMsgTableCRC4ErroredResultNo
             }
    ::= { hwMsPraL1CRCErrTable 1 }
  HwMsPraL1CRCErrEntry ::=
    SEQUENCE
    {
      hwMsPraMsgTableCRC4ErroredPortIndex                                   Integer32,
      hwMsPraMsgTableCRC4ErroredResultNo                                    Integer32,
      hwMsPraMsgTableCRC4ErroredDownErroredSeconds                          Counter32,
      hwMsPraMsgTableCRC4ErroredDownSeverelyErroredSeconds                  Counter32,
      hwMsPraMsgTableCRC4ErroredDownDegradedMinutes                         Counter32,
      hwMsPraMsgTableCRC4ErroredUpErroredSeconds                            Counter32,
      hwMsPraMsgTableCRC4ErroredUpSeverelyErroredSeconds                    Counter32,
      hwMsPraMsgTableCRC4ErroredUpDegradedMinutes                           Counter32,
      hwMsPraMsgTableCRC4ErroredUpUnavailableTime                           Counter32,
      hwMsPraMsgTableCRC4ErroredDownUnavailableTime                         Counter32,
      hwMsPraCRC4ErroredLastErroredTime                                     DateAndTime,
      hwMsPraMsgTableSection2CRC4ErroredDownErroredSeconds                  Counter32,
      hwMsPraMsgTableSection2CRC4ErroredDownSeverelyErroredSeconds          Counter32,
      hwMsPraMsgTableSection2CRC4ErroredDownDegradedMinutes                 Counter32,
      hwMsPraMsgTableSection2CRC4ErroredUpErroredSeconds                    Counter32,
      hwMsPraMsgTableSection2CRC4ErroredUpSeverelyErroredSeconds            Counter32,
      hwMsPraMsgTableSection2CRC4ErroredUpDegradedMinutes                   Counter32,
      hwMsPraMsgTableSection2CRC4ErroredUpUnavailableTime                   Counter32,
      hwMsPraMsgTableSection2CRC4ErroredDownUnavailableTime                 Counter32
    }
  hwMsPraMsgTableCRC4ErroredPortIndex OBJECT-TYPE
    SYNTAX      Integer32
    MAX-ACCESS  not-accessible
    STATUS      current
    DESCRIPTION
        "
        Indicates the index of the port.
        "
    ::= { hwMsPraL1CRCErrEntry 1 }

  hwMsPraMsgTableCRC4ErroredResultNo OBJECT-TYPE
    SYNTAX      Integer32
    MAX-ACCESS  not-accessible
    STATUS      current
    DESCRIPTION
        "
        Indicates the result number of statistics, 0: current value; 1: the value of the last quarter.
        "
    ::= { hwMsPraL1CRCErrEntry 2 }

  hwMsPraMsgTableCRC4ErroredDownErroredSeconds OBJECT-TYPE
    SYNTAX      Counter32
    MAX-ACCESS  read-only
    STATUS      current
    DESCRIPTION
        "
        Indicates the count of downlink errored seconds.
        "
    ::= { hwMsPraL1CRCErrEntry 3 }

  hwMsPraMsgTableCRC4ErroredDownSeverelyErroredSeconds OBJECT-TYPE
    SYNTAX      Counter32
    MAX-ACCESS  read-only
    STATUS      current
    DESCRIPTION
        "
        Indicates the count of downlink consecutive severely errored seconds.
        "
    ::= { hwMsPraL1CRCErrEntry 4 }

  hwMsPraMsgTableCRC4ErroredDownDegradedMinutes OBJECT-TYPE
    SYNTAX      Counter32
    MAX-ACCESS  read-only
    STATUS      current
    DESCRIPTION
        "
        Indicates the count of downlink degraded minutes.
        "
    ::= { hwMsPraL1CRCErrEntry 5 }

  hwMsPraMsgTableCRC4ErroredUpErroredSeconds OBJECT-TYPE
    SYNTAX      Counter32
    MAX-ACCESS  read-only
    STATUS      current
    DESCRIPTION
        "
        Indicates the count of uplink errored seconds.
        "
    ::= { hwMsPraL1CRCErrEntry 6 }

  hwMsPraMsgTableCRC4ErroredUpSeverelyErroredSeconds OBJECT-TYPE
    SYNTAX      Counter32
    MAX-ACCESS  read-only
    STATUS      current
    DESCRIPTION
        "
        Indicates the count of uplink consecutive severely errored seconds.
        "
    ::= { hwMsPraL1CRCErrEntry 7 }

  hwMsPraMsgTableCRC4ErroredUpDegradedMinutes OBJECT-TYPE
    SYNTAX      Counter32
    MAX-ACCESS  read-only
    STATUS      current
    DESCRIPTION
        "
        Indicates the count of uplink degraded minutes.
        "
    ::= { hwMsPraL1CRCErrEntry 8 }

  hwMsPraMsgTableCRC4ErroredUpUnavailableTime OBJECT-TYPE
    SYNTAX      Counter32
    MAX-ACCESS  read-only
    STATUS      current
    DESCRIPTION
        "
        Indicates the length of uplink unavailable time.
        "
    ::= { hwMsPraL1CRCErrEntry 9 }

  hwMsPraMsgTableCRC4ErroredDownUnavailableTime OBJECT-TYPE
    SYNTAX      Counter32
    MAX-ACCESS  read-only
    STATUS      current
    DESCRIPTION
        "
        Indicates the length of downlink unavailable time.
        "
    ::= { hwMsPraL1CRCErrEntry 10 }

  hwMsPraCRC4ErroredLastErroredTime OBJECT-TYPE
    SYNTAX      DateAndTime
    MAX-ACCESS  read-only
    STATUS      current
    DESCRIPTION
        "
        Indicates the time for generating the last error code.
        "
    ::= { hwMsPraL1CRCErrEntry 11 }

  hwMsPraMsgTableSection2CRC4ErroredDownErroredSeconds OBJECT-TYPE
    SYNTAX      Counter32
    MAX-ACCESS  read-only
    STATUS      current
    DESCRIPTION
        "
        Section2 Count of error bits in Second of down state:count of error bits
        or detect LOS/AIS/LFA/RAI/LMFA
        "
    ::= { hwMsPraL1CRCErrEntry 12 }
  hwMsPraMsgTableSection2CRC4ErroredDownSeverelyErroredSeconds OBJECT-TYPE
    SYNTAX      Counter32
    MAX-ACCESS  read-only
    STATUS      current
    DESCRIPTION
        "
        Section2 Count of severely error in second of down state: error rate >= 1/1000 in second
        or detect LOS/AIS/LFA/RAI/LMFA
        "
    ::= { hwMsPraL1CRCErrEntry 13 }
  hwMsPraMsgTableSection2CRC4ErroredDownDegradedMinutes OBJECT-TYPE
    SYNTAX      Counter32
    MAX-ACCESS  read-only
    STATUS      current
    DESCRIPTION
        "
        Section2 Count of degrade in minute: count of error bit in minute
        or detect LOS/AIS/LFA/RAI/LMFA
        "
    ::= { hwMsPraL1CRCErrEntry 14 }

  hwMsPraMsgTableSection2CRC4ErroredDownUnavailableTime OBJECT-TYPE
    SYNTAX      Counter32
    MAX-ACCESS  read-only
    STATUS      current
    DESCRIPTION
        "
        Section2 Unavailable time of Down state
        "
    ::= { hwMsPraL1CRCErrEntry 15 }

  hwMsPraMsgTableSection2CRC4ErroredUpErroredSeconds OBJECT-TYPE
    SYNTAX      Counter32
    MAX-ACCESS  read-only
    STATUS      current
    DESCRIPTION
        "
        Section2 count of error bits in second of up state
        "
    ::= { hwMsPraL1CRCErrEntry 16 }
  hwMsPraMsgTableSection2CRC4ErroredUpSeverelyErroredSeconds OBJECT-TYPE
    SYNTAX      Counter32
    MAX-ACCESS  read-only
    STATUS      current
    DESCRIPTION
        "
        Section2 count of severe bits in second of up state
        "
    ::= { hwMsPraL1CRCErrEntry 17 }
  hwMsPraMsgTableSection2CRC4ErroredUpDegradedMinutes OBJECT-TYPE
    SYNTAX      Counter32
    MAX-ACCESS  read-only
    STATUS      current
    DESCRIPTION
        "
        Section2 crc4 error of degrade minutes
        "
    ::= { hwMsPraL1CRCErrEntry 18 }
  hwMsPraMsgTableSection2CRC4ErroredUpUnavailableTime OBJECT-TYPE
    SYNTAX      Counter32
    MAX-ACCESS  read-only
    STATUS      current
    DESCRIPTION
        "
        Section2 unavailable time of up state
        "
    ::= { hwMsPraL1CRCErrEntry 19 }

   hwMsPraL1BITSErrTable OBJECT-TYPE
    SYNTAX      SEQUENCE OF HwMsPraL1BITSErrEntry
    MAX-ACCESS  not-accessible
    STATUS      current
    DESCRIPTION
      "
       Indicates the statistics of the PRA BER.
       The indexes of this table are hwMsPraMsgTableBITErroredRatePortIndex and hwMsPraMsgTableBITErroredRateResultNo.
      "
    ::= { hwMs 33 }
  hwMsPraL1BITSErrEntry OBJECT-TYPE
    SYNTAX      HwMsPraL1BITSErrEntry
    MAX-ACCESS  not-accessible
    STATUS      current
    DESCRIPTION
      "
       Indicates the statistics of the PRA BER.
       The indexes of this entry are hwMsPraMsgTableBITErroredRatePortIndex and hwMsPraMsgTableBITErroredRateResultNo."
    INDEX    {
              hwMsPraMsgTableBITErroredRatePortIndex,
              hwMsPraMsgTableBITErroredRateResultNo
             }
    ::= { hwMsPraL1BITSErrTable 1 }
  HwMsPraL1BITSErrEntry ::=
    SEQUENCE
    {
      hwMsPraMsgTableBITErroredRatePortIndex                                   Integer32,
      hwMsPraMsgTableBITErroredRateResultNo                                    Integer32,
      hwMsPraMsgTableBITErroredRateUpULF                                       Counter32,
      hwMsPraMsgTableBITErroredRateUpOLF                                       Counter32,
      hwMsPraMsgTableBITErroredRateUpLDT                                       Counter32,
      hwMsPraMsgTableBITErroredRateUpTestmoothCodeNum                          Counter32,
      hwMsPraMsgTableBITErroredRateDownULF                                     Counter32,
      hwMsPraMsgTableBITErroredRateDownOLF                     Counter32,
      hwMsPraMsgTableBITErroredRateDownLDT                                     Counter32,
      hwMsPraMsgTableBITErroredRateUpTestSmoothCodeNum                         Counter32,
      hwMsPraMsgTableBITErroredRateUpTestFrameSlipNum                          Counter32

    }
  hwMsPraMsgTableBITErroredRatePortIndex OBJECT-TYPE
    SYNTAX      Integer32
    MAX-ACCESS  not-accessible
    STATUS      current
    DESCRIPTION
        "
        Indicates the index of the port.
        "
    ::= { hwMsPraL1BITSErrEntry 1 }

  hwMsPraMsgTableBITErroredRateResultNo OBJECT-TYPE
    SYNTAX      Integer32
    MAX-ACCESS  not-accessible
    STATUS      current
    DESCRIPTION
        "
        Indicates the result number of statistics, 0: current value; 1: the value of the last quarter.
        "
    ::= { hwMsPraL1BITSErrEntry 2 }

  hwMsPraMsgTableBITErroredRateUpULF OBJECT-TYPE
    SYNTAX      Counter32
    MAX-ACCESS  read-only
    STATUS      current
    DESCRIPTION
        "
        Indicates the count of uplink ULFs.
        "
    ::= { hwMsPraL1BITSErrEntry 3 }

  hwMsPraMsgTableBITErroredRateUpOLF OBJECT-TYPE
    SYNTAX      Counter32
    MAX-ACCESS  read-only
    STATUS      current
    DESCRIPTION
        "
        Indicates the count of uplink OLFs.
        "
    ::= { hwMsPraL1BITSErrEntry 4 }

  hwMsPraMsgTableBITErroredRateUpLDT OBJECT-TYPE
    SYNTAX      Counter32
    MAX-ACCESS  read-only
    STATUS      current
    DESCRIPTION
        "
        Indicates the count of uplink LDTs.
        "
    ::= { hwMsPraL1BITSErrEntry 5 }

  hwMsPraMsgTableBITErroredRateUpTestmoothCodeNum OBJECT-TYPE
    SYNTAX      Counter32
    MAX-ACCESS  read-only
    STATUS      current
    DESCRIPTION
        "
        Indicates the count of uplink FRMSLIPs.
        "
    ::= { hwMsPraL1BITSErrEntry 6 }

  hwMsPraMsgTableBITErroredRateDownULF OBJECT-TYPE
    SYNTAX      Counter32
    MAX-ACCESS  read-only
    STATUS      current
    DESCRIPTION
        "
        Indicates the count of downlink ULFs.
        "
    ::= { hwMsPraL1BITSErrEntry 7 }

  hwMsPraMsgTableBITErroredRateDownOLF OBJECT-TYPE
    SYNTAX      Counter32
    MAX-ACCESS  read-only
    STATUS      current
    DESCRIPTION
        "
        Indicates the count of downlink OLFs.
        "
    ::= { hwMsPraL1BITSErrEntry 8 }

  hwMsPraMsgTableBITErroredRateDownLDT OBJECT-TYPE
    SYNTAX      Counter32
    MAX-ACCESS  read-only
    STATUS      current
    DESCRIPTION
        "
        Indicates the count of downlink LDTs.
        "
    ::= { hwMsPraL1BITSErrEntry 9 }

  hwMsPraMsgTableBITErroredRateUpTestSmoothCodeNum OBJECT-TYPE
    SYNTAX      Counter32
    MAX-ACCESS  read-only
    STATUS      current
    DESCRIPTION
        "
        Indicates the count of downlink FRMSLIPs.
        "
    ::= { hwMsPraL1BITSErrEntry 10 }

  hwMsPraMsgTableBITErroredRateUpTestFrameSlipNum OBJECT-TYPE
    SYNTAX      Counter32
    MAX-ACCESS  read-only
    STATUS      current
    DESCRIPTION
        "count of slip of test duration of up
        "
    ::= { hwMsPraL1BITSErrEntry 11 }

  hwMsKPIStatTable OBJECT IDENTIFIER ::= { hwMs 34 }

  hwMsUserRegSucc OBJECT-TYPE
    SYNTAX      Counter32
    MAX-ACCESS  read-only
    STATUS      current
    DESCRIPTION
        "
         Count the number of subscribers that successfully register.
        "
    ::= { hwMsKPIStatTable 1 }

  hwMsAttRegSucc OBJECT-TYPE
    SYNTAX      Counter32
    MAX-ACCESS  read-only
    STATUS      current
    DESCRIPTION
        "
         Count the number of successful registrations.
        "
    ::= { hwMsKPIStatTable 2 }

  hwMsAttRegFail OBJECT-TYPE
    SYNTAX      Counter32
    MAX-ACCESS  read-only
    STATUS      current
    DESCRIPTION
        "
         Count the number of failed registration.
        "
    ::= { hwMsKPIStatTable 3 }

  hwMsAttInSuccSes OBJECT-TYPE
    SYNTAX      Counter32
    MAX-ACCESS  read-only
    STATUS      current
    DESCRIPTION
        "
         Count the number of successful incoming calls.
        "
    ::= { hwMsKPIStatTable 4 }

  hwMsAttOutSuccSes OBJECT-TYPE
    SYNTAX      Counter32
    MAX-ACCESS  read-only
    STATUS      current
    DESCRIPTION
        "
         Count the number of successful outgoing calls.
        "
    ::= { hwMsKPIStatTable 5 }

  hwMsAttCallsIn OBJECT-TYPE
    SYNTAX      Counter32
    MAX-ACCESS  read-only
    STATUS      current
    DESCRIPTION
        "
         Count the number of calls in.
        "
    ::= { hwMsKPIStatTable 6 }

  hwMsAttCallsOut OBJECT-TYPE
    SYNTAX      Counter32
    MAX-ACCESS  read-only
    STATUS      current
    DESCRIPTION
        "
         Count the number of calls out.
        "
    ::= { hwMsKPIStatTable 7 }

  hwMsAttSuccessCallsIn OBJECT-TYPE
    SYNTAX      Counter32
    MAX-ACCESS  read-only
    STATUS      current
    DESCRIPTION
        "
         Count the number of successful calls in.
        "
    ::= { hwMsKPIStatTable 8 }

  hwMsAttSuccessCallsOut OBJECT-TYPE
    SYNTAX      Counter32
    MAX-ACCESS  read-only
    STATUS      current
    DESCRIPTION
        "
         Count the number of successful calls out.
        "
    ::= { hwMsKPIStatTable 9 }

    hwMsE1ErrorTable OBJECT-TYPE
    SYNTAX      SEQUENCE OF HwMsE1ErrorEntry
    MAX-ACCESS  not-accessible
    STATUS      current
    DESCRIPTION
      "
       Indicates the statistics of E1 Error.
       The index of this table is hwMsE1Layer1ErrorIndex.
      "
    ::= { hwMs 35 }
    hwMsE1ErrorEntry OBJECT-TYPE
    SYNTAX      HwMsE1ErrorEntry
    MAX-ACCESS  not-accessible
    STATUS      current
    DESCRIPTION
      "
      Indicates the statistics of E1 Error.
      The index of this entry is hwMsE1Layer1ErrorIndex.
      "
    INDEX    {
              hwMsE1Layer1ErrorIndex
             }
    ::= { hwMsE1ErrorTable 1 }
  HwMsE1ErrorEntry ::=
    SEQUENCE
    {
      hwMsE1Layer1ErrorIndex                         Integer32,
      hwMsE1Layer1ErrorOper                          INTEGER,
      hwMsE1Layer1ErrorCodeViolate                   Counter32,
      hwMsE1Layer1ErrorFrame                         Counter32,
      hwMsE1Layer1ErrorCRC                           Counter32,
      hwMsE1Layer1ErrorEBit                          Counter32,
      hwMsE1Layer1ErrorSa6Bit                        Counter32,
      hwMsE1Layer1ErrorMultiframePeriod              Counter32,
      hwMsE1Layer1ErrorCOFA                          Counter32
    }

  hwMsE1Layer1ErrorIndex OBJECT-TYPE
    SYNTAX      Integer32
    MAX-ACCESS  not-accessible
    STATUS      current
    DESCRIPTION
        "
        Indicates the index of the port.
        "
    ::= { hwMsE1ErrorEntry 1 }

  hwMsE1Layer1ErrorOper OBJECT-TYPE
    SYNTAX      INTEGER{get(1),clear(2)}
    MAX-ACCESS  read-create
    STATUS      current
    DESCRIPTION
        "
        Indicates the operation type, 1: get; 2: clear.
        Options:
        1. get(1)    -indicates that the get operation.
        2. clear(2)  -indicates that the clear operation.
        "
    ::= { hwMsE1ErrorEntry 2 }

  hwMsE1Layer1ErrorCodeViolate OBJECT-TYPE
    SYNTAX      Counter32
    MAX-ACCESS  read-only
    STATUS      current
    DESCRIPTION
        "
        Indicates the count of code violate.
        "
    ::= { hwMsE1ErrorEntry 3 }

  hwMsE1Layer1ErrorFrame OBJECT-TYPE
    SYNTAX      Counter32
    MAX-ACCESS  read-only
    STATUS      current
    DESCRIPTION
        "
        Indicates the count of Frame error.
        "
    ::= { hwMsE1ErrorEntry 4 }

  hwMsE1Layer1ErrorCRC OBJECT-TYPE
    SYNTAX      Counter32
    MAX-ACCESS  read-only
    STATUS      current
    DESCRIPTION
        "
        Indicates the count of CRC error.
        "
    ::= { hwMsE1ErrorEntry 5 }

  hwMsE1Layer1ErrorEBit OBJECT-TYPE
    SYNTAX      Counter32
    MAX-ACCESS  read-only
    STATUS      current
    DESCRIPTION
        "
        Indicates the count of E-bit error.
        "
    ::= { hwMsE1ErrorEntry 6 }

  hwMsE1Layer1ErrorSa6Bit OBJECT-TYPE
    SYNTAX      Counter32
    MAX-ACCESS  read-only
    STATUS      current
    DESCRIPTION
        "
        Indicates the count of Sa-6 bit error.
        "
    ::= { hwMsE1ErrorEntry 7 }

  hwMsE1Layer1ErrorMultiframePeriod OBJECT-TYPE
    SYNTAX      Counter32
    MAX-ACCESS  read-only
    STATUS      current
    DESCRIPTION
        "
        Indicates the count of Multiframe error.
        "
    ::= { hwMsE1ErrorEntry 8 }

  hwMsE1Layer1ErrorCOFA OBJECT-TYPE
    SYNTAX      Counter32
    MAX-ACCESS  read-only
    STATUS      current
    DESCRIPTION
        "
        Indicates the length of COFA.
        "
    ::= { hwMsE1ErrorEntry 9 }

  hwMsTraps OBJECT IDENTIFIER ::= { hwMs 60 }

  hwMsCommonTraps OBJECT IDENTIFIER ::= { hwMsTraps 1 }

  hwMsPeriodStatisticComTraps OBJECT IDENTIFIER ::= { hwMsCommonTraps 1 }


  hwMsPeriodStatChangeTrap NOTIFICATION-TYPE
    OBJECTS  { hwMsPeriodUnit, hwMsPeriodObject1, hwMsPeriodObject2}
    STATUS      current
    DESCRIPTION
        "
        The trap indicates that the period state changes, When the period state changes, the trap will be sent.
        "
    ::= { hwMsPeriodStatisticComTraps 0 1 }

  hwMsAlarmTraps OBJECT IDENTIFIER ::= { hwMsTraps 2 }

  END
