--
-- HUAWEI-STORAGE-ALARM-MIB.mib
-- MIB generated by MG-SOFT Visual MIB Builder Version 4.0 Build 347
-- Tuesday, December 27, 2016 at 19:31:15
--

	HUAWEI-STORAGE-ALARM-MIB DEFINITIONS ::= BEGIN

		IMPORTS
			OBJECT-GROUP, MODULE-COMPLIANCE, NOTIFICATION-GROUP
				FROM SNMPv2-CONF
			enterprises, Integer32, Unsigned32, Gauge32,
			Counter32, OBJECT-TYPE, MODULE-IDENTITY, NOTIFICATION-TYPE
				FROM SNMPv2-SMI
			DisplayString
				FROM SNMPv2-TC;


		storage MODULE-IDENTITY
			LAST-UPDATED "201612271804Z"		-- December 27, 2016 at 18:04 GMT
			ORGANIZATION
				"Huawei Technologies Co.,Ltd."
			CONTACT-INFO
				"Huawei Industrial Base
				Bantian, Longgang
				Shenzhen 518129
				People's Republic of China
				Website: http://www.huawei.com
				Email: support@huawei.com"
			DESCRIPTION
				"Description."
			::= { products 251 }




--
-- Node definitions
--

		huawei OBJECT IDENTIFIER ::= { enterprises 2011 }


		products OBJECT IDENTIFIER ::= { huawei 2 }


		alarm OBJECT IDENTIFIER ::= { storage 20 }


		hwStorageNotification OBJECT IDENTIFIER ::= { alarm 1 }


		hwStorageActiveAlarmInfo OBJECT IDENTIFIER ::= { hwStorageNotification 1 }


		hwStorageActiveAlarmInfoTable OBJECT-TYPE
			SYNTAX SEQUENCE OF HwStorageActiveAlarmInfoEntry
			MAX-ACCESS not-accessible
			STATUS current
			DESCRIPTION
				"ActiveAlarm Information Table
				"
			::= { hwStorageActiveAlarmInfo 1 }


		hwStorageActiveAlarmInfoEntry OBJECT-TYPE
			SYNTAX HwStorageActiveAlarmInfoEntry
			MAX-ACCESS not-accessible
			STATUS current
			DESCRIPTION
				"Entry of Active Alarm Information Table
				"
			INDEX { hwStorageActiveAlarmInfoNodeCode, hwStorageActiveAlarmInfoSerialNo }
			::= { hwStorageActiveAlarmInfoTable 1 }


		HwStorageActiveAlarmInfoEntry ::=
			SEQUENCE {
				hwStorageActiveAlarmInfoNodeCode
					OCTET STRING,
				hwStorageActiveAlarmInfoLocationInfo
					DisplayString,
				hwStorageActiveAlarmInfoRestoreAdvice
					DisplayString,
				hwStorageActiveAlarmInfoTitle
					DisplayString,
				hwStorageActiveAlarmInfoType
					INTEGER,
				hwStorageActiveAlarmInfoLevel
					INTEGER,
				hwStorageActiveAlarmInfoAlarmID
					Gauge32,
				hwStorageActiveAlarmInfoOccurTime
					OCTET STRING,
				hwStorageActiveAlarmInfoSerialNo
					Gauge32,
				hwStorageActiveAlarmInfoAddtionInfo
					OCTET STRING,
				hwStorageActiveAlarmInfoCategory
					INTEGER,
				hwStorageActiveAlarmInfoLocalAlarmID
					Counter64
			 }

		hwStorageActiveAlarmInfoNodeCode OBJECT-TYPE
			SYNTAX OCTET STRING
			MAX-ACCESS read-only
			STATUS current
			DESCRIPTION
				"Active Alarm NodeCode"
			::= { hwStorageActiveAlarmInfoEntry 1 }


		hwStorageActiveAlarmInfoLocationInfo OBJECT-TYPE
			SYNTAX DisplayString
			MAX-ACCESS read-only
			STATUS current
			DESCRIPTION
				"Active Alarm Location Information"
			::= { hwStorageActiveAlarmInfoEntry 2 }


		hwStorageActiveAlarmInfoRestoreAdvice OBJECT-TYPE
			SYNTAX DisplayString
			MAX-ACCESS read-only
			STATUS current
			DESCRIPTION
				"Active Alarm Restore Advice"
			::= { hwStorageActiveAlarmInfoEntry 3 }


		hwStorageActiveAlarmInfoTitle OBJECT-TYPE
			SYNTAX DisplayString
			MAX-ACCESS read-only
			STATUS current
			DESCRIPTION
				"Active Alarm Title"
			::= { hwStorageActiveAlarmInfoEntry 4 }


		hwStorageActiveAlarmInfoType OBJECT-TYPE
			SYNTAX INTEGER { equipmentFault(2) }
			MAX-ACCESS read-only
			STATUS current
			DESCRIPTION
				"Active Alarm Type"
			::= { hwStorageActiveAlarmInfoEntry 5 }


		hwStorageActiveAlarmInfoLevel OBJECT-TYPE
			SYNTAX INTEGER
				{
				criticalAlarm(1),
				majorAlarm(2),
				minorAlarm(3),
				warningAlarm(4)
				}
			MAX-ACCESS read-only
			STATUS current
			DESCRIPTION
				"Active Alarm Level


				1-criticalAlarm
				2-majorAlarm
				3-minorAlarm
				4-warningAlarm

				"
			::= { hwStorageActiveAlarmInfoEntry 6 }


		hwStorageActiveAlarmInfoAlarmID OBJECT-TYPE
			SYNTAX Gauge32
			MAX-ACCESS read-only
			STATUS current
			DESCRIPTION
				"Active Alarm ID"
			::= { hwStorageActiveAlarmInfoEntry 7 }


		hwStorageActiveAlarmInfoOccurTime OBJECT-TYPE
			SYNTAX OCTET STRING
			MAX-ACCESS read-only
			STATUS current
			DESCRIPTION
				"Occurrence Time of Alarm"
			::= { hwStorageActiveAlarmInfoEntry 8 }


		hwStorageActiveAlarmInfoSerialNo OBJECT-TYPE
			SYNTAX Gauge32
			MAX-ACCESS read-only
			STATUS current
			DESCRIPTION
				"Active Alarm Serial No."
			::= { hwStorageActiveAlarmInfoEntry 9 }


		hwStorageActiveAlarmInfoAddtionInfo OBJECT-TYPE
			SYNTAX OCTET STRING
			MAX-ACCESS read-only
			STATUS current
			DESCRIPTION
				"Active Alarm Addtion Information"
			::= { hwStorageActiveAlarmInfoEntry 10 }


		hwStorageActiveAlarmInfoCategory OBJECT-TYPE
			SYNTAX INTEGER
				{
				faultAlarm(1),
				resumeAlarm(2),
				eventAlarm(3)
				}
			MAX-ACCESS read-only
			STATUS current
			DESCRIPTION
				"Active Alarm Category


				1-faultAlarm
				2-resumeAlarm
				3-eventAlarm  "
			::= { hwStorageActiveAlarmInfoEntry 11 }


		hwStorageActiveAlarmInfoLocalAlarmID OBJECT-TYPE
			SYNTAX Counter64
			MAX-ACCESS read-only
			STATUS current
			DESCRIPTION
				"Active original Alarm ID"
			::= { hwStorageActiveAlarmInfoEntry 12 }


		hwStorageNotificationType OBJECT IDENTIFIER ::= { hwStorageNotification 2 }


		hwStorageAlarmReporting NOTIFICATION-TYPE
			OBJECTS { hwStorageReportingAlarmNodeCode, hwStorageReportingAlarmLocationInfo, hwStorageReportingAlarmRestoreAdvice, hwStorageReportingAlarmFaultTitle, hwStorageReportingAlarmFaultType,
				hwStorageReportingAlarmFaultLevel, hwStorageReportingAlarmAlarmID, hwStorageReportingAlarmFaultTime, hwStorageReportingAlarmSerialNo, hwStorageReportingAlarmAdditionInfo,
				hwStorageReportingAlarmFaultCategory, hwStorageReportingAlarmLocationAlarmID, hwStorageReportingAlarmProductModel, hwStorageReportingAlarmProductSN }
			STATUS current
			DESCRIPTION
				"Description."
			::= { hwStorageNotificationType 1 }


		hwStorageReportingAlarm OBJECT IDENTIFIER ::= { hwStorageNotification 3 }


--  1.3.6.1.4.1.2011.2.91.10.3.1.1.1
		hwStorageReportingAlarmNodeCode OBJECT-TYPE
			SYNTAX OCTET STRING
			MAX-ACCESS accessible-for-notify
			STATUS current
			DESCRIPTION
				"Alarm Node Code"
			REFERENCE
				"Location info of  Fault Alarm"
			::= { hwStorageReportingAlarm 1 }


--  1.3.6.1.4.1.2011.2.91.10.3.1.1.2
		hwStorageReportingAlarmLocationInfo OBJECT-TYPE
			SYNTAX DisplayString
			MAX-ACCESS accessible-for-notify
			STATUS current
			DESCRIPTION
				"Reporting Alarm Location Information"
			::= { hwStorageReportingAlarm 2 }


--  1.3.6.1.4.1.2011.2.91.10.3.1.1.3
		hwStorageReportingAlarmRestoreAdvice OBJECT-TYPE
			SYNTAX OCTET STRING (SIZE (0..256))
			MAX-ACCESS accessible-for-notify
			STATUS current
			DESCRIPTION
				"Advice of Restore Reporting Alarm "
			::= { hwStorageReportingAlarm 3 }


		hwStorageReportingAlarmFaultTitle OBJECT-TYPE
			SYNTAX OCTET STRING (SIZE (0..256))
			MAX-ACCESS accessible-for-notify
			STATUS current
			DESCRIPTION
				"Fault Alarm Title "
			::= { hwStorageReportingAlarm 4 }


		hwStorageReportingAlarmFaultType OBJECT-TYPE
			SYNTAX INTEGER
				{
				communicationQuality(1),
				equipmentFault(2),
				processError(3),
				serviceQuality(4),
				environmentFault(5),
				performanceLimit(6)
				}
			MAX-ACCESS accessible-for-notify
			STATUS current
			DESCRIPTION
				"Fault Alarm  Type"
			::= { hwStorageReportingAlarm 5 }


		hwStorageReportingAlarmFaultLevel OBJECT-TYPE
			SYNTAX INTEGER
				{
				criticalAlarm(1),
				majorAlarm(2),
				minorAlarm(3),
				warningAlarm(4)
				}
			MAX-ACCESS accessible-for-notify
			STATUS current
			DESCRIPTION
				"Level of Fault Alarm


				CriticalAlarm(1)
				MajorAlarm(2)
				MinorAlarm(3)
				WarningAlarm(4)
				"
			::= { hwStorageReportingAlarm 6 }


		hwStorageReportingAlarmAlarmID OBJECT-TYPE
			SYNTAX Gauge32
			MAX-ACCESS accessible-for-notify
			STATUS current
			DESCRIPTION
				"Fault Alarm ID"
			::= { hwStorageReportingAlarm 7 }


		hwStorageReportingAlarmFaultTime OBJECT-TYPE
			SYNTAX OCTET STRING
			MAX-ACCESS accessible-for-notify
			STATUS current
			DESCRIPTION
				"Occurrence Time of Fault Alarm"
			::= { hwStorageReportingAlarm 8 }


		hwStorageReportingAlarmSerialNo OBJECT-TYPE
			SYNTAX Gauge32
			MAX-ACCESS accessible-for-notify
			STATUS current
			DESCRIPTION
				"Fault Alarm Serial No."
			::= { hwStorageReportingAlarm 9 }


		hwStorageReportingAlarmAdditionInfo OBJECT-TYPE
			SYNTAX DisplayString
			MAX-ACCESS accessible-for-notify
			STATUS current
			DESCRIPTION
				"Addition Info of Fault Alarm"
			::= { hwStorageReportingAlarm 10 }


		hwStorageReportingAlarmFaultCategory OBJECT-TYPE
			SYNTAX INTEGER
				{
				faultAlarm(1),
				resumeAlarm(2),
				eventAlarm(3)
				}
			MAX-ACCESS accessible-for-notify
			STATUS current
			DESCRIPTION
				"Category of Fault Alarm


				faultAlarm (1):
				resumeAlarm (2):
				eventAlarm (3):
				"
			::= { hwStorageReportingAlarm 11 }


		hwStorageReportingAlarmLocationAlarmID OBJECT-TYPE
			SYNTAX Counter64
			MAX-ACCESS accessible-for-notify
			STATUS current
			DESCRIPTION
				"Description."
			::= { hwStorageReportingAlarm 12 }


--  1.3.6.1.4.1.2011.2.91.10.3.1.1.13
		hwStorageReportingAlarmProductModel OBJECT-TYPE
			SYNTAX Integer32
			MAX-ACCESS accessible-for-notify
			STATUS current
			DESCRIPTION
				"Description."
			::= { hwStorageReportingAlarm 13 }


--  1.3.6.1.4.1.2011.2.91.10.3.1.1.14
		hwStorageReportingAlarmProductSN OBJECT-TYPE
			SYNTAX OCTET STRING
			MAX-ACCESS accessible-for-notify
			STATUS current
			DESCRIPTION
				"Description."
			::= { hwStorageReportingAlarm 14 }


		hwStorageEvent OBJECT IDENTIFIER ::= { alarm 2 }


		notificationType OBJECT IDENTIFIER ::= { hwStorageEvent 1 }


		hwStorageEventType NOTIFICATION-TYPE
			OBJECTS { hwStorageTrapEventType, hwStorageTrapEventID, hwStorageTrapEventLevel, hwStorageTrapEventSequence, hwStorageTrapEventTime,
				hwStorageTrapEventRecoveryTime, hwStorageTrapEventParameter, hwStorageTrapEventID32Bit, hwStorageTrapEventTimeStr, hwStorageTrapEventRecoveryTimeStr
				 }
			STATUS current
			DESCRIPTION
				" "
			::= { notificationType 1 }


		trapEvent OBJECT IDENTIFIER ::= { hwStorageEvent 2 }


		hwStorageTrapEventType OBJECT-TYPE
			SYNTAX Unsigned32
			MAX-ACCESS accessible-for-notify
			STATUS current
			DESCRIPTION
				"Description."
			::= { trapEvent 1 }


		hwStorageTrapEventID OBJECT-TYPE
			SYNTAX Counter64
			MAX-ACCESS accessible-for-notify
			STATUS current
			DESCRIPTION
				"Description."
			::= { trapEvent 2 }


		hwStorageTrapEventLevel OBJECT-TYPE
			SYNTAX Unsigned32
			MAX-ACCESS accessible-for-notify
			STATUS current
			DESCRIPTION
				"Description."
			::= { trapEvent 3 }


		hwStorageTrapEventSequence OBJECT-TYPE
			SYNTAX Unsigned32
			MAX-ACCESS accessible-for-notify
			STATUS current
			DESCRIPTION
				"Description."
			::= { trapEvent 4 }


		hwStorageTrapEventTime OBJECT-TYPE
			SYNTAX Unsigned32
			MAX-ACCESS accessible-for-notify
			STATUS current
			DESCRIPTION
				"Description."
			::= { trapEvent 5 }


		hwStorageTrapEventRecoveryTime OBJECT-TYPE
			SYNTAX Unsigned32
			MAX-ACCESS accessible-for-notify
			STATUS current
			DESCRIPTION
				"Description."
			::= { trapEvent 6 }


		hwStorageTrapEventParameter OBJECT-TYPE
			SYNTAX OCTET STRING
			MAX-ACCESS accessible-for-notify
			STATUS current
			DESCRIPTION
				"Description."
			::= { trapEvent 7 }


		hwStorageTrapEventID32Bit OBJECT-TYPE
			SYNTAX Unsigned32
			MAX-ACCESS accessible-for-notify
			STATUS current
			DESCRIPTION
				"Description."
			::= { trapEvent 8 }


		hwStorageTrapEventTimeStr OBJECT-TYPE
			SYNTAX OCTET STRING
			MAX-ACCESS accessible-for-notify
			STATUS current
			DESCRIPTION
				"Description."
			::= { trapEvent 9 }


		hwStorageTrapEventRecoveryTimeStr OBJECT-TYPE
			SYNTAX OCTET STRING
			MAX-ACCESS accessible-for-notify
			STATUS current
			DESCRIPTION
				"Description."
			::= { trapEvent 10 }


--  1.6
		isoConformance OBJECT IDENTIFIER ::= { iso 6 }


--  1.6.1
		isoGroups OBJECT IDENTIFIER ::= { isoConformance 1 }


		currentObjectGroup OBJECT-GROUP
			OBJECTS { hwStorageActiveAlarmInfoNodeCode, hwStorageActiveAlarmInfoLocationInfo, hwStorageActiveAlarmInfoRestoreAdvice, hwStorageActiveAlarmInfoTitle, hwStorageActiveAlarmInfoType,
				hwStorageActiveAlarmInfoLevel, hwStorageActiveAlarmInfoAlarmID, hwStorageActiveAlarmInfoOccurTime, hwStorageActiveAlarmInfoSerialNo, hwStorageActiveAlarmInfoAddtionInfo,
				hwStorageActiveAlarmInfoCategory, hwStorageActiveAlarmInfoLocalAlarmID, hwStorageReportingAlarmNodeCode, hwStorageReportingAlarmLocationInfo, hwStorageReportingAlarmRestoreAdvice,
				hwStorageReportingAlarmFaultTitle, hwStorageReportingAlarmFaultType, hwStorageReportingAlarmFaultLevel, hwStorageReportingAlarmAlarmID, hwStorageReportingAlarmFaultTime,
				hwStorageReportingAlarmSerialNo, hwStorageReportingAlarmAdditionInfo, hwStorageReportingAlarmFaultCategory, hwStorageReportingAlarmLocationAlarmID, hwStorageReportingAlarmProductModel,
				hwStorageReportingAlarmProductSN, hwStorageTrapEventType, hwStorageTrapEventID, hwStorageTrapEventLevel, hwStorageTrapEventSequence,
				hwStorageTrapEventTime, hwStorageTrapEventRecoveryTime, hwStorageTrapEventParameter, hwStorageTrapEventID32Bit, hwStorageTrapEventTimeStr,
				hwStorageTrapEventRecoveryTimeStr }
			STATUS current
			DESCRIPTION
				"Enter the description of the created OBJECT-GROUP."
			::= { isoGroups 1 }


--  1.6.1.2
		currentNotificationGroup NOTIFICATION-GROUP
			NOTIFICATIONS { hwStorageAlarmReporting, hwStorageEventType }
			STATUS current
			DESCRIPTION
				"Enter the description of the created NOTIFICATION-GROUP."
			::= { isoGroups 2 }


		isoCompliances OBJECT IDENTIFIER ::= { isoConformance 2 }


		basicCompliance MODULE-COMPLIANCE
			STATUS current
			DESCRIPTION
				"Enter the description of the created MODULE-COMPLIANCE."
			MODULE -- this module
				MANDATORY-GROUPS { currentObjectGroup, currentNotificationGroup }
			::= { isoCompliances 1 }



	END

--
-- HUAWEI-STORAGE-ALARM-MIB.mib
--
