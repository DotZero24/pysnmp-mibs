-- ============================================================================
-- Copyright (C) 2012 by  HUAWEI TECHNOLOGIES. All rights reserved.
-- Description: This MIB module defines MIB objects which provides SIGTRAN management.
-- Reference:
-- Version: V1.23
-- ============================================================================

HWMUSA-SIGTRAN-MIB DEFINITIONS ::= BEGIN
IMPORTS
	MODULE-IDENTITY, OBJECT-TYPE, NOTIFICATION-TYPE, private
		FROM SNMPv2-SMI
	MODULE-COMPLIANCE, OBJECT-GROUP, NOTIFICATION-GROUP
		FROM SNMPv2-CONF
	TEXTUAL-CONVENTION
		FROM SNMPv2-TC
	RowStatus,DateAndTime,DisplayString
		FROM SNMPv2-TC
	IpAddress,Integer32,Unsigned32
		FROM SNMPv2-SMI
  ias
    FROM HUAWEI-MIB;

    hwIASSigtranObjects MODULE-IDENTITY
	    LAST-UPDATED "201202290000Z"
        ORGANIZATION "Huawei Technologies Co.,Ltd."
        CONTACT-INFO
                     "Huawei Industrial Base
                      Bantian, Longgang
    	              Shenzhen 518129
    	              People's Republic of China
    	              Website: http://www.huawei.com
    	              Email: support@huawei.com
    	             "
	    DESCRIPTION
	        "
	        This MIB module defines MIB objects which provides SIGTRAN management.
	        "

        --  Revision history
            REVISION     "201210120000Z"
            DESCRIPTION  "V1.23, modify the value range of hwL2uaLinkMaxInStreamNum,hwL2uaLinkMaxOutStreamNum in hwL2uaLinkMngtTable"

            REVISION     "201210120000Z"
            DESCRIPTION  "V1.23, modify the value range of hwL2uaLinkActiveStandbyFlag,hwL2uaLinkUsedOutStreamNum,hwL2uaLinkUsedInStreamNum,
            		          hwL2uaLinkCongestState,hwL2uaLinkMaintainOper,hwL2uaLinkLockStatus in hwL2uaLinkMngtTable"

            REVISION     "201202290000Z"
            DESCRIPTION  "V1.22, delete the default value of hwMifSctpCfgParaSendChecksum and hwMifSctpCfgParaRecvChecksum"

            REVISION     "201109210000Z"
            DESCRIPTION  "V1.21, revise the description errors"

            REVISION     "201110200000Z"
            DESCRIPTION  "V1.20, modified the type and range of the	hwSctpAssocLocalRwnd and hwSctpAssocRemoteRwnd"

            REVISION     "201009010000Z"
            DESCRIPTION  "V1.19, revise the description errors"

            REVISION     "201007010000Z"
            DESCRIPTION  "V1.18, revise the errors"

            REVISION     "201005050000Z"
            DESCRIPTION  "V1.17, revise the errors"

            REVISION     "201003220000Z"
            DESCRIPTION  "V1.16, correct the test errors"

	          REVISION   "201001250000Z"
            DESCRIPTION  "V1.15, add trap notification and correct compile error"

            REVISION     "200912180000Z"
            DESCRIPTION  "V1.14, add hwL2uaLinkLocalIpDynamicIPName to support DHCP"

            REVISION     "200911060000Z"
            DESCRIPTION  "V1.13, add hwSctpGlobalParaTable to SCTP global parameters configuration"


	    ::= { hwIASSigtran 1 }

hwIASSigtranTrapsVbOids OBJECT IDENTIFIER ::= { hwIASSigtran 2 }

hwIASSigtranTraps OBJECT IDENTIFIER ::= { hwIASSigtran 3 }

hwIASSigtranCommonTraps OBJECT IDENTIFIER ::= { hwIASSigtranTraps 1 }

hwIASSigtranAlarmTraps OBJECT IDENTIFIER ::= { hwIASSigtranTraps 2 }

hwIASSigtranL2uaTraps OBJECT IDENTIFIER ::= { hwIASSigtranCommonTraps 1 }

hwIASSigtranL2uaAlarmTraps OBJECT IDENTIFIER ::= { hwIASSigtranAlarmTraps 1 }

hwSctpVersionTable OBJECT IDENTIFIER ::= { hwIASSigtranObjects 11 }

hwL2uaVersionTable OBJECT IDENTIFIER ::= { hwIASSigtranObjects 10 }

hwSctpParaTable OBJECT IDENTIFIER ::= { hwIASSigtranObjects 9 }

hwSctpGlobalStatTable OBJECT IDENTIFIER ::= { hwIASSigtranObjects 8 }

hwIASSigtran OBJECT IDENTIFIER ::= { ias 6 }


  hwL2uaLinkSetMngtTable OBJECT-TYPE
    SYNTAX      SEQUENCE OF HwL2uaLinkSetMngtEntry
    MAX-ACCESS  not-accessible
    STATUS      current
    DESCRIPTION
      "
      This table is used to config L2UA linkset.
      The index of this table is hwL2uaLinkSetNo.
      "
    ::= { hwIASSigtranObjects 1 }

  hwL2uaLinkSetMngtEntry OBJECT-TYPE
    SYNTAX      HwL2uaLinkSetMngtEntry
    MAX-ACCESS  not-accessible
    STATUS      current
    DESCRIPTION
      "
      This table is used to config L2UA linkset.
      The index of this entry is hwL2uaLinkSetNo.
      "
    INDEX    {
              hwL2uaLinkSetNo
             }
    ::= { hwL2uaLinkSetMngtTable 1 }

  HwL2uaLinkSetMngtEntry ::=
    SEQUENCE
    {
      hwL2uaLinkSetNo	Integer32,
      hwL2uaLinkSetProtocolType	INTEGER,
      hwL2uaLinkSetPendingTime	Integer32,
      hwL2uaLinkSetTrafficMode	INTEGER,
      hwL2uaLinkSetCSMode	INTEGER,
      hwL2uaLinkSetIIDType	INTEGER,
      hwL2uaLinkSetLinkNum	Integer32,
      hwL2uaLinkSetOperState	INTEGER,
      hwL2uaLinkSetRowStatus	RowStatus,
      hwL2uaLinkSetMgId         Integer32,
      hwL2uaLinkSetIidMap       Integer32,
      hwL2uaLinkSetJointlyWork  INTEGER,
      hwL2uaLinkSetIidPrefix    OCTET STRING,
      hwL2uaLinkSetIidBraPrefix OCTET STRING,
      hwL2uaLinkSetIidBraSuffix OCTET STRING,
      hwL2uaLinkSetIidPraPrefix OCTET STRING,
      hwL2uaLinkSetIidPrasuffix OCTET STRING
    }

  hwL2uaLinkSetNo OBJECT-TYPE
    SYNTAX      Integer32(0..15)
    MAX-ACCESS  not-accessible
    STATUS      current
    DESCRIPTION
        "
         The link set number
        "
    ::= { hwL2uaLinkSetMngtEntry 1 }

  hwL2uaLinkSetProtocolType OBJECT-TYPE
    SYNTAX      INTEGER{iua(1),  -- IUA
                        m2ua(2), -- M2UA
                        v5ua(5)  -- V5UA
                        }
    MAX-ACCESS  read-write
    STATUS      current
    DESCRIPTION
        "
        Protocol type.
        Options:
        1. iua(1) -indicates that the Protocol type is IUA
        2. m2ua(2) -indicates that that the Protocol type is M2UA
        3. v5ua(5) -indicates that that the Protocol type is V5UA(currently, only IUA is supported.)
        "
    ::= { hwL2uaLinkSetMngtEntry 2 }

  hwL2uaLinkSetPendingTime OBJECT-TYPE
    SYNTAX      Integer32(1..100)
    MAX-ACCESS  read-write
    STATUS      current
    DESCRIPTION
        "
        The pending time of the link set (the last active link in the link set switches to another state. During the pending time length, if no link in the link set switches to the active state, the link set enters the inactive or down state.).
        Default: 4
        Unit: second
        "
    DEFVAL      { 4 }
    ::= { hwL2uaLinkSetMngtEntry 3 }

  hwL2uaLinkSetTrafficMode OBJECT-TYPE
    SYNTAX      INTEGER{override(1), -- override
                        loadshare(2) -- load share
                        }
    MAX-ACCESS  read-write
    STATUS      current
    DESCRIPTION
        "
        The working mode of the link set.
        Options:
        1. override(1) -indicates that the working mode of the link set is override
        2. loadshare(2) -indicates that the working mode of the link set is loadshare
        "
    ::= { hwL2uaLinkSetMngtEntry 4 }

  hwL2uaLinkSetCSMode OBJECT-TYPE
    SYNTAX      INTEGER{client(1),server(2)}
    MAX-ACCESS  read-write
    STATUS      current
    DESCRIPTION
        "
        C/S mode of the link set.
        Options:
        1. client(1) -indicates that the C/S mode of the link set is Client
        2. server(2) -indicates that the C/S mode of the link set is Server
        Default: 2
        "
    ::= { hwL2uaLinkSetMngtEntry 5 }

  hwL2uaLinkSetIIDType OBJECT-TYPE
    SYNTAX      INTEGER{integer(1),text(2)}
    MAX-ACCESS  read-only
    STATUS      current
    DESCRIPTION
        "
         Type of the interface ID.
         Options:
         1. integer(1) -integer
         2. text(2)    -text
        "
    ::= { hwL2uaLinkSetMngtEntry 6 }

  hwL2uaLinkSetLinkNum OBJECT-TYPE
    SYNTAX      Integer32
    MAX-ACCESS  read-only
    STATUS      current
    DESCRIPTION
        "
        The number of links in the link set
        "
    ::= { hwL2uaLinkSetMngtEntry 7 }

  hwL2uaLinkSetOperState OBJECT-TYPE
    SYNTAX      INTEGER{down(1),     -- unestablished
                        inactive(2), -- inactive
                        active(3),   -- active
                        pending(4)   -- pending
                        }
    MAX-ACCESS  read-only
    STATUS      current
    DESCRIPTION
        "
        Status of the link set.
        Options:
        1. down(1) -indicates that the Status of the link set is down
        2. inactive(2) -indicates that the Status of the link set is inactive
        3. active(3) -indicates that the Status of the link set is active
        4. pending(4) -indicates that the Status of the link set is pending
        "
    ::= { hwL2uaLinkSetMngtEntry 8 }

  hwL2uaLinkSetRowStatus OBJECT-TYPE
    SYNTAX      RowStatus
    MAX-ACCESS  read-write
    STATUS      current
    DESCRIPTION
        "
        Row status
        "
    ::= { hwL2uaLinkSetMngtEntry 9 }

  hwL2uaLinkSetMgId OBJECT-TYPE
    SYNTAX      Integer32(-1|0..16777215)
    MAX-ACCESS  read-write
    STATUS      current
    DESCRIPTION
        "
         MG interface ID.
         -1 means this parameter is not configured.
        "
    ::= { hwL2uaLinkSetMngtEntry 10 }

  hwL2uaLinkSetIidMap OBJECT-TYPE
    SYNTAX      Integer32(1..5)
    MAX-ACCESS  read-write
    STATUS      current
    DESCRIPTION
        "
        InterfaceID generation mode.
        1:generated by user input,use format:interfaceID
        2:generated automatically,use format:ffsspp, ff-shelf number,ss-slot number, pp-port number, decimal number
        3:generated automatically,use format:rrrrfffffssssspppppppxxxxxxxxxxx ,rrrr-rack, fffff-shelf number,sssss-slot number, ppppppp-port number,xxxxxxxxxxx-reserved,binary number
        4:generated automatically,FT text format:prefix+ff/ss/pp, ff-shelf number,ss-slot number, pp-port number, text
        5:generated by user input,use format:braprefix+interfaceID+brasuffix or praprefix+interfaceID+prasuffix, the length of praprefix+interfaceID+prasuffix must be  shorter than 31
        Default:1
        "
    ::= { hwL2uaLinkSetMngtEntry 11 }

  hwL2uaLinkSetJointlyWork OBJECT-TYPE
    SYNTAX      INTEGER{enable(1),disable(2)}
    MAX-ACCESS  read-write
    STATUS      current
    DESCRIPTION
        "
        IUA link joint work with MGC.
        Options:
        1.enable(1)  -support IUA Link joint work with MGC
        2.disable(2) -not support IUA Link joint work with MGC
        It must config together with hwL2uaLinkSetMgId.
        "
    ::= { hwL2uaLinkSetMngtEntry 12 }

  hwL2uaLinkSetIidPrefix OBJECT-TYPE
    SYNTAX      OCTET STRING(SIZE(0..20))
    MAX-ACCESS  read-write
    STATUS      current
    DESCRIPTION
        "Indicates the prefix of IID.The prefix is not allowed to contain the character:';'':'','"
    ::= { hwL2uaLinkSetMngtEntry 13 }

  hwL2uaLinkSetIidBraPrefix OBJECT-TYPE
    SYNTAX      OCTET STRING(SIZE(0..20))
    MAX-ACCESS  read-write
    STATUS      current
    DESCRIPTION
        "Indicates the bra prefix of IID.The prefix is not allowed to contain the character:';'':'','"
    ::= { hwL2uaLinkSetMngtEntry 14 }

  hwL2uaLinkSetIidBraSuffix OBJECT-TYPE
    SYNTAX      OCTET STRING(SIZE(0..20))
    MAX-ACCESS  read-write
    STATUS      current
    DESCRIPTION
        "Indicates the bra suffix of IID.The suffix is not allowed to contain the character:';'':'','"
    ::= { hwL2uaLinkSetMngtEntry 15 }

  hwL2uaLinkSetIidPraPrefix OBJECT-TYPE
    SYNTAX      OCTET STRING(SIZE(0..20))
    MAX-ACCESS  read-write
    STATUS      current
    DESCRIPTION
        "Indicates the pra prefix of IID.The prefix is not allowed to contain the character:';'':'','"
    ::= { hwL2uaLinkSetMngtEntry 16 }

  hwL2uaLinkSetIidPrasuffix OBJECT-TYPE
    SYNTAX      OCTET STRING(SIZE(0..20))
    MAX-ACCESS  read-write
    STATUS      current
    DESCRIPTION
        "Indicates the pra suffix of IID.The suffix is not allowed to contain the character:';'':'','"
    ::= { hwL2uaLinkSetMngtEntry 17 }

  hwL2uaLinkMngtTable OBJECT-TYPE
    SYNTAX      SEQUENCE OF HwL2uaLinkMngtEntry
    MAX-ACCESS  not-accessible
    STATUS      current
    DESCRIPTION
      "
      This table is used to config L2UA link.
      The index of this table is hwL2uaLinkNo.
      "
    ::= { hwIASSigtranObjects 2 }

  hwL2uaLinkMngtEntry OBJECT-TYPE
    SYNTAX      HwL2uaLinkMngtEntry
    MAX-ACCESS  not-accessible
    STATUS      current
    DESCRIPTION
      "
      This table is used to config L2UA link.
      The index of this entry is hwL2uaLinkNo.
      "
    INDEX    {
              hwL2uaLinkNo
             }
    ::= { hwL2uaLinkMngtTable 1 }

  HwL2uaLinkMngtEntry ::=
    SEQUENCE
    {
      hwL2uaLinkNo	Integer32,
      hwL2uaLinkLinkSetNo	Integer32,
      hwL2uaLinkLocalPort	Integer32,
      hwL2uaLinkLocalIpaddr	IpAddress,
      hwL2uaLinkRemotePort	Integer32,
      hwL2uaLinkRemoteIpaddr1	IpAddress,
      hwL2uaLinkRemoteIpaddr2	IpAddress,
      hwL2uaLinkMaxInStreamNum	Integer32,
      hwL2uaLinkMaxOutStreamNum	Integer32,
      hwL2uaLinkActiveStandbyFlag	INTEGER,
      hwL2uaLinkLockFlag    INTEGER,
      hwL2uaLinkUsedInStreamNum	Integer32,
      hwL2uaLinkUsedOutStreamNum	Integer32,
      hwL2uaLinkSctpAssocId	Integer32,
      hwL2uaLinkOperState	INTEGER,
      hwL2uaLinkCongestState	INTEGER,
      hwL2uaLinkMaintainOper	INTEGER,
      hwL2uaLinkRowStatus	RowStatus,
      hwL2uaLinkWithMedGwyCtrlIdx Integer32,
      hwL2uaLinkPriority          Integer32,
      hwL2uaLinkLockStatus  INTEGER,
      hwL2uaLinkLocalIpaddrDhcpClientIndex  Integer32,
      hwL2uaLinkLocalIpDnyAddrName   OCTET STRING
    }

  hwL2uaLinkNo OBJECT-TYPE
    SYNTAX      Integer32(0..15)
    MAX-ACCESS  not-accessible
    STATUS      current
    DESCRIPTION
        "
        Link No.
        "
    ::= { hwL2uaLinkMngtEntry 1 }

  hwL2uaLinkLinkSetNo OBJECT-TYPE
    SYNTAX      Integer32(0..15)
    MAX-ACCESS  read-write
    STATUS      current
    DESCRIPTION
        "
        Link set No.
        "
    ::= { hwL2uaLinkMngtEntry 2 }

  hwL2uaLinkLocalPort OBJECT-TYPE
    SYNTAX      Integer32(1..65534)
    MAX-ACCESS  read-write
    STATUS      current
    DESCRIPTION
        "
        Local port number
        "
    ::= { hwL2uaLinkMngtEntry 3 }

  hwL2uaLinkLocalIpaddr OBJECT-TYPE
    SYNTAX      IpAddress
    MAX-ACCESS  read-write
    STATUS      current
    DESCRIPTION
        "
        Local IP address
        "
    ::= { hwL2uaLinkMngtEntry 4 }

  hwL2uaLinkRemotePort OBJECT-TYPE
    SYNTAX      Integer32(1..65534)
    MAX-ACCESS  read-write
    STATUS      current
    DESCRIPTION
        "
          Remote port number
        "
    ::= { hwL2uaLinkMngtEntry 5 }

  hwL2uaLinkRemoteIpaddr1 OBJECT-TYPE
    SYNTAX      IpAddress
    MAX-ACCESS  read-write
    STATUS      current
    DESCRIPTION
        "
        Remote IP address 1
        "
    ::= { hwL2uaLinkMngtEntry 6 }

  hwL2uaLinkRemoteIpaddr2 OBJECT-TYPE
    SYNTAX      IpAddress
    MAX-ACCESS  read-write
    STATUS      current
    DESCRIPTION
        "
        Remote IP address 2
        "
    ::= { hwL2uaLinkMngtEntry 7 }

  hwL2uaLinkMaxInStreamNum OBJECT-TYPE
    SYNTAX      Integer32(-1|2..1025)
    MAX-ACCESS  read-write
    STATUS      current
    DESCRIPTION
        "
        Maximum number of inbound streams.
        -1 means the IUA link is configurated with DHCP but the vlan IP isn't gained by DHCP.
        "
    ::= { hwL2uaLinkMngtEntry 8 }

  hwL2uaLinkMaxOutStreamNum OBJECT-TYPE
    SYNTAX      Integer32(-1|2..1025)
    MAX-ACCESS  read-write
    STATUS      current
    DESCRIPTION
        "
        Maximum number of outbound streams.
        -1 means the IUA link is configurated with DHCP but the vlan IP isn't gained by DHCP.
        "
    ::= { hwL2uaLinkMngtEntry 9 }

  hwL2uaLinkActiveStandbyFlag OBJECT-TYPE
    SYNTAX      INTEGER{active(1),  -- active
                        standby(2), -- standby
                        null(-1)    -- null
                        }
    MAX-ACCESS  read-only
    STATUS      current
    DESCRIPTION
        "
        Active and standby flag.
        Options:
        1. active(1)-indicates that the Active and standby flag is active
        2. standby(2)-indicates that the Active and standby flag is standby
        3. null(-1)-indicates that the Active and standby flag is invalid
        Display -1 when the vlanid can't get Local IP in dhcp mode.
        "
    ::= { hwL2uaLinkMngtEntry 10 }

  hwL2uaLinkLockFlag OBJECT-TYPE
    SYNTAX      INTEGER{lock(1),  -- locked
                        unlock(2) -- unlocked
                        }
    MAX-ACCESS  read-write
    STATUS      current
    DESCRIPTION
        "
        IUA Link maintenance lock flag.
        Options:
        1. lock(1)-indicates that the IUA Link maintenance lock flag is active
        2. unlock(2)-indicates that the IUA Link maintenance lock flag is standby
        "
    ::= { hwL2uaLinkMngtEntry 11 }

  hwL2uaLinkUsedInStreamNum OBJECT-TYPE
    SYNTAX      Integer32(-1|0..1024)
    MAX-ACCESS  read-only
    STATUS      current
    DESCRIPTION
        "
         Number of inbound streams used currently
         -1 indicates that the number is invalid
        "
    ::= { hwL2uaLinkMngtEntry 12 }

  hwL2uaLinkUsedOutStreamNum OBJECT-TYPE
    SYNTAX      Integer32(-1|0..1024)
    MAX-ACCESS  read-only
    STATUS      current
    DESCRIPTION
        "
         Number of outbound streams used currently
         -1 indicates that the number is invalid
        "
    ::= { hwL2uaLinkMngtEntry 13 }

  hwL2uaLinkSctpAssocId OBJECT-TYPE
    SYNTAX      Integer32(-1|1..16)
    MAX-ACCESS  read-only
    STATUS      current
    DESCRIPTION
        "
         SCTP association ID that the L2UA link corresponds to
         -1 means there is no SCTP association.
        "
    ::= { hwL2uaLinkMngtEntry 14 }

  hwL2uaLinkOperState OBJECT-TYPE
    SYNTAX      INTEGER{unestablish(1), -- unestablished
                        establish(2),   -- established
                        inactive(3),    -- inactive
                        active(4)       -- active
                        }
    MAX-ACCESS  read-only
    STATUS      current
    DESCRIPTION
        "
        Link status.
        Options:
        1. unestablish(1)-indicates that the Link status is active
        2. establish(2)-indicates that the Link status is standby
        3. inactive(3)-indicates that the Link status is inactive
        4. active(4)-indicates that the Link status is active
        "
    ::= { hwL2uaLinkMngtEntry 15 }

  hwL2uaLinkCongestState OBJECT-TYPE
    SYNTAX      INTEGER{uncongest(1),congest(2),null(-1)}
    MAX-ACCESS  read-only
    STATUS      current
    DESCRIPTION
        "
        Congestion state.
        Options:
        1. uncongest(1) -not congested
        2. congest(2)   -congested
        3. null(-1)     -null
        Display -1 when the vlanid can't get Local IP in dhcp mode.
        "
    ::= { hwL2uaLinkMngtEntry 16 }

  hwL2uaLinkMaintainOper OBJECT-TYPE
    SYNTAX      INTEGER{lock(1),unlock(2),reset(3),null(-1)}
    MAX-ACCESS  read-write
    STATUS      current
    DESCRIPTION
        "
        Link maintenance operation.
        Options:
        1. lock(1)   -indicates that the link maintenance operation is Lock
        2. unlock(2) -indicates that the link maintenance operation is Unlock
        3. reset(3)  -indicates that the link status is Reset
        4. null(-1)  -indicates that the link maintenance operation is invalid
        "
    ::= { hwL2uaLinkMngtEntry 17 }

  hwL2uaLinkRowStatus OBJECT-TYPE
    SYNTAX      RowStatus
    MAX-ACCESS  read-write
    STATUS      current
    DESCRIPTION
        "
        Row status
        "
    ::= { hwL2uaLinkMngtEntry 18 }

  hwL2uaLinkWithMedGwyCtrlIdx OBJECT-TYPE
    SYNTAX      Integer32(-1|0..1)
    MAX-ACCESS  read-write
    STATUS      current
    DESCRIPTION
        "
        Config IUA Link jiont work with witch MGC.
        0:  Primary MGC.
        1:  Secondary MGC.
        -1 means this parameter is not configed.

        "
    ::= { hwL2uaLinkMngtEntry 19 }

  hwL2uaLinkPriority OBJECT-TYPE
    SYNTAX      Integer32(0..15)
    MAX-ACCESS  read-write
    STATUS      current
    DESCRIPTION
        "
        Is available when the working mode of the link set is Load-share.
        In Over ride mode, this parameter can be read, but no use.

        Default:0
        "
    ::= { hwL2uaLinkMngtEntry 20 }

  hwL2uaLinkLockStatus OBJECT-TYPE
    SYNTAX      INTEGER{unlock(1),         -- unlocked
                        servicelock(2),    -- locked cause to newwork
                        maintenancelock(3), -- locked cause to local operation such as locking
                        null(-1)            -- invalid local IP
                        }
    MAX-ACCESS  read-only
    STATUS      current
    DESCRIPTION
        "
        IUA Link current Lock State:
        Options:
        1. unlock(1)-indicates that the Current IUA Link not locked
        2. servicelock(2)-indicates that the Current IUA Link was locked for joint work with MGC
        3. maintenancelock(3)-indicates that the Current IUA Link was locked by maintenance operation
        Adminlock have pripority over autolock.
        4. display -1 when the vlanid can't get Local IP in dhcp mode.
        "
    ::= { hwL2uaLinkMngtEntry 21 }

    hwL2uaLinkLocalIpaddrDhcpClientIndex OBJECT-TYPE
    SYNTAX      Integer32(1..4093|-1)
    MAX-ACCESS  read-write
    STATUS      current
    DESCRIPTION
         "
         Dhcp L2ua vlan id.
         The valid value is 1..4093,if the value is -1, the static signal ip will be used.
         "
    ::= { hwL2uaLinkMngtEntry 22 }

    hwL2uaLinkLocalIpDnyAddrName OBJECT-TYPE
    SYNTAX      OCTET STRING(SIZE(0..64))
    MAX-ACCESS  read-write
    STATUS      current
    DESCRIPTION
         "
         Dynamic local IP name.
         "
    ::= { hwL2uaLinkMngtEntry 23 }

  hwSctpAssocStatTable OBJECT-TYPE
    SYNTAX      SEQUENCE OF HwSctpAssocStatEntry
    MAX-ACCESS  not-accessible
    STATUS      current
    DESCRIPTION
      "
      This table is used to query statistic of a SCTP association.
      The index of this table is hwSctpAssocStatAssocId.
      "
    ::= { hwIASSigtranObjects 7 }

  hwSctpAssocStatEntry OBJECT-TYPE
    SYNTAX      HwSctpAssocStatEntry
    MAX-ACCESS  not-accessible
    STATUS      current
    DESCRIPTION
      "
      This table is used to query statistic of a SCTP association.
      The index of this entry is hwSctpAssocStatAssocId.
      "
    INDEX    {
              hwSctpAssocStatAssocId
             }
    ::= { hwSctpAssocStatTable 1 }

  HwSctpAssocStatEntry ::=
    SEQUENCE
    {
      hwSctpAssocStatAssocId	        Integer32,
      hwSctpAssocStatT1Expired	        Integer32,
      hwSctpAssocStatT2Expired	        Integer32,
      hwSctpAssocStatRetransChunks	Integer32,
      hwSctpAssocStatSendDataChunks	Integer32,
      hwSctpAssocStatRevDataChunks	Integer32,
      hwSctpAssocStatRecPackets	        Integer32,
      hwSctpAssocStatRecErrPackets	Integer32,
      hwSctpAssocStatOperStatus	        INTEGER,
      hwSctpAssocStatSentSctpPackets    Integer32
    }

  hwSctpAssocStatAssocId OBJECT-TYPE
    SYNTAX      Integer32
    MAX-ACCESS  not-accessible
    STATUS      current
    DESCRIPTION
        "
        SCTP association ID
        Constructed by Protocol-Type, MGC-index/Proxy-index,
        IUA-Link-ID/H248-Interface-ID/SIP-Interface-ID;
        Format:xyzzzzzz(Hex)
        a) x for Protocol-Type: IUA(0),H.248(1),SIP(2);
        b) y for MGC-index/Proxy-index:
            if x is IUA(0),   y fixed to 0;
            if x is H.248(1), y for MGC index;
            if x is SIP(2),   y for Proxy index;
        c) z for IUA-Link-ID/H248-Interface-ID/SIP-Interface-ID:
            if x is IUA(0),   zzzzzz for IUA LinkNo;
            if x is H.248(1), zzzzzz for H248 interface ID;
            if x is SIP(2),   zzzzzz for SIP interface ID;
        "
    ::= { hwSctpAssocStatEntry 1 }

  hwSctpAssocStatT1Expired OBJECT-TYPE
    SYNTAX      Integer32
    MAX-ACCESS  read-only
    STATUS      current
    DESCRIPTION
        "
        The expired times of the T1 timer
        "
    ::= { hwSctpAssocStatEntry 2 }

  hwSctpAssocStatT2Expired OBJECT-TYPE
    SYNTAX      Integer32
    MAX-ACCESS  read-only
    STATUS      current
    DESCRIPTION
        "
        The expired times of the T2 timer
        "
    ::= { hwSctpAssocStatEntry 3 }

  hwSctpAssocStatRetransChunks OBJECT-TYPE
    SYNTAX      Integer32
    MAX-ACCESS  read-only
    STATUS      current
    DESCRIPTION
        "
        The number of retransmitted data chunks
        "
    ::= { hwSctpAssocStatEntry 4 }

  hwSctpAssocStatSendDataChunks OBJECT-TYPE
    SYNTAX      Integer32
    MAX-ACCESS  read-only
    STATUS      current
    DESCRIPTION
        "
        The number of transmitted data chunks.
         "
    ::= { hwSctpAssocStatEntry 5 }

  hwSctpAssocStatRevDataChunks OBJECT-TYPE
    SYNTAX      Integer32
    MAX-ACCESS  read-only
    STATUS      current
    DESCRIPTION
        "
        The number of received data chunks
        "
    ::= { hwSctpAssocStatEntry 6 }

  hwSctpAssocStatRecPackets OBJECT-TYPE
    SYNTAX      Integer32
    MAX-ACCESS  read-only
    STATUS      current
    DESCRIPTION
        "
        The number of received SCTP packets
        "
    ::= { hwSctpAssocStatEntry 7 }

  hwSctpAssocStatRecErrPackets OBJECT-TYPE
    SYNTAX      Integer32
    MAX-ACCESS  read-only
    STATUS      current
    DESCRIPTION
        "
        The number of received error SCTP packets
        "
    ::= { hwSctpAssocStatEntry 8 }

  hwSctpAssocStatOperStatus OBJECT-TYPE
    SYNTAX      INTEGER{clear(1)}
    MAX-ACCESS  read-write
    STATUS      current
    DESCRIPTION
        "
        Clearing the statistics of the associations.
        Options:
        1. clear(1) -clear
        "
    ::= { hwSctpAssocStatEntry 9 }

  hwSctpAssocStatSentSctpPackets OBJECT-TYPE
    SYNTAX      Integer32
    MAX-ACCESS  read-only
    STATUS      current
    DESCRIPTION
        "
        The number of the transmitted SCTP packets
        "
    ::= { hwSctpAssocStatEntry 10 }

  hwSctpGlobalStatAssocCurEstab OBJECT-TYPE
    SYNTAX      Integer32
    MAX-ACCESS  read-only
    STATUS      current
    DESCRIPTION
      "
      The number of current associations
      "
    ::= { hwSctpGlobalStatTable 1 }

  hwSctpGlobalStatAssocActEstab OBJECT-TYPE
    SYNTAX      Integer32
    MAX-ACCESS  read-only
    STATUS      current
    DESCRIPTION
      "
      The number of associations initiated by the local end
      "
    ::= { hwSctpGlobalStatTable 2 }

  hwSctpGlobalStatAssocPassiveEstab OBJECT-TYPE
    SYNTAX      Integer32
    MAX-ACCESS  read-only
    STATUS      current
    DESCRIPTION
      "
       The number of associations initiated by the remote end
      "
    ::= { hwSctpGlobalStatTable 3 }

  hwSctpGlobalStatAssocActFail OBJECT-TYPE
    SYNTAX      Integer32
    MAX-ACCESS  read-only
    STATUS      current
    DESCRIPTION
      "
       The number of failure associations initiated by the local end
      "
    ::= { hwSctpGlobalStatTable 4 }

  hwSctpGlobalStatAssocPassiveFail OBJECT-TYPE
    SYNTAX      Integer32
    MAX-ACCESS  read-only
    STATUS      current
    DESCRIPTION
      "
      The number of failure associations initiated by the remote end
      "
    ::= { hwSctpGlobalStatTable 5 }

  hwSctpGlobalStatAssocAborted OBJECT-TYPE
    SYNTAX      Integer32
    MAX-ACCESS  read-only
    STATUS      current
    DESCRIPTION
      "
      The number of abort associations
      "
    ::= { hwSctpGlobalStatTable 6 }

  hwSctpGlobalStatAssocShutdown OBJECT-TYPE
    SYNTAX      Integer32
    MAX-ACCESS  read-only
    STATUS      current
    DESCRIPTION
      "
      The number of shutdown associations
      "
    ::= { hwSctpGlobalStatTable 7 }

  hwSctpGlobalStatRecOotb OBJECT-TYPE
    SYNTAX      Integer32
    MAX-ACCESS  read-only
    STATUS      current
    DESCRIPTION
      "
      The number of received abnormal data chunks at the local end
      "
    ::= { hwSctpGlobalStatTable 8 }

  hwSctpGlobalStatSendCtrlChunks OBJECT-TYPE
    SYNTAX      Integer32
    MAX-ACCESS  read-only
    STATUS      current
    DESCRIPTION
      "
      The number of transmitted control data chunks
      "
    ::= { hwSctpGlobalStatTable 9 }

  hwSctpGlobalStatSendOrderChunks OBJECT-TYPE
    SYNTAX      Integer32
    MAX-ACCESS  read-only
    STATUS      current
    DESCRIPTION
      "
      The number of transmitted ordered data chunks
      "
    ::= { hwSctpGlobalStatTable 10 }

  hwSctpGlobalStatSendUnorderChunks OBJECT-TYPE
    SYNTAX      Integer32
    MAX-ACCESS  read-only
    STATUS      current
    DESCRIPTION
      "
      The number of transmitted unordered data chunks
      "
    ::= { hwSctpGlobalStatTable 11 }

  hwSctpGlobalStatRecCtrlChunks OBJECT-TYPE
    SYNTAX      Integer32
    MAX-ACCESS  read-only
    STATUS      current
    DESCRIPTION
      "
      The number of received control data chunks
      "
    ::= { hwSctpGlobalStatTable 12 }

  hwSctpGlobalStatRecOrderChunks OBJECT-TYPE
    SYNTAX      Integer32
    MAX-ACCESS  read-only
    STATUS      current
    DESCRIPTION
      "
       The number of received ordered data chunks
      "
    ::= { hwSctpGlobalStatTable 13 }

  hwSctpGlobalStatRecUnorderChunks OBJECT-TYPE
    SYNTAX      Integer32
    MAX-ACCESS  read-only
    STATUS      current
    DESCRIPTION
      "
      The number of received unordered data chunks
      "
    ::= { hwSctpGlobalStatTable 14 }

  hwSctpGlobalStatRetransDataChunks OBJECT-TYPE
    SYNTAX      Integer32
    MAX-ACCESS  read-only
    STATUS      current
    DESCRIPTION
      "
      The number of retransmitted data chunks
      "
    ::= { hwSctpGlobalStatTable 15 }

  hwSctpGlobalStatFragmentedUsrMsgs OBJECT-TYPE
    SYNTAX      Integer32
    MAX-ACCESS  read-only
    STATUS      current
    DESCRIPTION
      "
      The number of fragmented user messages
      "
    ::= { hwSctpGlobalStatTable 16 }

  hwSctpGlobalStatReassembledUsrMsgs OBJECT-TYPE
    SYNTAX      Integer32
    MAX-ACCESS  read-only
    STATUS      current
    DESCRIPTION
      "
      The number of reassembled user messages
      "
    ::= { hwSctpGlobalStatTable 17 }

  hwSctpGlobalStatChecksumErrors OBJECT-TYPE
    SYNTAX      Integer32
    MAX-ACCESS  read-only
    STATUS      current
    DESCRIPTION
      "
      The number of received checksum error packets
      "
    ::= { hwSctpGlobalStatTable 18 }

  hwSctpGlobalStatSentSctpPacks OBJECT-TYPE
    SYNTAX      Integer32
    MAX-ACCESS  read-only
    STATUS      current
    DESCRIPTION
      "
       The number of the transmitted SCTP packets
      "
    ::= { hwSctpGlobalStatTable 19 }

  hwSctpGlobalStatRecvSctpPacks OBJECT-TYPE
    SYNTAX      Integer32
    MAX-ACCESS  read-only
    STATUS      current
    DESCRIPTION
      "
      The number of the received SCTP packets
      "
    ::= { hwSctpGlobalStatTable 20 }

  hwSctpGlobalStatAdminStatus OBJECT-TYPE
    SYNTAX      INTEGER{clear(1)}
    MAX-ACCESS  read-write
    STATUS      current
    DESCRIPTION
      "
       Clearing the system statistics.
       Options:
       1. clear(1) -clear
      "
    ::= { hwSctpGlobalStatTable 21 }

  hwSctpParaRtoMin OBJECT-TYPE
    SYNTAX      Integer32(10..5000)
    MAX-ACCESS  read-write
    STATUS      current
    DESCRIPTION
      "
      The minimum RTO.
      To the UA5000R15C05, this leaf can be read and written, the value range is (10..5000).
      To other products, this leaf just can be read, the default value is 1000.
      Unit: millisecond
      "
    ::= { hwSctpParaTable 1 }

  hwSctpParaRtoMax OBJECT-TYPE
    SYNTAX      Integer32(200..120000)
    MAX-ACCESS  read-write
    STATUS      current
    DESCRIPTION
      "
      The maximum RTO.
      For Mg interface, default value 3000.
      For Iua-Link, default value 60000.
      To the UA5000R15C05, the value range is (200..120000).
      To other products, the value range is (3000..90000).
      Unit: millisecond
      "
    ::= { hwSctpParaTable 2 }

  hwSctpParaRtoInit OBJECT-TYPE
    SYNTAX      Integer32(10..120000)
    MAX-ACCESS  read-write
    STATUS      current
    DESCRIPTION
      "
      The initial RTO.
      To the UA5000R15C05, the value range is (10..120000), the default value is 100.
      To other products, the value range is (1000..6000), the default value is 3000.
      Unit: millisecond
      "
    ::= { hwSctpParaTable 3 }

  hwSctpParaValidCookieLife OBJECT-TYPE
    SYNTAX      Integer32(5000..120000)
    MAX-ACCESS  read-write
    STATUS      current
    DESCRIPTION
      "
      Cookie lifecycle.
      To the UA5000R15C05, the value range is (5000..120000).
      To other products, the value range is (30000..120000).
      Default: 60000
      Unit: millisecond
      "
    ::= { hwSctpParaTable 4 }

  hwSctpParaMaxInitRetrans OBJECT-TYPE
    SYNTAX      Integer32(1..10)
    MAX-ACCESS  read-write
    STATUS      current
    DESCRIPTION
      "
      The maximum retransmit attempts of INIT
      To the UA5000R15C05, the value range is (1..10).
      To other products, the value range is (3..10).
      Default: 6
      "
    ::= { hwSctpParaTable 5 }

  hwSctpParaRtoAlpha OBJECT-TYPE
    SYNTAX      Integer32(0..100)
    MAX-ACCESS  read-write
    STATUS      current
    DESCRIPTION
      "
      Parameter of RTO Alpha
      To the UA5000R15C05, the default value is 13, the value range is (1..100).
      To other products, the default value is 12, the value range is (0..100).
      "
    ::= { hwSctpParaTable 6 }

  hwSctpParaRtoBeta OBJECT-TYPE
    SYNTAX      Integer32(0..100)
    MAX-ACCESS  read-write
    STATUS      current
    DESCRIPTION
      "
      Parameter of RTO Beta
      To the UA5000R15C05, the value range is (1..100).
      To other products, the value range is (0..100).
      Default: 25
      "
    ::= { hwSctpParaTable 7 }

  hwSctpParaAssocMaxRetrans OBJECT-TYPE
    SYNTAX      Integer32(1..16)
    MAX-ACCESS  read-write
    STATUS      current
    DESCRIPTION
      "
      The maximum retransmit attempts in a association
      To the UA5000R15C05, the value range is (1..10), the default value is 8.
      To other products, the value range is (8..16), the default value is 10.
      "
    ::= { hwSctpParaTable 8 }

  hwSctpParaPathMaxRetrans OBJECT-TYPE
    SYNTAX      Integer32(1..10)
    MAX-ACCESS  read-write
    STATUS      current
    DESCRIPTION
      "
      The maximum Retransmit attempts in a path
      To the UA5000R15C05, the value range is (1..10), the default value is 8.
      To other products, the value range is (3..8), the default value is 5.
      "
    ::= { hwSctpParaTable 9 }

  hwSctpParaNoCongestionLevel OBJECT-TYPE
    SYNTAX      Integer32(0..60)
    MAX-ACCESS  read-write
    STATUS      current
    DESCRIPTION
      "
      Parameter of no-congestion level
      To the UA5000R15C05, the value range is (1..60).
      To other products, the value range is (0..60).
      Default: 40
      "

    ::= { hwSctpParaTable 10 }

  hwSctpParaLowCongestionLevel OBJECT-TYPE
    SYNTAX      Integer32(50..80)
    MAX-ACCESS  read-write
    STATUS      current
    DESCRIPTION
      "
      Parameter of low-congestion level.
      Default: 60
      "

    ::= { hwSctpParaTable 11 }

  hwSctpParaHighCongestionLevel OBJECT-TYPE
    SYNTAX      Integer32(70..100)
    MAX-ACCESS  read-write
    STATUS      current
    DESCRIPTION
      "
      Parameter of high-congestion level.
      Default: 80
      "

    ::= { hwSctpParaTable 12 }

  hwSctpParaHbInterval OBJECT-TYPE
    SYNTAX      Integer32(1000..300000)
    MAX-ACCESS  read-write
    STATUS      current
    DESCRIPTION
      "
      Heartbeat interval.
      To the UA5000R15C05, the value range is (1000..300000), the default value is 3000.
      To other products, the value range is (2000..120000), the default value is 30000.
      Unit: millisecond
      "
    ::= { hwSctpParaTable 13 }

  hwSctpParaSendChecksum OBJECT-TYPE
    SYNTAX      INTEGER{no(1),yes(2)}
    MAX-ACCESS  read-write
    STATUS      current
    DESCRIPTION
      "
      Sending the checksum.
      Options:
      1. no(1) -indicates that the checksum is not Sending
      2. yes(2) -indicates that the checksum is Sending
      Default: 2
      "

    ::= { hwSctpParaTable 14 }

  hwSctpParaRecvChecksum OBJECT-TYPE
    SYNTAX      INTEGER{no(1),yes(2)}
    MAX-ACCESS  read-write
    STATUS      current
    DESCRIPTION
      "
      Receiving the checksum.
      Options:
      1. no(1) -indicates that the checksum is not Receiving
      2. yes(2) -indicates that the checksum is Receiving
      Default: 2
      "

    ::= { hwSctpParaTable 15 }

  hwSctpParaChecksumArith OBJECT-TYPE
    SYNTAX      INTEGER{adler32(1),crc32(2)}
    MAX-ACCESS  read-write
    STATUS      current
    DESCRIPTION
      "
      Checksum algorithm.
      Options:
      1. adler32(1) -indicates that Checksum algorithm is ADLER32
      2. crc32(2) -indicates that Checksum algorithm is CRC32
      Default: 2
      "

    ::= { hwSctpParaTable 16 }

  hwSctpParaSACKPolicy OBJECT-TYPE
    SYNTAX      Integer32(0..2)
    MAX-ACCESS  read-write
    STATUS      current
    DESCRIPTION
      "
      SACK policy: 0-NoTimer; 1-Timer; 2-Commix.
      Default: 2
      "

    ::= { hwSctpParaTable 17 }

  hwSctpParaSACKPeriod OBJECT-TYPE
    SYNTAX      Integer32(20..500)
    MAX-ACCESS  read-write
    STATUS      current
    DESCRIPTION
      "
      SACK period.
      Default: 20
      Unit: millisecond
      "

    ::= { hwSctpParaTable 18 }

    hwSctpParaSACKFrquency OBJECT-TYPE
    SYNTAX      Integer32(1..5)
    MAX-ACCESS  read-write
    STATUS      current
    DESCRIPTION
      "
      Parameter of SACK frequency
      Default: 1
      "

    ::= { hwSctpParaTable 19 }

    hwSctpParaMTU OBJECT-TYPE
    SYNTAX      Integer32(68..64000)
    MAX-ACCESS  read-write
    STATUS      current
    DESCRIPTION
      "
      Parameter of MTU size.
      Default: 1500
      "

    ::= { hwSctpParaTable 20 }

  hwIuaVersionString OBJECT-TYPE
    SYNTAX      OCTET STRING(SIZE (0..255))
    MAX-ACCESS  read-only
    STATUS      current
    DESCRIPTION
      "
       The version of the L2UA protocol
      "
    ::= { hwL2uaVersionTable 1 }



  hwSctpVersionString OBJECT-TYPE
    SYNTAX      OCTET STRING(SIZE (0..255))
    MAX-ACCESS  read-only
    STATUS      current
    DESCRIPTION
      "
      SCTP version
      "
    ::= { hwSctpVersionTable 1 }

 hwSctpAssocInfoTable OBJECT-TYPE
    SYNTAX      SEQUENCE OF HwSctpAssocInfoEntry
    MAX-ACCESS  not-accessible
    STATUS      current
    DESCRIPTION
      "
      This table is used to query infomation of a SCTP association.
      The index of this table is hwSctpAssocId.
      "
    ::= { hwIASSigtranObjects 12 }

  hwSctpAssocInfoEntry OBJECT-TYPE
    SYNTAX      HwSctpAssocInfoEntry
    MAX-ACCESS  not-accessible
    STATUS      current
    DESCRIPTION
      "
      This table is used to query infomation of a SCTP association.
      The index of this entry is hwSctpAssocId.
      "
    INDEX    {
              hwSctpAssocId
             }
    ::= { hwSctpAssocInfoTable 1 }

  HwSctpAssocInfoEntry ::=
    SEQUENCE
    {
      hwSctpAssocId                     Integer32,
      hwSctpAssocState                  INTEGER,
      hwSctpAssocType                   INTEGER,
      hwSctpAssocApplId                 Integer32,
      hwSctpAssocLocalPort              Integer32,
      hwSctpAssocRemotePort             Integer32,
      hwSctpAssocLocalIPaddr            IpAddress,
      hwSctpAssocRemoteIPaddr           IpAddress,
      hwSctpAssocAllowHB                INTEGER,
      hwSctpAssocLocalRwnd              Unsigned32,
      hwSctpAssocRemoteRwnd             Unsigned32,
      hwSctpAssocUnfirmDataChunks       Integer32,
      hwSctpAssocRemoteIP1addr          IpAddress,
      hwSctpAssocRemoteIP1State         INTEGER,
      hwSctpAssocRemoteIP1WaitAck       Integer32,
      hwSctpAssocRemoteIP1Cwnd          Integer32,
      hwSctpAssocRemoteIP1Unfirm        Integer32,
      hwSctpAssocRemoteIP1Rto           Integer32,
      hwSctpAssocRemoteIP1Srtt          Integer32,
      hwSctpAssocRemoteIP1Rttvar        Integer32,
      hwSctpAssocRemoteIP1AllowHB       INTEGER,
      hwSctpAssocRemoteIP2addr          IpAddress,
      hwSctpAssocRemoteIP2State         INTEGER,
      hwSctpAssocRemoteIP2WaitAck       Integer32,
      hwSctpAssocRemoteIP2Cwnd          Integer32,
      hwSctpAssocRemoteIP2Unfirm        Integer32,
      hwSctpAssocRemoteIP2Rto           Integer32,
      hwSctpAssocRemoteIP2Srtt          Integer32,
      hwSctpAssocRemoteIP2Rttvar        Integer32,
      hwSctpAssocRemoteIP2AllowHB       INTEGER
    }

  hwSctpAssocId OBJECT-TYPE
    SYNTAX      Integer32(1..16)
    MAX-ACCESS  not-accessible
    STATUS      current
    DESCRIPTION
        "
        SCTP association ID
        Constructed by Protocol-Type, MGC-index/Proxy-index,
        IUA-Link-ID/H248-Interface-ID/SIP-Interface-ID;
        Format:xyzzzzzz(Hex)
        a) x for Protocol-Type: IUA(0),H.248(1),SIP(2);
        b) y for MGC-index/Proxy-index:
            if x is IUA(0),   y fixed to 0;
            if x is H.248(1), y for MGC index;
            if x is SIP(2),   y for Proxy index;
        c) z for IUA-Link-ID/H248-Interface-ID/SIP-Interface-ID:
            if x is IUA(0),   zzzzzz for IUA LinkNo;
            if x is H.248(1), zzzzzz for H248 interface ID;
            if x is SIP(2),   zzzzzz for SIP interface ID;
        "
    ::= { hwSctpAssocInfoEntry 1 }

  hwSctpAssocState OBJECT-TYPE
    SYNTAX      INTEGER{closed(1),cookiewait(2),cookieecho(3),established(4),shutdownpending(5),shutdownsent(6),shutdownreceived(7),shutdownacksent(8)}
    MAX-ACCESS  read-only
    STATUS      current
    DESCRIPTION
      "
       Current status of the association
       Options:
       1. closed(1) -indicates that the Current status of the association is closed
       2. cookiewait(2) -indicates that the Current status of the association is down
       3. cookieecho(3) -indicates that the Current status of the association is cookieecho
       4. established(4) -indicates that the Current status of the association is established
       5. shutdownpending(5) -indicates that the Current status of the association is shutdownpending
       6. shutdownsent(6) -indicates that the Current status of the association is shutdownsent
       7. shutdownreceived(7) -indicates that the Current status of the association is shutdownreceived
       8. shutdownacksent(8) -indicates that the Current status of the association is shutdownacksent
      "
    ::= { hwSctpAssocInfoEntry 2 }

  hwSctpAssocType OBJECT-TYPE
    SYNTAX      INTEGER{client(1),server(2)}
    MAX-ACCESS  read-only
    STATUS      current
    DESCRIPTION
      "
       Association type.
       Options:
       1. client(1) -indicates that the Association type is Client
       2. server(2) -indicates that the Association type is Server
      "

    ::= { hwSctpAssocInfoEntry 3 }

  hwSctpAssocApplId OBJECT-TYPE
    SYNTAX      Integer32(0..15)
    MAX-ACCESS  read-only
    STATUS      current
    DESCRIPTION
      "
      The upper-layer user ID
      "
    ::= { hwSctpAssocInfoEntry 4 }

  hwSctpAssocLocalPort OBJECT-TYPE
    SYNTAX      Integer32(1..65534)
    MAX-ACCESS  read-only
    STATUS      current
    DESCRIPTION
      "
       Local port number
      "
    ::= { hwSctpAssocInfoEntry 5 }

  hwSctpAssocRemotePort OBJECT-TYPE
    SYNTAX      Integer32(1..65534)
    MAX-ACCESS  read-only
    STATUS      current
    DESCRIPTION
      "
      Remote port number
      "
    ::= { hwSctpAssocInfoEntry 6 }

  hwSctpAssocLocalIPaddr OBJECT-TYPE
    SYNTAX      IpAddress
    MAX-ACCESS  read-only
    STATUS      current
    DESCRIPTION
      "
      The current local primary IP address
      "
    ::= { hwSctpAssocInfoEntry 7 }

  hwSctpAssocRemoteIPaddr OBJECT-TYPE
    SYNTAX      IpAddress
    MAX-ACCESS  read-only
    STATUS      current
    DESCRIPTION
      "
       The current remote primary IP address
      "
    ::= { hwSctpAssocInfoEntry 8 }

  hwSctpAssocAllowHB OBJECT-TYPE
    SYNTAX      INTEGER{no(1),yes(2)}
    MAX-ACCESS  read-only
    STATUS      current
    DESCRIPTION
      "
      Whether transmitting HB message.
      Options:
      1. no(1) -indicates not transmitting HB message
      2. yes(2) -indicates transmitting HB message
      Default: 2
      "

    ::= { hwSctpAssocInfoEntry 9 }

  hwSctpAssocLocalRwnd OBJECT-TYPE
    SYNTAX      Unsigned32(0..4294967295)
    MAX-ACCESS  read-only
    STATUS      current
    DESCRIPTION
      "
      The size of the local receiver window
      "
    ::= { hwSctpAssocInfoEntry 10 }

  hwSctpAssocRemoteRwnd OBJECT-TYPE
    SYNTAX      Unsigned32(0..4294967295)
    MAX-ACCESS  read-only
    STATUS      current
    DESCRIPTION
      "
      The size of the remote receiver window
      "
    ::= { hwSctpAssocInfoEntry 11 }

  hwSctpAssocUnfirmDataChunks OBJECT-TYPE
    SYNTAX      Integer32(0..8)
    MAX-ACCESS  read-only
    STATUS      current
    DESCRIPTION
      "
      The size of the unacknowledged data that is transmitted
      "
    ::= { hwSctpAssocInfoEntry 12 }

  hwSctpAssocRemoteIP1addr OBJECT-TYPE
    SYNTAX      IpAddress
    MAX-ACCESS  read-only
    STATUS      current
    DESCRIPTION
      "
      Remote IP address 1.
      Default: 80
      "

    ::= { hwSctpAssocInfoEntry 13 }

  hwSctpAssocRemoteIP1State OBJECT-TYPE
    SYNTAX      INTEGER{active(1),inactive(2)}
    MAX-ACCESS  read-only
    STATUS      current
    DESCRIPTION
      "
       The current status of remote IP address 1.
       Options:
       1. active(1)   -active
       2. inactive(2) -inactive
      "
    ::= { hwSctpAssocInfoEntry 14 }

  hwSctpAssocRemoteIP1WaitAck OBJECT-TYPE
    SYNTAX      Integer32(0..8)
    MAX-ACCESS  read-only
    STATUS      current
    DESCRIPTION
      "
      The number of the data blocks that is waiting for the acknowledgement by the remote SACK.
      Default: 2
      "

    ::= { hwSctpAssocInfoEntry 15 }

  hwSctpAssocRemoteIP1Cwnd OBJECT-TYPE
    SYNTAX      Integer32
    MAX-ACCESS  read-only
    STATUS      current
    DESCRIPTION
      "
      The size of the congestion window.
      Default: 2
      "

    ::= { hwSctpAssocInfoEntry 16 }

  hwSctpAssocRemoteIP1Unfirm OBJECT-TYPE
    SYNTAX      Integer32(0..8)
    MAX-ACCESS  read-only
    STATUS      current
    DESCRIPTION
      "
      The size of the unacknowledged data that is transmitted on the path.
      Default: 2
      "

    ::= { hwSctpAssocInfoEntry 17 }

  hwSctpAssocRemoteIP1Rto OBJECT-TYPE
    SYNTAX      Integer32(0..65535)
    MAX-ACCESS  read-only
    STATUS      current
    DESCRIPTION
      "
      Retransmission Time-out (ms)
      "
    ::= { hwSctpAssocInfoEntry 18 }

  hwSctpAssocRemoteIP1Srtt OBJECT-TYPE
    SYNTAX      Integer32(0..65535)
    MAX-ACCESS  read-only
    STATUS      current
    DESCRIPTION
      "
      Smoothed Round-trip Time (ms)
      "
    ::= { hwSctpAssocInfoEntry 19 }

  hwSctpAssocRemoteIP1Rttvar OBJECT-TYPE
    SYNTAX      Integer32(0..65535)
    MAX-ACCESS  read-only
    STATUS      current
    DESCRIPTION
      "
      Round-trip Time Variation (ms)
      "
    ::= { hwSctpAssocInfoEntry 20 }

  hwSctpAssocRemoteIP1AllowHB OBJECT-TYPE
    SYNTAX      INTEGER{no(1),yes(2)}
    MAX-ACCESS  read-only
    STATUS      current
    DESCRIPTION
      "
      Whether HB can be transmitted from this address.
      Options:
      1. no(1) -indicates that the HB can't be transmitted from this address
      2. yes(2) -indicates that the HB can be transmitted from this address
      "
    ::= { hwSctpAssocInfoEntry 21 }

  hwSctpAssocRemoteIP2addr OBJECT-TYPE
    SYNTAX      IpAddress
    MAX-ACCESS  read-only
    STATUS      current
    DESCRIPTION
      "
      Remote IP address 2.
      Default: 80
      "

    ::= { hwSctpAssocInfoEntry 22 }

  hwSctpAssocRemoteIP2State OBJECT-TYPE
    SYNTAX      INTEGER{active(1),inactive(2)}
    MAX-ACCESS  read-only
    STATUS      current
    DESCRIPTION
      "
      The current status of remote IP address 2
      Options:
      1. active(1) -indicates that the current status of remote IP address 2 is active
      2. inactive(2) -indicates that the current status of remote IP address 2 is inactive
      "
    ::= { hwSctpAssocInfoEntry 23 }

  hwSctpAssocRemoteIP2WaitAck OBJECT-TYPE
    SYNTAX      Integer32(-1|0..8)
    MAX-ACCESS  read-only
    STATUS      current
    DESCRIPTION
      "
      The number of the data that is waiting for the acknowledgement by the remote SACK.
      -1 returns by GET means associate with IP2 does not exist.
      Default: 2
      "

    ::= { hwSctpAssocInfoEntry 24 }

  hwSctpAssocRemoteIP2Cwnd OBJECT-TYPE
    SYNTAX      Integer32(-1|0..8)
    MAX-ACCESS  read-only
    STATUS      current
    DESCRIPTION
      "
      The size of the congestion window.
      -1 returns by GET means associate with IP2 does not exist.
      Default: 2
      "

    ::= { hwSctpAssocInfoEntry 25 }

  hwSctpAssocRemoteIP2Unfirm OBJECT-TYPE
    SYNTAX      Integer32(-1|0..8)
    MAX-ACCESS  read-only
    STATUS      current
    DESCRIPTION
      "
      The size of the unacknowledged data that is transmitted on the path.
      -1 returns by GET means associate with IP2 does not exist.
      Default: 2
      "

    ::= { hwSctpAssocInfoEntry 26 }

  hwSctpAssocRemoteIP2Rto OBJECT-TYPE
    SYNTAX      Integer32(-1|0..65535)
    MAX-ACCESS  read-only
    STATUS      current
    DESCRIPTION
      "
      Retransmission Time-out(ms)
      -1 returns by GET means associate with IP2 does not exist.
      "
    ::= { hwSctpAssocInfoEntry 27 }

  hwSctpAssocRemoteIP2Srtt OBJECT-TYPE
    SYNTAX      Integer32(-1|0..65535)
    MAX-ACCESS  read-only
    STATUS      current
    DESCRIPTION
      "
      Smoothed Round-trip Time (ms)
      -1 returns by GET means associate with IP2 does not exist.
     "
    ::= { hwSctpAssocInfoEntry 28 }

  hwSctpAssocRemoteIP2Rttvar OBJECT-TYPE
    SYNTAX      Integer32(-1|0..65535)
    MAX-ACCESS  read-only
    STATUS      current
    DESCRIPTION
      "
      Round-trip Time Variation (ms)
      -1 returns by GET means associate with IP2 does not exist.
      "
    ::= { hwSctpAssocInfoEntry 29 }

  hwSctpAssocRemoteIP2AllowHB OBJECT-TYPE
    SYNTAX      INTEGER{no(1),yes(2)}
    MAX-ACCESS  read-only
    STATUS      current
    DESCRIPTION
      "
      Whether HB can be sent from this address.
      Options:
      1. no(1) -indicates that the HB can't be sent from this address
      2. yes(2) -indicates that the HB can be sent from this address
      "
    ::= { hwSctpAssocInfoEntry 30 }


    hwIsdnIuaDuaErrStatsThresholdCfgTable OBJECT-TYPE
     SYNTAX      SEQUENCE OF HwIsdnIuaDuaErrStatsThresholdCfgEntry
     MAX-ACCESS  not-accessible
     STATUS      current
     DESCRIPTION
       "
       Configuration table of L2UA IUA/DUA link error statistic threshold.
       The index of this table is hwIsdnIuaDuaErrLinkNoIndex.
       "
     ::= { hwIASSigtranObjects 13 }

    hwIsdnIuaDuaErrStatsThresholdCfgEntry OBJECT-TYPE
    SYNTAX      HwIsdnIuaDuaErrStatsThresholdCfgEntry
    MAX-ACCESS  not-accessible
    STATUS      current
    DESCRIPTION
       "
       Configuration table of L2UA IUA/DUA link error statistic threshold.
       The index of this entry is hwIsdnIuaDuaErrLinkNoIndex.
       "
    INDEX    {
              hwIsdnIuaDuaErrLinkNoIndex
             }
    ::= { hwIsdnIuaDuaErrStatsThresholdCfgTable 1 }

    HwIsdnIuaDuaErrStatsThresholdCfgEntry ::=
    SEQUENCE
    {
      	hwIsdnIuaDuaErrLinkNoIndex                              Integer32,
      	hwIsdnIuaProtocolErrAlarmThreshold        	        Integer32,
	hwIsdnDuaProtocolErrAlarmThreshold    	                Integer32
    }

    hwIsdnIuaDuaErrLinkNoIndex OBJECT-TYPE
    SYNTAX      Integer32
    MAX-ACCESS  not-accessible
    STATUS      current
    DESCRIPTION
        "
        Link index.
        "
    ::= { hwIsdnIuaDuaErrStatsThresholdCfgEntry 1 }

    hwIsdnIuaProtocolErrAlarmThreshold     OBJECT-TYPE
    SYNTAX      Integer32(0..25)
    MAX-ACCESS  read-write
    STATUS      current
    DESCRIPTION
        "
        Threshold of IUA error alarm.
        "
    DEFVAL { 10 }
    ::= { hwIsdnIuaDuaErrStatsThresholdCfgEntry 2 }

    hwIsdnDuaProtocolErrAlarmThreshold     OBJECT-TYPE
    SYNTAX      Integer32(0..25)
    MAX-ACCESS  read-write
    STATUS      current
    DESCRIPTION
        "
        Threshold of DUA error alarm.
        "
    DEFVAL { 10 }
    ::= { hwIsdnIuaDuaErrStatsThresholdCfgEntry 3 }

     hwMifSctpCfgParaTable    OBJECT-TYPE
     SYNTAX      SEQUENCE OF HwMifSctpCfgParaEntry
     MAX-ACCESS  not-accessible
     STATUS      current
     DESCRIPTION
       "
       This table is used to config SCTP protocol parameters of a SCTP association.
       The indexes of this table are hwMifSctpCfgParaProtoType and hwMifSctpCfgParaInterfaceId.
       "
    ::= { hwIASSigtranObjects 14 }

    hwMifSctpCfgParaEntry OBJECT-TYPE
    SYNTAX      HwMifSctpCfgParaEntry
    MAX-ACCESS  not-accessible
    STATUS      current
    DESCRIPTION
       "
       This table is used to config SCTP protocol parameters of a SCTP association.
       The indexes of this entry are hwMifSctpCfgParaProtoType and hwMifSctpCfgParaInterfaceId.
       "
    INDEX    {
              hwMifSctpCfgParaProtoType,
              hwMifSctpCfgParaInterfaceId
             }
    ::= { hwMifSctpCfgParaTable 1 }

    HwMifSctpCfgParaEntry ::=
    SEQUENCE
    {
      	hwMifSctpCfgParaProtoType               Integer32,
      	hwMifSctpCfgParaInterfaceId             Integer32,
        hwMifSctpCfgParaMaxInStreamNum          Integer32,
        hwMifSctpCfgParaMaxOutStreamNum         Integer32,
        hwMifSctpCfgParaRtoMin                  Integer32,
        hwMifSctpCfgParaRtoMax                  Integer32,
        hwMifSctpCfgParaRtoInit                 Integer32,
        hwMifSctpCfgParaValidCookieLife         Integer32,
        hwMifSctpCfgParaMaxInitRetrans          Integer32,
        hwMifSctpCfgParaRtoAlpha                Integer32,
        hwMifSctpCfgParaRtoBeta                 Integer32,
        hwMifSctpCfgParaAssocMaxRetrans         Integer32,
        hwMifSctpCfgParaPathMaxRetrans          Integer32,
        hwMifSctpCfgParaNoCongestionLevel       Integer32,
        hwMifSctpCfgParaLowCongestionLevel      Integer32,
        hwMifSctpCfgParaHighCongestionLevel     Integer32,
        hwMifSctpCfgParaHbInterval              Integer32,
        hwMifSctpCfgParaSendChecksum            INTEGER,
        hwMifSctpCfgParaRecvChecksum            INTEGER,
        hwMifSctpCfgParaChecksumArith           INTEGER
    }

    hwMifSctpCfgParaProtoType   OBJECT-TYPE
    SYNTAX      Integer32(0..2)
    MAX-ACCESS  not-accessible
    STATUS      current
    DESCRIPTION
        "
        Protocol Type:
        IUA(0),H.248(1),SIP(2);
        "
    ::= { hwMifSctpCfgParaEntry 1 }

    hwMifSctpCfgParaInterfaceId OBJECT-TYPE
    SYNTAX      Integer32
    MAX-ACCESS  not-accessible
    STATUS      current
    DESCRIPTION
        "
        IUA-Link-ID/H248-Interface-ID/SIP-Interface-ID:
        if Protocol Type is IUA(0),   this parameter for IUA LinkNo;
        if Protocol Type is H.248(1), this parameter for H248 interface ID;
        if Protocol Type is SIP(2),   this parameter for SIP interface ID;
        "
    ::= { hwMifSctpCfgParaEntry 2 }

    hwMifSctpCfgParaMaxInStreamNum     OBJECT-TYPE
    SYNTAX      Integer32(2..1024)
    MAX-ACCESS  read-write
    STATUS      current
    DESCRIPTION
        "
        Maximum number of inbound streams.
        "
    DEFVAL { 33 }
    ::= { hwMifSctpCfgParaEntry 3 }

    hwMifSctpCfgParaMaxOutStreamNum  OBJECT-TYPE
    SYNTAX      Integer32(2..1024)
    MAX-ACCESS  read-write
    STATUS      current
    DESCRIPTION
        "
        Maximum number of outbound streams
        "
    DEFVAL { 33 }
    ::= { hwMifSctpCfgParaEntry 4 }

    hwMifSctpCfgParaRtoMin OBJECT-TYPE
    SYNTAX      Integer32
    MAX-ACCESS  read-only
    STATUS      current
    DESCRIPTION
      "
      The minimum RTO.
      Default: 1000
      Unit: millisecond
      "

    ::= { hwMifSctpCfgParaEntry 5 }

    hwMifSctpCfgParaRtoMax OBJECT-TYPE
    SYNTAX      Integer32(3000..90000)
    MAX-ACCESS  read-write
    STATUS      current
    DESCRIPTION
      "
      The maximum RTO.
      Default: 3000(Mg interface),60000(Iua-Link)
      Unit: millisecond
      "
    DEFVAL      { 60000 }
    ::= { hwMifSctpCfgParaEntry 6 }

    hwMifSctpCfgParaRtoInit OBJECT-TYPE
    SYNTAX      Integer32(1000..90000)
    MAX-ACCESS  read-write
    STATUS      current
    DESCRIPTION
      "
      The initial RTO.
      Unit: millisecond
      "
    DEFVAL      { 1000 }
    ::= { hwMifSctpCfgParaEntry 7 }

    hwMifSctpCfgParaValidCookieLife OBJECT-TYPE
    SYNTAX      Integer32(30000..120000)
    MAX-ACCESS  read-write
    STATUS      current
    DESCRIPTION
      "
      Cookie lifecycle.
      Unit: millisecond
      "
    DEFVAL      { 60000 }
    ::= { hwMifSctpCfgParaEntry 8 }

    hwMifSctpCfgParaMaxInitRetrans OBJECT-TYPE
    SYNTAX      Integer32(3..10)
    MAX-ACCESS  read-write
    STATUS      current
    DESCRIPTION
      "
       The maximum retransmit attempts of INIT
      "
    DEFVAL      { 8 }
    ::= { hwMifSctpCfgParaEntry 9 }

    hwMifSctpCfgParaRtoAlpha OBJECT-TYPE
    SYNTAX      Integer32(1..100)
    MAX-ACCESS  read-write
    STATUS      current
    DESCRIPTION
      "
       Parameter of RTO Alpha
      "
    DEFVAL      { 12 }
    ::= { hwMifSctpCfgParaEntry 10 }

    hwMifSctpCfgParaRtoBeta OBJECT-TYPE
    SYNTAX      Integer32(1..100)
    MAX-ACCESS  read-write
    STATUS      current
    DESCRIPTION
      "
      Parameter of RTO Beta
      "
    DEFVAL      { 25 }
    ::= { hwMifSctpCfgParaEntry 11 }

    hwMifSctpCfgParaAssocMaxRetrans OBJECT-TYPE
    SYNTAX      Integer32(8..16)
    MAX-ACCESS  read-write
    STATUS      current
    DESCRIPTION
      "
      The maximum retransmit attempts in a association
      "
    DEFVAL      { 10 }
    ::= { hwMifSctpCfgParaEntry 12 }

    hwMifSctpCfgParaPathMaxRetrans OBJECT-TYPE
    SYNTAX      Integer32(3..8)
    MAX-ACCESS  read-write
    STATUS      current
    DESCRIPTION
      "
      The maximum Retransmit attempts in a path
      "
    DEFVAL      { 5 }
    ::= { hwMifSctpCfgParaEntry 13 }

    hwMifSctpCfgParaNoCongestionLevel OBJECT-TYPE
    SYNTAX      Integer32(1..60)
    MAX-ACCESS  read-write
    STATUS      current
    DESCRIPTION
      "
      Parameter of no-congestion level
      "
    DEFVAL      { 40 }
    ::= { hwMifSctpCfgParaEntry 14 }

    hwMifSctpCfgParaLowCongestionLevel OBJECT-TYPE
    SYNTAX      Integer32(50..80)
    MAX-ACCESS  read-write
    STATUS      current
    DESCRIPTION
      "
      Parameter of low-congestion level
      "
    DEFVAL      { 60 }
    ::= { hwMifSctpCfgParaEntry 15 }

    hwMifSctpCfgParaHighCongestionLevel OBJECT-TYPE
    SYNTAX      Integer32(70..100)
    MAX-ACCESS  read-write
    STATUS      current
    DESCRIPTION
      "
      Parameter of high-congestion level
      "
    DEFVAL      { 80 }
    ::= { hwMifSctpCfgParaEntry 16 }

    hwMifSctpCfgParaHbInterval OBJECT-TYPE
    SYNTAX      Integer32(2000..120000)
    MAX-ACCESS  read-write
    STATUS      current
    DESCRIPTION
      "
      Heartbeat interval.
      For Mg interface, 10000~120000 is valid. For Iua-Link, 2000~120000 is valid.
      Default: 10000(Mg interface),30000(Iua-Link)
      Unit: millisecond
      "
    DEFVAL      { 30000 }
    ::= { hwMifSctpCfgParaEntry 17 }

    hwMifSctpCfgParaSendChecksum OBJECT-TYPE
    SYNTAX      INTEGER{no(1),yes(2)}
    MAX-ACCESS  read-only
    STATUS      current
    DESCRIPTION
      "
      Sending the checksum.
      Options:
      1. no(1) -indicates that the checksum is not Sending
      2. yes(2) -indicates that the checksum is Sending
      "
    ::= { hwMifSctpCfgParaEntry 18 }

    hwMifSctpCfgParaRecvChecksum OBJECT-TYPE
    SYNTAX      INTEGER{no(1),yes(2)}
    MAX-ACCESS  read-only
    STATUS      current
    DESCRIPTION
      "
      Receiving the checksum.
      Options:
      1. no(1) -indicates that the checksum is not Receiving
      2. yes(2) -indicates that the checksum is Receiving
      "
    ::= { hwMifSctpCfgParaEntry 19 }

    hwMifSctpCfgParaChecksumArith OBJECT-TYPE
    SYNTAX      INTEGER{adler32(1),crc32(2)}
    MAX-ACCESS  read-write
    STATUS      current
    DESCRIPTION
      "
      Checksum algorithm.
      Options:
      1. adler32(1) -indicates that Checksum algorithm is ADLER32
      2. crc32(2) -indicates that Checksum algorithm is CRC32
      "
    DEFVAL      { 2 }
    ::= { hwMifSctpCfgParaEntry 20 }



     hwMifSctpRunningParaTable    OBJECT-TYPE
     SYNTAX      SEQUENCE OF HwMifSctpRunningParaEntry
     MAX-ACCESS  not-accessible
     STATUS      current
     DESCRIPTION
       "
       This table is used to query current running SCTP protocol parameter.
       The indexes of this table are hwMifSctpRunningParaProtoType and hwMifSctpRunningParaInterfaceId.
       "
    ::= { hwIASSigtranObjects 15 }

    hwMifSctpRunningParaEntry OBJECT-TYPE
    SYNTAX      HwMifSctpRunningParaEntry
    MAX-ACCESS  not-accessible
    STATUS      current
    DESCRIPTION
       "
       This table is used to query current running SCTP protocol parameter.
       The indexes of this entry are hwMifSctpRunningParaProtoType and hwMifSctpRunningParaInterfaceId.
       "
    INDEX    {
              hwMifSctpRunningParaProtoType,
              hwMifSctpRunningParaInterfaceId
             }
    ::= { hwMifSctpRunningParaTable 1 }

    HwMifSctpRunningParaEntry ::=
    SEQUENCE
    {
      	hwMifSctpRunningParaProtoType        	                Integer32,
      	hwMifSctpRunningParaInterfaceId                         Integer32,
	hwMifSctpRunningParaMaxInStreamNum    	                Integer32,
	hwMifSctpRunningParaMaxOutStreamNum                     Integer32,
	hwMifSctpRunningParaRtoMin                              Integer32,
	hwMifSctpRunningParaRtoMax				Integer32,
	hwMifSctpRunningParaRtoInit				Integer32,
	hwMifSctpRunningParaValidCookieLife			Integer32,
	hwMifSctpRunningParaMaxInitRetrans			Integer32,
	hwMifSctpRunningParaRtoAlpha				Integer32,
	hwMifSctpRunningParaRtoBeta				Integer32,
	hwMifSctpRunningParaAssocMaxRetrans			Integer32,
	hwMifSctpRunningParaPathMaxRetrans			Integer32,
	hwMifSctpRunningParaNoCongestionLevel			Integer32,
	hwMifSctpRunningParaLowCongestionLevel			Integer32,
	hwMifSctpRunningParaHighCongestionLevel		        Integer32,
	hwMifSctpRunningParaHbInterval				Integer32,
	hwMifSctpRunningParaSendChecksum			INTEGER,
	hwMifSctpRunningParaRecvChecksum			INTEGER,
	hwMifSctpRunningParaChecksumArith			INTEGER
    }

    hwMifSctpRunningParaProtoType   OBJECT-TYPE
    SYNTAX      Integer32(0..2)
    MAX-ACCESS  not-accessible
    STATUS      current
    DESCRIPTION
        "
        Protocol Type:
        IUA(0),H.248(1),SIP(2);
        "
    ::= { hwMifSctpRunningParaEntry 1 }

    hwMifSctpRunningParaInterfaceId OBJECT-TYPE
    SYNTAX      Integer32
    MAX-ACCESS  not-accessible
    STATUS      current
    DESCRIPTION
        "
        IUA-Link-ID/H248-Interface-ID/SIP-Interface-ID:
        if Protocol Type is IUA(0),   this parameter for IUA LinkNo;
        if Protocol Type is H.248(1), this parameter for H248 interface ID;
        if Protocol Type is SIP(2),   this parameter for SIP interface ID;
        "
    ::= { hwMifSctpRunningParaEntry 2 }

    hwMifSctpRunningParaMaxInStreamNum     OBJECT-TYPE
    SYNTAX      Integer32(2..33)
    MAX-ACCESS  read-only
    STATUS      current
    DESCRIPTION
        "
        Maximum number of inbound streams.
        Default: 33
        "

    ::= { hwMifSctpRunningParaEntry 3 }

    hwMifSctpRunningParaMaxOutStreamNum  OBJECT-TYPE
    SYNTAX      Integer32(2..33)
    MAX-ACCESS  read-only
    STATUS      current
    DESCRIPTION
        "
        Maximum number of outbound streams.
        Default: 33
        "

    ::= { hwMifSctpRunningParaEntry 4 }

    hwMifSctpRunningParaRtoMin OBJECT-TYPE
    SYNTAX      Integer32
    MAX-ACCESS  read-only
    STATUS      current
    DESCRIPTION
      "
      The minimum RTO.
      Default: 1000
      Unit: millisecond
      "

    ::= { hwMifSctpRunningParaEntry 5 }

    hwMifSctpRunningParaRtoMax OBJECT-TYPE
    SYNTAX      Integer32(3000..90000)
    MAX-ACCESS  read-only
    STATUS      current
    DESCRIPTION
      "
      The maximum RTO.
      For Mg interface, default value 3000. For Iua-Link, default value 60000.
      Unit: millisecond
      "

    ::= { hwMifSctpRunningParaEntry 6 }

    hwMifSctpRunningParaRtoInit OBJECT-TYPE
    SYNTAX      Integer32(1000..6000)
    MAX-ACCESS  read-only
    STATUS      current
    DESCRIPTION
      "
      The initial RTO.
      Default: 1000
      Unit: millisecond
      "

    ::= { hwMifSctpRunningParaEntry 7 }

    hwMifSctpRunningParaValidCookieLife OBJECT-TYPE
    SYNTAX      Integer32(30000..120000)
    MAX-ACCESS  read-only
    STATUS      current
    DESCRIPTION
      "
      Cookie lifecycle.
      Default: 60000
      Unit: millisecond
      "

    ::= { hwMifSctpRunningParaEntry 8 }

    hwMifSctpRunningParaMaxInitRetrans OBJECT-TYPE
    SYNTAX      Integer32(3..10)
    MAX-ACCESS  read-only
    STATUS      current
    DESCRIPTION
      "
       The maximum retransmit attempts of INIT.
       Default: 8
      "

    ::= { hwMifSctpRunningParaEntry 9 }

    hwMifSctpRunningParaRtoAlpha OBJECT-TYPE
    SYNTAX      Integer32(1..100)
    MAX-ACCESS  read-only
    STATUS      current
    DESCRIPTION
      "
       Parameter of RTO Alpha.
       Default: 12
      "

    ::= { hwMifSctpRunningParaEntry 10 }

    hwMifSctpRunningParaRtoBeta OBJECT-TYPE
    SYNTAX      Integer32(1..100)
    MAX-ACCESS  read-only
    STATUS      current
    DESCRIPTION
      "
      Parameter of RTO Beta.
      Default: 25
      "

    ::= { hwMifSctpRunningParaEntry 11 }

    hwMifSctpRunningParaAssocMaxRetrans OBJECT-TYPE
    SYNTAX      Integer32(8..16)
    MAX-ACCESS  read-only
    STATUS      current
    DESCRIPTION
      "
      The maximum retransmit attempts in a association.
      Default: 10
      "

    ::= { hwMifSctpRunningParaEntry 12 }

    hwMifSctpRunningParaPathMaxRetrans OBJECT-TYPE
    SYNTAX      Integer32(3..8)
    MAX-ACCESS  read-only
    STATUS      current
    DESCRIPTION
      "
      The maximum Retransmit attempts in a path.
      Default: 5
      "

    ::= { hwMifSctpRunningParaEntry 13 }

    hwMifSctpRunningParaNoCongestionLevel OBJECT-TYPE
    SYNTAX      Integer32(1..60)
    MAX-ACCESS  read-only
    STATUS      current
    DESCRIPTION
      "
      Parameter of no-congestion level
      Default: 40
      "

    ::= { hwMifSctpRunningParaEntry 14 }

    hwMifSctpRunningParaLowCongestionLevel OBJECT-TYPE
    SYNTAX      Integer32(50..80)
    MAX-ACCESS  read-only
    STATUS      current
    DESCRIPTION
      "
      Parameter of low-congestion level
      Default: 60
      "

    ::= { hwMifSctpRunningParaEntry 15 }

    hwMifSctpRunningParaHighCongestionLevel OBJECT-TYPE
    SYNTAX      Integer32(70..100)
    MAX-ACCESS  read-only
    STATUS      current
    DESCRIPTION
      "
      Parameter of high-congestion level.
      Default: 80
      "

    ::= { hwMifSctpRunningParaEntry 16 }

    hwMifSctpRunningParaHbInterval OBJECT-TYPE
    SYNTAX      Integer32(2000..120000)
    MAX-ACCESS  read-only
    STATUS      current
    DESCRIPTION
      "
      Heartbeat interval.
      For Mg interface, default value 10000.
      Default: 30000
      Unit: millisecond
      "

    ::= { hwMifSctpRunningParaEntry 17 }

    hwMifSctpRunningParaSendChecksum OBJECT-TYPE
    SYNTAX      INTEGER{no(1),yes(2)}
    MAX-ACCESS  read-only
    STATUS      current
    DESCRIPTION
      "
      Sending the checksum.
      Options:
      1. no(1) -indicates that the checksum is not Sending
      2. yes(2) -indicates that the checksum is Sending
      Default: 2
      "

    ::= { hwMifSctpRunningParaEntry 18 }

    hwMifSctpRunningParaRecvChecksum OBJECT-TYPE
    SYNTAX      INTEGER{no(1),yes(2)}
    MAX-ACCESS  read-only
    STATUS      current
    DESCRIPTION
      "
      Receiving the checksum.
      Options:
      1. no(1) -indicates that the checksum is not Receiving
      2. yes(2) -indicates that the checksum is Receiving
      Default: 2
      "

    ::= { hwMifSctpRunningParaEntry 19 }

    hwMifSctpRunningParaChecksumArith OBJECT-TYPE
    SYNTAX      INTEGER{adler32(1),crc32(2)}
    MAX-ACCESS  read-only
    STATUS      current
    DESCRIPTION
      "
      Checksum algorithm.
      Options:
      1. adler32(1) -indicates that Checksum algorithm is ADLER32
      2. crc32(2) -indicates that Checksum algorithm is CRC32
      Default: 2
      "

    ::= { hwMifSctpRunningParaEntry 20 }

    hwSctpGlobalParaTable OBJECT IDENTIFIER ::= { hwIASSigtranObjects 16 }


    hwSctpGlobalParaSendChecksum OBJECT-TYPE
    SYNTAX      INTEGER{no(1),yes(2)}
    MAX-ACCESS  read-write
    STATUS      current
    DESCRIPTION
      "
      Sending the checksum:
      Options:
      1. no(1) -indicates that the checksum is not Sending
      2. yes(2) -indicates that the checksum is Sending
      Default: 2
      "
    ::= { hwSctpGlobalParaTable 1 }

    hwSctpGlobalParaRecvChecksum OBJECT-TYPE
    SYNTAX      INTEGER{no(1),yes(2)}
    MAX-ACCESS  read-write
    STATUS      current
    DESCRIPTION
      "
      Receiving the checksum.
      Options:
      1. no(1) -indicates that the checksum is not Receiving
      2. yes(2) -indicates that the checksum is Receiving
      Default: 2
      "
    ::= { hwSctpGlobalParaTable 2 }

 ------  /* Start hwIASSigtranL2uaAlarmTraps */

    hwIASSigtranL2uaLinkUnestTrap NOTIFICATION-TYPE
    OBJECTS  { hwL2uaLinkNo }
    STATUS      current
    DESCRIPTION
        "
        This notification indicates that the L2UA link is not established.
        "
    ::= { hwIASSigtranL2uaAlarmTraps 0 1 }

    hwIASSigtranL2uaLinkActiveTrap NOTIFICATION-TYPE
    OBJECTS  { hwL2uaLinkNo }
    STATUS      current
    DESCRIPTION
        "
        This notification indicates that the L2UA link is actived.
        "
    ::= { hwIASSigtranL2uaAlarmTraps 0 2 }

    hwIASSigtranL2uaLinksetDownTrap NOTIFICATION-TYPE
    OBJECTS  { hwL2uaLinkSetNo }
    STATUS      current
    DESCRIPTION
        "
        This notification indicates that the L2UA linkset is not activated.
        "
    ::= { hwIASSigtranL2uaAlarmTraps 0 3 }

    hwIASSigtranL2uaLinksetActiveTrap NOTIFICATION-TYPE
    OBJECTS  { hwL2uaLinkSetNo }
    STATUS      current
    DESCRIPTION
        "
        This notification indicates that the L2UA linkset is activated.
        "
    ::= { hwIASSigtranL2uaAlarmTraps 0 4 }


 ------  /*  End  hwIASSigtranL2uaAlarmTraps */

 ------  /* Start hwIASSigtranTrapsVbOids */

 ------  /*  End  hwIASSigtranTrapsVbOids */

END
