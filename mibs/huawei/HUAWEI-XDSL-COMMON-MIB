-- ============================================================================
-- Copyright (C) 2017 by  HUAWEI TECHNOLOGIES. All rights reserved.
-- Description:  This MIB is used for defining Huawei's XDSL common management MIB
--               objects, which provides XDSL management NMS interfaces.
-- Reference:
-- Version: V1.35
-- ============================================================================

    HUAWEI-XDSL-COMMON-MIB DEFINITIONS ::= BEGIN
        IMPORTS
            ifIndex
                FROM IF-MIB
             hwFrameIndex, hwSlotIndex,hwSubslotIndex,hwPortIndex,hwConfigChangeIP
                FROM HUAWEI-DEVICE-MIB
            Integer32, Unsigned32, Gauge32, Counter32, OBJECT-TYPE, NOTIFICATION-TYPE, MODULE-IDENTITY
                FROM SNMPv2-SMI
            RowStatus, PhysAddress, DateAndTime,TEXTUAL-CONVENTION
                FROM SNMPv2-TC
            huaweiUtility
                FROM HUAWEI-MIB
            hwAlarmId,hwAlarmTime,hwAlarmSn,hwCauseId,hwTrapType
                FROM HUAWEI-TC-MIB;

        hwXdslCommon MODULE-IDENTITY
           LAST-UPDATED "201711240000Z"
            ORGANIZATION "Huawei Technologies Co.,Ltd."
            CONTACT-INFO
                         "Huawei Industrial Base
                          Bantian, Longgang
                          Shenzhen 518129
                          People's Republic of China
                          Website: http://www.huawei.com
                          Email: support@huawei.com
                         "
            DESCRIPTION  "This MIB is used for defining Huawei's XDSL common management MIB objects,
                          which provides XDSL management NMS interfaces.
                         "
	 --  Revision history

	    REVISION     "201711240000Z"
        DESCRIPTION  "V1.35, Add the definition of the table hwXdslPortRateChangeReportConfig."

            REVISION     "201701120000Z"
        DESCRIPTION  "V1.34, Modified the description of leaf node hwXdslGfastCableOptimizationCableType."

	    REVISION     "201611020000Z"
        DESCRIPTION  "V1.33, Add leaf node hwXdslAttndrStandardMethod."

	    REVISION     "201609260000Z"
        DESCRIPTION  "V1.32, Modified the description of the node hwXdslBypassRelayMode."

	    REVISION     "201609140000Z"
        DESCRIPTION  "V1.31, Add the definition of the table hwXdslGfastCableOptimizationConfig."

	    REVISION     "201608160000Z"
        DESCRIPTION  "V1.30, Modified the description of the node hwXdslPortReactivateAfterPortResetRecoveryTrap."

	    REVISION     "201606200000Z"
        DESCRIPTION  "V1.29, Add leaf node hwXdslBypassRelayModeConfig,hwXdslBypassRelayMode."

	    REVISION     "201606140000Z"
        DESCRIPTION  "V1.28, Modify the description of the hwXdslGfastPowerAutoAllocation."

	    REVISION     "201606130000Z"
        DESCRIPTION  "V1.27, Add value dyingGasp(3) and disconnect(4) for hwXdslReversePoweringStatus and modify the description.
                             Add leaf node hwXdslReversePoweringCurrent,hwXdslReversePoweringVoltage,hwXdslReversePoweringPower."

	    REVISION     "201606050000Z"
        DESCRIPTION  "V1.26, Add the definition of the table hwXdslGfastPowerAutoAllocationConfig."

	    REVISION     "201603280000Z"
        DESCRIPTION  "V1.25, Add the definition of the table hwXdslGfastFastRestartConfig."

        REVISION     "201510280000Z"
        DESCRIPTION  "V1.24, Add the definition of the table hwXdslCellheadCompressConfig."

        REVISION     "201509070000Z"
        DESCRIPTION  "V1.23, add value xdslTR129LineConfTemplate(39),xdslTR129LineConfProf(40) and
                      xdslTR129ChConfProfile(41) for hwXdslAutoDeleteProfUnusedProfType."

        REVISION     "201505100000Z"
        DESCRIPTION  "V1.22, Modify value fastProfile(38) to   fastTddProfile(38)
                      for hwXdslAutoDeleteProfUnusedProfType and modify the description."

        REVISION     "201503180000Z"
        DESCRIPTION  "V1.21, Modify the SYNTAX INTEGER name of hwXdslAutoDeleteProfUnusedProfType."

        REVISION     "201412010000Z"
        DESCRIPTION  "V1.20, Add value fastAlarmConfTemplate(35), fastAlarmConfProfile(36), fastChAlarmConfProfile(37), fastProfile(38)
                      for hwXdslAutoDeleteProfUnusedProfType and modify the description."

        REVISION     "201411190000Z"
        DESCRIPTION  "V1.19, Add definition of the table hwXdslPortFrequentRetrainControlDefaultCfg.
	                  Add leaf node hwXdslPortFrequentRetrainControlFurtherControlCfg, hwXdslPortFrequentRetrainControlFurtherControlDetectPeriod
		              hwXdslPortFrequentRetrainControlFurtherControlPolicy, hwXdslPortFrequentRetrainControFurtherControllState,
		              hwXdslPortFrequentRetrainControlRemove.
		              Add the definition of the table hwXdslUpboEleM0CalculationConfig."

        REVISION     "201411120000Z"
        DESCRIPTION  "V1.18, Modify the description of the node hwXdslBoardConnectorMapping.
                             Modify the description of the node hwXdslPortAutoResetControl.
                             Add definition of the table hwXdslProfileTransmodeAuto."

        REVISION     "201408190000Z"
        DESCRIPTION  "V1.17, Add the definition of the table: hwXdslBoardConnectorMappingConfig."

        REVISION     "201408100000Z"
        DESCRIPTION  "V1.16, Add leaf node hwXdslPortUnableToUpAfterPortAutoResetAlarmTrap and hwXdslPortReactivateAfterPortResetRecoveryTrap."

        REVISION     "201406300000Z"
        DESCRIPTION  "V1.15, Modify the version of the mib."

        REVISION     "201406120000Z"
        DESCRIPTION  "V1.14, Add the definition of the table hwXdslADSLPtmDataPathConfig.
	                    Delete leaf node hwXdslPortAutoResetDetectPeriod, hwXdslPortAutoResetDetectTimes in table hwXdslPortAutoResetConfig.
	                    Modify the leaf node name from hwXdslReversePoweringFaultPortDeactivate to hwXdslReversePoweringFaultCauseActivefailure.
	                    Modify the description of the node hwXdslReversePoweringMode, hwXdslReversePoweringStatus, hwXdslPortReversePoweringFaultAlarmTrap,
	                    hwXdslPortReversePoweringNormalAlarmTrap.
	                   "

        REVISION     "201405150000Z"
        DESCRIPTION  "V1.13, changes in this revision:
	                    Add the definition of the table: hwXdslReversePoweringGlobalConfig, hwXdslReversePoweringLineTable.
	                    Add the definition of the node: hwXdslPortReversePoweringFaultAlarmTrap, hwXdslPortReversePoweringNormalAlarmTrap.
	                    Add hwXdslPortAutoResetDetectPeriod and hwXdslPortAutoResetDetectTimes.
	                    Add value vopSOSConfProf(34) for hwXdslAutoDeleteProfUnusedProfType and modify the description.
	                    Add the definition of the table: hwXdslPortAutoResetConfig.
	                   "

        REVISION     "201404020000Z"
        DESCRIPTION  "V1.12, changes in this revision:
	                    Add leaf node hwXdslPortStatusInfoCollectRequestId in table hwXdslPortStatusInfoCollectTable.
	                    Add the definition of the node: hwXdslPortStatusInfoCollectRequestId in hwXdslPortStatusInfoCollectTrap.
	                   "

        REVISION     "201402240000Z"
        DESCRIPTION  "V1.11, changes in this revision:
	                    Delete ifType import.
	                    Add value nonvectoring(4) for hwXdslPortFrequentRetrainControlPolicy and modify the description.
	                   "

        REVISION     "201312180000Z"
        DESCRIPTION  "V1.11, changes in this revision:
                      Add the definition of the table: hwXdslPortStatusInfoCollectTable.
                      Add hwXdslPortStatusInfoCollectTrap.
                      Add hwXdslPortStatusInfoCollectResult in hwXdslTrapsVbOids.
                     "

        REVISION     "201306260000Z"
        DESCRIPTION  "V1.10, Add leaf node hwXdslPortFrequentRetrainControlState, hwXdslPortFrequentRetrainControlRemainingTime
	   		              in table hwXdslPortFrequentRetrainControlTable for getting frequent retrain state.
	                   "

        REVISION     "201209021000Z"
        DESCRIPTION  "V1.09, Add the definition of the table hwXdslADSL1INPAdaptionConfig.
	                   "

        REVISION     "201207021000Z"
        DESCRIPTION  "V1.08, Add the definition of the table hwXdslPortFrequentRetrainControlTable.
	                    Add the definition of the table hwXdslAttndrConfig.
	                   "

        REVISION     "201105030000Z"
        DESCRIPTION  "V1.07, add value shdslLineConfProfile(31), shdslAlarmConfProfile(32), vopINMConfProf(33) for
                         hwXdslAutoDeleteProfUnusedProfType and modify the description.
                        "
        REVISION     "201009300000Z"
        DESCRIPTION  "V1.06, add leaf node hwXdslSeltTestStartResult in table hwAdslTrapsVbOids for trap optimization.
                         Add the definition of the trap node: hwXdslSeltStartResultTrap.
                       "

        REVISION     "201009150000Z"
        DESCRIPTION  "V1.05, add leaf node hwAllChActDataRateUs, hwAllChActDataRateDs
                      for the sum of net date rates that all bearer channels operating at.
                     "

        REVISION     "201008160000Z"
        DESCRIPTION  "V1.04, Modify data type of hwXdslDynamicCollectTime for trap notify."

        REVISION     "201007270000Z"
        DESCRIPTION  "V1.03, Add the definition of the trap node: hwAdslProfIDChangeTrap, hwXdslAutoDeactivateLackLicensesAlarmTrap, hwXdslPortActRateLowerThresholdAlarmTrap.
                         Add leaf node hwAdslProfIDType, hwXdslProfName, hwXdslPortActualUpRate, hwXdslPortActualDownRate in table hwAdslTrapsVbOids for trap optimization.
                         Add the definition of the trap node: hwXdslProfDeleteTrap.
                         Add leaf node hwXdslDelProfIndex, hwXdslProfName, hwXdslPortActualUpRate, hwXdslPortActualDownRate in table hwAdslTrapsVbOids for trap optimization."

        REVISION     "201003250000Z"
        DESCRIPTION  "V1.02, add leaf node hwXdslAutoDeleteProfUnusedProfType, hwvdslAutoDeleteProfUnusedOperType
                      for deleting unused profile.
                     "

        REVISION     "201003110000Z"
        DESCRIPTION  "V1.01, add the MIB for xDSL common use.
                         "

        REVISION     "201001240000Z"
        DESCRIPTION  "V1.00, Initial version."

            ::= { huaweiUtility 148 }

        hwXdslCommonMib OBJECT IDENTIFIER ::= { hwXdslCommon 1 }
        hwXdslAutoDeleteProfUnused OBJECT IDENTIFIER ::= { hwXdslCommonMib 1 }
        hwXdslAttndrConfig OBJECT IDENTIFIER ::= { hwXdslCommonMib 4 }
        hwXdslADSL1INPAdaptionConfig OBJECT IDENTIFIER ::= { hwXdslCommonMib 5 }
        hwXdslPortAutoResetConfig OBJECT IDENTIFIER ::= { hwXdslCommonMib 7 }
        hwXdslReversePoweringGlobalConfig OBJECT IDENTIFIER ::= { hwXdslCommonMib 8 }
        hwXdslADSLPtmDataPathConfig OBJECT IDENTIFIER ::= { hwXdslCommonMib 10 }
        hwXdslBoardConnectorMappingConfig OBJECT IDENTIFIER ::= { hwXdslCommonMib 11 }
        hwXdslProfileTransmodeAuto OBJECT IDENTIFIER ::= { hwXdslCommonMib 12 }
        hwXdslPortFrequentRetrainControlDefaultCfg OBJECT IDENTIFIER ::= { hwXdslCommonMib 13 }
        hwXdslUpboEleM0CalculationConfig OBJECT IDENTIFIER ::= { hwXdslCommonMib 14 }
        hwXdslCellheadCompressConfig OBJECT IDENTIFIER ::= { hwXdslCommonMib 15 }
        hwXdslGfastFastRestartConfig OBJECT IDENTIFIER ::= { hwXdslCommonMib 16 }
        hwXdslGfastPowerAutoAllocationConfig OBJECT IDENTIFIER ::= { hwXdslCommonMib 17 }
        hwXdslBypassRelayModeConfig OBJECT IDENTIFIER ::= { hwXdslCommonMib 18 }
        hwXdslGfastCableOptimizationConfig OBJECT IDENTIFIER ::= { hwXdslCommonMib 19 }
        hwXdslPortRateChangeReportConfig OBJECT IDENTIFIER ::= { hwXdslCommonMib 20 }
	hwXdslTrapsVbOids OBJECT IDENTIFIER ::= { hwXdslCommon 2 }
        hwXdslTraps  OBJECT IDENTIFIER ::= { hwXdslCommon 3 }
        hwXdslCommonTraps  OBJECT IDENTIFIER ::= { hwXdslTraps 1 }
        hwXdslCommonTrapsPrefix  OBJECT IDENTIFIER ::= { hwXdslCommonTraps 0 }
        hwXdslAlarmTraps  OBJECT IDENTIFIER ::= { hwXdslTraps 2 }
        hwXdslAlarmTrapsPrefix  OBJECT IDENTIFIER ::= { hwXdslAlarmTraps 0 }

 -- hwXdslCommonMib

        hwXdslAutoDeleteProfUnusedProfType   OBJECT-TYPE
            SYNTAX INTEGER
                {
                vdsl2LineConfTemplate(1),
                vdsl2LineConfProf(2),
                vdsl2ChConfProfile(3),
                vdsl2LineAlarmConfTemplate(4),
                vdsl2LineAlarmConfProfile(5),
                vdsl2ChAlarmConfProfile(6),
                vdsl2ServProf(7),
                vdsl2SpectrumProf(8),
                vdsl2DpboProf(9),
                vdsl2UpboProf(10),
                vdsl2NoiseMarginProf(11),
                vdsl2DelayInpProf(12),
                vopDataRateConfProf(13),
                vopLineSpectrumConfProf(14),
                vopUPBOConfProf(15),
                vopDPBOConfProf(16),
                vopRFIConfProf(17),
                vopSNRMarginConfProf(18),
                vopINPDelayConfProf(19),
                vopVirtualNoiseConfProf(20),
                vopModeSpecificPSDConfProf(21),
                adsl2LineConfTemplate(22),
                adsl2LineConfProf(23),
                adsl2ChConfProfile(24),
                adsl2LineAlarmConfTemplate(25),
                adsl2LineAlarmConfProfile(26),
                adsl2ChAlarmConfProfile(27),
                adslLineConfProfile(28),
                adslLineAlarmConfProfile(29),
                adslLineExtConfProfile(30),
                shdslLineConfProfile(31),
                shdslAlarmConfProfile(32),
                vopINMConfProf(33),
                vopSOSConfProf(34),
                fastAlarmConfTemplate(35),
                fastAlarmConfProfile(36),
                fastChAlarmConfProfile(37),
                fastTddProfile(38),
                xdslTR129LineConfTemplate(39),
                xdslTR129LineConfProf(40),
                xdslTR129ChConfProfile(41),
                invalidValue(-1)
                }
            MAX-ACCESS  read-write
            STATUS      current
            DESCRIPTION
                "The profile type of deleting unused XDSL profile.
                 Options:
                 1. vdsl2LineConfTemplate(1)        - Vdsl line template
                 2. vdsl2LineConfProf(2)            - Vdsl line profile
                 3. vdsl2ChConfProfile(3)           - Vdsl channel profile
                 4. vdsl2LineAlarmConfTemplate(4)   - Vdsl line alarm template
                 5. vdsl2LineAlarmConfProfile(5)    - Vdsl line alarm profile
                 6. vdsl2ChAlarmConfProfile(6)      - Vdsl channel alarm profile
                 7. vdsl2ServProf(7)                - Vdsl service profile (TI mode)
                 8. vdsl2SpectrumProf(8)            - Vdsl spectrum profile (TI mode)
                 9. vdsl2DpboProf(9)                - Vdsl DPBO profile (TI mode)
                 10. vdsl2UpboProf(10)              - Vdsl UPBO profile (TI mode)
                 11. vdsl2NoiseMarginProf(11)       - Vdsl noise-margin profile (TI mode)
                 12. vdsl2DelayInpProf(12)          - Vdsl delay-inp profile (TI mode)
                 13. vopDataRateConfProf(13)        - Xdsl data rate profile (TR165 mode)
                 14. vopLineSpectrumConfProf(14)    - Xdsl line spectrum profile (TR165 mode)
                 15. vopUPBOConfProf(15)            - Xdsl UPBO profile (TR165 mode)
                 16. vopDPBOConfProf(16)            - Xdsl DPBO profile (TR165 mode)
                 17. vopRFIConfProf(17)             - Xdsl RFI profile (TR165 mode)
                 18. vopSNRMarginConfProf(18)       - Xdsl SNR margin profile (TR165 mode)
                 19. vopINPDelayConfProf(19)        - Xdsl INP delay profile (TR165 mode)
                 20. vopVirtualNoiseConfProf(20)    - Xdsl virtual noise profile (TR165 mode)
                 21. vopModeSpecificPSDConfProf(21) - Xdsl mode specific PSD profile (TR165 mode)
                 22. adsl2LineConfTemplate(22)      - Adsl line template (RFC4706 mode)
                 23. adsl2LineConfProf(23)          - Adsl line profile (RFC4706 mode)
                 24. adsl2ChConfProfile(24)         - Adsl channel profile (RFC4706 mode)
                 25. adsl2LineAlarmConfTemplate(25) - Adsl line alarm template (RFC4706 mode)
                 26. adsl2LineAlarmConfProfile(26)  - Adsl line alarm profile (RFC4706 mode)
                 27. adsl2ChAlarmConfProfile(27)    - Adsl channel alarm profile (RFC4706 mode)
                 28. adslLineConfProfile(28)        - Adsl line profile (RFC2662 mode)
                 29. adslLineAlarmConfProfile(29)   - Adsl line alarm profile (RFC2662 mode)
                 30. adslLineExtConfProfile(30)     - Adsl line ext profile (RFC2662 mode)
                 31. shdslLineConfProfile(31)       - Shdsl line profile
                 32. shdslAlarmConfProfile(32)      - Shdsl alarm profile
                 33. vopINMConfProf(33)             - Xdsl INM profile (TR165 mode)
                 34. vopSOSConfProf(34)             - Xdsl SOS profile (TR165 mode)
                 35. fastAlarmConfTemplate(35)      - G.fast alarm template
                 36. fastAlarmConfProfile(36)       - G.fast alarm profile
                 37. fastChAlarmConfProfile(37)     - G.fast channel alarm profile
                 38. fastTddProfile(38)             - G.fast tdd-profile
                 39. xdslTR129LineConfTemplate(39)   - Xdsl TR129 line template
                 40. xdslTR129LineConfProf(40)       - Xdsl TR129 line profile
                 41. xdslTR129ChConfProfile(41)      - Xdsl TR129 channel profile
                 42. invalidValue(-1)               - Invalid value
                "

            ::= { hwXdslAutoDeleteProfUnused 1 }

        hwXdslAutoDeleteProfUnusedOperType  OBJECT-TYPE
            SYNTAX INTEGER
                {
                first(1),
                all(2),
                invalidValue(-1)
                }
            MAX-ACCESS  read-write
            STATUS      current
            DESCRIPTION
                "The operation type of deleting unused xDSL profile.
                 Options:
                 1. first(1)         - Delete the first unused xDSL profile
                 2. all(2)           - Delete all the unused xDSL profile
                 3. invalidValue(-1) - Invalid value
                "

            ::= { hwXdslAutoDeleteProfUnused 2 }


        hwXdslLineTable  OBJECT-TYPE
            SYNTAX      SEQUENCE  OF  HwXdslLineEntry
            MAX-ACCESS  not-accessible
            STATUS      current
            DESCRIPTION
                "The table hwXdslLineTable contains status
 	         parameters of xDSL line. The index of this table is
 	         ifIndex.
                "
            ::= { hwXdslCommonMib 2 }

        hwXdslLineEntry  OBJECT-TYPE
            SYNTAX      HwXdslLineEntry
            MAX-ACCESS  not-accessible
            STATUS      current
            DESCRIPTION
                "The table hwXdslLineTable contains status
 	         parameters of xDSL line. The index of this entry is ifIndex.
                "
            INDEX  { ifIndex }
            ::= { hwXdslLineTable 1 }

        HwXdslLineEntry  ::=
            SEQUENCE {
              hwAllChActDataRateDs            Unsigned32,
              hwAllChActDataRateUs            Unsigned32
            }

        hwAllChActDataRateDs  OBJECT-TYPE
            SYNTAX      Unsigned32
            UNITS       "bits/second"
            MAX-ACCESS  read-only
            STATUS      current
            DESCRIPTION
                "The downstream actual net data rate that the bearer channel is operating
                 at, if in L0 power management state.  In L1 or L2 states, it
                 relates to the previous L0 state. This is the sum of net date rates
                 that all bearer channels operating at.
                "
            ::= { hwXdslLineEntry 1 }

        hwAllChActDataRateUs  OBJECT-TYPE
            SYNTAX      Unsigned32
            UNITS       "bits/second"
            MAX-ACCESS  read-only
            STATUS      current
            DESCRIPTION
                "The upstream actual net data rate that the bearer channel is operating
                 at, if in L0 power management state.  In L1 or L2 states, it
                 relates to the previous L0 state. This is the sum of net date rates
                 that all bearer channels operating at.
                "
            ::= { hwXdslLineEntry 2 }

        hwXdslPortFrequentRetrainControlTable  OBJECT-TYPE
            SYNTAX      SEQUENCE  OF  HwXdslPortFrequentRetrainControlEntry
            MAX-ACCESS  not-accessible
            STATUS      current
            DESCRIPTION
                "The table hwXdslPortFrequentRetrainControlTable contains information
 	         of xDSL port frequent retrain control policy.
 	         The index of this table is ifIndex.
                "
            ::= { hwXdslCommonMib 3 }

        hwXdslPortFrequentRetrainControlEntry  OBJECT-TYPE
            SYNTAX      HwXdslPortFrequentRetrainControlEntry
            MAX-ACCESS  not-accessible
            STATUS      current
            DESCRIPTION
                "The table hwXdslPortFrequentRetrainControlTable contains information
 	         of xDSL port frequent retrain control policy.
 	         The index of this entry is ifIndex.
                "
            INDEX  { ifIndex }
            ::= { hwXdslPortFrequentRetrainControlTable 1 }

        HwXdslPortFrequentRetrainControlEntry  ::=
            SEQUENCE {
              hwXdslPortFrequentRetrainControlTimes                     Unsigned32,
              hwXdslPortFrequentRetrainControlPolicy                    INTEGER,
              hwXdslPortFrequentRetrainControlPostponedTime             Unsigned32,
              hwXdslPortFrequentRetrainControlState                     INTEGER,
              hwXdslPortFrequentRetrainControlRemainingTime             Unsigned32,
              hwXdslPortFrequentRetrainControlFurtherControlCfg          INTEGER,
              hwXdslPortFrequentRetrainControlFurtherControlDetectPeriod Unsigned32,
              hwXdslPortFrequentRetrainControlFurtherControlPolicy       INTEGER,
              hwXdslPortFrequentRetrainControFurtherControllState        INTEGER,
              hwXdslPortFrequentRetrainControlRemove                    INTEGER
            }

        hwXdslPortFrequentRetrainControlTimes  OBJECT-TYPE
            SYNTAX      Unsigned32 (3..15 | 4294967295)
            MAX-ACCESS  read-write
            STATUS      current
            DESCRIPTION
                "The times that xDSL port frequent retrain.
                 The invalid value is 4294967295.
                 If board does not support the operation, the invalid value will be returned.
                "
            DEFVAL    { 5 }
            ::= { hwXdslPortFrequentRetrainControlEntry 1 }

        hwXdslPortFrequentRetrainControlPolicy  OBJECT-TYPE
            SYNTAX      INTEGER
            {
            lock(1),
            nolimit(2),
            postponed(3),
            nonvectoring(4),
            invalidValue(-1)
            }
            MAX-ACCESS  read-write
            STATUS      current
            DESCRIPTION
                "The control policy that xDSL port frequent retrain.
                 Options:
                 1. lock(1)            - The port is not allowed to go online within 15 minutes
                 2. nolimit(2)         - The port can go online without the limitation of control policies
                 3. postponed(3)       - The port can go online after a postponed time when the number of frequent
                                         resynchronizations on the port reaches the threshold
                 4. nonvectoring(4)    - If a vectoring port meets frequent retrain control policy requirements,
                                         the vectoring port is considered as a legacy port during initialization
                 5. invalidValue(-1)   - Invalid value
                "
            DEFVAL    { nolimit }
            ::= { hwXdslPortFrequentRetrainControlEntry 2 }

        hwXdslPortFrequentRetrainControlPostponedTime  OBJECT-TYPE
            SYNTAX      Unsigned32 (5..3600 | 4294967295)
            UNITS       "minute"
            MAX-ACCESS  read-write
            STATUS      current
            DESCRIPTION
                "The postponed time when control policy of xDSL port frequent retrain is postponed.
                 The invalid value is 4294967295.
                 If board does not support the operation, the invalid value will be returned.
                "
            DEFVAL    { 5 }
            ::= { hwXdslPortFrequentRetrainControlEntry 3 }

        hwXdslPortFrequentRetrainControlState  OBJECT-TYPE
            SYNTAX      INTEGER
            {
            controlled(1),
            notControlled(2)
            }
            MAX-ACCESS  read-only
            STATUS      current
            DESCRIPTION
                "The actual control state of the port.
                 When the port is not under  frequent retrain control in the current interval, the value of the
                 remaining time of the current control interval must be 4294967295.
                 Options:
                 1. controlled(1)          - The port is under the frequent retrain control in the current interval.
                 2. notControlled(2)       - The port is under the frequent retrain control in the current interval until the maunal removal of the control status
                "
            ::= { hwXdslPortFrequentRetrainControlEntry 4 }

        hwXdslPortFrequentRetrainControlRemainingTime  OBJECT-TYPE
            SYNTAX      Unsigned32 (0..3600 | 4294967295)
            UNITS       "minute"
            MAX-ACCESS  read-only
            STATUS      current
            DESCRIPTION
                "The remaining time of the current control interval, a special value 4294967295 indicates
                 there is no limit for the link currently.
                "
            ::= { hwXdslPortFrequentRetrainControlEntry 5 }

        hwXdslPortFrequentRetrainControlFurtherControlCfg   OBJECT-TYPE
            SYNTAX      INTEGER
            {
            enable(1),
            disable(2)
            }
            MAX-ACCESS  read-write
            STATUS      current
            DESCRIPTION
                "Further control policy for frequent retrain.
                 Options:
                 1. enable(1)          - Enable the further control policy for frequent retrain
                 2. disable(2)         - Disable the further control policy for frequent retrain
                "
            DEFVAL    { disable }
            ::= { hwXdslPortFrequentRetrainControlEntry 6 }

         hwXdslPortFrequentRetrainControlFurtherControlDetectPeriod  OBJECT-TYPE
            SYNTAX      Unsigned32 (1..168 | 4294967295)
            UNITS       "hour"
            MAX-ACCESS  read-write
            STATUS      current
            DESCRIPTION
                "Detection period of the further control policy for frequent retrain.
                 The invalid value is 4294967295.
                "
            ::= { hwXdslPortFrequentRetrainControlEntry 7 }

          hwXdslPortFrequentRetrainControlFurtherControlPolicy  OBJECT-TYPE
            SYNTAX      INTEGER
            {
                permanentLock(1),
                permanentNonVectoring(2),
                invalidValue(-1)
            }
            MAX-ACCESS  read-write
            STATUS      current
            DESCRIPTION
                "Further control policy for frequent retrain.
                 Options:
                 1. permanentLock(1)                 - Permanently disable activation in any mode
                 2. permanentNonVectoring(2)         - Permanently disable activation in vectoring mode
                 3. invalidValue(-1)                 - Invalid value
                "
            ::= { hwXdslPortFrequentRetrainControlEntry 8 }

        hwXdslPortFrequentRetrainControFurtherControllState  OBJECT-TYPE
            SYNTAX      INTEGER
            {
            controlled(1),
            notControlled(2)
            }
            MAX-ACCESS  read-only
            STATUS      current
            DESCRIPTION
                "Control status of the further activation.
                 Options:
                 1. controlled(1)          - The port is under the further frequent retrain control.
                 2. notControlled(2)       - The port is under the further frequent retrain control until the maunal removal of the control status.
                "
            ::= { hwXdslPortFrequentRetrainControlEntry 9 }

        hwXdslPortFrequentRetrainControlRemove  OBJECT-TYPE
            SYNTAX      INTEGER
            {
            true(1),
            false(2)
            }
            MAX-ACCESS  read-write
            STATUS      current
            DESCRIPTION
                "Remove the current frequent retrain control.
  		 If it is set to true, the control status is removed, and the system returns false upon a reading request.
                 Options:
                 1. true(1)         - Remove the current frequent retrain control
                 2. false(2)        - The system returns false upon a reading request
                "
            ::= { hwXdslPortFrequentRetrainControlEntry 10 }

        hwXdslAttndrMethod  OBJECT-TYPE
            SYNTAX  INTEGER
            {
            attndrMethod0(0),
            attndrMethod1(1),
            attndrMethod2(2)
            }
            MAX-ACCESS  read-write
            STATUS      current
            DESCRIPTION
                "This parameter specifies the method to be used for the calculation of the ATTNDR
                 in the downstream and upstream direction. The parameter can take three values 0, 1 and 2.
                 Default values: attndrMethod1.
                 Options:
                 1. attndrMethod0(0)       - The basic Attainable Net Data Rate method
                 2. attndrMethod1(1)       - The improved Attainable Net Data Rate method, If the control
                                             parameter attndr_method is set to a value of 1, the VTU-O and
                                             VTU-R shall use the impulse noise protection limit INP_min0 with
                                             value as indicated in O-TPS. If O-TPS configures for dual bearer
                                             channel mode, then the highest INP_MINn over the bearer channels
                                             shall be used 1
                 3. attndrMethod2(2)       - The improved Attainable Net Data Rate method, If the control parameter
                                             attndr_method is set to a value of 2, the VTU-O and VTU-R shall use an
                                             impulse noise protection limit INP_MIN0 = 0

                 Note:  When hwXdslAttndrStandardMethod set to no, the VTU-O will use a vendor discretionary algorithm
                        to optimize the ATTNDR.
                "
            REFERENCE    "ITU-T G.993.2, paragraph 11.4.1.1.7"
            ::= { hwXdslAttndrConfig 1 }

        hwXdslAttndrStandardMethod  OBJECT-TYPE
            SYNTAX  INTEGER
            {
            yes(1),
            no(2)
            }
            MAX-ACCESS  read-write
            STATUS      current
            DESCRIPTION
                "This parameter specifies whether ATTNDR is calculated based on attndrMethod1 and attndrMethod2 required by the G.993.2 standard.
                 Default values: no.
                 Options:
                 1. yes(1)   - ATTNDR is calculated based on attndrMethod1 and attndrMethod2 required by the G.993.2 standard.
                 2. no(2)    - ATTNDR is modified based on the calculation of attndrMethod1 and attndrMethod2 required by the G.993.2 standard.
                "
            ::= { hwXdslAttndrConfig 2 }

        hwXdslADSL1INPAdaption  OBJECT-TYPE
            SYNTAX  INTEGER
            {
            enable(1),
            disable(2)
            }
            MAX-ACCESS  read-write
            STATUS      current
            DESCRIPTION
                "Enable/Disable the global ADSL1 INP Adaption configuration. This object is defaulted disable(2).
                 This configuration will take effect after port manually reactivated or board reset.
                 Options:
                 1. enable(1)        - Enable the ADSL1 INP Adaption configuration
                 2. disable(2)       - Disable the ADSL1 INP Adaption configuration
                "
            ::= { hwXdslADSL1INPAdaptionConfig 1 }

        hwXdslPortStatusInfoCollectTable  OBJECT-TYPE
            SYNTAX      SEQUENCE  OF  HwXdslPortStatusInfoCollectEntry
            MAX-ACCESS  not-accessible
            STATUS      current
            DESCRIPTION
                "
                Indicates the configuration of running line information collection.
                The indexes of this table are hwFrameIndex and hwSlotIndex.
                "
            ::= { hwXdslCommonMib 6 }

        hwXdslPortStatusInfoCollectEntry  OBJECT-TYPE
            SYNTAX      HwXdslPortStatusInfoCollectEntry
            MAX-ACCESS  not-accessible
            STATUS      current
            DESCRIPTION
                "
                Indicates the configuration of running line information collection.
                The indexes of this entry are hwFrameIndex and hwSlotIndex.
                "
            INDEX  {
                      hwFrameIndex,
                      hwSlotIndex
                   }
            ::= { hwXdslPortStatusInfoCollectTable 1 }

        HwXdslPortStatusInfoCollectEntry  ::=
            SEQUENCE {
              hwXdslPortStatusInfoCollectStart          INTEGER,
              hwXdslPortStatusInfoCollectState          INTEGER,
              hwXdslPortStatusInfoCollectPortList       OCTET STRING,
              hwXdslPortStatusInfoCollectRequestId      Unsigned32
            }

        hwXdslPortStatusInfoCollectStart  OBJECT-TYPE
            SYNTAX INTEGER
                      {
                          start(1),
                          invalid(-1)
                      }
            MAX-ACCESS  read-write
            STATUS      current
            DESCRIPTION
                "
                The leaf is used to start the running line information collection.
                Options:
                1. start(1)    - Start to collect information about running lines.
                2. invalid(-1) - Invalid value.
                "
            ::= { hwXdslPortStatusInfoCollectEntry 1 }

        hwXdslPortStatusInfoCollectState  OBJECT-TYPE
            SYNTAX INTEGER
                      {
                          nocollect(1),
                          collecting(2),
                          collected(3)
                      }
            MAX-ACCESS  read-only
            STATUS      current
            DESCRIPTION
                "
                 Indicates the status of running line information collection.
                 Options:
                 1. nocollect(1)    - The collection does not start.
                 2. collecting(2)   - The colleciton is running.
                 3. collected(3)    - The collection completed.
                "
            ::= { hwXdslPortStatusInfoCollectEntry 2 }

        hwXdslPortStatusInfoCollectPortList  OBJECT-TYPE
            SYNTAX      OCTET STRING (SIZE(0..16))
            MAX-ACCESS  read-write
            STATUS      current
            DESCRIPTION
                "
                Defines an operating port list of a certain xDSL board.
                Each bit of this string specifies a port. The bit whose value is 1 belongs to a port set and whose value is 0 does not belong to a port set.
                For example, if this node value is 0xFF 0xFE, information about port 0 to port 14 will be collected.
                If this node is not specified, all ports information on the board will be collected.
                "
            ::= { hwXdslPortStatusInfoCollectEntry 3 }

        hwXdslPortStatusInfoCollectRequestId OBJECT-TYPE
             SYNTAX      Unsigned32
             MAX-ACCESS  read-write
             STATUS      current
             DESCRIPTION
                     "
                      The xdsl port status info collect request ID, which identifies a collect request delivered by the NMS.
      	              An collect request ID can be any unsigned integer in the range of 0-4294967295.
      	              However, the IDs of different collect requests cannot duplicate.
      	              This object cannot be set independently.
      	              The value of 4294967295 indicates that request id is not specified.
                     "
             ::= { hwXdslPortStatusInfoCollectEntry 4 }

        hwXdslPortAutoResetControl  OBJECT-TYPE
            SYNTAX  INTEGER
            {
            enable(1),
            disable(2)
            }
            MAX-ACCESS  read-write
            STATUS      current
            DESCRIPTION
                "Enable/Disable the automatic detection for xDSL port offline and reset. This object is defaulted disable(2).
                 Options:
                 1. enable(1)        - Enable the xDSL port auto reset configuration
                 2. disable(2)       - Disable the xDSL port auto reset configuration
                "
            ::= { hwXdslPortAutoResetConfig 1 }

       hwXdslReversePoweringMode  OBJECT-TYPE
            SYNTAX  INTEGER
            {
                anyport(1),
                currentport(2)
            }
            MAX-ACCESS  read-write
            STATUS      current
            DESCRIPTION
                "This object indicates the reverse-powering mode of the system.
                 Warning: this operation will interrupt services on some ports.
                 Default values: currentport
                 Options:
                 1. anyport(1)        - In any port power supply mode, all ports can be activated.
                 2. currentport(2)    - In local port power supply mode, only the port that provides
                                        the power supply can be activated.
                "
            ::= { hwXdslReversePoweringGlobalConfig 1 }

        hwXdslReversePoweringLineTable  OBJECT-TYPE
            SYNTAX      SEQUENCE  OF  HwXdslReversePoweringLineEntry
            MAX-ACCESS  not-accessible
            STATUS      current
            DESCRIPTION
                "The table hwXdslReversePoweringLineTable contains reverse-powering
                 parameters of xDSL line.
                 The index of this table is ifIndex.
                "
            ::= { hwXdslCommonMib 9 }

        hwXdslReversePoweringLineEntry  OBJECT-TYPE
            SYNTAX      HwXdslReversePoweringLineEntry
            MAX-ACCESS  not-accessible
            STATUS      current
            DESCRIPTION
                "The table hwXdslReversePoweringLineTable contains reverse-powering
                 parameters of xDSL line.
                 The index of this entry is ifIndex.
                "
            INDEX  { ifIndex }
            ::= { hwXdslReversePoweringLineTable 1 }

        HwXdslReversePoweringLineEntry  ::=
            SEQUENCE {
              hwXdslReversePoweringStatus                        INTEGER,
              hwXdslReversePoweringFaultCauseActivefailure       INTEGER,
              hwXdslReversePoweringCurrent                       Unsigned32,
              hwXdslReversePoweringVoltage                       Unsigned32,
              hwXdslReversePoweringPower                         Unsigned32
            }

        hwXdslReversePoweringStatus  OBJECT-TYPE
            SYNTAX INTEGER
                      {
                          normal(1),
                          fault(2),
                          dyingGasp(3),
                          disconnect(4),
                          invalid(-1)
                      }
            MAX-ACCESS  read-only
            STATUS      current
            DESCRIPTION
                "Port reverse powering status.
                 Options:
                 1. normal(1)    - The CPE properly supplies power to the CO side.
                 2. fault(2)     - The CPE fails to supply power to the CO side.
                 3. dyingGasp(3) - The CPE is lost power.
                 4. disconnect(4) - The CPE is disconnected.
                 5. invalid(-1)  - Invalid value.
                "
            ::= { hwXdslReversePoweringLineEntry 1 }

        hwXdslReversePoweringFaultCauseActivefailure  OBJECT-TYPE
            SYNTAX INTEGER
                      {
                          yes(1),
                          no(2),
                          invalid(-1)
                      }
            MAX-ACCESS  read-only
            STATUS      current
            DESCRIPTION
                "Failed reverse-powering causes the activation failure.
                 Options:
                 1. yes(1)    - The port activation fails due to failed reverse power supply.
                 2. no(2)     - The port activation fails not due to failed reverse power supply.
                 3. invalid(-1)  - Invalid value.
                "
            ::= { hwXdslReversePoweringLineEntry 2 }

        hwXdslReversePoweringCurrent   OBJECT-TYPE
            SYNTAX      Unsigned32
            MAX-ACCESS  read-only
            STATUS      current
            DESCRIPTION
                "Indicate the port reverse powering current.
                 The invalid value is 4294967295.
                 Unit: mA.
                "
            ::= { hwXdslReversePoweringLineEntry 3 }

        hwXdslReversePoweringVoltage   OBJECT-TYPE
            SYNTAX      Unsigned32
            MAX-ACCESS  read-only
            STATUS      current
            DESCRIPTION
                "Indicate the port reverse powering voltage.
                 The invalid value is 4294967295.
                 Unit: 0.1V.
                "
            ::= { hwXdslReversePoweringLineEntry 4 }

        hwXdslReversePoweringPower   OBJECT-TYPE
            SYNTAX      Unsigned32
            MAX-ACCESS  read-only
            STATUS      current
            DESCRIPTION
                "Indicate the port reverse powering power.
                 The invalid value is 4294967295.
                 Unit: 0.01W.
                "
            ::= { hwXdslReversePoweringLineEntry 5 }

        hwXdslADSLPtmDataPath  OBJECT-TYPE
            SYNTAX  INTEGER
            {
            enable(1),
            disable(2)
            }
            MAX-ACCESS  read-write
            STATUS      current
            DESCRIPTION
                "Enable/Disable the global ADSL PTM switch function. This object is defaulted disable(2).
                 This configuration will take effect after port manually reactivated or board reset.
                 Options:
                 1. enable(1)        - Enable the global ADSL PTM switch function
                 2. disable(2)       - Disable the global ADSL PTM switch function
                "
            ::= { hwXdslADSLPtmDataPathConfig 1 }

        hwXdslBoardConnectorMapping  OBJECT-TYPE
            SYNTAX  INTEGER
            {
                normal(1),
                boardSubstitute48To64(2)
            }
            MAX-ACCESS  read-write
            STATUS      current
            DESCRIPTION
                "This parameter specifies the xdsl board connector mapping mode.
                 The parameter can take three values 1 and 2.
                 Warning: VDSL board will be reset after this node be written, It will take several minutes.
                 Options:
                 1. normal(1)                - The xdsl board connector mapping mode is normal,
                                               normally the port 0~63 mapping to line 0~63.
                 2. boardSubstitute48To64(2) - The xdsl board connector mapping mode is 48 board substitute,
                                               specially the port 24~31 mapping to line 48~55 and port 32~55 mapping to 24~47.
                                               The operation affects user services.
                "
            ::= { hwXdslBoardConnectorMappingConfig 1 }

        hwXdslProfileTransmodeAutoAdapt  OBJECT-TYPE
            SYNTAX  INTEGER
            {
            disable(1),
            enable(2)
            }
            MAX-ACCESS  read-write
            STATUS      current
            DESCRIPTION
                "Enable/Disable the profile transmode auto adapt switch. This object is defaulted disable(1).
                 Options:
                 1. disable(1)        - Disable the profile transmode auto adapt switch
                 2. enable(2)         - Enable the profile transmode auto adapt switch
                 After this switch is enabled,transmission modes not used by the device are removed when you
                 fill values back to the hwVOPLineSpectrumConfProfXtuTransSysEna node."
            ::= { hwXdslProfileTransmodeAuto 1 }

        hwXdslPortFrequentRetrainDefaultControlDefaultTimes  OBJECT-TYPE
            SYNTAX      Unsigned32 (3..15 | 4294967295)
            MAX-ACCESS  read-write
            STATUS      current
            DESCRIPTION
                "The times that xDSL port frequent retrain.
                 Values of this node are default values of the hwXdslPortFrequentRetrainControlTimes node.
                 The invalid value is 4294967295.
                "
            ::= { hwXdslPortFrequentRetrainControlDefaultCfg 1 }

        hwXdslPortFrequentRetrainDefaultControlDefaultPolicy  OBJECT-TYPE
            SYNTAX      INTEGER
            {
            lock(1),
            nolimit(2),
            postponed(3),
            nonvectoring(4),
            invalidValue(-1)
            }
            MAX-ACCESS  read-write
            STATUS      current
            DESCRIPTION
                "The control policy that xDSL port frequent retrain.
                 Values of this node are default values of the hwXdslPortFrequentRetrainControlPolicy node.

                 Options:
                 1. lock(1)            - The port is not allowed to go online within 15 minutes
                 2. nolimit(2)         - The port can go online without the limitation of control policies
                 3. postponed(3)       - The port can go online after a postponed time when the number of frequent
                                         resynchronizations on the port reaches the threshold
                 4. nonvectoring(4)    - If a vectoring port meets frequent retrain control policy requirements,
                                         the vectoring port is considered as a legacy port during initialization
                 5. invalidValue(-1)   - Invalid value
                "
            ::= { hwXdslPortFrequentRetrainControlDefaultCfg 2 }

        hwXdslPortFrequentRetrainControlDefaultPostponedTime  OBJECT-TYPE
            SYNTAX      Unsigned32 (5..3600 | 4294967295)
            UNITS       "minute"
            MAX-ACCESS  read-write
            STATUS      current
            DESCRIPTION
                "The postponed time when control policy of xDSL port frequent retrain is postponed.
                 Values of this node are default values of the hwXdslPortFrequentRetrainControlPostponedTime node.
                 The invalid value is 4294967295.
                "
            ::= { hwXdslPortFrequentRetrainControlDefaultCfg 3 }

        hwXdslPortFrequentRetrainControlDefaultFurtherCtrlCfg   OBJECT-TYPE
            SYNTAX      INTEGER
            {
            enable(1),
            disable(2)
            }
            MAX-ACCESS  read-write
            STATUS      current
            DESCRIPTION
                "Further control policy for frequent retrain.
                 Values of this node are default values of the hwXdslPortFrequentRetrainControlFurtherControlCfg node.
                 Options:
                 1. enable(1)          - Enable the further control policy for frequent retrain
                 2. disable(2)         - Disable the further control policy for frequent retrain
                "
            ::= { hwXdslPortFrequentRetrainControlDefaultCfg 4 }

         hwXdslPortFrequentRetrainControlDefaultFurtherCtrlDetectPeriod  OBJECT-TYPE
            SYNTAX      Unsigned32 (1..168 | 4294967295)
            UNITS       "hour"
            MAX-ACCESS  read-write
            STATUS      current
            DESCRIPTION
                "Detection period of the further control policy for frequent retrain.
                 Values of this node are default values of the hwXdslPortFrequentRetrainControlFurtherControlDetectPeriod node.
                 The invalid value is 4294967295.
                "
            ::= { hwXdslPortFrequentRetrainControlDefaultCfg 5 }

          hwXdslPortFrequentRetrainControlDefaultFurtherCtrlPolicy  OBJECT-TYPE
            SYNTAX      INTEGER
            {
                permanentLock(1),
                permanentNonVectoring(2),
                invalidValue(-1)
            }
            MAX-ACCESS  read-write
            STATUS      current
              DESCRIPTION
                "Further control policy for frequent retrain.
                 Values of this node are default values of the hwXdslPortFrequentRetrainControlFurtherControlPolicy node.
                 Options:
                 1. permanentLock(1)                 - Permanently disable activation in any mode
                 2. permanentNonVectoring(2)         - Permanently disable activation in vectoring mode
                 3. invalidValue(-1)                 - Invalid value
                "
            ::= { hwXdslPortFrequentRetrainControlDefaultCfg 6 }

       hwXdslUpboEleM0Calculation  OBJECT-TYPE
            SYNTAX  INTEGER
            {
                proprietary(1),
                minimumEleUs(2)
            }
            MAX-ACCESS  read-write
            STATUS      current
            DESCRIPTION
                "This parameter specifies the method to calculate kl0 when ELE-M0 is used.
                 The parameter can take two values 1, 2.
 	         Options:
                 1. proprietary(1)     - ELE-M0 is VTU-O proprietary estimate, refer to G.993.2 for detailed description.
                 2. minimumEleUs(2)    - Kl0 will use the minimum ELE of all US bands.
                "
            ::= { hwXdslUpboEleM0CalculationConfig 1 }

        hwXdslCellheadCompresscfg  OBJECT-TYPE
            SYNTAX  INTEGER
            {
            enable(1),
            disable(2)
            }
            MAX-ACCESS  read-write
            STATUS      current
            DESCRIPTION
                "Enable/Disable the nitro switch function. This object is defaulted disable(2).
                 Options:
                 1. enable(1)        - Enable the nitro switch function
                 2. disable(2)       - Disable the nitro switch function
                "
            ::= { hwXdslCellheadCompressConfig 1 }

        hwXdslGfastFastRestartMode  OBJECT-TYPE
            SYNTAX  INTEGER
            {
            enable(1),
            disable(2)
            }
            MAX-ACCESS  read-write
            STATUS      current
            DESCRIPTION
                "Enable/Disable the G.fast fast restart switch function. This object is defaulted disable(2).
                 Options:
                 1. enable(1)        - Enable the G.fast fast restart switch function
                 2. disable(2)       - Disable the G.fast fast restart switch function
                "
            ::= { hwXdslGfastFastRestartConfig 1 }

        hwXdslGfastPowerAutoAllocation  OBJECT-TYPE
            SYNTAX  INTEGER
            {
            disable(1),
            upstream(2),
            downstream(3),
            both(4)
            }
            MAX-ACCESS  read-write
            STATUS      current
            DESCRIPTION
                "Enable/Disable the G.fast power auto allocation switch.
                 Warning: this operation will reactivate all the G.fast ports.
                 This object is defaulted disable(1).
                 Options:
                 1. disable(1)        - Indicates that the G.fast power auto allocation switch is disabled
                 2. upstream(2)       - Indicates that the G.fast power auto allocation switch is enabled in upstream
                 3. downstream(3)     - Indicates that the G.fast power auto allocation switch is enabled in downstream
                 4. both(4)           - Indicates that the G.fast power auto allocation switch is enabled in both downstream and upstream
                "
            ::= { hwXdslGfastPowerAutoAllocationConfig 1 }

        hwXdslBypassRelayMode  OBJECT-TYPE
            SYNTAX  INTEGER
            {
            enable(1),
            disable(2)
            }
            MAX-ACCESS  read-write
            STATUS      current
            DESCRIPTION
                "Enable/Disable the Xdsl bypass relay mode.
                 This object is defaulted enable(1).
                 Options:
                 1. enable(1)        - Indicates that the Xdsl bypass relay mode is enabled
                 2. disable(2)       - Indicates that the Xdsl bypass relay mode is disabled
                "
            ::= { hwXdslBypassRelayModeConfig 1 }

        hwXdslGfastCableOptimization  OBJECT-TYPE
            SYNTAX  INTEGER
            {
            enable(1),
            disable(2)
            }
            MAX-ACCESS  read-write
            STATUS      current
            DESCRIPTION
                "Enable/Disable the G.fast cable optimization switch.
                 This object is defaulted disable(2).
                 Options:
                 1. enable(1)        - Indicates that the G.fast cable optimization switch is enabled
                 2. disable(2)       - Indicates that the G.fast cable optimization switch is disabled
                "
            ::= { hwXdslGfastCableOptimizationConfig 1 }

        hwXdslGfastCableOptimizationCableType  OBJECT-TYPE
            SYNTAX  INTEGER
            {
            atis(1),
            quad(2),
            paperInsulated(3),
            tp100(4),
            other(5)
            }
            MAX-ACCESS  read-write
            STATUS      current
            DESCRIPTION
                "
                Description: Cable type.
                Default values: tp100(4)
                Options:
                1. atis(1) - ATIS
                2. quad(2) - Quad
                3. paperInsulated(3) - Paper Insulated
                4. tp100(4) - TP100
                5. other(5) - Other
                "
            ::= { hwXdslGfastCableOptimizationConfig 2 }

        hwXdslRateChangeReportThresholdDs  OBJECT-TYPE
            SYNTAX      Gauge32 (0..500000000)
            UNITS       "bit/s"
            MAX-ACCESS  read-write
            STATUS      current
            DESCRIPTION
                "XDSL rate change report threshold in the downstream direction, default is 500000."
            ::= { hwXdslPortRateChangeReportConfig 1 }

        hwXdslRateChangeReportThresholdUs  OBJECT-TYPE
            SYNTAX      Gauge32 (0..500000000)
            UNITS       "bit/s"
            MAX-ACCESS  read-write
            STATUS      current
            DESCRIPTION
                "XDSL rate change report threshold in the upstream direction, default is 500000."
            ::= { hwXdslPortRateChangeReportConfig 2 }

        hwXdslRateChangeReportPeriod  OBJECT-TYPE
            SYNTAX      Gauge32 (0..86400)
            UNITS       "seconds"
            MAX-ACCESS  read-write
            STATUS      current
            DESCRIPTION
                "XDSL rate change report period, default is 10."
            ::= { hwXdslPortRateChangeReportConfig 3 }

        hwGfastRateChangeReportThresholdDs  OBJECT-TYPE
            SYNTAX      Gauge32 (0..2000000000)
            UNITS       "bit/s"
            MAX-ACCESS  read-write
            STATUS      current
            DESCRIPTION
                "G.fast rate change report threshold in the downstream direction, default is 500000."
            ::= { hwXdslPortRateChangeReportConfig 4 }

        hwGfastRateChangeReportThresholdUs  OBJECT-TYPE
            SYNTAX      Gauge32 (0..2000000000)
            UNITS       "bit/s"
            MAX-ACCESS  read-write
            STATUS      current
            DESCRIPTION
                "G.fast rate change report threshold in the upstream direction, default is 500000."
            ::= { hwXdslPortRateChangeReportConfig 5 }

        hwGfastlRateChangeReportPeriod  OBJECT-TYPE
            SYNTAX      Gauge32 (0..86400)
            UNITS       "seconds"
            MAX-ACCESS  read-write
            STATUS      current
            DESCRIPTION
                "G.fast rate change report period, default is 60."
            ::= { hwXdslPortRateChangeReportConfig 6 }

     -- Vboids
        hwXdslDynamicCollectResult OBJECT-TYPE
            SYNTAX  INTEGER
                {
                noFail(0),
                memFull(1),
                otherCause(2)
                }
            MAX-ACCESS accessible-for-notify
            STATUS current
            DESCRIPTION
                "Dynamic information collecting result.
                 Options:
                 1. noFail(0)     - The dynamic info has been collected successful
                 2. memFull(1)    - The memory used for dynamic info collecting is full
                 3. otherCause(2) - Other collect failure reason
                "
            ::= { hwXdslTrapsVbOids 1 }

        hwXdslDynamicCollectTime OBJECT-TYPE
            SYNTAX  DateAndTime
            MAX-ACCESS  accessible-for-notify
            STATUS     current
            DESCRIPTION
                "Time of the Dynamic information file."
            ::= { hwXdslTrapsVbOids 2 }

        hwXdslRequestID OBJECT-TYPE
            SYNTAX Integer32
            MAX-ACCESS accessible-for-notify
            STATUS current
            DESCRIPTION
                "Request ID."
            ::= { hwXdslTrapsVbOids 3 }

        hwXdslSeltCompleteResult OBJECT-TYPE
            SYNTAX INTEGER
                {
                success(1),
                fail(2)
                }
            MAX-ACCESS accessible-for-notify
            STATUS current
            DESCRIPTION
                "Selt test complete result.
                 Options:
                 1. success(1) - Selt test is successful
                 2. fail(2)    - Failed in selt test
                "
        ::= { hwXdslTrapsVbOids 4 }

        hwAdslProfIDType OBJECT-TYPE
            SYNTAX INTEGER
                {
                lineTemplate(1),
                alarmTemplate(2),
                extProfile(3)
                }
            MAX-ACCESS accessible-for-notify
            STATUS current
            DESCRIPTION
                "Type of the adsl template ID.
                 Options:
                 1. lineTemplate(1)  - Indicates line template ID
                 2. alarmTemplate(2) - Indicates alarm template ID
                 3. extProfile(3)    - Indicates ext profile ID
                "
            ::= { hwXdslTrapsVbOids 5 }

        hwXdslProfName OBJECT-TYPE
            SYNTAX OCTET STRING (SIZE (1..32))
            MAX-ACCESS accessible-for-notify
            STATUS current
            DESCRIPTION
                "The name of the XDSL profile."
            ::= { hwXdslTrapsVbOids 6}

        hwXdslPortActualUpRate OBJECT-TYPE
            SYNTAX Unsigned32
            MAX-ACCESS accessible-for-notify
            STATUS current
            DESCRIPTION
                "Xdsl port actual upstream rate."
            ::= { hwXdslTrapsVbOids 7}

        hwXdslPortActualDownRate OBJECT-TYPE
            SYNTAX Unsigned32
            MAX-ACCESS accessible-for-notify
            STATUS current
            DESCRIPTION
                "Xdsl port actual downstream rate."
            ::= { hwXdslTrapsVbOids 8}

        hwXdslDelProfIndex OBJECT-TYPE
            SYNTAX Unsigned32
            MAX-ACCESS accessible-for-notify
            STATUS current
            DESCRIPTION
                     "Index of the profile which is deleted.
                      If you delete all the profiles unused, this parameter will be 0xffffffff."
             ::= { hwXdslTrapsVbOids 9}

        hwXdslDelProfName OBJECT-TYPE
            SYNTAX OCTET STRING (SIZE (0..128))
            MAX-ACCESS accessible-for-notify
            STATUS current
            DESCRIPTION
                     "Name of the profile which is deleted.
                      If you delete all the profiles unused, this parameter will be a zero string."
             ::= { hwXdslTrapsVbOids 10}


        hwXdslSeltTestStartResult OBJECT-TYPE
            SYNTAX INTEGER
                {
                normal(1),
                failed(2)
                }
            MAX-ACCESS accessible-for-notify
            STATUS current
            DESCRIPTION
                     "XDSL selt test start result.
                      Options:
                      1. normal(1) - This notification indicates that a SELT task has been started successfully
                      2. failed(2) - This notification indicates that a SELT task failed to be started
                     "
             ::= { hwXdslTrapsVbOids 11 }

        hwXdslPortStatusInfoCollectResult OBJECT-TYPE
            SYNTAX  INTEGER
                {
                noFail(0),
                memFull(1),
                otherCause(2)
                }
            MAX-ACCESS accessible-for-notify
            STATUS current
            DESCRIPTION
                "Indicates the status of running line information collection.
                 Options:
                 1. noFail(0)     - The running line information has been collected successfully.
                 2. memFull(1)    - The memory used for running line information collection is used up.
                 3. otherCause(2) - Other collection failure reasons.
                "
            ::= { hwXdslTrapsVbOids 12 }

-- common trap
        hwXdslDynamicCollectInfoTrap NOTIFICATION-TYPE
            OBJECTS
                {
                hwXdslDynamicCollectResult,
                hwFrameIndex,
                hwSlotIndex,
                hwXdslDynamicCollectTime
                }
            STATUS current
            DESCRIPTION
                "XDSL dynamic collect trap.
                 This trap message is generated when XDSL dynamic collected.
                "
            ::= { hwXdslCommonTraps 0 1 }

        hwXdslSeltCompleteResultTrap NOTIFICATION-TYPE
            OBJECTS
                {
                hwXdslRequestID,
                hwXdslSeltCompleteResult
                }
            STATUS current
            DESCRIPTION
                "Selt test complete result trap.
                 This trap message is generated when selt test completed.
                "
            ::= { hwXdslCommonTraps 0 2 }
        hwAdslProfIDChangeTrap NOTIFICATION-TYPE
            OBJECTS
                {
                hwConfigChangeIP,
                hwAdslProfIDType,
                ifIndex,
                hwXdslProfName
                }
            STATUS current
            DESCRIPTION
                "Adsl profile ID change trap.
                 This trap message is generated when adsl profile ID changed.
                "
            ::= { hwXdslCommonTraps 0 3 }
        hwXdslProfDeleteTrap NOTIFICATION-TYPE
            OBJECTS {
                       hwConfigChangeIP,
                       hwXdslAutoDeleteProfUnusedProfType,
                       hwXdslAutoDeleteProfUnusedOperType,
                       hwXdslDelProfIndex,
                       hwXdslDelProfName
    	            }
            STATUS current
            DESCRIPTION
                   "This trap message is generated when Xdsl unused profile trap deleted."
            ::= { hwXdslCommonTraps 0 4 }

        hwXdslSeltStartResultTrap NOTIFICATION-TYPE
             OBJECTS {
                     hwXdslSeltTestStartResult,
                     hwXdslRequestID
    	             }
        STATUS current
        DESCRIPTION
            "XDSL selt test start trap.
             This notification indicates trap when xDSL selt test start.
            "
        ::= { hwXdslCommonTraps 0 5 }

        hwXdslPortStatusInfoCollectTrap NOTIFICATION-TYPE
            OBJECTS
                {
                hwFrameIndex,
                hwSlotIndex,
                hwXdslPortStatusInfoCollectResult,
                hwXdslPortStatusInfoCollectRequestId
                }
            STATUS current
            DESCRIPTION
               "This trap is generated when running line information collections is complete. "
            ::= { hwXdslCommonTraps 0 6 }

     -- alarm trap
        hwXdslAutoDeactivateLackLicensesAlarmTrap NOTIFICATION-TYPE
            OBJECTS
                {
                hwFrameIndex,
                hwSlotIndex
                }
            STATUS current
            DESCRIPTION
                "This trap message is generated when some xDSL ports or all the xDSL ports
                 are automatically deactivated due to lack of licenses."
            ::= { hwXdslAlarmTraps 0 1 }

        hwXdslPortActRateLowerThresholdAlarmTrap  NOTIFICATION-TYPE
            OBJECTS
                {
                hwFrameIndex,
                hwSlotIndex,
                hwPortIndex,
                hwXdslPortActualDownRate,
                hwXdslPortActualUpRate
                }
            STATUS current
            DESCRIPTION
                "This trap message is generated when the activation rate
                 of the xDSL line is lower than the threshold."
            ::= { hwXdslAlarmTraps 0 2 }

        hwXdslPortReversePoweringFaultAlarmTrap  NOTIFICATION-TYPE
            OBJECTS
                {
                hwFrameIndex,
                hwSlotIndex,
                hwPortIndex
                }
            STATUS current
            DESCRIPTION
                "This trap message is generated when the reverse power supply fails
                 or undervoltage occurs on the port."
            ::= { hwXdslAlarmTraps 0 3 }

        hwXdslPortReversePoweringNormalAlarmTrap  NOTIFICATION-TYPE
            OBJECTS
                {
                hwFrameIndex,
                hwSlotIndex,
                hwPortIndex
                }
            STATUS current
            DESCRIPTION
                "This trap message is generated when the reverse power supply recovers."
            ::= { hwXdslAlarmTraps 0 4 }

        hwXdslPortUnableToUpAfterPortAutoResetAlarmTrap  NOTIFICATION-TYPE
            OBJECTS
                {
                hwFrameIndex,
                hwSlotIndex,
                hwPortIndex
                }
            STATUS current
            DESCRIPTION
                "This trap message is generated when the port is unable to active after port auto reset."
            ::= { hwXdslAlarmTraps 0 5 }

        hwXdslPortReactivateAfterPortResetRecoveryTrap  NOTIFICATION-TYPE
            OBJECTS
                {
                hwFrameIndex,
                hwSlotIndex,
                hwPortIndex
                }
            STATUS current
            DESCRIPTION
                "This trap message is generated when the port is back to activated after port auto reset."
            ::= { hwXdslAlarmTraps 0 6 }
        END
