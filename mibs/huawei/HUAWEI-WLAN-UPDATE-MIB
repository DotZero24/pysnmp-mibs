--
-- HUAWEI-WLAN-UPDATE-MIB.my
-- MIB generated by MG-SOFT Visual MIB Builder Version 4.0 Build 341
-- Tuesday, February 19, 2013 at 16:03:04
--

--   ============================================================================
-- Copyright (C) 2014 by  HUAWEI TECHNOLOGIES. All rights reserved.
-- Description:  The mib is used for update the ap's program version.
-- Reference:HUAWEI-WLAN-MIB
-- Version: V1.02
--
-- ============================================================================

	HUAWEI-WLAN-UPDATE-MIB DEFINITIONS ::= BEGIN

		IMPORTS
			hwApType, hwApRegionIndex, hwApIndex, hwApMac
				FROM HUAWEI-WLAN-DEVICE-MIB
			hwWlan
				FROM HUAWEI-WLAN-MIB
			OBJECT-GROUP, MODULE-COMPLIANCE, NOTIFICATION-GROUP
				FROM SNMPv2-CONF
			IpAddress, Integer32, OBJECT-TYPE, MODULE-IDENTITY, NOTIFICATION-TYPE
				FROM SNMPv2-SMI
			RowStatus
				FROM SNMPv2-TC;


--  June 08, 2010 at 00:00 GMT
		-- 1.3.6.1.4.1.2011.6.139.7
		hwWlanUpdate MODULE-IDENTITY
			LAST-UPDATED "201411271000Z"		-- November 27, 2014 at 10:00 GMT
			ORGANIZATION
				"Huawei Technologies Co.,Ltd."
			CONTACT-INFO
			"Huawei Industrial Base
				   Bantian, Longgang
				   Shenzhen 518129
				   People's Republic of China
				   Website: http://www.huawei.com
				   Email: support@huawei.com
				  "
			DESCRIPTION
				"The MIB module defines the AP update operation."
			REVISION "201411271000Z"		-- November 27, 2014 at 10:00 GMT
			DESCRIPTION
				"The MIB module defines the AP update operation."
			REVISION "201310231500Z"		-- October 23, 2013 at 15:00 GMT
			DESCRIPTION
				"
				V1.01, Add for v2r5.
				"
			REVISION "201006080000Z"		-- June 08, 2010 at 00:00 GMT
			DESCRIPTION
				"
				V1.00, Inital version.
				"
			REVISION "201011100000Z"		-- November 10, 2010 at 00:00 GMT
			DESCRIPTION
				"V1.02, Add nine enum values in hwApUpdateResult leaf of hwWlanUpdateNotifyObjects"
			::= { hwWlan 7 }



		hwWlanUpdateNotifications OBJECT IDENTIFIER ::= { hwWlanUpdate 1 }
		hwApUpdateBeginNotify NOTIFICATION-TYPE
			OBJECTS { hwApIndex, hwApMac }
			STATUS current
			DESCRIPTION
				"This notification occurs when ap begin to update."
			::= { hwWlanUpdateNotifications 1 }

		hwApUpdateResultNotify NOTIFICATION-TYPE
			OBJECTS { hwApIndex, hwApUpdateResult, hwApMac, hwApUpdateTime, hwApUpdateByFileName,
				hwApUpdateNextOper, hwApUpdateResultStatus }
			STATUS current
			DESCRIPTION
				"This notification occurs when ap has updated successfully or failed."
			::= { hwWlanUpdateNotifications 2 }

		hwApUpdateUbootNotMatchNotify NOTIFICATION-TYPE
			OBJECTS { hwApIndex, hwApMac }
			STATUS current
			DESCRIPTION
				"This notification occurs when ap uboot not match version."
			::= { hwWlanUpdateNotifications 3 }
		hwWlanUpdateNotifyObjects OBJECT IDENTIFIER ::= { hwWlanUpdate 2 }

		hwApUpdateResult OBJECT-TYPE
			SYNTAX INTEGER
				{
				success(1),
				failureUnknownError(2),
				failureInsufficientMemory(3),
				failureDownloadFileFailure(4),
				failureMismatchVersionEfsAndFileName(5),
				failureInvalidFileName(6),
				failureMismatchApTypeInEfs(7),
				failureFileContentError(8),
				failureWriteFlashFailure(9),
				failureTimeoutForUpgrade(10),
				failureCommunicationFaultApAndAc(11)
				}
			MAX-ACCESS read-only
			STATUS current
			DESCRIPTION
				"Ap update result.
				1 means success
				2 means failure, unknown error
				3 means failure, insufficient AP memory
				4 means failure, fail to download the file
				5 means failure, mismatch between the version in the EFS tail and the version in the file name
				6 means failure, invalid file name
				7 means failure, mismatch between the AP type in the EFS tail and the AP
				8 means failure, file content error
				9 means failure, writing flash memory failure
				10 means failure, upgrade timeout
				11 means failure, the communication between AP and AC fails
				"
			::= { hwWlanUpdateNotifyObjects 1 }

		hwApUpdateTime OBJECT-TYPE
			SYNTAX OCTET STRING
			MAX-ACCESS read-only
			STATUS current
			DESCRIPTION
				"Description."
			::= { hwWlanUpdateNotifyObjects 2 }



		hwApUpdateByFileName OBJECT-TYPE
			SYNTAX OCTET STRING
			MAX-ACCESS read-only
			STATUS current
			DESCRIPTION
				"Description."
			::= { hwWlanUpdateNotifyObjects 3 }

		hwApUpdateNextOper OBJECT-TYPE
			SYNTAX INTEGER
				{
				notReset(1),
				reset(2)
				}
			MAX-ACCESS read-only
			STATUS current
			DESCRIPTION
				"Description."
			::= { hwWlanUpdateNotifyObjects 4 }

		hwApUpdateResultStatus OBJECT-TYPE
			SYNTAX OCTET STRING
			MAX-ACCESS read-only
			STATUS current
			DESCRIPTION
				"Description."
			::= { hwWlanUpdateNotifyObjects 5 }
		hwApUpdateObjects OBJECT IDENTIFIER ::= { hwWlanUpdate 3 }

		hwApUpdateConfig OBJECT IDENTIFIER ::= { hwApUpdateObjects 1 }

		hwApUpdateFTPIPAddress OBJECT-TYPE
			SYNTAX IpAddress
			MAX-ACCESS read-write
			STATUS current
			DESCRIPTION
				"FTP Server IP for Ap Update."
			::= { hwApUpdateConfig 1 }

		hwApUpdateFTPUsername OBJECT-TYPE
			SYNTAX OCTET STRING
			MAX-ACCESS read-write
			STATUS current
			DESCRIPTION
				"FTP Client Username for Ap Update."
			::= { hwApUpdateConfig 2 }

		hwApUpdateFTPPassword OBJECT-TYPE
			SYNTAX OCTET STRING
			MAX-ACCESS read-write
			STATUS current
			DESCRIPTION
				"FTP Client Password for Ap Update."
			::= { hwApUpdateConfig 3 }

		hwApUpdateMode OBJECT-TYPE
			SYNTAX INTEGER
				{
				ftp(1),
				ac(2),
				sftp(3)
				}
			MAX-ACCESS read-write
			STATUS current
			DESCRIPTION
				"The mode of Ap Update.
				ftp(1): Ap Image Update by ftp.
				ac(2): Ap Image Update by ac-ap protocol.
				"
			::= { hwApUpdateConfig 4 }

		-- 1.3.6.1.4.1.2011.6.139.7.3.1.5
		hwApUpdateSFTPIPAddress OBJECT-TYPE
			SYNTAX IpAddress
			MAX-ACCESS read-write
			STATUS current
			DESCRIPTION
				"Description."
			::= { hwApUpdateConfig 5 }


		-- 1.3.6.1.4.1.2011.6.139.7.3.1.6
		hwApUpdateSFTPUsername OBJECT-TYPE
			SYNTAX OCTET STRING
			MAX-ACCESS read-write
			STATUS current
			DESCRIPTION
				"Description."
			::= { hwApUpdateConfig 6 }


		-- 1.3.6.1.4.1.2011.6.139.7.3.1.7
		hwApUpdateSFTPPassword OBJECT-TYPE
			SYNTAX OCTET STRING
			MAX-ACCESS read-write
			STATUS current
			DESCRIPTION
				"Description."
			::= { hwApUpdateConfig 7 }
		hwApUpdateFTPMaxConnectNum OBJECT-TYPE
			SYNTAX Integer32
			MAX-ACCESS read-write
			STATUS current
			DESCRIPTION
				"Description."
			::= { hwApUpdateConfig 8 }
		hwApUpdateSFTPMaxConnectNum OBJECT-TYPE
			SYNTAX Integer32
			MAX-ACCESS read-write
			STATUS current
			DESCRIPTION
				"Description."
			::= { hwApUpdateConfig 9 }


		-- 1.3.6.1.4.1.2011.6.139.7.3.1.10
		hwApUpdateFTPIPv6Address OBJECT-TYPE
			SYNTAX OCTET STRING (SIZE (0..46))
			MAX-ACCESS read-write
			STATUS current
			DESCRIPTION
				"Description."
			::= { hwApUpdateConfig 10 }


		-- 1.3.6.1.4.1.2011.6.139.7.3.1.11
		hwApUpdateSFTPIPv6Address OBJECT-TYPE
			SYNTAX OCTET STRING (SIZE (0..46))
			MAX-ACCESS read-write
			STATUS current
			DESCRIPTION
				"Description."
			::= { hwApUpdateConfig 11 }

		hwApUpdateTable OBJECT-TYPE
			SYNTAX SEQUENCE OF HwApUpdateEntry
			MAX-ACCESS not-accessible
			STATUS current
			DESCRIPTION
				"Ap Update Table.
				The index of this table is hwApType.
				"
			::= { hwApUpdateObjects 2 }

		hwApUpdateEntry OBJECT-TYPE
			SYNTAX HwApUpdateEntry
			MAX-ACCESS not-accessible
			STATUS current
			DESCRIPTION
				"Ap UpdateEntry."
			INDEX { hwApType }
			::= { hwApUpdateTable 1 }


		HwApUpdateEntry ::=
			SEQUENCE {
				hwApUpdateFilename
					OCTET STRING,
				hwApUpdateResultMask
					OCTET STRING,
				hwApUpdateAdminOper
					INTEGER,
				hwApUpdatePercent
					Integer32,
				hwApUpdateRowStatus
					RowStatus,
				hwApUpdateResultInfo
					OCTET STRING,
				hwApUpdateApIdSetMask
					OCTET STRING
			 }

		hwApUpdateFilename OBJECT-TYPE
			SYNTAX OCTET STRING
			MAX-ACCESS read-create
			STATUS current
			DESCRIPTION
				"The ap image filename of ap update."
			::= { hwApUpdateEntry 1 }

		hwApUpdateResultMask OBJECT-TYPE
			SYNTAX OCTET STRING
			MAX-ACCESS read-only
			STATUS current
			DESCRIPTION
				"The result of ap update.
				Every bit is used to describe the ap updated successfully or unsuccessfully.
				0 means success, and 1 means unsuccess.
				The value of this node is hexadecimal integer block.
				Each Byte describes 8 aps are updated successfully or unsuccessfully.
				For example, the first Byte describes ap 0~7 is updated successfully or unsuccessfully,
				and the second Byte describes ap 8~15 is updated successfully or unsuccessfully.
				Such as, if only ap 0,4,5,6,7,9 is updated unsuccessfully, the binary number is 11110001 and 00000010,
				the hexadecimal number is 0xF1 and 0x2, so the first Byte of this node is 0xF1,
				and the second Byte is 0x2."
			::= { hwApUpdateEntry 2 }

		hwApUpdateAdminOper OBJECT-TYPE
			SYNTAX INTEGER
				{
				start(1),
				reset(2),
				cancel(3)
				}
			MAX-ACCESS read-create
			STATUS current
			DESCRIPTION
				"Ap update administration operation.
				start(1): start ap update.
				reset(2): reset all the ap with specifed type after update finished "
			::= { hwApUpdateEntry 3 }

		hwApUpdatePercent OBJECT-TYPE
			SYNTAX Integer32
			MAX-ACCESS read-only
			STATUS current
			DESCRIPTION
				"The percentage is only used for a online update operation.
                                If the update begins, the percentage becomes 1.
				when some AP's update is finished, the percentage stands for the percentage which is the number of APs upgraded to the total number of APs.
				If the update is finished, the percentage will be 100."
			::= { hwApUpdateEntry 4 }

		hwApUpdateRowStatus OBJECT-TYPE
			SYNTAX RowStatus
			MAX-ACCESS read-create
			STATUS current
			DESCRIPTION
				"Row status: mainly to support to add or delete the relationship of ap's type and the update filename.
				createAndGo(4): add a relationship.
				destroy(6): delete the relationship.
				"
			::= { hwApUpdateEntry 5 }

		hwApUpdateResultInfo OBJECT-TYPE
			SYNTAX OCTET STRING
			MAX-ACCESS read-only
			STATUS current
			DESCRIPTION
				"The result of ap update.
				Every bit is used to describe the ap updated successfully or unsuccessfully.
				0 means success, and 1 means unsuccess.
				The value of this node is hexadecimal integer block.
				Each Byte describes 8 aps are updated successfully or unsuccessfully.
				For example, the first Byte describes ap 0~7 is updated successfully or unsuccessfully,
				and the second Byte describes ap 8~15 is updated successfully or unsuccessfully.
				Such as, if only ap 0,4,5,6,7,9 is updated unsuccessfully, the binary number is 11110001 and 00000010,
				the hexadecimal number is 0xF1 and 0x2, so the first Byte of this node is 0xF1,
				and the second Byte is 0x2."
			::= { hwApUpdateEntry 6 }


		-- 1.3.6.1.4.1.2011.6.139.7.3.2.1.7
		hwApUpdateApIdSetMask OBJECT-TYPE
			SYNTAX OCTET STRING
			MAX-ACCESS read-write
			STATUS current
			DESCRIPTION
				"Description."
			::= { hwApUpdateEntry 7 }


		-- 1.3.6.1.4.1.2011.6.139.7.3.3
		hwApUpdateProgressTable OBJECT-TYPE
			SYNTAX SEQUENCE OF HwApUpdateProgressEntry
			MAX-ACCESS not-accessible
			STATUS current
			DESCRIPTION
				"Description."
			::= { hwApUpdateObjects 3 }

		hwApUpdateProgressEntry OBJECT-TYPE
			SYNTAX HwApUpdateProgressEntry
			MAX-ACCESS not-accessible
			STATUS current
			DESCRIPTION
				"Description."
			INDEX { hwApIndex }
			::= { hwApUpdateProgressTable 1 }


		HwApUpdateProgressEntry ::=
			SEQUENCE {
				hwApUpdateProgressStatus
					INTEGER,
				hwApUpdateProgress
					Integer32,
				hwApFlashProgress
					Integer32
			 }

		hwApUpdateProgressStatus OBJECT-TYPE
			SYNTAX INTEGER
				{
				noUpdateResult(-1),
				updating(0),
				updateSuccessful(1),
				updateFailed(2),
				insufficientApMemory(3),
				failToDownloadFile(4),
				efsAndVersionMismatched(5),
				invalidFileName(6),
				efsAndApTypeMismatched(7),
				fileContentError(8),
				writingMemoryError(9),
				updateTimeout(10),
				apAcLinkDown(11),
				noNeedToUpdate(12),
				updateCancel(13),
				sendFirstFileFailed(14),
				receiveFileFailed(15),
				retransferFileFailed(16),
				updateOverMaxTime(17),
				noResult(18),
				waitForNextBatch(19),
				noNeedUpdateNeedReset(20),
				neitherNeedUpdateNorReset(21),
				fileLoading(22),
				identifierErr(23),
				notInConfig(24),
				getFtpInfoFailed(25),
				getSftpInfoFailed(26),
				blockFull(27),
				readFileFailed(31),
				normalToStandby(32),
				modeChanged(33),
				succeedNeedReset(34)

				}
			MAX-ACCESS read-only
			STATUS current
			DESCRIPTION
				"Description."
			::= { hwApUpdateProgressEntry 1 }

		hwApUpdateProgress OBJECT-TYPE
			SYNTAX Integer32
			MAX-ACCESS read-only
			STATUS current
			DESCRIPTION
				"Description."
			::= { hwApUpdateProgressEntry 2 }

		hwApFlashProgress OBJECT-TYPE
			SYNTAX Integer32
			MAX-ACCESS read-only
			STATUS current
			DESCRIPTION
				"Description."
			::= { hwApUpdateProgressEntry 3 }
		hwMacApUpdateProgressTable OBJECT-TYPE
			SYNTAX SEQUENCE OF HwMacApUpdateProgressEntry
			MAX-ACCESS not-accessible
			STATUS current
			DESCRIPTION
				"Description."
			::= { hwApUpdateObjects 4 }

		hwMacApUpdateProgressEntry OBJECT-TYPE
			SYNTAX HwMacApUpdateProgressEntry
			MAX-ACCESS not-accessible
			STATUS current
			DESCRIPTION
				"Description."
			INDEX { hwApMac }
			::= { hwMacApUpdateProgressTable 1 }


		HwMacApUpdateProgressEntry ::=
			SEQUENCE {
				hwMacApUpdateProgressStatus
					INTEGER,
				hwMacApUpdateProgress
					Integer32,
				hwMacApFlashProgress
					Integer32
			 }

		hwMacApUpdateProgressStatus OBJECT-TYPE
			SYNTAX INTEGER
				{
				noUpdateResult(-1),
				updating(0),
				updateSuccessful(1),
				updateFailed(2),
				insufficientApMemory(3),
				failToDownloadFile(4),
				efsAndVersionMismatched(5),
				invalidFileName(6),
				efsAndApTypeMismatched(7),
				fileContentError(8),
				writingMemoryError(9),
				updateTimeout(10),
				apAcLinkDown(11),
				noNeedToUpdate(12),
				updateCancel(13),
				sendFirstFileFailed(14),
				receiveFileFailed(15),
				retransferFileFailed(16),
				updateOverMaxTime(17),
				noResult(18),
				waitForNextBatch(19),
				noNeedUpdateNeedReset(20),
				neitherNeedUpdateNorReset(21),
				fileLoading(22),
				identifierErr(23),
				notInConfig(24),
				getFtpInfoFailed(25),
				getSftpInfoFailed(26),
				blockFull(27),
				readFileFailed(31),
				normalToStandby(32),
				modeChanged(33),
				succeedNeedReset(34)
				}
			MAX-ACCESS read-only
			STATUS current
			DESCRIPTION
				"Description."
			::= { hwMacApUpdateProgressEntry 1 }

		hwMacApUpdateProgress OBJECT-TYPE
			SYNTAX Integer32
			MAX-ACCESS read-only
			STATUS current
			DESCRIPTION
				"Description."
			::= { hwMacApUpdateProgressEntry 2 }

		hwMacApFlashProgress OBJECT-TYPE
			SYNTAX Integer32
			MAX-ACCESS read-only
			STATUS current
			DESCRIPTION
				"Description."
			::= { hwMacApUpdateProgressEntry 3 }
--   1.3.6.1.4.1.2011.6.139.7.3.5
-- 1.3.6.1.4.1.2011.6.139.7.3.5
		-- 1.3.6.1.4.1.2011.6.139.7.3.5
		hwSingleApUpdateTable OBJECT-TYPE
			SYNTAX SEQUENCE OF HwSingleApUpdateEntry
			MAX-ACCESS not-accessible
			STATUS current
			DESCRIPTION
				"Description."
			::= { hwApUpdateObjects 5 }


--   1.3.6.1.4.1.2011.6.139.7.3.5.1
-- 1.3.6.1.4.1.2011.6.139.7.3.5.1
		-- 1.3.6.1.4.1.2011.6.139.7.3.5.1
		hwSingleApUpdateEntry OBJECT-TYPE
			SYNTAX HwSingleApUpdateEntry
			MAX-ACCESS not-accessible
			STATUS current
			DESCRIPTION
				"Description."
			INDEX { hwApIndex }
			::= { hwSingleApUpdateTable 1 }


		HwSingleApUpdateEntry ::=
			SEQUENCE {
				hwSingleApUpdateAdminOper
					INTEGER,
				hwSingleApUpdatePercent
					Integer32,
				hwSingleApUpdateResult
					INTEGER,
				hwSingleApUpdateFilename
					OCTET STRING
			 }

--   1.3.6.1.4.1.2011.6.139.7.3.5.1.1
-- 1.3.6.1.4.1.2011.6.139.7.3.5.1.1
		-- 1.3.6.1.4.1.2011.6.139.7.3.5.1.1
		hwSingleApUpdateAdminOper OBJECT-TYPE
			SYNTAX INTEGER
				{
				start(1),
				reset(2),
				cancel(3)
				}
			MAX-ACCESS read-write
			STATUS current
			DESCRIPTION
				"Description."
			::= { hwSingleApUpdateEntry 1 }


--   1.3.6.1.4.1.2011.6.139.7.3.5.1.2
-- 1.3.6.1.4.1.2011.6.139.7.3.5.1.2
		-- 1.3.6.1.4.1.2011.6.139.7.3.5.1.2
		hwSingleApUpdatePercent OBJECT-TYPE
			SYNTAX Integer32
			MAX-ACCESS read-only
			STATUS current
			DESCRIPTION
				"Description."
			::= { hwSingleApUpdateEntry 2 }


--   1.3.6.1.4.1.2011.6.139.7.3.5.1.3
-- 1.3.6.1.4.1.2011.6.139.7.3.5.1.3
		-- 1.3.6.1.4.1.2011.6.139.7.3.5.1.3
		hwSingleApUpdateResult OBJECT-TYPE
			SYNTAX INTEGER
				{
				success(0),
				failed(1)
				}
			MAX-ACCESS read-only
			STATUS current
			DESCRIPTION
				"Description."
			::= { hwSingleApUpdateEntry 3 }


--  1.3.6.1.4.1.2011.6.139.7.3.5.1.4
		-- 1.3.6.1.4.1.2011.6.139.7.3.5.1.4
		hwSingleApUpdateFilename OBJECT-TYPE
			SYNTAX OCTET STRING
			MAX-ACCESS read-create
			STATUS current
			DESCRIPTION
				"Description."
			::= { hwSingleApUpdateEntry 4 }


		-- 1.3.6.1.4.1.2011.6.139.7.3.6
		hwMacSingleApUpdateTable OBJECT-TYPE
			SYNTAX SEQUENCE OF HwMacSingleApUpdateEntry
			MAX-ACCESS not-accessible
			STATUS current
			DESCRIPTION
				"Description."
			::= { hwApUpdateObjects 6 }


		-- 1.3.6.1.4.1.2011.6.139.7.3.6.1
		hwMacSingleApUpdateEntry OBJECT-TYPE
			SYNTAX HwMacSingleApUpdateEntry
			MAX-ACCESS not-accessible
			STATUS current
			DESCRIPTION
				"Description."
			INDEX { hwApMac }
			::= { hwMacSingleApUpdateTable 1 }


		HwMacSingleApUpdateEntry ::=
			SEQUENCE {
				hwMacSingleApUpdateAdminOper
					INTEGER,
				hwMacSingleApUpdatePercent
					Integer32,
				hwMacSingleApUpdateResult
					INTEGER,
				hwMacSingleApUpdateFilename
					OCTET STRING
			 }

		-- 1.3.6.1.4.1.2011.6.139.7.3.6.1.1
		hwMacSingleApUpdateAdminOper OBJECT-TYPE
			SYNTAX INTEGER
				{
				start(1),
				reset(2),
				cancel(3)
				}
			MAX-ACCESS read-write
			STATUS current
			DESCRIPTION
				"Description."
			::= { hwMacSingleApUpdateEntry 1 }


		-- 1.3.6.1.4.1.2011.6.139.7.3.6.1.2
		hwMacSingleApUpdatePercent OBJECT-TYPE
			SYNTAX Integer32
			MAX-ACCESS read-only
			STATUS current
			DESCRIPTION
				"Description."
			::= { hwMacSingleApUpdateEntry 2 }


		-- 1.3.6.1.4.1.2011.6.139.7.3.6.1.3
		hwMacSingleApUpdateResult OBJECT-TYPE
			SYNTAX INTEGER
				{
				success(0),
				failed(1)
				}
			MAX-ACCESS read-only
			STATUS current
			DESCRIPTION
				"Description."
			::= { hwMacSingleApUpdateEntry 3 }


		-- 1.3.6.1.4.1.2011.6.139.7.3.6.1.4
		hwMacSingleApUpdateFilename OBJECT-TYPE
			SYNTAX OCTET STRING
			MAX-ACCESS read-create
			STATUS current
			DESCRIPTION
				"Description."
			::= { hwMacSingleApUpdateEntry 4 }


		-- 1.3.6.1.4.1.2011.6.139.7.3.7
		hwApTypeRegionUpdateTable OBJECT-TYPE
			SYNTAX SEQUENCE OF HwApTypeRegionUpdateEntry
			MAX-ACCESS not-accessible
			STATUS current
			DESCRIPTION
				"Description."
			::= { hwApUpdateObjects 7 }


		-- 1.3.6.1.4.1.2011.6.139.7.3.7.1
		hwApTypeRegionUpdateEntry OBJECT-TYPE
			SYNTAX HwApTypeRegionUpdateEntry
			MAX-ACCESS not-accessible
			STATUS current
			DESCRIPTION
				"Description."
			INDEX { hwApType, hwApRegionIndex }
			::= { hwApTypeRegionUpdateTable 1 }


		HwApTypeRegionUpdateEntry ::=
			SEQUENCE {
				hwApTypeRegionUpdateFilename
					OCTET STRING,
				hwApTypeRegionUpdateResultMask
					OCTET STRING,
				hwApTypeRegionUpdateAdminOper
					INTEGER,
				hwApTypeRegionUpdatePercent
					Integer32,
				hwApTypeRegionUpdateRowStatus
					RowStatus,
				hwApTypeRegionUpdateResultInfo
					OCTET STRING
			 }

		-- 1.3.6.1.4.1.2011.6.139.7.3.7.1.1
		hwApTypeRegionUpdateFilename OBJECT-TYPE
			SYNTAX OCTET STRING
			MAX-ACCESS read-write
			STATUS current
			DESCRIPTION
				"Description."
			::= { hwApTypeRegionUpdateEntry 1 }


		-- 1.3.6.1.4.1.2011.6.139.7.3.7.1.2
		hwApTypeRegionUpdateResultMask OBJECT-TYPE
			SYNTAX OCTET STRING
			MAX-ACCESS read-only
			STATUS current
			DESCRIPTION
				"Description.The result of ap update.
				 	Every bit is used to describe the ap updated successfully or unsuccessfully.
				 	0 means success, and 1 means unsuccess.
				 	The value of this node is hexadecimal integer block.
				 	Each Byte describes 8 aps are updated successfully or unsuccessfully.
				 	For example, the first Byte describes ap 0~7 is updated successfully or unsuccessfully,
				 	and the second Byte describes ap 8~15 is updated successfully or unsuccessfully.
				 	Such as, if only ap 0,4,5,6,7,9 is updated unsuccessfully, the binary number is 11110001 and 00000010,
				 	the hexadecimal number is 0xF1 and 0x2, so the first Byte of this node is 0xF1,
				 	and the second Byte is 0x2.
				"
			::= { hwApTypeRegionUpdateEntry 2 }


		-- 1.3.6.1.4.1.2011.6.139.7.3.7.1.3
		hwApTypeRegionUpdateAdminOper OBJECT-TYPE
			SYNTAX INTEGER
				{
				start(1),
				reset(2),
				cancel(3)
				}
			MAX-ACCESS read-write
			STATUS current
			DESCRIPTION
				"Description."
			::= { hwApTypeRegionUpdateEntry 3 }


		-- 1.3.6.1.4.1.2011.6.139.7.3.7.1.4
		hwApTypeRegionUpdatePercent OBJECT-TYPE
			SYNTAX Integer32
			MAX-ACCESS read-only
			STATUS current
			DESCRIPTION
				"Description."
			::= { hwApTypeRegionUpdateEntry 4 }


		-- 1.3.6.1.4.1.2011.6.139.7.3.7.1.5
		hwApTypeRegionUpdateRowStatus OBJECT-TYPE
			SYNTAX RowStatus
			MAX-ACCESS read-create
			STATUS current
			DESCRIPTION
				"Description."
			::= { hwApTypeRegionUpdateEntry 5 }


		-- 1.3.6.1.4.1.2011.6.139.7.3.7.1.6
		hwApTypeRegionUpdateResultInfo OBJECT-TYPE
			SYNTAX OCTET STRING
			MAX-ACCESS read-only
			STATUS current
			DESCRIPTION
				"Description."
			::= { hwApTypeRegionUpdateEntry 6 }


		-- 1.3.6.1.4.1.2011.6.139.7.4
		hwWlanUpdateObjects OBJECT IDENTIFIER ::= { hwWlanUpdate 4 }


		-- 1.3.6.1.4.1.2011.6.139.7.5
		hwWlanUpdateConformance OBJECT IDENTIFIER ::= { hwWlanUpdate 5 }


		-- 1.3.6.1.4.1.2011.6.139.7.5.1
		hwWlanUpdateCompliances OBJECT IDENTIFIER ::= { hwWlanUpdateConformance 1 }


		-- 1.3.6.1.4.1.2011.6.139.7.5.1.1
		hwWlanUpdateCompliance MODULE-COMPLIANCE
			STATUS current
			DESCRIPTION
				"Description."
			MODULE -- this module
				MANDATORY-GROUPS { hwWlanUpdateNotificationsGroup, hwWlanUpdateNotifyObjectsGroup, hwApUpdateObjectsGroup }
			::= { hwWlanUpdateCompliances 1 }

		-- 1.3.6.1.4.1.2011.6.139.7.5.2
		hwWlanUpdateObjectGroups OBJECT IDENTIFIER ::= { hwWlanUpdateConformance 2 }


		-- 1.3.6.1.4.1.2011.6.139.7.5.2.1
		hwWlanUpdateNotificationsGroup NOTIFICATION-GROUP
			NOTIFICATIONS { hwApUpdateBeginNotify, hwApUpdateResultNotify,hwApUpdateUbootNotMatchNotify  }
			STATUS current
			DESCRIPTION
				"Description."
			::= { hwWlanUpdateObjectGroups 1 }


		-- 1.3.6.1.4.1.2011.6.139.7.5.2.2
		hwWlanUpdateNotifyObjectsGroup OBJECT-GROUP
			OBJECTS { hwApUpdateResult, hwApUpdateTime, hwApUpdateByFileName, hwApUpdateNextOper,hwApUpdateResultStatus}
			STATUS current
			DESCRIPTION
				"Description."
			::= { hwWlanUpdateObjectGroups 2 }


		-- 1.3.6.1.4.1.2011.6.139.7.5.2.3
		hwApUpdateObjectsGroup OBJECT-GROUP
			OBJECTS { hwApUpdateSFTPIPAddress, hwApUpdateSFTPUsername, hwApUpdateSFTPPassword, hwApUpdateFTPMaxConnectNum, hwApUpdateFTPIPv6Address,
				hwApUpdateSFTPIPv6Address, hwApUpdateSFTPMaxConnectNum, hwApUpdateFilename, hwApUpdateResultMask, hwApUpdateAdminOper,
				hwApUpdatePercent, hwApUpdateRowStatus, hwApUpdateResultInfo, hwApFlashProgress, hwMacApFlashProgress,
				hwApUpdateApIdSetMask, hwApUpdateResult, hwApUpdateTime, hwApUpdateByFileName, hwApUpdateNextOper,
				hwApUpdateFTPIPAddress, hwApUpdateFTPUsername, hwApUpdateFTPPassword, hwApUpdateMode, hwApUpdateProgressStatus,
				hwApUpdateProgress, hwMacApUpdateProgressStatus, hwMacApUpdateProgress, hwSingleApUpdateAdminOper, hwSingleApUpdatePercent,
				hwSingleApUpdateResult, hwSingleApUpdateFilename, hwMacSingleApUpdateAdminOper, hwMacSingleApUpdatePercent, hwMacSingleApUpdateResult,
				hwMacSingleApUpdateFilename, hwApTypeRegionUpdateFilename, hwApTypeRegionUpdateResultMask, hwApTypeRegionUpdateAdminOper, hwApTypeRegionUpdatePercent,
				hwApTypeRegionUpdateRowStatus, hwApTypeRegionUpdateResultInfo }
			STATUS current
			DESCRIPTION
				"Description."
			::= { hwWlanUpdateObjectGroups 3 }



	END

--
-- HUAWEI-WLAN-UPDATE-MIB.my
--
